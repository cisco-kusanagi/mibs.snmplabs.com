-- *********************************************************************
-- CISCO-UNIFIED-COMPUTING-VNIC-MIB.my
-- 
-- MIB representation of the Cisco Unified Computing System
-- VNIC management information model package
-- 
-- Created January 2016 by Charles Bullis
-- 
-- Copyright (c) 2005-2016 Cisco Systems, Inc. All rights reserved.
-- 
-- *********************************************************************

CISCO-UNIFIED-COMPUTING-VNIC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsAdaptorPurpose,
    CucsConditionRemoteInvRslt,
    CucsDpsecForgedTransmit,
    CucsFabricHostPortId,
    CucsFabricVlanSharingType,
    CucsFsmCompletion,
    CucsFsmFlags,
    CucsFsmFsmStageStatus,
    CucsLsConfigState,
    CucsLsOwner,
    CucsNetworkSwitchId,
    CucsNwctrlAdminState,
    CucsNwctrlLinkFailAction,
    CucsNwctrlLldpAdminStateBitmask,
    CucsNwctrlRegistrationMode,
    CucsPolicyPolicyOwner,
    CucsVmMgmtPlane,
    CucsVnicAEtherIfType,
    CucsVnicAFcIfSwitchId,
    CucsVnicAFcIfType,
    CucsVnicAIpcIfType,
    CucsVnicAScsiIfType,
    CucsVnicCdnSource,
    CucsVnicConfigIssues,
    CucsVnicConnectionOwner,
    CucsVnicConnectionType,
    CucsVnicDefBehType,
    CucsVnicDefaultAction,
    CucsVnicDynamicConReqProtection,
    CucsVnicEtherBaseIfSwitchId,
    CucsVnicEtherBaseSwitchId,
    CucsVnicEtherType,
    CucsVnicExternalMgmtIPMode,
    CucsVnicFcBasePersBind,
    CucsVnicFcBaseType,
    CucsVnicFcNodeOwner,
    CucsVnicHostNwIOPerfPref,
    CucsVnicIPv4DnsPref,
    CucsVnicIScsiIfDefType,
    CucsVnicIScsiNodeOwner,
    CucsVnicIfOperState,
    CucsVnicInstantiation,
    CucsVnicIpPoolType,
    CucsVnicIpcType,
    CucsVnicLanConnTemplSwitchId,
    CucsVnicLunId,
    CucsVnicPortProfileType,
    CucsVnicProfileConfigQualifier,
    CucsVnicProfileSetFsmCurrentFsm,
    CucsVnicProfileSetFsmStageName,
    CucsVnicProfileSetFsmTaskItem,
    CucsVnicSanConnTemplTarget,
    CucsVnicScsiType,
    CucsVnicTemplateTarget,
    CucsVnicTemplateType,
    CucsVnicVhbaBehPolicyType,
    CucsVnicVirtualizationPreferenceType,
    CucsVnicVlanGroupUpdate,
    CucsVnicVnicBehPolicyType,
    CucsVnicVnicBootDev,
    CucsVnicVnicOperHostPort
        FROM CISCO-UNIFIED-COMPUTING-TC-MIB;

cucsVnicObjects MODULE-IDENTITY
    LAST-UPDATED    "201601180000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        VNIC management information model package"
    ::= { ciscoUnifiedComputingMIBObjects 53 }

cucsVnicBootIpPolicyTable OBJECT-TYPE
    SYNTAX           SEQUENCE OF CucsVnicBootIpPolicyEntry
    MAX-ACCESS       not-accessible
    STATUS           current
    DESCRIPTION
        "Cisco UCS vnic:BootIpPolicy managed object table"
    ::= { cucsVnicObjects 35 }

cucsVnicBootIpPolicyEntry OBJECT-TYPE
    SYNTAX           CucsVnicBootIpPolicyEntry
    MAX-ACCESS       not-accessible
    STATUS           current
    DESCRIPTION
        "Entry for the cucsVnicBootIpPolicyTable table."
    INDEX { cucsVnicBootIpPolicyInstanceId }
    ::= { cucsVnicBootIpPolicyTable 1 }

CucsVnicBootIpPolicyEntry ::= SEQUENCE {
    cucsVnicBootIpPolicyInstanceId                                   CucsManagedObjectId,
    cucsVnicBootIpPolicyDn                                           CucsManagedObjectDn,
    cucsVnicBootIpPolicyRn                                           SnmpAdminString,
    cucsVnicBootIpPolicyDescr                                        SnmpAdminString,
    cucsVnicBootIpPolicyIntId                                        SnmpAdminString,
    cucsVnicBootIpPolicyName                                         SnmpAdminString,
    cucsVnicBootIpPolicyPoolName                                     SnmpAdminString,
    cucsVnicBootIpPolicyPolicyLevel                                  Gauge32,
    cucsVnicBootIpPolicyPolicyOwner                                  CucsPolicyPolicyOwner
}

cucsVnicBootIpPolicyInstanceId OBJECT-TYPE
    SYNTAX       CucsManagedObjectId
    MAX-ACCESS   not-accessible
    STATUS       current
    DESCRIPTION
        "Instance identifier of the managed object."
    ::= { cucsVnicBootIpPolicyEntry 1 }

cucsVnicBootIpPolicyDn OBJECT-TYPE
    SYNTAX       CucsManagedObjectDn
    MAX-ACCESS   read-only
    STATUS       current
    DESCRIPTION
        "Cisco UCS vnic:BootIpPolicy:dn managed object property"
    ::= { cucsVnicBootIpPolicyEntry 2 }

cucsVnicBootIpPolicyRn OBJECT-TYPE
    SYNTAX       SnmpAdminString
    MAX-ACCESS   read-only
    STATUS       current
    DESCRIPTION
        "Cisco UCS vnic:BootIpPolicy:rn managed object property"
    ::= { cucsVnicBootIpPolicyEntry 3 }

cucsVnicBootIpPolicyDescr OBJECT-TYPE
    SYNTAX       SnmpAdminString
    MAX-ACCESS   read-only
    STATUS       current
    DESCRIPTION
        "Cisco UCS vnic:BootIpPolicy:descr managed object property"
    ::= { cucsVnicBootIpPolicyEntry 4 }

cucsVnicBootIpPolicyIntId OBJECT-TYPE
    SYNTAX       SnmpAdminString
    MAX-ACCESS   read-only
    STATUS       current
    DESCRIPTION
        "Cisco UCS vnic:BootIpPolicy:intId managed object property"
    ::= { cucsVnicBootIpPolicyEntry 5 }

cucsVnicBootIpPolicyName OBJECT-TYPE
    SYNTAX       SnmpAdminString
    MAX-ACCESS   read-only
    STATUS       current
    DESCRIPTION
        "Cisco UCS vnic:BootIpPolicy:name managed object property"
    ::= { cucsVnicBootIpPolicyEntry 6 }

cucsVnicBootIpPolicyPoolName OBJECT-TYPE
    SYNTAX       SnmpAdminString
    MAX-ACCESS   read-only
    STATUS       current
    DESCRIPTION
        "Cisco UCS vnic:BootIpPolicy:poolName managed object property"
    ::= { cucsVnicBootIpPolicyEntry 7 }

cucsVnicBootIpPolicyPolicyLevel OBJECT-TYPE
    SYNTAX       Gauge32
    MAX-ACCESS   read-only
    STATUS       current
    DESCRIPTION
        "Cisco UCS vnic:BootIpPolicy:policyLevel managed object property"
    ::= { cucsVnicBootIpPolicyEntry 8 }

cucsVnicBootIpPolicyPolicyOwner OBJECT-TYPE
    SYNTAX       CucsPolicyPolicyOwner
    MAX-ACCESS   read-only
    STATUS       current
    DESCRIPTION
        "Cisco UCS vnic:BootIpPolicy:policyOwner managed object property"
    ::= { cucsVnicBootIpPolicyEntry 9 }

cucsVnicBootTargetTable OBJECT-TYPE
    SYNTAX           SEQUENCE OF CucsVnicBootTargetEntry
    MAX-ACCESS       not-accessible
    STATUS           current
    DESCRIPTION
        "Cisco UCS vnic:BootTarget managed object table"
    ::= { cucsVnicObjects 1 }

cucsVnicBootTargetEntry OBJECT-TYPE
    SYNTAX           CucsVnicBootTargetEntry
    MAX-ACCESS       not-accessible
    STATUS           current
    DESCRIPTION
        "Entry for the cucsVnicBootTargetTable table."
    INDEX { cucsVnicBootTargetInstanceId }
    ::= { cucsVnicBootTargetTable 1 }

CucsVnicBootTargetEntry ::= SEQUENCE {
    cucsVnicBootTargetInstanceId                                     CucsManagedObjectId,
    cucsVnicBootTargetDn                                             CucsManagedObjectDn,
    cucsVnicBootTargetRn                                             SnmpAdminString,
    cucsVnicBootTargetLun                                            SnmpAdminString,
    cucsVnicBootTargetWwn                                            Unsigned64
}

cucsVnicBootTargetInstanceId OBJECT-TYPE
    SYNTAX       CucsManagedObjectId
    MAX-ACCESS   not-accessible
    STATUS       current
    DESCRIPTION
        "Instance identifier of the managed object."
    ::= { cucsVnicBootTargetEntry 1 }

cucsVnicBootTargetDn OBJECT-TYPE
    SYNTAX       CucsManagedObjectDn
    MAX-ACCESS   read-only
    STATUS       current
    DESCRIPTION
        "Cisco UCS vnic:BootTarget:dn managed object property"
    ::= { cucsVnicBootTargetEntry 2 }

cucsVnicBootTargetRn OBJECT-TYPE
    SYNTAX       SnmpAdminString
    MAX-ACCESS   read-only
    STATUS       current
    DESCRIPTION
        "Cisco UCS vnic:BootTarget:rn managed object property"
    ::= { cucsVnicBootTargetEntry 3 }

cucsVnicBootTargetLun OBJECT-TYPE
    SYNTAX       SnmpAdminString
    MAX-ACCESS   read-only
    STATUS       current
    DESCRIPTION
        "Cisco UCS vnic:BootTarget:lun managed object property"
    ::= { cucsVnicBootTargetEntry 4 }

cucsVnicBootTargetWwn OBJECT-TYPE
    SYNTAX       Unsigned64
    MAX-ACCESS   read-only
    STATUS       current
    DESCRIPTION
        "Cisco UCS vnic:BootTarget:wwn managed object property"
    ::= { cucsVnicBootTargetEntry 5 }

cucsVnicConnDefTable OBJECT-TYPE
    SYNTAX           SEQUENCE OF CucsVnicConnDefEntry
    MAX-ACCESS       not-accessible
    STATUS           current
    DESCRIPTION
        "Cisco UCS vnic:ConnDef managed object table"
    ::= { cucsVnicObjects 46 }

cucsVnicConnDefEntry OBJECT-TYPE
    SYNTAX           CucsVnicConnDefEntry
    MAX-ACCESS       not-accessible
    STATUS           current
    DESCRIPTION
        "Entry for the cucsVnicConnDefTable table."
    INDEX { cucsVnicConnDefInstanceId }
    ::= { cucsVnicConnDefTable 1 }

CucsVnicConnDefEntry ::= SEQUENCE {
    cucsVnicConnDefInstanceId                                        CucsManagedObjectId,
    cucsVnicConnDefDn                                                CucsManagedObjectDn,
    cucsVnicConnDefRn                                                SnmpAdminString,
    cucsVnicConnDefFltAggr                                           Unsigned64,
    cucsVnicConnDefLanConnPolicyName                                 SnmpAdminString,
    cucsVnicConnDefOperLanConnPolicyName                             SnmpAdminString,
    cucsVnicConnDefOperSanConnPolicyName                             SnmpAdminString,
    cucsVnicConnDefSanConnPolicyName                                 SnmpAdminString,
    cucsVnicConnDefPropAcl                                           Unsigned64
}

cucsVnicConnDefInstanceId OBJECT-TYPE
    SYNTAX       CucsManagedObjectId
    MAX-ACCESS   not-accessible
    STATUS       current
    DESCRIPTION
        "Instance identifier of the managed object."
    ::= { cucsVnicConnDefEntry 1 }

cucsVnicConnDefDn OBJECT-TYPE
    SYNTAX       CucsManagedObjectDn
    MAX-ACCESS   read-only
    STATUS       current
    DESCRIPTION
        "Cisco UCS vnic:ConnDef:dn managed object property"
    ::= { cucsVnicConnDefEntry 2 }

cucsVnicConnDefRn OBJECT-TYPE
    SYNTAX       SnmpAdminString
    MAX-ACCESS   read-only
    STATUS       current
    DESCRIPTION
        "Cisco UCS vnic:ConnDef:rn managed object property"
    ::= { cucsVnicConnDefEntry 3 }

cucsVnicConnDefFltAggr OBJECT-TYPE
    SYNTAX       Unsigned64
    MAX-ACCESS   read-only
    STATUS       current
    DESCRIPTION
        "Cisco UCS vnic:ConnDef:fltAggr managed object property"
    ::= { cucsVnicConnDefEntry 4 }

cucsVnicConnDefLanConnPolicyName OBJECT-TYPE
    SYNTAX       SnmpAdminString
    MAX-ACCESS   read-only
    STATUS       current
    DESCRIPTION
        "Cisco UCS vnic:ConnDef:lanConnPolicyName managed object property"
    ::= { cucsVnicConnDefEntry 5 }

cucsVnicConnDefOperLanConnPolicyName OBJECT-TYPE
    SYNTAX       SnmpAdminString
    MAX-ACCESS   read-only
    STATUS       current
    DESCRIPTION
        "Cisco UCS vnic:ConnDef:operLanConnPolicyName managed
        object property"
    ::= { cucsVnicConnDefEntry 6 }

cucsVnicConnDefOperSanConnPolicyName OBJECT-TYPE
    SYNTAX       SnmpAdminString
    MAX-ACCESS   read-only
    STATUS       current
    DESCRIPTION
        "Cisco UCS vnic:ConnDef:operSanConnPolicyName managed
        object property"
    ::= { cucsVnicConnDefEntry 7 }

cucsVnicConnDefSanConnPolicyName OBJECT-TYPE
    SYNTAX       SnmpAdminString
    MAX-ACCESS   read-only
    STATUS       current
    DESCRIPTION
        "Cisco UCS vnic:ConnDef:sanConnPolicyName managed object property"
    ::= { cucsVnicConnDefEntry 8 }

cucsVnicConnDefPropAcl OBJECT-TYPE
    SYNTAX       Unsigned64
    MAX-ACCESS   read-only
    STATUS       current
    DESCRIPTION
        "Cisco UCS vnic:ConnDef:propAcl managed object property"
    ::= { cucsVnicConnDefEntry 9 }

cucsVnicDefBehTable OBJECT-TYPE
    SYNTAX           SEQUENCE OF CucsVnicDefBehEntry
    MAX-ACCESS       not-accessible
    STATUS           current
    DESCRIPTION
        "Cisco UCS vnic:DefBeh managed object table"
    ::= { cucsVnicObjects 2 }

cucsVnicDefBehEntry OBJECT-TYPE
    SYNTAX           CucsVnicDefBehEntry
    MAX-ACCESS       not-accessible
    STATUS           current
    DESCRIPTION
        "Entry for the cucsVnicDefBehTable table."
    INDEX { cucsVnicDefBehInstanceId }
    ::= { cucsVnicDefBehTable 1 }

CucsVnicDefBehEntry ::= SEQUENCE {
    cucsVnicDefBehInstanceId                                         CucsManagedObjectId,
    cucsVnicDefBehDn                                                 CucsManagedObjectDn,
    cucsVnicDefBehRn                                                 SnmpAdminString,
    cucsVnicDefBehAction                                             CucsVnicDefaultAction,
    cucsVnicDefBehNwTemplName                                        SnmpAdminString,
    cucsVnicDefBehType                                               CucsVnicDefBehType,
    cucsVnicDefBehDescr                                              SnmpAdminString,
    cucsVnicDefBehIntId                                              SnmpAdminString,
    cucsVnicDefBehName                                               SnmpAdminString,
    cucsVnicDefBehPolicyLevel                                        Gauge32,
    cucsVnicDefBehPolicyOwner                                        CucsPolicyPolicyOwner
}

cucsVnicDefBehInstanceId OBJECT-TYPE
    SYNTAX       CucsManagedObjectId
    MAX-ACCESS   not-accessible
    STATUS       current
    DESCRIPTION
        "Instance identifier of the managed object."
    ::= { cucsVnicDefBehEntry 1 }

cucsVnicDefBehDn OBJECT-TYPE
    SYNTAX       CucsManagedObjectDn
    MAX-ACCESS   read-only
    STATUS       current
    DESCRIPTION
        "Cisco UCS vnic:DefBeh:dn managed object property"
    ::= { cucsVnicDefBehEntry 2 }

cucsVnicDefBehRn OBJECT-TYPE
    SYNTAX       SnmpAdminString
    MAX-ACCESS   read-only
    STATUS       current
    DESCRIPTION
        "Cisco UCS vnic:DefBeh:rn managed object property"
    ::= { cucsVnicDefBehEntry 3 }

cucsVnicDefBehAction OBJECT-TYPE
    SYNTAX       CucsVnicDefaultAction
    MAX-ACCESS   read-only
    STATUS       current
    DESCRIPTION
        "Cisco UCS vnic:DefBeh:action managed object property"
    ::= { cucsVnicDefBehEntry 4 }

cucsVnicDefBehNwTemplName OBJECT-TYPE
    SYNTAX       SnmpAdminString
    MAX-ACCESS   read-only
    STATUS       current
    DESCRIPTION
        "Cisco UCS vnic:DefBeh:nwTemplName managed object property"
    ::= { cucsVnicDefBehEntry 5 }

cucsVnicDefBehType OBJECT-TYPE
    SYNTAX       CucsVnicDefBehType
    MAX-ACCESS   read-only
    STATUS       current
    DESCRIPTION
        "Cisco UCS vnic:DefBeh:type managed object property"
    ::= { cucsVnicDefBehEntry 6 }

cucsVnicDefBehDescr OBJECT-TYPE
    SYNTAX       SnmpAdminString
    MAX-ACCESS   read-only
    STATUS       current
    DESCRIPTION
        "Cisco UCS vnic:DefBeh:descr managed object property"
    ::= { cucsVnicDefBehEntry 7 }

cucsVnicDefBehIntId OBJECT-TYPE
    SYNTAX       SnmpAdminString
    MAX-ACCESS   read-only
    STATUS       current
    DESCRIPTION
        "Cisco UCS vnic:DefBeh:intId managed object property"
    ::= { cucsVnicDefBehEntry 8 }

cucsVnicDefBehName OBJECT-TYPE
    SYNTAX       SnmpAdminString
    MAX-ACCESS   read-only
    STATUS       current
    DESCRIPTION
        "Cisco UCS vnic:DefBeh:name managed object property"
    ::= { cucsVnicDefBehEntry 9 }

cucsVnicDefBehPolicyLevel OBJECT-TYPE
    SYNTAX       Gauge32
    MAX-ACCESS   read-only
    STATUS       current
    DESCRIPTION
        "Cisco UCS vnic:DefBeh:policyLevel managed object property"
    ::= { cucsVnicDefBehEntry 10 }

cucsVnicDefBehPolicyOwner OBJECT-TYPE
    SYNTAX       CucsPolicyPolicyOwner
    MAX-ACCESS   read-only
    STATUS       current
    DESCRIPTION
        "Cisco UCS vnic:DefBeh:policyOwner managed object property"
    ::= { cucsVnicDefBehEntry 11 }

cucsVnicDynamicConTable OBJECT-TYPE
    SYNTAX           SEQUENCE OF CucsVnicDynamicConEntry
    MAX-ACCESS       not-accessible
    STATUS           current
    DESCRIPTION
        "Cisco UCS vnic:DynamicCon managed object table"
    ::= { cucsVnicObjects 3 }

cucsVnicDynamicConEntry OBJECT-TYPE
    SYNTAX           CucsVnicDynamicConEntry
    MAX-ACCESS       not-accessible
    STATUS           current
    DESCRIPTION
        "Entry for the cucsVnicDynamicConTable table."
    INDEX { cucsVnicDynamicConInstanceId }
    ::= { cucsVnicDynamicConTable 1 }

CucsVnicDynamicConEntry ::= SEQUENCE {
    cucsVnicDynamicConInstanceId                                     CucsManagedObjectId,
    cucsVnicDynamicConDn                                             CucsManagedObjectDn,
    cucsVnicDynamicConRn                                             SnmpAdminString,
    cucsVnicDynamicConAdaptorProfileName                             SnmpAdminString,
    cucsVnicDynamicConDescr                                          SnmpAdminString,
    cucsVnicDynamicConDynamicEth                                     Gauge32,
    cucsVnicDynamicConIntId                                          SnmpAdminString,
    cucsVnicDynamicConMtu                                            Gauge32,
    cucsVnicDynamicConName                                           SnmpAdminString,
    cucsVnicDynamicConNamingPrefix                                   SnmpAdminString,
    cucsVnicDynamicConProtection                                     CucsVnicDynamicConReqProtection,
    cucsVnicDynamicConPolicyLevel                                    Gauge32,
    cucsVnicDynamicConPolicyOwner                                    CucsPolicyPolicyOwner
}

cucsVnicDynamicConInstanceId OBJECT-TYPE
    SYNTAX       CucsManagedObjectId
    MAX-ACCESS   not-accessible
    STATUS       current
    DESCRIPTION
        "Instance identifier of the managed object."
    ::= { cucsVnicDynamicConEntry 1 }

cucsVnicDynamicConDn OBJECT-TYPE
    SYNTAX       CucsManagedObjectDn
    MAX-ACCESS   read-only
    STATUS       current
    DESCRIPTION
        "Cisco UCS vnic:DynamicCon:dn managed object property"
    ::= { cucsVnicDynamicConEntry 2 }

cucsVnicDynamicConRn OBJECT-TYPE
    SYNTAX       SnmpAdminString
    MAX-ACCESS   read-only
    STATUS       current
    DESCRIPTION
        "Cisco UCS vnic:DynamicCon:rn managed object property"
    ::= { cucsVnicDynamicConEntry 3 }

cucsVnicDynamicConAdaptorProfileName OBJECT-TYPE
    SYNTAX       SnmpAdminString
    MAX-ACCESS   read-only
    STATUS       current
    DESCRIPTION
        "Cisco UCS vnic:DynamicCon:adaptorProfileName managed
        object property"
    ::= { cucsVnicDynamicConEntry 4 }

cucsVnicDynamicConDescr OBJECT-TYPE
    SYNTAX       SnmpAdminString
    MAX-ACCESS   read-only
    STATUS       current
    DESCRIPTION
        "Cisco UCS vnic:DynamicCon:descr managed object property"
    ::= { cucsVnicDynamicConEntry 5 }

cucsVnicDynamicConDynamicEth OBJECT-TYPE
    SYNTAX       Gauge32
    MAX-ACCESS   read-only
    STATUS       current
    DESCRIPTION
        "Cisco UCS vnic:DynamicCon:dynamicEth managed object property"
    ::= { cucsVnicDynamicConEntry 6 }

cucsVnicDynamicConIntId OBJECT-TYPE
    SYNTAX       SnmpAdminString
    MAX-ACCESS   read-only
    STATUS       current
    DESCRIPTION
        "Cisco UCS vnic:DynamicCon:intId managed object property"
    ::= { cucsVnicDynamicConEntry 7 }

cucsVnicDynamicConMtu OBJECT-TYPE
    SYNTAX       Gauge32
    MAX-ACCESS   read-only
    STATUS       current
    DESCRIPTION
        "Cisco UCS vnic:DynamicCon:mtu managed object property"
    ::= { cucsVnicDynamicConEntry 8 }

cucsVnicDynamicConName OBJECT-TYPE
    SYNTAX       SnmpAdminString
    MAX-ACCESS   read-only
    STATUS       current
    DESCRIPTION
        "Cisco UCS vnic:DynamicCon:name managed object property"
    ::= { cucsVnicDynamicConEntry 9 }

cucsVnicDynamicConNamingPrefix OBJECT-TYPE
    SYNTAX       SnmpAdminString
    MAX-ACCESS   read-only
    STATUS       current
    DESCRIPTION
        "Cisco UCS vnic:DynamicCon:namingPrefix managed object property"
    ::= { cucsVnicDynamicConEntry 10 }

cucsVnicDynamicConProtection OBJECT-TYPE
    SYNTAX       CucsVnicDynamicConReqProtection
    MAX-ACCESS   read-only
    STATUS       current
    DESCRIPTION
        "Cisco UCS vnic:DynamicCon:protection managed object property"
    ::= { cucsVnicDynamicConEntry 11 }

cucsVnicDynamicConPolicyLevel OBJECT-TYPE
    SYNTAX       Gauge32
    MAX-ACCESS   read-only
    STATUS       current
    DESCRIPTION
        "Cisco UCS vnic:DynamicCon:policyLevel managed object property"
    ::= { cucsVnicDynamicConEntry 12 }

cucsVnicDynamicConPolicyOwner OBJECT-TYPE
    SYNTAX       CucsPolicyPolicyOwner
    MAX-ACCESS   read-only
    STATUS       current
    DESCRIPTION
        "Cisco UCS vnic:DynamicCon:policyOwner managed object property"
    ::= { cucsVnicDynamicConEntry 13 }

cucsVnicDynamicConPolicyTable OBJECT-TYPE
    SYNTAX           SEQUENCE OF CucsVnicDynamicConPolicyEntry
    MAX-ACCESS       not-accessible
    STATUS           current
    DESCRIPTION
        "Cisco UCS vnic:DynamicConPolicy managed object table"
    ::= { cucsVnicObjects 4 }

cucsVnicDynamicConPolicyEntry OBJECT-TYPE
    SYNTAX           CucsVnicDynamicConPolicyEntry
    MAX-ACCESS       not-accessible
    STATUS           current
    DESCRIPTION
        "Entry for the cucsVnicDynamicConPolicyTable table."
    INDEX { cucsVnicDynamicConPolicyInstanceId }
    ::= { cucsVnicDynamicConPolicyTable 1 }

CucsVnicDynamicConPolicyEntry ::= SEQUENCE {
    cucsVnicDynamicConPolicyInstanceId                               CucsManagedObjectId,
    cucsVnicDynamicConPolicyDn                                       CucsManagedObjectDn,
    cucsVnicDynamicConPolicyRn                                       SnmpAdminString,
    cucsVnicDynamicConPolicyAdaptorProfileName                       SnmpAdminString,
    cucsVnicDynamicConPolicyDescr                                    SnmpAdminString,
    cucsVnicDynamicConPolicyDynamicEth                               Gauge32,
    cucsVnicDynamicConPolicyIntId                                    SnmpAdminString,
    cucsVnicDynamicConPolicyMtu                                      Gauge32,
    cucsVnicDynamicConPolicyName                                     SnmpAdminString,
    cucsVnicDynamicConPolicyNamingPrefix                             SnmpAdminString,
    cucsVnicDynamicConPolicyProtection                               CucsVnicDynamicConReqProtection,
    cucsVnicDynamicConPolicyPolicyLevel                              Gauge32,
    cucsVnicDynamicConPolicyPolicyOwner                              CucsPolicyPolicyOwner
}

cucsVnicDynamicConPolicyInstanceId OBJECT-TYPE
    SYNTAX       CucsManagedObjectId
    MAX-ACCESS   not-accessible
    STATUS       current
    DESCRIPTION
        "Instance identifier of the managed object."
    ::= { cucsVnicDynamicConPolicyEntry 1 }

cucsVnicDynamicConPolicyDn OBJECT-TYPE
    SYNTAX       CucsManagedObjectDn
    MAX-ACCESS   read-only
    STATUS       current
    DESCRIPTION
        "Cisco UCS vnic:DynamicConPolicy:dn managed object property"
    ::= { cucsVnicDynamicConPolicyEntry 2 }

cucsVnicDynamicConPolicyRn OBJECT-TYPE
    SYNTAX       SnmpAdminString
    MAX-ACCESS   read-only
    STATUS       current
    DESCRIPTION
        "Cisco UCS vnic:DynamicConPolicy:rn managed object property"
    ::= { cucsVnicDynamicConPolicyEntry 3 }

cucsVnicDynamicConPolicyAdaptorProfileName OBJECT-TYPE
    SYNTAX       SnmpAdminString
    MAX-ACCESS   read-only
    STATUS       current
    DESCRIPTION
        "Cisco UCS vnic:DynamicConPolicy:adaptorProfileName
        managed object property"
    ::= { cucsVnicDynamicConPolicyEntry 4 }

cucsVnicDynamicConPolicyDescr OBJECT-TYPE
    SYNTAX       SnmpAdminString
    MAX-ACCESS   read-only
    STATUS       current
    DESCRIPTION
        "Cisco UCS vnic:DynamicConPolicy:descr managed object property"
    ::= { cucsVnicDynamicConPolicyEntry 5 }

cucsVnicDynamicConPolicyDynamicEth OBJECT-TYPE
    SYNTAX       Gauge32
    MAX-ACCESS   read-only
    STATUS       current
    DESCRIPTION
        "Cisco UCS vnic:DynamicConPolicy:dynamicEth managed
        object property"
    ::= { cucsVnicDynamicConPolicyEntry 6 }

cucsVnicDynamicConPolicyIntId OBJECT-TYPE
    SYNTAX       SnmpAdminString
    MAX-ACCESS   read-only
    STATUS       current
    DESCRIPTION
        "Cisco UCS vnic:DynamicConPolicy:intId managed object property"
    ::= { cucsVnicDynamicConPolicyEntry 7 }

cucsVnicDynamicConPolicyMtu OBJECT-TYPE
    SYNTAX       Gauge32
    MAX-ACCESS   read-only
    STATUS       current
    DESCRIPTION
        "Cisco UCS vnic:DynamicConPolicy:mtu managed object property"
    ::= { cucsVnicDynamicConPolicyEntry 8 }

cucsVnicDynamicConPolicyName OBJECT-TYPE
    SYNTAX       SnmpAdminString
    MAX-ACCESS   read-only
    STATUS       current
    DESCRIPTION
        "Cisco UCS vnic:DynamicConPolicy:name managed object property"
    ::= { cucsVnicDynamicConPolicyEntry 9 }

cucsVnicDynamicConPolicyNamingPrefix OBJECT-TYPE
    SYNTAX       SnmpAdminString
    MAX-ACCESS   read-only
    STATUS       current
    DESCRIPTION
        "Cisco UCS vnic:DynamicConPolicy:namingPrefix managed
        object property"
    ::= { cucsVnicDynamicConPolicyEntry 10 }

cucsVnicDynamicConPolicyProtection OBJECT-TYPE
    SYNTAX       CucsVnicDynamicConReqProtection
    MAX-ACCESS   read-only
    STATUS       current
    DESCRIPTION
        "Cisco UCS vnic:DynamicConPolicy:protection managed
        object property"
    ::= { cucsVnicDynamicConPolicyEntry 11 }

cucsVnicDynamicConPolicyPolicyLevel OBJECT-TYPE
    SYNTAX       Gauge32
    MAX-ACCESS   read-only
    STATUS       current
    DESCRIPTION
        "Cisco UCS vnic:DynamicConPolicy:policyLevel managed
        object property"
    ::= { cucsVnicDynamicConPolicyEntry 12 }

cucsVnicDynamicConPolicyPolicyOwner OBJECT-TYPE
    SYNTAX       CucsPolicyPolicyOwner
    MAX-ACCESS   read-only
    STATUS       current
    DESCRIPTION
        "Cisco UCS vnic:DynamicConPolicy:policyOwner managed
        object property"
    ::= { cucsVnicDynamicConPolicyEntry 13 }

cucsVnicDynamicConPolicyRefTable OBJECT-TYPE
    SYNTAX           SEQUENCE OF CucsVnicDynamicConPolicyRefEntry
    MAX-ACCESS       not-accessible
    STATUS           current
    DESCRIPTION
        "Cisco UCS vnic:DynamicConPolicyRef managed object table"
    ::= { cucsVnicObjects 47 }

cucsVnicDynamicConPolicyRefEntry OBJECT-TYPE
    SYNTAX           CucsVnicDynamicConPolicyRefEntry
    MAX-ACCESS       not-accessible
    STATUS           current
    DESCRIPTION
        "Entry for the cucsVnicDynamicConPolicyRefTable table."
    INDEX { cucsVnicDynamicConPolicyRefInstanceId }
    ::= { cucsVnicDynamicConPolicyRefTable 1 }

CucsVnicDynamicConPolicyRefEntry ::= SEQUENCE {
    cucsVnicDynamicConPolicyRefInstanceId                            CucsManagedObjectId,
    cucsVnicDynamicConPolicyRefDn                                    CucsManagedObjectDn,
    cucsVnicDynamicConPolicyRefRn                                    SnmpAdminString,
    cucsVnicDynamicConPolicyRefConPolicyName                         SnmpAdminString,
    cucsVnicDynamicConPolicyRefOperConPolicyName                     SnmpAdminString
}

cucsVnicDynamicConPolicyRefInstanceId OBJECT-TYPE
    SYNTAX       CucsManagedObjectId
    MAX-ACCESS   not-accessible
    STATUS       current
    DESCRIPTION
        "Instance identifier of the managed object."
    ::= { cucsVnicDynamicConPolicyRefEntry 1 }

cucsVnicDynamicConPolicyRefDn OBJECT-TYPE
    SYNTAX       CucsManagedObjectDn
    MAX-ACCESS   read-only
    STATUS       current
    DESCRIPTION
        "Cisco UCS vnic:DynamicConPolicyRef:dn managed object property"
    ::= { cucsVnicDynamicConPolicyRefEntry 2 }

cucsVnicDynamicConPolicyRefRn OBJECT-TYPE
    SYNTAX       SnmpAdminString
    MAX-ACCESS   read-only
    STATUS       current
    DESCRIPTION
        "Cisco UCS vnic:DynamicConPolicyRef:rn managed object property"
    ::= { cucsVnicDynamicConPolicyRefEntry 3 }

cucsVnicDynamicConPolicyRefConPolicyName OBJECT-TYPE
    SYNTAX       SnmpAdminString
    MAX-ACCESS   read-only
    STATUS       current
    DESCRIPTION
        "Cisco UCS vnic:DynamicConPolicyRef:conPolicyName
        managed object property"
    ::= { cucsVnicDynamicConPolicyRefEntry 4 }

cucsVnicDynamicConPolicyRefOperConPolicyName OBJECT-TYPE
    SYNTAX       SnmpAdminString
    MAX-ACCESS   read-only
    STATUS       current
    DESCRIPTION
        "Cisco UCS vnic:DynamicConPolicyRef:operConPolicyName
        managed object property"
    ::= { cucsVnicDynamicConPolicyRefEntry 5 }

cucsVnicDynamicIdUniverseTable OBJECT-TYPE
    SYNTAX           SEQUENCE OF CucsVnicDynamicIdUniverseEntry
    MAX-ACCESS       not-accessible
    STATUS           current
    DESCRIPTION
        "Cisco UCS vnic:DynamicIdUniverse managed object table"
    ::= { cucsVnicObjects 5 }

cucsVnicDynamicIdUniverseEntry OBJECT-TYPE
    SYNTAX           CucsVnicDynamicIdUniverseEntry
    MAX-ACCESS       not-accessible
    STATUS           current
    DESCRIPTION
        "Entry for the cucsVnicDynamicIdUniverseTable table."
    INDEX { cucsVnicDynamicIdUniverseInstanceId }
    ::= { cucsVnicDynamicIdUniverseTable 1 }

CucsVnicDynamicIdUniverseEntry ::= SEQUENCE {
    cucsVnicDynamicIdUniverseInstanceId                              CucsManagedObjectId,
    cucsVnicDynamicIdUniverseDn                                      CucsManagedObjectDn,
    cucsVnicDynamicIdUniverseRn                                      SnmpAdminString,
    cucsVnicDynamicIdUniverseDescr                                   SnmpAdminString,
    cucsVnicDynamicIdUniverseIntId                                   SnmpAdminString,
    cucsVnicDynamicIdUniverseName                                    SnmpAdminString,
    cucsVnicDynamicIdUniversePolicyLevel                             Gauge32,
    cucsVnicDynamicIdUniversePolicyOwner                             CucsPolicyPolicyOwner
}

cucsVnicDynamicIdUniverseInstanceId OBJECT-TYPE
    SYNTAX       CucsManagedObjectId
    MAX-ACCESS   not-accessible
    STATUS       current
    DESCRIPTION
        "Instance identifier of the managed object."
    ::= { cucsVnicDynamicIdUniverseEntry 1 }

cucsVnicDynamicIdUniverseDn OBJECT-TYPE
    SYNTAX       CucsManagedObjectDn
    MAX-ACCESS   read-only
    STATUS       current
    DESCRIPTION
        "Cisco UCS vnic:DynamicIdUniverse:dn managed object property"
    ::= { cucsVnicDynamicIdUniverseEntry 2 }

cucsVnicDynamicIdUniverseRn OBJECT-TYPE
    SYNTAX       SnmpAdminString
    MAX-ACCESS   read-only
    STATUS       current
    DESCRIPTION
        "Cisco UCS vnic:DynamicIdUniverse:rn managed object property"
    ::= { cucsVnicDynamicIdUniverseEntry 3 }

cucsVnicDynamicIdUniverseDescr OBJECT-TYPE
    SYNTAX       SnmpAdminString
    MAX-ACCESS   read-only
    STATUS       current
    DESCRIPTION
        "Cisco UCS vnic:DynamicIdUniverse:descr managed object property"
    ::= { cucsVnicDynamicIdUniverseEntry 4 }

cucsVnicDynamicIdUniverseIntId OBJECT-TYPE
    SYNTAX       SnmpAdminString
    MAX-ACCESS   read-only
    STATUS       current
    DESCRIPTION
        "Cisco UCS vnic:DynamicIdUniverse:intId managed object property"
    ::= { cucsVnicDynamicIdUniverseEntry 5 }

cucsVnicDynamicIdUniverseName OBJECT-TYPE
    SYNTAX       SnmpAdminString
    MAX-ACCESS   read-only
    STATUS       current
    DESCRIPTION
        "Cisco UCS vnic:DynamicIdUniverse:name managed object property"
    ::= { cucsVnicDynamicIdUniverseEntry 6 }

cucsVnicDynamicIdUniversePolicyLevel OBJECT-TYPE
    SYNTAX       Gauge32
    MAX-ACCESS   read-only
    STATUS       current
    DESCRIPTION
        "Cisco UCS vnic:DynamicIdUniverse:policyLevel managed
        object property"
    ::= { cucsVnicDynamicIdUniverseEntry 7 }

cucsVnicDynamicIdUniversePolicyOwner OBJECT-TYPE
    SYNTAX       CucsPolicyPolicyOwner
    MAX-ACCESS   read-only
    STATUS       current
    DESCRIPTION
        "Cisco UCS vnic:DynamicIdUniverse:policyOwner managed
        object property"
    ::= { cucsVnicDynamicIdUniverseEntry 8 }

cucsVnicDynamicProviderTable OBJECT-TYPE
    SYNTAX           SEQUENCE OF CucsVnicDynamicProviderEntry
    MAX-ACCESS       not-accessible
    STATUS           current
    DESCRIPTION
        "Cisco UCS vnic:DynamicProvider managed object table"
    ::= { cucsVnicObjects 6 }

cucsVnicDynamicProviderEntry OBJECT-TYPE
    SYNTAX           CucsVnicDynamicProviderEntry
    MAX-ACCESS       not-accessible
    STATUS           current
    DESCRIPTION
        "Entry for the cucsVnicDynamicProviderTable table."
    INDEX { cucsVnicDynamicProviderInstanceId }
    ::= { cucsVnicDynamicProviderTable 1 }

CucsVnicDynamicProviderEntry ::= SEQUENCE {
    cucsVnicDynamicProviderInstanceId                                CucsManagedObjectId,
    cucsVnicDynamicProviderDn                                        CucsManagedObjectDn,
    cucsVnicDynamicProviderRn                                        SnmpAdminString,
    cucsVnicDynamicProviderName                                      SnmpAdminString
}

cucsVnicDynamicProviderInstanceId OBJECT-TYPE
    SYNTAX       CucsManagedObjectId
    MAX-ACCESS   not-accessible
    STATUS       current
    DESCRIPTION
        "Instance identifier of the managed object."
    ::= { cucsVnicDynamicProviderEntry 1 }

cucsVnicDynamicProviderDn OBJECT-TYPE
    SYNTAX       CucsManagedObjectDn
    MAX-ACCESS   read-only
    STATUS       current
    DESCRIPTION
        "Cisco UCS vnic:DynamicProvider:dn managed object property"
    ::= { cucsVnicDynamicProviderEntry 2 }

cucsVnicDynamicProviderRn OBJECT-TYPE
    SYNTAX       SnmpAdminString
    MAX-ACCESS   read-only
    STATUS       current
    DESCRIPTION
        "Cisco UCS vnic:DynamicProvider:rn managed object property"
    ::= { cucsVnicDynamicProviderEntry 3 }

cucsVnicDynamicProviderName OBJECT-TYPE
    SYNTAX       SnmpAdminString
    MAX-ACCESS   read-only
    STATUS       current
    DESCRIPTION
        "Cisco UCS vnic:DynamicProvider:name managed object property"
    ::= { cucsVnicDynamicProviderEntry 4 }

cucsVnicDynamicProviderEpTable OBJECT-TYPE
    SYNTAX           SEQUENCE OF CucsVnicDynamicProviderEpEntry
    MAX-ACCESS       not-accessible
    STATUS           current
    DESCRIPTION
        "Cisco UCS vnic:DynamicProviderEp managed object table"
    ::= { cucsVnicObjects 7 }

cucsVnicDynamicProviderEpEntry OBJECT-TYPE
    SYNTAX           CucsVnicDynamicProviderEpEntry
    MAX-ACCESS       not-accessible
    STATUS           current
    DESCRIPTION
        "Entry for the cucsVnicDynamicProviderEpTable table."
    INDEX { cucsVnicDynamicProviderEpInstanceId }
    ::= { cucsVnicDynamicProviderEpTable 1 }

CucsVnicDynamicProviderEpEntry ::= SEQUENCE {
    cucsVnicDynamicProviderEpInstanceId                              CucsManagedObjectId,
    cucsVnicDynamicProviderEpDn                                      CucsManagedObjectDn,
    cucsVnicDynamicProviderEpRn                                      SnmpAdminString,
    cucsVnicDynamicProviderEpChassisId                               Gauge32,
    cucsVnicDynamicProviderEpPortId                                  Gauge32,
    cucsVnicDynamicProviderEpSlotId                                  Gauge32,
    cucsVnicDynamicProviderEpSwitchId                                CucsNetworkSwitchId
}

cucsVnicDynamicProviderEpInstanceId OBJECT-TYPE
    SYNTAX       CucsManagedObjectId
    MAX-ACCESS   not-accessible
    STATUS       current
    DESCRIPTION
        "Instance identifier of the managed object."
    ::= { cucsVnicDynamicProviderEpEntry 1 }

cucsVnicDynamicProviderEpDn OBJECT-TYPE
    SYNTAX       CucsManagedObjectDn
    MAX-ACCESS   read-only
    STATUS       current
    DESCRIPTION
        "Cisco UCS vnic:DynamicProviderEp:dn managed object property"
    ::= { cucsVnicDynamicProviderEpEntry 2 }

cucsVnicDynamicProviderEpRn OBJECT-TYPE
    SYNTAX       SnmpAdminString
    MAX-ACCESS   read-only
    STATUS       current
    DESCRIPTION
        "Cisco UCS vnic:DynamicProviderEp:rn managed object property"
    ::= { cucsVnicDynamicProviderEpEntry 3 }

cucsVnicDynamicProviderEpChassisId OBJECT-TYPE
    SYNTAX       Gauge32
    MAX-ACCESS   read-only
    STATUS       current
    DESCRIPTION
        "Cisco UCS vnic:DynamicProviderEp:chassisId managed
        object property"
    ::= { cucsVnicDynamicProviderEpEntry 4 }

cucsVnicDynamicProviderEpPortId OBJECT-TYPE
    SYNTAX       Gauge32
    MAX-ACCESS   read-only
    STATUS       current
    DESCRIPTION
        "Cisco UCS vnic:DynamicProviderEp:portId managed object property"
    ::= { cucsVnicDynamicProviderEpEntry 5 }

cucsVnicDynamicProviderEpSlotId OBJECT-TYPE
    SYNTAX       Gauge32
    MAX-ACCESS   read-only
    STATUS       current
    DESCRIPTION
        "Cisco UCS vnic:DynamicProviderEp:slotId managed object property"
    ::= { cucsVnicDynamicProviderEpEntry 6 }

cucsVnicDynamicProviderEpSwitchId OBJECT-TYPE
    SYNTAX       CucsNetworkSwitchId
    MAX-ACCESS   read-only
    STATUS       current
    DESCRIPTION
        "Cisco UCS vnic:DynamicProviderEp:switchId managed
        object property"
    ::= { cucsVnicDynamicProviderEpEntry 7 }

cucsVnicEthConfigTable OBJECT-TYPE
    SYNTAX           SEQUENCE OF CucsVnicEthConfigEntry
    MAX-ACCESS       not-accessible
    STATUS           current
    DESCRIPTION
        "Cisco UCS vnic:EthConfig managed object table"
    ::= { cucsVnicObjects 74 }

cucsVnicEthConfigEntry OBJECT-TYPE
    SYNTAX           CucsVnicEthConfigEntry
    MAX-ACCESS       not-accessible
    STATUS           current
    DESCRIPTION
        "Entry for the cucsVnicEthConfigTable table."
    INDEX { cucsVnicEthConfigInstanceId }
    ::= { cucsVnicEthConfigTable 1 }

CucsVnicEthConfigEntry ::= SEQUENCE {
    cucsVnicEthConfigInstanceId                                      CucsManagedObjectId,
    cucsVnicEthConfigDn                                              CucsManagedObjectDn,
    cucsVnicEthConfigRn                                              SnmpAdminString,
    cucsVnicEthConfigAdaptorProfileName                              SnmpAdminString,
    cucsVnicEthConfigMacPoolName                                     SnmpAdminString,
    cucsVnicEthConfigNwCtrlPolicyName                                SnmpAdminString,
    cucsVnicEthConfigOperAdaptorProfileName                          SnmpAdminString,
    cucsVnicEthConfigOperMacPoolName                                 SnmpAdminString,
    cucsVnicEthConfigOperNwCtrlPolicyName                            SnmpAdminString,
    cucsVnicEthConfigOperStatsPolicyName                             SnmpAdminString,
    cucsVnicEthConfigStatsPolicyName                                 SnmpAdminString
}

cucsVnicEthConfigInstanceId OBJECT-TYPE
    SYNTAX       CucsManagedObjectId
    MAX-ACCESS   not-accessible
    STATUS       current
    DESCRIPTION
        "Instance identifier of the managed object."
    ::= { cucsVnicEthConfigEntry 1 }

cucsVnicEthConfigDn OBJECT-TYPE
    SYNTAX       CucsManagedObjectDn
    MAX-ACCESS   read-only
    STATUS       current
    DESCRIPTION
        "Cisco UCS vnic:EthConfig:dn managed object property"
    ::= { cucsVnicEthConfigEntry 2 }

cucsVnicEthConfigRn OBJECT-TYPE
    SYNTAX       SnmpAdminString
    MAX-ACCESS   read-only
    STATUS       current
    DESCRIPTION
        "Cisco UCS vnic:EthConfig:rn managed object property"
    ::= { cucsVnicEthConfigEntry 3 }

cucsVnicEthConfigAdaptorProfileName OBJECT-TYPE
    SYNTAX       SnmpAdminString
    MAX-ACCESS   read-only
    STATUS       current
    DESCRIPTION
        "Cisco UCS vnic:EthConfig:adaptorProfileName managed
        object property"
    ::= { cucsVnicEthConfigEntry 4 }

cucsVnicEthConfigMacPoolName OBJECT-TYPE
    SYNTAX       SnmpAdminString
    MAX-ACCESS   read-only
    STATUS       current
    DESCRIPTION
        "Cisco UCS vnic:EthConfig:macPoolName managed object property"
    ::= { cucsVnicEthConfigEntry 5 }

cucsVnicEthConfigNwCtrlPolicyName OBJECT-TYPE
    SYNTAX       SnmpAdminString
    MAX-ACCESS   read-only
    STATUS       current
    DESCRIPTION
        "Cisco UCS vnic:EthConfig:nwCtrlPolicyName managed
        object property"
    ::= { cucsVnicEthConfigEntry 6 }

cucsVnicEthConfigOperAdaptorProfileName OBJECT-TYPE
    SYNTAX       SnmpAdminString
    MAX-ACCESS   read-only
    STATUS       current
    DESCRIPTION
        "Cisco UCS vnic:EthConfig:operAdaptorProfileName
        managed object property"
    ::= { cucsVnicEthConfigEntry 7 }

cucsVnicEthConfigOperMacPoolName OBJECT-TYPE
    SYNTAX       SnmpAdminString
    MAX-ACCESS   read-only
    STATUS       current
    DESCRIPTION
        "Cisco UCS vnic:EthConfig:operMacPoolName managed object property"
    ::= { cucsVnicEthConfigEntry 8 }

cucsVnicEthConfigOperNwCtrlPolicyName OBJECT-TYPE
    SYNTAX       SnmpAdminString
    MAX-ACCESS   read-only
    STATUS       current
    DESCRIPTION
        "Cisco UCS vnic:EthConfig:operNwCtrlPolicyName
        managed object property"
    ::= { cucsVnicEthConfigEntry 9 }

cucsVnicEthConfigOperStatsPolicyName OBJECT-TYPE
    SYNTAX       SnmpAdminString
    MAX-ACCESS   read-only
    STATUS       current
    DESCRIPTION
        "Cisco UCS vnic:EthConfig:operStatsPolicyName managed
        object property"
    ::= { cucsVnicEthConfigEntry 10 }

cucsVnicEthConfigStatsPolicyName OBJECT-TYPE
    SYNTAX       SnmpAdminString
    MAX-ACCESS   read-only
    STATUS       current
    DESCRIPTION
        "Cisco UCS vnic:EthConfig:statsPolicyName managed object property"
    ::= { cucsVnicEthConfigEntry 11 }

cucsVnicEthLifTable OBJECT-TYPE
    SYNTAX           SEQUENCE OF CucsVnicEthLifEntry
    MAX-ACCESS       not-accessible
    STATUS           current
    DESCRIPTION
        "Cisco UCS vnic:EthLif managed object table"
    ::= { cucsVnicObjects 8 }

cucsVnicEthLifEntry OBJECT-TYPE
    SYNTAX           CucsVnicEthLifEntry
    MAX-ACCESS       not-accessible
    STATUS           current
    DESCRIPTION
        "Entry for the cucsVnicEthLifTable table."
    INDEX { cucsVnicEthLifInstanceId }
    ::= { cucsVnicEthLifTable 1 }

CucsVnicEthLifEntry ::= SEQUENCE {
    cucsVnicEthLifInstanceId                                         CucsManagedObjectId,
    cucsVnicEthLifDn                                                 CucsManagedObjectDn,
    cucsVnicEthLifRn                                                 SnmpAdminString,
    cucsVnicEthLifAddr                                               MacAddress,
    cucsVnicEthLifName                                               SnmpAdminString,
    cucsVnicEthLifNicDn                                              SnmpAdminString,
    cucsVnicEthLifOwner                                              CucsVnicConnectionOwner,
    cucsVnicEthLifSwitchId                                           CucsNetworkSwitchId,
    cucsVnicEthLifType                                               CucsVnicConnectionType,
    cucsVnicEthLifVnicDn                                             SnmpAdminString
}

cucsVnicEthLifInstanceId OBJECT-TYPE
    SYNTAX       CucsManagedObjectId
    MAX-ACCESS   not-accessible
    STATUS       current
    DESCRIPTION
        "Instance identifier of the managed object."
    ::= { cucsVnicEthLifEntry 1 }

cucsVnicEthLifDn OBJECT-TYPE
    SYNTAX       CucsManagedObjectDn
    MAX-ACCESS   read-only
    STATUS       current
    DESCRIPTION
        "Cisco UCS vnic:EthLif:dn managed object property"
    ::= { cucsVnicEthLifEntry 2 }

cucsVnicEthLifRn OBJECT-TYPE
    SYNTAX       SnmpAdminString
    MAX-ACCESS   read-only
    STATUS       current
    DESCRIPTION
        "Cisco UCS vnic:EthLif:rn managed object property"
    ::= { cucsVnicEthLifEntry 3 }

cucsVnicEthLifAddr OBJECT-TYPE
    SYNTAX       MacAddress
    MAX-ACCESS   read-only
    STATUS       current
    DESCRIPTION
        "Cisco UCS vnic:EthLif:addr managed object property"
    ::= { cucsVnicEthLifEntry 4 }

cucsVnicEthLifName OBJECT-TYPE
    SYNTAX       SnmpAdminString
    MAX-ACCESS   read-only
    STATUS       current
    DESCRIPTION
        "Cisco UCS vnic:EthLif:name managed object property"
    ::= { cucsVnicEthLifEntry 5 }

cucsVnicEthLifNicDn OBJECT-TYPE
    SYNTAX       SnmpAdminString
    MAX-ACCESS   read-only
    STATUS       current
    DESCRIPTION
        "Cisco UCS vnic:EthLif:nicDn managed object property"
    ::= { cucsVnicEthLifEntry 6 }

cucsVnicEthLifOwner OBJECT-TYPE
    SYNTAX       CucsVnicConnectionOwner
    MAX-ACCESS   read-only
    STATUS       current
    DESCRIPTION
        "Cisco UCS vnic:EthLif:owner managed object property"
    ::= { cucsVnicEthLifEntry 7 }

cucsVnicEthLifSwitchId OBJECT-TYPE
    SYNTAX       CucsNetworkSwitchId
    MAX-ACCESS   read-only
    STATUS       current
    DESCRIPTION
        "Cisco UCS vnic:EthLif:switchId managed object property"
    ::= { cucsVnicEthLifEntry 8 }

cucsVnicEthLifType OBJECT-TYPE
    SYNTAX       CucsVnicConnectionType
    MAX-ACCESS   read-only
    STATUS       current
    DESCRIPTION
        "Cisco UCS vnic:EthLif:type managed object property"
    ::= { cucsVnicEthLifEntry 9 }

cucsVnicEthLifVnicDn OBJECT-TYPE
    SYNTAX       SnmpAdminString
    MAX-ACCESS   read-only
    STATUS       current
    DESCRIPTION
        "Cisco UCS vnic:EthLif:vnicDn managed object property"
    ::= { cucsVnicEthLifEntry 10 }

cucsVnicEtherTable OBJECT-TYPE
    SYNTAX           SEQUENCE OF CucsVnicEtherEntry
    MAX-ACCESS       not-accessible
    STATUS           current
    DESCRIPTION
        "Cisco UCS vnic:Ether managed object table"
    ::= { cucsVnicObjects 9 }

cucsVnicEtherEntry OBJECT-TYPE
    SYNTAX           CucsVnicEtherEntry
    MAX-ACCESS       not-accessible
    STATUS           current
    DESCRIPTION
        "Entry for the cucsVnicEtherTable table."
    INDEX { cucsVnicEtherInstanceId }
    ::= { cucsVnicEtherTable 1 }

CucsVnicEtherEntry ::= SEQUENCE {
    cucsVnicEtherInstanceId                                          CucsManagedObjectId,
    cucsVnicEtherDn                                                  CucsManagedObjectDn,
    cucsVnicEtherRn                                                  SnmpAdminString,
    cucsVnicEtherAdaptorProfileName                                  SnmpAdminString,
    cucsVnicEtherAddr                                                MacAddress,
    cucsVnicEtherAdminVcon                                           SnmpAdminString,
    cucsVnicEtherBootDev                                             CucsVnicVnicBootDev,
    cucsVnicEtherConfigState                                         CucsLsConfigState,
    cucsVnicEtherEquipmentDn                                         SnmpAdminString,
    cucsVnicEtherFltAggr                                             Unsigned64,
    cucsVnicEtherIdentPoolName                                       SnmpAdminString,
    cucsVnicEtherInstType                                            CucsVnicInstantiation,
    cucsVnicEtherMtu                                                 Gauge32,
    cucsVnicEtherName                                                SnmpAdminString,
    cucsVnicEtherNwCtrlPolicyName                                    SnmpAdminString,
    cucsVnicEtherNwTemplName                                         SnmpAdminString,
    cucsVnicEtherOperAdaptorProfileName                              SnmpAdminString,
    cucsVnicEtherOperIdentPoolName                                   SnmpAdminString,
    cucsVnicEtherOperNwCtrlPolicyName                                SnmpAdminString,
    cucsVnicEtherOperNwTemplName                                     SnmpAdminString,
    cucsVnicEtherOperOrder                                           Gauge32,
    cucsVnicEtherOperQosPolicyName                                   SnmpAdminString,
    cucsVnicEtherOperSpeed                                           Gauge32,
    cucsVnicEtherOperStatsPolicyName                                 SnmpAdminString,
    cucsVnicEtherOperVcon                                            SnmpAdminString,
    cucsVnicEtherOrder                                               Gauge32,
    cucsVnicEtherOwner                                               CucsVnicConnectionOwner,
    cucsVnicEtherPinToGroupName                                      SnmpAdminString,
    cucsVnicEtherQosPolicyName                                       SnmpAdminString,
    cucsVnicEtherStatsPolicyName                                     SnmpAdminString,
    cucsVnicEtherSwitchId                                            CucsVnicEtherBaseSwitchId,
    cucsVnicEtherType                                                CucsVnicEtherType,
    cucsVnicEtherOperPinToGroupName                                  SnmpAdminString,
    cucsVnicEtherConfigQualifier                                     CucsVnicConfigIssues,
    cucsVnicEtherDynamicId                                           Gauge32,
    cucsVnicEtherPfDn                                                SnmpAdminString,
    cucsVnicEtherVirtualizationPreference                            CucsVnicVirtualizationPreferenceType,
    cucsVnicEtherAdminHostPort                                       CucsFabricHostPortId,
    cucsVnicEtherOperHostPort                                        CucsVnicVnicOperHostPort,
    cucsVnicEtherPropAcl                                             Unsigned64,
    cucsVnicEtherPurpose                                             CucsAdaptorPurpose,
    cucsVnicEtherAdminCdnName                                        SnmpAdminString,
    cucsVnicEtherOperCdnName                                         SnmpAdminString,
    cucsVnicEtherCdnSource                                           CucsVnicCdnSource,
    cucsVnicEtherCdnPropInSync                                       TruthValue
}

cucsVnicEtherInstanceId OBJECT-TYPE
    SYNTAX       CucsManagedObjectId
    MAX-ACCESS   not-accessible
    STATUS       current
    DESCRIPTION
        "Instance identifier of the managed object."
    ::= { cucsVnicEtherEntry 1 }

cucsVnicEtherDn OBJECT-TYPE
    SYNTAX       CucsManagedObjectDn
    MAX-ACCESS   read-only
    STATUS       current
    DESCRIPTION
        "Cisco UCS vnic:Ether:dn managed object property"
    ::= { cucsVnicEtherEntry 2 }

cucsVnicEtherRn OBJECT-TYPE
    SYNTAX       SnmpAdminString
    MAX-ACCESS   read-only
    STATUS       current
    DESCRIPTION
        "Cisco UCS vnic:Ether:rn managed object property"
    ::= { cucsVnicEtherEntry 3 }

cucsVnicEtherAdaptorProfileName OBJECT-TYPE
    SYNTAX       SnmpAdminString
    MAX-ACCESS   read-only
    STATUS       current
    DESCRIPTION
        "Cisco UCS vnic:Ether:adaptorProfileName managed object property"
    ::= { cucsVnicEtherEntry 4 }

cucsVnicEtherAddr OBJECT-TYPE
    SYNTAX       MacAddress
    MAX-ACCESS   read-only
    STATUS       current
    DESCRIPTION
        "Cisco UCS vnic:Ether:addr managed object property"
    ::= { cucsVnicEtherEntry 5 }

cucsVnicEtherAdminVcon OBJECT-TYPE
    SYNTAX       SnmpAdminString
    MAX-ACCESS   read-only
    STATUS       current
    DESCRIPTION
        "Cisco UCS vnic:Ether:adminVcon managed object property"
    ::= { cucsVnicEtherEntry 6 }

cucsVnicEtherBootDev OBJECT-TYPE
    SYNTAX       CucsVnicVnicBootDev
    MAX-ACCESS   read-only
    STATUS       current
    DESCRIPTION
        "Cisco UCS vnic:Ether:bootDev managed object property"
    ::= { cucsVnicEtherEntry 7 }

cucsVnicEtherConfigState OBJECT-TYPE
    SYNTAX       CucsLsConfigState
    MAX-ACCESS   read-only
    STATUS       current
    DESCRIPTION
        "Cisco UCS vnic:Ether:configState managed object property"
    ::= { cucsVnicEtherEntry 8 }

cucsVnicEtherEquipmentDn OBJECT-TYPE
    SYNTAX       SnmpAdminString
    MAX-ACCESS   read-only
    STATUS       current
    DESCRIPTION
        "Cisco UCS vnic:Ether:equipmentDn managed object property"
    ::= { cucsVnicEtherEntry 9 }

cucsVnicEtherFltAggr OBJECT-TYPE
    SYNTAX       Unsigned64
    MAX-ACCESS   read-only
    STATUS       current
    DESCRIPTION
        "Cisco UCS vnic:Ether:fltAggr managed object property"
    ::= { cucsVnicEtherEntry 10 }

cucsVnicEtherIdentPoolName OBJECT-TYPE
    SYNTAX       SnmpAdminString
    MAX-ACCESS   read-only
    STATUS       current
    DESCRIPTION
        "Cisco UCS vnic:Ether:identPoolName managed object property"
    ::= { cucsVnicEtherEntry 11 }

cucsVnicEtherInstType OBJECT-TYPE
    SYNTAX       CucsVnicInstantiation
    MAX-ACCESS   read-only
    STATUS       current
    DESCRIPTION
        "Cisco UCS vnic:Ether:instType managed object property"
    ::= { cucsVnicEtherEntry 12 }

cucsVnicEtherMtu OBJECT-TYPE
    SYNTAX       Gauge32
    MAX-ACCESS   read-only
    STATUS       current
    DESCRIPTION
        "Cisco UCS vnic:Ether:mtu managed object property"
    ::= { cucsVnicEtherEntry 13 }

cucsVnicEtherName OBJECT-TYPE
    SYNTAX       SnmpAdminString
    MAX-ACCESS   read-only
    STATUS       current
    DESCRIPTION
        "Cisco UCS vnic:Ether:name managed object property"
    ::= { cucsVnicEtherEntry 14 }

cucsVnicEtherNwCtrlPolicyName OBJECT-TYPE
    SYNTAX       SnmpAdminString
    MAX-ACCESS   read-only
    STATUS       current
    DESCRIPTION
        "Cisco UCS vnic:Ether:nwCtrlPolicyName managed object property"
    ::= { cucsVnicEtherEntry 15 }

cucsVnicEtherNwTemplName OBJECT-TYPE
    SYNTAX       SnmpAdminString
    MAX-ACCESS   read-only
    STATUS       current
    DESCRIPTION
        "Cisco UCS vnic:Ether:nwTemplName managed object property"
    ::= { cucsVnicEtherEntry 16 }

cucsVnicEtherOperAdaptorProfileName OBJECT-TYPE
    SYNTAX       SnmpAdminString
    MAX-ACCESS   read-only
    STATUS       current
    DESCRIPTION
        "Cisco UCS vnic:Ether:operAdaptorProfileName managed
        object property"
    ::= { cucsVnicEtherEntry 17 }

cucsVnicEtherOperIdentPoolName OBJECT-TYPE
    SYNTAX       SnmpAdminString
    MAX-ACCESS   read-only
    STATUS       current
    DESCRIPTION
        "Cisco UCS vnic:Ether:operIdentPoolName managed object property"
    ::= { cucsVnicEtherEntry 18 }

cucsVnicEtherOperNwCtrlPolicyName OBJECT-TYPE
    SYNTAX       SnmpAdminString
    MAX-ACCESS   read-only
    STATUS       current
    DESCRIPTION
        "Cisco UCS vnic:Ether:operNwCtrlPolicyName managed
        object property"
    ::= { cucsVnicEtherEntry 19 }

cucsVnicEtherOperNwTemplName OBJECT-TYPE
    SYNTAX       SnmpAdminString
    MAX-ACCESS   read-only
    STATUS       current
    DESCRIPTION
        "Cisco UCS vnic:Ether:operNwTemplName managed object property"
    ::= { cucsVnicEtherEntry 20 }

cucsVnicEtherOperOrder OBJECT-TYPE
    SYNTAX       Gauge32
    MAX-ACCESS   read-only
    STATUS       current
    DESCRIPTION
        "Cisco UCS vnic:Ether:operOrder managed object property"
    ::= { cucsVnicEtherEntry 21 }

cucsVnicEtherOperQosPolicyName OBJECT-TYPE
    SYNTAX       SnmpAdminString
    MAX-ACCESS   read-only
    STATUS       current
    DESCRIPTION
        "Cisco UCS vnic:Ether:operQosPolicyName managed object property"
    ::= { cucsVnicEtherEntry 22 }

cucsVnicEtherOperSpeed OBJECT-TYPE
    SYNTAX       Gauge32
    MAX-ACCESS   read-only
    STATUS       current
    DESCRIPTION
        "Cisco UCS vnic:Ether:operSpeed managed object property"
    ::= { cucsVnicEtherEntry 23 }

cucsVnicEtherOperStatsPolicyName OBJECT-TYPE
    SYNTAX       SnmpAdminString
    MAX-ACCESS   read-only
    STATUS       current
    DESCRIPTION
        "Cisco UCS vnic:Ether:operStatsPolicyName managed object property"
    ::= { cucsVnicEtherEntry 24 }

cucsVnicEtherOperVcon OBJECT-TYPE
    SYNTAX       SnmpAdminString
    MAX-ACCESS   read-only
    STATUS       current
    DESCRIPTION
        "Cisco UCS vnic:Ether:operVcon managed object property"
    ::= { cucsVnicEtherEntry 25 }

cucsVnicEtherOrder OBJECT-TYPE
    SYNTAX       Gauge32
    MAX-ACCESS   read-only
    STATUS       current
    DESCRIPTION
        "Cisco UCS vnic:Ether:order managed object property"
    ::= { cucsVnicEtherEntry 26 }

cucsVnicEtherOwner OBJECT-TYPE
    SYNTAX       CucsVnicConnectionOwner
    MAX-ACCESS   read-only
    STATUS       current
    DESCRIPTION
        "Cisco UCS vnic:Ether:owner managed object property"
    ::= { cucsVnicEtherEntry 27 }

cucsVnicEtherPinToGroupName OBJECT-TYPE
    SYNTAX       SnmpAdminString
    MAX-ACCESS   read-only
    STATUS       current
    DESCRIPTION
        "Cisco UCS vnic:Ether:pinToGroupName managed object property"
    ::= { cucsVnicEtherEntry 28 }

cucsVnicEtherQosPolicyName OBJECT-TYPE
    SYNTAX       SnmpAdminString
    MAX-ACCESS   read-only
    STATUS       current
    DESCRIPTION
        "Cisco UCS vnic:Ether:qosPolicyName managed object property"
    ::= { cucsVnicEtherEntry 29 }

cucsVnicEtherStatsPolicyName OBJECT-TYPE
    SYNTAX       SnmpAdminString
    MAX-ACCESS   read-only
    STATUS       current
    DESCRIPTION
        "Cisco UCS vnic:Ether:statsPolicyName managed object property"
    ::= { cucsVnicEtherEntry 30 }

cucsVnicEtherSwitchId OBJECT-TYPE
    SYNTAX       CucsVnicEtherBaseSwitchId
    MAX-ACCESS   read-only
    STATUS       current
    DESCRIPTION
        "Cisco UCS vnic:Ether:switchId managed object property"
    ::= { cucsVnicEtherEntry 31 }

cucsVnicEtherType OBJECT-TYPE
    SYNTAX       CucsVnicEtherType
    MAX-ACCESS   read-only
    STATUS       current
    DESCRIPTION
        "Cisco UCS vnic:Ether:type managed object property"
    ::= { cucsVnicEtherEntry 32 }

cucsVnicEtherOperPinToGroupName OBJECT-TYPE
    SYNTAX       SnmpAdminString
    MAX-ACCESS   read-only
    STATUS       current
    DESCRIPTION
        "Cisco UCS vnic:Ether:operPinToGroupName managed object property"
    ::= { cucsVnicEtherEntry 33 }

cucsVnicEtherConfigQualifier OBJECT-TYPE
    SYNTAX       CucsVnicConfigIssues
    MAX-ACCESS   read-only
    STATUS       current
    DESCRIPTION
        "Cisco UCS vnic:Ether:configQualifier managed object property"
    ::= { cucsVnicEtherEntry 34 }

cucsVnicEtherDynamicId OBJECT-TYPE
    SYNTAX       Gauge32
    MAX-ACCESS   read-only
    STATUS       current
    DESCRIPTION
        "Cisco UCS vnic:Ether:dynamicId managed object property"
    ::= { cucsVnicEtherEntry 35 }

cucsVnicEtherPfDn OBJECT-TYPE
    SYNTAX       SnmpAdminString
    MAX-ACCESS   read-only
    STATUS       current
    DESCRIPTION
        "Cisco UCS vnic:Ether:pfDn managed object property"
    ::= { cucsVnicEtherEntry 36 }

cucsVnicEtherVirtualizationPreference OBJECT-TYPE
    SYNTAX       CucsVnicVirtualizationPreferenceType
    MAX-ACCESS   read-only
    STATUS       current
    DESCRIPTION
        "Cisco UCS vnic:Ether:virtualizationPreference
        managed object property"
    ::= { cucsVnicEtherEntry 37 }

cucsVnicEtherAdminHostPort OBJECT-TYPE
    SYNTAX       CucsFabricHostPortId
    MAX-ACCESS   read-only
    STATUS       current
    DESCRIPTION
        "Cisco UCS vnic:Ether:adminHostPort managed object property"
    ::= { cucsVnicEtherEntry 39 }

cucsVnicEtherOperHostPort OBJECT-TYPE
    SYNTAX       CucsVnicVnicOperHostPort
    MAX-ACCESS   read-only
    STATUS       current
    DESCRIPTION
        "Cisco UCS vnic:Ether:operHostPort managed object property"
    ::= { cucsVnicEtherEntry 40 }

cucsVnicEtherPropAcl OBJECT-TYPE
    SYNTAX       Unsigned64
    MAX-ACCESS   read-only
    STATUS       current
    DESCRIPTION
        "Cisco UCS vnic:Ether:propAcl managed object property"
    ::= { cucsVnicEtherEntry 41 }

cucsVnicEtherPurpose OBJECT-TYPE
    SYNTAX       CucsAdaptorPurpose
    MAX-ACCESS   read-only
    STATUS       current
    DESCRIPTION
        "Cisco UCS vnic:Ether:purpose managed object property"
    ::= { cucsVnicEtherEntry 42 }

cucsVnicEtherAdminCdnName OBJECT-TYPE
    SYNTAX       SnmpAdminString
    MAX-ACCESS   read-only
    STATUS       current
    DESCRIPTION
        "Cisco UCS vnic:Ether:adminCdnName managed object property"
    ::= { cucsVnicEtherEntry 43 }

cucsVnicEtherOperCdnName OBJECT-TYPE
    SYNTAX       SnmpAdminString
    MAX-ACCESS   read-only
    STATUS       current
    DESCRIPTION
        "Cisco UCS vnic:Ether:operCdnName managed object property"
    ::= { cucsVnicEtherEntry 44 }

cucsVnicEtherCdnSource OBJECT-TYPE
    SYNTAX       CucsVnicCdnSource
    MAX-ACCESS   read-only
    STATUS       current
    DESCRIPTION
        "Cisco UCS vnic:Ether:cdnSource managed object property"
    ::= { cucsVnicEtherEntry 45 }

cucsVnicEtherCdnPropInSync OBJECT-TYPE
    SYNTAX       TruthValue
    MAX-ACCESS   read-only
    STATUS       current
    DESCRIPTION
        "Cisco UCS vnic:Ether:cdnPropInSync managed object property"
    ::= { cucsVnicEtherEntry 46 }

cucsVnicEtherIfTable OBJECT-TYPE
    SYNTAX           SEQUENCE OF CucsVnicEtherIfEntry
    MAX-ACCESS       not-accessible
    STATUS           current
    DESCRIPTION
        "Cisco UCS vnic:EtherIf managed object table"
    ::= { cucsVnicObjects 10 }

cucsVnicEtherIfEntry OBJECT-TYPE
    SYNTAX           CucsVnicEtherIfEntry
    MAX-ACCESS       not-accessible
    STATUS           current
    DESCRIPTION
        "Entry for the cucsVnicEtherIfTable table."
    INDEX { cucsVnicEtherIfInstanceId }
    ::= { cucsVnicEtherIfTable 1 }

CucsVnicEtherIfEntry ::= SEQUENCE {
    cucsVnicEtherIfInstanceId                                        CucsManagedObjectId,
    cucsVnicEtherIfDn                                                CucsManagedObjectDn,
    cucsVnicEtherIfRn                                                SnmpAdminString,
    cucsVnicEtherIfAddr                                              MacAddress,
    cucsVnicEtherIfDefaultNet                                        TruthValue,
    cucsVnicEtherIfName                                              SnmpAdminString,
    cucsVnicEtherIfOperState                                         CucsVnicIfOperState,
    cucsVnicEtherIfOwner                                             CucsVnicConnectionOwner,
    cucsVnicEtherIfSwitchId                                          CucsVnicEtherBaseIfSwitchId,
    cucsVnicEtherIfType                                              CucsVnicAEtherIfType,
    cucsVnicEtherIfVnet                                              Gauge32,
    cucsVnicEtherIfOperVnetDn                                        SnmpAdminString,
    cucsVnicEtherIfOperVnetName                                      SnmpAdminString,
    cucsVnicEtherIfConfigQualifier                                   CucsVnicConfigIssues,
    cucsVnicEtherIfFltAggr                                           Unsigned64,
    cucsVnicEtherIfPubNwId                                           Gauge32,
    cucsVnicEtherIfSharing                                           CucsFabricVlanSharingType,
    cucsVnicEtherIfPropAcl                                           Unsigned64,
    cucsVnicEtherIfOperPrimaryVnetDn                                 SnmpAdminString,
    cucsVnicEtherIfOperPrimaryVnetName                               SnmpAdminString
}

cucsVnicEtherIfInstanceId OBJECT-TYPE
    SYNTAX       CucsManagedObjectId
    MAX-ACCESS   not-accessible
    STATUS       current
    DESCRIPTION
        "Instance identifier of the managed object."
    ::= { cucsVnicEtherIfEntry 1 }

cucsVnicEtherIfDn OBJECT-TYPE
    SYNTAX       CucsManagedObjectDn
    MAX-ACCESS   read-only
    STATUS       current
    DESCRIPTION
        "Cisco UCS vnic:EtherIf:dn managed object property"
    ::= { cucsVnicEtherIfEntry 2 }

cucsVnicEtherIfRn OBJECT-TYPE
    SYNTAX       SnmpAdminString
    MAX-ACCESS   read-only
    STATUS       current
    DESCRIPTION
        "Cisco UCS vnic:EtherIf:rn managed object property"
    ::= { cucsVnicEtherIfEntry 3 }

cucsVnicEtherIfAddr OBJECT-TYPE
    SYNTAX       MacAddress
    MAX-ACCESS   read-only
    STATUS       current
    DESCRIPTION
        "Cisco UCS vnic:EtherIf:addr managed object property"
    ::= { cucsVnicEtherIfEntry 4 }

cucsVnicEtherIfDefaultNet OBJECT-TYPE
    SYNTAX       TruthValue
    MAX-ACCESS   read-only
    STATUS       current
    DESCRIPTION
        "Cisco UCS vnic:EtherIf:defaultNet managed object property"
    ::= { cucsVnicEtherIfEntry 5 }

cucsVnicEtherIfName OBJECT-TYPE
    SYNTAX       SnmpAdminString
    MAX-ACCESS   read-only
    STATUS       current
    DESCRIPTION
        "Cisco UCS vnic:EtherIf:name managed object property"
    ::= { cucsVnicEtherIfEntry 6 }

cucsVnicEtherIfOperState OBJECT-TYPE
    SYNTAX       CucsVnicIfOperState
    MAX-ACCESS   read-only
    STATUS       current
    DESCRIPTION
        "Cisco UCS vnic:EtherIf:operState managed object property"
    ::= { cucsVnicEtherIfEntry 7 }

cucsVnicEtherIfOwner OBJECT-TYPE
    SYNTAX       CucsVnicConnectionOwner
    MAX-ACCESS   read-only
    STATUS       current
    DESCRIPTION
        "Cisco UCS vnic:EtherIf:owner managed object property"
    ::= { cucsVnicEtherIfEntry 8 }

cucsVnicEtherIfSwitchId OBJECT-TYPE
    SYNTAX       CucsVnicEtherBaseIfSwitchId
    MAX-ACCESS   read-only
    STATUS       current
    DESCRIPTION
        "Cisco UCS vnic:EtherIf:switchId managed object property"
    ::= { cucsVnicEtherIfEntry 9 }

cucsVnicEtherIfType OBJECT-TYPE
    SYNTAX       CucsVnicAEtherIfType
    MAX-ACCESS   read-only
    STATUS       current
    DESCRIPTION
        "Cisco UCS vnic:EtherIf:type managed object property"
    ::= { cucsVnicEtherIfEntry 10 }

cucsVnicEtherIfVnet OBJECT-TYPE
    SYNTAX       Gauge32
    MAX-ACCESS   read-only
    STATUS       current
    DESCRIPTION
        "Cisco UCS vnic:EtherIf:vnet managed object property"
    ::= { cucsVnicEtherIfEntry 11 }

cucsVnicEtherIfOperVnetDn OBJECT-TYPE
    SYNTAX       SnmpAdminString
    MAX-ACCESS   read-only
    STATUS       current
    DESCRIPTION
        "Cisco UCS vnic:EtherIf:operVnetDn managed object property"
    ::= { cucsVnicEtherIfEntry 12 }

cucsVnicEtherIfOperVnetName OBJECT-TYPE
    SYNTAX       SnmpAdminString
    MAX-ACCESS   read-only
    STATUS       current
    DESCRIPTION
        "Cisco UCS vnic:EtherIf:operVnetName managed object property"
    ::= { cucsVnicEtherIfEntry 13 }

cucsVnicEtherIfConfigQualifier OBJECT-TYPE
    SYNTAX       CucsVnicConfigIssues
    MAX-ACCESS   read-only
    STATUS       current
    DESCRIPTION
        "Cisco UCS vnic:EtherIf:configQualifier managed object property"
    ::= { cucsVnicEtherIfEntry 14 }

cucsVnicEtherIfFltAggr OBJECT-TYPE
    SYNTAX       Unsigned64
    MAX-ACCESS   read-only
    STATUS       current
    DESCRIPTION
        "Cisco UCS vnic:EtherIf:fltAggr managed object property"
    ::= { cucsVnicEtherIfEntry 15 }

cucsVnicEtherIfPubNwId OBJECT-TYPE
    SYNTAX       Gauge32
    MAX-ACCESS   read-only
    STATUS       current
    DESCRIPTION
        "Cisco UCS vnic:EtherIf:pubNwId managed object property"
    ::= { cucsVnicEtherIfEntry 17 }

cucsVnicEtherIfSharing OBJECT-TYPE
    SYNTAX       CucsFabricVlanSharingType
    MAX-ACCESS   read-only
    STATUS       current
    DESCRIPTION
        "Cisco UCS vnic:EtherIf:sharing managed object property"
    ::= { cucsVnicEtherIfEntry 18 }

cucsVnicEtherIfPropAcl OBJECT-TYPE
    SYNTAX       Unsigned64
    MAX-ACCESS   read-only
    STATUS       current
    DESCRIPTION
        "Cisco UCS vnic:EtherIf:propAcl managed object property"
    ::= { cucsVnicEtherIfEntry 19 }

cucsVnicEtherIfOperPrimaryVnetDn OBJECT-TYPE
    SYNTAX       SnmpAdminString
    MAX-ACCESS   read-only
    STATUS       current
    DESCRIPTION
        "Cisco UCS vnic:EtherIf:operPrimaryVnetDn managed object property"
    ::= { cucsVnicEtherIfEntry 20 }

cucsVnicEtherIfOperPrimaryVnetName OBJECT-TYPE
    SYNTAX       SnmpAdminString
    MAX-ACCESS   read-only
    STATUS       current
    DESCRIPTION
        "Cisco UCS vnic:EtherIf:operPrimaryVnetName managed
        object property"
    ::= { cucsVnicEtherIfEntry 21 }

cucsVnicFcTable OBJECT-TYPE
    SYNTAX           SEQUENCE OF CucsVnicFcEntry
    MAX-ACCESS       not-accessible
    STATUS           current
    DESCRIPTION
        "Cisco UCS vnic:Fc managed object table"
    ::= { cucsVnicObjects 11 }

cucsVnicFcEntry OBJECT-TYPE
    SYNTAX           CucsVnicFcEntry
    MAX-ACCESS       not-accessible
    STATUS           current
    DESCRIPTION
        "Entry for the cucsVnicFcTable table."
    INDEX { cucsVnicFcInstanceId }
    ::= { cucsVnicFcTable 1 }

CucsVnicFcEntry ::= SEQUENCE {
    cucsVnicFcInstanceId                                             CucsManagedObjectId,
    cucsVnicFcDn                                                     CucsManagedObjectDn,
    cucsVnicFcRn                                                     SnmpAdminString,
    cucsVnicFcAdaptorProfileName                                     SnmpAdminString,
    cucsVnicFcAddr                                                   Unsigned64,
    cucsVnicFcAdminVcon                                              SnmpAdminString,
    cucsVnicFcBootDev                                                CucsVnicVnicBootDev,
    cucsVnicFcConfigState                                            CucsLsConfigState,
    cucsVnicFcEquipmentDn                                            SnmpAdminString,
    cucsVnicFcFltAggr                                                Unsigned64,
    cucsVnicFcIdentPoolName                                          SnmpAdminString,
    cucsVnicFcInstType                                               CucsVnicInstantiation,
    cucsVnicFcMaxDataFieldSize                                       Gauge32,
    cucsVnicFcName                                                   SnmpAdminString,
    cucsVnicFcNdAddr                                                 Unsigned64,
    cucsVnicFcNwTemplName                                            SnmpAdminString,
    cucsVnicFcOperAdaptorProfileName                                 SnmpAdminString,
    cucsVnicFcOperIdentPoolName                                      SnmpAdminString,
    cucsVnicFcOperNwTemplName                                        SnmpAdminString,
    cucsVnicFcOperOrder                                              Gauge32,
    cucsVnicFcOperQosPolicyName                                      SnmpAdminString,
    cucsVnicFcOperSpeed                                              Gauge32,
    cucsVnicFcOperStatsPolicyName                                    SnmpAdminString,
    cucsVnicFcOperVcon                                               SnmpAdminString,
    cucsVnicFcOrder                                                  Gauge32,
    cucsVnicFcOwner                                                  CucsVnicConnectionOwner,
    cucsVnicFcPersBind                                               CucsVnicFcBasePersBind,
    cucsVnicFcPersBindClear                                          TruthValue,
    cucsVnicFcPinToGroupName                                         SnmpAdminString,
    cucsVnicFcQosPolicyName                                          SnmpAdminString,
    cucsVnicFcStatsPolicyName                                        SnmpAdminString,
    cucsVnicFcSwitchId                                               CucsNetworkSwitchId,
    cucsVnicFcType                                                   CucsVnicFcBaseType,
    cucsVnicFcOperPinToGroupName                                     SnmpAdminString,
    cucsVnicFcConfigQualifier                                        CucsVnicConfigIssues,
    cucsVnicFcAdminHostPort                                          CucsFabricHostPortId,
    cucsVnicFcOperHostPort                                           CucsVnicVnicOperHostPort,
    cucsVnicFcAdminCdnName                                           SnmpAdminString,
    cucsVnicFcOperCdnName                                            SnmpAdminString,
    cucsVnicFcCdnSource                                              CucsVnicCdnSource,
    cucsVnicFcCdnPropInSync                                          TruthValue
}

cucsVnicFcInstanceId OBJECT-TYPE
    SYNTAX       CucsManagedObjectId
    MAX-ACCESS   not-accessible
    STATUS       current
    DESCRIPTION
        "Instance identifier of the managed object."
    ::= { cucsVnicFcEntry 1 }

cucsVnicFcDn OBJECT-TYPE
    SYNTAX       CucsManagedObjectDn
    MAX-ACCESS   read-only
    STATUS       current
    DESCRIPTION
        "Cisco UCS vnic:Fc:dn managed object property"
    ::= { cucsVnicFcEntry 2 }

cucsVnicFcRn OBJECT-TYPE
    SYNTAX       SnmpAdminString
    MAX-ACCESS   read-only
    STATUS       current
    DESCRIPTION
        "Cisco UCS vnic:Fc:rn managed object property"
    ::= { cucsVnicFcEntry 3 }

cucsVnicFcAdaptorProfileName OBJECT-TYPE
    SYNTAX       SnmpAdminString
    MAX-ACCESS   read-only
    STATUS       current
    DESCRIPTION
        "Cisco UCS vnic:Fc:adaptorProfileName managed object property"
    ::= { cucsVnicFcEntry 4 }

cucsVnicFcAddr OBJECT-TYPE
    SYNTAX       Unsigned64
    MAX-ACCESS   read-only
    STATUS       current
    DESCRIPTION
        "Cisco UCS vnic:Fc:addr managed object property"
    ::= { cucsVnicFcEntry 5 }

cucsVnicFcAdminVcon OBJECT-TYPE
    SYNTAX       SnmpAdminString
    MAX-ACCESS   read-only
    STATUS       current
    DESCRIPTION
        "Cisco UCS vnic:Fc:adminVcon managed object property"
    ::= { cucsVnicFcEntry 6 }

cucsVnicFcBootDev OBJECT-TYPE
    SYNTAX       CucsVnicVnicBootDev
    MAX-ACCESS   read-only
    STATUS       current
    DESCRIPTION
        "Cisco UCS vnic:Fc:bootDev managed object property"
    ::= { cucsVnicFcEntry 7 }

cucsVnicFcConfigState OBJECT-TYPE
    SYNTAX       CucsLsConfigState
    MAX-ACCESS   read-only
    STATUS       current
    DESCRIPTION
        "Cisco UCS vnic:Fc:configState managed object property"
    ::= { cucsVnicFcEntry 8 }

cucsVnicFcEquipmentDn OBJECT-TYPE
    SYNTAX       SnmpAdminString
    MAX-ACCESS   read-only
    STATUS       current
    DESCRIPTION
        "Cisco UCS vnic:Fc:equipmentDn managed object property"
    ::= { cucsVnicFcEntry 9 }

cucsVnicFcFltAggr OBJECT-TYPE
    SYNTAX       Unsigned64
    MAX-ACCESS   read-only
    STATUS       current
    DESCRIPTION
        "Cisco UCS vnic:Fc:fltAggr managed object property"
    ::= { cucsVnicFcEntry 10 }

cucsVnicFcIdentPoolName OBJECT-TYPE
    SYNTAX       SnmpAdminString
    MAX-ACCESS   read-only
    STATUS       current
    DESCRIPTION
        "Cisco UCS vnic:Fc:identPoolName managed object property"
    ::= { cucsVnicFcEntry 11 }

cucsVnicFcInstType OBJECT-TYPE
    SYNTAX       CucsVnicInstantiation
    MAX-ACCESS   read-only
    STATUS       current
    DESCRIPTION
        "Cisco UCS vnic:Fc:instType managed object property"
    ::= { cucsVnicFcEntry 12 }

cucsVnicFcMaxDataFieldSize OBJECT-TYPE
    SYNTAX       Gauge32
    MAX-ACCESS   read-only
    STATUS       current
    DESCRIPTION
        "Cisco UCS vnic:Fc:maxDataFieldSize managed object property"
    ::= { cucsVnicFcEntry 13 }

cucsVnicFcName OBJECT-TYPE
    SYNTAX       SnmpAdminString
    MAX-ACCESS   read-only
    STATUS       current
    DESCRIPTION
        "Cisco UCS vnic:Fc:name managed object property"
    ::= { cucsVnicFcEntry 14 }

cucsVnicFcNdAddr OBJECT-TYPE
    SYNTAX       Unsigned64
    MAX-ACCESS   read-only
    STATUS       current
    DESCRIPTION
        "Cisco UCS vnic:Fc:nodeAddr managed object property"
    ::= { cucsVnicFcEntry 15 }

cucsVnicFcNwTemplName OBJECT-TYPE
    SYNTAX       SnmpAdminString
    MAX-ACCESS   read-only
    STATUS       current
    DESCRIPTION
        "Cisco UCS vnic:Fc:nwTemplName managed object property"
    ::= { cucsVnicFcEntry 16 }

cucsVnicFcOperAdaptorProfileName OBJECT-TYPE
    SYNTAX       SnmpAdminString
    MAX-ACCESS   read-only
    STATUS       current
    DESCRIPTION
        "Cisco UCS vnic:Fc:operAdaptorProfileName managed object property"
    ::= { cucsVnicFcEntry 17 }

cucsVnicFcOperIdentPoolName OBJECT-TYPE
    SYNTAX       SnmpAdminString
    MAX-ACCESS   read-only
    STATUS       current
    DESCRIPTION
        "Cisco UCS vnic:Fc:operIdentPoolName managed object property"
    ::= { cucsVnicFcEntry 18 }

cucsVnicFcOperNwTemplName OBJECT-TYPE
    SYNTAX       SnmpAdminString
    MAX-ACCESS   read-only
    STATUS       current
    DESCRIPTION
        "Cisco UCS vnic:Fc:operNwTemplName managed object property"
    ::= { cucsVnicFcEntry 19 }

cucsVnicFcOperOrder OBJECT-TYPE
    SYNTAX       Gauge32
    MAX-ACCESS   read-only
    STATUS       current
    DESCRIPTION
        "Cisco UCS vnic:Fc:operOrder managed object property"
    ::= { cucsVnicFcEntry 20 }

cucsVnicFcOperQosPolicyName OBJECT-TYPE
    SYNTAX       SnmpAdminString
    MAX-ACCESS   read-only
    STATUS       current
    DESCRIPTION
        "Cisco UCS vnic:Fc:operQosPolicyName managed object property"
    ::= { cucsVnicFcEntry 21 }

cucsVnicFcOperSpeed OBJECT-TYPE
    SYNTAX       Gauge32
    MAX-ACCESS   read-only
    STATUS       current
    DESCRIPTION
        "Cisco UCS vnic:Fc:operSpeed managed object property"
    ::= { cucsVnicFcEntry 22 }

cucsVnicFcOperStatsPolicyName OBJECT-TYPE
    SYNTAX       SnmpAdminString
    MAX-ACCESS   read-only
    STATUS       current
    DESCRIPTION
        "Cisco UCS vnic:Fc:operStatsPolicyName managed object property"
    ::= { cucsVnicFcEntry 23 }

cucsVnicFcOperVcon OBJECT-TYPE
    SYNTAX       SnmpAdminString
    MAX-ACCESS   read-only
    STATUS       current
    DESCRIPTION
        "Cisco UCS vnic:Fc:operVcon managed object property"
    ::= { cucsVnicFcEntry 24 }

cucsVnicFcOrder OBJECT-TYPE
    SYNTAX       Gauge32
    MAX-ACCESS   read-only
    STATUS       current
    DESCRIPTION
        "Cisco UCS vnic:Fc:order managed object property"
    ::= { cucsVnicFcEntry 25 }

cucsVnicFcOwner OBJECT-TYPE
    SYNTAX       CucsVnicConnectionOwner
    MAX-ACCESS   read-only
    STATUS       current
    DESCRIPTION
        "Cisco UCS vnic:Fc:owner managed object property"
    ::= { cucsVnicFcEntry 26 }

cucsVnicFcPersBind OBJECT-TYPE
    SYNTAX       CucsVnicFcBasePersBind
    MAX-ACCESS   read-only
    STATUS       current
    DESCRIPTION
        "Cisco UCS vnic:Fc:persBind managed object property"
    ::= { cucsVnicFcEntry 27 }

cucsVnicFcPersBindClear OBJECT-TYPE
    SYNTAX       TruthValue
    MAX-ACCESS   read-only
    STATUS       current
    DESCRIPTION
        "Cisco UCS vnic:Fc:persBindClear managed object property"
    ::= { cucsVnicFcEntry 28 }

cucsVnicFcPinToGroupName OBJECT-TYPE
    SYNTAX       SnmpAdminString
    MAX-ACCESS   read-only
    STATUS       current
    DESCRIPTION
        "Cisco UCS vnic:Fc:pinToGroupName managed object property"
    ::= { cucsVnicFcEntry 29 }

cucsVnicFcQosPolicyName OBJECT-TYPE
    SYNTAX       SnmpAdminString
    MAX-ACCESS   read-only
    STATUS       current
    DESCRIPTION
        "Cisco UCS vnic:Fc:qosPolicyName managed object property"
    ::= { cucsVnicFcEntry 30 }

cucsVnicFcStatsPolicyName OBJECT-TYPE
    SYNTAX       SnmpAdminString
    MAX-ACCESS   read-only
    STATUS       current
    DESCRIPTION
        "Cisco UCS vnic:Fc:statsPolicyName managed object property"
    ::= { cucsVnicFcEntry 31 }

cucsVnicFcSwitchId OBJECT-TYPE
    SYNTAX       CucsNetworkSwitchId
    MAX-ACCESS   read-only
    STATUS       current
    DESCRIPTION
        "Cisco UCS vnic:Fc:switchId managed object property"
    ::= { cucsVnicFcEntry 32 }

cucsVnicFcType OBJECT-TYPE
    SYNTAX       CucsVnicFcBaseType
    MAX-ACCESS   read-only
    STATUS       current
    DESCRIPTION
        "Cisco UCS vnic:Fc:type managed object property"
    ::= { cucsVnicFcEntry 33 }

cucsVnicFcOperPinToGroupName OBJECT-TYPE
    SYNTAX       SnmpAdminString
    MAX-ACCESS   read-only
    STATUS       current
    DESCRIPTION
        "Cisco UCS vnic:Fc:operPinToGroupName managed object property"
    ::= { cucsVnicFcEntry 34 }

cucsVnicFcConfigQualifier OBJECT-TYPE
    SYNTAX       CucsVnicConfigIssues
    MAX-ACCESS   read-only
    STATUS       current
    DESCRIPTION
        "Cisco UCS vnic:Fc:configQualifier managed object property"
    ::= { cucsVnicFcEntry 35 }

cucsVnicFcAdminHostPort OBJECT-TYPE
    SYNTAX       CucsFabricHostPortId
    MAX-ACCESS   read-only
    STATUS       current
    DESCRIPTION
        "Cisco UCS vnic:Fc:adminHostPort managed object property"
    ::= { cucsVnicFcEntry 37 }

cucsVnicFcOperHostPort OBJECT-TYPE
    SYNTAX       CucsVnicVnicOperHostPort
    MAX-ACCESS   read-only
    STATUS       current
    DESCRIPTION
        "Cisco UCS vnic:Fc:operHostPort managed object property"
    ::= { cucsVnicFcEntry 38 }

cucsVnicFcAdminCdnName OBJECT-TYPE
    SYNTAX       SnmpAdminString
    MAX-ACCESS   read-only
    STATUS       current
    DESCRIPTION
        "Cisco UCS vnic:Fc:adminCdnName managed object property"
    ::= { cucsVnicFcEntry 39 }

cucsVnicFcOperCdnName OBJECT-TYPE
    SYNTAX       SnmpAdminString
    MAX-ACCESS   read-only
    STATUS       current
    DESCRIPTION
        "Cisco UCS vnic:Fc:operCdnName managed object property"
    ::= { cucsVnicFcEntry 40 }

cucsVnicFcCdnSource OBJECT-TYPE
    SYNTAX       CucsVnicCdnSource
    MAX-ACCESS   read-only
    STATUS       current
    DESCRIPTION
        "Cisco UCS vnic:Fc:cdnSource managed object property"
    ::= { cucsVnicFcEntry 41 }

cucsVnicFcCdnPropInSync OBJECT-TYPE
    SYNTAX       TruthValue
    MAX-ACCESS   read-only
    STATUS       current
    DESCRIPTION
        "Cisco UCS vnic:Fc:cdnPropInSync managed object property"
    ::= { cucsVnicFcEntry 42 }

cucsVnicFcGroupDefTable OBJECT-TYPE
    SYNTAX           SEQUENCE OF CucsVnicFcGroupDefEntry
    MAX-ACCESS       not-accessible
    STATUS           current
    DESCRIPTION
        "Cisco UCS vnic:FcGroupDef managed object table"
    ::= { cucsVnicObjects 48 }

cucsVnicFcGroupDefEntry OBJECT-TYPE
    SYNTAX           CucsVnicFcGroupDefEntry
    MAX-ACCESS       not-accessible
    STATUS           current
    DESCRIPTION
        "Entry for the cucsVnicFcGroupDefTable table."
    INDEX { cucsVnicFcGroupDefInstanceId }
    ::= { cucsVnicFcGroupDefTable 1 }

CucsVnicFcGroupDefEntry ::= SEQUENCE {
    cucsVnicFcGroupDefInstanceId                                     CucsManagedObjectId,
    cucsVnicFcGroupDefDn                                             CucsManagedObjectDn,
    cucsVnicFcGroupDefRn                                             SnmpAdminString,
    cucsVnicFcGroupDefAdaptorProfileName                             SnmpAdminString,
    cucsVnicFcGroupDefDescr                                          SnmpAdminString,
    cucsVnicFcGroupDefIdentPoolName                                  SnmpAdminString,
    cucsVnicFcGroupDefIntId                                          SnmpAdminString,
    cucsVnicFcGroupDefMaxDataFieldSize                               Gauge32,
    cucsVnicFcGroupDefName                                           SnmpAdminString,
    cucsVnicFcGroupDefNwTemplName                                    SnmpAdminString,
    cucsVnicFcGroupDefOperStatsPolicyName                            SnmpAdminString,
    cucsVnicFcGroupDefOperStorageConnPolicyName                      SnmpAdminString,
    cucsVnicFcGroupDefPolicyLevel                                    Gauge32,
    cucsVnicFcGroupDefPolicyOwner                                    CucsPolicyPolicyOwner,
    cucsVnicFcGroupDefQosPolicyName                                  SnmpAdminString,
    cucsVnicFcGroupDefStatsPolicyName                                SnmpAdminString,
    cucsVnicFcGroupDefStorageConnPolicyName                          SnmpAdminString
}

cucsVnicFcGroupDefInstanceId OBJECT-TYPE
    SYNTAX       CucsManagedObjectId
    MAX-ACCESS   not-accessible
    STATUS       current
    DESCRIPTION
        "Instance identifier of the managed object."
    ::= { cucsVnicFcGroupDefEntry 1 }

cucsVnicFcGroupDefDn OBJECT-TYPE
    SYNTAX       CucsManagedObjectDn
    MAX-ACCESS   read-only
    STATUS       current
    DESCRIPTION
        "Cisco UCS vnic:FcGroupDef:dn managed object property"
    ::= { cucsVnicFcGroupDefEntry 2 }

cucsVnicFcGroupDefRn OBJECT-TYPE
    SYNTAX       SnmpAdminString
    MAX-ACCESS   read-only
    STATUS       current
    DESCRIPTION
        "Cisco UCS vnic:FcGroupDef:rn managed object property"
    ::= { cucsVnicFcGroupDefEntry 3 }

cucsVnicFcGroupDefAdaptorProfileName OBJECT-TYPE
    SYNTAX       SnmpAdminString
    MAX-ACCESS   read-only
    STATUS       current
    DESCRIPTION
        "Cisco UCS vnic:FcGroupDef:adaptorProfileName managed
        object property"
    ::= { cucsVnicFcGroupDefEntry 4 }

cucsVnicFcGroupDefDescr OBJECT-TYPE
    SYNTAX       SnmpAdminString
    MAX-ACCESS   read-only
    STATUS       current
    DESCRIPTION
        "Cisco UCS vnic:FcGroupDef:descr managed object property"
    ::= { cucsVnicFcGroupDefEntry 5 }

cucsVnicFcGroupDefIdentPoolName OBJECT-TYPE
    SYNTAX       SnmpAdminString
    MAX-ACCESS   read-only
    STATUS       current
    DESCRIPTION
        "Cisco UCS vnic:FcGroupDef:identPoolName managed object property"
    ::= { cucsVnicFcGroupDefEntry 6 }

cucsVnicFcGroupDefIntId OBJECT-TYPE
    SYNTAX       SnmpAdminString
    MAX-ACCESS   read-only
    STATUS       current
    DESCRIPTION
        "Cisco UCS vnic:FcGroupDef:intId managed object property"
    ::= { cucsVnicFcGroupDefEntry 7 }

cucsVnicFcGroupDefMaxDataFieldSize OBJECT-TYPE
    SYNTAX       Gauge32
    MAX-ACCESS   read-only
    STATUS       current
    DESCRIPTION
        "Cisco UCS vnic:FcGroupDef:maxDataFieldSize managed
        object property"
    ::= { cucsVnicFcGroupDefEntry 8 }

cucsVnicFcGroupDefName OBJECT-TYPE
    SYNTAX       SnmpAdminString
    MAX-ACCESS   read-only
    STATUS       current
    DESCRIPTION
        "Cisco UCS vnic:FcGroupDef:name managed object property"
    ::= { cucsVnicFcGroupDefEntry 9 }

cucsVnicFcGroupDefNwTemplName OBJECT-TYPE
    SYNTAX       SnmpAdminString
    MAX-ACCESS   read-only
    STATUS       current
    DESCRIPTION
        "Cisco UCS vnic:FcGroupDef:nwTemplName managed object property"
    ::= { cucsVnicFcGroupDefEntry 10 }

cucsVnicFcGroupDefOperStatsPolicyName OBJECT-TYPE
    SYNTAX       SnmpAdminString
    MAX-ACCESS   read-only
    STATUS       current
    DESCRIPTION
        "Cisco UCS vnic:FcGroupDef:operStatsPolicyName
        managed object property"
    ::= { cucsVnicFcGroupDefEntry 11 }

cucsVnicFcGroupDefOperStorageConnPolicyName OBJECT-TYPE
    SYNTAX       SnmpAdminString
    MAX-ACCESS   read-only
    STATUS       current
    DESCRIPTION
        "Cisco UCS vnic:FcGroupDef:operStorageConnPolicyName
        managed object property"
    ::= { cucsVnicFcGroupDefEntry 12 }

cucsVnicFcGroupDefPolicyLevel OBJECT-TYPE
    SYNTAX       Gauge32
    MAX-ACCESS   read-only
    STATUS       current
    DESCRIPTION
        "Cisco UCS vnic:FcGroupDef:policyLevel managed object property"
    ::= { cucsVnicFcGroupDefEntry 13 }

cucsVnicFcGroupDefPolicyOwner OBJECT-TYPE
    SYNTAX       CucsPolicyPolicyOwner
    MAX-ACCESS   read-only
    STATUS       current
    DESCRIPTION
        "Cisco UCS vnic:FcGroupDef:policyOwner managed object property"
    ::= { cucsVnicFcGroupDefEntry 14 }

cucsVnicFcGroupDefQosPolicyName OBJECT-TYPE
    SYNTAX       SnmpAdminString
    MAX-ACCESS   read-only
    STATUS       current
    DESCRIPTION
        "Cisco UCS vnic:FcGroupDef:qosPolicyName managed object property"
    ::= { cucsVnicFcGroupDefEntry 15 }

cucsVnicFcGroupDefStatsPolicyName OBJECT-TYPE
    SYNTAX       SnmpAdminString
    MAX-ACCESS   read-only
    STATUS       current
    DESCRIPTION
        "Cisco UCS vnic:FcGroupDef:statsPolicyName managed
        object property"
    ::= { cucsVnicFcGroupDefEntry 16 }

cucsVnicFcGroupDefStorageConnPolicyName OBJECT-TYPE
    SYNTAX       SnmpAdminString
    MAX-ACCESS   read-only
    STATUS       current
    DESCRIPTION
        "Cisco UCS vnic:FcGroupDef:storageConnPolicyName
        managed object property"
    ::= { cucsVnicFcGroupDefEntry 17 }

cucsVnicFcGroupTemplTable OBJECT-TYPE
    SYNTAX           SEQUENCE OF CucsVnicFcGroupTemplEntry
    MAX-ACCESS       not-accessible
    STATUS           current
    DESCRIPTION
        "Cisco UCS vnic:FcGroupTempl managed object table"
    ::= { cucsVnicObjects 49 }

cucsVnicFcGroupTemplEntry OBJECT-TYPE
    SYNTAX           CucsVnicFcGroupTemplEntry
    MAX-ACCESS       not-accessible
    STATUS           current
    DESCRIPTION
        "Entry for the cucsVnicFcGroupTemplTable table."
    INDEX { cucsVnicFcGroupTemplInstanceId }
    ::= { cucsVnicFcGroupTemplTable 1 }

CucsVnicFcGroupTemplEntry ::= SEQUENCE {
    cucsVnicFcGroupTemplInstanceId                                   CucsManagedObjectId,
    cucsVnicFcGroupTemplDn                                           CucsManagedObjectDn,
    cucsVnicFcGroupTemplRn                                           SnmpAdminString,
    cucsVnicFcGroupTemplAdaptorProfileName                           SnmpAdminString,
    cucsVnicFcGroupTemplDescr                                        SnmpAdminString,
    cucsVnicFcGroupTemplIdentPoolName                                SnmpAdminString,
    cucsVnicFcGroupTemplIntId                                        SnmpAdminString,
    cucsVnicFcGroupTemplMaxDataFieldSize                             Gauge32,
    cucsVnicFcGroupTemplName                                         SnmpAdminString,
    cucsVnicFcGroupTemplNwTemplName                                  SnmpAdminString,
    cucsVnicFcGroupTemplOperStatsPolicyName                          SnmpAdminString,
    cucsVnicFcGroupTemplOperStorageConnPolicyName                    SnmpAdminString,
    cucsVnicFcGroupTemplPolicyLevel                                  Gauge32,
    cucsVnicFcGroupTemplPolicyOwner                                  CucsPolicyPolicyOwner,
    cucsVnicFcGroupTemplQosPolicyName                                SnmpAdminString,
    cucsVnicFcGroupTemplStatsPolicyName                              SnmpAdminString,
    cucsVnicFcGroupTemplStorageConnPolicyName                        SnmpAdminString,
    cucsVnicFcGroupTemplTemplType                                    CucsVnicTemplateType
}

cucsVnicFcGroupTemplInstanceId OBJECT-TYPE
    SYNTAX       CucsManagedObjectId
    MAX-ACCESS   not-accessible
    STATUS       current
    DESCRIPTION
        "Instance identifier of the managed object."
    ::= { cucsVnicFcGroupTemplEntry 1 }

cucsVnicFcGroupTemplDn OBJECT-TYPE
    SYNTAX       CucsManagedObjectDn
    MAX-ACCESS   read-only
    STATUS       current
    DESCRIPTION
        "Cisco UCS vnic:FcGroupTempl:dn managed object property"
    ::= { cucsVnicFcGroupTemplEntry 2 }

cucsVnicFcGroupTemplRn OBJECT-TYPE
    SYNTAX       SnmpAdminString
    MAX-ACCESS   read-only
    STATUS       current
    DESCRIPTION
        "Cisco UCS vnic:FcGroupTempl:rn managed object property"
    ::= { cucsVnicFcGroupTemplEntry 3 }

cucsVnicFcGroupTemplAdaptorProfileName OBJECT-TYPE
    SYNTAX       SnmpAdminString
    MAX-ACCESS   read-only
    STATUS       current
    DESCRIPTION
        "Cisco UCS vnic:FcGroupTempl:adaptorProfileName
        managed object property"
    ::= { cucsVnicFcGroupTemplEntry 4 }

cucsVnicFcGroupTemplDescr OBJECT-TYPE
    SYNTAX       SnmpAdminString
    MAX-ACCESS   read-only
    STATUS       current
    DESCRIPTION
        "Cisco UCS vnic:FcGroupTempl:descr managed object property"
    ::= { cucsVnicFcGroupTemplEntry 5 }

cucsVnicFcGroupTemplIdentPoolName OBJECT-TYPE
    SYNTAX       SnmpAdminString
    MAX-ACCESS   read-only
    STATUS       current
    DESCRIPTION
        "Cisco UCS vnic:FcGroupTempl:identPoolName managed
        object property"
    ::= { cucsVnicFcGroupTemplEntry 6 }

cucsVnicFcGroupTemplIntId OBJECT-TYPE
    SYNTAX       SnmpAdminString
    MAX-ACCESS   read-only
    STATUS       current
    DESCRIPTION
        "Cisco UCS vnic:FcGroupTempl:intId managed object property"
    ::= { cucsVnicFcGroupTemplEntry 7 }

cucsVnicFcGroupTemplMaxDataFieldSize OBJECT-TYPE
    SYNTAX       Gauge32
    MAX-ACCESS   read-only
    STATUS       current
    DESCRIPTION
        "Cisco UCS vnic:FcGroupTempl:maxDataFieldSize managed
        object property"
    ::= { cucsVnicFcGroupTemplEntry 8 }

cucsVnicFcGroupTemplName OBJECT-TYPE
    SYNTAX       SnmpAdminString
    MAX-ACCESS   read-only
    STATUS       current
    DESCRIPTION
        "Cisco UCS vnic:FcGroupTempl:name managed object property"
    ::= { cucsVnicFcGroupTemplEntry 9 }

cucsVnicFcGroupTemplNwTemplName OBJECT-TYPE
    SYNTAX       SnmpAdminString
    MAX-ACCESS   read-only
    STATUS       current
    DESCRIPTION
        "Cisco UCS vnic:FcGroupTempl:nwTemplName managed object property"
    ::= { cucsVnicFcGroupTemplEntry 10 }

cucsVnicFcGroupTemplOperStatsPolicyName OBJECT-TYPE
    SYNTAX       SnmpAdminString
    MAX-ACCESS   read-only
    STATUS       current
    DESCRIPTION
        "Cisco UCS vnic:FcGroupTempl:operStatsPolicyName
        managed object property"
    ::= { cucsVnicFcGroupTemplEntry 11 }

cucsVnicFcGroupTemplOperStorageConnPolicyName OBJECT-TYPE
    SYNTAX       SnmpAdminString
    MAX-ACCESS   read-only
    STATUS       current
    DESCRIPTION
        "Cisco UCS vnic:FcGroupTempl:operStorageConnPolicyName
        managed object property"
    ::= { cucsVnicFcGroupTemplEntry 12 }

cucsVnicFcGroupTemplPolicyLevel OBJECT-TYPE
    SYNTAX       Gauge32
    MAX-ACCESS   read-only
    STATUS       current
    DESCRIPTION
        "Cisco UCS vnic:FcGroupTempl:policyLevel managed object property"
    ::= { cucsVnicFcGroupTemplEntry 13 }

cucsVnicFcGroupTemplPolicyOwner OBJECT-TYPE
    SYNTAX       CucsPolicyPolicyOwner
    MAX-ACCESS   read-only
    STATUS       current
    DESCRIPTION
        "Cisco UCS vnic:FcGroupTempl:policyOwner managed object property"
    ::= { cucsVnicFcGroupTemplEntry 14 }

cucsVnicFcGroupTemplQosPolicyName OBJECT-TYPE
    SYNTAX       SnmpAdminString
    MAX-ACCESS   read-only
    STATUS       current
    DESCRIPTION
        "Cisco UCS vnic:FcGroupTempl:qosPolicyName managed
        object property"
    ::= { cucsVnicFcGroupTemplEntry 15 }

cucsVnicFcGroupTemplStatsPolicyName OBJECT-TYPE
    SYNTAX       SnmpAdminString
    MAX-ACCESS   read-only
    STATUS       current
    DESCRIPTION
        "Cisco UCS vnic:FcGroupTempl:statsPolicyName managed
        object property"
    ::= { cucsVnicFcGroupTemplEntry 16 }

cucsVnicFcGroupTemplStorageConnPolicyName OBJECT-TYPE
    SYNTAX       SnmpAdminString
    MAX-ACCESS   read-only
    STATUS       current
    DESCRIPTION
        "Cisco UCS vnic:FcGroupTempl:storageConnPolicyName
        managed object property"
    ::= { cucsVnicFcGroupTemplEntry 17 }

cucsVnicFcGroupTemplTemplType OBJECT-TYPE
    SYNTAX       CucsVnicTemplateType
    MAX-ACCESS   read-only
    STATUS       current
    DESCRIPTION
        "Cisco UCS vnic:FcGroupTempl:templType managed object property"
    ::= { cucsVnicFcGroupTemplEntry 18 }

cucsVnicFcIfTable OBJECT-TYPE
    SYNTAX           SEQUENCE OF CucsVnicFcIfEntry
    MAX-ACCESS       not-accessible
    STATUS           current
    DESCRIPTION
        "Cisco UCS vnic:FcIf managed object table"
    ::= { cucsVnicObjects 12 }

cucsVnicFcIfEntry OBJECT-TYPE
    SYNTAX           CucsVnicFcIfEntry
    MAX-ACCESS       not-accessible
    STATUS           current
    DESCRIPTION
        "Entry for the cucsVnicFcIfTable table."
    INDEX { cucsVnicFcIfInstanceId }
    ::= { cucsVnicFcIfTable 1 }

CucsVnicFcIfEntry ::= SEQUENCE {
    cucsVnicFcIfInstanceId                                           CucsManagedObjectId,
    cucsVnicFcIfDn                                                   CucsManagedObjectDn,
    cucsVnicFcIfRn                                                   SnmpAdminString,
    cucsVnicFcIfInitiator                                            Unsigned64,
    cucsVnicFcIfName                                                 SnmpAdminString,
    cucsVnicFcIfOperState                                            CucsVnicIfOperState,
    cucsVnicFcIfOwner                                                CucsVnicConnectionOwner,
    cucsVnicFcIfSwitchId                                             CucsVnicAFcIfSwitchId,
    cucsVnicFcIfType                                                 CucsVnicAFcIfType,
    cucsVnicFcIfVnet                                                 Gauge32,
    cucsVnicFcIfOperVnetDn                                           SnmpAdminString,
    cucsVnicFcIfOperVnetName                                         SnmpAdminString,
    cucsVnicFcIfConfigQualifier                                      CucsVnicConfigIssues,
    cucsVnicFcIfPubNwId                                              Gauge32,
    cucsVnicFcIfSharing                                              CucsFabricVlanSharingType,
    cucsVnicFcIfOperPrimaryVnetDn                                    SnmpAdminString,
    cucsVnicFcIfOperPrimaryVnetName                                  SnmpAdminString
}

cucsVnicFcIfInstanceId OBJECT-TYPE
    SYNTAX       CucsManagedObjectId
    MAX-ACCESS   not-accessible
    STATUS       current
    DESCRIPTION
        "Instance identifier of the managed object."
    ::= { cucsVnicFcIfEntry 1 }

cucsVnicFcIfDn OBJECT-TYPE
    SYNTAX       CucsManagedObjectDn
    MAX-ACCESS   read-only
    STATUS       current
    DESCRIPTION
        "Cisco UCS vnic:FcIf:dn managed object property"
    ::= { cucsVnicFcIfEntry 2 }

cucsVnicFcIfRn OBJECT-TYPE
    SYNTAX       SnmpAdminString
    MAX-ACCESS   read-only
    STATUS       current
    DESCRIPTION
        "Cisco UCS vnic:FcIf:rn managed object property"
    ::= { cucsVnicFcIfEntry 3 }

cucsVnicFcIfInitiator OBJECT-TYPE
    SYNTAX       Unsigned64
    MAX-ACCESS   read-only
    STATUS       current
    DESCRIPTION
        "Cisco UCS vnic:FcIf:initiator managed object property"
    ::= { cucsVnicFcIfEntry 4 }

cucsVnicFcIfName OBJECT-TYPE
    SYNTAX       SnmpAdminString
    MAX-ACCESS   read-only
    STATUS       current
    DESCRIPTION
        "Cisco UCS vnic:FcIf:name managed object property"
    ::= { cucsVnicFcIfEntry 5 }

cucsVnicFcIfOperState OBJECT-TYPE
    SYNTAX       CucsVnicIfOperState
    MAX-ACCESS   read-only
    STATUS       current
    DESCRIPTION
        "Cisco UCS vnic:FcIf:operState managed object property"
    ::= { cucsVnicFcIfEntry 6 }

cucsVnicFcIfOwner OBJECT-TYPE
    SYNTAX       CucsVnicConnectionOwner
    MAX-ACCESS   read-only
    STATUS       current
    DESCRIPTION
        "Cisco UCS vnic:FcIf:owner managed object property"
    ::= { cucsVnicFcIfEntry 7 }

cucsVnicFcIfSwitchId OBJECT-TYPE
    SYNTAX       CucsVnicAFcIfSwitchId
    MAX-ACCESS   read-only
    STATUS       current
    DESCRIPTION
        "Cisco UCS vnic:FcIf:switchId managed object property"
    ::= { cucsVnicFcIfEntry 8 }

cucsVnicFcIfType OBJECT-TYPE
    SYNTAX       CucsVnicAFcIfType
    MAX-ACCESS   read-only
    STATUS       current
    DESCRIPTION
        "Cisco UCS vnic:FcIf:type managed object property"
    ::= { cucsVnicFcIfEntry 9 }

cucsVnicFcIfVnet OBJECT-TYPE
    SYNTAX       Gauge32
    MAX-ACCESS   read-only
    STATUS       current
    DESCRIPTION
        "Cisco UCS vnic:FcIf:vnet managed object property"
    ::= { cucsVnicFcIfEntry 10 }

cucsVnicFcIfOperVnetDn OBJECT-TYPE
    SYNTAX       SnmpAdminString
    MAX-ACCESS   read-only
    STATUS       current
    DESCRIPTION
        "Cisco UCS vnic:FcIf:operVnetDn managed object property"
    ::= { cucsVnicFcIfEntry 11 }

cucsVnicFcIfOperVnetName OBJECT-TYPE
    SYNTAX       SnmpAdminString
    MAX-ACCESS   read-only
    STATUS       current
    DESCRIPTION
        "Cisco UCS vnic:FcIf:operVnetName managed object property"
    ::= { cucsVnicFcIfEntry 12 }

cucsVnicFcIfConfigQualifier OBJECT-TYPE
    SYNTAX       CucsVnicConfigIssues
    MAX-ACCESS   read-only
    STATUS       current
    DESCRIPTION
        "Cisco UCS vnic:FcIf:configQualifier managed object property"
    ::= { cucsVnicFcIfEntry 13 }

cucsVnicFcIfPubNwId OBJECT-TYPE
    SYNTAX       Gauge32
    MAX-ACCESS   read-only
    STATUS       current
    DESCRIPTION
        "Cisco UCS vnic:FcIf:pubNwId managed object property"
    ::= { cucsVnicFcIfEntry 15 }

cucsVnicFcIfSharing OBJECT-TYPE
    SYNTAX       CucsFabricVlanSharingType
    MAX-ACCESS   read-only
    STATUS       current
    DESCRIPTION
        "Cisco UCS vnic:FcIf:sharing managed object property"
    ::= { cucsVnicFcIfEntry 16 }

cucsVnicFcIfOperPrimaryVnetDn OBJECT-TYPE
    SYNTAX       SnmpAdminString
    MAX-ACCESS   read-only
    STATUS       current
    DESCRIPTION
        "Cisco UCS vnic:FcIf:operPrimaryVnetDn managed object property"
    ::= { cucsVnicFcIfEntry 17 }

cucsVnicFcIfOperPrimaryVnetName OBJECT-TYPE
    SYNTAX       SnmpAdminString
    MAX-ACCESS   read-only
    STATUS       current
    DESCRIPTION
        "Cisco UCS vnic:FcIf:operPrimaryVnetName managed object property"
    ::= { cucsVnicFcIfEntry 18 }

cucsVnicFcLifTable OBJECT-TYPE
    SYNTAX           SEQUENCE OF CucsVnicFcLifEntry
    MAX-ACCESS       not-accessible
    STATUS           current
    DESCRIPTION
        "Cisco UCS vnic:FcLif managed object table"
    ::= { cucsVnicObjects 13 }

cucsVnicFcLifEntry OBJECT-TYPE
    SYNTAX           CucsVnicFcLifEntry
    MAX-ACCESS       not-accessible
    STATUS           current
    DESCRIPTION
        "Entry for the cucsVnicFcLifTable table."
    INDEX { cucsVnicFcLifInstanceId }
    ::= { cucsVnicFcLifTable 1 }

CucsVnicFcLifEntry ::= SEQUENCE {
    cucsVnicFcLifInstanceId                                          CucsManagedObjectId,
    cucsVnicFcLifDn                                                  CucsManagedObjectDn,
    cucsVnicFcLifRn                                                  SnmpAdminString,
    cucsVnicFcLifAddr                                                Unsigned64,
    cucsVnicFcLifName                                                SnmpAdminString,
    cucsVnicFcLifNicDn                                               SnmpAdminString,
    cucsVnicFcLifOwner                                               CucsVnicConnectionOwner,
    cucsVnicFcLifSwitchId                                            CucsNetworkSwitchId,
    cucsVnicFcLifType                                                CucsVnicConnectionType,
    cucsVnicFcLifVnicDn                                              SnmpAdminString
}

cucsVnicFcLifInstanceId OBJECT-TYPE
    SYNTAX       CucsManagedObjectId
    MAX-ACCESS   not-accessible
    STATUS       current
    DESCRIPTION
        "Instance identifier of the managed object."
    ::= { cucsVnicFcLifEntry 1 }

cucsVnicFcLifDn OBJECT-TYPE
    SYNTAX       CucsManagedObjectDn
    MAX-ACCESS   read-only
    STATUS       current
    DESCRIPTION
        "Cisco UCS vnic:FcLif:dn managed object property"
    ::= { cucsVnicFcLifEntry 2 }

cucsVnicFcLifRn OBJECT-TYPE
    SYNTAX       SnmpAdminString
    MAX-ACCESS   read-only
    STATUS       current
    DESCRIPTION
        "Cisco UCS vnic:FcLif:rn managed object property"
    ::= { cucsVnicFcLifEntry 3 }

cucsVnicFcLifAddr OBJECT-TYPE
    SYNTAX       Unsigned64
    MAX-ACCESS   read-only
    STATUS       current
    DESCRIPTION
        "Cisco UCS vnic:FcLif:addr managed object property"
    ::= { cucsVnicFcLifEntry 4 }

cucsVnicFcLifName OBJECT-TYPE
    SYNTAX       SnmpAdminString
    MAX-ACCESS   read-only
    STATUS       current
    DESCRIPTION
        "Cisco UCS vnic:FcLif:name managed object property"
    ::= { cucsVnicFcLifEntry 5 }

cucsVnicFcLifNicDn OBJECT-TYPE
    SYNTAX       SnmpAdminString
    MAX-ACCESS   read-only
    STATUS       current
    DESCRIPTION
        "Cisco UCS vnic:FcLif:nicDn managed object property"
    ::= { cucsVnicFcLifEntry 6 }

cucsVnicFcLifOwner OBJECT-TYPE
    SYNTAX       CucsVnicConnectionOwner
    MAX-ACCESS   read-only
    STATUS       current
    DESCRIPTION
        "Cisco UCS vnic:FcLif:owner managed object property"
    ::= { cucsVnicFcLifEntry 7 }

cucsVnicFcLifSwitchId OBJECT-TYPE
    SYNTAX       CucsNetworkSwitchId
    MAX-ACCESS   read-only
    STATUS       current
    DESCRIPTION
        "Cisco UCS vnic:FcLif:switchId managed object property"
    ::= { cucsVnicFcLifEntry 8 }

cucsVnicFcLifType OBJECT-TYPE
    SYNTAX       CucsVnicConnectionType
    MAX-ACCESS   read-only
    STATUS       current
    DESCRIPTION
        "Cisco UCS vnic:FcLif:type managed object property"
    ::= { cucsVnicFcLifEntry 9 }

cucsVnicFcLifVnicDn OBJECT-TYPE
    SYNTAX       SnmpAdminString
    MAX-ACCESS   read-only
    STATUS       current
    DESCRIPTION
        "Cisco UCS vnic:FcLif:vnicDn managed object property"
    ::= { cucsVnicFcLifEntry 10 }

cucsVnicFcNodeTable OBJECT-TYPE
    SYNTAX           SEQUENCE OF CucsVnicFcNodeEntry
    MAX-ACCESS       not-accessible
    STATUS           current
    DESCRIPTION
        "Cisco UCS vnic:FcNode managed object table"
    ::= { cucsVnicObjects 14 }

cucsVnicFcNodeEntry OBJECT-TYPE
    SYNTAX           CucsVnicFcNodeEntry
    MAX-ACCESS       not-accessible
    STATUS           current
    DESCRIPTION
        "Entry for the cucsVnicFcNodeTable table."
    INDEX { cucsVnicFcNodeInstanceId }
    ::= { cucsVnicFcNodeTable 1 }

CucsVnicFcNodeEntry ::= SEQUENCE {
    cucsVnicFcNodeInstanceId                                         CucsManagedObjectId,
    cucsVnicFcNodeDn                                                 CucsManagedObjectDn,
    cucsVnicFcNodeRn                                                 SnmpAdminString,
    cucsVnicFcNodeAddr                                               Unsigned64,
    cucsVnicFcNodeFltAggr                                            Unsigned64,
    cucsVnicFcNodeIdentPoolName                                      SnmpAdminString,
    cucsVnicFcNodeOperIdentPoolName                                  SnmpAdminString,
    cucsVnicFcNodeMaxDerivableWWPN                                   Gauge32,
    cucsVnicFcNodeOwner                                              CucsVnicFcNodeOwner
}

cucsVnicFcNodeInstanceId OBJECT-TYPE
    SYNTAX       CucsManagedObjectId
    MAX-ACCESS   not-accessible
    STATUS       current
    DESCRIPTION
        "Instance identifier of the managed object."
    ::= { cucsVnicFcNodeEntry 1 }

cucsVnicFcNodeDn OBJECT-TYPE
    SYNTAX       CucsManagedObjectDn
    MAX-ACCESS   read-only
    STATUS       current
    DESCRIPTION
        "Cisco UCS vnic:FcNode:dn managed object property"
    ::= { cucsVnicFcNodeEntry 2 }

cucsVnicFcNodeRn OBJECT-TYPE
    SYNTAX       SnmpAdminString
    MAX-ACCESS   read-only
    STATUS       current
    DESCRIPTION
        "Cisco UCS vnic:FcNode:rn managed object property"
    ::= { cucsVnicFcNodeEntry 3 }

cucsVnicFcNodeAddr OBJECT-TYPE
    SYNTAX       Unsigned64
    MAX-ACCESS   read-only
    STATUS       current
    DESCRIPTION
        "Cisco UCS vnic:FcNode:addr managed object property"
    ::= { cucsVnicFcNodeEntry 4 }

cucsVnicFcNodeFltAggr OBJECT-TYPE
    SYNTAX       Unsigned64
    MAX-ACCESS   read-only
    STATUS       current
    DESCRIPTION
        "Cisco UCS vnic:FcNode:fltAggr managed object property"
    ::= { cucsVnicFcNodeEntry 5 }

cucsVnicFcNodeIdentPoolName OBJECT-TYPE
    SYNTAX       SnmpAdminString
    MAX-ACCESS   read-only
    STATUS       current
    DESCRIPTION
        "Cisco UCS vnic:FcNode:identPoolName managed object property"
    ::= { cucsVnicFcNodeEntry 6 }

cucsVnicFcNodeOperIdentPoolName OBJECT-TYPE
    SYNTAX       SnmpAdminString
    MAX-ACCESS   read-only
    STATUS       current
    DESCRIPTION
        "Cisco UCS vnic:FcNode:operIdentPoolName managed object property"
    ::= { cucsVnicFcNodeEntry 7 }

cucsVnicFcNodeMaxDerivableWWPN OBJECT-TYPE
    SYNTAX       Gauge32
    MAX-ACCESS   read-only
    STATUS       current
    DESCRIPTION
        "Cisco UCS vnic:FcNode:maxDerivableWWPN managed object property"
    ::= { cucsVnicFcNodeEntry 8 }

cucsVnicFcNodeOwner OBJECT-TYPE
    SYNTAX       CucsVnicFcNodeOwner
    MAX-ACCESS   read-only
    STATUS       current
    DESCRIPTION
        "Cisco UCS vnic:FcNode:owner managed object property"
    ::= { cucsVnicFcNodeEntry 9 }

cucsVnicFcOEIfTable OBJECT-TYPE
    SYNTAX           SEQUENCE OF CucsVnicFcOEIfEntry
    MAX-ACCESS       not-accessible
    STATUS           current
    DESCRIPTION
        "Cisco UCS vnic:FcOEIf managed object table"
    ::= { cucsVnicObjects 15 }

cucsVnicFcOEIfEntry OBJECT-TYPE
    SYNTAX           CucsVnicFcOEIfEntry
    MAX-ACCESS       not-accessible
    STATUS           current
    DESCRIPTION
        "Entry for the cucsVnicFcOEIfTable table."
    INDEX { cucsVnicFcOEIfInstanceId }
    ::= { cucsVnicFcOEIfTable 1 }

CucsVnicFcOEIfEntry ::= SEQUENCE {
    cucsVnicFcOEIfInstanceId                                         CucsManagedObjectId,
    cucsVnicFcOEIfDn                                                 CucsManagedObjectDn,
    cucsVnicFcOEIfRn                                                 SnmpAdminString,
    cucsVnicFcOEIfInitiator                                          Unsigned64,
    cucsVnicFcOEIfName                                               SnmpAdminString,
    cucsVnicFcOEIfOperState                                          CucsVnicIfOperState,
    cucsVnicFcOEIfOwner                                              CucsVnicConnectionOwner,
    cucsVnicFcOEIfSwitchId                                           CucsVnicAFcIfSwitchId,
    cucsVnicFcOEIfType                                               CucsVnicAFcIfType,
    cucsVnicFcOEIfVnet                                               Gauge32,
    cucsVnicFcOEIfConfigQualifier                                    CucsVnicConfigIssues,
    cucsVnicFcOEIfOperVnetDn                                         SnmpAdminString,
    cucsVnicFcOEIfOperVnetName                                       SnmpAdminString,
    cucsVnicFcOEIfPubNwId                                            Gauge32,
    cucsVnicFcOEIfSharing                                            CucsFabricVlanSharingType,
    cucsVnicFcOEIfOperPrimaryVnetDn                                  SnmpAdminString,
    cucsVnicFcOEIfOperPrimaryVnetName                                SnmpAdminString
}

cucsVnicFcOEIfInstanceId OBJECT-TYPE
    SYNTAX       CucsManagedObjectId
    MAX-ACCESS   not-accessible
    STATUS       current
    DESCRIPTION
        "Instance identifier of the managed object."
    ::= { cucsVnicFcOEIfEntry 1 }

cucsVnicFcOEIfDn OBJECT-TYPE
    SYNTAX       CucsManagedObjectDn
    MAX-ACCESS   read-only
    STATUS       current
    DESCRIPTION
        "Cisco UCS vnic:FcOEIf:dn managed object property"
    ::= { cucsVnicFcOEIfEntry 2 }

cucsVnicFcOEIfRn OBJECT-TYPE
    SYNTAX       SnmpAdminString
    MAX-ACCESS   read-only
    STATUS       current
    DESCRIPTION
        "Cisco UCS vnic:FcOEIf:rn managed object property"
    ::= { cucsVnicFcOEIfEntry 3 }

cucsVnicFcOEIfInitiator OBJECT-TYPE
    SYNTAX       Unsigned64
    MAX-ACCESS   read-only
    STATUS       current
    DESCRIPTION
        "Cisco UCS vnic:FcOEIf:initiator managed object property"
    ::= { cucsVnicFcOEIfEntry 4 }

cucsVnicFcOEIfName OBJECT-TYPE
    SYNTAX       SnmpAdminString
    MAX-ACCESS   read-only
    STATUS       current
    DESCRIPTION
        "Cisco UCS vnic:FcOEIf:name managed object property"
    ::= { cucsVnicFcOEIfEntry 5 }

cucsVnicFcOEIfOperState OBJECT-TYPE
    SYNTAX       CucsVnicIfOperState
    MAX-ACCESS   read-only
    STATUS       current
    DESCRIPTION
        "Cisco UCS vnic:FcOEIf:operState managed object property"
    ::= { cucsVnicFcOEIfEntry 6 }

cucsVnicFcOEIfOwner OBJECT-TYPE
    SYNTAX       CucsVnicConnectionOwner
    MAX-ACCESS   read-only
    STATUS       current
    DESCRIPTION
        "Cisco UCS vnic:FcOEIf:owner managed object property"
    ::= { cucsVnicFcOEIfEntry 7 }

cucsVnicFcOEIfSwitchId OBJECT-TYPE
    SYNTAX       CucsVnicAFcIfSwitchId
    MAX-ACCESS   read-only
    STATUS       current
    DESCRIPTION
        "Cisco UCS vnic:FcOEIf:switchId managed object property"
    ::= { cucsVnicFcOEIfEntry 8 }

cucsVnicFcOEIfType OBJECT-TYPE
    SYNTAX       CucsVnicAFcIfType
    MAX-ACCESS   read-only
    STATUS       current
    DESCRIPTION
        "Cisco UCS vnic:FcOEIf:type managed object property"
    ::= { cucsVnicFcOEIfEntry 9 }

cucsVnicFcOEIfVnet OBJECT-TYPE
    SYNTAX       Gauge32
    MAX-ACCESS   read-only
    STATUS       current
    DESCRIPTION
        "Cisco UCS vnic:FcOEIf:vnet managed object property"
    ::= { cucsVnicFcOEIfEntry 10 }

cucsVnicFcOEIfConfigQualifier OBJECT-TYPE
    SYNTAX       CucsVnicConfigIssues
    MAX-ACCESS   read-only
    STATUS       current
    DESCRIPTION
        "Cisco UCS vnic:FcOEIf:configQualifier managed object property"
    ::= { cucsVnicFcOEIfEntry 11 }

cucsVnicFcOEIfOperVnetDn OBJECT-TYPE
    SYNTAX       SnmpAdminString
    MAX-ACCESS   read-only
    STATUS       current
    DESCRIPTION
        "Cisco UCS vnic:FcOEIf:operVnetDn managed object property"
    ::= { cucsVnicFcOEIfEntry 13 }

cucsVnicFcOEIfOperVnetName OBJECT-TYPE
    SYNTAX       SnmpAdminString
    MAX-ACCESS   read-only
    STATUS       current
    DESCRIPTION
        "Cisco UCS vnic:FcOEIf:operVnetName managed object property"
    ::= { cucsVnicFcOEIfEntry 14 }

cucsVnicFcOEIfPubNwId OBJECT-TYPE
    SYNTAX       Gauge32
    MAX-ACCESS   read-only
    STATUS       current
    DESCRIPTION
        "Cisco UCS vnic:FcOEIf:pubNwId managed object property"
    ::= { cucsVnicFcOEIfEntry 15 }

cucsVnicFcOEIfSharing OBJECT-TYPE
    SYNTAX       CucsFabricVlanSharingType
    MAX-ACCESS   read-only
    STATUS       current
    DESCRIPTION
        "Cisco UCS vnic:FcOEIf:sharing managed object property"
    ::= { cucsVnicFcOEIfEntry 16 }

cucsVnicFcOEIfOperPrimaryVnetDn OBJECT-TYPE
    SYNTAX       SnmpAdminString
    MAX-ACCESS   read-only
    STATUS       current
    DESCRIPTION
        "Cisco UCS vnic:FcOEIf:operPrimaryVnetDn managed object property"
    ::= { cucsVnicFcOEIfEntry 17 }

cucsVnicFcOEIfOperPrimaryVnetName OBJECT-TYPE
    SYNTAX       SnmpAdminString
    MAX-ACCESS   read-only
    STATUS       current
    DESCRIPTION
        "Cisco UCS vnic:FcOEIf:operPrimaryVnetName managed
        object property"
    ::= { cucsVnicFcOEIfEntry 18 }

cucsVnicIPv4DhcpTable OBJECT-TYPE
    SYNTAX           SEQUENCE OF CucsVnicIPv4DhcpEntry
    MAX-ACCESS       not-accessible
    STATUS           current
    DESCRIPTION
        "Cisco UCS vnic:IPv4Dhcp managed object table"
    ::= { cucsVnicObjects 16 }

cucsVnicIPv4DhcpEntry OBJECT-TYPE
    SYNTAX           CucsVnicIPv4DhcpEntry
    MAX-ACCESS       not-accessible
    STATUS           current
    DESCRIPTION
        "Entry for the cucsVnicIPv4DhcpTable table."
    INDEX { cucsVnicIPv4DhcpInstanceId }
    ::= { cucsVnicIPv4DhcpTable 1 }

CucsVnicIPv4DhcpEntry ::= SEQUENCE {
    cucsVnicIPv4DhcpInstanceId                                       CucsManagedObjectId,
    cucsVnicIPv4DhcpDn                                               CucsManagedObjectDn,
    cucsVnicIPv4DhcpRn                                               SnmpAdminString,
    cucsVnicIPv4DhcpAddr                                             InetAddressIPv4,
    cucsVnicIPv4DhcpDefGw                                            InetAddressIPv4,
    cucsVnicIPv4DhcpSubnet                                           InetAddressIPv4
}

cucsVnicIPv4DhcpInstanceId OBJECT-TYPE
    SYNTAX       CucsManagedObjectId
    MAX-ACCESS   not-accessible
    STATUS       current
    DESCRIPTION
        "Instance identifier of the managed object."
    ::= { cucsVnicIPv4DhcpEntry 1 }

cucsVnicIPv4DhcpDn OBJECT-TYPE
    SYNTAX       CucsManagedObjectDn
    MAX-ACCESS   read-only
    STATUS       current
    DESCRIPTION
        "Cisco UCS vnic:IPv4Dhcp:dn managed object property"
    ::= { cucsVnicIPv4DhcpEntry 2 }

cucsVnicIPv4DhcpRn OBJECT-TYPE
    SYNTAX       SnmpAdminString
    MAX-ACCESS   read-only
    STATUS       current
    DESCRIPTION
        "Cisco UCS vnic:IPv4Dhcp:rn managed object property"
    ::= { cucsVnicIPv4DhcpEntry 3 }

cucsVnicIPv4DhcpAddr OBJECT-TYPE
    SYNTAX       InetAddressIPv4
    MAX-ACCESS   read-only
    STATUS       current
    DESCRIPTION
        "Cisco UCS vnic:IPv4Dhcp:addr managed object property"
    ::= { cucsVnicIPv4DhcpEntry 4 }

cucsVnicIPv4DhcpDefGw OBJECT-TYPE
    SYNTAX       InetAddressIPv4
    MAX-ACCESS   read-only
    STATUS       current
    DESCRIPTION
        "Cisco UCS vnic:IPv4Dhcp:defGw managed object property"
    ::= { cucsVnicIPv4DhcpEntry 5 }

cucsVnicIPv4DhcpSubnet OBJECT-TYPE
    SYNTAX       InetAddressIPv4
    MAX-ACCESS   read-only
    STATUS       current
    DESCRIPTION
        "Cisco UCS vnic:IPv4Dhcp:subnet managed object property"
    ::= { cucsVnicIPv4DhcpEntry 6 }

cucsVnicIPv4DnsTable OBJECT-TYPE
    SYNTAX           SEQUENCE OF CucsVnicIPv4DnsEntry
    MAX-ACCESS       not-accessible
    STATUS           current
    DESCRIPTION
        "Cisco UCS vnic:IPv4Dns managed object table"
    ::= { cucsVnicObjects 17 }

cucsVnicIPv4DnsEntry OBJECT-TYPE
    SYNTAX           CucsVnicIPv4DnsEntry
    MAX-ACCESS       not-accessible
    STATUS           current
    DESCRIPTION
        "Entry for the cucsVnicIPv4DnsTable table."
    INDEX { cucsVnicIPv4DnsInstanceId }
    ::= { cucsVnicIPv4DnsTable 1 }

CucsVnicIPv4DnsEntry ::= SEQUENCE {
    cucsVnicIPv4DnsInstanceId                                        CucsManagedObjectId,
    cucsVnicIPv4DnsDn                                                CucsManagedObjectDn,
    cucsVnicIPv4DnsRn                                                SnmpAdminString,
    cucsVnicIPv4DnsAddr                                              InetAddressIPv4,
    cucsVnicIPv4DnsDefGw                                             InetAddressIPv4,
    cucsVnicIPv4DnsPref                                              CucsVnicIPv4DnsPref,
    cucsVnicIPv4DnsSubnet                                            InetAddressIPv4
}

cucsVnicIPv4DnsInstanceId OBJECT-TYPE
    SYNTAX       CucsManagedObjectId
    MAX-ACCESS   not-accessible
    STATUS       current
    DESCRIPTION
        "Instance identifier of the managed object."
    ::= { cucsVnicIPv4DnsEntry 1 }

cucsVnicIPv4DnsDn OBJECT-TYPE
    SYNTAX       CucsManagedObjectDn
    MAX-ACCESS   read-only
    STATUS       current
    DESCRIPTION
        "Cisco UCS vnic:IPv4Dns:dn managed object property"
    ::= { cucsVnicIPv4DnsEntry 2 }

cucsVnicIPv4DnsRn OBJECT-TYPE
    SYNTAX       SnmpAdminString
    MAX-ACCESS   read-only
    STATUS       current
    DESCRIPTION
        "Cisco UCS vnic:IPv4Dns:rn managed object property"
    ::= { cucsVnicIPv4DnsEntry 3 }

cucsVnicIPv4DnsAddr OBJECT-TYPE
    SYNTAX       InetAddressIPv4
    MAX-ACCESS   read-only
    STATUS       current
    DESCRIPTION
        "Cisco UCS vnic:IPv4Dns:addr managed object property"
    ::= { cucsVnicIPv4DnsEntry 4 }

cucsVnicIPv4DnsDefGw OBJECT-TYPE
    SYNTAX       InetAddressIPv4
    MAX-ACCESS   read-only
    STATUS       current
    DESCRIPTION
        "Cisco UCS vnic:IPv4Dns:defGw managed object property"
    ::= { cucsVnicIPv4DnsEntry 5 }

cucsVnicIPv4DnsPref OBJECT-TYPE
    SYNTAX       CucsVnicIPv4DnsPref
    MAX-ACCESS   read-only
    STATUS       current
    DESCRIPTION
        "Cisco UCS vnic:IPv4Dns:pref managed object property"
    ::= { cucsVnicIPv4DnsEntry 6 }

cucsVnicIPv4DnsSubnet OBJECT-TYPE
    SYNTAX       InetAddressIPv4
    MAX-ACCESS   read-only
    STATUS       current
    DESCRIPTION
        "Cisco UCS vnic:IPv4Dns:subnet managed object property"
    ::= { cucsVnicIPv4DnsEntry 7 }

cucsVnicIPv4IfTable OBJECT-TYPE
    SYNTAX           SEQUENCE OF CucsVnicIPv4IfEntry
    MAX-ACCESS       not-accessible
    STATUS           current
    DESCRIPTION
        "Cisco UCS vnic:IPv4If managed object table"
    ::= { cucsVnicObjects 18 }

cucsVnicIPv4IfEntry OBJECT-TYPE
    SYNTAX           CucsVnicIPv4IfEntry
    MAX-ACCESS       not-accessible
    STATUS           current
    DESCRIPTION
        "Entry for the cucsVnicIPv4IfTable table."
    INDEX { cucsVnicIPv4IfInstanceId }
    ::= { cucsVnicIPv4IfTable 1 }

CucsVnicIPv4IfEntry ::= SEQUENCE {
    cucsVnicIPv4IfInstanceId                                         CucsManagedObjectId,
    cucsVnicIPv4IfDn                                                 CucsManagedObjectDn,
    cucsVnicIPv4IfRn                                                 SnmpAdminString,
    cucsVnicIPv4IfAddr                                               InetAddressIPv4,
    cucsVnicIPv4IfName                                               SnmpAdminString,
    cucsVnicIPv4IfOperState                                          CucsVnicIfOperState,
    cucsVnicIPv4IfOwner                                              CucsVnicConnectionOwner,
    cucsVnicIPv4IfSwitchId                                           CucsNetworkSwitchId,
    cucsVnicIPv4IfType                                               CucsVnicConnectionType,
    cucsVnicIPv4IfVnet                                               Gauge32,
    cucsVnicIPv4IfConfigQualifier                                    CucsVnicConfigIssues,
    cucsVnicIPv4IfOperVnetDn                                         SnmpAdminString,
    cucsVnicIPv4IfOperVnetName                                       SnmpAdminString,
    cucsVnicIPv4IfPubNwId                                            Gauge32,
    cucsVnicIPv4IfSharing                                            CucsFabricVlanSharingType,
    cucsVnicIPv4IfPropAcl                                            Unsigned64,
    cucsVnicIPv4IfOperPrimaryVnetDn                                  SnmpAdminString,
    cucsVnicIPv4IfOperPrimaryVnetName                                SnmpAdminString
}

cucsVnicIPv4IfInstanceId OBJECT-TYPE
    SYNTAX       CucsManagedObjectId
    MAX-ACCESS   not-accessible
    STATUS       current
    DESCRIPTION
        "Instance identifier of the managed object."
    ::= { cucsVnicIPv4IfEntry 1 }

cucsVnicIPv4IfDn OBJECT-TYPE
    SYNTAX       CucsManagedObjectDn
    MAX-ACCESS   read-only
    STATUS       current
    DESCRIPTION
        "Cisco UCS vnic:IPv4If:dn managed object property"
    ::= { cucsVnicIPv4IfEntry 2 }

cucsVnicIPv4IfRn OBJECT-TYPE
    SYNTAX       SnmpAdminString
    MAX-ACCESS   read-only
    STATUS       current
    DESCRIPTION
        "Cisco UCS vnic:IPv4If:rn managed object property"
    ::= { cucsVnicIPv4IfEntry 3 }

cucsVnicIPv4IfAddr OBJECT-TYPE
    SYNTAX       InetAddressIPv4
    MAX-ACCESS   read-only
    STATUS       current
    DESCRIPTION
        "Cisco UCS vnic:IPv4If:addr managed object property"
    ::= { cucsVnicIPv4IfEntry 4 }

cucsVnicIPv4IfName OBJECT-TYPE
    SYNTAX       SnmpAdminString
    MAX-ACCESS   read-only
    STATUS       current
    DESCRIPTION
        "Cisco UCS vnic:IPv4If:name managed object property"
    ::= { cucsVnicIPv4IfEntry 5 }

cucsVnicIPv4IfOperState OBJECT-TYPE
    SYNTAX       CucsVnicIfOperState
    MAX-ACCESS   read-only
    STATUS       current
    DESCRIPTION
        "Cisco UCS vnic:IPv4If:operState managed object property"
    ::= { cucsVnicIPv4IfEntry 6 }

cucsVnicIPv4IfOwner OBJECT-TYPE
    SYNTAX       CucsVnicConnectionOwner
    MAX-ACCESS   read-only
    STATUS       current
    DESCRIPTION
        "Cisco UCS vnic:IPv4If:owner managed object property"
    ::= { cucsVnicIPv4IfEntry 7 }

cucsVnicIPv4IfSwitchId OBJECT-TYPE
    SYNTAX       CucsNetworkSwitchId
    MAX-ACCESS   read-only
    STATUS       current
    DESCRIPTION
        "Cisco UCS vnic:IPv4If:switchId managed object property"
    ::= { cucsVnicIPv4IfEntry 8 }

cucsVnicIPv4IfType OBJECT-TYPE
    SYNTAX       CucsVnicConnectionType
    MAX-ACCESS   read-only
    STATUS       current
    DESCRIPTION
        "Cisco UCS vnic:IPv4If:type managed object property"
    ::= { cucsVnicIPv4IfEntry 9 }

cucsVnicIPv4IfVnet OBJECT-TYPE
    SYNTAX       Gauge32
    MAX-ACCESS   read-only
    STATUS       current
    DESCRIPTION
        "Cisco UCS vnic:IPv4If:vnet managed object property"
    ::= { cucsVnicIPv4IfEntry 10 }

cucsVnicIPv4IfConfigQualifier OBJECT-TYPE
    SYNTAX       CucsVnicConfigIssues
    MAX-ACCESS   read-only
    STATUS       current
    DESCRIPTION
        "Cisco UCS vnic:IPv4If:configQualifier managed object property"
    ::= { cucsVnicIPv4IfEntry 11 }

cucsVnicIPv4IfOperVnetDn OBJECT-TYPE
    SYNTAX       SnmpAdminString
    MAX-ACCESS   read-only
    STATUS       current
    DESCRIPTION
        "Cisco UCS vnic:IPv4If:operVnetDn managed object property"
    ::= { cucsVnicIPv4IfEntry 13 }

cucsVnicIPv4IfOperVnetName OBJECT-TYPE
    SYNTAX       SnmpAdminString
    MAX-ACCESS   read-only
    STATUS       current
    DESCRIPTION
        "Cisco UCS vnic:IPv4If:operVnetName managed object property"
    ::= { cucsVnicIPv4IfEntry 14 }

cucsVnicIPv4IfPubNwId OBJECT-TYPE
    SYNTAX       Gauge32
    MAX-ACCESS   read-only
    STATUS       current
    DESCRIPTION
        "Cisco UCS vnic:IPv4If:pubNwId managed object property"
    ::= { cucsVnicIPv4IfEntry 15 }

cucsVnicIPv4IfSharing OBJECT-TYPE
    SYNTAX       CucsFabricVlanSharingType
    MAX-ACCESS   read-only
    STATUS       current
    DESCRIPTION
        "Cisco UCS vnic:IPv4If:sharing managed object property"
    ::= { cucsVnicIPv4IfEntry 16 }

cucsVnicIPv4IfPropAcl OBJECT-TYPE
    SYNTAX       Unsigned64
    MAX-ACCESS   read-only
    STATUS       current
    DESCRIPTION
        "Cisco UCS vnic:IPv4If:propAcl managed object property"
    ::= { cucsVnicIPv4IfEntry 17 }

cucsVnicIPv4IfOperPrimaryVnetDn OBJECT-TYPE
    SYNTAX       SnmpAdminString
    MAX-ACCESS   read-only
    STATUS       current
    DESCRIPTION
        "Cisco UCS vnic:IPv4If:operPrimaryVnetDn managed object property"
    ::= { cucsVnicIPv4IfEntry 18 }

cucsVnicIPv4IfOperPrimaryVnetName OBJECT-TYPE
    SYNTAX       SnmpAdminString
    MAX-ACCESS   read-only
    STATUS       current
    DESCRIPTION
        "Cisco UCS vnic:IPv4If:operPrimaryVnetName managed
        object property"
    ::= { cucsVnicIPv4IfEntry 19 }

cucsVnicIPv4IscsiAddrTable OBJECT-TYPE
    SYNTAX           SEQUENCE OF CucsVnicIPv4IscsiAddrEntry
    MAX-ACCESS       not-accessible
    STATUS           current
    DESCRIPTION
        "Cisco UCS vnic:IPv4IscsiAddr managed object table"
    ::= { cucsVnicObjects 36 }

cucsVnicIPv4IscsiAddrEntry OBJECT-TYPE
    SYNTAX           CucsVnicIPv4IscsiAddrEntry
    MAX-ACCESS       not-accessible
    STATUS           current
    DESCRIPTION
        "Entry for the cucsVnicIPv4IscsiAddrTable table."
    INDEX { cucsVnicIPv4IscsiAddrInstanceId }
    ::= { cucsVnicIPv4IscsiAddrTable 1 }

CucsVnicIPv4IscsiAddrEntry ::= SEQUENCE {
    cucsVnicIPv4IscsiAddrInstanceId                                  CucsManagedObjectId,
    cucsVnicIPv4IscsiAddrDn                                          CucsManagedObjectDn,
    cucsVnicIPv4IscsiAddrRn                                          SnmpAdminString,
    cucsVnicIPv4IscsiAddrAddr                                        InetAddressIPv4,
    cucsVnicIPv4IscsiAddrDefGw                                       InetAddressIPv4,
    cucsVnicIPv4IscsiAddrPrimDns                                     InetAddressIPv4,
    cucsVnicIPv4IscsiAddrSecDns                                      InetAddressIPv4,
    cucsVnicIPv4IscsiAddrSubnet                                      InetAddressIPv4
}

cucsVnicIPv4IscsiAddrInstanceId OBJECT-TYPE
    SYNTAX       CucsManagedObjectId
    MAX-ACCESS   not-accessible
    STATUS       current
    DESCRIPTION
        "Instance identifier of the managed object."
    ::= { cucsVnicIPv4IscsiAddrEntry 1 }

cucsVnicIPv4IscsiAddrDn OBJECT-TYPE
    SYNTAX       CucsManagedObjectDn
    MAX-ACCESS   read-only
    STATUS       current
    DESCRIPTION
        "Cisco UCS vnic:IPv4IscsiAddr:dn managed object property"
    ::= { cucsVnicIPv4IscsiAddrEntry 2 }

cucsVnicIPv4IscsiAddrRn OBJECT-TYPE
    SYNTAX       SnmpAdminString
    MAX-ACCESS   read-only
    STATUS       current
    DESCRIPTION
        "Cisco UCS vnic:IPv4IscsiAddr:rn managed object property"
    ::= { cucsVnicIPv4IscsiAddrEntry 3 }

cucsVnicIPv4IscsiAddrAddr OBJECT-TYPE
    SYNTAX       InetAddressIPv4
    MAX-ACCESS   read-only
    STATUS       current
    DESCRIPTION
        "Cisco UCS vnic:IPv4IscsiAddr:addr managed object property"
    ::= { cucsVnicIPv4IscsiAddrEntry 4 }

cucsVnicIPv4IscsiAddrDefGw OBJECT-TYPE
    SYNTAX       InetAddressIPv4
    MAX-ACCESS   read-only
    STATUS       current
    DESCRIPTION
        "Cisco UCS vnic:IPv4IscsiAddr:defGw managed object property"
    ::= { cucsVnicIPv4IscsiAddrEntry 5 }

cucsVnicIPv4IscsiAddrPrimDns OBJECT-TYPE
    SYNTAX       InetAddressIPv4
    MAX-ACCESS   read-only
    STATUS       current
    DESCRIPTION
        "Cisco UCS vnic:IPv4IscsiAddr:primDns managed object property"
    ::= { cucsVnicIPv4IscsiAddrEntry 6 }

cucsVnicIPv4IscsiAddrSecDns OBJECT-TYPE
    SYNTAX       InetAddressIPv4
    MAX-ACCESS   read-only
    STATUS       current
    DESCRIPTION
        "Cisco UCS vnic:IPv4IscsiAddr:secDns managed object property"
    ::= { cucsVnicIPv4IscsiAddrEntry 7 }

cucsVnicIPv4IscsiAddrSubnet OBJECT-TYPE
    SYNTAX       InetAddressIPv4
    MAX-ACCESS   read-only
    STATUS       current
    DESCRIPTION
        "Cisco UCS vnic:IPv4IscsiAddr:subnet managed object property"
    ::= { cucsVnicIPv4IscsiAddrEntry 8 }

cucsVnicIPv4PooledIscsiAddrTable OBJECT-TYPE
    SYNTAX           SEQUENCE OF CucsVnicIPv4PooledIscsiAddrEntry
    MAX-ACCESS       not-accessible
    STATUS           current
    DESCRIPTION
        "Cisco UCS vnic:IPv4PooledIscsiAddr managed object table"
    ::= { cucsVnicObjects 37 }

cucsVnicIPv4PooledIscsiAddrEntry OBJECT-TYPE
    SYNTAX           CucsVnicIPv4PooledIscsiAddrEntry
    MAX-ACCESS       not-accessible
    STATUS           current
    DESCRIPTION
        "Entry for the cucsVnicIPv4PooledIscsiAddrTable table."
    INDEX { cucsVnicIPv4PooledIscsiAddrInstanceId }
    ::= { cucsVnicIPv4PooledIscsiAddrTable 1 }

CucsVnicIPv4PooledIscsiAddrEntry ::= SEQUENCE {
    cucsVnicIPv4PooledIscsiAddrInstanceId                            CucsManagedObjectId,
    cucsVnicIPv4PooledIscsiAddrDn                                    CucsManagedObjectDn,
    cucsVnicIPv4PooledIscsiAddrRn                                    SnmpAdminString,
    cucsVnicIPv4PooledIscsiAddrAddr                                  InetAddressIPv4,
    cucsVnicIPv4PooledIscsiAddrDefGw                                 InetAddressIPv4,
    cucsVnicIPv4PooledIscsiAddrIdentPoolName                         SnmpAdminString,
    cucsVnicIPv4PooledIscsiAddrOperIdentPoolName                     SnmpAdminString,
    cucsVnicIPv4PooledIscsiAddrPrimDns                               InetAddressIPv4,
    cucsVnicIPv4PooledIscsiAddrSecDns                                InetAddressIPv4,
    cucsVnicIPv4PooledIscsiAddrSubnet                                InetAddressIPv4
}

cucsVnicIPv4PooledIscsiAddrInstanceId OBJECT-TYPE
    SYNTAX       CucsManagedObjectId
    MAX-ACCESS   not-accessible
    STATUS       current
    DESCRIPTION
        "Instance identifier of the managed object."
    ::= { cucsVnicIPv4PooledIscsiAddrEntry 1 }

cucsVnicIPv4PooledIscsiAddrDn OBJECT-TYPE
    SYNTAX       CucsManagedObjectDn
    MAX-ACCESS   read-only
    STATUS       current
    DESCRIPTION
        "Cisco UCS vnic:IPv4PooledIscsiAddr:dn managed object property"
    ::= { cucsVnicIPv4PooledIscsiAddrEntry 2 }

cucsVnicIPv4PooledIscsiAddrRn OBJECT-TYPE
    SYNTAX       SnmpAdminString
    MAX-ACCESS   read-only
    STATUS       current
    DESCRIPTION
        "Cisco UCS vnic:IPv4PooledIscsiAddr:rn managed object property"
    ::= { cucsVnicIPv4PooledIscsiAddrEntry 3 }

cucsVnicIPv4PooledIscsiAddrAddr OBJECT-TYPE
    SYNTAX       InetAddressIPv4
    MAX-ACCESS   read-only
    STATUS       current
    DESCRIPTION
        "Cisco UCS vnic:IPv4PooledIscsiAddr:addr managed object property"
    ::= { cucsVnicIPv4PooledIscsiAddrEntry 4 }

cucsVnicIPv4PooledIscsiAddrDefGw OBJECT-TYPE
    SYNTAX       InetAddressIPv4
    MAX-ACCESS   read-only
    STATUS       current
    DESCRIPTION
        "Cisco UCS vnic:IPv4PooledIscsiAddr:defGw managed object property"
    ::= { cucsVnicIPv4PooledIscsiAddrEntry 5 }

cucsVnicIPv4PooledIscsiAddrIdentPoolName OBJECT-TYPE
    SYNTAX       SnmpAdminString
    MAX-ACCESS   read-only
    STATUS       current
    DESCRIPTION
        "Cisco UCS vnic:IPv4PooledIscsiAddr:identPoolName
        managed object property"
    ::= { cucsVnicIPv4PooledIscsiAddrEntry 6 }

cucsVnicIPv4PooledIscsiAddrOperIdentPoolName OBJECT-TYPE
    SYNTAX       SnmpAdminString
    MAX-ACCESS   read-only
    STATUS       current
    DESCRIPTION
        "Cisco UCS vnic:IPv4PooledIscsiAddr:operIdentPoolName
        managed object property"
    ::= { cucsVnicIPv4PooledIscsiAddrEntry 7 }

cucsVnicIPv4PooledIscsiAddrPrimDns OBJECT-TYPE
    SYNTAX       InetAddressIPv4
    MAX-ACCESS   read-only
    STATUS       current
    DESCRIPTION
        "Cisco UCS vnic:IPv4PooledIscsiAddr:primDns managed
        object property"
    ::= { cucsVnicIPv4PooledIscsiAddrEntry 8 }

cucsVnicIPv4PooledIscsiAddrSecDns OBJECT-TYPE
    SYNTAX       InetAddressIPv4
    MAX-ACCESS   read-only
    STATUS       current
    DESCRIPTION
        "Cisco UCS vnic:IPv4PooledIscsiAddr:secDns managed
        object property"
    ::= { cucsVnicIPv4PooledIscsiAddrEntry 9 }

cucsVnicIPv4PooledIscsiAddrSubnet OBJECT-TYPE
    SYNTAX       InetAddressIPv4
    MAX-ACCESS   read-only
    STATUS       current
    DESCRIPTION
        "Cisco UCS vnic:IPv4PooledIscsiAddr:subnet managed
        object property"
    ::= { cucsVnicIPv4PooledIscsiAddrEntry 10 }

cucsVnicIPv4StaticRouteTable OBJECT-TYPE
    SYNTAX           SEQUENCE OF CucsVnicIPv4StaticRouteEntry
    MAX-ACCESS       not-accessible
    STATUS           current
    DESCRIPTION
        "Cisco UCS vnic:IPv4StaticRoute managed object table"
    ::= { cucsVnicObjects 19 }

cucsVnicIPv4StaticRouteEntry OBJECT-TYPE
    SYNTAX           CucsVnicIPv4StaticRouteEntry
    MAX-ACCESS       not-accessible
    STATUS           current
    DESCRIPTION
        "Entry for the cucsVnicIPv4StaticRouteTable table."
    INDEX { cucsVnicIPv4StaticRouteInstanceId }
    ::= { cucsVnicIPv4StaticRouteTable 1 }

CucsVnicIPv4StaticRouteEntry ::= SEQUENCE {
    cucsVnicIPv4StaticRouteInstanceId                                CucsManagedObjectId,
    cucsVnicIPv4StaticRouteDn                                        CucsManagedObjectDn,
    cucsVnicIPv4StaticRouteRn                                        SnmpAdminString,
    cucsVnicIPv4StaticRouteAddr                                      InetAddressIPv4,
    cucsVnicIPv4StaticRouteDefGw                                     InetAddressIPv4,
    cucsVnicIPv4StaticRouteGwAddr                                    InetAddressIPv4,
    cucsVnicIPv4StaticRouteGwSubnet                                  InetAddressIPv4,
    cucsVnicIPv4StaticRouteSubnet                                    InetAddressIPv4
}

cucsVnicIPv4StaticRouteInstanceId OBJECT-TYPE
    SYNTAX       CucsManagedObjectId
    MAX-ACCESS   not-accessible
    STATUS       current
    DESCRIPTION
        "Instance identifier of the managed object."
    ::= { cucsVnicIPv4StaticRouteEntry 1 }

cucsVnicIPv4StaticRouteDn OBJECT-TYPE
    SYNTAX       CucsManagedObjectDn
    MAX-ACCESS   read-only
    STATUS       current
    DESCRIPTION
        "Cisco UCS vnic:IPv4StaticRoute:dn managed object property"
    ::= { cucsVnicIPv4StaticRouteEntry 2 }

cucsVnicIPv4StaticRouteRn OBJECT-TYPE
    SYNTAX       SnmpAdminString
    MAX-ACCESS   read-only
    STATUS       current
    DESCRIPTION
        "Cisco UCS vnic:IPv4StaticRoute:rn managed object property"
    ::= { cucsVnicIPv4StaticRouteEntry 3 }

cucsVnicIPv4StaticRouteAddr OBJECT-TYPE
    SYNTAX       InetAddressIPv4
    MAX-ACCESS   read-only
    STATUS       current
    DESCRIPTION
        "Cisco UCS vnic:IPv4StaticRoute:addr managed object property"
    ::= { cucsVnicIPv4StaticRouteEntry 4 }

cucsVnicIPv4StaticRouteDefGw OBJECT-TYPE
    SYNTAX       InetAddressIPv4
    MAX-ACCESS   read-only
    STATUS       current
    DESCRIPTION
        "Cisco UCS vnic:IPv4StaticRoute:defGw managed object property"
    ::= { cucsVnicIPv4StaticRouteEntry 5 }

cucsVnicIPv4StaticRouteGwAddr OBJECT-TYPE
    SYNTAX       InetAddressIPv4
    MAX-ACCESS   read-only
    STATUS       current
    DESCRIPTION
        "Cisco UCS vnic:IPv4StaticRoute:gwAddr managed object property"
    ::= { cucsVnicIPv4StaticRouteEntry 6 }

cucsVnicIPv4StaticRouteGwSubnet OBJECT-TYPE
    SYNTAX       InetAddressIPv4
    MAX-ACCESS   read-only
    STATUS       current
    DESCRIPTION
        "Cisco UCS vnic:IPv4StaticRoute:gwSubnet managed object property"
    ::= { cucsVnicIPv4StaticRouteEntry 7 }

cucsVnicIPv4StaticRouteSubnet OBJECT-TYPE
    SYNTAX       InetAddressIPv4
    MAX-ACCESS   read-only
    STATUS       current
    DESCRIPTION
        "Cisco UCS vnic:IPv4StaticRoute:subnet managed object property"
    ::= { cucsVnicIPv4StaticRouteEntry 8 }

cucsVnicIPv6IfTable OBJECT-TYPE
    SYNTAX           SEQUENCE OF CucsVnicIPv6IfEntry
    MAX-ACCESS       not-accessible
    STATUS           current
    DESCRIPTION
        "Cisco UCS vnic:IPv6If managed object table"
    ::= { cucsVnicObjects 75 }

cucsVnicIPv6IfEntry OBJECT-TYPE
    SYNTAX           CucsVnicIPv6IfEntry
    MAX-ACCESS       not-accessible
    STATUS           current
    DESCRIPTION
        "Entry for the cucsVnicIPv6IfTable table."
    INDEX { cucsVnicIPv6IfInstanceId }
    ::= { cucsVnicIPv6IfTable 1 }

CucsVnicIPv6IfEntry ::= SEQUENCE {
    cucsVnicIPv6IfInstanceId                                         CucsManagedObjectId,
    cucsVnicIPv6IfDn                                                 CucsManagedObjectDn,
    cucsVnicIPv6IfRn                                                 SnmpAdminString,
    cucsVnicIPv6IfAddr                                               InetAddressIPv6,
    cucsVnicIPv6IfConfigQualifier                                    CucsVnicConfigIssues,
    cucsVnicIPv6IfName                                               SnmpAdminString,
    cucsVnicIPv6IfOperState                                          CucsVnicIfOperState,
    cucsVnicIPv6IfOperVnetDn                                         SnmpAdminString,
    cucsVnicIPv6IfOperVnetName                                       SnmpAdminString,
    cucsVnicIPv6IfOwner                                              CucsVnicConnectionOwner,
    cucsVnicIPv6IfPubNwId                                            Gauge32,
    cucsVnicIPv6IfSharing                                            CucsFabricVlanSharingType,
    cucsVnicIPv6IfSwitchId                                           CucsNetworkSwitchId,
    cucsVnicIPv6IfType                                               CucsVnicConnectionType,
    cucsVnicIPv6IfVnet                                               Gauge32,
    cucsVnicIPv6IfOperPrimaryVnetDn                                  SnmpAdminString,
    cucsVnicIPv6IfOperPrimaryVnetName                                SnmpAdminString
}

cucsVnicIPv6IfInstanceId OBJECT-TYPE
    SYNTAX       CucsManagedObjectId
    MAX-ACCESS   not-accessible
    STATUS       current
    DESCRIPTION
        "Instance identifier of the managed object."
    ::= { cucsVnicIPv6IfEntry 1 }

cucsVnicIPv6IfDn OBJECT-TYPE
    SYNTAX       CucsManagedObjectDn
    MAX-ACCESS   read-only
    STATUS       current
    DESCRIPTION
        "Cisco UCS vnic:IPv6If:dn managed object property"
    ::= { cucsVnicIPv6IfEntry 2 }

cucsVnicIPv6IfRn OBJECT-TYPE
    SYNTAX       SnmpAdminString
    MAX-ACCESS   read-only
    STATUS       current
    DESCRIPTION
        "Cisco UCS vnic:IPv6If:rn managed object property"
    ::= { cucsVnicIPv6IfEntry 3 }

cucsVnicIPv6IfAddr OBJECT-TYPE
    SYNTAX       InetAddressIPv6
    MAX-ACCESS   read-only
    STATUS       current
    DESCRIPTION
        "Cisco UCS vnic:IPv6If:addr managed object property"
    ::= { cucsVnicIPv6IfEntry 4 }

cucsVnicIPv6IfConfigQualifier OBJECT-TYPE
    SYNTAX       CucsVnicConfigIssues
    MAX-ACCESS   read-only
    STATUS       current
    DESCRIPTION
        "Cisco UCS vnic:IPv6If:configQualifier managed object property"
    ::= { cucsVnicIPv6IfEntry 5 }

cucsVnicIPv6IfName OBJECT-TYPE
    SYNTAX       SnmpAdminString
    MAX-ACCESS   read-only
    STATUS       current
    DESCRIPTION
        "Cisco UCS vnic:IPv6If:name managed object property"
    ::= { cucsVnicIPv6IfEntry 6 }

cucsVnicIPv6IfOperState OBJECT-TYPE
    SYNTAX       CucsVnicIfOperState
    MAX-ACCESS   read-only
    STATUS       current
    DESCRIPTION
        "Cisco UCS vnic:IPv6If:operState managed object property"
    ::= { cucsVnicIPv6IfEntry 7 }

cucsVnicIPv6IfOperVnetDn OBJECT-TYPE
    SYNTAX       SnmpAdminString
    MAX-ACCESS   read-only
    STATUS       current
    DESCRIPTION
        "Cisco UCS vnic:IPv6If:operVnetDn managed object property"
    ::= { cucsVnicIPv6IfEntry 8 }

cucsVnicIPv6IfOperVnetName OBJECT-TYPE
    SYNTAX       SnmpAdminString
    MAX-ACCESS   read-only
    STATUS       current
    DESCRIPTION
        "Cisco UCS vnic:IPv6If:operVnetName managed object property"
    ::= { cucsVnicIPv6IfEntry 9 }

cucsVnicIPv6IfOwner OBJECT-TYPE
    SYNTAX       CucsVnicConnectionOwner
    MAX-ACCESS   read-only
    STATUS       current
    DESCRIPTION
        "Cisco UCS vnic:IPv6If:owner managed object property"
    ::= { cucsVnicIPv6IfEntry 10 }

cucsVnicIPv6IfPubNwId OBJECT-TYPE
    SYNTAX       Gauge32
    MAX-ACCESS   read-only
    STATUS       current
    DESCRIPTION
        "Cisco UCS vnic:IPv6If:pubNwId managed object property"
    ::= { cucsVnicIPv6IfEntry 11 }

cucsVnicIPv6IfSharing OBJECT-TYPE
    SYNTAX       CucsFabricVlanSharingType
    MAX-ACCESS   read-only
    STATUS       current
    DESCRIPTION
        "Cisco UCS vnic:IPv6If:sharing managed object property"
    ::= { cucsVnicIPv6IfEntry 12 }

cucsVnicIPv6IfSwitchId OBJECT-TYPE
    SYNTAX       CucsNetworkSwitchId
    MAX-ACCESS   read-only
    STATUS       current
    DESCRIPTION
        "Cisco UCS vnic:IPv6If:switchId managed object property"
    ::= { cucsVnicIPv6IfEntry 13 }

cucsVnicIPv6IfType OBJECT-TYPE
    SYNTAX       CucsVnicConnectionType
    MAX-ACCESS   read-only
    STATUS       current
    DESCRIPTION
        "Cisco UCS vnic:IPv6If:type managed object property"
    ::= { cucsVnicIPv6IfEntry 14 }

cucsVnicIPv6IfVnet OBJECT-TYPE
    SYNTAX       Gauge32
    MAX-ACCESS   read-only
    STATUS       current
    DESCRIPTION
        "Cisco UCS vnic:IPv6If:vnet managed object property"
    ::= { cucsVnicIPv6IfEntry 15 }

cucsVnicIPv6IfOperPrimaryVnetDn OBJECT-TYPE
    SYNTAX       SnmpAdminString
    MAX-ACCESS   read-only
    STATUS       current
    DESCRIPTION
        "Cisco UCS vnic:IPv6If:operPrimaryVnetDn managed object property"
    ::= { cucsVnicIPv6IfEntry 16 }

cucsVnicIPv6IfOperPrimaryVnetName OBJECT-TYPE
    SYNTAX       SnmpAdminString
    MAX-ACCESS   read-only
    STATUS       current
    DESCRIPTION
        "Cisco UCS vnic:IPv6If:operPrimaryVnetName managed
        object property"
    ::= { cucsVnicIPv6IfEntry 17 }

cucsVnicIScsiTable OBJECT-TYPE
    SYNTAX           SEQUENCE OF CucsVnicIScsiEntry
    MAX-ACCESS       not-accessible
    STATUS           current
    DESCRIPTION
        "Cisco UCS vnic:IScsi managed object table"
    ::= { cucsVnicObjects 38 }

cucsVnicIScsiEntry OBJECT-TYPE
    SYNTAX           CucsVnicIScsiEntry
    MAX-ACCESS       not-accessible
    STATUS           current
    DESCRIPTION
        "Entry for the cucsVnicIScsiTable table."
    INDEX { cucsVnicIScsiInstanceId }
    ::= { cucsVnicIScsiTable 1 }

CucsVnicIScsiEntry ::= SEQUENCE {
    cucsVnicIScsiInstanceId                                          CucsManagedObjectId,
    cucsVnicIScsiDn                                                  CucsManagedObjectDn,
    cucsVnicIScsiRn                                                  SnmpAdminString,
    cucsVnicIScsiAdaptorProfileName                                  SnmpAdminString,
    cucsVnicIScsiAddr                                                MacAddress,
    cucsVnicIScsiAdminVcon                                           SnmpAdminString,
    cucsVnicIScsiAuthProfileName                                     SnmpAdminString,
    cucsVnicIScsiBootDev                                             CucsVnicVnicBootDev,
    cucsVnicIScsiConfigState                                         CucsLsConfigState,
    cucsVnicIScsiEquipmentDn                                         SnmpAdminString,
    cucsVnicIScsiEthEpDn                                             SnmpAdminString,
    cucsVnicIScsiExtIPState                                          CucsVnicExternalMgmtIPMode,
    cucsVnicIScsiFltAggr                                             Unsigned64,
    cucsVnicIScsiIdentPoolName                                       SnmpAdminString,
    cucsVnicIScsiInitiatorName                                       SnmpAdminString,
    cucsVnicIScsiInstType                                            CucsVnicInstantiation,
    cucsVnicIScsiIqnIdentPoolName                                    SnmpAdminString,
    cucsVnicIScsiName                                                SnmpAdminString,
    cucsVnicIScsiNwTemplName                                         SnmpAdminString,
    cucsVnicIScsiOperAdaptorProfileName                              SnmpAdminString,
    cucsVnicIScsiOperAuthProfileName                                 SnmpAdminString,
    cucsVnicIScsiOperIqnIdentPoolName                                SnmpAdminString,
    cucsVnicIScsiOperOrder                                           Gauge32,
    cucsVnicIScsiOperSpeed                                           Gauge32,
    cucsVnicIScsiOperStatsPolicyName                                 SnmpAdminString,
    cucsVnicIScsiOperVcon                                            SnmpAdminString,
    cucsVnicIScsiOrder                                               Gauge32,
    cucsVnicIScsiOwner                                               CucsVnicConnectionOwner,
    cucsVnicIScsiPinToGroupName                                      SnmpAdminString,
    cucsVnicIScsiQosPolicyName                                       SnmpAdminString,
    cucsVnicIScsiStatsPolicyName                                     SnmpAdminString,
    cucsVnicIScsiSwitchId                                            CucsNetworkSwitchId,
    cucsVnicIScsiType                                                CucsVnicConnectionType,
    cucsVnicIScsiVnicDefType                                         CucsVnicIScsiIfDefType,
    cucsVnicIScsiVnicName                                            SnmpAdminString,
    cucsVnicIScsiConfigQualifier                                     CucsVnicConfigIssues,
    cucsVnicIScsiInitNameSuffix                                      SnmpAdminString,
    cucsVnicIScsiOperIdentPoolName                                   SnmpAdminString,
    cucsVnicIScsiAdminHostPort                                       CucsFabricHostPortId,
    cucsVnicIScsiOperHostPort                                        CucsVnicVnicOperHostPort,
    cucsVnicIScsiPropAcl                                             Unsigned64,
    cucsVnicIScsiAdminCdnName                                        SnmpAdminString,
    cucsVnicIScsiOperCdnName                                         SnmpAdminString,
    cucsVnicIScsiCdnSource                                           CucsVnicCdnSource,
    cucsVnicIScsiCdnPropInSync                                       TruthValue
}

cucsVnicIScsiInstanceId OBJECT-TYPE
    SYNTAX       CucsManagedObjectId
    MAX-ACCESS   not-accessible
    STATUS       current
    DESCRIPTION
        "Instance identifier of the managed object."
    ::= { cucsVnicIScsiEntry 1 }

cucsVnicIScsiDn OBJECT-TYPE
    SYNTAX       CucsManagedObjectDn
    MAX-ACCESS   read-only
    STATUS       current
    DESCRIPTION
        "Cisco UCS vnic:IScsi:dn managed object property"
    ::= { cucsVnicIScsiEntry 2 }

cucsVnicIScsiRn OBJECT-TYPE
    SYNTAX       SnmpAdminString
    MAX-ACCESS   read-only
    STATUS       current
    DESCRIPTION
        "Cisco UCS vnic:IScsi:rn managed object property"
    ::= { cucsVnicIScsiEntry 3 }

cucsVnicIScsiAdaptorProfileName OBJECT-TYPE
    SYNTAX       SnmpAdminString
    MAX-ACCESS   read-only
    STATUS       current
    DESCRIPTION
        "Cisco UCS vnic:IScsi:adaptorProfileName managed object property"
    ::= { cucsVnicIScsiEntry 4 }

cucsVnicIScsiAddr OBJECT-TYPE
    SYNTAX       MacAddress
    MAX-ACCESS   read-only
    STATUS       current
    DESCRIPTION
        "Cisco UCS vnic:IScsi:addr managed object property"
    ::= { cucsVnicIScsiEntry 5 }

cucsVnicIScsiAdminVcon OBJECT-TYPE
    SYNTAX       SnmpAdminString
    MAX-ACCESS   read-only
    STATUS       current
    DESCRIPTION
        "Cisco UCS vnic:IScsi:adminVcon managed object property"
    ::= { cucsVnicIScsiEntry 6 }

cucsVnicIScsiAuthProfileName OBJECT-TYPE
    SYNTAX       SnmpAdminString
    MAX-ACCESS   read-only
    STATUS       current
    DESCRIPTION
        "Cisco UCS vnic:IScsi:authProfileName managed object property"
    ::= { cucsVnicIScsiEntry 7 }

cucsVnicIScsiBootDev OBJECT-TYPE
    SYNTAX       CucsVnicVnicBootDev
    MAX-ACCESS   read-only
    STATUS       current
    DESCRIPTION
        "Cisco UCS vnic:IScsi:bootDev managed object property"
    ::= { cucsVnicIScsiEntry 8 }

cucsVnicIScsiConfigState OBJECT-TYPE
    SYNTAX       CucsLsConfigState
    MAX-ACCESS   read-only
    STATUS       current
    DESCRIPTION
        "Cisco UCS vnic:IScsi:configState managed object property"
    ::= { cucsVnicIScsiEntry 10 }

cucsVnicIScsiEquipmentDn OBJECT-TYPE
    SYNTAX       SnmpAdminString
    MAX-ACCESS   read-only
    STATUS       current
    DESCRIPTION
        "Cisco UCS vnic:IScsi:equipmentDn managed object property"
    ::= { cucsVnicIScsiEntry 11 }

cucsVnicIScsiEthEpDn OBJECT-TYPE
    SYNTAX       SnmpAdminString
    MAX-ACCESS   read-only
    STATUS       current
    DESCRIPTION
        "Cisco UCS vnic:IScsi:ethEpDn managed object property"
    ::= { cucsVnicIScsiEntry 12 }

cucsVnicIScsiExtIPState OBJECT-TYPE
    SYNTAX       CucsVnicExternalMgmtIPMode
    MAX-ACCESS   read-only
    STATUS       current
    DESCRIPTION
        "Cisco UCS vnic:IScsi:extIPState managed object property"
    ::= { cucsVnicIScsiEntry 13 }

cucsVnicIScsiFltAggr OBJECT-TYPE
    SYNTAX       Unsigned64
    MAX-ACCESS   read-only
    STATUS       current
    DESCRIPTION
        "Cisco UCS vnic:IScsi:fltAggr managed object property"
    ::= { cucsVnicIScsiEntry 14 }

cucsVnicIScsiIdentPoolName OBJECT-TYPE
    SYNTAX       SnmpAdminString
    MAX-ACCESS   read-only
    STATUS       current
    DESCRIPTION
        "Cisco UCS vnic:IScsi:identPoolName managed object property"
    ::= { cucsVnicIScsiEntry 15 }

cucsVnicIScsiInitiatorName OBJECT-TYPE
    SYNTAX       SnmpAdminString
    MAX-ACCESS   read-only
    STATUS       current
    DESCRIPTION
        "Cisco UCS vnic:IScsi:initiatorName managed object property"
    ::= { cucsVnicIScsiEntry 16 }

cucsVnicIScsiInstType OBJECT-TYPE
    SYNTAX       CucsVnicInstantiation
    MAX-ACCESS   read-only
    STATUS       current
    DESCRIPTION
        "Cisco UCS vnic:IScsi:instType managed object property"
    ::= { cucsVnicIScsiEntry 17 }

cucsVnicIScsiIqnIdentPoolName OBJECT-TYPE
    SYNTAX       SnmpAdminString
    MAX-ACCESS   read-only
    STATUS       current
    DESCRIPTION
        "Cisco UCS vnic:IScsi:iqnIdentPoolName managed object property"
    ::= { cucsVnicIScsiEntry 18 }

cucsVnicIScsiName OBJECT-TYPE
    SYNTAX       SnmpAdminString
    MAX-ACCESS   read-only
    STATUS       current
    DESCRIPTION
        "Cisco UCS vnic:IScsi:name managed object property"
    ::= { cucsVnicIScsiEntry 19 }

cucsVnicIScsiNwTemplName OBJECT-TYPE
    SYNTAX       SnmpAdminString
    MAX-ACCESS   read-only
    STATUS       current
    DESCRIPTION
        "Cisco UCS vnic:IScsi:nwTemplName managed object property"
    ::= { cucsVnicIScsiEntry 20 }

cucsVnicIScsiOperAdaptorProfileName OBJECT-TYPE
    SYNTAX       SnmpAdminString
    MAX-ACCESS   read-only
    STATUS       current
    DESCRIPTION
        "Cisco UCS vnic:IScsi:operAdaptorProfileName managed
        object property"
    ::= { cucsVnicIScsiEntry 21 }

cucsVnicIScsiOperAuthProfileName OBJECT-TYPE
    SYNTAX       SnmpAdminString
    MAX-ACCESS   read-only
    STATUS       current
    DESCRIPTION
        "Cisco UCS vnic:IScsi:operAuthProfileName managed object property"
    ::= { cucsVnicIScsiEntry 22 }

cucsVnicIScsiOperIqnIdentPoolName OBJECT-TYPE
    SYNTAX       SnmpAdminString
    MAX-ACCESS   read-only
    STATUS       current
    DESCRIPTION
        "Cisco UCS vnic:IScsi:operIqnIdentPoolName managed
        object property"
    ::= { cucsVnicIScsiEntry 24 }

cucsVnicIScsiOperOrder OBJECT-TYPE
    SYNTAX       Gauge32
    MAX-ACCESS   read-only
    STATUS       current
    DESCRIPTION
        "Cisco UCS vnic:IScsi:operOrder managed object property"
    ::= { cucsVnicIScsiEntry 25 }

cucsVnicIScsiOperSpeed OBJECT-TYPE
    SYNTAX       Gauge32
    MAX-ACCESS   read-only
    STATUS       current
    DESCRIPTION
        "Cisco UCS vnic:IScsi:operSpeed managed object property"
    ::= { cucsVnicIScsiEntry 27 }

cucsVnicIScsiOperStatsPolicyName OBJECT-TYPE
    SYNTAX       SnmpAdminString
    MAX-ACCESS   read-only
    STATUS       current
    DESCRIPTION
        "Cisco UCS vnic:IScsi:operStatsPolicyName managed object property"
    ::= { cucsVnicIScsiEntry 28 }

cucsVnicIScsiOperVcon OBJECT-TYPE
    SYNTAX       SnmpAdminString
    MAX-ACCESS   read-only
    STATUS       current
    DESCRIPTION
        "Cisco UCS vnic:IScsi:operVcon managed object property"
    ::= { cucsVnicIScsiEntry 29 }

cucsVnicIScsiOrder OBJECT-TYPE
    SYNTAX       Gauge32
    MAX-ACCESS   read-only
    STATUS       current
    DESCRIPTION
        "Cisco UCS vnic:IScsi:order managed object property"
    ::= { cucsVnicIScsiEntry 30 }

cucsVnicIScsiOwner OBJECT-TYPE
    SYNTAX       CucsVnicConnectionOwner
    MAX-ACCESS   read-only
    STATUS       current
    DESCRIPTION
        "Cisco UCS vnic:IScsi:owner managed object property"
    ::= { cucsVnicIScsiEntry 31 }

cucsVnicIScsiPinToGroupName OBJECT-TYPE
    SYNTAX       SnmpAdminString
    MAX-ACCESS   read-only
    STATUS       current
    DESCRIPTION
        "Cisco UCS vnic:IScsi:pinToGroupName managed object property"
    ::= { cucsVnicIScsiEntry 32 }

cucsVnicIScsiQosPolicyName OBJECT-TYPE
    SYNTAX       SnmpAdminString
    MAX-ACCESS   read-only
    STATUS       current
    DESCRIPTION
        "Cisco UCS vnic:IScsi:qosPolicyName managed object property"
    ::= { cucsVnicIScsiEntry 33 }

cucsVnicIScsiStatsPolicyName OBJECT-TYPE
    SYNTAX       SnmpAdminString
    MAX-ACCESS   read-only
    STATUS       current
    DESCRIPTION
        "Cisco UCS vnic:IScsi:statsPolicyName managed object property"
    ::= { cucsVnicIScsiEntry 34 }

cucsVnicIScsiSwitchId OBJECT-TYPE
    SYNTAX       CucsNetworkSwitchId
    MAX-ACCESS   read-only
    STATUS       current
    DESCRIPTION
        "Cisco UCS vnic:IScsi:switchId managed object property"
    ::= { cucsVnicIScsiEntry 35 }

cucsVnicIScsiType OBJECT-TYPE
    SYNTAX       CucsVnicConnectionType
    MAX-ACCESS   read-only
    STATUS       current
    DESCRIPTION
        "Cisco UCS vnic:IScsi:type managed object property"
    ::= { cucsVnicIScsiEntry 36 }

cucsVnicIScsiVnicDefType OBJECT-TYPE
    SYNTAX       CucsVnicIScsiIfDefType
    MAX-ACCESS   read-only
    STATUS       current
    DESCRIPTION
        "Cisco UCS vnic:IScsi:vnicDefType managed object property"
    ::= { cucsVnicIScsiEntry 37 }

cucsVnicIScsiVnicName OBJECT-TYPE
    SYNTAX       SnmpAdminString
    MAX-ACCESS   read-only
    STATUS       current
    DESCRIPTION
        "Cisco UCS vnic:IScsi:vnicName managed object property"
    ::= { cucsVnicIScsiEntry 38 }

cucsVnicIScsiConfigQualifier OBJECT-TYPE
    SYNTAX       CucsVnicConfigIssues
    MAX-ACCESS   read-only
    STATUS       current
    DESCRIPTION
        "Cisco UCS vnic:IScsi:configQualifier managed object property"
    ::= { cucsVnicIScsiEntry 39 }

cucsVnicIScsiInitNameSuffix OBJECT-TYPE
    SYNTAX       SnmpAdminString
    MAX-ACCESS   read-only
    STATUS       current
    DESCRIPTION
        "Cisco UCS vnic:IScsi:initNameSuffix managed object property"
    ::= { cucsVnicIScsiEntry 40 }

cucsVnicIScsiOperIdentPoolName OBJECT-TYPE
    SYNTAX       SnmpAdminString
    MAX-ACCESS   read-only
    STATUS       current
    DESCRIPTION
        "Cisco UCS vnic:IScsi:operIdentPoolName managed object property"
    ::= { cucsVnicIScsiEntry 41 }

cucsVnicIScsiAdminHostPort OBJECT-TYPE
    SYNTAX       CucsFabricHostPortId
    MAX-ACCESS   read-only
    STATUS       current
    DESCRIPTION
        "Cisco UCS vnic:IScsi:adminHostPort managed object property"
    ::= { cucsVnicIScsiEntry 43 }

cucsVnicIScsiOperHostPort OBJECT-TYPE
    SYNTAX       CucsVnicVnicOperHostPort
    MAX-ACCESS   read-only
    STATUS       current
    DESCRIPTION
        "Cisco UCS vnic:IScsi:operHostPort managed object property"
    ::= { cucsVnicIScsiEntry 44 }

cucsVnicIScsiPropAcl OBJECT-TYPE
    SYNTAX       Unsigned64
    MAX-ACCESS   read-only
    STATUS       current
    DESCRIPTION
        "Cisco UCS vnic:IScsi:propAcl managed object property"
    ::= { cucsVnicIScsiEntry 45 }

cucsVnicIScsiAdminCdnName OBJECT-TYPE
    SYNTAX       SnmpAdminString
    MAX-ACCESS   read-only
    STATUS       current
    DESCRIPTION
        "Cisco UCS vnic:IScsi:adminCdnName managed object property"
    ::= { cucsVnicIScsiEntry 47 }

cucsVnicIScsiOperCdnName OBJECT-TYPE
    SYNTAX       SnmpAdminString
    MAX-ACCESS   read-only
    STATUS       current
    DESCRIPTION
        "Cisco UCS vnic:IScsi:operCdnName managed object property"
    ::= { cucsVnicIScsiEntry 48 }

cucsVnicIScsiCdnSource OBJECT-TYPE
    SYNTAX       CucsVnicCdnSource
    MAX-ACCESS   read-only
    STATUS       current
    DESCRIPTION
        "Cisco UCS vnic:IScsi:cdnSource managed object property"
    ::= { cucsVnicIScsiEntry 49 }

cucsVnicIScsiCdnPropInSync OBJECT-TYPE
    SYNTAX       TruthValue
    MAX-ACCESS   read-only
    STATUS       current
    DESCRIPTION
        "Cisco UCS vnic:IScsi:cdnPropInSync managed object property"
    ::= { cucsVnicIScsiEntry 50 }

cucsVnicIScsiAutoTargetIfTable OBJECT-TYPE
    SYNTAX           SEQUENCE OF CucsVnicIScsiAutoTargetIfEntry
    MAX-ACCESS       not-accessible
    STATUS           current
    DESCRIPTION
        "Cisco UCS vnic:IScsiAutoTargetIf managed object table"
    ::= { cucsVnicObjects 39 }

cucsVnicIScsiAutoTargetIfEntry OBJECT-TYPE
    SYNTAX           CucsVnicIScsiAutoTargetIfEntry
    MAX-ACCESS       not-accessible
    STATUS           current
    DESCRIPTION
        "Entry for the cucsVnicIScsiAutoTargetIfTable table."
    INDEX { cucsVnicIScsiAutoTargetIfInstanceId }
    ::= { cucsVnicIScsiAutoTargetIfTable 1 }

CucsVnicIScsiAutoTargetIfEntry ::= SEQUENCE {
    cucsVnicIScsiAutoTargetIfInstanceId                              CucsManagedObjectId,
    cucsVnicIScsiAutoTargetIfDn                                      CucsManagedObjectDn,
    cucsVnicIScsiAutoTargetIfRn                                      SnmpAdminString,
    cucsVnicIScsiAutoTargetIfDhcpVendorId                            SnmpAdminString
}

cucsVnicIScsiAutoTargetIfInstanceId OBJECT-TYPE
    SYNTAX       CucsManagedObjectId
    MAX-ACCESS   not-accessible
    STATUS       current
    DESCRIPTION
        "Instance identifier of the managed object."
    ::= { cucsVnicIScsiAutoTargetIfEntry 1 }

cucsVnicIScsiAutoTargetIfDn OBJECT-TYPE
    SYNTAX       CucsManagedObjectDn
    MAX-ACCESS   read-only
    STATUS       current
    DESCRIPTION
        "Cisco UCS vnic:IScsiAutoTargetIf:dn managed object property"
    ::= { cucsVnicIScsiAutoTargetIfEntry 2 }

cucsVnicIScsiAutoTargetIfRn OBJECT-TYPE
    SYNTAX       SnmpAdminString
    MAX-ACCESS   read-only
    STATUS       current
    DESCRIPTION
        "Cisco UCS vnic:IScsiAutoTargetIf:rn managed object property"
    ::= { cucsVnicIScsiAutoTargetIfEntry 3 }

cucsVnicIScsiAutoTargetIfDhcpVendorId OBJECT-TYPE
    SYNTAX       SnmpAdminString
    MAX-ACCESS   read-only
    STATUS       current
    DESCRIPTION
        "Cisco UCS vnic:IScsiAutoTargetIf:dhcpVendorId
        managed object property"
    ::= { cucsVnicIScsiAutoTargetIfEntry 4 }

cucsVnicIScsiBootParamsTable OBJECT-TYPE
    SYNTAX           SEQUENCE OF CucsVnicIScsiBootParamsEntry
    MAX-ACCESS       not-accessible
    STATUS           current
    DESCRIPTION
        "Cisco UCS vnic:IScsiBootParams managed object table"
    ::= { cucsVnicObjects 50 }

cucsVnicIScsiBootParamsEntry OBJECT-TYPE
    SYNTAX           CucsVnicIScsiBootParamsEntry
    MAX-ACCESS       not-accessible
    STATUS           current
    DESCRIPTION
        "Entry for the cucsVnicIScsiBootParamsTable table."
    INDEX { cucsVnicIScsiBootParamsInstanceId }
    ::= { cucsVnicIScsiBootParamsTable 1 }

CucsVnicIScsiBootParamsEntry ::= SEQUENCE {
    cucsVnicIScsiBootParamsInstanceId                                CucsManagedObjectId,
    cucsVnicIScsiBootParamsDn                                        CucsManagedObjectDn,
    cucsVnicIScsiBootParamsRn                                        SnmpAdminString,
    cucsVnicIScsiBootParamsDescr                                     SnmpAdminString,
    cucsVnicIScsiBootParamsIntId                                     SnmpAdminString,
    cucsVnicIScsiBootParamsName                                      SnmpAdminString,
    cucsVnicIScsiBootParamsPolicyLevel                               Gauge32,
    cucsVnicIScsiBootParamsPolicyOwner                               CucsPolicyPolicyOwner,
    cucsVnicIScsiBootParamsOwner                                     CucsLsOwner,
    cucsVnicIScsiBootParamsPropAcl                                   Unsigned64
}

cucsVnicIScsiBootParamsInstanceId OBJECT-TYPE
    SYNTAX       CucsManagedObjectId
    MAX-ACCESS   not-accessible
    STATUS       current
    DESCRIPTION
        "Instance identifier of the managed object."
    ::= { cucsVnicIScsiBootParamsEntry 1 }

cucsVnicIScsiBootParamsDn OBJECT-TYPE
    SYNTAX       CucsManagedObjectDn
    MAX-ACCESS   read-only
    STATUS       current
    DESCRIPTION
        "Cisco UCS vnic:IScsiBootParams:dn managed object property"
    ::= { cucsVnicIScsiBootParamsEntry 2 }

cucsVnicIScsiBootParamsRn OBJECT-TYPE
    SYNTAX       SnmpAdminString
    MAX-ACCESS   read-only
    STATUS       current
    DESCRIPTION
        "Cisco UCS vnic:IScsiBootParams:rn managed object property"
    ::= { cucsVnicIScsiBootParamsEntry 3 }

cucsVnicIScsiBootParamsDescr OBJECT-TYPE
    SYNTAX       SnmpAdminString
    MAX-ACCESS   read-only
    STATUS       current
    DESCRIPTION
        "Cisco UCS vnic:IScsiBootParams:descr managed object property"
    ::= { cucsVnicIScsiBootParamsEntry 4 }

cucsVnicIScsiBootParamsIntId OBJECT-TYPE
    SYNTAX       SnmpAdminString
    MAX-ACCESS   read-only
    STATUS       current
    DESCRIPTION
        "Cisco UCS vnic:IScsiBootParams:intId managed object property"
    ::= { cucsVnicIScsiBootParamsEntry 5 }

cucsVnicIScsiBootParamsName OBJECT-TYPE
    SYNTAX       SnmpAdminString
    MAX-ACCESS   read-only
    STATUS       current
    DESCRIPTION
        "Cisco UCS vnic:IScsiBootParams:name managed object property"
    ::= { cucsVnicIScsiBootParamsEntry 6 }

cucsVnicIScsiBootParamsPolicyLevel OBJECT-TYPE
    SYNTAX       Gauge32
    MAX-ACCESS   read-only
    STATUS       current
    DESCRIPTION
        "Cisco UCS vnic:IScsiBootParams:policyLevel managed
        object property"
    ::= { cucsVnicIScsiBootParamsEntry 7 }

cucsVnicIScsiBootParamsPolicyOwner OBJECT-TYPE
    SYNTAX       CucsPolicyPolicyOwner
    MAX-ACCESS   read-only
    STATUS       current
    DESCRIPTION
        "Cisco UCS vnic:IScsiBootParams:policyOwner managed
        object property"
    ::= { cucsVnicIScsiBootParamsEntry 8 }

cucsVnicIScsiBootParamsOwner OBJECT-TYPE
    SYNTAX       CucsLsOwner
    MAX-ACCESS   read-only
    STATUS       current
    DESCRIPTION
        "Cisco UCS vnic:IScsiBootParams:owner managed object property"
    ::= { cucsVnicIScsiBootParamsEntry 9 }

cucsVnicIScsiBootParamsPropAcl OBJECT-TYPE
    SYNTAX       Unsigned64
    MAX-ACCESS   read-only
    STATUS       current
    DESCRIPTION
        "Cisco UCS vnic:IScsiBootParams:propAcl managed object property"
    ::= { cucsVnicIScsiBootParamsEntry 10 }

cucsVnicIScsiBootVnicTable OBJECT-TYPE
    SYNTAX           SEQUENCE OF CucsVnicIScsiBootVnicEntry
    MAX-ACCESS       not-accessible
    STATUS           current
    DESCRIPTION
        "Cisco UCS vnic:IScsiBootVnic managed object table"
    ::= { cucsVnicObjects 51 }

cucsVnicIScsiBootVnicEntry OBJECT-TYPE
    SYNTAX           CucsVnicIScsiBootVnicEntry
    MAX-ACCESS       not-accessible
    STATUS           current
    DESCRIPTION
        "Entry for the cucsVnicIScsiBootVnicTable table."
    INDEX { cucsVnicIScsiBootVnicInstanceId }
    ::= { cucsVnicIScsiBootVnicTable 1 }

CucsVnicIScsiBootVnicEntry ::= SEQUENCE {
    cucsVnicIScsiBootVnicInstanceId                                  CucsManagedObjectId,
    cucsVnicIScsiBootVnicDn                                          CucsManagedObjectDn,
    cucsVnicIScsiBootVnicRn                                          SnmpAdminString,
    cucsVnicIScsiBootVnicAuthProfileName                             SnmpAdminString,
    cucsVnicIScsiBootVnicDescr                                       SnmpAdminString,
    cucsVnicIScsiBootVnicInitiatorName                               SnmpAdminString,
    cucsVnicIScsiBootVnicIntId                                       SnmpAdminString,
    cucsVnicIScsiBootVnicIqnIdentPoolName                            SnmpAdminString,
    cucsVnicIScsiBootVnicName                                        SnmpAdminString,
    cucsVnicIScsiBootVnicOperAuthProfileName                         SnmpAdminString,
    cucsVnicIScsiBootVnicOperIqnIdentPoolName                        SnmpAdminString,
    cucsVnicIScsiBootVnicPolicyLevel                                 Gauge32,
    cucsVnicIScsiBootVnicPolicyOwner                                 CucsPolicyPolicyOwner
}

cucsVnicIScsiBootVnicInstanceId OBJECT-TYPE
    SYNTAX       CucsManagedObjectId
    MAX-ACCESS   not-accessible
    STATUS       current
    DESCRIPTION
        "Instance identifier of the managed object."
    ::= { cucsVnicIScsiBootVnicEntry 1 }

cucsVnicIScsiBootVnicDn OBJECT-TYPE
    SYNTAX       CucsManagedObjectDn
    MAX-ACCESS   read-only
    STATUS       current
    DESCRIPTION
        "Cisco UCS vnic:IScsiBootVnic:dn managed object property"
    ::= { cucsVnicIScsiBootVnicEntry 2 }

cucsVnicIScsiBootVnicRn OBJECT-TYPE
    SYNTAX       SnmpAdminString
    MAX-ACCESS   read-only
    STATUS       current
    DESCRIPTION
        "Cisco UCS vnic:IScsiBootVnic:rn managed object property"
    ::= { cucsVnicIScsiBootVnicEntry 3 }

cucsVnicIScsiBootVnicAuthProfileName OBJECT-TYPE
    SYNTAX       SnmpAdminString
    MAX-ACCESS   read-only
    STATUS       current
    DESCRIPTION
        "Cisco UCS vnic:IScsiBootVnic:authProfileName managed
        object property"
    ::= { cucsVnicIScsiBootVnicEntry 4 }

cucsVnicIScsiBootVnicDescr OBJECT-TYPE
    SYNTAX       SnmpAdminString
    MAX-ACCESS   read-only
    STATUS       current
    DESCRIPTION
        "Cisco UCS vnic:IScsiBootVnic:descr managed object property"
    ::= { cucsVnicIScsiBootVnicEntry 5 }

cucsVnicIScsiBootVnicInitiatorName OBJECT-TYPE
    SYNTAX       SnmpAdminString
    MAX-ACCESS   read-only
    STATUS       current
    DESCRIPTION
        "Cisco UCS vnic:IScsiBootVnic:initiatorName managed
        object property"
    ::= { cucsVnicIScsiBootVnicEntry 6 }

cucsVnicIScsiBootVnicIntId OBJECT-TYPE
    SYNTAX       SnmpAdminString
    MAX-ACCESS   read-only
    STATUS       current
    DESCRIPTION
        "Cisco UCS vnic:IScsiBootVnic:intId managed object property"
    ::= { cucsVnicIScsiBootVnicEntry 7 }

cucsVnicIScsiBootVnicIqnIdentPoolName OBJECT-TYPE
    SYNTAX       SnmpAdminString
    MAX-ACCESS   read-only
    STATUS       current
    DESCRIPTION
        "Cisco UCS vnic:IScsiBootVnic:iqnIdentPoolName
        managed object property"
    ::= { cucsVnicIScsiBootVnicEntry 8 }

cucsVnicIScsiBootVnicName OBJECT-TYPE
    SYNTAX       SnmpAdminString
    MAX-ACCESS   read-only
    STATUS       current
    DESCRIPTION
        "Cisco UCS vnic:IScsiBootVnic:name managed object property"
    ::= { cucsVnicIScsiBootVnicEntry 9 }

cucsVnicIScsiBootVnicOperAuthProfileName OBJECT-TYPE
    SYNTAX       SnmpAdminString
    MAX-ACCESS   read-only
    STATUS       current
    DESCRIPTION
        "Cisco UCS vnic:IScsiBootVnic:operAuthProfileName
        managed object property"
    ::= { cucsVnicIScsiBootVnicEntry 10 }

cucsVnicIScsiBootVnicOperIqnIdentPoolName OBJECT-TYPE
    SYNTAX       SnmpAdminString
    MAX-ACCESS   read-only
    STATUS       current
    DESCRIPTION
        "Cisco UCS vnic:IScsiBootVnic:operIqnIdentPoolName
        managed object property"
    ::= { cucsVnicIScsiBootVnicEntry 11 }

cucsVnicIScsiBootVnicPolicyLevel OBJECT-TYPE
    SYNTAX       Gauge32
    MAX-ACCESS   read-only
    STATUS       current
    DESCRIPTION
        "Cisco UCS vnic:IScsiBootVnic:policyLevel managed object property"
    ::= { cucsVnicIScsiBootVnicEntry 12 }

cucsVnicIScsiBootVnicPolicyOwner OBJECT-TYPE
    SYNTAX       CucsPolicyPolicyOwner
    MAX-ACCESS   read-only
    STATUS       current
    DESCRIPTION
        "Cisco UCS vnic:IScsiBootVnic:policyOwner managed object property"
    ::= { cucsVnicIScsiBootVnicEntry 13 }

cucsVnicIScsiConfigTable OBJECT-TYPE
    SYNTAX           SEQUENCE OF CucsVnicIScsiConfigEntry
    MAX-ACCESS       not-accessible
    STATUS           current
    DESCRIPTION
        "Cisco UCS vnic:IScsiConfig managed object table"
    ::= { cucsVnicObjects 76 }

cucsVnicIScsiConfigEntry OBJECT-TYPE
    SYNTAX           CucsVnicIScsiConfigEntry
    MAX-ACCESS       not-accessible
    STATUS           current
    DESCRIPTION
        "Entry for the cucsVnicIScsiConfigTable table."
    INDEX { cucsVnicIScsiConfigInstanceId }
    ::= { cucsVnicIScsiConfigTable 1 }

CucsVnicIScsiConfigEntry ::= SEQUENCE {
    cucsVnicIScsiConfigInstanceId                                    CucsManagedObjectId,
    cucsVnicIScsiConfigDn                                            CucsManagedObjectDn,
    cucsVnicIScsiConfigRn                                            SnmpAdminString,
    cucsVnicIScsiConfigAdaptorProfileName                            SnmpAdminString,
    cucsVnicIScsiConfigIpPoolName                                    SnmpAdminString,
    cucsVnicIScsiConfigIpPoolNameFabricB                             SnmpAdminString,
    cucsVnicIScsiConfigIpPoolType                                    CucsVnicIpPoolType,
    cucsVnicIScsiConfigIqnPoolName                                   SnmpAdminString,
    cucsVnicIScsiConfigOperAdaptorProfileName                        SnmpAdminString,
    cucsVnicIScsiConfigOperIpPoolName                                SnmpAdminString,
    cucsVnicIScsiConfigOperIpPoolNameFabricB                         SnmpAdminString,
    cucsVnicIScsiConfigOperIqnPoolName                               SnmpAdminString
}

cucsVnicIScsiConfigInstanceId OBJECT-TYPE
    SYNTAX       CucsManagedObjectId
    MAX-ACCESS   not-accessible
    STATUS       current
    DESCRIPTION
        "Instance identifier of the managed object."
    ::= { cucsVnicIScsiConfigEntry 1 }

cucsVnicIScsiConfigDn OBJECT-TYPE
    SYNTAX       CucsManagedObjectDn
    MAX-ACCESS   read-only
    STATUS       current
    DESCRIPTION
        "Cisco UCS vnic:IScsiConfig:dn managed object property"
    ::= { cucsVnicIScsiConfigEntry 2 }

cucsVnicIScsiConfigRn OBJECT-TYPE
    SYNTAX       SnmpAdminString
    MAX-ACCESS   read-only
    STATUS       current
    DESCRIPTION
        "Cisco UCS vnic:IScsiConfig:rn managed object property"
    ::= { cucsVnicIScsiConfigEntry 3 }

cucsVnicIScsiConfigAdaptorProfileName OBJECT-TYPE
    SYNTAX       SnmpAdminString
    MAX-ACCESS   read-only
    STATUS       current
    DESCRIPTION
        "Cisco UCS vnic:IScsiConfig:adaptorProfileName
        managed object property"
    ::= { cucsVnicIScsiConfigEntry 4 }

cucsVnicIScsiConfigIpPoolName OBJECT-TYPE
    SYNTAX       SnmpAdminString
    MAX-ACCESS   read-only
    STATUS       current
    DESCRIPTION
        "Cisco UCS vnic:IScsiConfig:ipPoolName managed object property"
    ::= { cucsVnicIScsiConfigEntry 5 }

cucsVnicIScsiConfigIpPoolNameFabricB OBJECT-TYPE
    SYNTAX       SnmpAdminString
    MAX-ACCESS   read-only
    STATUS       current
    DESCRIPTION
        "Cisco UCS vnic:IScsiConfig:ipPoolNameFabricB managed
        object property"
    ::= { cucsVnicIScsiConfigEntry 6 }

cucsVnicIScsiConfigIpPoolType OBJECT-TYPE
    SYNTAX       CucsVnicIpPoolType
    MAX-ACCESS   read-only
    STATUS       current
    DESCRIPTION
        "Cisco UCS vnic:IScsiConfig:ipPoolType managed object property"
    ::= { cucsVnicIScsiConfigEntry 7 }

cucsVnicIScsiConfigIqnPoolName OBJECT-TYPE
    SYNTAX       SnmpAdminString
    MAX-ACCESS   read-only
    STATUS       current
    DESCRIPTION
        "Cisco UCS vnic:IScsiConfig:iqnPoolName managed object property"
    ::= { cucsVnicIScsiConfigEntry 8 }

cucsVnicIScsiConfigOperAdaptorProfileName OBJECT-TYPE
    SYNTAX       SnmpAdminString
    MAX-ACCESS   read-only
    STATUS       current
    DESCRIPTION
        "Cisco UCS vnic:IScsiConfig:operAdaptorProfileName
        managed object property"
    ::= { cucsVnicIScsiConfigEntry 9 }

cucsVnicIScsiConfigOperIpPoolName OBJECT-TYPE
    SYNTAX       SnmpAdminString
    MAX-ACCESS   read-only
    STATUS       current
    DESCRIPTION
        "Cisco UCS vnic:IScsiConfig:operIpPoolName managed
        object property"
    ::= { cucsVnicIScsiConfigEntry 10 }

cucsVnicIScsiConfigOperIpPoolNameFabricB OBJECT-TYPE
    SYNTAX       SnmpAdminString
    MAX-ACCESS   read-only
    STATUS       current
    DESCRIPTION
        "Cisco UCS vnic:IScsiConfig:operIpPoolNameFabricB
        managed object property"
    ::= { cucsVnicIScsiConfigEntry 11 }

cucsVnicIScsiConfigOperIqnPoolName OBJECT-TYPE
    SYNTAX       SnmpAdminString
    MAX-ACCESS   read-only
    STATUS       current
    DESCRIPTION
        "Cisco UCS vnic:IScsiConfig:operIqnPoolName managed
        object property"
    ::= { cucsVnicIScsiConfigEntry 12 }

cucsVnicIScsiInitAutoConfigPolicyTable OBJECT-TYPE
    SYNTAX           SEQUENCE OF CucsVnicIScsiInitAutoConfigPolicyEntry
    MAX-ACCESS       not-accessible
    STATUS           current
    DESCRIPTION
        "Cisco UCS vnic:IScsiInitAutoConfigPolicy managed object table"
    ::= { cucsVnicObjects 77 }

cucsVnicIScsiInitAutoConfigPolicyEntry OBJECT-TYPE
    SYNTAX           CucsVnicIScsiInitAutoConfigPolicyEntry
    MAX-ACCESS       not-accessible
    STATUS           current
    DESCRIPTION
        "Entry for the cucsVnicIScsiInitAutoConfigPolicyTable table."
    INDEX { cucsVnicIScsiInitAutoConfigPolicyInstanceId }
    ::= { cucsVnicIScsiInitAutoConfigPolicyTable 1 }

CucsVnicIScsiInitAutoConfigPolicyEntry ::= SEQUENCE {
    cucsVnicIScsiInitAutoConfigPolicyInstanceId                      CucsManagedObjectId,
    cucsVnicIScsiInitAutoConfigPolicyDn                              CucsManagedObjectDn,
    cucsVnicIScsiInitAutoConfigPolicyRn                              SnmpAdminString,
    cucsVnicIScsiInitAutoConfigPolicyDescr                           SnmpAdminString,
    cucsVnicIScsiInitAutoConfigPolicyFabricPath                      SnmpAdminString,
    cucsVnicIScsiInitAutoConfigPolicyIntId                           SnmpAdminString,
    cucsVnicIScsiInitAutoConfigPolicyName                            SnmpAdminString,
    cucsVnicIScsiInitAutoConfigPolicyPolicyLevel                     Gauge32,
    cucsVnicIScsiInitAutoConfigPolicyPolicyOwner                     CucsPolicyPolicyOwner
}

cucsVnicIScsiInitAutoConfigPolicyInstanceId OBJECT-TYPE
    SYNTAX       CucsManagedObjectId
    MAX-ACCESS   not-accessible
    STATUS       current
    DESCRIPTION
        "Instance identifier of the managed object."
    ::= { cucsVnicIScsiInitAutoConfigPolicyEntry 1 }

cucsVnicIScsiInitAutoConfigPolicyDn OBJECT-TYPE
    SYNTAX       CucsManagedObjectDn
    MAX-ACCESS   read-only
    STATUS       current
    DESCRIPTION
        "Cisco UCS vnic:IScsiInitAutoConfigPolicy:dn managed
        object property"
    ::= { cucsVnicIScsiInitAutoConfigPolicyEntry 2 }

cucsVnicIScsiInitAutoConfigPolicyRn OBJECT-TYPE
    SYNTAX       SnmpAdminString
    MAX-ACCESS   read-only
    STATUS       current
    DESCRIPTION
        "Cisco UCS vnic:IScsiInitAutoConfigPolicy:rn managed
        object property"
    ::= { cucsVnicIScsiInitAutoConfigPolicyEntry 3 }

cucsVnicIScsiInitAutoConfigPolicyDescr OBJECT-TYPE
    SYNTAX       SnmpAdminString
    MAX-ACCESS   read-only
    STATUS       current
    DESCRIPTION
        "Cisco UCS vnic:IScsiInitAutoConfigPolicy:descr
        managed object property"
    ::= { cucsVnicIScsiInitAutoConfigPolicyEntry 4 }

cucsVnicIScsiInitAutoConfigPolicyFabricPath OBJECT-TYPE
    SYNTAX       SnmpAdminString
    MAX-ACCESS   read-only
    STATUS       current
    DESCRIPTION
        "Cisco UCS vnic:IScsiInitAutoConfigPolicy:fabricPath
        managed object property"
    ::= { cucsVnicIScsiInitAutoConfigPolicyEntry 5 }

cucsVnicIScsiInitAutoConfigPolicyIntId OBJECT-TYPE
    SYNTAX       SnmpAdminString
    MAX-ACCESS   read-only
    STATUS       current
    DESCRIPTION
        "Cisco UCS vnic:IScsiInitAutoConfigPolicy:intId
        managed object property"
    ::= { cucsVnicIScsiInitAutoConfigPolicyEntry 6 }

cucsVnicIScsiInitAutoConfigPolicyName OBJECT-TYPE
    SYNTAX       SnmpAdminString
    MAX-ACCESS   read-only
    STATUS       current
    DESCRIPTION
        "Cisco UCS vnic:IScsiInitAutoConfigPolicy:name
        managed object property"
    ::= { cucsVnicIScsiInitAutoConfigPolicyEntry 7 }

cucsVnicIScsiInitAutoConfigPolicyPolicyLevel OBJECT-TYPE
    SYNTAX       Gauge32
    MAX-ACCESS   read-only
    STATUS       current
    DESCRIPTION
        "Cisco UCS vnic:IScsiInitAutoConfigPolicy:policyLevel
        managed object property"
    ::= { cucsVnicIScsiInitAutoConfigPolicyEntry 8 }

cucsVnicIScsiInitAutoConfigPolicyPolicyOwner OBJECT-TYPE
    SYNTAX       CucsPolicyPolicyOwner
    MAX-ACCESS   read-only
    STATUS       current
    DESCRIPTION
        "Cisco UCS vnic:IScsiInitAutoConfigPolicy:policyOwner
        managed object property"
    ::= { cucsVnicIScsiInitAutoConfigPolicyEntry 9 }

cucsVnicIScsiLCPTable OBJECT-TYPE
    SYNTAX           SEQUENCE OF CucsVnicIScsiLCPEntry
    MAX-ACCESS       not-accessible
    STATUS           current
    DESCRIPTION
        "Cisco UCS vnic:IScsiLCP managed object table"
    ::= { cucsVnicObjects 52 }

cucsVnicIScsiLCPEntry OBJECT-TYPE
    SYNTAX           CucsVnicIScsiLCPEntry
    MAX-ACCESS       not-accessible
    STATUS           current
    DESCRIPTION
        "Entry for the cucsVnicIScsiLCPTable table."
    INDEX { cucsVnicIScsiLCPInstanceId }
    ::= { cucsVnicIScsiLCPTable 1 }

CucsVnicIScsiLCPEntry ::= SEQUENCE {
    cucsVnicIScsiLCPInstanceId                                       CucsManagedObjectId,
    cucsVnicIScsiLCPDn                                               CucsManagedObjectDn,
    cucsVnicIScsiLCPRn                                               SnmpAdminString,
    cucsVnicIScsiLCPAdaptorProfileName                               SnmpAdminString,
    cucsVnicIScsiLCPAddr                                             MacAddress,
    cucsVnicIScsiLCPAdminVcon                                        SnmpAdminString,
    cucsVnicIScsiLCPBootDev                                          CucsVnicVnicBootDev,
    cucsVnicIScsiLCPConfigQualifier                                  CucsVnicConfigIssues,
    cucsVnicIScsiLCPConfigState                                      CucsLsConfigState,
    cucsVnicIScsiLCPEquipmentDn                                      SnmpAdminString,
    cucsVnicIScsiLCPFltAggr                                          Unsigned64,
    cucsVnicIScsiLCPIdentPoolName                                    SnmpAdminString,
    cucsVnicIScsiLCPInstType                                         CucsVnicInstantiation,
    cucsVnicIScsiLCPName                                             SnmpAdminString,
    cucsVnicIScsiLCPNwTemplName                                      SnmpAdminString,
    cucsVnicIScsiLCPOperAdaptorProfileName                           SnmpAdminString,
    cucsVnicIScsiLCPOperIdentPoolName                                SnmpAdminString,
    cucsVnicIScsiLCPOperOrder                                        Gauge32,
    cucsVnicIScsiLCPOperSpeed                                        Gauge32,
    cucsVnicIScsiLCPOperStatsPolicyName                              SnmpAdminString,
    cucsVnicIScsiLCPOperVcon                                         SnmpAdminString,
    cucsVnicIScsiLCPOrder                                            Gauge32,
    cucsVnicIScsiLCPOwner                                            CucsVnicConnectionOwner,
    cucsVnicIScsiLCPPinToGroupName                                   SnmpAdminString,
    cucsVnicIScsiLCPQosPolicyName                                    SnmpAdminString,
    cucsVnicIScsiLCPStatsPolicyName                                  SnmpAdminString,
    cucsVnicIScsiLCPSwitchId                                         CucsNetworkSwitchId,
    cucsVnicIScsiLCPType                                             CucsVnicConnectionType,
    cucsVnicIScsiLCPVnicName                                         SnmpAdminString,
    cucsVnicIScsiLCPAdminHostPort                                    CucsFabricHostPortId,
    cucsVnicIScsiLCPOperHostPort                                     CucsVnicVnicOperHostPort,
    cucsVnicIScsiLCPAdminCdnName                                     SnmpAdminString,
    cucsVnicIScsiLCPOperCdnName                                      SnmpAdminString,
    cucsVnicIScsiLCPCdnSource                                        CucsVnicCdnSource,
    cucsVnicIScsiLCPCdnPropInSync                                    TruthValue
}

cucsVnicIScsiLCPInstanceId OBJECT-TYPE
    SYNTAX       CucsManagedObjectId
    MAX-ACCESS   not-accessible
    STATUS       current
    DESCRIPTION
        "Instance identifier of the managed object."
    ::= { cucsVnicIScsiLCPEntry 1 }

cucsVnicIScsiLCPDn OBJECT-TYPE
    SYNTAX       CucsManagedObjectDn
    MAX-ACCESS   read-only
    STATUS       current
    DESCRIPTION
        "Cisco UCS vnic:IScsiLCP:dn managed object property"
    ::= { cucsVnicIScsiLCPEntry 2 }

cucsVnicIScsiLCPRn OBJECT-TYPE
    SYNTAX       SnmpAdminString
    MAX-ACCESS   read-only
    STATUS       current
    DESCRIPTION
        "Cisco UCS vnic:IScsiLCP:rn managed object property"
    ::= { cucsVnicIScsiLCPEntry 3 }

cucsVnicIScsiLCPAdaptorProfileName OBJECT-TYPE
    SYNTAX       SnmpAdminString
    MAX-ACCESS   read-only
    STATUS       current
    DESCRIPTION
        "Cisco UCS vnic:IScsiLCP:adaptorProfileName managed
        object property"
    ::= { cucsVnicIScsiLCPEntry 4 }

cucsVnicIScsiLCPAddr OBJECT-TYPE
    SYNTAX       MacAddress
    MAX-ACCESS   read-only
    STATUS       current
    DESCRIPTION
        "Cisco UCS vnic:IScsiLCP:addr managed object property"
    ::= { cucsVnicIScsiLCPEntry 5 }

cucsVnicIScsiLCPAdminVcon OBJECT-TYPE
    SYNTAX       SnmpAdminString
    MAX-ACCESS   read-only
    STATUS       current
    DESCRIPTION
        "Cisco UCS vnic:IScsiLCP:adminVcon managed object property"
    ::= { cucsVnicIScsiLCPEntry 6 }

cucsVnicIScsiLCPBootDev OBJECT-TYPE
    SYNTAX       CucsVnicVnicBootDev
    MAX-ACCESS   read-only
    STATUS       current
    DESCRIPTION
        "Cisco UCS vnic:IScsiLCP:bootDev managed object property"
    ::= { cucsVnicIScsiLCPEntry 7 }

cucsVnicIScsiLCPConfigQualifier OBJECT-TYPE
    SYNTAX       CucsVnicConfigIssues
    MAX-ACCESS   read-only
    STATUS       current
    DESCRIPTION
        "Cisco UCS vnic:IScsiLCP:configQualifier managed object property"
    ::= { cucsVnicIScsiLCPEntry 8 }

cucsVnicIScsiLCPConfigState OBJECT-TYPE
    SYNTAX       CucsLsConfigState
    MAX-ACCESS   read-only
    STATUS       current
    DESCRIPTION
        "Cisco UCS vnic:IScsiLCP:configState managed object property"
    ::= { cucsVnicIScsiLCPEntry 9 }

cucsVnicIScsiLCPEquipmentDn OBJECT-TYPE
    SYNTAX       SnmpAdminString
    MAX-ACCESS   read-only
    STATUS       current
    DESCRIPTION
        "Cisco UCS vnic:IScsiLCP:equipmentDn managed object property"
    ::= { cucsVnicIScsiLCPEntry 10 }

cucsVnicIScsiLCPFltAggr OBJECT-TYPE
    SYNTAX       Unsigned64
    MAX-ACCESS   read-only
    STATUS       current
    DESCRIPTION
        "Cisco UCS vnic:IScsiLCP:fltAggr managed object property"
    ::= { cucsVnicIScsiLCPEntry 11 }

cucsVnicIScsiLCPIdentPoolName OBJECT-TYPE
    SYNTAX       SnmpAdminString
    MAX-ACCESS   read-only
    STATUS       current
    DESCRIPTION
        "Cisco UCS vnic:IScsiLCP:identPoolName managed object property"
    ::= { cucsVnicIScsiLCPEntry 12 }

cucsVnicIScsiLCPInstType OBJECT-TYPE
    SYNTAX       CucsVnicInstantiation
    MAX-ACCESS   read-only
    STATUS       current
    DESCRIPTION
        "Cisco UCS vnic:IScsiLCP:instType managed object property"
    ::= { cucsVnicIScsiLCPEntry 13 }

cucsVnicIScsiLCPName OBJECT-TYPE
    SYNTAX       SnmpAdminString
    MAX-ACCESS   read-only
    STATUS       current
    DESCRIPTION
        "Cisco UCS vnic:IScsiLCP:name managed object property"
    ::= { cucsVnicIScsiLCPEntry 14 }

cucsVnicIScsiLCPNwTemplName OBJECT-TYPE
    SYNTAX       SnmpAdminString
    MAX-ACCESS   read-only
    STATUS       current
    DESCRIPTION
        "Cisco UCS vnic:IScsiLCP:nwTemplName managed object property"
    ::= { cucsVnicIScsiLCPEntry 15 }

cucsVnicIScsiLCPOperAdaptorProfileName OBJECT-TYPE
    SYNTAX       SnmpAdminString
    MAX-ACCESS   read-only
    STATUS       current
    DESCRIPTION
        "Cisco UCS vnic:IScsiLCP:operAdaptorProfileName
        managed object property"
    ::= { cucsVnicIScsiLCPEntry 16 }

cucsVnicIScsiLCPOperIdentPoolName OBJECT-TYPE
    SYNTAX       SnmpAdminString
    MAX-ACCESS   read-only
    STATUS       current
    DESCRIPTION
        "Cisco UCS vnic:IScsiLCP:operIdentPoolName managed
        object property"
    ::= { cucsVnicIScsiLCPEntry 17 }

cucsVnicIScsiLCPOperOrder OBJECT-TYPE
    SYNTAX       Gauge32
    MAX-ACCESS   read-only
    STATUS       current
    DESCRIPTION
        "Cisco UCS vnic:IScsiLCP:operOrder managed object property"
    ::= { cucsVnicIScsiLCPEntry 18 }

cucsVnicIScsiLCPOperSpeed OBJECT-TYPE
    SYNTAX       Gauge32
    MAX-ACCESS   read-only
    STATUS       current
    DESCRIPTION
        "Cisco UCS vnic:IScsiLCP:operSpeed managed object property"
    ::= { cucsVnicIScsiLCPEntry 19 }

cucsVnicIScsiLCPOperStatsPolicyName OBJECT-TYPE
    SYNTAX       SnmpAdminString
    MAX-ACCESS   read-only
    STATUS       current
    DESCRIPTION
        "Cisco UCS vnic:IScsiLCP:operStatsPolicyName managed
        object property"
    ::= { cucsVnicIScsiLCPEntry 20 }

cucsVnicIScsiLCPOperVcon OBJECT-TYPE
    SYNTAX       SnmpAdminString
    MAX-ACCESS   read-only
    STATUS       current
    DESCRIPTION
        "Cisco UCS vnic:IScsiLCP:operVcon managed object property"
    ::= { cucsVnicIScsiLCPEntry 21 }

cucsVnicIScsiLCPOrder OBJECT-TYPE
    SYNTAX       Gauge32
    MAX-ACCESS   read-only
    STATUS       current
    DESCRIPTION
        "Cisco UCS vnic:IScsiLCP:order managed object property"
    ::= { cucsVnicIScsiLCPEntry 22 }

cucsVnicIScsiLCPOwner OBJECT-TYPE
    SYNTAX       CucsVnicConnectionOwner
    MAX-ACCESS   read-only
    STATUS       current
    DESCRIPTION
        "Cisco UCS vnic:IScsiLCP:owner managed object property"
    ::= { cucsVnicIScsiLCPEntry 23 }

cucsVnicIScsiLCPPinToGroupName OBJECT-TYPE
    SYNTAX       SnmpAdminString
    MAX-ACCESS   read-only
    STATUS       current
    DESCRIPTION
        "Cisco UCS vnic:IScsiLCP:pinToGroupName managed object property"
    ::= { cucsVnicIScsiLCPEntry 24 }

cucsVnicIScsiLCPQosPolicyName OBJECT-TYPE
    SYNTAX       SnmpAdminString
    MAX-ACCESS   read-only
    STATUS       current
    DESCRIPTION
        "Cisco UCS vnic:IScsiLCP:qosPolicyName managed object property"
    ::= { cucsVnicIScsiLCPEntry 25 }

cucsVnicIScsiLCPStatsPolicyName OBJECT-TYPE
    SYNTAX       SnmpAdminString
    MAX-ACCESS   read-only
    STATUS       current
    DESCRIPTION
        "Cisco UCS vnic:IScsiLCP:statsPolicyName managed object property"
    ::= { cucsVnicIScsiLCPEntry 26 }

cucsVnicIScsiLCPSwitchId OBJECT-TYPE
    SYNTAX       CucsNetworkSwitchId
    MAX-ACCESS   read-only
    STATUS       current
    DESCRIPTION
        "Cisco UCS vnic:IScsiLCP:switchId managed object property"
    ::= { cucsVnicIScsiLCPEntry 27 }

cucsVnicIScsiLCPType OBJECT-TYPE
    SYNTAX       CucsVnicConnectionType
    MAX-ACCESS   read-only
    STATUS       current
    DESCRIPTION
        "Cisco UCS vnic:IScsiLCP:type managed object property"
    ::= { cucsVnicIScsiLCPEntry 28 }

cucsVnicIScsiLCPVnicName OBJECT-TYPE
    SYNTAX       SnmpAdminString
    MAX-ACCESS   read-only
    STATUS       current
    DESCRIPTION
        "Cisco UCS vnic:IScsiLCP:vnicName managed object property"
    ::= { cucsVnicIScsiLCPEntry 29 }

cucsVnicIScsiLCPAdminHostPort OBJECT-TYPE
    SYNTAX       CucsFabricHostPortId
    MAX-ACCESS   read-only
    STATUS       current
    DESCRIPTION
        "Cisco UCS vnic:IScsiLCP:adminHostPort managed object property"
    ::= { cucsVnicIScsiLCPEntry 31 }

cucsVnicIScsiLCPOperHostPort OBJECT-TYPE
    SYNTAX       CucsVnicVnicOperHostPort
    MAX-ACCESS   read-only
    STATUS       current
    DESCRIPTION
        "Cisco UCS vnic:IScsiLCP:operHostPort managed object property"
    ::= { cucsVnicIScsiLCPEntry 32 }

cucsVnicIScsiLCPAdminCdnName OBJECT-TYPE
    SYNTAX       SnmpAdminString
    MAX-ACCESS   read-only
    STATUS       current
    DESCRIPTION
        "Cisco UCS vnic:IScsiLCP:adminCdnName managed object property"
    ::= { cucsVnicIScsiLCPEntry 33 }

cucsVnicIScsiLCPOperCdnName OBJECT-TYPE
    SYNTAX       SnmpAdminString
    MAX-ACCESS   read-only
    STATUS       current
    DESCRIPTION
        "Cisco UCS vnic:IScsiLCP:operCdnName managed object property"
    ::= { cucsVnicIScsiLCPEntry 34 }

cucsVnicIScsiLCPCdnSource OBJECT-TYPE
    SYNTAX       CucsVnicCdnSource
    MAX-ACCESS   read-only
    STATUS       current
    DESCRIPTION
        "Cisco UCS vnic:IScsiLCP:cdnSource managed object property"
    ::= { cucsVnicIScsiLCPEntry 35 }

cucsVnicIScsiLCPCdnPropInSync OBJECT-TYPE
    SYNTAX       TruthValue
    MAX-ACCESS   read-only
    STATUS       current
    DESCRIPTION
        "Cisco UCS vnic:IScsiLCP:cdnPropInSync managed object property"
    ::= { cucsVnicIScsiLCPEntry 36 }

cucsVnicIScsiNodeTable OBJECT-TYPE
    SYNTAX           SEQUENCE OF CucsVnicIScsiNodeEntry
    MAX-ACCESS       not-accessible
    STATUS           current
    DESCRIPTION
        "Cisco UCS vnic:IScsiNode managed object table"
    ::= { cucsVnicObjects 40 }

cucsVnicIScsiNodeEntry OBJECT-TYPE
    SYNTAX           CucsVnicIScsiNodeEntry
    MAX-ACCESS       not-accessible
    STATUS           current
    DESCRIPTION
        "Entry for the cucsVnicIScsiNodeTable table."
    INDEX { cucsVnicIScsiNodeInstanceId }
    ::= { cucsVnicIScsiNodeTable 1 }

CucsVnicIScsiNodeEntry ::= SEQUENCE {
    cucsVnicIScsiNodeInstanceId                                      CucsManagedObjectId,
    cucsVnicIScsiNodeDn                                              CucsManagedObjectDn,
    cucsVnicIScsiNodeRn                                              SnmpAdminString,
    cucsVnicIScsiNodeFltAggr                                         Unsigned64,
    cucsVnicIScsiNodeInitiatorName                                   SnmpAdminString,
    cucsVnicIScsiNodeOwner                                           CucsVnicIScsiNodeOwner,
    cucsVnicIScsiNodeInitNameSuffix                                  SnmpAdminString,
    cucsVnicIScsiNodeIqnIdentPoolName                                SnmpAdminString,
    cucsVnicIScsiNodeOperIqnIdentPoolName                            SnmpAdminString,
    cucsVnicIScsiNodeInitiatorPolicyName                             SnmpAdminString,
    cucsVnicIScsiNodeOperInitiatorPolicyName                         SnmpAdminString,
    cucsVnicIScsiNodePropAcl                                         Unsigned64
}

cucsVnicIScsiNodeInstanceId OBJECT-TYPE
    SYNTAX       CucsManagedObjectId
    MAX-ACCESS   not-accessible
    STATUS       current
    DESCRIPTION
        "Instance identifier of the managed object."
    ::= { cucsVnicIScsiNodeEntry 1 }

cucsVnicIScsiNodeDn OBJECT-TYPE
    SYNTAX       CucsManagedObjectDn
    MAX-ACCESS   read-only
    STATUS       current
    DESCRIPTION
        "Cisco UCS vnic:IScsiNode:dn managed object property"
    ::= { cucsVnicIScsiNodeEntry 2 }

cucsVnicIScsiNodeRn OBJECT-TYPE
    SYNTAX       SnmpAdminString
    MAX-ACCESS   read-only
    STATUS       current
    DESCRIPTION
        "Cisco UCS vnic:IScsiNode:rn managed object property"
    ::= { cucsVnicIScsiNodeEntry 3 }

cucsVnicIScsiNodeFltAggr OBJECT-TYPE
    SYNTAX       Unsigned64
    MAX-ACCESS   read-only
    STATUS       current
    DESCRIPTION
        "Cisco UCS vnic:IScsiNode:fltAggr managed object property"
    ::= { cucsVnicIScsiNodeEntry 4 }

cucsVnicIScsiNodeInitiatorName OBJECT-TYPE
    SYNTAX       SnmpAdminString
    MAX-ACCESS   read-only
    STATUS       current
    DESCRIPTION
        "Cisco UCS vnic:IScsiNode:initiatorName managed object property"
    ::= { cucsVnicIScsiNodeEntry 5 }

cucsVnicIScsiNodeOwner OBJECT-TYPE
    SYNTAX       CucsVnicIScsiNodeOwner
    MAX-ACCESS   read-only
    STATUS       current
    DESCRIPTION
        "Cisco UCS vnic:IScsiNode:owner managed object property"
    ::= { cucsVnicIScsiNodeEntry 6 }

cucsVnicIScsiNodeInitNameSuffix OBJECT-TYPE
    SYNTAX       SnmpAdminString
    MAX-ACCESS   read-only
    STATUS       current
    DESCRIPTION
        "Cisco UCS vnic:IScsiNode:initNameSuffix managed object property"
    ::= { cucsVnicIScsiNodeEntry 7 }

cucsVnicIScsiNodeIqnIdentPoolName OBJECT-TYPE
    SYNTAX       SnmpAdminString
    MAX-ACCESS   read-only
    STATUS       current
    DESCRIPTION
        "Cisco UCS vnic:IScsiNode:iqnIdentPoolName managed
        object property"
    ::= { cucsVnicIScsiNodeEntry 8 }

cucsVnicIScsiNodeOperIqnIdentPoolName OBJECT-TYPE
    SYNTAX       SnmpAdminString
    MAX-ACCESS   read-only
    STATUS       current
    DESCRIPTION
        "Cisco UCS vnic:IScsiNode:operIqnIdentPoolName
        managed object property"
    ::= { cucsVnicIScsiNodeEntry 9 }

cucsVnicIScsiNodeInitiatorPolicyName OBJECT-TYPE
    SYNTAX       SnmpAdminString
    MAX-ACCESS   read-only
    STATUS       current
    DESCRIPTION
        "Cisco UCS vnic:IScsiNode:initiatorPolicyName managed
        object property"
    ::= { cucsVnicIScsiNodeEntry 10 }

cucsVnicIScsiNodeOperInitiatorPolicyName OBJECT-TYPE
    SYNTAX       SnmpAdminString
    MAX-ACCESS   read-only
    STATUS       current
    DESCRIPTION
        "Cisco UCS vnic:IScsiNode:operInitiatorPolicyName
        managed object property"
    ::= { cucsVnicIScsiNodeEntry 11 }

cucsVnicIScsiNodePropAcl OBJECT-TYPE
    SYNTAX       Unsigned64
    MAX-ACCESS   read-only
    STATUS       current
    DESCRIPTION
        "Cisco UCS vnic:IScsiNode:propAcl managed object property"
    ::= { cucsVnicIScsiNodeEntry 12 }

cucsVnicIScsiStaticTargetIfTable OBJECT-TYPE
    SYNTAX           SEQUENCE OF CucsVnicIScsiStaticTargetIfEntry
    MAX-ACCESS       not-accessible
    STATUS           current
    DESCRIPTION
        "Cisco UCS vnic:IScsiStaticTargetIf managed object table"
    ::= { cucsVnicObjects 41 }

cucsVnicIScsiStaticTargetIfEntry OBJECT-TYPE
    SYNTAX           CucsVnicIScsiStaticTargetIfEntry
    MAX-ACCESS       not-accessible
    STATUS           current
    DESCRIPTION
        "Entry for the cucsVnicIScsiStaticTargetIfTable table."
    INDEX { cucsVnicIScsiStaticTargetIfInstanceId }
    ::= { cucsVnicIScsiStaticTargetIfTable 1 }

CucsVnicIScsiStaticTargetIfEntry ::= SEQUENCE {
    cucsVnicIScsiStaticTargetIfInstanceId                            CucsManagedObjectId,
    cucsVnicIScsiStaticTargetIfDn                                    CucsManagedObjectDn,
    cucsVnicIScsiStaticTargetIfRn                                    SnmpAdminString,
    cucsVnicIScsiStaticTargetIfAuthProfileName                       SnmpAdminString,
    cucsVnicIScsiStaticTargetIfIpAddress                             InetAddressIPv4,
    cucsVnicIScsiStaticTargetIfName                                  SnmpAdminString,
    cucsVnicIScsiStaticTargetIfOperAuthProfileName                   SnmpAdminString,
    cucsVnicIScsiStaticTargetIfPort                                  Gauge32,
    cucsVnicIScsiStaticTargetIfPriority                              Gauge32,
    cucsVnicIScsiStaticTargetIfPropAcl                               Unsigned64
}

cucsVnicIScsiStaticTargetIfInstanceId OBJECT-TYPE
    SYNTAX       CucsManagedObjectId
    MAX-ACCESS   not-accessible
    STATUS       current
    DESCRIPTION
        "Instance identifier of the managed object."
    ::= { cucsVnicIScsiStaticTargetIfEntry 1 }

cucsVnicIScsiStaticTargetIfDn OBJECT-TYPE
    SYNTAX       CucsManagedObjectDn
    MAX-ACCESS   read-only
    STATUS       current
    DESCRIPTION
        "Cisco UCS vnic:IScsiStaticTargetIf:dn managed object property"
    ::= { cucsVnicIScsiStaticTargetIfEntry 2 }

cucsVnicIScsiStaticTargetIfRn OBJECT-TYPE
    SYNTAX       SnmpAdminString
    MAX-ACCESS   read-only
    STATUS       current
    DESCRIPTION
        "Cisco UCS vnic:IScsiStaticTargetIf:rn managed object property"
    ::= { cucsVnicIScsiStaticTargetIfEntry 3 }

cucsVnicIScsiStaticTargetIfAuthProfileName OBJECT-TYPE
    SYNTAX       SnmpAdminString
    MAX-ACCESS   read-only
    STATUS       current
    DESCRIPTION
        "Cisco UCS vnic:IScsiStaticTargetIf:authProfileName
        managed object property"
    ::= { cucsVnicIScsiStaticTargetIfEntry 4 }

cucsVnicIScsiStaticTargetIfIpAddress OBJECT-TYPE
    SYNTAX       InetAddressIPv4
    MAX-ACCESS   read-only
    STATUS       current
    DESCRIPTION
        "Cisco UCS vnic:IScsiStaticTargetIf:ipAddress managed
        object property"
    ::= { cucsVnicIScsiStaticTargetIfEntry 5 }

cucsVnicIScsiStaticTargetIfName OBJECT-TYPE
    SYNTAX       SnmpAdminString
    MAX-ACCESS   read-only
    STATUS       current
    DESCRIPTION
        "Cisco UCS vnic:IScsiStaticTargetIf:name managed object property"
    ::= { cucsVnicIScsiStaticTargetIfEntry 6 }

cucsVnicIScsiStaticTargetIfOperAuthProfileName OBJECT-TYPE
    SYNTAX       SnmpAdminString
    MAX-ACCESS   read-only
    STATUS       current
    DESCRIPTION
        "Cisco UCS vnic:IScsiStaticTargetIf:operAuthProfileName
        managed object property"
    ::= { cucsVnicIScsiStaticTargetIfEntry 7 }

cucsVnicIScsiStaticTargetIfPort OBJECT-TYPE
    SYNTAX       Gauge32
    MAX-ACCESS   read-only
    STATUS       current
    DESCRIPTION
        "Cisco UCS vnic:IScsiStaticTargetIf:port managed object property"
    ::= { cucsVnicIScsiStaticTargetIfEntry 8 }

cucsVnicIScsiStaticTargetIfPriority OBJECT-TYPE
    SYNTAX       Gauge32
    MAX-ACCESS   read-only
    STATUS       current
    DESCRIPTION
        "Cisco UCS vnic:IScsiStaticTargetIf:priority managed
        object property"
    ::= { cucsVnicIScsiStaticTargetIfEntry 9 }

cucsVnicIScsiStaticTargetIfPropAcl OBJECT-TYPE
    SYNTAX       Unsigned64
    MAX-ACCESS   read-only
    STATUS       current
    DESCRIPTION
        "Cisco UCS vnic:IScsiStaticTargetIf:propAcl managed
        object property"
    ::= { cucsVnicIScsiStaticTargetIfEntry 11 }

cucsVnicInternalProfileTable OBJECT-TYPE
    SYNTAX           SEQUENCE OF CucsVnicInternalProfileEntry
    MAX-ACCESS       not-accessible
    STATUS           current
    DESCRIPTION
        "Cisco UCS vnic:InternalProfile managed object table"
    ::= { cucsVnicObjects 42 }

cucsVnicInternalProfileEntry OBJECT-TYPE
    SYNTAX           CucsVnicInternalProfileEntry
    MAX-ACCESS       not-accessible
    STATUS           current
    DESCRIPTION
        "Entry for the cucsVnicInternalProfileTable table."
    INDEX { cucsVnicInternalProfileInstanceId }
    ::= { cucsVnicInternalProfileTable 1 }

CucsVnicInternalProfileEntry ::= SEQUENCE {
    cucsVnicInternalProfileInstanceId                                CucsManagedObjectId,
    cucsVnicInternalProfileDn                                        CucsManagedObjectDn,
    cucsVnicInternalProfileRn                                        SnmpAdminString,
    cucsVnicInternalProfileDescr                                     SnmpAdminString,
    cucsVnicInternalProfileIntId                                     SnmpAdminString,
    cucsVnicInternalProfileMaxPorts                                  Gauge32,
    cucsVnicInternalProfileName                                      SnmpAdminString,
    cucsVnicInternalProfilePolicyLevel                               Gauge32,
    cucsVnicInternalProfilePolicyOwner                               CucsPolicyPolicyOwner
}

cucsVnicInternalProfileInstanceId OBJECT-TYPE
    SYNTAX       CucsManagedObjectId
    MAX-ACCESS   not-accessible
    STATUS       current
    DESCRIPTION
        "Instance identifier of the managed object."
    ::= { cucsVnicInternalProfileEntry 1 }

cucsVnicInternalProfileDn OBJECT-TYPE
    SYNTAX       CucsManagedObjectDn
    MAX-ACCESS   read-only
    STATUS       current
    DESCRIPTION
        "Cisco UCS vnic:InternalProfile:dn managed object property"
    ::= { cucsVnicInternalProfileEntry 2 }

cucsVnicInternalProfileRn OBJECT-TYPE
    SYNTAX       SnmpAdminString
    MAX-ACCESS   read-only
    STATUS       current
    DESCRIPTION
        "Cisco UCS vnic:InternalProfile:rn managed object property"
    ::= { cucsVnicInternalProfileEntry 3 }

cucsVnicInternalProfileDescr OBJECT-TYPE
    SYNTAX       SnmpAdminString
    MAX-ACCESS   read-only
    STATUS       current
    DESCRIPTION
        "Cisco UCS vnic:InternalProfile:descr managed object property"
    ::= { cucsVnicInternalProfileEntry 4 }

cucsVnicInternalProfileIntId OBJECT-TYPE
    SYNTAX       SnmpAdminString
    MAX-ACCESS   read-only
    STATUS       current
    DESCRIPTION
        "Cisco UCS vnic:InternalProfile:intId managed object property"
    ::= { cucsVnicInternalProfileEntry 5 }

cucsVnicInternalProfileMaxPorts OBJECT-TYPE
    SYNTAX       Gauge32
    MAX-ACCESS   read-only
    STATUS       current
    DESCRIPTION
        "Cisco UCS vnic:InternalProfile:maxPorts managed object property"
    ::= { cucsVnicInternalProfileEntry 6 }

cucsVnicInternalProfileName OBJECT-TYPE
    SYNTAX       SnmpAdminString
    MAX-ACCESS   read-only
    STATUS       current
    DESCRIPTION
        "Cisco UCS vnic:InternalProfile:name managed object property"
    ::= { cucsVnicInternalProfileEntry 7 }

cucsVnicInternalProfilePolicyLevel OBJECT-TYPE
    SYNTAX       Gauge32
    MAX-ACCESS   read-only
    STATUS       current
    DESCRIPTION
        "Cisco UCS vnic:InternalProfile:policyLevel managed
        object property"
    ::= { cucsVnicInternalProfileEntry 8 }

cucsVnicInternalProfilePolicyOwner OBJECT-TYPE
    SYNTAX       CucsPolicyPolicyOwner
    MAX-ACCESS   read-only
    STATUS       current
    DESCRIPTION
        "Cisco UCS vnic:InternalProfile:policyOwner managed
        object property"
    ::= { cucsVnicInternalProfileEntry 9 }

cucsVnicIpV4HistoryTable OBJECT-TYPE
    SYNTAX           SEQUENCE OF CucsVnicIpV4HistoryEntry
    MAX-ACCESS       not-accessible
    STATUS           current
    DESCRIPTION
        "Cisco UCS vnic:IpV4History managed object table"
    ::= { cucsVnicObjects 60 }

cucsVnicIpV4HistoryEntry OBJECT-TYPE
    SYNTAX           CucsVnicIpV4HistoryEntry
    MAX-ACCESS       not-accessible
    STATUS           current
    DESCRIPTION
        "Entry for the cucsVnicIpV4HistoryTable table."
    INDEX { cucsVnicIpV4HistoryInstanceId }
    ::= { cucsVnicIpV4HistoryTable 1 }

CucsVnicIpV4HistoryEntry ::= SEQUENCE {
    cucsVnicIpV4HistoryInstanceId                                    CucsManagedObjectId,
    cucsVnicIpV4HistoryDn                                            CucsManagedObjectDn,
    cucsVnicIpV4HistoryRn                                            SnmpAdminString,
    cucsVnicIpV4HistoryOldIpV4Addr                                   InetAddressIPv4
}

cucsVnicIpV4HistoryInstanceId OBJECT-TYPE
    SYNTAX       CucsManagedObjectId
    MAX-ACCESS   not-accessible
    STATUS       current
    DESCRIPTION
        "Instance identifier of the managed object."
    ::= { cucsVnicIpV4HistoryEntry 1 }

cucsVnicIpV4HistoryDn OBJECT-TYPE
    SYNTAX       CucsManagedObjectDn
    MAX-ACCESS   read-only
    STATUS       current
    DESCRIPTION
        "Cisco UCS vnic:IpV4History:dn managed object property"
    ::= { cucsVnicIpV4HistoryEntry 2 }

cucsVnicIpV4HistoryRn OBJECT-TYPE
    SYNTAX       SnmpAdminString
    MAX-ACCESS   read-only
    STATUS       current
    DESCRIPTION
        "Cisco UCS vnic:IpV4History:rn managed object property"
    ::= { cucsVnicIpV4HistoryEntry 3 }

cucsVnicIpV4HistoryOldIpV4Addr OBJECT-TYPE
    SYNTAX       InetAddressIPv4
    MAX-ACCESS   read-only
    STATUS       current
    DESCRIPTION
        "Cisco UCS vnic:IpV4History:oldIpV4Addr managed object property"
    ::= { cucsVnicIpV4HistoryEntry 4 }

cucsVnicIpV4MgmtPooledAddrTable OBJECT-TYPE
    SYNTAX           SEQUENCE OF CucsVnicIpV4MgmtPooledAddrEntry
    MAX-ACCESS       not-accessible
    STATUS           current
    DESCRIPTION
        "Cisco UCS vnic:IpV4MgmtPooledAddr managed object table"
    ::= { cucsVnicObjects 65 }

cucsVnicIpV4MgmtPooledAddrEntry OBJECT-TYPE
    SYNTAX           CucsVnicIpV4MgmtPooledAddrEntry
    MAX-ACCESS       not-accessible
    STATUS           current
    DESCRIPTION
        "Entry for the cucsVnicIpV4MgmtPooledAddrTable table."
    INDEX { cucsVnicIpV4MgmtPooledAddrInstanceId }
    ::= { cucsVnicIpV4MgmtPooledAddrTable 1 }

CucsVnicIpV4MgmtPooledAddrEntry ::= SEQUENCE {
    cucsVnicIpV4MgmtPooledAddrInstanceId                             CucsManagedObjectId,
    cucsVnicIpV4MgmtPooledAddrDn                                     CucsManagedObjectDn,
    cucsVnicIpV4MgmtPooledAddrRn                                     SnmpAdminString,
    cucsVnicIpV4MgmtPooledAddrAddr                                   InetAddressIPv4,
    cucsVnicIpV4MgmtPooledAddrDefGw                                  InetAddressIPv4,
    cucsVnicIpV4MgmtPooledAddrName                                   SnmpAdminString,
    cucsVnicIpV4MgmtPooledAddrOperName                               SnmpAdminString,
    cucsVnicIpV4MgmtPooledAddrSubnet                                 InetAddressIPv4,
    cucsVnicIpV4MgmtPooledAddrPrimDns                                InetAddressIPv4,
    cucsVnicIpV4MgmtPooledAddrSecDns                                 InetAddressIPv4
}

cucsVnicIpV4MgmtPooledAddrInstanceId OBJECT-TYPE
    SYNTAX       CucsManagedObjectId
    MAX-ACCESS   not-accessible
    STATUS       current
    DESCRIPTION
        "Instance identifier of the managed object."
    ::= { cucsVnicIpV4MgmtPooledAddrEntry 1 }

cucsVnicIpV4MgmtPooledAddrDn OBJECT-TYPE
    SYNTAX       CucsManagedObjectDn
    MAX-ACCESS   read-only
    STATUS       current
    DESCRIPTION
        "Cisco UCS vnic:IpV4MgmtPooledAddr:dn managed object property"
    ::= { cucsVnicIpV4MgmtPooledAddrEntry 2 }

cucsVnicIpV4MgmtPooledAddrRn OBJECT-TYPE
    SYNTAX       SnmpAdminString
    MAX-ACCESS   read-only
    STATUS       current
    DESCRIPTION
        "Cisco UCS vnic:IpV4MgmtPooledAddr:rn managed object property"
    ::= { cucsVnicIpV4MgmtPooledAddrEntry 3 }

cucsVnicIpV4MgmtPooledAddrAddr OBJECT-TYPE
    SYNTAX       InetAddressIPv4
    MAX-ACCESS   read-only
    STATUS       current
    DESCRIPTION
        "Cisco UCS vnic:IpV4MgmtPooledAddr:addr managed object property"
    ::= { cucsVnicIpV4MgmtPooledAddrEntry 4 }

cucsVnicIpV4MgmtPooledAddrDefGw OBJECT-TYPE
    SYNTAX       InetAddressIPv4
    MAX-ACCESS   read-only
    STATUS       current
    DESCRIPTION
        "Cisco UCS vnic:IpV4MgmtPooledAddr:defGw managed object property"
    ::= { cucsVnicIpV4MgmtPooledAddrEntry 5 }

cucsVnicIpV4MgmtPooledAddrName OBJECT-TYPE
    SYNTAX       SnmpAdminString
    MAX-ACCESS   read-only
    STATUS       current
    DESCRIPTION
        "Cisco UCS vnic:IpV4MgmtPooledAddr:name managed object property"
    ::= { cucsVnicIpV4MgmtPooledAddrEntry 6 }

cucsVnicIpV4MgmtPooledAddrOperName OBJECT-TYPE
    SYNTAX       SnmpAdminString
    MAX-ACCESS   read-only
    STATUS       current
    DESCRIPTION
        "Cisco UCS vnic:IpV4MgmtPooledAddr:operName managed
        object property"
    ::= { cucsVnicIpV4MgmtPooledAddrEntry 7 }

cucsVnicIpV4MgmtPooledAddrSubnet OBJECT-TYPE
    SYNTAX       InetAddressIPv4
    MAX-ACCESS   read-only
    STATUS       current
    DESCRIPTION
        "Cisco UCS vnic:IpV4MgmtPooledAddr:subnet managed object property"
    ::= { cucsVnicIpV4MgmtPooledAddrEntry 8 }

cucsVnicIpV4MgmtPooledAddrPrimDns OBJECT-TYPE
    SYNTAX       InetAddressIPv4
    MAX-ACCESS   read-only
    STATUS       current
    DESCRIPTION
        "Cisco UCS vnic:IpV4MgmtPooledAddr:primDns managed
        object property"
    ::= { cucsVnicIpV4MgmtPooledAddrEntry 9 }

cucsVnicIpV4MgmtPooledAddrSecDns OBJECT-TYPE
    SYNTAX       InetAddressIPv4
    MAX-ACCESS   read-only
    STATUS       current
    DESCRIPTION
        "Cisco UCS vnic:IpV4MgmtPooledAddr:secDns managed object property"
    ::= { cucsVnicIpV4MgmtPooledAddrEntry 10 }

cucsVnicIpV4PooledAddrTable OBJECT-TYPE
    SYNTAX           SEQUENCE OF CucsVnicIpV4PooledAddrEntry
    MAX-ACCESS       not-accessible
    STATUS           current
    DESCRIPTION
        "Cisco UCS vnic:IpV4PooledAddr managed object table"
    ::= { cucsVnicObjects 20 }

cucsVnicIpV4PooledAddrEntry OBJECT-TYPE
    SYNTAX           CucsVnicIpV4PooledAddrEntry
    MAX-ACCESS       not-accessible
    STATUS           current
    DESCRIPTION
        "Entry for the cucsVnicIpV4PooledAddrTable table."
    INDEX { cucsVnicIpV4PooledAddrInstanceId }
    ::= { cucsVnicIpV4PooledAddrTable 1 }

CucsVnicIpV4PooledAddrEntry ::= SEQUENCE {
    cucsVnicIpV4PooledAddrInstanceId                                 CucsManagedObjectId,
    cucsVnicIpV4PooledAddrDn                                         CucsManagedObjectDn,
    cucsVnicIpV4PooledAddrRn                                         SnmpAdminString,
    cucsVnicIpV4PooledAddrAddr                                       InetAddressIPv4,
    cucsVnicIpV4PooledAddrDefGw                                      InetAddressIPv4,
    cucsVnicIpV4PooledAddrName                                       SnmpAdminString,
    cucsVnicIpV4PooledAddrSubnet                                     InetAddressIPv4,
    cucsVnicIpV4PooledAddrOperName                                   SnmpAdminString,
    cucsVnicIpV4PooledAddrPrimDns                                    InetAddressIPv4,
    cucsVnicIpV4PooledAddrSecDns                                     InetAddressIPv4
}

cucsVnicIpV4PooledAddrInstanceId OBJECT-TYPE
    SYNTAX       CucsManagedObjectId
    MAX-ACCESS   not-accessible
    STATUS       current
    DESCRIPTION
        "Instance identifier of the managed object."
    ::= { cucsVnicIpV4PooledAddrEntry 1 }

cucsVnicIpV4PooledAddrDn OBJECT-TYPE
    SYNTAX       CucsManagedObjectDn
    MAX-ACCESS   read-only
    STATUS       current
    DESCRIPTION
        "Cisco UCS vnic:IpV4PooledAddr:dn managed object property"
    ::= { cucsVnicIpV4PooledAddrEntry 2 }

cucsVnicIpV4PooledAddrRn OBJECT-TYPE
    SYNTAX       SnmpAdminString
    MAX-ACCESS   read-only
    STATUS       current
    DESCRIPTION
        "Cisco UCS vnic:IpV4PooledAddr:rn managed object property"
    ::= { cucsVnicIpV4PooledAddrEntry 3 }

cucsVnicIpV4PooledAddrAddr OBJECT-TYPE
    SYNTAX       InetAddressIPv4
    MAX-ACCESS   read-only
    STATUS       current
    DESCRIPTION
        "Cisco UCS vnic:IpV4PooledAddr:addr managed object property"
    ::= { cucsVnicIpV4PooledAddrEntry 4 }

cucsVnicIpV4PooledAddrDefGw OBJECT-TYPE
    SYNTAX       InetAddressIPv4
    MAX-ACCESS   read-only
    STATUS       current
    DESCRIPTION
        "Cisco UCS vnic:IpV4PooledAddr:defGw managed object property"
    ::= { cucsVnicIpV4PooledAddrEntry 5 }

cucsVnicIpV4PooledAddrName OBJECT-TYPE
    SYNTAX       SnmpAdminString
    MAX-ACCESS   read-only
    STATUS       current
    DESCRIPTION
        "Cisco UCS vnic:IpV4PooledAddr:name managed object property"
    ::= { cucsVnicIpV4PooledAddrEntry 6 }

cucsVnicIpV4PooledAddrSubnet OBJECT-TYPE
    SYNTAX       InetAddressIPv4
    MAX-ACCESS   read-only
    STATUS       current
    DESCRIPTION
        "Cisco UCS vnic:IpV4PooledAddr:subnet managed object property"
    ::= { cucsVnicIpV4PooledAddrEntry 7 }

cucsVnicIpV4PooledAddrOperName OBJECT-TYPE
    SYNTAX       SnmpAdminString
    MAX-ACCESS   read-only
    STATUS       current
    DESCRIPTION
        "Cisco UCS vnic:IpV4PooledAddr:operName managed object property"
    ::= { cucsVnicIpV4PooledAddrEntry 8 }

cucsVnicIpV4PooledAddrPrimDns OBJECT-TYPE
    SYNTAX       InetAddressIPv4
    MAX-ACCESS   read-only
    STATUS       current
    DESCRIPTION
        "Cisco UCS vnic:IpV4PooledAddr:primDns managed object property"
    ::= { cucsVnicIpV4PooledAddrEntry 9 }

cucsVnicIpV4PooledAddrSecDns OBJECT-TYPE
    SYNTAX       InetAddressIPv4
    MAX-ACCESS   read-only
    STATUS       current
    DESCRIPTION
        "Cisco UCS vnic:IpV4PooledAddr:secDns managed object property"
    ::= { cucsVnicIpV4PooledAddrEntry 10 }

cucsVnicIpV4ProfDerivedAddrTable OBJECT-TYPE
    SYNTAX           SEQUENCE OF CucsVnicIpV4ProfDerivedAddrEntry
    MAX-ACCESS       not-accessible
    STATUS           current
    DESCRIPTION
        "Cisco UCS vnic:IpV4ProfDerivedAddr managed object table"
    ::= { cucsVnicObjects 21 }

cucsVnicIpV4ProfDerivedAddrEntry OBJECT-TYPE
    SYNTAX           CucsVnicIpV4ProfDerivedAddrEntry
    MAX-ACCESS       not-accessible
    STATUS           current
    DESCRIPTION
        "Entry for the cucsVnicIpV4ProfDerivedAddrTable table."
    INDEX { cucsVnicIpV4ProfDerivedAddrInstanceId }
    ::= { cucsVnicIpV4ProfDerivedAddrTable 1 }

CucsVnicIpV4ProfDerivedAddrEntry ::= SEQUENCE {
    cucsVnicIpV4ProfDerivedAddrInstanceId                            CucsManagedObjectId,
    cucsVnicIpV4ProfDerivedAddrDn                                    CucsManagedObjectDn,
    cucsVnicIpV4ProfDerivedAddrRn                                    SnmpAdminString,
    cucsVnicIpV4ProfDerivedAddrAddr                                  InetAddressIPv4,
    cucsVnicIpV4ProfDerivedAddrDefGw                                 InetAddressIPv4,
    cucsVnicIpV4ProfDerivedAddrSubnet                                InetAddressIPv4
}

cucsVnicIpV4ProfDerivedAddrInstanceId OBJECT-TYPE
    SYNTAX       CucsManagedObjectId
    MAX-ACCESS   not-accessible
    STATUS       current
    DESCRIPTION
        "Instance identifier of the managed object."
    ::= { cucsVnicIpV4ProfDerivedAddrEntry 1 }

cucsVnicIpV4ProfDerivedAddrDn OBJECT-TYPE
    SYNTAX       CucsManagedObjectDn
    MAX-ACCESS   read-only
    STATUS       current
    DESCRIPTION
        "Cisco UCS vnic:IpV4ProfDerivedAddr:dn managed object property"
    ::= { cucsVnicIpV4ProfDerivedAddrEntry 2 }

cucsVnicIpV4ProfDerivedAddrRn OBJECT-TYPE
    SYNTAX       SnmpAdminString
    MAX-ACCESS   read-only
    STATUS       current
    DESCRIPTION
        "Cisco UCS vnic:IpV4ProfDerivedAddr:rn managed object property"
    ::= { cucsVnicIpV4ProfDerivedAddrEntry 3 }

cucsVnicIpV4ProfDerivedAddrAddr OBJECT-TYPE
    SYNTAX       InetAddressIPv4
    MAX-ACCESS   read-only
    STATUS       current
    DESCRIPTION
        "Cisco UCS vnic:IpV4ProfDerivedAddr:addr managed object property"
    ::= { cucsVnicIpV4ProfDerivedAddrEntry 4 }

cucsVnicIpV4ProfDerivedAddrDefGw OBJECT-TYPE
    SYNTAX       InetAddressIPv4
    MAX-ACCESS   read-only
    STATUS       current
    DESCRIPTION
        "Cisco UCS vnic:IpV4ProfDerivedAddr:defGw managed object property"
    ::= { cucsVnicIpV4ProfDerivedAddrEntry 5 }

cucsVnicIpV4ProfDerivedAddrSubnet OBJECT-TYPE
    SYNTAX       InetAddressIPv4
    MAX-ACCESS   read-only
    STATUS       current
    DESCRIPTION
        "Cisco UCS vnic:IpV4ProfDerivedAddr:subnet managed
        object property"
    ::= { cucsVnicIpV4ProfDerivedAddrEntry 6 }

cucsVnicIpV4StaticAddrTable OBJECT-TYPE
    SYNTAX           SEQUENCE OF CucsVnicIpV4StaticAddrEntry
    MAX-ACCESS       not-accessible
    STATUS           current
    DESCRIPTION
        "Cisco UCS vnic:IpV4StaticAddr managed object table"
    ::= { cucsVnicObjects 22 }

cucsVnicIpV4StaticAddrEntry OBJECT-TYPE
    SYNTAX           CucsVnicIpV4StaticAddrEntry
    MAX-ACCESS       not-accessible
    STATUS           current
    DESCRIPTION
        "Entry for the cucsVnicIpV4StaticAddrTable table."
    INDEX { cucsVnicIpV4StaticAddrInstanceId }
    ::= { cucsVnicIpV4StaticAddrTable 1 }

CucsVnicIpV4StaticAddrEntry ::= SEQUENCE {
    cucsVnicIpV4StaticAddrInstanceId                                 CucsManagedObjectId,
    cucsVnicIpV4StaticAddrDn                                         CucsManagedObjectDn,
    cucsVnicIpV4StaticAddrRn                                         SnmpAdminString,
    cucsVnicIpV4StaticAddrAddr                                       InetAddressIPv4,
    cucsVnicIpV4StaticAddrDefGw                                      InetAddressIPv4,
    cucsVnicIpV4StaticAddrSubnet                                     InetAddressIPv4,
    cucsVnicIpV4StaticAddrPrimDns                                    InetAddressIPv4,
    cucsVnicIpV4StaticAddrSecDns                                     InetAddressIPv4
}

cucsVnicIpV4StaticAddrInstanceId OBJECT-TYPE
    SYNTAX       CucsManagedObjectId
    MAX-ACCESS   not-accessible
    STATUS       current
    DESCRIPTION
        "Instance identifier of the managed object."
    ::= { cucsVnicIpV4StaticAddrEntry 1 }

cucsVnicIpV4StaticAddrDn OBJECT-TYPE
    SYNTAX       CucsManagedObjectDn
    MAX-ACCESS   read-only
    STATUS       current
    DESCRIPTION
        "Cisco UCS vnic:IpV4StaticAddr:dn managed object property"
    ::= { cucsVnicIpV4StaticAddrEntry 2 }

cucsVnicIpV4StaticAddrRn OBJECT-TYPE
    SYNTAX       SnmpAdminString
    MAX-ACCESS   read-only
    STATUS       current
    DESCRIPTION
        "Cisco UCS vnic:IpV4StaticAddr:rn managed object property"
    ::= { cucsVnicIpV4StaticAddrEntry 3 }

cucsVnicIpV4StaticAddrAddr OBJECT-TYPE
    SYNTAX       InetAddressIPv4
    MAX-ACCESS   read-only
    STATUS       current
    DESCRIPTION
        "Cisco UCS vnic:IpV4StaticAddr:addr managed object property"
    ::= { cucsVnicIpV4StaticAddrEntry 4 }

cucsVnicIpV4StaticAddrDefGw OBJECT-TYPE
    SYNTAX       InetAddressIPv4
    MAX-ACCESS   read-only
    STATUS       current
    DESCRIPTION
        "Cisco UCS vnic:IpV4StaticAddr:defGw managed object property"
    ::= { cucsVnicIpV4StaticAddrEntry 5 }

cucsVnicIpV4StaticAddrSubnet OBJECT-TYPE
    SYNTAX       InetAddressIPv4
    MAX-ACCESS   read-only
    STATUS       current
    DESCRIPTION
        "Cisco UCS vnic:IpV4StaticAddr:subnet managed object property"
    ::= { cucsVnicIpV4StaticAddrEntry 6 }

cucsVnicIpV4StaticAddrPrimDns OBJECT-TYPE
    SYNTAX       InetAddressIPv4
    MAX-ACCESS   read-only
    STATUS       current
    DESCRIPTION
        "Cisco UCS vnic:IpV4StaticAddr:primDns managed object property"
    ::= { cucsVnicIpV4StaticAddrEntry 7 }

cucsVnicIpV4StaticAddrSecDns OBJECT-TYPE
    SYNTAX       InetAddressIPv4
    MAX-ACCESS   read-only
    STATUS       current
    DESCRIPTION
        "Cisco UCS vnic:IpV4StaticAddr:secDns managed object property"
    ::= { cucsVnicIpV4StaticAddrEntry 8 }

cucsVnicIpV6HistoryTable OBJECT-TYPE
    SYNTAX           SEQUENCE OF CucsVnicIpV6HistoryEntry
    MAX-ACCESS       not-accessible
    STATUS           current
    DESCRIPTION
        "Cisco UCS vnic:IpV6History managed object table"
    ::= { cucsVnicObjects 73 }

cucsVnicIpV6HistoryEntry OBJECT-TYPE
    SYNTAX           CucsVnicIpV6HistoryEntry
    MAX-ACCESS       not-accessible
    STATUS           current
    DESCRIPTION
        "Entry for the cucsVnicIpV6HistoryTable table."
    INDEX { cucsVnicIpV6HistoryInstanceId }
    ::= { cucsVnicIpV6HistoryTable 1 }

CucsVnicIpV6HistoryEntry ::= SEQUENCE {
    cucsVnicIpV6HistoryInstanceId                                    CucsManagedObjectId,
    cucsVnicIpV6HistoryDn                                            CucsManagedObjectDn,
    cucsVnicIpV6HistoryRn                                            SnmpAdminString,
    cucsVnicIpV6HistoryOldIpV6Addr                                   InetAddressIPv6
}

cucsVnicIpV6HistoryInstanceId OBJECT-TYPE
    SYNTAX       CucsManagedObjectId
    MAX-ACCESS   not-accessible
    STATUS       current
    DESCRIPTION
        "Instance identifier of the managed object."
    ::= { cucsVnicIpV6HistoryEntry 1 }

cucsVnicIpV6HistoryDn OBJECT-TYPE
    SYNTAX       CucsManagedObjectDn
    MAX-ACCESS   read-only
    STATUS       current
    DESCRIPTION
        "Cisco UCS vnic:IpV6History:dn managed object property"
    ::= { cucsVnicIpV6HistoryEntry 2 }

cucsVnicIpV6HistoryRn OBJECT-TYPE
    SYNTAX       SnmpAdminString
    MAX-ACCESS   read-only
    STATUS       current
    DESCRIPTION
        "Cisco UCS vnic:IpV6History:rn managed object property"
    ::= { cucsVnicIpV6HistoryEntry 3 }

cucsVnicIpV6HistoryOldIpV6Addr OBJECT-TYPE
    SYNTAX       InetAddressIPv6
    MAX-ACCESS   read-only
    STATUS       current
    DESCRIPTION
        "Cisco UCS vnic:IpV6History:oldIpV6Addr managed object property"
    ::= { cucsVnicIpV6HistoryEntry 4 }

cucsVnicIpV6MgmtPooledAddrTable OBJECT-TYPE
    SYNTAX           SEQUENCE OF CucsVnicIpV6MgmtPooledAddrEntry
    MAX-ACCESS       not-accessible
    STATUS           current
    DESCRIPTION
        "Cisco UCS vnic:IpV6MgmtPooledAddr managed object table"
    ::= { cucsVnicObjects 66 }

cucsVnicIpV6MgmtPooledAddrEntry OBJECT-TYPE
    SYNTAX           CucsVnicIpV6MgmtPooledAddrEntry
    MAX-ACCESS       not-accessible
    STATUS           current
    DESCRIPTION
        "Entry for the cucsVnicIpV6MgmtPooledAddrTable table."
    INDEX { cucsVnicIpV6MgmtPooledAddrInstanceId }
    ::= { cucsVnicIpV6MgmtPooledAddrTable 1 }

CucsVnicIpV6MgmtPooledAddrEntry ::= SEQUENCE {
    cucsVnicIpV6MgmtPooledAddrInstanceId                             CucsManagedObjectId,
    cucsVnicIpV6MgmtPooledAddrDn                                     CucsManagedObjectDn,
    cucsVnicIpV6MgmtPooledAddrRn                                     SnmpAdminString,
    cucsVnicIpV6MgmtPooledAddrAddr                                   InetAddressIPv6,
    cucsVnicIpV6MgmtPooledAddrDefGw                                  InetAddressIPv6,
    cucsVnicIpV6MgmtPooledAddrName                                   SnmpAdminString,
    cucsVnicIpV6MgmtPooledAddrOperName                               SnmpAdminString,
    cucsVnicIpV6MgmtPooledAddrPrefix                                 Gauge32,
    cucsVnicIpV6MgmtPooledAddrPrimDns                                InetAddressIPv6,
    cucsVnicIpV6MgmtPooledAddrSecDns                                 InetAddressIPv6
}

cucsVnicIpV6MgmtPooledAddrInstanceId OBJECT-TYPE
    SYNTAX       CucsManagedObjectId
    MAX-ACCESS   not-accessible
    STATUS       current
    DESCRIPTION
        "Instance identifier of the managed object."
    ::= { cucsVnicIpV6MgmtPooledAddrEntry 1 }

cucsVnicIpV6MgmtPooledAddrDn OBJECT-TYPE
    SYNTAX       CucsManagedObjectDn
    MAX-ACCESS   read-only
    STATUS       current
    DESCRIPTION
        "Cisco UCS vnic:IpV6MgmtPooledAddr:dn managed object property"
    ::= { cucsVnicIpV6MgmtPooledAddrEntry 2 }

cucsVnicIpV6MgmtPooledAddrRn OBJECT-TYPE
    SYNTAX       SnmpAdminString
    MAX-ACCESS   read-only
    STATUS       current
    DESCRIPTION
        "Cisco UCS vnic:IpV6MgmtPooledAddr:rn managed object property"
    ::= { cucsVnicIpV6MgmtPooledAddrEntry 3 }

cucsVnicIpV6MgmtPooledAddrAddr OBJECT-TYPE
    SYNTAX       InetAddressIPv6
    MAX-ACCESS   read-only
    STATUS       current
    DESCRIPTION
        "Cisco UCS vnic:IpV6MgmtPooledAddr:addr managed object property"
    ::= { cucsVnicIpV6MgmtPooledAddrEntry 4 }

cucsVnicIpV6MgmtPooledAddrDefGw OBJECT-TYPE
    SYNTAX       InetAddressIPv6
    MAX-ACCESS   read-only
    STATUS       current
    DESCRIPTION
        "Cisco UCS vnic:IpV6MgmtPooledAddr:defGw managed object property"
    ::= { cucsVnicIpV6MgmtPooledAddrEntry 5 }

cucsVnicIpV6MgmtPooledAddrName OBJECT-TYPE
    SYNTAX       SnmpAdminString
    MAX-ACCESS   read-only
    STATUS       current
    DESCRIPTION
        "Cisco UCS vnic:IpV6MgmtPooledAddr:name managed object property"
    ::= { cucsVnicIpV6MgmtPooledAddrEntry 6 }

cucsVnicIpV6MgmtPooledAddrOperName OBJECT-TYPE
    SYNTAX       SnmpAdminString
    MAX-ACCESS   read-only
    STATUS       current
    DESCRIPTION
        "Cisco UCS vnic:IpV6MgmtPooledAddr:operName managed
        object property"
    ::= { cucsVnicIpV6MgmtPooledAddrEntry 7 }

cucsVnicIpV6MgmtPooledAddrPrefix OBJECT-TYPE
    SYNTAX       Gauge32
    MAX-ACCESS   read-only
    STATUS       current
    DESCRIPTION
        "Cisco UCS vnic:IpV6MgmtPooledAddr:prefix managed object property"
    ::= { cucsVnicIpV6MgmtPooledAddrEntry 8 }

cucsVnicIpV6MgmtPooledAddrPrimDns OBJECT-TYPE
    SYNTAX       InetAddressIPv6
    MAX-ACCESS   read-only
    STATUS       current
    DESCRIPTION
        "Cisco UCS vnic:IpV6MgmtPooledAddr:primDns managed
        object property"
    ::= { cucsVnicIpV6MgmtPooledAddrEntry 9 }

cucsVnicIpV6MgmtPooledAddrSecDns OBJECT-TYPE
    SYNTAX       InetAddressIPv6
    MAX-ACCESS   read-only
    STATUS       current
    DESCRIPTION
        "Cisco UCS vnic:IpV6MgmtPooledAddr:secDns managed object property"
    ::= { cucsVnicIpV6MgmtPooledAddrEntry 10 }

cucsVnicIpV6StaticAddrTable OBJECT-TYPE
    SYNTAX           SEQUENCE OF CucsVnicIpV6StaticAddrEntry
    MAX-ACCESS       not-accessible
    STATUS           current
    DESCRIPTION
        "Cisco UCS vnic:IpV6StaticAddr managed object table"
    ::= { cucsVnicObjects 67 }

cucsVnicIpV6StaticAddrEntry OBJECT-TYPE
    SYNTAX           CucsVnicIpV6StaticAddrEntry
    MAX-ACCESS       not-accessible
    STATUS           current
    DESCRIPTION
        "Entry for the cucsVnicIpV6StaticAddrTable table."
    INDEX { cucsVnicIpV6StaticAddrInstanceId }
    ::= { cucsVnicIpV6StaticAddrTable 1 }

CucsVnicIpV6StaticAddrEntry ::= SEQUENCE {
    cucsVnicIpV6StaticAddrInstanceId                                 CucsManagedObjectId,
    cucsVnicIpV6StaticAddrDn                                         CucsManagedObjectDn,
    cucsVnicIpV6StaticAddrRn                                         SnmpAdminString,
    cucsVnicIpV6StaticAddrAddr                                       InetAddressIPv6,
    cucsVnicIpV6StaticAddrDefGw                                      InetAddressIPv6,
    cucsVnicIpV6StaticAddrPrefix                                     Gauge32,
    cucsVnicIpV6StaticAddrPrimDns                                    InetAddressIPv6,
    cucsVnicIpV6StaticAddrSecDns                                     InetAddressIPv6
}

cucsVnicIpV6StaticAddrInstanceId OBJECT-TYPE
    SYNTAX       CucsManagedObjectId
    MAX-ACCESS   not-accessible
    STATUS       current
    DESCRIPTION
        "Instance identifier of the managed object."
    ::= { cucsVnicIpV6StaticAddrEntry 1 }

cucsVnicIpV6StaticAddrDn OBJECT-TYPE
    SYNTAX       CucsManagedObjectDn
    MAX-ACCESS   read-only
    STATUS       current
    DESCRIPTION
        "Cisco UCS vnic:IpV6StaticAddr:dn managed object property"
    ::= { cucsVnicIpV6StaticAddrEntry 2 }

cucsVnicIpV6StaticAddrRn OBJECT-TYPE
    SYNTAX       SnmpAdminString
    MAX-ACCESS   read-only
    STATUS       current
    DESCRIPTION
        "Cisco UCS vnic:IpV6StaticAddr:rn managed object property"
    ::= { cucsVnicIpV6StaticAddrEntry 3 }

cucsVnicIpV6StaticAddrAddr OBJECT-TYPE
    SYNTAX       InetAddressIPv6
    MAX-ACCESS   read-only
    STATUS       current
    DESCRIPTION
        "Cisco UCS vnic:IpV6StaticAddr:addr managed object property"
    ::= { cucsVnicIpV6StaticAddrEntry 4 }

cucsVnicIpV6StaticAddrDefGw OBJECT-TYPE
    SYNTAX       InetAddressIPv6
    MAX-ACCESS   read-only
    STATUS       current
    DESCRIPTION
        "Cisco UCS vnic:IpV6StaticAddr:defGw managed object property"
    ::= { cucsVnicIpV6StaticAddrEntry 5 }

cucsVnicIpV6StaticAddrPrefix OBJECT-TYPE
    SYNTAX       Gauge32
    MAX-ACCESS   read-only
    STATUS       current
    DESCRIPTION
        "Cisco UCS vnic:IpV6StaticAddr:prefix managed object property"
    ::= { cucsVnicIpV6StaticAddrEntry 6 }

cucsVnicIpV6StaticAddrPrimDns OBJECT-TYPE
    SYNTAX       InetAddressIPv6
    MAX-ACCESS   read-only
    STATUS       current
    DESCRIPTION
        "Cisco UCS vnic:IpV6StaticAddr:primDns managed object property"
    ::= { cucsVnicIpV6StaticAddrEntry 7 }

cucsVnicIpV6StaticAddrSecDns OBJECT-TYPE
    SYNTAX       InetAddressIPv6
    MAX-ACCESS   read-only
    STATUS       current
    DESCRIPTION
        "Cisco UCS vnic:IpV6StaticAddr:secDns managed object property"
    ::= { cucsVnicIpV6StaticAddrEntry 8 }

cucsVnicIpcTable OBJECT-TYPE
    SYNTAX           SEQUENCE OF CucsVnicIpcEntry
    MAX-ACCESS       not-accessible
    STATUS           current
    DESCRIPTION
        "Cisco UCS vnic:Ipc managed object table"
    ::= { cucsVnicObjects 23 }

cucsVnicIpcEntry OBJECT-TYPE
    SYNTAX           CucsVnicIpcEntry
    MAX-ACCESS       not-accessible
    STATUS           current
    DESCRIPTION
        "Entry for the cucsVnicIpcTable table."
    INDEX { cucsVnicIpcInstanceId }
    ::= { cucsVnicIpcTable 1 }

CucsVnicIpcEntry ::= SEQUENCE {
    cucsVnicIpcInstanceId                                            CucsManagedObjectId,
    cucsVnicIpcDn                                                    CucsManagedObjectDn,
    cucsVnicIpcRn                                                    SnmpAdminString,
    cucsVnicIpcAdaptorProfileName                                    SnmpAdminString,
    cucsVnicIpcAddr                                                  MacAddress,
    cucsVnicIpcAdminVcon                                             SnmpAdminString,
    cucsVnicIpcBootDev                                               CucsVnicVnicBootDev,
    cucsVnicIpcConfigState                                           CucsLsConfigState,
    cucsVnicIpcEquipmentDn                                           SnmpAdminString,
    cucsVnicIpcIdentPoolName                                         SnmpAdminString,
    cucsVnicIpcInstType                                              CucsVnicInstantiation,
    cucsVnicIpcMtu                                                   Gauge32,
    cucsVnicIpcName                                                  SnmpAdminString,
    cucsVnicIpcNwCtrlPolicyName                                      SnmpAdminString,
    cucsVnicIpcNwTemplName                                           SnmpAdminString,
    cucsVnicIpcOperAdaptorProfileName                                SnmpAdminString,
    cucsVnicIpcOperIdentPoolName                                     SnmpAdminString,
    cucsVnicIpcOperNwCtrlPolicyName                                  SnmpAdminString,
    cucsVnicIpcOperNwTemplName                                       SnmpAdminString,
    cucsVnicIpcOperOrder                                             Gauge32,
    cucsVnicIpcOperQosPolicyName                                     SnmpAdminString,
    cucsVnicIpcOperSpeed                                             Gauge32,
    cucsVnicIpcOperStatsPolicyName                                   SnmpAdminString,
    cucsVnicIpcOperVcon                                              SnmpAdminString,
    cucsVnicIpcOrder                                                 Gauge32,
    cucsVnicIpcOwner                                                 CucsVnicConnectionOwner,
    cucsVnicIpcPinToGroupName                                        SnmpAdminString,
    cucsVnicIpcQosPolicyName                                         SnmpAdminString,
    cucsVnicIpcStatsPolicyName                                       SnmpAdminString,
    cucsVnicIpcSwitchId                                              CucsVnicEtherBaseSwitchId,
    cucsVnicIpcType                                                  CucsVnicIpcType,
    cucsVnicIpcOperPinToGroupName                                    SnmpAdminString,
    cucsVnicIpcConfigQualifier                                       CucsVnicConfigIssues,
    cucsVnicIpcAdminHostPort                                         CucsFabricHostPortId,
    cucsVnicIpcOperHostPort                                          CucsVnicVnicOperHostPort,
    cucsVnicIpcPurpose                                               CucsAdaptorPurpose,
    cucsVnicIpcAdminCdnName                                          SnmpAdminString,
    cucsVnicIpcOperCdnName                                           SnmpAdminString,
    cucsVnicIpcCdnPropInSync                                         TruthValue,
    cucsVnicIpcCdnSource                                             CucsVnicCdnSource
}

cucsVnicIpcInstanceId OBJECT-TYPE
    SYNTAX       CucsManagedObjectId
    MAX-ACCESS   not-accessible
    STATUS       current
    DESCRIPTION
        "Instance identifier of the managed object."
    ::= { cucsVnicIpcEntry 1 }

cucsVnicIpcDn OBJECT-TYPE
    SYNTAX       CucsManagedObjectDn
    MAX-ACCESS   read-only
    STATUS       current
    DESCRIPTION
        "Cisco UCS vnic:Ipc:dn managed object property"
    ::= { cucsVnicIpcEntry 2 }

cucsVnicIpcRn OBJECT-TYPE
    SYNTAX       SnmpAdminString
    MAX-ACCESS   read-only
    STATUS       current
    DESCRIPTION
        "Cisco UCS vnic:Ipc:rn managed object property"
    ::= { cucsVnicIpcEntry 3 }

cucsVnicIpcAdaptorProfileName OBJECT-TYPE
    SYNTAX       SnmpAdminString
    MAX-ACCESS   read-only
    STATUS       current
    DESCRIPTION
        "Cisco UCS vnic:Ipc:adaptorProfileName managed object property"
    ::= { cucsVnicIpcEntry 4 }

cucsVnicIpcAddr OBJECT-TYPE
    SYNTAX       MacAddress
    MAX-ACCESS   read-only
    STATUS       current
    DESCRIPTION
        "Cisco UCS vnic:Ipc:addr managed object property"
    ::= { cucsVnicIpcEntry 5 }

cucsVnicIpcAdminVcon OBJECT-TYPE
    SYNTAX       SnmpAdminString
    MAX-ACCESS   read-only
    STATUS       current
    DESCRIPTION
        "Cisco UCS vnic:Ipc:adminVcon managed object property"
    ::= { cucsVnicIpcEntry 6 }

cucsVnicIpcBootDev OBJECT-TYPE
    SYNTAX       CucsVnicVnicBootDev
    MAX-ACCESS   read-only
    STATUS       current
    DESCRIPTION
        "Cisco UCS vnic:Ipc:bootDev managed object property"
    ::= { cucsVnicIpcEntry 7 }

cucsVnicIpcConfigState OBJECT-TYPE
    SYNTAX       CucsLsConfigState
    MAX-ACCESS   read-only
    STATUS       current
    DESCRIPTION
        "Cisco UCS vnic:Ipc:configState managed object property"
    ::= { cucsVnicIpcEntry 8 }

cucsVnicIpcEquipmentDn OBJECT-TYPE
    SYNTAX       SnmpAdminString
    MAX-ACCESS   read-only
    STATUS       current
    DESCRIPTION
        "Cisco UCS vnic:Ipc:equipmentDn managed object property"
    ::= { cucsVnicIpcEntry 9 }

cucsVnicIpcIdentPoolName OBJECT-TYPE
    SYNTAX       SnmpAdminString
    MAX-ACCESS   read-only
    STATUS       current
    DESCRIPTION
        "Cisco UCS vnic:Ipc:identPoolName managed object property"
    ::= { cucsVnicIpcEntry 10 }

cucsVnicIpcInstType OBJECT-TYPE
    SYNTAX       CucsVnicInstantiation
    MAX-ACCESS   read-only
    STATUS       current
    DESCRIPTION
        "Cisco UCS vnic:Ipc:instType managed object property"
    ::= { cucsVnicIpcEntry 11 }

cucsVnicIpcMtu OBJECT-TYPE
    SYNTAX       Gauge32
    MAX-ACCESS   read-only
    STATUS       current
    DESCRIPTION
        "Cisco UCS vnic:Ipc:mtu managed object property"
    ::= { cucsVnicIpcEntry 12 }

cucsVnicIpcName OBJECT-TYPE
    SYNTAX       SnmpAdminString
    MAX-ACCESS   read-only
    STATUS       current
    DESCRIPTION
        "Cisco UCS vnic:Ipc:name managed object property"
    ::= { cucsVnicIpcEntry 13 }

cucsVnicIpcNwCtrlPolicyName OBJECT-TYPE
    SYNTAX       SnmpAdminString
    MAX-ACCESS   read-only
    STATUS       current
    DESCRIPTION
        "Cisco UCS vnic:Ipc:nwCtrlPolicyName managed object property"
    ::= { cucsVnicIpcEntry 14 }

cucsVnicIpcNwTemplName OBJECT-TYPE
    SYNTAX       SnmpAdminString
    MAX-ACCESS   read-only
    STATUS       current
    DESCRIPTION
        "Cisco UCS vnic:Ipc:nwTemplName managed object property"
    ::= { cucsVnicIpcEntry 15 }

cucsVnicIpcOperAdaptorProfileName OBJECT-TYPE
    SYNTAX       SnmpAdminString
    MAX-ACCESS   read-only
    STATUS       current
    DESCRIPTION
        "Cisco UCS vnic:Ipc:operAdaptorProfileName managed
        object property"
    ::= { cucsVnicIpcEntry 16 }

cucsVnicIpcOperIdentPoolName OBJECT-TYPE
    SYNTAX       SnmpAdminString
    MAX-ACCESS   read-only
    STATUS       current
    DESCRIPTION
        "Cisco UCS vnic:Ipc:operIdentPoolName managed object property"
    ::= { cucsVnicIpcEntry 17 }

cucsVnicIpcOperNwCtrlPolicyName OBJECT-TYPE
    SYNTAX       SnmpAdminString
    MAX-ACCESS   read-only
    STATUS       current
    DESCRIPTION
        "Cisco UCS vnic:Ipc:operNwCtrlPolicyName managed object property"
    ::= { cucsVnicIpcEntry 18 }

cucsVnicIpcOperNwTemplName OBJECT-TYPE
    SYNTAX       SnmpAdminString
    MAX-ACCESS   read-only
    STATUS       current
    DESCRIPTION
        "Cisco UCS vnic:Ipc:operNwTemplName managed object property"
    ::= { cucsVnicIpcEntry 19 }

cucsVnicIpcOperOrder OBJECT-TYPE
    SYNTAX       Gauge32
    MAX-ACCESS   read-only
    STATUS       current
    DESCRIPTION
        "Cisco UCS vnic:Ipc:operOrder managed object property"
    ::= { cucsVnicIpcEntry 20 }

cucsVnicIpcOperQosPolicyName OBJECT-TYPE
    SYNTAX       SnmpAdminString
    MAX-ACCESS   read-only
    STATUS       current
    DESCRIPTION
        "Cisco UCS vnic:Ipc:operQosPolicyName managed object property"
    ::= { cucsVnicIpcEntry 21 }

cucsVnicIpcOperSpeed OBJECT-TYPE
    SYNTAX       Gauge32
    MAX-ACCESS   read-only
    STATUS       current
    DESCRIPTION
        "Cisco UCS vnic:Ipc:operSpeed managed object property"
    ::= { cucsVnicIpcEntry 22 }

cucsVnicIpcOperStatsPolicyName OBJECT-TYPE
    SYNTAX       SnmpAdminString
    MAX-ACCESS   read-only
    STATUS       current
    DESCRIPTION
        "Cisco UCS vnic:Ipc:operStatsPolicyName managed object property"
    ::= { cucsVnicIpcEntry 23 }

cucsVnicIpcOperVcon OBJECT-TYPE
    SYNTAX       SnmpAdminString
    MAX-ACCESS   read-only
    STATUS       current
    DESCRIPTION
        "Cisco UCS vnic:Ipc:operVcon managed object property"
    ::= { cucsVnicIpcEntry 24 }

cucsVnicIpcOrder OBJECT-TYPE
    SYNTAX       Gauge32
    MAX-ACCESS   read-only
    STATUS       current
    DESCRIPTION
        "Cisco UCS vnic:Ipc:order managed object property"
    ::= { cucsVnicIpcEntry 25 }

cucsVnicIpcOwner OBJECT-TYPE
    SYNTAX       CucsVnicConnectionOwner
    MAX-ACCESS   read-only
    STATUS       current
    DESCRIPTION
        "Cisco UCS vnic:Ipc:owner managed object property"
    ::= { cucsVnicIpcEntry 26 }

cucsVnicIpcPinToGroupName OBJECT-TYPE
    SYNTAX       SnmpAdminString
    MAX-ACCESS   read-only
    STATUS       current
    DESCRIPTION
        "Cisco UCS vnic:Ipc:pinToGroupName managed object property"
    ::= { cucsVnicIpcEntry 27 }

cucsVnicIpcQosPolicyName OBJECT-TYPE
    SYNTAX       SnmpAdminString
    MAX-ACCESS   read-only
    STATUS       current
    DESCRIPTION
        "Cisco UCS vnic:Ipc:qosPolicyName managed object property"
    ::= { cucsVnicIpcEntry 28 }

cucsVnicIpcStatsPolicyName OBJECT-TYPE
    SYNTAX       SnmpAdminString
    MAX-ACCESS   read-only
    STATUS       current
    DESCRIPTION
        "Cisco UCS vnic:Ipc:statsPolicyName managed object property"
    ::= { cucsVnicIpcEntry 29 }

cucsVnicIpcSwitchId OBJECT-TYPE
    SYNTAX       CucsVnicEtherBaseSwitchId
    MAX-ACCESS   read-only
    STATUS       current
    DESCRIPTION
        "Cisco UCS vnic:Ipc:switchId managed object property"
    ::= { cucsVnicIpcEntry 30 }

cucsVnicIpcType OBJECT-TYPE
    SYNTAX       CucsVnicIpcType
    MAX-ACCESS   read-only
    STATUS       current
    DESCRIPTION
        "Cisco UCS vnic:Ipc:type managed object property"
    ::= { cucsVnicIpcEntry 31 }

cucsVnicIpcOperPinToGroupName OBJECT-TYPE
    SYNTAX       SnmpAdminString
    MAX-ACCESS   read-only
    STATUS       current
    DESCRIPTION
        "Cisco UCS vnic:Ipc:operPinToGroupName managed object property"
    ::= { cucsVnicIpcEntry 32 }

cucsVnicIpcConfigQualifier OBJECT-TYPE
    SYNTAX       CucsVnicConfigIssues
    MAX-ACCESS   read-only
    STATUS       current
    DESCRIPTION
        "Cisco UCS vnic:Ipc:configQualifier managed object property"
    ::= { cucsVnicIpcEntry 33 }

cucsVnicIpcAdminHostPort OBJECT-TYPE
    SYNTAX       CucsFabricHostPortId
    MAX-ACCESS   read-only
    STATUS       current
    DESCRIPTION
        "Cisco UCS vnic:Ipc:adminHostPort managed object property"
    ::= { cucsVnicIpcEntry 35 }

cucsVnicIpcOperHostPort OBJECT-TYPE
    SYNTAX       CucsVnicVnicOperHostPort
    MAX-ACCESS   read-only
    STATUS       current
    DESCRIPTION
        "Cisco UCS vnic:Ipc:operHostPort managed object property"
    ::= { cucsVnicIpcEntry 36 }

cucsVnicIpcPurpose OBJECT-TYPE
    SYNTAX       CucsAdaptorPurpose
    MAX-ACCESS   read-only
    STATUS       current
    DESCRIPTION
        "Cisco UCS vnic:Ipc:purpose managed object property"
    ::= { cucsVnicIpcEntry 37 }

cucsVnicIpcAdminCdnName OBJECT-TYPE
    SYNTAX       SnmpAdminString
    MAX-ACCESS   read-only
    STATUS       current
    DESCRIPTION
        "Cisco UCS vnic:Ipc:adminCdnName managed object property"
    ::= { cucsVnicIpcEntry 38 }

cucsVnicIpcOperCdnName OBJECT-TYPE
    SYNTAX       SnmpAdminString
    MAX-ACCESS   read-only
    STATUS       current
    DESCRIPTION
        "Cisco UCS vnic:Ipc:operCdnName managed object property"
    ::= { cucsVnicIpcEntry 39 }

cucsVnicIpcCdnPropInSync OBJECT-TYPE
    SYNTAX       TruthValue
    MAX-ACCESS   read-only
    STATUS       current
    DESCRIPTION
        "Cisco UCS vnic:Ipc:cdnPropInSync managed object property"
    ::= { cucsVnicIpcEntry 40 }

cucsVnicIpcCdnSource OBJECT-TYPE
    SYNTAX       CucsVnicCdnSource
    MAX-ACCESS   read-only
    STATUS       current
    DESCRIPTION
        "Cisco UCS vnic:Ipc:cdnSource managed object property"
    ::= { cucsVnicIpcEntry 41 }

cucsVnicIpcIfTable OBJECT-TYPE
    SYNTAX           SEQUENCE OF CucsVnicIpcIfEntry
    MAX-ACCESS       not-accessible
    STATUS           current
    DESCRIPTION
        "Cisco UCS vnic:IpcIf managed object table"
    ::= { cucsVnicObjects 24 }

cucsVnicIpcIfEntry OBJECT-TYPE
    SYNTAX           CucsVnicIpcIfEntry
    MAX-ACCESS       not-accessible
    STATUS           current
    DESCRIPTION
        "Entry for the cucsVnicIpcIfTable table."
    INDEX { cucsVnicIpcIfInstanceId }
    ::= { cucsVnicIpcIfTable 1 }

CucsVnicIpcIfEntry ::= SEQUENCE {
    cucsVnicIpcIfInstanceId                                          CucsManagedObjectId,
    cucsVnicIpcIfDn                                                  CucsManagedObjectDn,
    cucsVnicIpcIfRn                                                  SnmpAdminString,
    cucsVnicIpcIfAddr                                                MacAddress,
    cucsVnicIpcIfDefaultNet                                          TruthValue,
    cucsVnicIpcIfName                                                SnmpAdminString,
    cucsVnicIpcIfOperState                                           CucsVnicIfOperState,
    cucsVnicIpcIfOwner                                               CucsVnicConnectionOwner,
    cucsVnicIpcIfSwitchId                                            CucsVnicEtherBaseIfSwitchId,
    cucsVnicIpcIfType                                                CucsVnicAIpcIfType,
    cucsVnicIpcIfVnet                                                Gauge32,
    cucsVnicIpcIfConfigQualifier                                     CucsVnicConfigIssues,
    cucsVnicIpcIfOperVnetDn                                          SnmpAdminString,
    cucsVnicIpcIfOperVnetName                                        SnmpAdminString,
    cucsVnicIpcIfPubNwId                                             Gauge32,
    cucsVnicIpcIfSharing                                             CucsFabricVlanSharingType,
    cucsVnicIpcIfOperPrimaryVnetDn                                   SnmpAdminString,
    cucsVnicIpcIfOperPrimaryVnetName                                 SnmpAdminString
}

cucsVnicIpcIfInstanceId OBJECT-TYPE
    SYNTAX       CucsManagedObjectId
    MAX-ACCESS   not-accessible
    STATUS       current
    DESCRIPTION
        "Instance identifier of the managed object."
    ::= { cucsVnicIpcIfEntry 1 }

cucsVnicIpcIfDn OBJECT-TYPE
    SYNTAX       CucsManagedObjectDn
    MAX-ACCESS   read-only
    STATUS       current
    DESCRIPTION
        "Cisco UCS vnic:IpcIf:dn managed object property"
    ::= { cucsVnicIpcIfEntry 2 }

cucsVnicIpcIfRn OBJECT-TYPE
    SYNTAX       SnmpAdminString
    MAX-ACCESS   read-only
    STATUS       current
    DESCRIPTION
        "Cisco UCS vnic:IpcIf:rn managed object property"
    ::= { cucsVnicIpcIfEntry 3 }

cucsVnicIpcIfAddr OBJECT-TYPE
    SYNTAX       MacAddress
    MAX-ACCESS   read-only
    STATUS       current
    DESCRIPTION
        "Cisco UCS vnic:IpcIf:addr managed object property"
    ::= { cucsVnicIpcIfEntry 4 }

cucsVnicIpcIfDefaultNet OBJECT-TYPE
    SYNTAX       TruthValue
    MAX-ACCESS   read-only
    STATUS       current
    DESCRIPTION
        "Cisco UCS vnic:IpcIf:defaultNet managed object property"
    ::= { cucsVnicIpcIfEntry 5 }

cucsVnicIpcIfName OBJECT-TYPE
    SYNTAX       SnmpAdminString
    MAX-ACCESS   read-only
    STATUS       current
    DESCRIPTION
        "Cisco UCS vnic:IpcIf:name managed object property"
    ::= { cucsVnicIpcIfEntry 6 }

cucsVnicIpcIfOperState OBJECT-TYPE
    SYNTAX       CucsVnicIfOperState
    MAX-ACCESS   read-only
    STATUS       current
    DESCRIPTION
        "Cisco UCS vnic:IpcIf:operState managed object property"
    ::= { cucsVnicIpcIfEntry 7 }

cucsVnicIpcIfOwner OBJECT-TYPE
    SYNTAX       CucsVnicConnectionOwner
    MAX-ACCESS   read-only
    STATUS       current
    DESCRIPTION
        "Cisco UCS vnic:IpcIf:owner managed object property"
    ::= { cucsVnicIpcIfEntry 8 }

cucsVnicIpcIfSwitchId OBJECT-TYPE
    SYNTAX       CucsVnicEtherBaseIfSwitchId
    MAX-ACCESS   read-only
    STATUS       current
    DESCRIPTION
        "Cisco UCS vnic:IpcIf:switchId managed object property"
    ::= { cucsVnicIpcIfEntry 9 }

cucsVnicIpcIfType OBJECT-TYPE
    SYNTAX       CucsVnicAIpcIfType
    MAX-ACCESS   read-only
    STATUS       current
    DESCRIPTION
        "Cisco UCS vnic:IpcIf:type managed object property"
    ::= { cucsVnicIpcIfEntry 10 }

cucsVnicIpcIfVnet OBJECT-TYPE
    SYNTAX       Gauge32
    MAX-ACCESS   read-only
    STATUS       current
    DESCRIPTION
        "Cisco UCS vnic:IpcIf:vnet managed object property"
    ::= { cucsVnicIpcIfEntry 11 }

cucsVnicIpcIfConfigQualifier OBJECT-TYPE
    SYNTAX       CucsVnicConfigIssues
    MAX-ACCESS   read-only
    STATUS       current
    DESCRIPTION
        "Cisco UCS vnic:IpcIf:configQualifier managed object property"
    ::= { cucsVnicIpcIfEntry 12 }

cucsVnicIpcIfOperVnetDn OBJECT-TYPE
    SYNTAX       SnmpAdminString
    MAX-ACCESS   read-only
    STATUS       current
    DESCRIPTION
        "Cisco UCS vnic:IpcIf:operVnetDn managed object property"
    ::= { cucsVnicIpcIfEntry 14 }

cucsVnicIpcIfOperVnetName OBJECT-TYPE
    SYNTAX       SnmpAdminString
    MAX-ACCESS   read-only
    STATUS       current
    DESCRIPTION
        "Cisco UCS vnic:IpcIf:operVnetName managed object property"
    ::= { cucsVnicIpcIfEntry 15 }

cucsVnicIpcIfPubNwId OBJECT-TYPE
    SYNTAX       Gauge32
    MAX-ACCESS   read-only
    STATUS       current
    DESCRIPTION
        "Cisco UCS vnic:IpcIf:pubNwId managed object property"
    ::= { cucsVnicIpcIfEntry 16 }

cucsVnicIpcIfSharing OBJECT-TYPE
    SYNTAX       CucsFabricVlanSharingType
    MAX-ACCESS   read-only
    STATUS       current
    DESCRIPTION
        "Cisco UCS vnic:IpcIf:sharing managed object property"
    ::= { cucsVnicIpcIfEntry 17 }

cucsVnicIpcIfOperPrimaryVnetDn OBJECT-TYPE
    SYNTAX       SnmpAdminString
    MAX-ACCESS   read-only
    STATUS       current
    DESCRIPTION
        "Cisco UCS vnic:IpcIf:operPrimaryVnetDn managed object property"
    ::= { cucsVnicIpcIfEntry 18 }

cucsVnicIpcIfOperPrimaryVnetName OBJECT-TYPE
    SYNTAX       SnmpAdminString
    MAX-ACCESS   read-only
    STATUS       current
    DESCRIPTION
        "Cisco UCS vnic:IpcIf:operPrimaryVnetName managed object property"
    ::= { cucsVnicIpcIfEntry 19 }

cucsVnicIqnHistoryTable OBJECT-TYPE
    SYNTAX           SEQUENCE OF CucsVnicIqnHistoryEntry
    MAX-ACCESS       not-accessible
    STATUS           current
    DESCRIPTION
        "Cisco UCS vnic:IqnHistory managed object table"
    ::= { cucsVnicObjects 61 }

cucsVnicIqnHistoryEntry OBJECT-TYPE
    SYNTAX           CucsVnicIqnHistoryEntry
    MAX-ACCESS       not-accessible
    STATUS           current
    DESCRIPTION
        "Entry for the cucsVnicIqnHistoryTable table."
    INDEX { cucsVnicIqnHistoryInstanceId }
    ::= { cucsVnicIqnHistoryTable 1 }

CucsVnicIqnHistoryEntry ::= SEQUENCE {
    cucsVnicIqnHistoryInstanceId                                     CucsManagedObjectId,
    cucsVnicIqnHistoryDn                                             CucsManagedObjectDn,
    cucsVnicIqnHistoryRn                                             SnmpAdminString,
    cucsVnicIqnHistoryOldInitiatorName                               SnmpAdminString
}

cucsVnicIqnHistoryInstanceId OBJECT-TYPE
    SYNTAX       CucsManagedObjectId
    MAX-ACCESS   not-accessible
    STATUS       current
    DESCRIPTION
        "Instance identifier of the managed object."
    ::= { cucsVnicIqnHistoryEntry 1 }

cucsVnicIqnHistoryDn OBJECT-TYPE
    SYNTAX       CucsManagedObjectDn
    MAX-ACCESS   read-only
    STATUS       current
    DESCRIPTION
        "Cisco UCS vnic:IqnHistory:dn managed object property"
    ::= { cucsVnicIqnHistoryEntry 2 }

cucsVnicIqnHistoryRn OBJECT-TYPE
    SYNTAX       SnmpAdminString
    MAX-ACCESS   read-only
    STATUS       current
    DESCRIPTION
        "Cisco UCS vnic:IqnHistory:rn managed object property"
    ::= { cucsVnicIqnHistoryEntry 3 }

cucsVnicIqnHistoryOldInitiatorName OBJECT-TYPE
    SYNTAX       SnmpAdminString
    MAX-ACCESS   read-only
    STATUS       current
    DESCRIPTION
        "Cisco UCS vnic:IqnHistory:oldInitiatorName managed
        object property"
    ::= { cucsVnicIqnHistoryEntry 4 }

cucsVnicLanConnPolicyTable OBJECT-TYPE
    SYNTAX           SEQUENCE OF CucsVnicLanConnPolicyEntry
    MAX-ACCESS       not-accessible
    STATUS           current
    DESCRIPTION
        "Cisco UCS vnic:LanConnPolicy managed object table"
    ::= { cucsVnicObjects 53 }

cucsVnicLanConnPolicyEntry OBJECT-TYPE
    SYNTAX           CucsVnicLanConnPolicyEntry
    MAX-ACCESS       not-accessible
    STATUS           current
    DESCRIPTION
        "Entry for the cucsVnicLanConnPolicyTable table."
    INDEX { cucsVnicLanConnPolicyInstanceId }
    ::= { cucsVnicLanConnPolicyTable 1 }

CucsVnicLanConnPolicyEntry ::= SEQUENCE {
    cucsVnicLanConnPolicyInstanceId                                  CucsManagedObjectId,
    cucsVnicLanConnPolicyDn                                          CucsManagedObjectDn,
    cucsVnicLanConnPolicyRn                                          SnmpAdminString,
    cucsVnicLanConnPolicyDescr                                       SnmpAdminString,
    cucsVnicLanConnPolicyFltAggr                                     Unsigned64,
    cucsVnicLanConnPolicyIntId                                       SnmpAdminString,
    cucsVnicLanConnPolicyName                                        SnmpAdminString,
    cucsVnicLanConnPolicyPolicyLevel                                 Gauge32,
    cucsVnicLanConnPolicyPolicyOwner                                 CucsPolicyPolicyOwner
}

cucsVnicLanConnPolicyInstanceId OBJECT-TYPE
    SYNTAX       CucsManagedObjectId
    MAX-ACCESS   not-accessible
    STATUS       current
    DESCRIPTION
        "Instance identifier of the managed object."
    ::= { cucsVnicLanConnPolicyEntry 1 }

cucsVnicLanConnPolicyDn OBJECT-TYPE
    SYNTAX       CucsManagedObjectDn
    MAX-ACCESS   read-only
    STATUS       current
    DESCRIPTION
        "Cisco UCS vnic:LanConnPolicy:dn managed object property"
    ::= { cucsVnicLanConnPolicyEntry 2 }

cucsVnicLanConnPolicyRn OBJECT-TYPE
    SYNTAX       SnmpAdminString
    MAX-ACCESS   read-only
    STATUS       current
    DESCRIPTION
        "Cisco UCS vnic:LanConnPolicy:rn managed object property"
    ::= { cucsVnicLanConnPolicyEntry 3 }

cucsVnicLanConnPolicyDescr OBJECT-TYPE
    SYNTAX       SnmpAdminString
    MAX-ACCESS   read-only
    STATUS       current
    DESCRIPTION
        "Cisco UCS vnic:LanConnPolicy:descr managed object property"
    ::= { cucsVnicLanConnPolicyEntry 4 }

cucsVnicLanConnPolicyFltAggr OBJECT-TYPE
    SYNTAX       Unsigned64
    MAX-ACCESS   read-only
    STATUS       current
    DESCRIPTION
        "Cisco UCS vnic:LanConnPolicy:fltAggr managed object property"
    ::= { cucsVnicLanConnPolicyEntry 5 }

cucsVnicLanConnPolicyIntId OBJECT-TYPE
    SYNTAX       SnmpAdminString
    MAX-ACCESS   read-only
    STATUS       current
    DESCRIPTION
        "Cisco UCS vnic:LanConnPolicy:intId managed object property"
    ::= { cucsVnicLanConnPolicyEntry 6 }

cucsVnicLanConnPolicyName OBJECT-TYPE
    SYNTAX       SnmpAdminString
    MAX-ACCESS   read-only
    STATUS       current
    DESCRIPTION
        "Cisco UCS vnic:LanConnPolicy:name managed object property"
    ::= { cucsVnicLanConnPolicyEntry 7 }

cucsVnicLanConnPolicyPolicyLevel OBJECT-TYPE
    SYNTAX       Gauge32
    MAX-ACCESS   read-only
    STATUS       current
    DESCRIPTION
        "Cisco UCS vnic:LanConnPolicy:policyLevel managed object property"
    ::= { cucsVnicLanConnPolicyEntry 8 }

cucsVnicLanConnPolicyPolicyOwner OBJECT-TYPE
    SYNTAX       CucsPolicyPolicyOwner
    MAX-ACCESS   read-only
    STATUS       current
    DESCRIPTION
        "Cisco UCS vnic:LanConnPolicy:policyOwner managed object property"
    ::= { cucsVnicLanConnPolicyEntry 9 }

cucsVnicLanConnTemplTable OBJECT-TYPE
    SYNTAX           SEQUENCE OF CucsVnicLanConnTemplEntry
    MAX-ACCESS       not-accessible
    STATUS           current
    DESCRIPTION
        "Cisco UCS vnic:LanConnTempl managed object table"
    ::= { cucsVnicObjects 25 }

cucsVnicLanConnTemplEntry OBJECT-TYPE
    SYNTAX           CucsVnicLanConnTemplEntry
    MAX-ACCESS       not-accessible
    STATUS           current
    DESCRIPTION
        "Entry for the cucsVnicLanConnTemplTable table."
    INDEX { cucsVnicLanConnTemplInstanceId }
    ::= { cucsVnicLanConnTemplTable 1 }

CucsVnicLanConnTemplEntry ::= SEQUENCE {
    cucsVnicLanConnTemplInstanceId                                   CucsManagedObjectId,
    cucsVnicLanConnTemplDn                                           CucsManagedObjectDn,
    cucsVnicLanConnTemplRn                                           SnmpAdminString,
    cucsVnicLanConnTemplDescr                                        SnmpAdminString,
    cucsVnicLanConnTemplIdentPoolName                                SnmpAdminString,
    cucsVnicLanConnTemplIntId                                        SnmpAdminString,
    cucsVnicLanConnTemplMtu                                          Gauge32,
    cucsVnicLanConnTemplName                                         SnmpAdminString,
    cucsVnicLanConnTemplNwCtrlPolicyName                             SnmpAdminString,
    cucsVnicLanConnTemplOperIdentPoolName                            SnmpAdminString,
    cucsVnicLanConnTemplOperNwCtrlPolicyName                         SnmpAdminString,
    cucsVnicLanConnTemplOperQosPolicyName                            SnmpAdminString,
    cucsVnicLanConnTemplOperStatsPolicyName                          SnmpAdminString,
    cucsVnicLanConnTemplPinToGroupName                               SnmpAdminString,
    cucsVnicLanConnTemplQosPolicyName                                SnmpAdminString,
    cucsVnicLanConnTemplStatsPolicyName                              SnmpAdminString,
    cucsVnicLanConnTemplSwitchId                                     CucsVnicLanConnTemplSwitchId,
    cucsVnicLanConnTemplTarget                                       CucsVnicTemplateTarget,
    cucsVnicLanConnTemplTemplType                                    CucsVnicTemplateType,
    cucsVnicLanConnTemplPolicyLevel                                  Gauge32,
    cucsVnicLanConnTemplPolicyOwner                                  CucsPolicyPolicyOwner,
    cucsVnicLanConnTemplAdminCdnName                                 SnmpAdminString,
    cucsVnicLanConnTemplCdnSource                                    CucsVnicCdnSource
}

cucsVnicLanConnTemplInstanceId OBJECT-TYPE
    SYNTAX       CucsManagedObjectId
    MAX-ACCESS   not-accessible
    STATUS       current
    DESCRIPTION
        "Instance identifier of the managed object."
    ::= { cucsVnicLanConnTemplEntry 1 }

cucsVnicLanConnTemplDn OBJECT-TYPE
    SYNTAX       CucsManagedObjectDn
    MAX-ACCESS   read-only
    STATUS       current
    DESCRIPTION
        "Cisco UCS vnic:LanConnTempl:dn managed object property"
    ::= { cucsVnicLanConnTemplEntry 2 }

cucsVnicLanConnTemplRn OBJECT-TYPE
    SYNTAX       SnmpAdminString
    MAX-ACCESS   read-only
    STATUS       current
    DESCRIPTION
        "Cisco UCS vnic:LanConnTempl:rn managed object property"
    ::= { cucsVnicLanConnTemplEntry 3 }

cucsVnicLanConnTemplDescr OBJECT-TYPE
    SYNTAX       SnmpAdminString
    MAX-ACCESS   read-only
    STATUS       current
    DESCRIPTION
        "Cisco UCS vnic:LanConnTempl:descr managed object property"
    ::= { cucsVnicLanConnTemplEntry 4 }

cucsVnicLanConnTemplIdentPoolName OBJECT-TYPE
    SYNTAX       SnmpAdminString
    MAX-ACCESS   read-only
    STATUS       current
    DESCRIPTION
        "Cisco UCS vnic:LanConnTempl:identPoolName managed
        object property"
    ::= { cucsVnicLanConnTemplEntry 5 }

cucsVnicLanConnTemplIntId OBJECT-TYPE
    SYNTAX       SnmpAdminString
    MAX-ACCESS   read-only
    STATUS       current
    DESCRIPTION
        "Cisco UCS vnic:LanConnTempl:intId managed object property"
    ::= { cucsVnicLanConnTemplEntry 6 }

cucsVnicLanConnTemplMtu OBJECT-TYPE
    SYNTAX       Gauge32
    MAX-ACCESS   read-only
    STATUS       current
    DESCRIPTION
        "Cisco UCS vnic:LanConnTempl:mtu managed object property"
    ::= { cucsVnicLanConnTemplEntry 7 }

cucsVnicLanConnTemplName OBJECT-TYPE
    SYNTAX       SnmpAdminString
    MAX-ACCESS   read-only
    STATUS       current
    DESCRIPTION
        "Cisco UCS vnic:LanConnTempl:name managed object property"
    ::= { cucsVnicLanConnTemplEntry 8 }

cucsVnicLanConnTemplNwCtrlPolicyName OBJECT-TYPE
    SYNTAX       SnmpAdminString
    MAX-ACCESS   read-only
    STATUS       current
    DESCRIPTION
        "Cisco UCS vnic:LanConnTempl:nwCtrlPolicyName managed
        object property"
    ::= { cucsVnicLanConnTemplEntry 9 }

cucsVnicLanConnTemplOperIdentPoolName OBJECT-TYPE
    SYNTAX       SnmpAdminString
    MAX-ACCESS   read-only
    STATUS       current
    DESCRIPTION
        "Cisco UCS vnic:LanConnTempl:operIdentPoolName
        managed object property"
    ::= { cucsVnicLanConnTemplEntry 10 }

cucsVnicLanConnTemplOperNwCtrlPolicyName OBJECT-TYPE
    SYNTAX       SnmpAdminString
    MAX-ACCESS   read-only
    STATUS       current
    DESCRIPTION
        "Cisco UCS vnic:LanConnTempl:operNwCtrlPolicyName
        managed object property"
    ::= { cucsVnicLanConnTemplEntry 11 }

cucsVnicLanConnTemplOperQosPolicyName OBJECT-TYPE
    SYNTAX       SnmpAdminString
    MAX-ACCESS   read-only
    STATUS       current
    DESCRIPTION
        "Cisco UCS vnic:LanConnTempl:operQosPolicyName
        managed object property"
    ::= { cucsVnicLanConnTemplEntry 12 }

cucsVnicLanConnTemplOperStatsPolicyName OBJECT-TYPE
    SYNTAX       SnmpAdminString
    MAX-ACCESS   read-only
    STATUS       current
    DESCRIPTION
        "Cisco UCS vnic:LanConnTempl:operStatsPolicyName
        managed object property"
    ::= { cucsVnicLanConnTemplEntry 13 }

cucsVnicLanConnTemplPinToGroupName OBJECT-TYPE
    SYNTAX       SnmpAdminString
    MAX-ACCESS   read-only
    STATUS       current
    DESCRIPTION
        "Cisco UCS vnic:LanConnTempl:pinToGroupName managed
        object property"
    ::= { cucsVnicLanConnTemplEntry 14 }

cucsVnicLanConnTemplQosPolicyName OBJECT-TYPE
    SYNTAX       SnmpAdminString
    MAX-ACCESS   read-only
    STATUS       current
    DESCRIPTION
        "Cisco UCS vnic:LanConnTempl:qosPolicyName managed
        object property"
    ::= { cucsVnicLanConnTemplEntry 15 }

cucsVnicLanConnTemplStatsPolicyName OBJECT-TYPE
    SYNTAX       SnmpAdminString
    MAX-ACCESS   read-only
    STATUS       current
    DESCRIPTION
        "Cisco UCS vnic:LanConnTempl:statsPolicyName managed
        object property"
    ::= { cucsVnicLanConnTemplEntry 16 }

cucsVnicLanConnTemplSwitchId OBJECT-TYPE
    SYNTAX       CucsVnicLanConnTemplSwitchId
    MAX-ACCESS   read-only
    STATUS       current
    DESCRIPTION
        "Cisco UCS vnic:LanConnTempl:switchId managed object property"
    ::= { cucsVnicLanConnTemplEntry 17 }

cucsVnicLanConnTemplTarget OBJECT-TYPE
    SYNTAX       CucsVnicTemplateTarget
    MAX-ACCESS   read-only
    STATUS       current
    DESCRIPTION
        "Cisco UCS vnic:LanConnTempl:target managed object property"
    ::= { cucsVnicLanConnTemplEntry 18 }

cucsVnicLanConnTemplTemplType OBJECT-TYPE
    SYNTAX       CucsVnicTemplateType
    MAX-ACCESS   read-only
    STATUS       current
    DESCRIPTION
        "Cisco UCS vnic:LanConnTempl:templType managed object property"
    ::= { cucsVnicLanConnTemplEntry 19 }

cucsVnicLanConnTemplPolicyLevel OBJECT-TYPE
    SYNTAX       Gauge32
    MAX-ACCESS   read-only
    STATUS       current
    DESCRIPTION
        "Cisco UCS vnic:LanConnTempl:policyLevel managed object property"
    ::= { cucsVnicLanConnTemplEntry 20 }

cucsVnicLanConnTemplPolicyOwner OBJECT-TYPE
    SYNTAX       CucsPolicyPolicyOwner
    MAX-ACCESS   read-only
    STATUS       current
    DESCRIPTION
        "Cisco UCS vnic:LanConnTempl:policyOwner managed object property"
    ::= { cucsVnicLanConnTemplEntry 21 }

cucsVnicLanConnTemplAdminCdnName OBJECT-TYPE
    SYNTAX       SnmpAdminString
    MAX-ACCESS   read-only
    STATUS       current
    DESCRIPTION
        "Cisco UCS vnic:LanConnTempl:adminCdnName managed object property"
    ::= { cucsVnicLanConnTemplEntry 22 }

cucsVnicLanConnTemplCdnSource OBJECT-TYPE
    SYNTAX       CucsVnicCdnSource
    MAX-ACCESS   read-only
    STATUS       current
    DESCRIPTION
        "Cisco UCS vnic:LanConnTempl:cdnSource managed object property"
    ::= { cucsVnicLanConnTemplEntry 23 }

cucsVnicLifVlanTable OBJECT-TYPE
    SYNTAX           SEQUENCE OF CucsVnicLifVlanEntry
    MAX-ACCESS       not-accessible
    STATUS           current
    DESCRIPTION
        "Cisco UCS vnic:LifVlan managed object table"
    ::= { cucsVnicObjects 26 }

cucsVnicLifVlanEntry OBJECT-TYPE
    SYNTAX           CucsVnicLifVlanEntry
    MAX-ACCESS       not-accessible
    STATUS           current
    DESCRIPTION
        "Entry for the cucsVnicLifVlanTable table."
    INDEX { cucsVnicLifVlanInstanceId }
    ::= { cucsVnicLifVlanTable 1 }

CucsVnicLifVlanEntry ::= SEQUENCE {
    cucsVnicLifVlanInstanceId                                        CucsManagedObjectId,
    cucsVnicLifVlanDn                                                CucsManagedObjectDn,
    cucsVnicLifVlanRn                                                SnmpAdminString,
    cucsVnicLifVlanAddr                                              MacAddress,
    cucsVnicLifVlanDefaultNet                                        TruthValue,
    cucsVnicLifVlanName                                              SnmpAdminString,
    cucsVnicLifVlanOperState                                         CucsVnicIfOperState,
    cucsVnicLifVlanOwner                                             CucsVnicConnectionOwner,
    cucsVnicLifVlanSwitchId                                          CucsVnicEtherBaseIfSwitchId,
    cucsVnicLifVlanType                                              CucsVnicAEtherIfType,
    cucsVnicLifVlanVnet                                              Gauge32,
    cucsVnicLifVlanConfigQualifier                                   CucsVnicConfigIssues,
    cucsVnicLifVlanOperVnetDn                                        SnmpAdminString,
    cucsVnicLifVlanOperVnetName                                      SnmpAdminString,
    cucsVnicLifVlanPubNwId                                           Gauge32,
    cucsVnicLifVlanSharing                                           CucsFabricVlanSharingType,
    cucsVnicLifVlanPropAcl                                           Unsigned64,
    cucsVnicLifVlanOperPrimaryVnetDn                                 SnmpAdminString,
    cucsVnicLifVlanOperPrimaryVnetName                               SnmpAdminString
}

cucsVnicLifVlanInstanceId OBJECT-TYPE
    SYNTAX       CucsManagedObjectId
    MAX-ACCESS   not-accessible
    STATUS       current
    DESCRIPTION
        "Instance identifier of the managed object."
    ::= { cucsVnicLifVlanEntry 1 }

cucsVnicLifVlanDn OBJECT-TYPE
    SYNTAX       CucsManagedObjectDn
    MAX-ACCESS   read-only
    STATUS       current
    DESCRIPTION
        "Cisco UCS vnic:LifVlan:dn managed object property"
    ::= { cucsVnicLifVlanEntry 2 }

cucsVnicLifVlanRn OBJECT-TYPE
    SYNTAX       SnmpAdminString
    MAX-ACCESS   read-only
    STATUS       current
    DESCRIPTION
        "Cisco UCS vnic:LifVlan:rn managed object property"
    ::= { cucsVnicLifVlanEntry 3 }

cucsVnicLifVlanAddr OBJECT-TYPE
    SYNTAX       MacAddress
    MAX-ACCESS   read-only
    STATUS       current
    DESCRIPTION
        "Cisco UCS vnic:LifVlan:addr managed object property"
    ::= { cucsVnicLifVlanEntry 4 }

cucsVnicLifVlanDefaultNet OBJECT-TYPE
    SYNTAX       TruthValue
    MAX-ACCESS   read-only
    STATUS       current
    DESCRIPTION
        "Cisco UCS vnic:LifVlan:defaultNet managed object property"
    ::= { cucsVnicLifVlanEntry 5 }

cucsVnicLifVlanName OBJECT-TYPE
    SYNTAX       SnmpAdminString
    MAX-ACCESS   read-only
    STATUS       current
    DESCRIPTION
        "Cisco UCS vnic:LifVlan:name managed object property"
    ::= { cucsVnicLifVlanEntry 6 }

cucsVnicLifVlanOperState OBJECT-TYPE
    SYNTAX       CucsVnicIfOperState
    MAX-ACCESS   read-only
    STATUS       current
    DESCRIPTION
        "Cisco UCS vnic:LifVlan:operState managed object property"
    ::= { cucsVnicLifVlanEntry 7 }

cucsVnicLifVlanOwner OBJECT-TYPE
    SYNTAX       CucsVnicConnectionOwner
    MAX-ACCESS   read-only
    STATUS       current
    DESCRIPTION
        "Cisco UCS vnic:LifVlan:owner managed object property"
    ::= { cucsVnicLifVlanEntry 8 }

cucsVnicLifVlanSwitchId OBJECT-TYPE
    SYNTAX       CucsVnicEtherBaseIfSwitchId
    MAX-ACCESS   read-only
    STATUS       current
    DESCRIPTION
        "Cisco UCS vnic:LifVlan:switchId managed object property"
    ::= { cucsVnicLifVlanEntry 9 }

cucsVnicLifVlanType OBJECT-TYPE
    SYNTAX       CucsVnicAEtherIfType
    MAX-ACCESS   read-only
    STATUS       current
    DESCRIPTION
        "Cisco UCS vnic:LifVlan:type managed object property"
    ::= { cucsVnicLifVlanEntry 10 }

cucsVnicLifVlanVnet OBJECT-TYPE
    SYNTAX       Gauge32
    MAX-ACCESS   read-only
    STATUS       current
    DESCRIPTION
        "Cisco UCS vnic:LifVlan:vnet managed object property"
    ::= { cucsVnicLifVlanEntry 11 }

cucsVnicLifVlanConfigQualifier OBJECT-TYPE
    SYNTAX       CucsVnicConfigIssues
    MAX-ACCESS   read-only
    STATUS       current
    DESCRIPTION
        "Cisco UCS vnic:LifVlan:configQualifier managed object property"
    ::= { cucsVnicLifVlanEntry 12 }

cucsVnicLifVlanOperVnetDn OBJECT-TYPE
    SYNTAX       SnmpAdminString
    MAX-ACCESS   read-only
    STATUS       current
    DESCRIPTION
        "Cisco UCS vnic:LifVlan:operVnetDn managed object property"
    ::= { cucsVnicLifVlanEntry 14 }

cucsVnicLifVlanOperVnetName OBJECT-TYPE
    SYNTAX       SnmpAdminString
    MAX-ACCESS   read-only
    STATUS       current
    DESCRIPTION
        "Cisco UCS vnic:LifVlan:operVnetName managed object property"
    ::= { cucsVnicLifVlanEntry 15 }

cucsVnicLifVlanPubNwId OBJECT-TYPE
    SYNTAX       Gauge32
    MAX-ACCESS   read-only
    STATUS       current
    DESCRIPTION
        "Cisco UCS vnic:LifVlan:pubNwId managed object property"
    ::= { cucsVnicLifVlanEntry 16 }

cucsVnicLifVlanSharing OBJECT-TYPE
    SYNTAX       CucsFabricVlanSharingType
    MAX-ACCESS   read-only
    STATUS       current
    DESCRIPTION
        "Cisco UCS vnic:LifVlan:sharing managed object property"
    ::= { cucsVnicLifVlanEntry 17 }

cucsVnicLifVlanPropAcl OBJECT-TYPE
    SYNTAX       Unsigned64
    MAX-ACCESS   read-only
    STATUS       current
    DESCRIPTION
        "Cisco UCS vnic:LifVlan:propAcl managed object property"
    ::= { cucsVnicLifVlanEntry 18 }

cucsVnicLifVlanOperPrimaryVnetDn OBJECT-TYPE
    SYNTAX       SnmpAdminString
    MAX-ACCESS   read-only
    STATUS       current
    DESCRIPTION
        "Cisco UCS vnic:LifVlan:operPrimaryVnetDn managed object property"
    ::= { cucsVnicLifVlanEntry 19 }

cucsVnicLifVlanOperPrimaryVnetName OBJECT-TYPE
    SYNTAX       SnmpAdminString
    MAX-ACCESS   read-only
    STATUS       current
    DESCRIPTION
        "Cisco UCS vnic:LifVlan:operPrimaryVnetName managed
        object property"
    ::= { cucsVnicLifVlanEntry 20 }

cucsVnicLifVsanTable OBJECT-TYPE
    SYNTAX           SEQUENCE OF CucsVnicLifVsanEntry
    MAX-ACCESS       not-accessible
    STATUS           current
    DESCRIPTION
        "Cisco UCS vnic:LifVsan managed object table"
    ::= { cucsVnicObjects 27 }

cucsVnicLifVsanEntry OBJECT-TYPE
    SYNTAX           CucsVnicLifVsanEntry
    MAX-ACCESS       not-accessible
    STATUS           current
    DESCRIPTION
        "Entry for the cucsVnicLifVsanTable table."
    INDEX { cucsVnicLifVsanInstanceId }
    ::= { cucsVnicLifVsanTable 1 }

CucsVnicLifVsanEntry ::= SEQUENCE {
    cucsVnicLifVsanInstanceId                                        CucsManagedObjectId,
    cucsVnicLifVsanDn                                                CucsManagedObjectDn,
    cucsVnicLifVsanRn                                                SnmpAdminString,
    cucsVnicLifVsanInitiator                                         Unsigned64,
    cucsVnicLifVsanName                                              SnmpAdminString,
    cucsVnicLifVsanOperState                                         CucsVnicIfOperState,
    cucsVnicLifVsanOwner                                             CucsVnicConnectionOwner,
    cucsVnicLifVsanSwitchId                                          CucsVnicAFcIfSwitchId,
    cucsVnicLifVsanType                                              CucsVnicAFcIfType,
    cucsVnicLifVsanVnet                                              Gauge32,
    cucsVnicLifVsanConfigQualifier                                   CucsVnicConfigIssues,
    cucsVnicLifVsanOperVnetDn                                        SnmpAdminString,
    cucsVnicLifVsanOperVnetName                                      SnmpAdminString,
    cucsVnicLifVsanPubNwId                                           Gauge32,
    cucsVnicLifVsanSharing                                           CucsFabricVlanSharingType,
    cucsVnicLifVsanOperPrimaryVnetDn                                 SnmpAdminString,
    cucsVnicLifVsanOperPrimaryVnetName                               SnmpAdminString
}

cucsVnicLifVsanInstanceId OBJECT-TYPE
    SYNTAX       CucsManagedObjectId
    MAX-ACCESS   not-accessible
    STATUS       current
    DESCRIPTION
        "Instance identifier of the managed object."
    ::= { cucsVnicLifVsanEntry 1 }

cucsVnicLifVsanDn OBJECT-TYPE
    SYNTAX       CucsManagedObjectDn
    MAX-ACCESS   read-only
    STATUS       current
    DESCRIPTION
        "Cisco UCS vnic:LifVsan:dn managed object property"
    ::= { cucsVnicLifVsanEntry 2 }

cucsVnicLifVsanRn OBJECT-TYPE
    SYNTAX       SnmpAdminString
    MAX-ACCESS   read-only
    STATUS       current
    DESCRIPTION
        "Cisco UCS vnic:LifVsan:rn managed object property"
    ::= { cucsVnicLifVsanEntry 3 }

cucsVnicLifVsanInitiator OBJECT-TYPE
    SYNTAX       Unsigned64
    MAX-ACCESS   read-only
    STATUS       current
    DESCRIPTION
        "Cisco UCS vnic:LifVsan:initiator managed object property"
    ::= { cucsVnicLifVsanEntry 4 }

cucsVnicLifVsanName OBJECT-TYPE
    SYNTAX       SnmpAdminString
    MAX-ACCESS   read-only
    STATUS       current
    DESCRIPTION
        "Cisco UCS vnic:LifVsan:name managed object property"
    ::= { cucsVnicLifVsanEntry 5 }

cucsVnicLifVsanOperState OBJECT-TYPE
    SYNTAX       CucsVnicIfOperState
    MAX-ACCESS   read-only
    STATUS       current
    DESCRIPTION
        "Cisco UCS vnic:LifVsan:operState managed object property"
    ::= { cucsVnicLifVsanEntry 6 }

cucsVnicLifVsanOwner OBJECT-TYPE
    SYNTAX       CucsVnicConnectionOwner
    MAX-ACCESS   read-only
    STATUS       current
    DESCRIPTION
        "Cisco UCS vnic:LifVsan:owner managed object property"
    ::= { cucsVnicLifVsanEntry 7 }

cucsVnicLifVsanSwitchId OBJECT-TYPE
    SYNTAX       CucsVnicAFcIfSwitchId
    MAX-ACCESS   read-only
    STATUS       current
    DESCRIPTION
        "Cisco UCS vnic:LifVsan:switchId managed object property"
    ::= { cucsVnicLifVsanEntry 8 }

cucsVnicLifVsanType OBJECT-TYPE
    SYNTAX       CucsVnicAFcIfType
    MAX-ACCESS   read-only
    STATUS       current
    DESCRIPTION
        "Cisco UCS vnic:LifVsan:type managed object property"
    ::= { cucsVnicLifVsanEntry 9 }

cucsVnicLifVsanVnet OBJECT-TYPE
    SYNTAX       Gauge32
    MAX-ACCESS   read-only
    STATUS       current
    DESCRIPTION
        "Cisco UCS vnic:LifVsan:vnet managed object property"
    ::= { cucsVnicLifVsanEntry 10 }

cucsVnicLifVsanConfigQualifier OBJECT-TYPE
    SYNTAX       CucsVnicConfigIssues
    MAX-ACCESS   read-only
    STATUS       current
    DESCRIPTION
        "Cisco UCS vnic:LifVsan:configQualifier managed object property"
    ::= { cucsVnicLifVsanEntry 11 }

cucsVnicLifVsanOperVnetDn OBJECT-TYPE
    SYNTAX       SnmpAdminString
    MAX-ACCESS   read-only
    STATUS       current
    DESCRIPTION
        "Cisco UCS vnic:LifVsan:operVnetDn managed object property"
    ::= { cucsVnicLifVsanEntry 13 }

cucsVnicLifVsanOperVnetName OBJECT-TYPE
    SYNTAX       SnmpAdminString
    MAX-ACCESS   read-only
    STATUS       current
    DESCRIPTION
        "Cisco UCS vnic:LifVsan:operVnetName managed object property"
    ::= { cucsVnicLifVsanEntry 14 }

cucsVnicLifVsanPubNwId OBJECT-TYPE
    SYNTAX       Gauge32
    MAX-ACCESS   read-only
    STATUS       current
    DESCRIPTION
        "Cisco UCS vnic:LifVsan:pubNwId managed object property"
    ::= { cucsVnicLifVsanEntry 15 }

cucsVnicLifVsanSharing OBJECT-TYPE
    SYNTAX       CucsFabricVlanSharingType
    MAX-ACCESS   read-only
    STATUS       current
    DESCRIPTION
        "Cisco UCS vnic:LifVsan:sharing managed object property"
    ::= { cucsVnicLifVsanEntry 16 }

cucsVnicLifVsanOperPrimaryVnetDn OBJECT-TYPE
    SYNTAX       SnmpAdminString
    MAX-ACCESS   read-only
    STATUS       current
    DESCRIPTION
        "Cisco UCS vnic:LifVsan:operPrimaryVnetDn managed object property"
    ::= { cucsVnicLifVsanEntry 17 }

cucsVnicLifVsanOperPrimaryVnetName OBJECT-TYPE
    SYNTAX       SnmpAdminString
    MAX-ACCESS   read-only
    STATUS       current
    DESCRIPTION
        "Cisco UCS vnic:LifVsan:operPrimaryVnetName managed
        object property"
    ::= { cucsVnicLifVsanEntry 18 }

cucsVnicLunTable OBJECT-TYPE
    SYNTAX           SEQUENCE OF CucsVnicLunEntry
    MAX-ACCESS       not-accessible
    STATUS           current
    DESCRIPTION
        "Cisco UCS vnic:Lun managed object table"
    ::= { cucsVnicObjects 43 }

cucsVnicLunEntry OBJECT-TYPE
    SYNTAX           CucsVnicLunEntry
    MAX-ACCESS       not-accessible
    STATUS           current
    DESCRIPTION
        "Entry for the cucsVnicLunTable table."
    INDEX { cucsVnicLunInstanceId }
    ::= { cucsVnicLunTable 1 }

CucsVnicLunEntry ::= SEQUENCE {
    cucsVnicLunInstanceId                                            CucsManagedObjectId,
    cucsVnicLunDn                                                    CucsManagedObjectDn,
    cucsVnicLunRn                                                    SnmpAdminString,
    cucsVnicLunBootable                                              TruthValue,
    cucsVnicLunId                                                    CucsVnicLunId
}

cucsVnicLunInstanceId OBJECT-TYPE
    SYNTAX       CucsManagedObjectId
    MAX-ACCESS   not-accessible
    STATUS       current
    DESCRIPTION
        "Instance identifier of the managed object."
    ::= { cucsVnicLunEntry 1 }

cucsVnicLunDn OBJECT-TYPE
    SYNTAX       CucsManagedObjectDn
    MAX-ACCESS   read-only
    STATUS       current
    DESCRIPTION
        "Cisco UCS vnic:Lun:dn managed object property"
    ::= { cucsVnicLunEntry 2 }

cucsVnicLunRn OBJECT-TYPE
    SYNTAX       SnmpAdminString
    MAX-ACCESS   read-only
    STATUS       current
    DESCRIPTION
        "Cisco UCS vnic:Lun:rn managed object property"
    ::= { cucsVnicLunEntry 3 }

cucsVnicLunBootable OBJECT-TYPE
    SYNTAX       TruthValue
    MAX-ACCESS   read-only
    STATUS       current
    DESCRIPTION
        "Cisco UCS vnic:Lun:bootable managed object property"
    ::= { cucsVnicLunEntry 4 }

cucsVnicLunId OBJECT-TYPE
    SYNTAX       CucsVnicLunId
    MAX-ACCESS   read-only
    STATUS       current
    DESCRIPTION
        "Cisco UCS vnic:Lun:id managed object property"
    ::= { cucsVnicLunEntry 5 }

cucsVnicMacHistoryTable OBJECT-TYPE
    SYNTAX           SEQUENCE OF CucsVnicMacHistoryEntry
    MAX-ACCESS       not-accessible
    STATUS           current
    DESCRIPTION
        "Cisco UCS vnic:MacHistory managed object table"
    ::= { cucsVnicObjects 62 }

cucsVnicMacHistoryEntry OBJECT-TYPE
    SYNTAX           CucsVnicMacHistoryEntry
    MAX-ACCESS       not-accessible
    STATUS           current
    DESCRIPTION
        "Entry for the cucsVnicMacHistoryTable table."
    INDEX { cucsVnicMacHistoryInstanceId }
    ::= { cucsVnicMacHistoryTable 1 }

CucsVnicMacHistoryEntry ::= SEQUENCE {
    cucsVnicMacHistoryInstanceId                                     CucsManagedObjectId,
    cucsVnicMacHistoryDn                                             CucsManagedObjectDn,
    cucsVnicMacHistoryRn                                             SnmpAdminString,
    cucsVnicMacHistoryOldaddr                                        MacAddress
}

cucsVnicMacHistoryInstanceId OBJECT-TYPE
    SYNTAX       CucsManagedObjectId
    MAX-ACCESS   not-accessible
    STATUS       current
    DESCRIPTION
        "Instance identifier of the managed object."
    ::= { cucsVnicMacHistoryEntry 1 }

cucsVnicMacHistoryDn OBJECT-TYPE
    SYNTAX       CucsManagedObjectDn
    MAX-ACCESS   read-only
    STATUS       current
    DESCRIPTION
        "Cisco UCS vnic:MacHistory:dn managed object property"
    ::= { cucsVnicMacHistoryEntry 2 }

cucsVnicMacHistoryRn OBJECT-TYPE
    SYNTAX       SnmpAdminString
    MAX-ACCESS   read-only
    STATUS       current
    DESCRIPTION
        "Cisco UCS vnic:MacHistory:rn managed object property"
    ::= { cucsVnicMacHistoryEntry 3 }

cucsVnicMacHistoryOldaddr OBJECT-TYPE
    SYNTAX       MacAddress
    MAX-ACCESS   read-only
    STATUS       current
    DESCRIPTION
        "Cisco UCS vnic:MacHistory:oldaddr managed object property"
    ::= { cucsVnicMacHistoryEntry 4 }

cucsVnicOProfileAliasTable OBJECT-TYPE
    SYNTAX           SEQUENCE OF CucsVnicOProfileAliasEntry
    MAX-ACCESS       not-accessible
    STATUS           current
    DESCRIPTION
        "Cisco UCS vnic:OProfileAlias managed object table"
    ::= { cucsVnicObjects 44 }

cucsVnicOProfileAliasEntry OBJECT-TYPE
    SYNTAX           CucsVnicOProfileAliasEntry
    MAX-ACCESS       not-accessible
    STATUS           current
    DESCRIPTION
        "Entry for the cucsVnicOProfileAliasTable table."
    INDEX { cucsVnicOProfileAliasInstanceId }
    ::= { cucsVnicOProfileAliasTable 1 }

CucsVnicOProfileAliasEntry ::= SEQUENCE {
    cucsVnicOProfileAliasInstanceId                                  CucsManagedObjectId,
    cucsVnicOProfileAliasDn                                          CucsManagedObjectDn,
    cucsVnicOProfileAliasRn                                          SnmpAdminString,
    cucsVnicOProfileAliasAlias                                       SnmpAdminString,
    cucsVnicOProfileAliasMgmtPlane                                   CucsVmMgmtPlane,
    cucsVnicOProfileAliasVSwitchId                                   SnmpAdminString,
    cucsVnicOProfileAliasVSwitchName                                 SnmpAdminString
}

cucsVnicOProfileAliasInstanceId OBJECT-TYPE
    SYNTAX       CucsManagedObjectId
    MAX-ACCESS   not-accessible
    STATUS       current
    DESCRIPTION
        "Instance identifier of the managed object."
    ::= { cucsVnicOProfileAliasEntry 1 }

cucsVnicOProfileAliasDn OBJECT-TYPE
    SYNTAX       CucsManagedObjectDn
    MAX-ACCESS   read-only
    STATUS       current
    DESCRIPTION
        "Cisco UCS vnic:OProfileAlias:dn managed object property"
    ::= { cucsVnicOProfileAliasEntry 2 }

cucsVnicOProfileAliasRn OBJECT-TYPE
    SYNTAX       SnmpAdminString
    MAX-ACCESS   read-only
    STATUS       current
    DESCRIPTION
        "Cisco UCS vnic:OProfileAlias:rn managed object property"
    ::= { cucsVnicOProfileAliasEntry 3 }

cucsVnicOProfileAliasAlias OBJECT-TYPE
    SYNTAX       SnmpAdminString
    MAX-ACCESS   read-only
    STATUS       current
    DESCRIPTION
        "Cisco UCS vnic:OProfileAlias:alias managed object property"
    ::= { cucsVnicOProfileAliasEntry 4 }

cucsVnicOProfileAliasMgmtPlane OBJECT-TYPE
    SYNTAX       CucsVmMgmtPlane
    MAX-ACCESS   read-only
    STATUS       current
    DESCRIPTION
        "Cisco UCS vnic:OProfileAlias:mgmtPlane managed object property"
    ::= { cucsVnicOProfileAliasEntry 5 }

cucsVnicOProfileAliasVSwitchId OBJECT-TYPE
    SYNTAX       SnmpAdminString
    MAX-ACCESS   read-only
    STATUS       current
    DESCRIPTION
        "Cisco UCS vnic:OProfileAlias:vSwitchId managed object property"
    ::= { cucsVnicOProfileAliasEntry 6 }

cucsVnicOProfileAliasVSwitchName OBJECT-TYPE
    SYNTAX       SnmpAdminString
    MAX-ACCESS   read-only
    STATUS       current
    DESCRIPTION
        "Cisco UCS vnic:OProfileAlias:vSwitchName managed object property"
    ::= { cucsVnicOProfileAliasEntry 7 }

cucsVnicProfileTable OBJECT-TYPE
    SYNTAX           SEQUENCE OF CucsVnicProfileEntry
    MAX-ACCESS       not-accessible
    STATUS           current
    DESCRIPTION
        "Cisco UCS vnic:Profile managed object table"
    ::= { cucsVnicObjects 28 }

cucsVnicProfileEntry OBJECT-TYPE
    SYNTAX           CucsVnicProfileEntry
    MAX-ACCESS       not-accessible
    STATUS           current
    DESCRIPTION
        "Entry for the cucsVnicProfileTable table."
    INDEX { cucsVnicProfileInstanceId }
    ::= { cucsVnicProfileTable 1 }

CucsVnicProfileEntry ::= SEQUENCE {
    cucsVnicProfileInstanceId                                        CucsManagedObjectId,
    cucsVnicProfileDn                                                CucsManagedObjectDn,
    cucsVnicProfileRn                                                SnmpAdminString,
    cucsVnicProfileCdp                                               CucsNwctrlAdminState,
    cucsVnicProfileCos                                               Gauge32,
    cucsVnicProfileDescr                                             SnmpAdminString,
    cucsVnicProfileForgeMac                                          CucsDpsecForgedTransmit,
    cucsVnicProfileIntId                                             SnmpAdminString,
    cucsVnicProfileMaxPorts                                          Gauge32,
    cucsVnicProfileName                                              SnmpAdminString,
    cucsVnicProfileNwCtrlPolicyName                                  SnmpAdminString,
    cucsVnicProfileOperNwCtrlPolicyName                              SnmpAdminString,
    cucsVnicProfileOperQosPolicyName                                 SnmpAdminString,
    cucsVnicProfilePinToGroupName                                    SnmpAdminString,
    cucsVnicProfileQosPolicyId                                       SnmpAdminString,
    cucsVnicProfileQosPolicyName                                     SnmpAdminString,
    cucsVnicProfileSwABorderPort                                     Gauge32,
    cucsVnicProfileSwABorderSlot                                     Gauge32,
    cucsVnicProfileSwBBorderPort                                     Gauge32,
    cucsVnicProfileSwBBorderSlot                                     Gauge32,
    cucsVnicProfileUplinkFailAction                                  CucsNwctrlLinkFailAction,
    cucsVnicProfileHostNwIOPerf                                      CucsVnicHostNwIOPerfPref,
    cucsVnicProfilePrimaryVlanId                                     Gauge32,
    cucsVnicProfileQosPolicyDn                                       SnmpAdminString,
    cucsVnicProfileConfigQualifier                                   CucsVnicProfileConfigQualifier,
    cucsVnicProfileMacRegisterMode                                   CucsNwctrlRegistrationMode,
    cucsVnicProfilePolicyLevel                                       Gauge32,
    cucsVnicProfilePolicyOwner                                       CucsPolicyPolicyOwner,
    cucsVnicProfilePortProfileUuid                                   SnmpAdminString,
    cucsVnicProfileType                                              CucsVnicPortProfileType,
    cucsVnicProfileSwABorderAggrPort                                 Gauge32,
    cucsVnicProfileSwBBorderAggrPort                                 Gauge32,
    cucsVnicProfileLldp                                              CucsNwctrlLldpAdminStateBitmask
}

cucsVnicProfileInstanceId OBJECT-TYPE
    SYNTAX       CucsManagedObjectId
    MAX-ACCESS   not-accessible
    STATUS       current
    DESCRIPTION
        "Instance identifier of the managed object."
    ::= { cucsVnicProfileEntry 1 }

cucsVnicProfileDn OBJECT-TYPE
    SYNTAX       CucsManagedObjectDn
    MAX-ACCESS   read-only
    STATUS       current
    DESCRIPTION
        "Cisco UCS vnic:Profile:dn managed object property"
    ::= { cucsVnicProfileEntry 2 }

cucsVnicProfileRn OBJECT-TYPE
    SYNTAX       SnmpAdminString
    MAX-ACCESS   read-only
    STATUS       current
    DESCRIPTION
        "Cisco UCS vnic:Profile:rn managed object property"
    ::= { cucsVnicProfileEntry 3 }

cucsVnicProfileCdp OBJECT-TYPE
    SYNTAX       CucsNwctrlAdminState
    MAX-ACCESS   read-only
    STATUS       current
    DESCRIPTION
        "Cisco UCS vnic:Profile:cdp managed object property"
    ::= { cucsVnicProfileEntry 5 }

cucsVnicProfileCos OBJECT-TYPE
    SYNTAX       Gauge32
    MAX-ACCESS   read-only
    STATUS       current
    DESCRIPTION
        "Cisco UCS vnic:Profile:cos managed object property"
    ::= { cucsVnicProfileEntry 6 }

cucsVnicProfileDescr OBJECT-TYPE
    SYNTAX       SnmpAdminString
    MAX-ACCESS   read-only
    STATUS       current
    DESCRIPTION
        "Cisco UCS vnic:Profile:descr managed object property"
    ::= { cucsVnicProfileEntry 7 }

cucsVnicProfileForgeMac OBJECT-TYPE
    SYNTAX       CucsDpsecForgedTransmit
    MAX-ACCESS   read-only
    STATUS       current
    DESCRIPTION
        "Cisco UCS vnic:Profile:forgeMac managed object property"
    ::= { cucsVnicProfileEntry 8 }

cucsVnicProfileIntId OBJECT-TYPE
    SYNTAX       SnmpAdminString
    MAX-ACCESS   read-only
    STATUS       current
    DESCRIPTION
        "Cisco UCS vnic:Profile:intId managed object property"
    ::= { cucsVnicProfileEntry 9 }

cucsVnicProfileMaxPorts OBJECT-TYPE
    SYNTAX       Gauge32
    MAX-ACCESS   read-only
    STATUS       current
    DESCRIPTION
        "Cisco UCS vnic:Profile:maxPorts managed object property"
    ::= { cucsVnicProfileEntry 10 }

cucsVnicProfileName OBJECT-TYPE
    SYNTAX       SnmpAdminString
    MAX-ACCESS   read-only
    STATUS       current
    DESCRIPTION
        "Cisco UCS vnic:Profile:name managed object property"
    ::= { cucsVnicProfileEntry 11 }

cucsVnicProfileNwCtrlPolicyName OBJECT-TYPE
    SYNTAX       SnmpAdminString
    MAX-ACCESS   read-only
    STATUS       current
    DESCRIPTION
        "Cisco UCS vnic:Profile:nwCtrlPolicyName managed object property"
    ::= { cucsVnicProfileEntry 12 }

cucsVnicProfileOperNwCtrlPolicyName OBJECT-TYPE
    SYNTAX       SnmpAdminString
    MAX-ACCESS   read-only
    STATUS       current
    DESCRIPTION
        "Cisco UCS vnic:Profile:operNwCtrlPolicyName managed
        object property"
    ::= { cucsVnicProfileEntry 13 }

cucsVnicProfileOperQosPolicyName OBJECT-TYPE
    SYNTAX       SnmpAdminString
    MAX-ACCESS   read-only
    STATUS       current
    DESCRIPTION
        "Cisco UCS vnic:Profile:operQosPolicyName managed object property"
    ::= { cucsVnicProfileEntry 14 }

cucsVnicProfilePinToGroupName OBJECT-TYPE
    SYNTAX       SnmpAdminString
    MAX-ACCESS   read-only
    STATUS       current
    DESCRIPTION
        "Cisco UCS vnic:Profile:pinToGroupName managed object property"
    ::= { cucsVnicProfileEntry 15 }

cucsVnicProfileQosPolicyId OBJECT-TYPE
    SYNTAX       SnmpAdminString
    MAX-ACCESS   read-only
    STATUS       current
    DESCRIPTION
        "Cisco UCS vnic:Profile:qosPolicyId managed object property"
    ::= { cucsVnicProfileEntry 16 }

cucsVnicProfileQosPolicyName OBJECT-TYPE
    SYNTAX       SnmpAdminString
    MAX-ACCESS   read-only
    STATUS       current
    DESCRIPTION
        "Cisco UCS vnic:Profile:qosPolicyName managed object property"
    ::= { cucsVnicProfileEntry 17 }

cucsVnicProfileSwABorderPort OBJECT-TYPE
    SYNTAX       Gauge32
    MAX-ACCESS   read-only
    STATUS       current
    DESCRIPTION
        "Cisco UCS vnic:Profile:swABorderPort managed object property"
    ::= { cucsVnicProfileEntry 19 }

cucsVnicProfileSwABorderSlot OBJECT-TYPE
    SYNTAX       Gauge32
    MAX-ACCESS   read-only
    STATUS       current
    DESCRIPTION
        "Cisco UCS vnic:Profile:swABorderSlot managed object property"
    ::= { cucsVnicProfileEntry 20 }

cucsVnicProfileSwBBorderPort OBJECT-TYPE
    SYNTAX       Gauge32
    MAX-ACCESS   read-only
    STATUS       current
    DESCRIPTION
        "Cisco UCS vnic:Profile:swBBorderPort managed object property"
    ::= { cucsVnicProfileEntry 21 }

cucsVnicProfileSwBBorderSlot OBJECT-TYPE
    SYNTAX       Gauge32
    MAX-ACCESS   read-only
    STATUS       current
    DESCRIPTION
        "Cisco UCS vnic:Profile:swBBorderSlot managed object property"
    ::= { cucsVnicProfileEntry 22 }

cucsVnicProfileUplinkFailAction OBJECT-TYPE
    SYNTAX       CucsNwctrlLinkFailAction
    MAX-ACCESS   read-only
    STATUS       current
    DESCRIPTION
        "Cisco UCS vnic:Profile:uplinkFailAction managed object property"
    ::= { cucsVnicProfileEntry 23 }

cucsVnicProfileHostNwIOPerf OBJECT-TYPE
    SYNTAX       CucsVnicHostNwIOPerfPref
    MAX-ACCESS   read-only
    STATUS       current
    DESCRIPTION
        "Cisco UCS vnic:Profile:hostNwIOPerf managed object property"
    ::= { cucsVnicProfileEntry 24 }

cucsVnicProfilePrimaryVlanId OBJECT-TYPE
    SYNTAX       Gauge32
    MAX-ACCESS   read-only
    STATUS       current
    DESCRIPTION
        "Cisco UCS vnic:Profile:primaryVlanId managed object property"
    ::= { cucsVnicProfileEntry 25 }

cucsVnicProfileQosPolicyDn OBJECT-TYPE
    SYNTAX       SnmpAdminString
    MAX-ACCESS   read-only
    STATUS       current
    DESCRIPTION
        "Cisco UCS vnic:Profile:qosPolicyDn managed object property"
    ::= { cucsVnicProfileEntry 26 }

cucsVnicProfileConfigQualifier OBJECT-TYPE
    SYNTAX       CucsVnicProfileConfigQualifier
    MAX-ACCESS   read-only
    STATUS       current
    DESCRIPTION
        "Cisco UCS vnic:Profile:configQualifier managed object property"
    ::= { cucsVnicProfileEntry 27 }

cucsVnicProfileMacRegisterMode OBJECT-TYPE
    SYNTAX       CucsNwctrlRegistrationMode
    MAX-ACCESS   read-only
    STATUS       current
    DESCRIPTION
        "Cisco UCS vnic:Profile:macRegisterMode managed object property"
    ::= { cucsVnicProfileEntry 28 }

cucsVnicProfilePolicyLevel OBJECT-TYPE
    SYNTAX       Gauge32
    MAX-ACCESS   read-only
    STATUS       current
    DESCRIPTION
        "Cisco UCS vnic:Profile:policyLevel managed object property"
    ::= { cucsVnicProfileEntry 29 }

cucsVnicProfilePolicyOwner OBJECT-TYPE
    SYNTAX       CucsPolicyPolicyOwner
    MAX-ACCESS   read-only
    STATUS       current
    DESCRIPTION
        "Cisco UCS vnic:Profile:policyOwner managed object property"
    ::= { cucsVnicProfileEntry 30 }

cucsVnicProfilePortProfileUuid OBJECT-TYPE
    SYNTAX       SnmpAdminString
    MAX-ACCESS   read-only
    STATUS       current
    DESCRIPTION
        "Cisco UCS vnic:Profile:portProfileUuid managed object property"
    ::= { cucsVnicProfileEntry 31 }

cucsVnicProfileType OBJECT-TYPE
    SYNTAX       CucsVnicPortProfileType
    MAX-ACCESS   read-only
    STATUS       current
    DESCRIPTION
        "Cisco UCS vnic:Profile:type managed object property"
    ::= { cucsVnicProfileEntry 32 }

cucsVnicProfileSwABorderAggrPort OBJECT-TYPE
    SYNTAX       Gauge32
    MAX-ACCESS   read-only
    STATUS       current
    DESCRIPTION
        "Cisco UCS vnic:Profile:swABorderAggrPort managed object property"
    ::= { cucsVnicProfileEntry 33 }

cucsVnicProfileSwBBorderAggrPort OBJECT-TYPE
    SYNTAX       Gauge32
    MAX-ACCESS   read-only
    STATUS       current
    DESCRIPTION
        "Cisco UCS vnic:Profile:swBBorderAggrPort managed object property"
    ::= { cucsVnicProfileEntry 34 }

cucsVnicProfileLldp OBJECT-TYPE
    SYNTAX       CucsNwctrlLldpAdminStateBitmask
    MAX-ACCESS   read-only
    STATUS       current
    DESCRIPTION
        "Cisco UCS vnic:Profile:lldp managed object property"
    ::= { cucsVnicProfileEntry 35 }

cucsVnicProfileAliasTable OBJECT-TYPE
    SYNTAX           SEQUENCE OF CucsVnicProfileAliasEntry
    MAX-ACCESS       not-accessible
    STATUS           current
    DESCRIPTION
        "Cisco UCS vnic:ProfileAlias managed object table"
    ::= { cucsVnicObjects 29 }

cucsVnicProfileAliasEntry OBJECT-TYPE
    SYNTAX           CucsVnicProfileAliasEntry
    MAX-ACCESS       not-accessible
    STATUS           current
    DESCRIPTION
        "Entry for the cucsVnicProfileAliasTable table."
    INDEX { cucsVnicProfileAliasInstanceId }
    ::= { cucsVnicProfileAliasTable 1 }

CucsVnicProfileAliasEntry ::= SEQUENCE {
    cucsVnicProfileAliasInstanceId                                   CucsManagedObjectId,
    cucsVnicProfileAliasDn                                           CucsManagedObjectDn,
    cucsVnicProfileAliasRn                                           SnmpAdminString,
    cucsVnicProfileAliasAlias                                        SnmpAdminString,
    cucsVnicProfileAliasSwUuid                                       SnmpAdminString
}

cucsVnicProfileAliasInstanceId OBJECT-TYPE
    SYNTAX       CucsManagedObjectId
    MAX-ACCESS   not-accessible
    STATUS       current
    DESCRIPTION
        "Instance identifier of the managed object."
    ::= { cucsVnicProfileAliasEntry 1 }

cucsVnicProfileAliasDn OBJECT-TYPE
    SYNTAX       CucsManagedObjectDn
    MAX-ACCESS   read-only
    STATUS       current
    DESCRIPTION
        "Cisco UCS vnic:ProfileAlias:dn managed object property"
    ::= { cucsVnicProfileAliasEntry 2 }

cucsVnicProfileAliasRn OBJECT-TYPE
    SYNTAX       SnmpAdminString
    MAX-ACCESS   read-only
    STATUS       current
    DESCRIPTION
        "Cisco UCS vnic:ProfileAlias:rn managed object property"
    ::= { cucsVnicProfileAliasEntry 3 }

cucsVnicProfileAliasAlias OBJECT-TYPE
    SYNTAX       SnmpAdminString
    MAX-ACCESS   read-only
    STATUS       current
    DESCRIPTION
        "Cisco UCS vnic:ProfileAlias:alias managed object property"
    ::= { cucsVnicProfileAliasEntry 4 }

cucsVnicProfileAliasSwUuid OBJECT-TYPE
    SYNTAX       SnmpAdminString
    MAX-ACCESS   read-only
    STATUS       current
    DESCRIPTION
        "Cisco UCS vnic:ProfileAlias:swUuid managed object property"
    ::= { cucsVnicProfileAliasEntry 5 }

cucsVnicProfileRefTable OBJECT-TYPE
    SYNTAX           SEQUENCE OF CucsVnicProfileRefEntry
    MAX-ACCESS       not-accessible
    STATUS           current
    DESCRIPTION
        "Cisco UCS vnic:ProfileRef managed object table"
    ::= { cucsVnicObjects 68 }

cucsVnicProfileRefEntry OBJECT-TYPE
    SYNTAX           CucsVnicProfileRefEntry
    MAX-ACCESS       not-accessible
    STATUS           current
    DESCRIPTION
        "Entry for the cucsVnicProfileRefTable table."
    INDEX { cucsVnicProfileRefInstanceId }
    ::= { cucsVnicProfileRefTable 1 }

CucsVnicProfileRefEntry ::= SEQUENCE {
    cucsVnicProfileRefInstanceId                                     CucsManagedObjectId,
    cucsVnicProfileRefDn                                             CucsManagedObjectDn,
    cucsVnicProfileRefRn                                             SnmpAdminString,
    cucsVnicProfileRefName                                           SnmpAdminString,
    cucsVnicProfileRefSourceDn                                       SnmpAdminString
}

cucsVnicProfileRefInstanceId OBJECT-TYPE
    SYNTAX       CucsManagedObjectId
    MAX-ACCESS   not-accessible
    STATUS       current
    DESCRIPTION
        "Instance identifier of the managed object."
    ::= { cucsVnicProfileRefEntry 1 }

cucsVnicProfileRefDn OBJECT-TYPE
    SYNTAX       CucsManagedObjectDn
    MAX-ACCESS   read-only
    STATUS       current
    DESCRIPTION
        "Cisco UCS vnic:ProfileRef:dn managed object property"
    ::= { cucsVnicProfileRefEntry 2 }

cucsVnicProfileRefRn OBJECT-TYPE
    SYNTAX       SnmpAdminString
    MAX-ACCESS   read-only
    STATUS       current
    DESCRIPTION
        "Cisco UCS vnic:ProfileRef:rn managed object property"
    ::= { cucsVnicProfileRefEntry 3 }

cucsVnicProfileRefName OBJECT-TYPE
    SYNTAX       SnmpAdminString
    MAX-ACCESS   read-only
    STATUS       current
    DESCRIPTION
        "Cisco UCS vnic:ProfileRef:name managed object property"
    ::= { cucsVnicProfileRefEntry 4 }

cucsVnicProfileRefSourceDn OBJECT-TYPE
    SYNTAX       SnmpAdminString
    MAX-ACCESS   read-only
    STATUS       current
    DESCRIPTION
        "Cisco UCS vnic:ProfileRef:sourceDn managed object property"
    ::= { cucsVnicProfileRefEntry 5 }

cucsVnicProfileSetTable OBJECT-TYPE
    SYNTAX           SEQUENCE OF CucsVnicProfileSetEntry
    MAX-ACCESS       not-accessible
    STATUS           current
    DESCRIPTION
        "Cisco UCS vnic:ProfileSet managed object table"
    ::= { cucsVnicObjects 30 }

cucsVnicProfileSetEntry OBJECT-TYPE
    SYNTAX           CucsVnicProfileSetEntry
    MAX-ACCESS       not-accessible
    STATUS           current
    DESCRIPTION
        "Entry for the cucsVnicProfileSetTable table."
    INDEX { cucsVnicProfileSetInstanceId }
    ::= { cucsVnicProfileSetTable 1 }

CucsVnicProfileSetEntry ::= SEQUENCE {
    cucsVnicProfileSetInstanceId                                     CucsManagedObjectId,
    cucsVnicProfileSetDn                                             CucsManagedObjectDn,
    cucsVnicProfileSetRn                                             SnmpAdminString,
    cucsVnicProfileSetFsmDescr                                       SnmpAdminString,
    cucsVnicProfileSetFsmPrev                                        SnmpAdminString,
    cucsVnicProfileSetFsmProgr                                       Gauge32,
    cucsVnicProfileSetFsmRmtInvErrCode                               Gauge32,
    cucsVnicProfileSetFsmRmtInvErrDescr                              SnmpAdminString,
    cucsVnicProfileSetFsmRmtInvRslt                                  CucsConditionRemoteInvRslt,
    cucsVnicProfileSetFsmStageDescr                                  SnmpAdminString,
    cucsVnicProfileSetFsmStamp                                       DateAndTime,
    cucsVnicProfileSetFsmStatus                                      SnmpAdminString,
    cucsVnicProfileSetFsmTry                                         Gauge32,
    cucsVnicProfileSetFltAggr                                        Unsigned64,
    cucsVnicProfileSetGenNum                                         Gauge32,
    cucsVnicProfileSetVlanGroupUpdate                                CucsVnicVlanGroupUpdate
}

cucsVnicProfileSetInstanceId OBJECT-TYPE
    SYNTAX       CucsManagedObjectId
    MAX-ACCESS   not-accessible
    STATUS       current
    DESCRIPTION
        "Instance identifier of the managed object."
    ::= { cucsVnicProfileSetEntry 1 }

cucsVnicProfileSetDn OBJECT-TYPE
    SYNTAX       CucsManagedObjectDn
    MAX-ACCESS   read-only
    STATUS       current
    DESCRIPTION
        "Cisco UCS vnic:ProfileSet:dn managed object property"
    ::= { cucsVnicProfileSetEntry 2 }

cucsVnicProfileSetRn OBJECT-TYPE
    SYNTAX       SnmpAdminString
    MAX-ACCESS   read-only
    STATUS       current
    DESCRIPTION
        "Cisco UCS vnic:ProfileSet:rn managed object property"
    ::= { cucsVnicProfileSetEntry 3 }

cucsVnicProfileSetFsmDescr OBJECT-TYPE
    SYNTAX       SnmpAdminString
    MAX-ACCESS   read-only
    STATUS       current
    DESCRIPTION
        "Cisco UCS vnic:ProfileSet:fsmDescr managed object property"
    ::= { cucsVnicProfileSetEntry 4 }

cucsVnicProfileSetFsmPrev OBJECT-TYPE
    SYNTAX       SnmpAdminString
    MAX-ACCESS   read-only
    STATUS       current
    DESCRIPTION
        "Cisco UCS vnic:ProfileSet:fsmPrev managed object property"
    ::= { cucsVnicProfileSetEntry 5 }

cucsVnicProfileSetFsmProgr OBJECT-TYPE
    SYNTAX       Gauge32
    MAX-ACCESS   read-only
    STATUS       current
    DESCRIPTION
        "Cisco UCS vnic:ProfileSet:fsmProgr managed object property"
    ::= { cucsVnicProfileSetEntry 6 }

cucsVnicProfileSetFsmRmtInvErrCode OBJECT-TYPE
    SYNTAX       Gauge32
    MAX-ACCESS   read-only
    STATUS       current
    DESCRIPTION
        "Cisco UCS vnic:ProfileSet:fsmRmtInvErrCode managed
        object property"
    ::= { cucsVnicProfileSetEntry 7 }

cucsVnicProfileSetFsmRmtInvErrDescr OBJECT-TYPE
    SYNTAX       SnmpAdminString
    MAX-ACCESS   read-only
    STATUS       current
    DESCRIPTION
        "Cisco UCS vnic:ProfileSet:fsmRmtInvErrDescr managed
        object property"
    ::= { cucsVnicProfileSetEntry 8 }

cucsVnicProfileSetFsmRmtInvRslt OBJECT-TYPE
    SYNTAX       CucsConditionRemoteInvRslt
    MAX-ACCESS   read-only
    STATUS       current
    DESCRIPTION
        "Cisco UCS vnic:ProfileSet:fsmRmtInvRslt managed object property"
    ::= { cucsVnicProfileSetEntry 9 }

cucsVnicProfileSetFsmStageDescr OBJECT-TYPE
    SYNTAX       SnmpAdminString
    MAX-ACCESS   read-only
    STATUS       current
    DESCRIPTION
        "Cisco UCS vnic:ProfileSet:fsmStageDescr managed object property"
    ::= { cucsVnicProfileSetEntry 10 }

cucsVnicProfileSetFsmStamp OBJECT-TYPE
    SYNTAX       DateAndTime
    MAX-ACCESS   read-only
    STATUS       current
    DESCRIPTION
        "Cisco UCS vnic:ProfileSet:fsmStamp managed object property"
    ::= { cucsVnicProfileSetEntry 11 }

cucsVnicProfileSetFsmStatus OBJECT-TYPE
    SYNTAX       SnmpAdminString
    MAX-ACCESS   read-only
    STATUS       current
    DESCRIPTION
        "Cisco UCS vnic:ProfileSet:fsmStatus managed object property"
    ::= { cucsVnicProfileSetEntry 12 }

cucsVnicProfileSetFsmTry OBJECT-TYPE
    SYNTAX       Gauge32
    MAX-ACCESS   read-only
    STATUS       current
    DESCRIPTION
        "Cisco UCS vnic:ProfileSet:fsmTry managed object property"
    ::= { cucsVnicProfileSetEntry 13 }

cucsVnicProfileSetFltAggr OBJECT-TYPE
    SYNTAX       Unsigned64
    MAX-ACCESS   read-only
    STATUS       current
    DESCRIPTION
        "Cisco UCS vnic:ProfileSet:fltAggr managed object property"
    ::= { cucsVnicProfileSetEntry 14 }

cucsVnicProfileSetGenNum OBJECT-TYPE
    SYNTAX       Gauge32
    MAX-ACCESS   read-only
    STATUS       current
    DESCRIPTION
        "Cisco UCS vnic:ProfileSet:genNum managed object property"
    ::= { cucsVnicProfileSetEntry 15 }

cucsVnicProfileSetVlanGroupUpdate OBJECT-TYPE
    SYNTAX       CucsVnicVlanGroupUpdate
    MAX-ACCESS   read-only
    STATUS       current
    DESCRIPTION
        "Cisco UCS vnic:ProfileSet:vlanGroupUpdate managed
        object property"
    ::= { cucsVnicProfileSetEntry 16 }

cucsVnicProfileSetFsmTable OBJECT-TYPE
    SYNTAX           SEQUENCE OF CucsVnicProfileSetFsmEntry
    MAX-ACCESS       not-accessible
    STATUS           current
    DESCRIPTION
        "Cisco UCS vnic:ProfileSetFsm managed object table"
    ::= { cucsVnicObjects 54 }

cucsVnicProfileSetFsmEntry OBJECT-TYPE
    SYNTAX           CucsVnicProfileSetFsmEntry
    MAX-ACCESS       not-accessible
    STATUS           current
    DESCRIPTION
        "Entry for the cucsVnicProfileSetFsmTable table."
    INDEX { cucsVnicProfileSetFsmInstanceId }
    ::= { cucsVnicProfileSetFsmTable 1 }

CucsVnicProfileSetFsmEntry ::= SEQUENCE {
    cucsVnicProfileSetFsmInstanceId                                  CucsManagedObjectId,
    cucsVnicProfileSetFsmDn                                          CucsManagedObjectDn,
    cucsVnicProfileSetFsmRn                                          SnmpAdminString,
    cucsVnicProfileSetFsmCompletionTime                              DateAndTime,
    cucsVnicProfileSetFsmCurrentFsm                                  CucsVnicProfileSetFsmCurrentFsm,
    cucsVnicProfileSetFsmDescrData                                   SnmpAdminString,
    cucsVnicProfileSetFsmFsmStatus                                   CucsFsmFsmStageStatus,
    cucsVnicProfileSetFsmProgress                                    Gauge32,
    cucsVnicProfileSetFsmRmtErrCode                                  Gauge32,
    cucsVnicProfileSetFsmRmtErrDescr                                 SnmpAdminString,
    cucsVnicProfileSetFsmRmtRslt                                     CucsConditionRemoteInvRslt
}

cucsVnicProfileSetFsmInstanceId OBJECT-TYPE
    SYNTAX       CucsManagedObjectId
    MAX-ACCESS   not-accessible
    STATUS       current
    DESCRIPTION
        "Instance identifier of the managed object."
    ::= { cucsVnicProfileSetFsmEntry 1 }

cucsVnicProfileSetFsmDn OBJECT-TYPE
    SYNTAX       CucsManagedObjectDn
    MAX-ACCESS   read-only
    STATUS       current
    DESCRIPTION
        "Cisco UCS vnic:ProfileSetFsm:dn managed object property"
    ::= { cucsVnicProfileSetFsmEntry 2 }

cucsVnicProfileSetFsmRn OBJECT-TYPE
    SYNTAX       SnmpAdminString
    MAX-ACCESS   read-only
    STATUS       current
    DESCRIPTION
        "Cisco UCS vnic:ProfileSetFsm:rn managed object property"
    ::= { cucsVnicProfileSetFsmEntry 3 }

cucsVnicProfileSetFsmCompletionTime OBJECT-TYPE
    SYNTAX       DateAndTime
    MAX-ACCESS   read-only
    STATUS       current
    DESCRIPTION
        "Cisco UCS vnic:ProfileSetFsm:completionTime managed
        object property"
    ::= { cucsVnicProfileSetFsmEntry 4 }

cucsVnicProfileSetFsmCurrentFsm OBJECT-TYPE
    SYNTAX       CucsVnicProfileSetFsmCurrentFsm
    MAX-ACCESS   read-only
    STATUS       current
    DESCRIPTION
        "Cisco UCS vnic:ProfileSetFsm:currentFsm managed object property"
    ::= { cucsVnicProfileSetFsmEntry 5 }

cucsVnicProfileSetFsmDescrData OBJECT-TYPE
    SYNTAX       SnmpAdminString
    MAX-ACCESS   read-only
    STATUS       current
    DESCRIPTION
        "Cisco UCS vnic:ProfileSetFsm:descr managed object property"
    ::= { cucsVnicProfileSetFsmEntry 6 }

cucsVnicProfileSetFsmFsmStatus OBJECT-TYPE
    SYNTAX       CucsFsmFsmStageStatus
    MAX-ACCESS   read-only
    STATUS       current
    DESCRIPTION
        "Cisco UCS vnic:ProfileSetFsm:fsmStatus managed object property"
    ::= { cucsVnicProfileSetFsmEntry 7 }

cucsVnicProfileSetFsmProgress OBJECT-TYPE
    SYNTAX       Gauge32
    MAX-ACCESS   read-only
    STATUS       current
    DESCRIPTION
        "Cisco UCS vnic:ProfileSetFsm:progress managed object property"
    ::= { cucsVnicProfileSetFsmEntry 8 }

cucsVnicProfileSetFsmRmtErrCode OBJECT-TYPE
    SYNTAX       Gauge32
    MAX-ACCESS   read-only
    STATUS       current
    DESCRIPTION
        "Cisco UCS vnic:ProfileSetFsm:rmtErrCode managed object property"
    ::= { cucsVnicProfileSetFsmEntry 9 }

cucsVnicProfileSetFsmRmtErrDescr OBJECT-TYPE
    SYNTAX       SnmpAdminString
    MAX-ACCESS   read-only
    STATUS       current
    DESCRIPTION
        "Cisco UCS vnic:ProfileSetFsm:rmtErrDescr managed object property"
    ::= { cucsVnicProfileSetFsmEntry 10 }

cucsVnicProfileSetFsmRmtRslt OBJECT-TYPE
    SYNTAX       CucsConditionRemoteInvRslt
    MAX-ACCESS   read-only
    STATUS       current
    DESCRIPTION
        "Cisco UCS vnic:ProfileSetFsm:rmtRslt managed object property"
    ::= { cucsVnicProfileSetFsmEntry 11 }

cucsVnicProfileSetFsmStageTable OBJECT-TYPE
    SYNTAX           SEQUENCE OF CucsVnicProfileSetFsmStageEntry
    MAX-ACCESS       not-accessible
    STATUS           current
    DESCRIPTION
        "Cisco UCS vnic:ProfileSetFsmStage managed object table"
    ::= { cucsVnicObjects 55 }

cucsVnicProfileSetFsmStageEntry OBJECT-TYPE
    SYNTAX           CucsVnicProfileSetFsmStageEntry
    MAX-ACCESS       not-accessible
    STATUS           current
    DESCRIPTION
        "Entry for the cucsVnicProfileSetFsmStageTable table."
    INDEX { cucsVnicProfileSetFsmStageInstanceId }
    ::= { cucsVnicProfileSetFsmStageTable 1 }

CucsVnicProfileSetFsmStageEntry ::= SEQUENCE {
    cucsVnicProfileSetFsmStageInstanceId                             CucsManagedObjectId,
    cucsVnicProfileSetFsmStageDn                                     CucsManagedObjectDn,
    cucsVnicProfileSetFsmStageRn                                     SnmpAdminString,
    cucsVnicProfileSetFsmStageDescrData                              SnmpAdminString,
    cucsVnicProfileSetFsmStageLastUpdateTime                         DateAndTime,
    cucsVnicProfileSetFsmStageName                                   CucsVnicProfileSetFsmStageName,
    cucsVnicProfileSetFsmStageOrder                                  Gauge32,
    cucsVnicProfileSetFsmStageRetry                                  Gauge32,
    cucsVnicProfileSetFsmStageStageStatus                            CucsFsmFsmStageStatus
}

cucsVnicProfileSetFsmStageInstanceId OBJECT-TYPE
    SYNTAX       CucsManagedObjectId
    MAX-ACCESS   not-accessible
    STATUS       current
    DESCRIPTION
        "Instance identifier of the managed object."
    ::= { cucsVnicProfileSetFsmStageEntry 1 }

cucsVnicProfileSetFsmStageDn OBJECT-TYPE
    SYNTAX       CucsManagedObjectDn
    MAX-ACCESS   read-only
    STATUS       current
    DESCRIPTION
        "Cisco UCS vnic:ProfileSetFsmStage:dn managed object property"
    ::= { cucsVnicProfileSetFsmStageEntry 2 }

cucsVnicProfileSetFsmStageRn OBJECT-TYPE
    SYNTAX       SnmpAdminString
    MAX-ACCESS   read-only
    STATUS       current
    DESCRIPTION
        "Cisco UCS vnic:ProfileSetFsmStage:rn managed object property"
    ::= { cucsVnicProfileSetFsmStageEntry 3 }

cucsVnicProfileSetFsmStageDescrData OBJECT-TYPE
    SYNTAX       SnmpAdminString
    MAX-ACCESS   read-only
    STATUS       current
    DESCRIPTION
        "Cisco UCS vnic:ProfileSetFsmStage:descr managed object property"
    ::= { cucsVnicProfileSetFsmStageEntry 4 }

cucsVnicProfileSetFsmStageLastUpdateTime OBJECT-TYPE
    SYNTAX       DateAndTime
    MAX-ACCESS   read-only
    STATUS       current
    DESCRIPTION
        "Cisco UCS vnic:ProfileSetFsmStage:lastUpdateTime
        managed object property"
    ::= { cucsVnicProfileSetFsmStageEntry 5 }

cucsVnicProfileSetFsmStageName OBJECT-TYPE
    SYNTAX       CucsVnicProfileSetFsmStageName
    MAX-ACCESS   read-only
    STATUS       current
    DESCRIPTION
        "Cisco UCS vnic:ProfileSetFsmStage:name managed object property"
    ::= { cucsVnicProfileSetFsmStageEntry 6 }

cucsVnicProfileSetFsmStageOrder OBJECT-TYPE
    SYNTAX       Gauge32
    MAX-ACCESS   read-only
    STATUS       current
    DESCRIPTION
        "Cisco UCS vnic:ProfileSetFsmStage:order managed object property"
    ::= { cucsVnicProfileSetFsmStageEntry 7 }

cucsVnicProfileSetFsmStageRetry OBJECT-TYPE
    SYNTAX       Gauge32
    MAX-ACCESS   read-only
    STATUS       current
    DESCRIPTION
        "Cisco UCS vnic:ProfileSetFsmStage:retry managed object property"
    ::= { cucsVnicProfileSetFsmStageEntry 8 }

cucsVnicProfileSetFsmStageStageStatus OBJECT-TYPE
    SYNTAX       CucsFsmFsmStageStatus
    MAX-ACCESS   read-only
    STATUS       current
    DESCRIPTION
        "Cisco UCS vnic:ProfileSetFsmStage:stageStatus
        managed object property"
    ::= { cucsVnicProfileSetFsmStageEntry 9 }

cucsVnicProfileSetFsmTaskTable OBJECT-TYPE
    SYNTAX           SEQUENCE OF CucsVnicProfileSetFsmTaskEntry
    MAX-ACCESS       not-accessible
    STATUS           current
    DESCRIPTION
        "Cisco UCS vnic:ProfileSetFsmTask managed object table"
    ::= { cucsVnicObjects 31 }

cucsVnicProfileSetFsmTaskEntry OBJECT-TYPE
    SYNTAX           CucsVnicProfileSetFsmTaskEntry
    MAX-ACCESS       not-accessible
    STATUS           current
    DESCRIPTION
        "Entry for the cucsVnicProfileSetFsmTaskTable table."
    INDEX { cucsVnicProfileSetFsmTaskInstanceId }
    ::= { cucsVnicProfileSetFsmTaskTable 1 }

CucsVnicProfileSetFsmTaskEntry ::= SEQUENCE {
    cucsVnicProfileSetFsmTaskInstanceId                              CucsManagedObjectId,
    cucsVnicProfileSetFsmTaskDn                                      CucsManagedObjectDn,
    cucsVnicProfileSetFsmTaskRn                                      SnmpAdminString,
    cucsVnicProfileSetFsmTaskCompletion                              CucsFsmCompletion,
    cucsVnicProfileSetFsmTaskFlags                                   CucsFsmFlags,
    cucsVnicProfileSetFsmTaskItem                                    CucsVnicProfileSetFsmTaskItem,
    cucsVnicProfileSetFsmTaskSeqId                                   Gauge32
}

cucsVnicProfileSetFsmTaskInstanceId OBJECT-TYPE
    SYNTAX       CucsManagedObjectId
    MAX-ACCESS   not-accessible
    STATUS       current
    DESCRIPTION
        "Instance identifier of the managed object."
    ::= { cucsVnicProfileSetFsmTaskEntry 1 }

cucsVnicProfileSetFsmTaskDn OBJECT-TYPE
    SYNTAX       CucsManagedObjectDn
    MAX-ACCESS   read-only
    STATUS       current
    DESCRIPTION
        "Cisco UCS vnic:ProfileSetFsmTask:dn managed object property"
    ::= { cucsVnicProfileSetFsmTaskEntry 2 }

cucsVnicProfileSetFsmTaskRn OBJECT-TYPE
    SYNTAX       SnmpAdminString
    MAX-ACCESS   read-only
    STATUS       current
    DESCRIPTION
        "Cisco UCS vnic:ProfileSetFsmTask:rn managed object property"
    ::= { cucsVnicProfileSetFsmTaskEntry 3 }

cucsVnicProfileSetFsmTaskCompletion OBJECT-TYPE
    SYNTAX       CucsFsmCompletion
    MAX-ACCESS   read-only
    STATUS       current
    DESCRIPTION
        "Cisco UCS vnic:ProfileSetFsmTask:completion managed
        object property"
    ::= { cucsVnicProfileSetFsmTaskEntry 4 }

cucsVnicProfileSetFsmTaskFlags OBJECT-TYPE
    SYNTAX       CucsFsmFlags
    MAX-ACCESS   read-only
    STATUS       current
    DESCRIPTION
        "Cisco UCS vnic:ProfileSetFsmTask:flags managed object property"
    ::= { cucsVnicProfileSetFsmTaskEntry 5 }

cucsVnicProfileSetFsmTaskItem OBJECT-TYPE
    SYNTAX       CucsVnicProfileSetFsmTaskItem
    MAX-ACCESS   read-only
    STATUS       current
    DESCRIPTION
        "Cisco UCS vnic:ProfileSetFsmTask:item managed object property"
    ::= { cucsVnicProfileSetFsmTaskEntry 6 }

cucsVnicProfileSetFsmTaskSeqId OBJECT-TYPE
    SYNTAX       Gauge32
    MAX-ACCESS   read-only
    STATUS       current
    DESCRIPTION
        "Cisco UCS vnic:ProfileSetFsmTask:seqId managed object property"
    ::= { cucsVnicProfileSetFsmTaskEntry 7 }

cucsVnicRackServerDiscoveryProfileTable OBJECT-TYPE
    SYNTAX           SEQUENCE OF CucsVnicRackServerDiscoveryProfileEntry
    MAX-ACCESS       not-accessible
    STATUS           current
    DESCRIPTION
        "Cisco UCS vnic:RackServerDiscoveryProfile managed object table"
    ::= { cucsVnicObjects 56 }

cucsVnicRackServerDiscoveryProfileEntry OBJECT-TYPE
    SYNTAX           CucsVnicRackServerDiscoveryProfileEntry
    MAX-ACCESS       not-accessible
    STATUS           current
    DESCRIPTION
        "Entry for the cucsVnicRackServerDiscoveryProfileTable table."
    INDEX { cucsVnicRackServerDiscoveryProfileInstanceId }
    ::= { cucsVnicRackServerDiscoveryProfileTable 1 }

CucsVnicRackServerDiscoveryProfileEntry ::= SEQUENCE {
    cucsVnicRackServerDiscoveryProfileInstanceId                     CucsManagedObjectId,
    cucsVnicRackServerDiscoveryProfileDn                             CucsManagedObjectDn,
    cucsVnicRackServerDiscoveryProfileRn                             SnmpAdminString,
    cucsVnicRackServerDiscoveryProfileDescr                          SnmpAdminString,
    cucsVnicRackServerDiscoveryProfileIntId                          SnmpAdminString,
    cucsVnicRackServerDiscoveryProfileMaxPorts                       Gauge32,
    cucsVnicRackServerDiscoveryProfileName                           SnmpAdminString,
    cucsVnicRackServerDiscoveryProfilePolicyLevel                    Gauge32,
    cucsVnicRackServerDiscoveryProfilePolicyOwner                    CucsPolicyPolicyOwner
}

cucsVnicRackServerDiscoveryProfileInstanceId OBJECT-TYPE
    SYNTAX       CucsManagedObjectId
    MAX-ACCESS   not-accessible
    STATUS       current
    DESCRIPTION
        "Instance identifier of the managed object."
    ::= { cucsVnicRackServerDiscoveryProfileEntry 1 }

cucsVnicRackServerDiscoveryProfileDn OBJECT-TYPE
    SYNTAX       CucsManagedObjectDn
    MAX-ACCESS   read-only
    STATUS       current
    DESCRIPTION
        "Cisco UCS vnic:RackServerDiscoveryProfile:dn managed
        object property"
    ::= { cucsVnicRackServerDiscoveryProfileEntry 2 }

cucsVnicRackServerDiscoveryProfileRn OBJECT-TYPE
    SYNTAX       SnmpAdminString
    MAX-ACCESS   read-only
    STATUS       current
    DESCRIPTION
        "Cisco UCS vnic:RackServerDiscoveryProfile:rn managed
        object property"
    ::= { cucsVnicRackServerDiscoveryProfileEntry 3 }

cucsVnicRackServerDiscoveryProfileDescr OBJECT-TYPE
    SYNTAX       SnmpAdminString
    MAX-ACCESS   read-only
    STATUS       current
    DESCRIPTION
        "Cisco UCS vnic:RackServerDiscoveryProfile:descr
        managed object property"
    ::= { cucsVnicRackServerDiscoveryProfileEntry 4 }

cucsVnicRackServerDiscoveryProfileIntId OBJECT-TYPE
    SYNTAX       SnmpAdminString
    MAX-ACCESS   read-only
    STATUS       current
    DESCRIPTION
        "Cisco UCS vnic:RackServerDiscoveryProfile:intId
        managed object property"
    ::= { cucsVnicRackServerDiscoveryProfileEntry 5 }

cucsVnicRackServerDiscoveryProfileMaxPorts OBJECT-TYPE
    SYNTAX       Gauge32
    MAX-ACCESS   read-only
    STATUS       current
    DESCRIPTION
        "Cisco UCS vnic:RackServerDiscoveryProfile:maxPorts
        managed object property"
    ::= { cucsVnicRackServerDiscoveryProfileEntry 6 }

cucsVnicRackServerDiscoveryProfileName OBJECT-TYPE
    SYNTAX       SnmpAdminString
    MAX-ACCESS   read-only
    STATUS       current
    DESCRIPTION
        "Cisco UCS vnic:RackServerDiscoveryProfile:name
        managed object property"
    ::= { cucsVnicRackServerDiscoveryProfileEntry 7 }

cucsVnicRackServerDiscoveryProfilePolicyLevel OBJECT-TYPE
    SYNTAX       Gauge32
    MAX-ACCESS   read-only
    STATUS       current
    DESCRIPTION
        "Cisco UCS vnic:RackServerDiscoveryProfile:policyLevel
        managed object property"
    ::= { cucsVnicRackServerDiscoveryProfileEntry 8 }

cucsVnicRackServerDiscoveryProfilePolicyOwner OBJECT-TYPE
    SYNTAX       CucsPolicyPolicyOwner
    MAX-ACCESS   read-only
    STATUS       current
    DESCRIPTION
        "Cisco UCS vnic:RackServerDiscoveryProfile:policyOwner
        managed object property"
    ::= { cucsVnicRackServerDiscoveryProfileEntry 9 }

cucsVnicSanConnPolicyTable OBJECT-TYPE
    SYNTAX           SEQUENCE OF CucsVnicSanConnPolicyEntry
    MAX-ACCESS       not-accessible
    STATUS           current
    DESCRIPTION
        "Cisco UCS vnic:SanConnPolicy managed object table"
    ::= { cucsVnicObjects 57 }

cucsVnicSanConnPolicyEntry OBJECT-TYPE
    SYNTAX           CucsVnicSanConnPolicyEntry
    MAX-ACCESS       not-accessible
    STATUS           current
    DESCRIPTION
        "Entry for the cucsVnicSanConnPolicyTable table."
    INDEX { cucsVnicSanConnPolicyInstanceId }
    ::= { cucsVnicSanConnPolicyTable 1 }

CucsVnicSanConnPolicyEntry ::= SEQUENCE {
    cucsVnicSanConnPolicyInstanceId                                  CucsManagedObjectId,
    cucsVnicSanConnPolicyDn                                          CucsManagedObjectDn,
    cucsVnicSanConnPolicyRn                                          SnmpAdminString,
    cucsVnicSanConnPolicyDescr                                       SnmpAdminString,
    cucsVnicSanConnPolicyFltAggr                                     Unsigned64,
    cucsVnicSanConnPolicyIntId                                       SnmpAdminString,
    cucsVnicSanConnPolicyName                                        SnmpAdminString,
    cucsVnicSanConnPolicyPolicyLevel                                 Gauge32,
    cucsVnicSanConnPolicyPolicyOwner                                 CucsPolicyPolicyOwner
}

cucsVnicSanConnPolicyInstanceId OBJECT-TYPE
    SYNTAX       CucsManagedObjectId
    MAX-ACCESS   not-accessible
    STATUS       current
    DESCRIPTION
        "Instance identifier of the managed object."
    ::= { cucsVnicSanConnPolicyEntry 1 }

cucsVnicSanConnPolicyDn OBJECT-TYPE
    SYNTAX       CucsManagedObjectDn
    MAX-ACCESS   read-only
    STATUS       current
    DESCRIPTION
        "Cisco UCS vnic:SanConnPolicy:dn managed object property"
    ::= { cucsVnicSanConnPolicyEntry 2 }

cucsVnicSanConnPolicyRn OBJECT-TYPE
    SYNTAX       SnmpAdminString
    MAX-ACCESS   read-only
    STATUS       current
    DESCRIPTION
        "Cisco UCS vnic:SanConnPolicy:rn managed object property"
    ::= { cucsVnicSanConnPolicyEntry 3 }

cucsVnicSanConnPolicyDescr OBJECT-TYPE
    SYNTAX       SnmpAdminString
    MAX-ACCESS   read-only
    STATUS       current
    DESCRIPTION
        "Cisco UCS vnic:SanConnPolicy:descr managed object property"
    ::= { cucsVnicSanConnPolicyEntry 4 }

cucsVnicSanConnPolicyFltAggr OBJECT-TYPE
    SYNTAX       Unsigned64
    MAX-ACCESS   read-only
    STATUS       current
    DESCRIPTION
        "Cisco UCS vnic:SanConnPolicy:fltAggr managed object property"
    ::= { cucsVnicSanConnPolicyEntry 5 }

cucsVnicSanConnPolicyIntId OBJECT-TYPE
    SYNTAX       SnmpAdminString
    MAX-ACCESS   read-only
    STATUS       current
    DESCRIPTION
        "Cisco UCS vnic:SanConnPolicy:intId managed object property"
    ::= { cucsVnicSanConnPolicyEntry 6 }

cucsVnicSanConnPolicyName OBJECT-TYPE
    SYNTAX       SnmpAdminString
    MAX-ACCESS   read-only
    STATUS       current
    DESCRIPTION
        "Cisco UCS vnic:SanConnPolicy:name managed object property"
    ::= { cucsVnicSanConnPolicyEntry 7 }

cucsVnicSanConnPolicyPolicyLevel OBJECT-TYPE
    SYNTAX       Gauge32
    MAX-ACCESS   read-only
    STATUS       current
    DESCRIPTION
        "Cisco UCS vnic:SanConnPolicy:policyLevel managed object property"
    ::= { cucsVnicSanConnPolicyEntry 8 }

cucsVnicSanConnPolicyPolicyOwner OBJECT-TYPE
    SYNTAX       CucsPolicyPolicyOwner
    MAX-ACCESS   read-only
    STATUS       current
    DESCRIPTION
        "Cisco UCS vnic:SanConnPolicy:policyOwner managed object property"
    ::= { cucsVnicSanConnPolicyEntry 9 }

cucsVnicSanConnTemplTable OBJECT-TYPE
    SYNTAX           SEQUENCE OF CucsVnicSanConnTemplEntry
    MAX-ACCESS       not-accessible
    STATUS           current
    DESCRIPTION
        "Cisco UCS vnic:SanConnTempl managed object table"
    ::= { cucsVnicObjects 32 }

cucsVnicSanConnTemplEntry OBJECT-TYPE
    SYNTAX           CucsVnicSanConnTemplEntry
    MAX-ACCESS       not-accessible
    STATUS           current
    DESCRIPTION
        "Entry for the cucsVnicSanConnTemplTable table."
    INDEX { cucsVnicSanConnTemplInstanceId }
    ::= { cucsVnicSanConnTemplTable 1 }

CucsVnicSanConnTemplEntry ::= SEQUENCE {
    cucsVnicSanConnTemplInstanceId                                   CucsManagedObjectId,
    cucsVnicSanConnTemplDn                                           CucsManagedObjectDn,
    cucsVnicSanConnTemplRn                                           SnmpAdminString,
    cucsVnicSanConnTemplDescr                                        SnmpAdminString,
    cucsVnicSanConnTemplIdentPoolName                                SnmpAdminString,
    cucsVnicSanConnTemplIntId                                        SnmpAdminString,
    cucsVnicSanConnTemplMaxDataFieldSize                             Gauge32,
    cucsVnicSanConnTemplName                                         SnmpAdminString,
    cucsVnicSanConnTemplNwCtrlPolicyName                             SnmpAdminString,
    cucsVnicSanConnTemplOperIdentPoolName                            SnmpAdminString,
    cucsVnicSanConnTemplOperQosPolicyName                            SnmpAdminString,
    cucsVnicSanConnTemplOperStatsPolicyName                          SnmpAdminString,
    cucsVnicSanConnTemplPinToGroupName                               SnmpAdminString,
    cucsVnicSanConnTemplQosPolicyName                                SnmpAdminString,
    cucsVnicSanConnTemplStatsPolicyName                              SnmpAdminString,
    cucsVnicSanConnTemplSwitchId                                     CucsNetworkSwitchId,
    cucsVnicSanConnTemplTarget                                       CucsVnicSanConnTemplTarget,
    cucsVnicSanConnTemplTemplType                                    CucsVnicTemplateType,
    cucsVnicSanConnTemplPolicyLevel                                  Gauge32,
    cucsVnicSanConnTemplPolicyOwner                                  CucsPolicyPolicyOwner
}

cucsVnicSanConnTemplInstanceId OBJECT-TYPE
    SYNTAX       CucsManagedObjectId
    MAX-ACCESS   not-accessible
    STATUS       current
    DESCRIPTION
        "Instance identifier of the managed object."
    ::= { cucsVnicSanConnTemplEntry 1 }

cucsVnicSanConnTemplDn OBJECT-TYPE
    SYNTAX       CucsManagedObjectDn
    MAX-ACCESS   read-only
    STATUS       current
    DESCRIPTION
        "Cisco UCS vnic:SanConnTempl:dn managed object property"
    ::= { cucsVnicSanConnTemplEntry 2 }

cucsVnicSanConnTemplRn OBJECT-TYPE
    SYNTAX       SnmpAdminString
    MAX-ACCESS   read-only
    STATUS       current
    DESCRIPTION
        "Cisco UCS vnic:SanConnTempl:rn managed object property"
    ::= { cucsVnicSanConnTemplEntry 3 }

cucsVnicSanConnTemplDescr OBJECT-TYPE
    SYNTAX       SnmpAdminString
    MAX-ACCESS   read-only
    STATUS       current
    DESCRIPTION
        "Cisco UCS vnic:SanConnTempl:descr managed object property"
    ::= { cucsVnicSanConnTemplEntry 4 }

cucsVnicSanConnTemplIdentPoolName OBJECT-TYPE
    SYNTAX       SnmpAdminString
    MAX-ACCESS   read-only
    STATUS       current
    DESCRIPTION
        "Cisco UCS vnic:SanConnTempl:identPoolName managed
        object property"
    ::= { cucsVnicSanConnTemplEntry 5 }

cucsVnicSanConnTemplIntId OBJECT-TYPE
    SYNTAX       SnmpAdminString
    MAX-ACCESS   read-only
    STATUS       current
    DESCRIPTION
        "Cisco UCS vnic:SanConnTempl:intId managed object property"
    ::= { cucsVnicSanConnTemplEntry 6 }

cucsVnicSanConnTemplMaxDataFieldSize OBJECT-TYPE
    SYNTAX       Gauge32
    MAX-ACCESS   read-only
    STATUS       current
    DESCRIPTION
        "Cisco UCS vnic:SanConnTempl:maxDataFieldSize managed
        object property"
    ::= { cucsVnicSanConnTemplEntry 7 }

cucsVnicSanConnTemplName OBJECT-TYPE
    SYNTAX       SnmpAdminString
    MAX-ACCESS   read-only
    STATUS       current
    DESCRIPTION
        "Cisco UCS vnic:SanConnTempl:name managed object property"
    ::= { cucsVnicSanConnTemplEntry 8 }

cucsVnicSanConnTemplNwCtrlPolicyName OBJECT-TYPE
    SYNTAX       SnmpAdminString
    MAX-ACCESS   read-only
    STATUS       current
    DESCRIPTION
        "Cisco UCS vnic:SanConnTempl:nwCtrlPolicyName managed
        object property"
    ::= { cucsVnicSanConnTemplEntry 9 }

cucsVnicSanConnTemplOperIdentPoolName OBJECT-TYPE
    SYNTAX       SnmpAdminString
    MAX-ACCESS   read-only
    STATUS       current
    DESCRIPTION
        "Cisco UCS vnic:SanConnTempl:operIdentPoolName
        managed object property"
    ::= { cucsVnicSanConnTemplEntry 10 }

cucsVnicSanConnTemplOperQosPolicyName OBJECT-TYPE
    SYNTAX       SnmpAdminString
    MAX-ACCESS   read-only
    STATUS       current
    DESCRIPTION
        "Cisco UCS vnic:SanConnTempl:operQosPolicyName
        managed object property"
    ::= { cucsVnicSanConnTemplEntry 11 }

cucsVnicSanConnTemplOperStatsPolicyName OBJECT-TYPE
    SYNTAX       SnmpAdminString
    MAX-ACCESS   read-only
    STATUS       current
    DESCRIPTION
        "Cisco UCS vnic:SanConnTempl:operStatsPolicyName
        managed object property"
    ::= { cucsVnicSanConnTemplEntry 12 }

cucsVnicSanConnTemplPinToGroupName OBJECT-TYPE
    SYNTAX       SnmpAdminString
    MAX-ACCESS   read-only
    STATUS       current
    DESCRIPTION
        "Cisco UCS vnic:SanConnTempl:pinToGroupName managed
        object property"
    ::= { cucsVnicSanConnTemplEntry 13 }

cucsVnicSanConnTemplQosPolicyName OBJECT-TYPE
    SYNTAX       SnmpAdminString
    MAX-ACCESS   read-only
    STATUS       current
    DESCRIPTION
        "Cisco UCS vnic:SanConnTempl:qosPolicyName managed
        object property"
    ::= { cucsVnicSanConnTemplEntry 14 }

cucsVnicSanConnTemplStatsPolicyName OBJECT-TYPE
    SYNTAX       SnmpAdminString
    MAX-ACCESS   read-only
    STATUS       current
    DESCRIPTION
        "Cisco UCS vnic:SanConnTempl:statsPolicyName managed
        object property"
    ::= { cucsVnicSanConnTemplEntry 15 }

cucsVnicSanConnTemplSwitchId OBJECT-TYPE
    SYNTAX       CucsNetworkSwitchId
    MAX-ACCESS   read-only
    STATUS       current
    DESCRIPTION
        "Cisco UCS vnic:SanConnTempl:switchId managed object property"
    ::= { cucsVnicSanConnTemplEntry 16 }

cucsVnicSanConnTemplTarget OBJECT-TYPE
    SYNTAX       CucsVnicSanConnTemplTarget
    MAX-ACCESS   read-only
    STATUS       current
    DESCRIPTION
        "Cisco UCS vnic:SanConnTempl:target managed object property"
    ::= { cucsVnicSanConnTemplEntry 17 }

cucsVnicSanConnTemplTemplType OBJECT-TYPE
    SYNTAX       CucsVnicTemplateType
    MAX-ACCESS   read-only
    STATUS       current
    DESCRIPTION
        "Cisco UCS vnic:SanConnTempl:templType managed object property"
    ::= { cucsVnicSanConnTemplEntry 18 }

cucsVnicSanConnTemplPolicyLevel OBJECT-TYPE
    SYNTAX       Gauge32
    MAX-ACCESS   read-only
    STATUS       current
    DESCRIPTION
        "Cisco UCS vnic:SanConnTempl:policyLevel managed object property"
    ::= { cucsVnicSanConnTemplEntry 19 }

cucsVnicSanConnTemplPolicyOwner OBJECT-TYPE
    SYNTAX       CucsPolicyPolicyOwner
    MAX-ACCESS   read-only
    STATUS       current
    DESCRIPTION
        "Cisco UCS vnic:SanConnTempl:policyOwner managed object property"
    ::= { cucsVnicSanConnTemplEntry 20 }

cucsVnicScsiTable OBJECT-TYPE
    SYNTAX           SEQUENCE OF CucsVnicScsiEntry
    MAX-ACCESS       not-accessible
    STATUS           current
    DESCRIPTION
        "Cisco UCS vnic:Scsi managed object table"
    ::= { cucsVnicObjects 33 }

cucsVnicScsiEntry OBJECT-TYPE
    SYNTAX           CucsVnicScsiEntry
    MAX-ACCESS       not-accessible
    STATUS           current
    DESCRIPTION
        "Entry for the cucsVnicScsiTable table."
    INDEX { cucsVnicScsiInstanceId }
    ::= { cucsVnicScsiTable 1 }

CucsVnicScsiEntry ::= SEQUENCE {
    cucsVnicScsiInstanceId                                           CucsManagedObjectId,
    cucsVnicScsiDn                                                   CucsManagedObjectDn,
    cucsVnicScsiRn                                                   SnmpAdminString,
    cucsVnicScsiAdaptorProfileName                                   SnmpAdminString,
    cucsVnicScsiAdminVcon                                            SnmpAdminString,
    cucsVnicScsiBootDev                                              CucsVnicVnicBootDev,
    cucsVnicScsiConfigState                                          CucsLsConfigState,
    cucsVnicScsiEquipmentDn                                          SnmpAdminString,
    cucsVnicScsiIdentPoolName                                        SnmpAdminString,
    cucsVnicScsiInstType                                             CucsVnicInstantiation,
    cucsVnicScsiName                                                 SnmpAdminString,
    cucsVnicScsiNwTemplName                                          SnmpAdminString,
    cucsVnicScsiOperOrder                                            Gauge32,
    cucsVnicScsiOperSpeed                                            Gauge32,
    cucsVnicScsiOperStatsPolicyName                                  SnmpAdminString,
    cucsVnicScsiOperVcon                                             SnmpAdminString,
    cucsVnicScsiOrder                                                Gauge32,
    cucsVnicScsiOwner                                                CucsVnicConnectionOwner,
    cucsVnicScsiPinToGroupName                                       SnmpAdminString,
    cucsVnicScsiQosPolicyName                                        SnmpAdminString,
    cucsVnicScsiStatsPolicyName                                      SnmpAdminString,
    cucsVnicScsiSwitchId                                             CucsNetworkSwitchId,
    cucsVnicScsiType                                                 CucsVnicScsiType,
    cucsVnicScsiConfigQualifier                                      CucsVnicConfigIssues,
    cucsVnicScsiAdminHostPort                                        CucsFabricHostPortId,
    cucsVnicScsiOperHostPort                                         CucsVnicVnicOperHostPort,
    cucsVnicScsiAdminCdnName                                         SnmpAdminString,
    cucsVnicScsiOperCdnName                                          SnmpAdminString,
    cucsVnicScsiCdnPropInSync                                        TruthValue,
    cucsVnicScsiCdnSource                                            CucsVnicCdnSource
}

cucsVnicScsiInstanceId OBJECT-TYPE
    SYNTAX       CucsManagedObjectId
    MAX-ACCESS   not-accessible
    STATUS       current
    DESCRIPTION
        "Instance identifier of the managed object."
    ::= { cucsVnicScsiEntry 1 }

cucsVnicScsiDn OBJECT-TYPE
    SYNTAX       CucsManagedObjectDn
    MAX-ACCESS   read-only
    STATUS       current
    DESCRIPTION
        "Cisco UCS vnic:Scsi:dn managed object property"
    ::= { cucsVnicScsiEntry 2 }

cucsVnicScsiRn OBJECT-TYPE
    SYNTAX       SnmpAdminString
    MAX-ACCESS   read-only
    STATUS       current
    DESCRIPTION
        "Cisco UCS vnic:Scsi:rn managed object property"
    ::= { cucsVnicScsiEntry 3 }

cucsVnicScsiAdaptorProfileName OBJECT-TYPE
    SYNTAX       SnmpAdminString
    MAX-ACCESS   read-only
    STATUS       current
    DESCRIPTION
        "Cisco UCS vnic:Scsi:adaptorProfileName managed object property"
    ::= { cucsVnicScsiEntry 4 }

cucsVnicScsiAdminVcon OBJECT-TYPE
    SYNTAX       SnmpAdminString
    MAX-ACCESS   read-only
    STATUS       current
    DESCRIPTION
        "Cisco UCS vnic:Scsi:adminVcon managed object property"
    ::= { cucsVnicScsiEntry 5 }

cucsVnicScsiBootDev OBJECT-TYPE
    SYNTAX       CucsVnicVnicBootDev
    MAX-ACCESS   read-only
    STATUS       current
    DESCRIPTION
        "Cisco UCS vnic:Scsi:bootDev managed object property"
    ::= { cucsVnicScsiEntry 6 }

cucsVnicScsiConfigState OBJECT-TYPE
    SYNTAX       CucsLsConfigState
    MAX-ACCESS   read-only
    STATUS       current
    DESCRIPTION
        "Cisco UCS vnic:Scsi:configState managed object property"
    ::= { cucsVnicScsiEntry 7 }

cucsVnicScsiEquipmentDn OBJECT-TYPE
    SYNTAX       SnmpAdminString
    MAX-ACCESS   read-only
    STATUS       current
    DESCRIPTION
        "Cisco UCS vnic:Scsi:equipmentDn managed object property"
    ::= { cucsVnicScsiEntry 8 }

cucsVnicScsiIdentPoolName OBJECT-TYPE
    SYNTAX       SnmpAdminString
    MAX-ACCESS   read-only
    STATUS       current
    DESCRIPTION
        "Cisco UCS vnic:Scsi:identPoolName managed object property"
    ::= { cucsVnicScsiEntry 9 }

cucsVnicScsiInstType OBJECT-TYPE
    SYNTAX       CucsVnicInstantiation
    MAX-ACCESS   read-only
    STATUS       current
    DESCRIPTION
        "Cisco UCS vnic:Scsi:instType managed object property"
    ::= { cucsVnicScsiEntry 10 }

cucsVnicScsiName OBJECT-TYPE
    SYNTAX       SnmpAdminString
    MAX-ACCESS   read-only
    STATUS       current
    DESCRIPTION
        "Cisco UCS vnic:Scsi:name managed object property"
    ::= { cucsVnicScsiEntry 11 }

cucsVnicScsiNwTemplName OBJECT-TYPE
    SYNTAX       SnmpAdminString
    MAX-ACCESS   read-only
    STATUS       current
    DESCRIPTION
        "Cisco UCS vnic:Scsi:nwTemplName managed object property"
    ::= { cucsVnicScsiEntry 12 }

cucsVnicScsiOperOrder OBJECT-TYPE
    SYNTAX       Gauge32
    MAX-ACCESS   read-only
    STATUS       current
    DESCRIPTION
        "Cisco UCS vnic:Scsi:operOrder managed object property"
    ::= { cucsVnicScsiEntry 13 }

cucsVnicScsiOperSpeed OBJECT-TYPE
    SYNTAX       Gauge32
    MAX-ACCESS   read-only
    STATUS       current
    DESCRIPTION
        "Cisco UCS vnic:Scsi:operSpeed managed object property"
    ::= { cucsVnicScsiEntry 14 }

cucsVnicScsiOperStatsPolicyName OBJECT-TYPE
    SYNTAX       SnmpAdminString
    MAX-ACCESS   read-only
    STATUS       current
    DESCRIPTION
        "Cisco UCS vnic:Scsi:operStatsPolicyName managed object property"
    ::= { cucsVnicScsiEntry 15 }

cucsVnicScsiOperVcon OBJECT-TYPE
    SYNTAX       SnmpAdminString
    MAX-ACCESS   read-only
    STATUS       current
    DESCRIPTION
        "Cisco UCS vnic:Scsi:operVcon managed object property"
    ::= { cucsVnicScsiEntry 16 }

cucsVnicScsiOrder OBJECT-TYPE
    SYNTAX       Gauge32
    MAX-ACCESS   read-only
    STATUS       current
    DESCRIPTION
        "Cisco UCS vnic:Scsi:order managed object property"
    ::= { cucsVnicScsiEntry 17 }

cucsVnicScsiOwner OBJECT-TYPE
    SYNTAX       CucsVnicConnectionOwner
    MAX-ACCESS   read-only
    STATUS       current
    DESCRIPTION
        "Cisco UCS vnic:Scsi:owner managed object property"
    ::= { cucsVnicScsiEntry 18 }

cucsVnicScsiPinToGroupName OBJECT-TYPE
    SYNTAX       SnmpAdminString
    MAX-ACCESS   read-only
    STATUS       current
    DESCRIPTION
        "Cisco UCS vnic:Scsi:pinToGroupName managed object property"
    ::= { cucsVnicScsiEntry 19 }

cucsVnicScsiQosPolicyName OBJECT-TYPE
    SYNTAX       SnmpAdminString
    MAX-ACCESS   read-only
    STATUS       current
    DESCRIPTION
        "Cisco UCS vnic:Scsi:qosPolicyName managed object property"
    ::= { cucsVnicScsiEntry 20 }

cucsVnicScsiStatsPolicyName OBJECT-TYPE
    SYNTAX       SnmpAdminString
    MAX-ACCESS   read-only
    STATUS       current
    DESCRIPTION
        "Cisco UCS vnic:Scsi:statsPolicyName managed object property"
    ::= { cucsVnicScsiEntry 21 }

cucsVnicScsiSwitchId OBJECT-TYPE
    SYNTAX       CucsNetworkSwitchId
    MAX-ACCESS   read-only
    STATUS       current
    DESCRIPTION
        "Cisco UCS vnic:Scsi:switchId managed object property"
    ::= { cucsVnicScsiEntry 22 }

cucsVnicScsiType OBJECT-TYPE
    SYNTAX       CucsVnicScsiType
    MAX-ACCESS   read-only
    STATUS       current
    DESCRIPTION
        "Cisco UCS vnic:Scsi:type managed object property"
    ::= { cucsVnicScsiEntry 23 }

cucsVnicScsiConfigQualifier OBJECT-TYPE
    SYNTAX       CucsVnicConfigIssues
    MAX-ACCESS   read-only
    STATUS       current
    DESCRIPTION
        "Cisco UCS vnic:Scsi:configQualifier managed object property"
    ::= { cucsVnicScsiEntry 25 }

cucsVnicScsiAdminHostPort OBJECT-TYPE
    SYNTAX       CucsFabricHostPortId
    MAX-ACCESS   read-only
    STATUS       current
    DESCRIPTION
        "Cisco UCS vnic:Scsi:adminHostPort managed object property"
    ::= { cucsVnicScsiEntry 27 }

cucsVnicScsiOperHostPort OBJECT-TYPE
    SYNTAX       CucsVnicVnicOperHostPort
    MAX-ACCESS   read-only
    STATUS       current
    DESCRIPTION
        "Cisco UCS vnic:Scsi:operHostPort managed object property"
    ::= { cucsVnicScsiEntry 28 }

cucsVnicScsiAdminCdnName OBJECT-TYPE
    SYNTAX       SnmpAdminString
    MAX-ACCESS   read-only
    STATUS       current
    DESCRIPTION
        "Cisco UCS vnic:Scsi:adminCdnName managed object property"
    ::= { cucsVnicScsiEntry 29 }

cucsVnicScsiOperCdnName OBJECT-TYPE
    SYNTAX       SnmpAdminString
    MAX-ACCESS   read-only
    STATUS       current
    DESCRIPTION
        "Cisco UCS vnic:Scsi:operCdnName managed object property"
    ::= { cucsVnicScsiEntry 30 }

cucsVnicScsiCdnPropInSync OBJECT-TYPE
    SYNTAX       TruthValue
    MAX-ACCESS   read-only
    STATUS       current
    DESCRIPTION
        "Cisco UCS vnic:Scsi:cdnPropInSync managed object property"
    ::= { cucsVnicScsiEntry 31 }

cucsVnicScsiCdnSource OBJECT-TYPE
    SYNTAX       CucsVnicCdnSource
    MAX-ACCESS   read-only
    STATUS       current
    DESCRIPTION
        "Cisco UCS vnic:Scsi:cdnSource managed object property"
    ::= { cucsVnicScsiEntry 32 }

cucsVnicScsiIfTable OBJECT-TYPE
    SYNTAX           SEQUENCE OF CucsVnicScsiIfEntry
    MAX-ACCESS       not-accessible
    STATUS           current
    DESCRIPTION
        "Cisco UCS vnic:ScsiIf managed object table"
    ::= { cucsVnicObjects 34 }

cucsVnicScsiIfEntry OBJECT-TYPE
    SYNTAX           CucsVnicScsiIfEntry
    MAX-ACCESS       not-accessible
    STATUS           current
    DESCRIPTION
        "Entry for the cucsVnicScsiIfTable table."
    INDEX { cucsVnicScsiIfInstanceId }
    ::= { cucsVnicScsiIfTable 1 }

CucsVnicScsiIfEntry ::= SEQUENCE {
    cucsVnicScsiIfInstanceId                                         CucsManagedObjectId,
    cucsVnicScsiIfDn                                                 CucsManagedObjectDn,
    cucsVnicScsiIfRn                                                 SnmpAdminString,
    cucsVnicScsiIfAddr                                               Unsigned64,
    cucsVnicScsiIfName                                               SnmpAdminString,
    cucsVnicScsiIfOperState                                          CucsVnicIfOperState,
    cucsVnicScsiIfOwner                                              CucsVnicConnectionOwner,
    cucsVnicScsiIfSwitchId                                           CucsNetworkSwitchId,
    cucsVnicScsiIfType                                               CucsVnicAScsiIfType,
    cucsVnicScsiIfVnet                                               Gauge32,
    cucsVnicScsiIfConfigQualifier                                    CucsVnicConfigIssues,
    cucsVnicScsiIfOperVnetDn                                         SnmpAdminString,
    cucsVnicScsiIfOperVnetName                                       SnmpAdminString,
    cucsVnicScsiIfPubNwId                                            Gauge32,
    cucsVnicScsiIfSharing                                            CucsFabricVlanSharingType,
    cucsVnicScsiIfOperPrimaryVnetDn                                  SnmpAdminString,
    cucsVnicScsiIfOperPrimaryVnetName                                SnmpAdminString
}

cucsVnicScsiIfInstanceId OBJECT-TYPE
    SYNTAX       CucsManagedObjectId
    MAX-ACCESS   not-accessible
    STATUS       current
    DESCRIPTION
        "Instance identifier of the managed object."
    ::= { cucsVnicScsiIfEntry 1 }

cucsVnicScsiIfDn OBJECT-TYPE
    SYNTAX       CucsManagedObjectDn
    MAX-ACCESS   read-only
    STATUS       current
    DESCRIPTION
        "Cisco UCS vnic:ScsiIf:dn managed object property"
    ::= { cucsVnicScsiIfEntry 2 }

cucsVnicScsiIfRn OBJECT-TYPE
    SYNTAX       SnmpAdminString
    MAX-ACCESS   read-only
    STATUS       current
    DESCRIPTION
        "Cisco UCS vnic:ScsiIf:rn managed object property"
    ::= { cucsVnicScsiIfEntry 3 }

cucsVnicScsiIfAddr OBJECT-TYPE
    SYNTAX       Unsigned64
    MAX-ACCESS   read-only
    STATUS       current
    DESCRIPTION
        "Cisco UCS vnic:ScsiIf:addr managed object property"
    ::= { cucsVnicScsiIfEntry 4 }

cucsVnicScsiIfName OBJECT-TYPE
    SYNTAX       SnmpAdminString
    MAX-ACCESS   read-only
    STATUS       current
    DESCRIPTION
        "Cisco UCS vnic:ScsiIf:name managed object property"
    ::= { cucsVnicScsiIfEntry 5 }

cucsVnicScsiIfOperState OBJECT-TYPE
    SYNTAX       CucsVnicIfOperState
    MAX-ACCESS   read-only
    STATUS       current
    DESCRIPTION
        "Cisco UCS vnic:ScsiIf:operState managed object property"
    ::= { cucsVnicScsiIfEntry 6 }

cucsVnicScsiIfOwner OBJECT-TYPE
    SYNTAX       CucsVnicConnectionOwner
    MAX-ACCESS   read-only
    STATUS       current
    DESCRIPTION
        "Cisco UCS vnic:ScsiIf:owner managed object property"
    ::= { cucsVnicScsiIfEntry 7 }

cucsVnicScsiIfSwitchId OBJECT-TYPE
    SYNTAX       CucsNetworkSwitchId
    MAX-ACCESS   read-only
    STATUS       current
    DESCRIPTION
        "Cisco UCS vnic:ScsiIf:switchId managed object property"
    ::= { cucsVnicScsiIfEntry 8 }

cucsVnicScsiIfType OBJECT-TYPE
    SYNTAX       CucsVnicAScsiIfType
    MAX-ACCESS   read-only
    STATUS       current
    DESCRIPTION
        "Cisco UCS vnic:ScsiIf:type managed object property"
    ::= { cucsVnicScsiIfEntry 9 }

cucsVnicScsiIfVnet OBJECT-TYPE
    SYNTAX       Gauge32
    MAX-ACCESS   read-only
    STATUS       current
    DESCRIPTION
        "Cisco UCS vnic:ScsiIf:vnet managed object property"
    ::= { cucsVnicScsiIfEntry 10 }

cucsVnicScsiIfConfigQualifier OBJECT-TYPE
    SYNTAX       CucsVnicConfigIssues
    MAX-ACCESS   read-only
    STATUS       current
    DESCRIPTION
        "Cisco UCS vnic:ScsiIf:configQualifier managed object property"
    ::= { cucsVnicScsiIfEntry 11 }

cucsVnicScsiIfOperVnetDn OBJECT-TYPE
    SYNTAX       SnmpAdminString
    MAX-ACCESS   read-only
    STATUS       current
    DESCRIPTION
        "Cisco UCS vnic:ScsiIf:operVnetDn managed object property"
    ::= { cucsVnicScsiIfEntry 13 }

cucsVnicScsiIfOperVnetName OBJECT-TYPE
    SYNTAX       SnmpAdminString
    MAX-ACCESS   read-only
    STATUS       current
    DESCRIPTION
        "Cisco UCS vnic:ScsiIf:operVnetName managed object property"
    ::= { cucsVnicScsiIfEntry 14 }

cucsVnicScsiIfPubNwId OBJECT-TYPE
    SYNTAX       Gauge32
    MAX-ACCESS   read-only
    STATUS       current
    DESCRIPTION
        "Cisco UCS vnic:ScsiIf:pubNwId managed object property"
    ::= { cucsVnicScsiIfEntry 15 }

cucsVnicScsiIfSharing OBJECT-TYPE
    SYNTAX       CucsFabricVlanSharingType
    MAX-ACCESS   read-only
    STATUS       current
    DESCRIPTION
        "Cisco UCS vnic:ScsiIf:sharing managed object property"
    ::= { cucsVnicScsiIfEntry 16 }

cucsVnicScsiIfOperPrimaryVnetDn OBJECT-TYPE
    SYNTAX       SnmpAdminString
    MAX-ACCESS   read-only
    STATUS       current
    DESCRIPTION
        "Cisco UCS vnic:ScsiIf:operPrimaryVnetDn managed object property"
    ::= { cucsVnicScsiIfEntry 17 }

cucsVnicScsiIfOperPrimaryVnetName OBJECT-TYPE
    SYNTAX       SnmpAdminString
    MAX-ACCESS   read-only
    STATUS       current
    DESCRIPTION
        "Cisco UCS vnic:ScsiIf:operPrimaryVnetName managed
        object property"
    ::= { cucsVnicScsiIfEntry 18 }

cucsVnicUsnicConPolicyTable OBJECT-TYPE
    SYNTAX           SEQUENCE OF CucsVnicUsnicConPolicyEntry
    MAX-ACCESS       not-accessible
    STATUS           current
    DESCRIPTION
        "Cisco UCS vnic:UsnicConPolicy managed object table"
    ::= { cucsVnicObjects 69 }

cucsVnicUsnicConPolicyEntry OBJECT-TYPE
    SYNTAX           CucsVnicUsnicConPolicyEntry
    MAX-ACCESS       not-accessible
    STATUS           current
    DESCRIPTION
        "Entry for the cucsVnicUsnicConPolicyTable table."
    INDEX { cucsVnicUsnicConPolicyInstanceId }
    ::= { cucsVnicUsnicConPolicyTable 1 }

CucsVnicUsnicConPolicyEntry ::= SEQUENCE {
    cucsVnicUsnicConPolicyInstanceId                                 CucsManagedObjectId,
    cucsVnicUsnicConPolicyDn                                         CucsManagedObjectDn,
    cucsVnicUsnicConPolicyRn                                         SnmpAdminString,
    cucsVnicUsnicConPolicyAdaptorProfileName                         SnmpAdminString,
    cucsVnicUsnicConPolicyDescr                                      SnmpAdminString,
    cucsVnicUsnicConPolicyIntId                                      SnmpAdminString,
    cucsVnicUsnicConPolicyName                                       SnmpAdminString,
    cucsVnicUsnicConPolicyPolicyLevel                                Gauge32,
    cucsVnicUsnicConPolicyPolicyOwner                                CucsPolicyPolicyOwner,
    cucsVnicUsnicConPolicyUsnicCount                                 Gauge32
}

cucsVnicUsnicConPolicyInstanceId OBJECT-TYPE
    SYNTAX       CucsManagedObjectId
    MAX-ACCESS   not-accessible
    STATUS       current
    DESCRIPTION
        "Instance identifier of the managed object."
    ::= { cucsVnicUsnicConPolicyEntry 1 }

cucsVnicUsnicConPolicyDn OBJECT-TYPE
    SYNTAX       CucsManagedObjectDn
    MAX-ACCESS   read-only
    STATUS       current
    DESCRIPTION
        "Cisco UCS vnic:UsnicConPolicy:dn managed object property"
    ::= { cucsVnicUsnicConPolicyEntry 2 }

cucsVnicUsnicConPolicyRn OBJECT-TYPE
    SYNTAX       SnmpAdminString
    MAX-ACCESS   read-only
    STATUS       current
    DESCRIPTION
        "Cisco UCS vnic:UsnicConPolicy:rn managed object property"
    ::= { cucsVnicUsnicConPolicyEntry 3 }

cucsVnicUsnicConPolicyAdaptorProfileName OBJECT-TYPE
    SYNTAX       SnmpAdminString
    MAX-ACCESS   read-only
    STATUS       current
    DESCRIPTION
        "Cisco UCS vnic:UsnicConPolicy:adaptorProfileName
        managed object property"
    ::= { cucsVnicUsnicConPolicyEntry 4 }

cucsVnicUsnicConPolicyDescr OBJECT-TYPE
    SYNTAX       SnmpAdminString
    MAX-ACCESS   read-only
    STATUS       current
    DESCRIPTION
        "Cisco UCS vnic:UsnicConPolicy:descr managed object property"
    ::= { cucsVnicUsnicConPolicyEntry 5 }

cucsVnicUsnicConPolicyIntId OBJECT-TYPE
    SYNTAX       SnmpAdminString
    MAX-ACCESS   read-only
    STATUS       current
    DESCRIPTION
        "Cisco UCS vnic:UsnicConPolicy:intId managed object property"
    ::= { cucsVnicUsnicConPolicyEntry 6 }

cucsVnicUsnicConPolicyName OBJECT-TYPE
    SYNTAX       SnmpAdminString
    MAX-ACCESS   read-only
    STATUS       current
    DESCRIPTION
        "Cisco UCS vnic:UsnicConPolicy:name managed object property"
    ::= { cucsVnicUsnicConPolicyEntry 7 }

cucsVnicUsnicConPolicyPolicyLevel OBJECT-TYPE
    SYNTAX       Gauge32
    MAX-ACCESS   read-only
    STATUS       current
    DESCRIPTION
        "Cisco UCS vnic:UsnicConPolicy:policyLevel managed
        object property"
    ::= { cucsVnicUsnicConPolicyEntry 8 }

cucsVnicUsnicConPolicyPolicyOwner OBJECT-TYPE
    SYNTAX       CucsPolicyPolicyOwner
    MAX-ACCESS   read-only
    STATUS       current
    DESCRIPTION
        "Cisco UCS vnic:UsnicConPolicy:policyOwner managed
        object property"
    ::= { cucsVnicUsnicConPolicyEntry 9 }

cucsVnicUsnicConPolicyUsnicCount OBJECT-TYPE
    SYNTAX       Gauge32
    MAX-ACCESS   read-only
    STATUS       current
    DESCRIPTION
        "Cisco UCS vnic:UsnicConPolicy:usnicCount managed object property"
    ::= { cucsVnicUsnicConPolicyEntry 10 }

cucsVnicUsnicConPolicyRefTable OBJECT-TYPE
    SYNTAX           SEQUENCE OF CucsVnicUsnicConPolicyRefEntry
    MAX-ACCESS       not-accessible
    STATUS           current
    DESCRIPTION
        "Cisco UCS vnic:UsnicConPolicyRef managed object table"
    ::= { cucsVnicObjects 70 }

cucsVnicUsnicConPolicyRefEntry OBJECT-TYPE
    SYNTAX           CucsVnicUsnicConPolicyRefEntry
    MAX-ACCESS       not-accessible
    STATUS           current
    DESCRIPTION
        "Entry for the cucsVnicUsnicConPolicyRefTable table."
    INDEX { cucsVnicUsnicConPolicyRefInstanceId }
    ::= { cucsVnicUsnicConPolicyRefTable 1 }

CucsVnicUsnicConPolicyRefEntry ::= SEQUENCE {
    cucsVnicUsnicConPolicyRefInstanceId                              CucsManagedObjectId,
    cucsVnicUsnicConPolicyRefDn                                      CucsManagedObjectDn,
    cucsVnicUsnicConPolicyRefRn                                      SnmpAdminString,
    cucsVnicUsnicConPolicyRefConPolicyName                           SnmpAdminString,
    cucsVnicUsnicConPolicyRefOperConPolicyName                       SnmpAdminString
}

cucsVnicUsnicConPolicyRefInstanceId OBJECT-TYPE
    SYNTAX       CucsManagedObjectId
    MAX-ACCESS   not-accessible
    STATUS       current
    DESCRIPTION
        "Instance identifier of the managed object."
    ::= { cucsVnicUsnicConPolicyRefEntry 1 }

cucsVnicUsnicConPolicyRefDn OBJECT-TYPE
    SYNTAX       CucsManagedObjectDn
    MAX-ACCESS   read-only
    STATUS       current
    DESCRIPTION
        "Cisco UCS vnic:UsnicConPolicyRef:dn managed object property"
    ::= { cucsVnicUsnicConPolicyRefEntry 2 }

cucsVnicUsnicConPolicyRefRn OBJECT-TYPE
    SYNTAX       SnmpAdminString
    MAX-ACCESS   read-only
    STATUS       current
    DESCRIPTION
        "Cisco UCS vnic:UsnicConPolicyRef:rn managed object property"
    ::= { cucsVnicUsnicConPolicyRefEntry 3 }

cucsVnicUsnicConPolicyRefConPolicyName OBJECT-TYPE
    SYNTAX       SnmpAdminString
    MAX-ACCESS   read-only
    STATUS       current
    DESCRIPTION
        "Cisco UCS vnic:UsnicConPolicyRef:conPolicyName
        managed object property"
    ::= { cucsVnicUsnicConPolicyRefEntry 4 }

cucsVnicUsnicConPolicyRefOperConPolicyName OBJECT-TYPE
    SYNTAX       SnmpAdminString
    MAX-ACCESS   read-only
    STATUS       current
    DESCRIPTION
        "Cisco UCS vnic:UsnicConPolicyRef:operConPolicyName
        managed object property"
    ::= { cucsVnicUsnicConPolicyRefEntry 5 }

cucsVnicVhbaBehPolicyTable OBJECT-TYPE
    SYNTAX           SEQUENCE OF CucsVnicVhbaBehPolicyEntry
    MAX-ACCESS       not-accessible
    STATUS           current
    DESCRIPTION
        "Cisco UCS vnic:VhbaBehPolicy managed object table"
    ::= { cucsVnicObjects 58 }

cucsVnicVhbaBehPolicyEntry OBJECT-TYPE
    SYNTAX           CucsVnicVhbaBehPolicyEntry
    MAX-ACCESS       not-accessible
    STATUS           current
    DESCRIPTION
        "Entry for the cucsVnicVhbaBehPolicyTable table."
    INDEX { cucsVnicVhbaBehPolicyInstanceId }
    ::= { cucsVnicVhbaBehPolicyTable 1 }

CucsVnicVhbaBehPolicyEntry ::= SEQUENCE {
    cucsVnicVhbaBehPolicyInstanceId                                  CucsManagedObjectId,
    cucsVnicVhbaBehPolicyDn                                          CucsManagedObjectDn,
    cucsVnicVhbaBehPolicyRn                                          SnmpAdminString,
    cucsVnicVhbaBehPolicyAction                                      CucsVnicDefaultAction,
    cucsVnicVhbaBehPolicyDescr                                       SnmpAdminString,
    cucsVnicVhbaBehPolicyIntId                                       SnmpAdminString,
    cucsVnicVhbaBehPolicyName                                        SnmpAdminString,
    cucsVnicVhbaBehPolicyNwTemplName                                 SnmpAdminString,
    cucsVnicVhbaBehPolicyPolicyLevel                                 Gauge32,
    cucsVnicVhbaBehPolicyPolicyOwner                                 CucsPolicyPolicyOwner,
    cucsVnicVhbaBehPolicyType                                        CucsVnicVhbaBehPolicyType
}

cucsVnicVhbaBehPolicyInstanceId OBJECT-TYPE
    SYNTAX       CucsManagedObjectId
    MAX-ACCESS   not-accessible
    STATUS       current
    DESCRIPTION
        "Instance identifier of the managed object."
    ::= { cucsVnicVhbaBehPolicyEntry 1 }

cucsVnicVhbaBehPolicyDn OBJECT-TYPE
    SYNTAX       CucsManagedObjectDn
    MAX-ACCESS   read-only
    STATUS       current
    DESCRIPTION
        "Cisco UCS vnic:VhbaBehPolicy:dn managed object property"
    ::= { cucsVnicVhbaBehPolicyEntry 2 }

cucsVnicVhbaBehPolicyRn OBJECT-TYPE
    SYNTAX       SnmpAdminString
    MAX-ACCESS   read-only
    STATUS       current
    DESCRIPTION
        "Cisco UCS vnic:VhbaBehPolicy:rn managed object property"
    ::= { cucsVnicVhbaBehPolicyEntry 3 }

cucsVnicVhbaBehPolicyAction OBJECT-TYPE
    SYNTAX       CucsVnicDefaultAction
    MAX-ACCESS   read-only
    STATUS       current
    DESCRIPTION
        "Cisco UCS vnic:VhbaBehPolicy:action managed object property"
    ::= { cucsVnicVhbaBehPolicyEntry 4 }

cucsVnicVhbaBehPolicyDescr OBJECT-TYPE
    SYNTAX       SnmpAdminString
    MAX-ACCESS   read-only
    STATUS       current
    DESCRIPTION
        "Cisco UCS vnic:VhbaBehPolicy:descr managed object property"
    ::= { cucsVnicVhbaBehPolicyEntry 5 }

cucsVnicVhbaBehPolicyIntId OBJECT-TYPE
    SYNTAX       SnmpAdminString
    MAX-ACCESS   read-only
    STATUS       current
    DESCRIPTION
        "Cisco UCS vnic:VhbaBehPolicy:intId managed object property"
    ::= { cucsVnicVhbaBehPolicyEntry 6 }

cucsVnicVhbaBehPolicyName OBJECT-TYPE
    SYNTAX       SnmpAdminString
    MAX-ACCESS   read-only
    STATUS       current
    DESCRIPTION
        "Cisco UCS vnic:VhbaBehPolicy:name managed object property"
    ::= { cucsVnicVhbaBehPolicyEntry 7 }

cucsVnicVhbaBehPolicyNwTemplName OBJECT-TYPE
    SYNTAX       SnmpAdminString
    MAX-ACCESS   read-only
    STATUS       current
    DESCRIPTION
        "Cisco UCS vnic:VhbaBehPolicy:nwTemplName managed object property"
    ::= { cucsVnicVhbaBehPolicyEntry 8 }

cucsVnicVhbaBehPolicyPolicyLevel OBJECT-TYPE
    SYNTAX       Gauge32
    MAX-ACCESS   read-only
    STATUS       current
    DESCRIPTION
        "Cisco UCS vnic:VhbaBehPolicy:policyLevel managed object property"
    ::= { cucsVnicVhbaBehPolicyEntry 9 }

cucsVnicVhbaBehPolicyPolicyOwner OBJECT-TYPE
    SYNTAX       CucsPolicyPolicyOwner
    MAX-ACCESS   read-only
    STATUS       current
    DESCRIPTION
        "Cisco UCS vnic:VhbaBehPolicy:policyOwner managed object property"
    ::= { cucsVnicVhbaBehPolicyEntry 10 }

cucsVnicVhbaBehPolicyType OBJECT-TYPE
    SYNTAX       CucsVnicVhbaBehPolicyType
    MAX-ACCESS   read-only
    STATUS       current
    DESCRIPTION
        "Cisco UCS vnic:VhbaBehPolicy:type managed object property"
    ::= { cucsVnicVhbaBehPolicyEntry 11 }

cucsVnicVlanTable OBJECT-TYPE
    SYNTAX           SEQUENCE OF CucsVnicVlanEntry
    MAX-ACCESS       not-accessible
    STATUS           current
    DESCRIPTION
        "Cisco UCS vnic:Vlan managed object table"
    ::= { cucsVnicObjects 45 }

cucsVnicVlanEntry OBJECT-TYPE
    SYNTAX           CucsVnicVlanEntry
    MAX-ACCESS       not-accessible
    STATUS           current
    DESCRIPTION
        "Entry for the cucsVnicVlanTable table."
    INDEX { cucsVnicVlanInstanceId }
    ::= { cucsVnicVlanTable 1 }

CucsVnicVlanEntry ::= SEQUENCE {
    cucsVnicVlanInstanceId                                           CucsManagedObjectId,
    cucsVnicVlanDn                                                   CucsManagedObjectDn,
    cucsVnicVlanRn                                                   SnmpAdminString,
    cucsVnicVlanFltAggr                                              Unsigned64,
    cucsVnicVlanName                                                 SnmpAdminString,
    cucsVnicVlanOperState                                            CucsVnicIfOperState,
    cucsVnicVlanOwner                                                CucsVnicConnectionOwner,
    cucsVnicVlanSwitchId                                             CucsNetworkSwitchId,
    cucsVnicVlanType                                                 CucsVnicConnectionType,
    cucsVnicVlanVlanName                                             SnmpAdminString,
    cucsVnicVlanVnet                                                 Gauge32,
    cucsVnicVlanConfigQualifier                                      CucsVnicConfigIssues,
    cucsVnicVlanOperVnetDn                                           SnmpAdminString,
    cucsVnicVlanOperVnetName                                         SnmpAdminString,
    cucsVnicVlanPubNwId                                              Gauge32,
    cucsVnicVlanSharing                                              CucsFabricVlanSharingType,
    cucsVnicVlanOperPrimaryVnetDn                                    SnmpAdminString,
    cucsVnicVlanOperPrimaryVnetName                                  SnmpAdminString
}

cucsVnicVlanInstanceId OBJECT-TYPE
    SYNTAX       CucsManagedObjectId
    MAX-ACCESS   not-accessible
    STATUS       current
    DESCRIPTION
        "Instance identifier of the managed object."
    ::= { cucsVnicVlanEntry 1 }

cucsVnicVlanDn OBJECT-TYPE
    SYNTAX       CucsManagedObjectDn
    MAX-ACCESS   read-only
    STATUS       current
    DESCRIPTION
        "Cisco UCS vnic:Vlan:dn managed object property"
    ::= { cucsVnicVlanEntry 2 }

cucsVnicVlanRn OBJECT-TYPE
    SYNTAX       SnmpAdminString
    MAX-ACCESS   read-only
    STATUS       current
    DESCRIPTION
        "Cisco UCS vnic:Vlan:rn managed object property"
    ::= { cucsVnicVlanEntry 3 }

cucsVnicVlanFltAggr OBJECT-TYPE
    SYNTAX       Unsigned64
    MAX-ACCESS   read-only
    STATUS       current
    DESCRIPTION
        "Cisco UCS vnic:Vlan:fltAggr managed object property"
    ::= { cucsVnicVlanEntry 4 }

cucsVnicVlanName OBJECT-TYPE
    SYNTAX       SnmpAdminString
    MAX-ACCESS   read-only
    STATUS       current
    DESCRIPTION
        "Cisco UCS vnic:Vlan:name managed object property"
    ::= { cucsVnicVlanEntry 5 }

cucsVnicVlanOperState OBJECT-TYPE
    SYNTAX       CucsVnicIfOperState
    MAX-ACCESS   read-only
    STATUS       current
    DESCRIPTION
        "Cisco UCS vnic:Vlan:operState managed object property"
    ::= { cucsVnicVlanEntry 6 }

cucsVnicVlanOwner OBJECT-TYPE
    SYNTAX       CucsVnicConnectionOwner
    MAX-ACCESS   read-only
    STATUS       current
    DESCRIPTION
        "Cisco UCS vnic:Vlan:owner managed object property"
    ::= { cucsVnicVlanEntry 7 }

cucsVnicVlanSwitchId OBJECT-TYPE
    SYNTAX       CucsNetworkSwitchId
    MAX-ACCESS   read-only
    STATUS       current
    DESCRIPTION
        "Cisco UCS vnic:Vlan:switchId managed object property"
    ::= { cucsVnicVlanEntry 8 }

cucsVnicVlanType OBJECT-TYPE
    SYNTAX       CucsVnicConnectionType
    MAX-ACCESS   read-only
    STATUS       current
    DESCRIPTION
        "Cisco UCS vnic:Vlan:type managed object property"
    ::= { cucsVnicVlanEntry 9 }

cucsVnicVlanVlanName OBJECT-TYPE
    SYNTAX       SnmpAdminString
    MAX-ACCESS   read-only
    STATUS       current
    DESCRIPTION
        "Cisco UCS vnic:Vlan:vlanName managed object property"
    ::= { cucsVnicVlanEntry 10 }

cucsVnicVlanVnet OBJECT-TYPE
    SYNTAX       Gauge32
    MAX-ACCESS   read-only
    STATUS       current
    DESCRIPTION
        "Cisco UCS vnic:Vlan:vnet managed object property"
    ::= { cucsVnicVlanEntry 11 }

cucsVnicVlanConfigQualifier OBJECT-TYPE
    SYNTAX       CucsVnicConfigIssues
    MAX-ACCESS   read-only
    STATUS       current
    DESCRIPTION
        "Cisco UCS vnic:Vlan:configQualifier managed object property"
    ::= { cucsVnicVlanEntry 12 }

cucsVnicVlanOperVnetDn OBJECT-TYPE
    SYNTAX       SnmpAdminString
    MAX-ACCESS   read-only
    STATUS       current
    DESCRIPTION
        "Cisco UCS vnic:Vlan:operVnetDn managed object property"
    ::= { cucsVnicVlanEntry 14 }

cucsVnicVlanOperVnetName OBJECT-TYPE
    SYNTAX       SnmpAdminString
    MAX-ACCESS   read-only
    STATUS       current
    DESCRIPTION
        "Cisco UCS vnic:Vlan:operVnetName managed object property"
    ::= { cucsVnicVlanEntry 15 }

cucsVnicVlanPubNwId OBJECT-TYPE
    SYNTAX       Gauge32
    MAX-ACCESS   read-only
    STATUS       current
    DESCRIPTION
        "Cisco UCS vnic:Vlan:pubNwId managed object property"
    ::= { cucsVnicVlanEntry 16 }

cucsVnicVlanSharing OBJECT-TYPE
    SYNTAX       CucsFabricVlanSharingType
    MAX-ACCESS   read-only
    STATUS       current
    DESCRIPTION
        "Cisco UCS vnic:Vlan:sharing managed object property"
    ::= { cucsVnicVlanEntry 17 }

cucsVnicVlanOperPrimaryVnetDn OBJECT-TYPE
    SYNTAX       SnmpAdminString
    MAX-ACCESS   read-only
    STATUS       current
    DESCRIPTION
        "Cisco UCS vnic:Vlan:operPrimaryVnetDn managed object property"
    ::= { cucsVnicVlanEntry 18 }

cucsVnicVlanOperPrimaryVnetName OBJECT-TYPE
    SYNTAX       SnmpAdminString
    MAX-ACCESS   read-only
    STATUS       current
    DESCRIPTION
        "Cisco UCS vnic:Vlan:operPrimaryVnetName managed object property"
    ::= { cucsVnicVlanEntry 19 }

cucsVnicVmqConPolicyTable OBJECT-TYPE
    SYNTAX           SEQUENCE OF CucsVnicVmqConPolicyEntry
    MAX-ACCESS       not-accessible
    STATUS           current
    DESCRIPTION
        "Cisco UCS vnic:VmqConPolicy managed object table"
    ::= { cucsVnicObjects 71 }

cucsVnicVmqConPolicyEntry OBJECT-TYPE
    SYNTAX           CucsVnicVmqConPolicyEntry
    MAX-ACCESS       not-accessible
    STATUS           current
    DESCRIPTION
        "Entry for the cucsVnicVmqConPolicyTable table."
    INDEX { cucsVnicVmqConPolicyInstanceId }
    ::= { cucsVnicVmqConPolicyTable 1 }

CucsVnicVmqConPolicyEntry ::= SEQUENCE {
    cucsVnicVmqConPolicyInstanceId                                   CucsManagedObjectId,
    cucsVnicVmqConPolicyDn                                           CucsManagedObjectDn,
    cucsVnicVmqConPolicyRn                                           SnmpAdminString,
    cucsVnicVmqConPolicyDescr                                        SnmpAdminString,
    cucsVnicVmqConPolicyIntId                                        SnmpAdminString,
    cucsVnicVmqConPolicyIntrCount                                    Gauge32,
    cucsVnicVmqConPolicyName                                         SnmpAdminString,
    cucsVnicVmqConPolicyPolicyLevel                                  Gauge32,
    cucsVnicVmqConPolicyPolicyOwner                                  CucsPolicyPolicyOwner,
    cucsVnicVmqConPolicyVmqCount                                     Gauge32
}

cucsVnicVmqConPolicyInstanceId OBJECT-TYPE
    SYNTAX       CucsManagedObjectId
    MAX-ACCESS   not-accessible
    STATUS       current
    DESCRIPTION
        "Instance identifier of the managed object."
    ::= { cucsVnicVmqConPolicyEntry 1 }

cucsVnicVmqConPolicyDn OBJECT-TYPE
    SYNTAX       CucsManagedObjectDn
    MAX-ACCESS   read-only
    STATUS       current
    DESCRIPTION
        "Cisco UCS vnic:VmqConPolicy:dn managed object property"
    ::= { cucsVnicVmqConPolicyEntry 2 }

cucsVnicVmqConPolicyRn OBJECT-TYPE
    SYNTAX       SnmpAdminString
    MAX-ACCESS   read-only
    STATUS       current
    DESCRIPTION
        "Cisco UCS vnic:VmqConPolicy:rn managed object property"
    ::= { cucsVnicVmqConPolicyEntry 3 }

cucsVnicVmqConPolicyDescr OBJECT-TYPE
    SYNTAX       SnmpAdminString
    MAX-ACCESS   read-only
    STATUS       current
    DESCRIPTION
        "Cisco UCS vnic:VmqConPolicy:descr managed object property"
    ::= { cucsVnicVmqConPolicyEntry 4 }

cucsVnicVmqConPolicyIntId OBJECT-TYPE
    SYNTAX       SnmpAdminString
    MAX-ACCESS   read-only
    STATUS       current
    DESCRIPTION
        "Cisco UCS vnic:VmqConPolicy:intId managed object property"
    ::= { cucsVnicVmqConPolicyEntry 5 }

cucsVnicVmqConPolicyIntrCount OBJECT-TYPE
    SYNTAX       Gauge32
    MAX-ACCESS   read-only
    STATUS       current
    DESCRIPTION
        "Cisco UCS vnic:VmqConPolicy:intrCount managed object property"
    ::= { cucsVnicVmqConPolicyEntry 6 }

cucsVnicVmqConPolicyName OBJECT-TYPE
    SYNTAX       SnmpAdminString
    MAX-ACCESS   read-only
    STATUS       current
    DESCRIPTION
        "Cisco UCS vnic:VmqConPolicy:name managed object property"
    ::= { cucsVnicVmqConPolicyEntry 7 }

cucsVnicVmqConPolicyPolicyLevel OBJECT-TYPE
    SYNTAX       Gauge32
    MAX-ACCESS   read-only
    STATUS       current
    DESCRIPTION
        "Cisco UCS vnic:VmqConPolicy:policyLevel managed object property"
    ::= { cucsVnicVmqConPolicyEntry 8 }

cucsVnicVmqConPolicyPolicyOwner OBJECT-TYPE
    SYNTAX       CucsPolicyPolicyOwner
    MAX-ACCESS   read-only
    STATUS       current
    DESCRIPTION
        "Cisco UCS vnic:VmqConPolicy:policyOwner managed object property"
    ::= { cucsVnicVmqConPolicyEntry 9 }

cucsVnicVmqConPolicyVmqCount OBJECT-TYPE
    SYNTAX       Gauge32
    MAX-ACCESS   read-only
    STATUS       current
    DESCRIPTION
        "Cisco UCS vnic:VmqConPolicy:vmqCount managed object property"
    ::= { cucsVnicVmqConPolicyEntry 10 }

cucsVnicVmqConPolicyRefTable OBJECT-TYPE
    SYNTAX           SEQUENCE OF CucsVnicVmqConPolicyRefEntry
    MAX-ACCESS       not-accessible
    STATUS           current
    DESCRIPTION
        "Cisco UCS vnic:VmqConPolicyRef managed object table"
    ::= { cucsVnicObjects 72 }

cucsVnicVmqConPolicyRefEntry OBJECT-TYPE
    SYNTAX           CucsVnicVmqConPolicyRefEntry
    MAX-ACCESS       not-accessible
    STATUS           current
    DESCRIPTION
        "Entry for the cucsVnicVmqConPolicyRefTable table."
    INDEX { cucsVnicVmqConPolicyRefInstanceId }
    ::= { cucsVnicVmqConPolicyRefTable 1 }

CucsVnicVmqConPolicyRefEntry ::= SEQUENCE {
    cucsVnicVmqConPolicyRefInstanceId                                CucsManagedObjectId,
    cucsVnicVmqConPolicyRefDn                                        CucsManagedObjectDn,
    cucsVnicVmqConPolicyRefRn                                        SnmpAdminString,
    cucsVnicVmqConPolicyRefConPolicyName                             SnmpAdminString,
    cucsVnicVmqConPolicyRefOperConPolicyName                         SnmpAdminString
}

cucsVnicVmqConPolicyRefInstanceId OBJECT-TYPE
    SYNTAX       CucsManagedObjectId
    MAX-ACCESS   not-accessible
    STATUS       current
    DESCRIPTION
        "Instance identifier of the managed object."
    ::= { cucsVnicVmqConPolicyRefEntry 1 }

cucsVnicVmqConPolicyRefDn OBJECT-TYPE
    SYNTAX       CucsManagedObjectDn
    MAX-ACCESS   read-only
    STATUS       current
    DESCRIPTION
        "Cisco UCS vnic:VmqConPolicyRef:dn managed object property"
    ::= { cucsVnicVmqConPolicyRefEntry 2 }

cucsVnicVmqConPolicyRefRn OBJECT-TYPE
    SYNTAX       SnmpAdminString
    MAX-ACCESS   read-only
    STATUS       current
    DESCRIPTION
        "Cisco UCS vnic:VmqConPolicyRef:rn managed object property"
    ::= { cucsVnicVmqConPolicyRefEntry 3 }

cucsVnicVmqConPolicyRefConPolicyName OBJECT-TYPE
    SYNTAX       SnmpAdminString
    MAX-ACCESS   read-only
    STATUS       current
    DESCRIPTION
        "Cisco UCS vnic:VmqConPolicyRef:conPolicyName managed
        object property"
    ::= { cucsVnicVmqConPolicyRefEntry 4 }

cucsVnicVmqConPolicyRefOperConPolicyName OBJECT-TYPE
    SYNTAX       SnmpAdminString
    MAX-ACCESS   read-only
    STATUS       current
    DESCRIPTION
        "Cisco UCS vnic:VmqConPolicyRef:operConPolicyName
        managed object property"
    ::= { cucsVnicVmqConPolicyRefEntry 5 }

cucsVnicVnicBehPolicyTable OBJECT-TYPE
    SYNTAX           SEQUENCE OF CucsVnicVnicBehPolicyEntry
    MAX-ACCESS       not-accessible
    STATUS           current
    DESCRIPTION
        "Cisco UCS vnic:VnicBehPolicy managed object table"
    ::= { cucsVnicObjects 59 }

cucsVnicVnicBehPolicyEntry OBJECT-TYPE
    SYNTAX           CucsVnicVnicBehPolicyEntry
    MAX-ACCESS       not-accessible
    STATUS           current
    DESCRIPTION
        "Entry for the cucsVnicVnicBehPolicyTable table."
    INDEX { cucsVnicVnicBehPolicyInstanceId }
    ::= { cucsVnicVnicBehPolicyTable 1 }

CucsVnicVnicBehPolicyEntry ::= SEQUENCE {
    cucsVnicVnicBehPolicyInstanceId                                  CucsManagedObjectId,
    cucsVnicVnicBehPolicyDn                                          CucsManagedObjectDn,
    cucsVnicVnicBehPolicyRn                                          SnmpAdminString,
    cucsVnicVnicBehPolicyAction                                      CucsVnicDefaultAction,
    cucsVnicVnicBehPolicyDescr                                       SnmpAdminString,
    cucsVnicVnicBehPolicyIntId                                       SnmpAdminString,
    cucsVnicVnicBehPolicyName                                        SnmpAdminString,
    cucsVnicVnicBehPolicyNwTemplName                                 SnmpAdminString,
    cucsVnicVnicBehPolicyPolicyLevel                                 Gauge32,
    cucsVnicVnicBehPolicyPolicyOwner                                 CucsPolicyPolicyOwner,
    cucsVnicVnicBehPolicyType                                        CucsVnicVnicBehPolicyType
}

cucsVnicVnicBehPolicyInstanceId OBJECT-TYPE
    SYNTAX       CucsManagedObjectId
    MAX-ACCESS   not-accessible
    STATUS       current
    DESCRIPTION
        "Instance identifier of the managed object."
    ::= { cucsVnicVnicBehPolicyEntry 1 }

cucsVnicVnicBehPolicyDn OBJECT-TYPE
    SYNTAX       CucsManagedObjectDn
    MAX-ACCESS   read-only
    STATUS       current
    DESCRIPTION
        "Cisco UCS vnic:VnicBehPolicy:dn managed object property"
    ::= { cucsVnicVnicBehPolicyEntry 2 }

cucsVnicVnicBehPolicyRn OBJECT-TYPE
    SYNTAX       SnmpAdminString
    MAX-ACCESS   read-only
    STATUS       current
    DESCRIPTION
        "Cisco UCS vnic:VnicBehPolicy:rn managed object property"
    ::= { cucsVnicVnicBehPolicyEntry 3 }

cucsVnicVnicBehPolicyAction OBJECT-TYPE
    SYNTAX       CucsVnicDefaultAction
    MAX-ACCESS   read-only
    STATUS       current
    DESCRIPTION
        "Cisco UCS vnic:VnicBehPolicy:action managed object property"
    ::= { cucsVnicVnicBehPolicyEntry 4 }

cucsVnicVnicBehPolicyDescr OBJECT-TYPE
    SYNTAX       SnmpAdminString
    MAX-ACCESS   read-only
    STATUS       current
    DESCRIPTION
        "Cisco UCS vnic:VnicBehPolicy:descr managed object property"
    ::= { cucsVnicVnicBehPolicyEntry 5 }

cucsVnicVnicBehPolicyIntId OBJECT-TYPE
    SYNTAX       SnmpAdminString
    MAX-ACCESS   read-only
    STATUS       current
    DESCRIPTION
        "Cisco UCS vnic:VnicBehPolicy:intId managed object property"
    ::= { cucsVnicVnicBehPolicyEntry 6 }

cucsVnicVnicBehPolicyName OBJECT-TYPE
    SYNTAX       SnmpAdminString
    MAX-ACCESS   read-only
    STATUS       current
    DESCRIPTION
        "Cisco UCS vnic:VnicBehPolicy:name managed object property"
    ::= { cucsVnicVnicBehPolicyEntry 7 }

cucsVnicVnicBehPolicyNwTemplName OBJECT-TYPE
    SYNTAX       SnmpAdminString
    MAX-ACCESS   read-only
    STATUS       current
    DESCRIPTION
        "Cisco UCS vnic:VnicBehPolicy:nwTemplName managed object property"
    ::= { cucsVnicVnicBehPolicyEntry 8 }

cucsVnicVnicBehPolicyPolicyLevel OBJECT-TYPE
    SYNTAX       Gauge32
    MAX-ACCESS   read-only
    STATUS       current
    DESCRIPTION
        "Cisco UCS vnic:VnicBehPolicy:policyLevel managed object property"
    ::= { cucsVnicVnicBehPolicyEntry 9 }

cucsVnicVnicBehPolicyPolicyOwner OBJECT-TYPE
    SYNTAX       CucsPolicyPolicyOwner
    MAX-ACCESS   read-only
    STATUS       current
    DESCRIPTION
        "Cisco UCS vnic:VnicBehPolicy:policyOwner managed object property"
    ::= { cucsVnicVnicBehPolicyEntry 10 }

cucsVnicVnicBehPolicyType OBJECT-TYPE
    SYNTAX       CucsVnicVnicBehPolicyType
    MAX-ACCESS   read-only
    STATUS       current
    DESCRIPTION
        "Cisco UCS vnic:VnicBehPolicy:type managed object property"
    ::= { cucsVnicVnicBehPolicyEntry 11 }

cucsVnicWwnnHistoryTable OBJECT-TYPE
    SYNTAX           SEQUENCE OF CucsVnicWwnnHistoryEntry
    MAX-ACCESS       not-accessible
    STATUS           current
    DESCRIPTION
        "Cisco UCS vnic:WwnnHistory managed object table"
    ::= { cucsVnicObjects 63 }

cucsVnicWwnnHistoryEntry OBJECT-TYPE
    SYNTAX           CucsVnicWwnnHistoryEntry
    MAX-ACCESS       not-accessible
    STATUS           current
    DESCRIPTION
        "Entry for the cucsVnicWwnnHistoryTable table."
    INDEX { cucsVnicWwnnHistoryInstanceId }
    ::= { cucsVnicWwnnHistoryTable 1 }

CucsVnicWwnnHistoryEntry ::= SEQUENCE {
    cucsVnicWwnnHistoryInstanceId                                    CucsManagedObjectId,
    cucsVnicWwnnHistoryDn                                            CucsManagedObjectDn,
    cucsVnicWwnnHistoryRn                                            SnmpAdminString,
    cucsVnicWwnnHistoryOldwwnn                                       Unsigned64
}

cucsVnicWwnnHistoryInstanceId OBJECT-TYPE
    SYNTAX       CucsManagedObjectId
    MAX-ACCESS   not-accessible
    STATUS       current
    DESCRIPTION
        "Instance identifier of the managed object."
    ::= { cucsVnicWwnnHistoryEntry 1 }

cucsVnicWwnnHistoryDn OBJECT-TYPE
    SYNTAX       CucsManagedObjectDn
    MAX-ACCESS   read-only
    STATUS       current
    DESCRIPTION
        "Cisco UCS vnic:WwnnHistory:dn managed object property"
    ::= { cucsVnicWwnnHistoryEntry 2 }

cucsVnicWwnnHistoryRn OBJECT-TYPE
    SYNTAX       SnmpAdminString
    MAX-ACCESS   read-only
    STATUS       current
    DESCRIPTION
        "Cisco UCS vnic:WwnnHistory:rn managed object property"
    ::= { cucsVnicWwnnHistoryEntry 3 }

cucsVnicWwnnHistoryOldwwnn OBJECT-TYPE
    SYNTAX       Unsigned64
    MAX-ACCESS   read-only
    STATUS       current
    DESCRIPTION
        "Cisco UCS vnic:WwnnHistory:oldwwnn managed object property"
    ::= { cucsVnicWwnnHistoryEntry 4 }

cucsVnicWwpnHistoryTable OBJECT-TYPE
    SYNTAX           SEQUENCE OF CucsVnicWwpnHistoryEntry
    MAX-ACCESS       not-accessible
    STATUS           current
    DESCRIPTION
        "Cisco UCS vnic:WwpnHistory managed object table"
    ::= { cucsVnicObjects 64 }

cucsVnicWwpnHistoryEntry OBJECT-TYPE
    SYNTAX           CucsVnicWwpnHistoryEntry
    MAX-ACCESS       not-accessible
    STATUS           current
    DESCRIPTION
        "Entry for the cucsVnicWwpnHistoryTable table."
    INDEX { cucsVnicWwpnHistoryInstanceId }
    ::= { cucsVnicWwpnHistoryTable 1 }

CucsVnicWwpnHistoryEntry ::= SEQUENCE {
    cucsVnicWwpnHistoryInstanceId                                    CucsManagedObjectId,
    cucsVnicWwpnHistoryDn                                            CucsManagedObjectDn,
    cucsVnicWwpnHistoryRn                                            SnmpAdminString,
    cucsVnicWwpnHistoryOldaddr                                       Unsigned64
}

cucsVnicWwpnHistoryInstanceId OBJECT-TYPE
    SYNTAX       CucsManagedObjectId
    MAX-ACCESS   not-accessible
    STATUS       current
    DESCRIPTION
        "Instance identifier of the managed object."
    ::= { cucsVnicWwpnHistoryEntry 1 }

cucsVnicWwpnHistoryDn OBJECT-TYPE
    SYNTAX       CucsManagedObjectDn
    MAX-ACCESS   read-only
    STATUS       current
    DESCRIPTION
        "Cisco UCS vnic:WwpnHistory:dn managed object property"
    ::= { cucsVnicWwpnHistoryEntry 2 }

cucsVnicWwpnHistoryRn OBJECT-TYPE
    SYNTAX       SnmpAdminString
    MAX-ACCESS   read-only
    STATUS       current
    DESCRIPTION
        "Cisco UCS vnic:WwpnHistory:rn managed object property"
    ::= { cucsVnicWwpnHistoryEntry 3 }

cucsVnicWwpnHistoryOldaddr OBJECT-TYPE
    SYNTAX       Unsigned64
    MAX-ACCESS   read-only
    STATUS       current
    DESCRIPTION
        "Cisco UCS vnic:WwpnHistory:oldaddr managed object property"
    ::= { cucsVnicWwpnHistoryEntry 4 }

END
