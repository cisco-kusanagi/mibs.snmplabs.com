PAIRGAIN-ETSI-HDSL-MIB

-- PairGain ETSI HDSL MIB Release 1.1
-- Revision 05/21/97

-- Copyright 1996 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.
--

DEFINITIONS ::= BEGIN

-- SECTION 1: Top Level Definitions

IMPORTS
        OBJECT-TYPE
            FROM RFC-1212
        pgainHDSL
            FROM PAIRGAIN-COMMON-HD-MIB;
 
 
-- Define a one byte integer
    Byte ::= INTEGER (0..255)

-- Define a two bytes integer
    Short ::= INTEGER (0..65535)

-- Define a time stamp structure. The time stamp consists of 6 bytes,
-- with the following format :
--     byte 1 : year within century,
--     byte 2 : month of year,
--     byte 3 : day of month,
--     byte 4 : hour (24 hour format)
--     byte 5 : minutes
--     byte 6 : seconds

    PgTimeStamp ::= OCTET STRING (SIZE(6))

    PgAlarmSeverityMode ::=
       INTEGER {
               disable(1),
               minor(2),
               major(3),
               notAvailable(4)
       }

    PgAlarmSeverityProtectionSwitchMode ::=
       INTEGER {
               disable(1),
               minor(2),
               major(3),
               protectionSwitchMajor(4),
               notAvailable(5)
       }

--
-- BER Threshold value
-- 
-- The BER is represented in two bytes, with the first byte represents
-- Mantissa of BER and second byte represents Exponent of BER.
--
--
-- The Mantissa of BER is represented in two BCD digits,
-- with the data point between the two digits."
--
-- Although the exponent value is positive, it shall be treated as a
-- negative value.
--
    PgBERThreshold ::= INTEGER (0..65535)

    ----------------------------------------------------
    -- HDSL 15-minute Performance History for All spans
    ----------------------------------------------------
    hdslSpan15mPerformanceTable  OBJECT-TYPE
        SYNTAX    SEQUENCE OF HdslSpan15mPerformanceEntry
        ACCESS    not-accessible
        STATUS    mandatory
        DESCRIPTION
            "This table provides the 15-minute performance history monitoring
             of the last 24 hours for all HDSL spans Errored Seconds (ES), 
             Severely Errored Seconds (SES) and Unavailable Seconds (UAS)."
        ::= {pgainHDSL 1}

    hdslSpan15mPerformanceEntry  OBJECT-TYPE
        SYNTAX    HdslSpan15mPerformanceEntry
        ACCESS    not-accessible
        STATUS    mandatory
        DESCRIPTION
            "Entries of the HDSL span 15-min performance table "
        INDEX
            {hdslSpan15mSlotId, hdslSpan15mSpanId, hdslSpan15mHistoryId}
        ::= {hdslSpan15mPerformanceTable 1}

    HdslSpan15mPerformanceEntry ::= SEQUENCE {
        hdslSpan15mSlotId
                INTEGER,
        hdslSpan15mSpanId
                INTEGER,
        hdslSpan15mHistoryId
                INTEGER,
        hdsl15mESLoopANet
                Short,
        hdsl15mESLoopBNet
                Short,
        hdsl15mUASLoopANet
                Short,
        hdsl15mUASLoopBNet
                Short,
        hdsl15mSESLoopANet
                Short,
        hdsl15mSESLoopBNet
                Short,
        hdsl15mESLoopACust
                Short,
        hdsl15mESLoopBCust
                Short,
        hdsl15mUASLoopACust
                Short,
        hdsl15mUASLoopBCust
                Short,
        hdsl15mSESLoopACust
                Short,
        hdsl15mSESLoopBCust
                Short
        }

    hdslSpan15mSlotId OBJECT-TYPE
        SYNTAX    INTEGER
        ACCESS    read-only
        STATUS    mandatory
        DESCRIPTION
            "Identifies the HDSL line occupied in the chassis.
             The slots are numbered 1 through 16 from left to right."
        ::= {hdslSpan15mPerformanceEntry 1}

    hdslSpan15mSpanId  OBJECT-TYPE
        SYNTAX    INTEGER
        ACCESS    read-only
        STATUS    mandatory
        DESCRIPTION
            "Identifies the span of the HDSL line we are monitoring.
             Depending on the number of regenerator(s) (REGs)
             present in an HDSL loop, a span will be numbered as follows:
                 0 REG   - only 1 span.
                 1 REG   - span between LTU and REG is identified as 1.
                           span between REG and NTU is identified as 2.
                 2 REGs  - span between LTU and REG #1 is identified as 1.
                           span between REG #1 and REG #2 is identified as 2.
                           span between REG #2 and NTU is identified as 3.
             "
        ::= {hdslSpan15mPerformanceEntry 2}

    hdslSpan15mHistoryId  OBJECT-TYPE
        SYNTAX    INTEGER
        ACCESS    read-only
        STATUS    mandatory
        DESCRIPTION
            "Identify the history ID within the 96 15-minute performance
             history.
            "
        ::= {hdslSpan15mPerformanceEntry 3}

    hdsl15mESLoopANet  OBJECT-TYPE
        SYNTAX    Short
        ACCESS    read-only
        STATUS    mandatory
        DESCRIPTION
            "HDSL 15-min ES count on Loop A's Network side of the span."
        ::= {hdslSpan15mPerformanceEntry 4}

    hdsl15mESLoopBNet  OBJECT-TYPE
        SYNTAX    Short
        ACCESS    read-only
        STATUS    mandatory
        DESCRIPTION
            "HDSL 15-min ES count on Loop B's Network side of the span."
        ::= {hdslSpan15mPerformanceEntry 5}

    hdsl15mUASLoopANet OBJECT-TYPE
        SYNTAX    Short
        ACCESS    read-only
        STATUS    mandatory
        DESCRIPTION
            "HDSL 15-min UAS count on Loop A's Network side of the span."
        ::= {hdslSpan15mPerformanceEntry 6}

    hdsl15mUASLoopBNet OBJECT-TYPE
        SYNTAX    Short
        ACCESS    read-only
        STATUS    mandatory
        DESCRIPTION
            "HDSL 15-min UAS count on Loop B's Network side of the span."
        ::= {hdslSpan15mPerformanceEntry 7}

    hdsl15mSESLoopANet OBJECT-TYPE
        SYNTAX    Short
        ACCESS    read-only
        STATUS    mandatory
        DESCRIPTION
            "HDSL 15-min SES count on Loop A's Network side of the span."
        ::= {hdslSpan15mPerformanceEntry 8}

    hdsl15mSESLoopBNet OBJECT-TYPE
        SYNTAX    Short
        ACCESS    read-only
        STATUS    mandatory
        DESCRIPTION
            "HDSL 15-min SES count on Loop B's Network side of the span."
        ::= {hdslSpan15mPerformanceEntry 9}

    hdsl15mESLoopACust OBJECT-TYPE
        SYNTAX    Short
        ACCESS    read-only
        STATUS    mandatory
        DESCRIPTION
            "HDSL 15-min ES count on Loop A's Customer side of the span."
        ::= {hdslSpan15mPerformanceEntry 10}

    hdsl15mESLoopBCust OBJECT-TYPE
        SYNTAX    Short
        ACCESS    read-only
        STATUS    mandatory
        DESCRIPTION
            "HDSL 15-min ES count on Loop B's Customer side of the span."
        ::= {hdslSpan15mPerformanceEntry 11}

    hdsl15mUASLoopACust OBJECT-TYPE
        SYNTAX    Short
        ACCESS    read-only
        STATUS    mandatory
        DESCRIPTION
            "HDSL 15-min UAS count on Loop A's Customer side of the span."
        ::= {hdslSpan15mPerformanceEntry 12}

    hdsl15mUASLoopBCust OBJECT-TYPE
        SYNTAX    Short
        ACCESS    read-only
        STATUS    mandatory
        DESCRIPTION
            "HDSL 15-min UAS count on Loop B's Customer side of the span."
        ::= {hdslSpan15mPerformanceEntry 13}
 
    hdsl15mSESLoopACust OBJECT-TYPE 
        SYNTAX    Short 
        ACCESS    read-only 
        STATUS    mandatory 
        DESCRIPTION
            "HDSL 15-min SES count on Loop A's customer side of the span."
        ::= {hdslSpan15mPerformanceEntry 14}
 
    hdsl15mSESLoopBCust OBJECT-TYPE 
        SYNTAX    Short    
        ACCESS    read-only 
        STATUS    mandatory 
        DESCRIPTION  
            "HDSL 15-min SES count on Loop B's customer side of the span."
        ::= {hdslSpan15mPerformanceEntry 15}

    ----------------------------------------------------
    -- HDSL 24-Hour Performance History for All spans
    ----------------------------------------------------
    hdslSpan24hPerformanceTable  OBJECT-TYPE
        SYNTAX    SEQUENCE OF HdslSpan24hPerformanceEntry
        ACCESS    not-accessible
        STATUS    mandatory
        DESCRIPTION
            "This table provides 24-hour performance history monitoring of the
             last 7 days for all HDSL spans Errored Seconds (ES), Severely Errored 
             Seconds (SES) and Unavailable Seconds (UAS)."
        ::= {pgainHDSL 2}

    hdslSpan24hPerformanceEntry  OBJECT-TYPE
        SYNTAX    HdslSpan24hPerformanceEntry
        ACCESS    not-accessible
        STATUS    mandatory
        DESCRIPTION
            "Entries of the HDSL span 24-hour performance table "
        INDEX
            {hdslSpan24hSlotId, hdslSpan24hSpanId, hdslSpan24hHistoryId}
        ::= {hdslSpan24hPerformanceTable 1}

    HdslSpan24hPerformanceEntry ::= SEQUENCE {
        hdslSpan24hSlotId
                INTEGER,
        hdslSpan24hSpanId
                INTEGER,
        hdslSpan24hHistoryId
                INTEGER,
        hdsl24hESLoopANet
                INTEGER,
        hdsl24hESLoopBNet
                INTEGER,
        hdsl24hUASLoopANet
                INTEGER,
        hdsl24hUASLoopBNet
                INTEGER,
        hdsl24hSESLoopANet
                INTEGER,
        hdsl24hSESLoopBNet
                INTEGER,
        hdsl24hESLoopACust
                INTEGER,
        hdsl24hESLoopBCust
                INTEGER,
        hdsl24hUASLoopACust
                INTEGER,
        hdsl24hUASLoopBCust
                INTEGER,
        hdsl24hSESLoopACust
                INTEGER,
        hdsl24hSESLoopBCust
                INTEGER
        }

    hdslSpan24hSlotId OBJECT-TYPE
        SYNTAX    INTEGER
        ACCESS    read-only
        STATUS    mandatory
        DESCRIPTION
            "Identifies the HDSL line occupied in the chassis.
             The slots are numbered 1 through 16 from left to right."
        ::= {hdslSpan24hPerformanceEntry 1}

    hdslSpan24hSpanId  OBJECT-TYPE
        SYNTAX    INTEGER
        ACCESS    read-only
        STATUS    mandatory
        DESCRIPTION
            "Identifies the span of the HDSL line we are monitoring.
             Depending on the number of regenerator(s) (REGs)
             present in an HDSL loop, a span will be numbered as follows:
                 0 REG   - only 1 span.
                 1 REG   - span between LTU and REG is identified as 1.
                           span between REG and NTU is identified as 2.
                 2 REGs  - span between LTU and REG #1 is identified as 1.
                           span between REG #1 and REG #2 is identified as 2.
                           span between REG #2 and NTU is identified as 3.
             "
        ::= {hdslSpan24hPerformanceEntry 2}

    hdslSpan24hHistoryId  OBJECT-TYPE
        SYNTAX    INTEGER
        ACCESS    read-only
        STATUS    mandatory
        DESCRIPTION
            "Identify the history ID within the 7 24-hour performance
             history.
            "
        ::= {hdslSpan24hPerformanceEntry 3}

    hdsl24hESLoopANet  OBJECT-TYPE
        SYNTAX    INTEGER 
        ACCESS    read-only
        STATUS    mandatory
        DESCRIPTION
            "HDSL 24-hour ES count on Loop A's Network side of the span."
        ::= {hdslSpan24hPerformanceEntry 4}

    hdsl24hESLoopBNet  OBJECT-TYPE
        SYNTAX    INTEGER 
        ACCESS    read-only
        STATUS    mandatory
        DESCRIPTION
            "HDSL 24-hour ES count on Loop B's Network side of the span."
        ::= {hdslSpan24hPerformanceEntry 5}

    hdsl24hUASLoopANet OBJECT-TYPE
        SYNTAX    INTEGER 
        ACCESS    read-only
        STATUS    mandatory
        DESCRIPTION
            "HDSL 24-hour UAS count on Loop A's Network side of the span."
        ::= {hdslSpan24hPerformanceEntry 6}

    hdsl24hUASLoopBNet OBJECT-TYPE
        SYNTAX    INTEGER 
        ACCESS    read-only
        STATUS    mandatory
        DESCRIPTION
            "HDSL 24-hour UAS count on Loop B's Network side of the span."
        ::= {hdslSpan24hPerformanceEntry 7}

    hdsl24hSESLoopANet OBJECT-TYPE
        SYNTAX    INTEGER
        ACCESS    read-only
        STATUS    mandatory
        DESCRIPTION
            "HDSL 24-hour SES count on Loop A's Network side of the span."
        ::= {hdslSpan24hPerformanceEntry 8}

    hdsl24hSESLoopBNet OBJECT-TYPE
        SYNTAX    INTEGER
        ACCESS    read-only
        STATUS    mandatory
        DESCRIPTION
            "HDSL 24-hour SES count on Loop B's Network side of the span."
        ::= {hdslSpan24hPerformanceEntry 9}

    hdsl24hESLoopACust OBJECT-TYPE
        SYNTAX    INTEGER 
        ACCESS    read-only
        STATUS    mandatory
        DESCRIPTION
            "HDSL 24-hour ES count on Loop A's Customer side of the span."
        ::= {hdslSpan24hPerformanceEntry 10}

    hdsl24hESLoopBCust OBJECT-TYPE
        SYNTAX    INTEGER 
        ACCESS    read-only
        STATUS    mandatory
        DESCRIPTION
            "HDSL 24-hour ES count on Loop B's Customer side of the span."
        ::= {hdslSpan24hPerformanceEntry 11}

    hdsl24hUASLoopACust OBJECT-TYPE
        SYNTAX    INTEGER 
        ACCESS    read-only
        STATUS    mandatory
        DESCRIPTION
            "HDSL 24-hour UAS count on Loop A's Customer side of the span."
        ::= {hdslSpan24hPerformanceEntry 12}

    hdsl24hUASLoopBCust OBJECT-TYPE
        SYNTAX    INTEGER 
        ACCESS    read-only
        STATUS    mandatory
        DESCRIPTION
            "HDSL 24-hour UAS count on Loop B's Customer side of the span."
        ::= {hdslSpan24hPerformanceEntry 13}

    hdsl24hSESLoopACust OBJECT-TYPE 
        SYNTAX    INTEGER 
        ACCESS    read-only 
        STATUS    mandatory
        DESCRIPTION 
            "HDSL 24-hour SES count on Loop A's Customer side of the span."
        ::= {hdslSpan24hPerformanceEntry 14} 
 
    hdsl24hSESLoopBCust OBJECT-TYPE 
        SYNTAX    INTEGER    
        ACCESS    read-only 
        STATUS    mandatory 
        DESCRIPTION 
            "HDSL 24-hour SES count on Loop B's Customer side of the span."
        ::= {hdslSpan24hPerformanceEntry 15} 
 


    ----------------------------------------------------
    -- HDSL Current 24-Hour Performance Counts for All spans
    ----------------------------------------------------
    hdslSpanCurr24hPerformanceTable  OBJECT-TYPE
        SYNTAX    SEQUENCE OF HdslSpanCurr24hPerformanceEntry
        ACCESS    not-accessible
        STATUS    mandatory
        DESCRIPTION
            "This table provides the current 24-hour performance history 
             monitoring for all HDSL spans Errored Seconds (ES), Severely 
             Errored Seconds (SES) and Unavailable Seconds (UAS)."
        ::= {pgainHDSL 3}

    hdslSpanCurr24hPerformanceEntry  OBJECT-TYPE
        SYNTAX    HdslSpanCurr24hPerformanceEntry
        ACCESS    not-accessible
        STATUS    mandatory
        DESCRIPTION
            "Entries of the HDSL span Current 24-hour PM counts table "
        INDEX
            {hdslSpanCurr24hSlotId, hdslSpanCurr24hSpanId}
        ::= {hdslSpanCurr24hPerformanceTable 1}

    HdslSpanCurr24hPerformanceEntry ::= SEQUENCE {
        hdslSpanCurr24hSlotId
                INTEGER,
        hdslSpanCurr24hSpanId
                INTEGER,
        hdslCurr24hESLoopANet
                INTEGER,
        hdslCurr24hESLoopBNet
                INTEGER,
        hdslCurr24hUASLoopANet
                INTEGER,
        hdslCurr24hUASLoopBNet
                INTEGER,
        hdslCurr24hSESLoopANet
                INTEGER,
        hdslCurr24hSESLoopBNet
                INTEGER,
        hdslCurr24hESLoopACust
                INTEGER,
        hdslCurr24hESLoopBCust
                INTEGER,
        hdslCurr24hUASLoopACust
                INTEGER,
        hdslCurr24hUASLoopBCust
                INTEGER,
        hdslCurr24hSESLoopACust
                INTEGER,
        hdslCurr24hSESLoopBCust
                INTEGER
        }

    hdslSpanCurr24hSlotId OBJECT-TYPE
        SYNTAX    INTEGER
        ACCESS    read-only
        STATUS    mandatory
        DESCRIPTION
            "Identifies the HDSL line occupied in the chassis.
             The slots are numbered 1 through 16 from left to right."
        ::= {hdslSpanCurr24hPerformanceEntry 1}

    hdslSpanCurr24hSpanId  OBJECT-TYPE
        SYNTAX    INTEGER
        ACCESS    read-only
        STATUS    mandatory
        DESCRIPTION
            "Identifies the span of the HDSL line we are monitoring.
             Depending on the number of regenerator(s) (REGs)
             present in an HDSL loop, a span will be numbered as follows:
                 0 REG   - only 1 span.
                 1 REG   - span between LTU and REG is identified as 1.
                           span between REG and NTU is identified as 2.
                 2 REGs  - span between LTU and REG #1 is identified as 1.
                           span between REG #1 and REG #2 is identified as 2.
                           span between REG #2 and NTU is identified as 3.
             "
        ::= {hdslSpanCurr24hPerformanceEntry 2}

    hdslCurr24hESLoopANet  OBJECT-TYPE
        SYNTAX    INTEGER 
        ACCESS    read-only
        STATUS    mandatory
        DESCRIPTION
            "HDSL Current 24-hour ES count on Loop A's Network side of the span."
        ::= {hdslSpanCurr24hPerformanceEntry 3}

    hdslCurr24hESLoopBNet  OBJECT-TYPE
        SYNTAX    INTEGER 
        ACCESS    read-only
        STATUS    mandatory
        DESCRIPTION
            "HDSL 24-hour ES count on Loop B's Network side of the span."
        ::= {hdslSpanCurr24hPerformanceEntry 4}

    hdslCurr24hUASLoopANet OBJECT-TYPE
        SYNTAX    INTEGER 
        ACCESS    read-only
        STATUS    mandatory
        DESCRIPTION
            "HDSL 24-hour UAS count on Loop A's Network side of the span."
        ::= {hdslSpanCurr24hPerformanceEntry 5}

    hdslCurr24hUASLoopBNet OBJECT-TYPE
        SYNTAX    INTEGER 
        ACCESS    read-only
        STATUS    mandatory
        DESCRIPTION
            "HDSL 24-hour UAS count on Loop B's Network side of the span."
        ::= {hdslSpanCurr24hPerformanceEntry 6}

    hdslCurr24hSESLoopANet OBJECT-TYPE
        SYNTAX    INTEGER
        ACCESS    read-only
        STATUS    mandatory
        DESCRIPTION
            "HDSL 24-hour SES count on Loop A's Network side of the span."
        ::= {hdslSpanCurr24hPerformanceEntry 7}
 
    hdslCurr24hSESLoopBNet OBJECT-TYPE
        SYNTAX    INTEGER
        ACCESS    read-only
        STATUS    mandatory
        DESCRIPTION
            "HDSL 24-hour SES count on Loop B's Network side of the span."
        ::= {hdslSpanCurr24hPerformanceEntry 8}

    hdslCurr24hESLoopACust OBJECT-TYPE
        SYNTAX    INTEGER 
        ACCESS    read-only
        STATUS    mandatory
        DESCRIPTION
            "HDSL 24-hour ES count on Loop A's Customer side of the span."
        ::= {hdslSpanCurr24hPerformanceEntry 9}

    hdslCurr24hESLoopBCust OBJECT-TYPE
        SYNTAX    INTEGER 
        ACCESS    read-only
        STATUS    mandatory
        DESCRIPTION
            "HDSL 24-hour ES count on Loop B's Customer side of the span."
        ::= {hdslSpanCurr24hPerformanceEntry 10}

    hdslCurr24hUASLoopACust OBJECT-TYPE
        SYNTAX    INTEGER 
        ACCESS    read-only
        STATUS    mandatory
        DESCRIPTION
            "HDSL 24-hour UAS count on Loop A's Customer side of the span."
        ::= {hdslSpanCurr24hPerformanceEntry 11}

    hdslCurr24hUASLoopBCust OBJECT-TYPE
        SYNTAX    INTEGER 
        ACCESS    read-only
        STATUS    mandatory
        DESCRIPTION
            "HDSL 24-hour UAS count on Loop B's Customer side of the span."
        ::= {hdslSpanCurr24hPerformanceEntry 12}

    hdslCurr24hSESLoopACust OBJECT-TYPE
        SYNTAX    INTEGER
        ACCESS    read-only
        STATUS    mandatory
        DESCRIPTION
            "HDSL 24-hour SES count on Loop A's Customer side of the span."        
        ::= {hdslSpanCurr24hPerformanceEntry 13}
 
    hdslCurr24hSESLoopBCust OBJECT-TYPE
        SYNTAX    INTEGER
        ACCESS    read-only
        STATUS    mandatory
        DESCRIPTION
            "HDSL 24-hour SES count on Loop B's Customer side of the span."        
        ::= {hdslSpanCurr24hPerformanceEntry 14}

    ----------------------------------------------------
    -- HDSL Statistics for All spans
    ----------------------------------------------------
    hdslSpanStatisticsTable  OBJECT-TYPE
        SYNTAX    SEQUENCE OF HdslSpanStatisticsEntry
        ACCESS    not-accessible
        STATUS    mandatory
        DESCRIPTION
            "This table lists statistics for margin, pulse attenuation and 
             state of the loop for all spans of the HDSL loop.
            "
        ::= {pgainHDSL 4}

    hdslSpanStatisticsEntry  OBJECT-TYPE
        SYNTAX    HdslSpanStatisticsEntry
        ACCESS    not-accessible
        STATUS    mandatory
        DESCRIPTION
            "Entries of the HDSL span statistics table "
        INDEX
            {hdslStatisticsSlotId, hdslStatisticsSpanId}
        ::= {hdslSpanStatisticsTable 1}

    HdslSpanStatisticsEntry ::= SEQUENCE {
        hdslStatisticsSlotId
            INTEGER,
        hdslStatisticsSpanId
            INTEGER,
        hdslLoopPairState
            Byte,
        hdslLoopATipRingReversal
            Byte,
        hdslLoopBTipRingReversal
            Byte,
        hdslLoopAUpState
            Byte,
        hdslLoopBUpState
            Byte,
        hdslMarginLoopANet
            Byte,
        hdslMarginHighLoopANet
            Byte,
        hdslMarginLowLoopANet
            Byte,
        hdslMarginLoopBNet
            Byte,
        hdslMarginHighLoopBNet
            Byte,
        hdslMarginLowLoopBNet
            Byte,
        hdslPulseAttenuationLoopANet
            Byte,
        hdslPulseAttenuationLoopBNet
            Byte,
        hdslMarginLoopACust
            Byte,
        hdslMarginHighLoopACust
            Byte,
        hdslMarginLowLoopACust
            Byte,
        hdslMarginLoopBCust
            Byte,
        hdslMarginHighLoopBCust
            Byte,
        hdslMarginLowLoopBCust
            Byte,
        hdslPulseAttenuationLoopACust
            Byte,
        hdslPulseAttenuationLoopBCust
            Byte
        }

    hdslStatisticsSlotId  OBJECT-TYPE
        SYNTAX    INTEGER
        ACCESS    read-only
        STATUS    mandatory
        DESCRIPTION
            "Identifies the HDSL line occupied in the chassis.
             The slots are numbered 1 through 16 from left to right."
        ::= {hdslSpanStatisticsEntry 1}

    hdslStatisticsSpanId  OBJECT-TYPE
        SYNTAX    INTEGER
        ACCESS    read-only
        STATUS    mandatory
        DESCRIPTION
            "Identifies the span of the HDSL line we are monitoring.
             Depending on the number of regenerator(s) (REGs)
             present in an HDSL loop, a span will be numbered as follows:
                 0 REG   - only 1 span.
                 1 REG   - span between LTU and REG is identified as 1.
                           span between REG and NTU is identified as 2.
                 2 REGs  - span between LTU and REG #1 is identified as 1.
                           span between REG #1 and REG #2 is identified as 2.
                           span between REG #2 and NTU is identified as 3.
             "
        ::= {hdslSpanStatisticsEntry 2}

    hdslLoopPairState OBJECT-TYPE
        SYNTAX    Byte
        ACCESS    read-only
        STATUS    mandatory
        DESCRIPTION
            "Current state on the HDSL loop of span:
                 0 - loop pair is normal 
                 1 - loop pair is exchanged.
            "
        ::= {hdslSpanStatisticsEntry 3}

    hdslLoopATipRingReversal OBJECT-TYPE
        SYNTAX    Byte
        ACCESS    read-only 
        STATUS    mandatory 
        DESCRIPTION  
            "Current TIP/RING state on the HDSL loop A of span: 
                 0 - TIP/RING on loop A is not reversed. 
                 1 - TIP/RING on loop A is reversed.   
            " 
        ::= {hdslSpanStatisticsEntry 4}

    hdslLoopBTipRingReversal OBJECT-TYPE
        SYNTAX    Byte
        ACCESS    read-only 
        STATUS    mandatory 
        DESCRIPTION  
            "Current TIP/RING state on the HDSL loop B of span: 
                 0 - TIP/RING on loop B is not reversed. 
                 1 - TIP/RING on loop B is reversed.   
            " 
        ::= {hdslSpanStatisticsEntry 5}

    hdslLoopAUpState  OBJECT-TYPE
        SYNTAX    Byte
        ACCESS    read-only
        STATUS    mandatory
        DESCRIPTION
            "Current loop state on loop A of the span:
                 0 - loop is up.
                 1 - loop is acquiring/converging.
                 2 - loop is signaling.
            "
        ::= {hdslSpanStatisticsEntry 6}

    hdslLoopBUpState  OBJECT-TYPE
        SYNTAX    Byte
        ACCESS    read-only
        STATUS    mandatory
        DESCRIPTION
            "Current loop state on loop B of the span:
                 0 - loop is up.
                 1 - loop is acquiring/converging.
                 2 - loop is signaling.
            "
        ::= {hdslSpanStatisticsEntry 7}

    hdslMarginLoopANet  OBJECT-TYPE
        SYNTAX    Byte
        ACCESS    read-only
        STATUS    mandatory
        DESCRIPTION
            "Current Margin on Loop A's Network side of the span."
        ::= {hdslSpanStatisticsEntry 8}

    hdslMarginHighLoopANet  OBJECT-TYPE
        SYNTAX    Byte
        ACCESS    read-only
        STATUS    mandatory
        DESCRIPTION
            "Highest Margin on Loop A's Network side of the span."
        ::= {hdslSpanStatisticsEntry 9}

    hdslMarginLowLoopANet  OBJECT-TYPE
        SYNTAX    Byte
        ACCESS    read-only
        STATUS    mandatory
        DESCRIPTION
            "Lowest Margin on Loop A's Network side of the span."
        ::= {hdslSpanStatisticsEntry 10}

    hdslMarginLoopBNet  OBJECT-TYPE
        SYNTAX    Byte
        ACCESS    read-only
        STATUS    mandatory
        DESCRIPTION
            "Current Margin on Loop B's Network side of the span."
        ::= {hdslSpanStatisticsEntry 11}

    hdslMarginHighLoopBNet  OBJECT-TYPE
        SYNTAX    Byte
        ACCESS    read-only
        STATUS    mandatory
        DESCRIPTION
            "Highest Margin on Loop B's Network side of the span."
        ::= {hdslSpanStatisticsEntry 12}

    hdslMarginLowLoopBNet  OBJECT-TYPE
        SYNTAX    Byte
        ACCESS    read-only
        STATUS    mandatory
        DESCRIPTION
            "Lowest Margin on Loop B's Network side of the span."
        ::= {hdslSpanStatisticsEntry 13}

    hdslPulseAttenuationLoopANet  OBJECT-TYPE
        SYNTAX    Byte
        ACCESS    read-only
        STATUS    mandatory
        DESCRIPTION
            "Pulse Attenuation on Loop A's Network side of the span."
        ::= {hdslSpanStatisticsEntry 14}

    hdslPulseAttenuationLoopBNet  OBJECT-TYPE
        SYNTAX    Byte
        ACCESS    read-only
        STATUS    mandatory
        DESCRIPTION
            "Pulse Attenuation on Loop B's Network side of the span."
        ::= {hdslSpanStatisticsEntry 15}

    hdslMarginLoopACust  OBJECT-TYPE
        SYNTAX    Byte
        ACCESS    read-only
        STATUS    mandatory
        DESCRIPTION
            "Current Margin on Loop A's Customer side of the span."
        ::= {hdslSpanStatisticsEntry 16}

    hdslMarginHighLoopACust  OBJECT-TYPE
        SYNTAX    Byte
        ACCESS    read-only
        STATUS    mandatory
        DESCRIPTION
            "Highest Margin on Loop A's Customer side of the span."
        ::= {hdslSpanStatisticsEntry 17}

    hdslMarginLowLoopACust  OBJECT-TYPE
        SYNTAX    Byte
        ACCESS    read-only
        STATUS    mandatory
        DESCRIPTION
            "Lowest Margin on Loop A's Customer side of the span."
        ::= {hdslSpanStatisticsEntry 18}

    hdslMarginLoopBCust  OBJECT-TYPE
        SYNTAX    Byte
        ACCESS    read-only
        STATUS    mandatory
        DESCRIPTION
            "Current Margin on Loop B's Customer side of the span."
        ::= {hdslSpanStatisticsEntry 19}

    hdslMarginHighLoopBCust  OBJECT-TYPE
        SYNTAX    Byte
        ACCESS    read-only
        STATUS    mandatory
        DESCRIPTION
            "Highest Margin on Loop B's Customer side of the span."
        ::= {hdslSpanStatisticsEntry 20}

    hdslMarginLowLoopBCust  OBJECT-TYPE
        SYNTAX    Byte
        ACCESS    read-only
        STATUS    mandatory
        DESCRIPTION
            "Lowest Margin on Loop B's Customer side of the span."
        ::= {hdslSpanStatisticsEntry 21}

    hdslPulseAttenuationLoopACust  OBJECT-TYPE
        SYNTAX    Byte
        ACCESS    read-only
        STATUS    mandatory
        DESCRIPTION
            "Pulse Attenuation on Loop A's Customer side of the span."
        ::= {hdslSpanStatisticsEntry 22}

    hdslPulseAttenuationLoopBCust  OBJECT-TYPE
        SYNTAX    Byte
        ACCESS    read-only
        STATUS    mandatory
        DESCRIPTION
            "Pulse Attenuation on Loop B's Customer side of the span."
        ::= {hdslSpanStatisticsEntry 23}


    ----------------------------------------------------
    -- HDSL Alarms Table for All spans
    ----------------------------------------------------
    hdslSpanAlarmTable  OBJECT-TYPE
        SYNTAX    SEQUENCE OF HdslSpanAlarmEntry
        ACCESS    not-accessible
        STATUS    mandatory
        DESCRIPTION
            "This table provides the HDSL alarms indication on both loops
             of the HDSL spans.
            "
        ::= {pgainHDSL 5}

    hdslSpanAlarmEntry  OBJECT-TYPE
        SYNTAX    HdslSpanAlarmEntry
        ACCESS    not-accessible
        STATUS    mandatory
        DESCRIPTION
            "Entries of the HDSL span alarm table "
        INDEX
            {hdslSpanAlarmSlotId, hdslSpanAlarmSpanId}
        ::= {hdslSpanAlarmTable 1}

    HdslSpanAlarmEntry ::= SEQUENCE {
        hdslSpanAlarmSlotId
            INTEGER,
        hdslSpanAlarmSpanId
            INTEGER,
        hdslMarginAlarmLoopANet
            Byte,
        hdslMarginAlarmLoopBNet
            Byte,
        hdslESAlarmLoopANet
            Byte,
        hdslESAlarmLoopBNet
            Byte,
        hdslUASAlarmLoopANet
            Byte,
        hdslUASAlarmLoopBNet
            Byte,
        hdslMarginAlarmLoopACust
            Byte,  
        hdslMarginAlarmLoopBCust  
            Byte,  
        hdslESAlarmLoopACust 
            Byte, 
        hdslESAlarmLoopBCust
            Byte,
        hdslUASAlarmLoopACust 
            Byte, 
        hdslUASAlarmLoopBCust
            Byte,
        hdslLOSWAlarmLoopA
            Byte,
        hdslLOSWAlarmLoopB
            Byte,
        hdslPFOAlarmLoopA
            Byte,
        hdslPFOAlarmLoopB
            Byte,
        hdslPFSAlarmLoopA
            Byte,
        hdslPFSAlarmLoopB
            Byte,
        hdslBERAlarmLoopA
            Byte,
        hdslBERAlarmLoopB
            Byte

    }

    hdslSpanAlarmSlotId  OBJECT-TYPE
        SYNTAX    INTEGER
        ACCESS    read-only
        STATUS    mandatory
        DESCRIPTION
            "Identifies the HDSL line occupied in the chassis.
             The slots are numbered 1 through 16 from left to right."
        ::= {hdslSpanAlarmEntry 1}

    hdslSpanAlarmSpanId  OBJECT-TYPE
        SYNTAX    INTEGER
        ACCESS    read-only
        STATUS    mandatory
        DESCRIPTION
            "Identifies the span of the HDSL line we are monitoring.
             Depending on the number of regenerator(s) (REGs)
             present in an HDSL loop, a span will be numbered as follows:
                 0 REG   - only 1 span.
                 1 REG   - span between LTU and REG is identified as 1.
                           span between REG and NTU is identified as 2.
                 2 REGs  - span between LTU and REG #1 is identified as 1.
                           span between REG #1 and REG #2 is identified as 2.
                           span between REG #2 and NTU is identified as 3.
             "
        ::= {hdslSpanAlarmEntry 2}

    hdslMarginAlarmLoopANet OBJECT-TYPE
        SYNTAX    Byte
        ACCESS    read-only
        STATUS    mandatory
        DESCRIPTION
            "Margin Threshold Exceeded on loop A's Network side of the span."
        ::= {hdslSpanAlarmEntry 3}

    hdslMarginAlarmLoopBNet OBJECT-TYPE
        SYNTAX    Byte
        ACCESS    read-only
        STATUS    mandatory
        DESCRIPTION
            "Margin Threshold Exceeded on loop B's Network side of the span."
        ::= {hdslSpanAlarmEntry 4}

    hdslESAlarmLoopANet OBJECT-TYPE
        SYNTAX    Byte
        ACCESS    read-only
        STATUS    mandatory
        DESCRIPTION
            "Errored Seconds threshold exceeded on loop A's Network side 
             of the span.
            "
        ::= {hdslSpanAlarmEntry 5}

    hdslESAlarmLoopBNet OBJECT-TYPE
        SYNTAX    Byte
        ACCESS    read-only
        STATUS    mandatory
        DESCRIPTION
            "Errored Seconds threshold exceeded on loop B's Network side 
             of the span."
        ::= {hdslSpanAlarmEntry 6}

    hdslUASAlarmLoopANet OBJECT-TYPE
        SYNTAX    Byte
        ACCESS    read-only
        STATUS    mandatory
        DESCRIPTION
            "Unavailable Seconds threshold exceeded on loop A's Network 
             side of the span.
            "
        ::= {hdslSpanAlarmEntry 7}

    hdslUASAlarmLoopBNet OBJECT-TYPE
        SYNTAX    Byte
        ACCESS    read-only
        STATUS    mandatory
        DESCRIPTION
            "Unavailable Seconds threshold exceeded on loop B's Network 
             side of the span.
            "          
        ::= {hdslSpanAlarmEntry 8}

    hdslMarginAlarmLoopACust OBJECT-TYPE
        SYNTAX    Byte
        ACCESS    read-only
        STATUS    mandatory
        DESCRIPTION
            "Margin Threshold Exceeded on loop A's Customer side of the
             span.
            "
        ::= {hdslSpanAlarmEntry 9}

    hdslMarginAlarmLoopBCust OBJECT-TYPE
        SYNTAX    Byte
        ACCESS    read-only
        STATUS    mandatory
        DESCRIPTION
            "Margin Threshold Exceeded on loop B's Customer side of the
             span.
            "
        ::= {hdslSpanAlarmEntry 10}

    hdslESAlarmLoopACust OBJECT-TYPE
        SYNTAX    Byte
        ACCESS    read-only
        STATUS    mandatory
        DESCRIPTION
            "Errored Seconds Exceeded on loop A's Customer side of the span."
        ::= {hdslSpanAlarmEntry 11}

    hdslESAlarmLoopBCust OBJECT-TYPE
        SYNTAX    Byte
        ACCESS    read-only
        STATUS    mandatory
        DESCRIPTION
            "Errored Seconds Exceeded on loop B's Customer side of the span."
        ::= {hdslSpanAlarmEntry 12}

    hdslUASAlarmLoopACust OBJECT-TYPE
        SYNTAX    Byte
        ACCESS    read-only
        STATUS    mandatory
        DESCRIPTION
            "Unavailable Seconds threshold exceeded on loop A's customer 
             side of the span.
            "
        ::= {hdslSpanAlarmEntry 13}

    hdslUASAlarmLoopBCust OBJECT-TYPE
        SYNTAX    Byte
        ACCESS    read-only
        STATUS    mandatory
        DESCRIPTION
            "Unavailable Seconds threshold exceeded on loop B's customer 
             side of the span.
            "          
        ::= {hdslSpanAlarmEntry 14}

    hdslLOSWAlarmLoopA  OBJECT-TYPE
        SYNTAX    Byte
        ACCESS    read-only
        STATUS    mandatory
        DESCRIPTION
            "Loss of Sync Word (LOSW) occurred on loop A's Network side of             the HDSL loop.
            "
        ::= {hdslSpanAlarmEntry 15}

    hdslLOSWAlarmLoopB  OBJECT-TYPE
        SYNTAX    Byte
        ACCESS    read-only
        STATUS    mandatory
        DESCRIPTION
            "Loss of Sync Word (LOSW) occurred on loop B's Network side of
             the HDSL loop.
            "
        ::= {hdslSpanAlarmEntry 16}

    hdslPFOAlarmLoopA  OBJECT-TYPE
        SYNTAX    Byte
        ACCESS    read-only
        STATUS    mandatory
        DESCRIPTION
            "Power Feed Open (PFO) on loop A's Network side of the HDSL
             loop.
            "
        ::= {hdslSpanAlarmEntry 17}

    hdslPFOAlarmLoopB  OBJECT-TYPE
        SYNTAX    Byte
        ACCESS    read-only
        STATUS    mandatory
        DESCRIPTION
            "Power Feed Open (PFO) on loop B's Network side of the HDSL
             loop.
            "
        ::= {hdslSpanAlarmEntry 18}

    hdslPFSAlarmLoopA  OBJECT-TYPE
        SYNTAX    Byte
        ACCESS    read-only
        STATUS    mandatory
        DESCRIPTION
            "Power Feed Short (PFS) on loop A's Network side of the HDSL 
             loop.
            "
        ::= {hdslSpanAlarmEntry 19}

    hdslPFSAlarmLoopB  OBJECT-TYPE
        SYNTAX    Byte
        ACCESS    read-only
        STATUS    mandatory
        DESCRIPTION
            "Power Feed Short (PFS) on loop B's Network side of the HDSL
             loop.
            "
        ::= {hdslSpanAlarmEntry 20}

    hdslBERAlarmLoopA  OBJECT-TYPE
        SYNTAX    Byte
        ACCESS    read-only
        STATUS    mandatory
        DESCRIPTION
            "Bit Error Rate (BER) on loop A's Network side of the HDSL
             loop.
            "
        ::= {hdslSpanAlarmEntry 21}
 
    hdslBERAlarmLoopB  OBJECT-TYPE
        SYNTAX    Byte
        ACCESS    read-only
        STATUS    mandatory
        DESCRIPTION
            "Bit Error Rate (BER) on loop B's Network side of the HDSL
             loop.
            "
        ::= {hdslSpanAlarmEntry 22}

    ----------------------------------------------------
    -- HDSL Alarms History Table for HDSL spans  
    ----------------------------------------------------
    hdslSpanAlarmHistoryTable  OBJECT-TYPE
        SYNTAX    SEQUENCE OF HdslSpanAlarmHistoryEntry
        ACCESS    not-accessible
        STATUS    mandatory
        DESCRIPTION
            "This table provides the HDSL alarms history on both loops
             of the HDSL spans."
        ::= {pgainHDSL 6}

    hdslSpanAlarmHistoryEntry  OBJECT-TYPE
        SYNTAX    HdslSpanAlarmHistoryEntry
        ACCESS    not-accessible
        STATUS    mandatory
        DESCRIPTION
            "Entries of the HDSL span Alarm History table "
        INDEX
            {hdslSpanAlarmHistorySlotId, hdslSpanAlarmHistorySpanId}
        ::= {hdslSpanAlarmHistoryTable 1}

    HdslSpanAlarmHistoryEntry ::= SEQUENCE {
        hdslSpanAlarmHistorySlotId
            INTEGER,
        hdslSpanAlarmHistorySpanId
            INTEGER,
        hdslMarginAlarmFirstLoopA
            PgTimeStamp,
        hdslMarginAlarmLastLoopA
            PgTimeStamp,
        hdslMarginAlarmCountLoopA
            INTEGER,
        hdslMarginAlarmFirstLoopB
            PgTimeStamp,
        hdslMarginAlarmLastLoopB
            PgTimeStamp,
        hdslMarginAlarmCountLoopB
            INTEGER,
        hdslESAlarmFirstLoopA
            PgTimeStamp,
        hdslESAlarmLastLoopA
            PgTimeStamp,
        hdslESAlarmCountLoopA
            INTEGER,
        hdslESAlarmFirstLoopB
            PgTimeStamp,
        hdslESAlarmLastLoopB
            PgTimeStamp,
        hdslESAlarmCountLoopB
            INTEGER,
        hdslUASAlarmFirstLoopA
            PgTimeStamp,
        hdslUASAlarmLastLoopA
            PgTimeStamp,
        hdslUASAlarmCountLoopA
            INTEGER,
        hdslUASAlarmFirstLoopB
            PgTimeStamp,
        hdslUASAlarmLastLoopB
            PgTimeStamp,
        hdslUASAlarmCountLoopB
            INTEGER,
        hdslLOSWAlarmFirstLoopA
            PgTimeStamp,
        hdslLOSWAlarmLastLoopA
            PgTimeStamp,
        hdslLOSWAlarmCountLoopA
            INTEGER,
        hdslLOSWAlarmFirstLoopB
            PgTimeStamp,
        hdslLOSWAlarmLastLoopB
            PgTimeStamp,
        hdslLOSWAlarmCountLoopB
            INTEGER,
        hdslPFOAlarmFirstLoopA
            PgTimeStamp,
        hdslPFOAlarmLastLoopA
            PgTimeStamp,
        hdslPFOAlarmCountLoopA
            INTEGER,
        hdslPFOAlarmFirstLoopB
            PgTimeStamp,
        hdslPFOAlarmLastLoopB
            PgTimeStamp,
        hdslPFOAlarmCountLoopB
            INTEGER,
        hdslPFSAlarmFirstLoopA
            PgTimeStamp,
        hdslPFSAlarmLastLoopA
            PgTimeStamp,
        hdslPFSAlarmCountLoopA
            INTEGER,
        hdslPFSAlarmFirstLoopB
            PgTimeStamp,
        hdslPFSAlarmLastLoopB
            PgTimeStamp,
        hdslPFSAlarmCountLoopB
            INTEGER,
        hdslBERAlarmFirstLoopA
            PgTimeStamp,
        hdslBERAlarmLastLoopA
            PgTimeStamp,
        hdslBERAlarmCountLoopA
            INTEGER,
        hdslBERAlarmFirstLoopB 
            PgTimeStamp, 
        hdslBERAlarmLastLoopB 
            PgTimeStamp, 
        hdslBERAlarmCountLoopB
            INTEGER
 
    }

    hdslSpanAlarmHistorySlotId  OBJECT-TYPE
        SYNTAX    INTEGER
        ACCESS    read-only
        STATUS    mandatory
        DESCRIPTION
            "Identifies the HDSL line occupied in the chassis.
             The slots are numbered 1 through 16 from left to right."
        ::= {hdslSpanAlarmHistoryEntry 1}

    hdslSpanAlarmHistorySpanId  OBJECT-TYPE
        SYNTAX    INTEGER
        ACCESS    read-only
        STATUS    mandatory
        DESCRIPTION
            "Identifies the span of the HDSL line we are monitoring.
             Depending on the number of regenerator(s) (REGs)
             present in an HDSL loop, a span will be numbered as follows:
                 0 REG   - only 1 span.
                 1 REG   - Span between LTU and REG is identified as 1.
                           Span between REG and NTU is identified as 2.
                 2 REGs  - Span between LTU and REG #1 is identified as 1.
                           Span between REG #1 and REG #2 is identified as 2.
                           Span between REG #2 and NTU is identified as 3.
             "
        ::= {hdslSpanAlarmHistoryEntry 2}

    hdslMarginAlarmFirstLoopA  OBJECT-TYPE
        SYNTAX    PgTimeStamp
        ACCESS    read-only
        STATUS    mandatory
        DESCRIPTION
            "Date and time Margin threshold exceeded alarm first occurred
             on Loop A of a span"
        ::= {hdslSpanAlarmHistoryEntry 3}

    hdslMarginAlarmLastLoopA  OBJECT-TYPE
        SYNTAX    PgTimeStamp
        ACCESS    read-only
        STATUS    mandatory
        DESCRIPTION
            "Date and time Margin threshold exceeded alarm last occurred 
             on Loop A of a span"
        ::= {hdslSpanAlarmHistoryEntry 4}

    hdslMarginAlarmCountLoopA  OBJECT-TYPE
        SYNTAX    INTEGER
        ACCESS    read-only
        STATUS    mandatory
        DESCRIPTION
            "The number of times the Margin threshold exceeded alarm has occurred
             on Loop A of a span."
        ::= {hdslSpanAlarmHistoryEntry 5}

    hdslMarginAlarmFirstLoopB  OBJECT-TYPE
        SYNTAX    PgTimeStamp
        ACCESS    read-only
        STATUS    mandatory
        DESCRIPTION
            "Date and time Margin threshold exceeded alarm first occurred 
             on Loop B of a span"
        ::= {hdslSpanAlarmHistoryEntry 6}

    hdslMarginAlarmLastLoopB  OBJECT-TYPE
        SYNTAX    PgTimeStamp
        ACCESS    read-only
        STATUS    mandatory
        DESCRIPTION
            "Date and time Margin threshold exceeded alarm last occurred 
             on Loop B of a span"
        ::= {hdslSpanAlarmHistoryEntry 7}

    hdslMarginAlarmCountLoopB  OBJECT-TYPE
        SYNTAX    INTEGER
        ACCESS    read-only
        STATUS    mandatory
        DESCRIPTION
            "The number of times the Margin threshold exceeded alarm has occurred 
             on Loop B of a span."
        ::= {hdslSpanAlarmHistoryEntry 8}

    hdslESAlarmFirstLoopA OBJECT-TYPE
        SYNTAX    PgTimeStamp
        ACCESS    read-only
        STATUS    mandatory
        DESCRIPTION
            "Date and time Errored Seconds threshold exceeded alarm first occurred 
             on Loop A of a span"
        ::= {hdslSpanAlarmHistoryEntry 9}

    hdslESAlarmLastLoopA OBJECT-TYPE
        SYNTAX    PgTimeStamp
        ACCESS    read-only
        STATUS    mandatory
        DESCRIPTION
            "Date and time Errored Seconds threshold exceeded alarm last occurred 
             on Loop A of a span"
        ::= {hdslSpanAlarmHistoryEntry 10}

     hdslESAlarmCountLoopA OBJECT-TYPE
        SYNTAX    INTEGER
        ACCESS    read-only
        STATUS    mandatory
        DESCRIPTION
            "The number of times the Errored Seconds threshold exceeded alarm has 
             occurred on Loop A of a span."
        ::= {hdslSpanAlarmHistoryEntry 11}

    hdslESAlarmFirstLoopB OBJECT-TYPE
        SYNTAX    PgTimeStamp
        ACCESS    read-only
        STATUS    mandatory
        DESCRIPTION
            "Date and time Errored Seconds threshold exceeded alarm first occurred
             on Loop B of a span"
        ::= {hdslSpanAlarmHistoryEntry 12}

    hdslESAlarmLastLoopB OBJECT-TYPE
        SYNTAX    PgTimeStamp
        ACCESS    read-only
        STATUS    mandatory
        DESCRIPTION
            "Date and time Errored Seconds threshold exceeded alarm last occurred
             on Loop B of a span"
        ::= {hdslSpanAlarmHistoryEntry 13}

     hdslESAlarmCountLoopB OBJECT-TYPE
        SYNTAX    INTEGER
        ACCESS    read-only
        STATUS    mandatory
        DESCRIPTION
            "The number of times the Errored Seconds threshold exceeded alarm has 
             occurred on Loop B of a span."
        ::= {hdslSpanAlarmHistoryEntry 14}

    hdslUASAlarmFirstLoopA OBJECT-TYPE
        SYNTAX    PgTimeStamp
        ACCESS    read-only
        STATUS    mandatory
        DESCRIPTION
            "Date and time Unavailable Seconds threshold exceeded alarm 
             first occurred on Loop A of a span"
        ::= {hdslSpanAlarmHistoryEntry 15}

    hdslUASAlarmLastLoopA OBJECT-TYPE
        SYNTAX    PgTimeStamp
        ACCESS    read-only
        STATUS    mandatory
        DESCRIPTION
            "Date and time Unavailable Seconds threshold exceeded alarm 
             last occurred on Loop A of a span"
        ::= {hdslSpanAlarmHistoryEntry 16}

     hdslUASAlarmCountLoopA OBJECT-TYPE
        SYNTAX    INTEGER
        ACCESS    read-only
        STATUS    mandatory
        DESCRIPTION
            "The number of times the Unavailable Seconds threshold exceeded alarm 
             has occurred on Loop A of a span."
        ::= {hdslSpanAlarmHistoryEntry 17}

    hdslUASAlarmFirstLoopB OBJECT-TYPE
        SYNTAX    PgTimeStamp
        ACCESS    read-only
        STATUS    mandatory
        DESCRIPTION
            "Date and time Unavailable Seconds threshold exceeded alarm 
             first occurred on Loop B of a span"
        ::= {hdslSpanAlarmHistoryEntry 18}

    hdslUASAlarmLastLoopB OBJECT-TYPE
        SYNTAX    PgTimeStamp
        ACCESS    read-only
        STATUS    mandatory
        DESCRIPTION
            "Date and time Unavailable Seconds threshold exceeded alarm 
             last occurred on Loop B of a span"
        ::= {hdslSpanAlarmHistoryEntry 19}

     hdslUASAlarmCountLoopB OBJECT-TYPE
        SYNTAX    INTEGER
        ACCESS    read-only
        STATUS    mandatory
        DESCRIPTION
            "The number of times the Unavailable Seconds threshold exceeded alarm 
             has occurred on Loop B of a span."
        ::= {hdslSpanAlarmHistoryEntry 20}

    hdslLOSWAlarmFirstLoopA  OBJECT-TYPE
        SYNTAX    PgTimeStamp
        ACCESS    read-only
        STATUS    mandatory
        DESCRIPTION
            "Date and time the Loss of Sync Word alarm first occurred 
             on Loop A of a span"
        ::= {hdslSpanAlarmHistoryEntry 21}

    hdslLOSWAlarmLastLoopA   OBJECT-TYPE
        SYNTAX    PgTimeStamp
        ACCESS    read-only
        STATUS    mandatory
        DESCRIPTION
            "Date and time the Loss of Sync Word alarm last occurred 
             on Loop A of a span"
        ::= {hdslSpanAlarmHistoryEntry 22}
 
    hdslLOSWAlarmCountLoopA  OBJECT-TYPE
        SYNTAX    INTEGER
        ACCESS    read-only
        STATUS    mandatory
        DESCRIPTION
            "The number of times the Loss of Sync Word alarm 
             has occurred on Loop A of a span."
        ::= {hdslSpanAlarmHistoryEntry 23}

    hdslLOSWAlarmFirstLoopB  OBJECT-TYPE
        SYNTAX    PgTimeStamp
        ACCESS    read-only
        STATUS    mandatory
        DESCRIPTION
            "Date and time the Loss of Sync Word alarm first occurred 
             on Loop B of a span"
        ::= {hdslSpanAlarmHistoryEntry 24}
 
    hdslLOSWAlarmLastLoopB  OBJECT-TYPE
        SYNTAX    PgTimeStamp
        ACCESS    read-only
        STATUS    mandatory
        DESCRIPTION
            "Date and time the Loss of Sync Word alarm last occurred 
             on Loop B of a span"
        ::= {hdslSpanAlarmHistoryEntry 25}
 
    hdslLOSWAlarmCountLoopB  OBJECT-TYPE
        SYNTAX    INTEGER
        ACCESS    read-only
        STATUS    mandatory
        DESCRIPTION
            "The number of times the Loss of Sync Word alarm 
             has occurred on Loop B of a span."
        ::= {hdslSpanAlarmHistoryEntry 26}

    hdslPFOAlarmFirstLoopA  OBJECT-TYPE
        SYNTAX    PgTimeStamp
        ACCESS    read-only
        STATUS    mandatory
        DESCRIPTION
            "Date and time the Power Feed Open alarm first occurred
             on Loop A of a span"
        ::= {hdslSpanAlarmHistoryEntry 27}
 
    hdslPFOAlarmLastLoopA OBJECT-TYPE
        SYNTAX    PgTimeStamp
        ACCESS    read-only
        STATUS    mandatory
        DESCRIPTION
            "Date and time the Power Feed Open alarm last occurred
             on Loop A of a span"
        ::= {hdslSpanAlarmHistoryEntry 28}
 
    hdslPFOAlarmCountLoopA OBJECT-TYPE
        SYNTAX    INTEGER
        ACCESS    read-only
        STATUS    mandatory
        DESCRIPTION
            "The number of times the Power Feed Open alarm
             has occurred on Loop A of a span."
        ::= {hdslSpanAlarmHistoryEntry 29}

    hdslPFOAlarmFirstLoopB OBJECT-TYPE
        SYNTAX    PgTimeStamp
        ACCESS    read-only
        STATUS    mandatory
        DESCRIPTION
            "Date and time the Power Feed Open alarm first occurred
             on Loop B of a span"
        ::= {hdslSpanAlarmHistoryEntry 30} 
 
    hdslPFOAlarmLastLoopB OBJECT-TYPE
        SYNTAX    PgTimeStamp
        ACCESS    read-only
        STATUS    mandatory
        DESCRIPTION
            "Date and time the Power Feed Open alarm last occurred
             on Loop B of a span"
        ::= {hdslSpanAlarmHistoryEntry 31}
 
    hdslPFOAlarmCountLoopB  OBJECT-TYPE
        SYNTAX    INTEGER
        ACCESS    read-only
        STATUS    mandatory
        DESCRIPTION
            "The number of times the Power Feed Open alarm
             has occurred on Loop B of a span."
        ::= {hdslSpanAlarmHistoryEntry 32}

    hdslPFSAlarmFirstLoopA  OBJECT-TYPE
        SYNTAX    PgTimeStamp
        ACCESS    read-only
        STATUS    mandatory
        DESCRIPTION
            "Date and time the Power Feed Short alarm first occurred
             on Loop A of a span"
        ::= {hdslSpanAlarmHistoryEntry 33}
 
    hdslPFSAlarmLastLoopA  OBJECT-TYPE
        SYNTAX    PgTimeStamp
        ACCESS    read-only
        STATUS    mandatory
        DESCRIPTION
            "Date and time the Power Feed Short alarm last occurred
             on Loop A of a span"
        ::= {hdslSpanAlarmHistoryEntry 34}
 
    hdslPFSAlarmCountLoopA  OBJECT-TYPE
        SYNTAX    INTEGER
        ACCESS    read-only
        STATUS    mandatory
        DESCRIPTION
            "The number of times the Power Feed Short alarm
             has occurred on Loop A of a span."
        ::= {hdslSpanAlarmHistoryEntry 35}

    hdslPFSAlarmFirstLoopB   OBJECT-TYPE
        SYNTAX    PgTimeStamp
        ACCESS    read-only
        STATUS    mandatory
        DESCRIPTION
            "Date and time the Power Feed Short alarm first occurred
             on Loop B of a span"
        ::= {hdslSpanAlarmHistoryEntry 36}
 
    hdslPFSAlarmLastLoopB  OBJECT-TYPE
        SYNTAX    PgTimeStamp
        ACCESS    read-only
        STATUS    mandatory
        DESCRIPTION
            "Date and time the Power Feed Short alarm last occurred
             on Loop B of a span"
        ::= {hdslSpanAlarmHistoryEntry 37}
 
    hdslPFSAlarmCountLoopB  OBJECT-TYPE
        SYNTAX    INTEGER
        ACCESS    read-only
        STATUS    mandatory
        DESCRIPTION
            "The number of times the Power Feed Short alarm
             has occurred on Loop B of a span."
        ::= {hdslSpanAlarmHistoryEntry 38}

    hdslBERAlarmFirstLoopA  OBJECT-TYPE
        SYNTAX    PgTimeStamp
        ACCESS    read-only
        STATUS    mandatory
        DESCRIPTION
            "Date and time the BER threshold exceeded alarm first occurred
             on Loop A of a span"
        ::= {hdslSpanAlarmHistoryEntry 39}
 
    hdslBERAlarmLastLoopA  OBJECT-TYPE
        SYNTAX    PgTimeStamp
        ACCESS    read-only
        STATUS    mandatory
        DESCRIPTION
            "Date and time the BER threshold exceeded alarm last occurred
             on Loop A of a span"
        ::= {hdslSpanAlarmHistoryEntry 40}
 
    hdslBERAlarmCountLoopA  OBJECT-TYPE
        SYNTAX    INTEGER
        ACCESS    read-only
        STATUS    mandatory
        DESCRIPTION
            "The number of times the BER threshold exceeded alarm
             has occurred on Loop A of a span."
        ::= {hdslSpanAlarmHistoryEntry 41}

    hdslBERAlarmFirstLoopB  OBJECT-TYPE
        SYNTAX    PgTimeStamp
        ACCESS    read-only
        STATUS    mandatory
        DESCRIPTION
            "Date and time the BER threshold exceeded alarm first occurred
             on Loop B of a span"
        ::= {hdslSpanAlarmHistoryEntry 42}
 
    hdslBERAlarmLastLoopB  OBJECT-TYPE
        SYNTAX    PgTimeStamp
        ACCESS    read-only
        STATUS    mandatory
        DESCRIPTION
            "Date and time the BER threshold exceeded alarm last occurred
             on Loop B of a span"
        ::= {hdslSpanAlarmHistoryEntry 43}
 
    hdslBERAlarmCountLoopB  OBJECT-TYPE
        SYNTAX    INTEGER
        ACCESS    read-only
        STATUS    mandatory
        DESCRIPTION
            "The number of times the BER threshold exceeded alarm
             has occurred on Loop B of a span."
        ::= {hdslSpanAlarmHistoryEntry 44}
 
----------------------------------------------------------
--- HDSL Span Alarm Severity Settings.
----------------------------------------------------------
    hdslSpanAlarmSeverityTable  OBJECT-TYPE
        SYNTAX    SEQUENCE OF HdslSpanAlarmSeverityEntry
        ACCESS    not-accessible
        STATUS    mandatory
        DESCRIPTION
            "The HDSL span alarm severity table provides severity settings
             for HDSL alarms reporting and threshold settings for 
             Errored Second(ES), Margin(MAR), Unavailable Seconds(UAS) and
             Bit Error Rate(BER)."
        ::= {pgainHDSL 7}

    hdslSpanAlarmSeverityEntry OBJECT-TYPE
        SYNTAX    HdslSpanAlarmSeverityEntry
        ACCESS    not-accessible
        STATUS    mandatory
        DESCRIPTION
            "Entry in the hdslSpanAlarmSeverityTable"
        INDEX
            {hdslSpanAlarmSeveritySlotId, hdslSpanAlarmSeveritySpanId}
        ::= { hdslSpanAlarmSeverityTable 1 }

    HdslSpanAlarmSeverityEntry ::= SEQUENCE {
        hdslSpanAlarmSeveritySlotId
            INTEGER,
        hdslSpanAlarmSeveritySpanId 
            INTEGER,
        hdslSpanLOSWAlarmSetting
            PgAlarmSeverityProtectionSwitchMode,
        hdslSpanPFOAlarmSetting
            PgAlarmSeverityMode,
        hdslSpanPFSAlarmSetting
            PgAlarmSeverityMode,
        hdslSpanMarginThreshold
            Byte,
        hdslSpanMarginAlarmSetting
            PgAlarmSeverityProtectionSwitchMode,
        hdslSpanESThreshold
            Byte,
        hdslSpanESAlarmSetting
            PgAlarmSeverityProtectionSwitchMode,
        hdslSpanUASThreshold
            Byte,
        hdslSpanUASAlarmSetting
            PgAlarmSeverityMode,
        hdslSpanBERThreshold
            PgBERThreshold,
        hdslSpanBERAlarmSetting
            PgAlarmSeverityMode
    }

    hdslSpanAlarmSeveritySlotId OBJECT-TYPE
        SYNTAX    INTEGER
        ACCESS    read-only
        STATUS    mandatory
        DESCRIPTION
            "The slot number of the HDSL loop whose
             alarm severity or threshold we are setting.
             The slots are numbered 1 through 16 from left to right."
        ::= {hdslSpanAlarmSeverityEntry 1}

    hdslSpanAlarmSeveritySpanId OBJECT-TYPE
        SYNTAX    INTEGER
        ACCESS    read-only
        STATUS    mandatory
        DESCRIPTION
            "The span number of the HDSL loop whose
             alarm severity or threshold we are setting.
             Depending on the number of regenerator(s) (REGs) 
             present in an HDSL loop, a span will be numbered as follows:
                 0 REG   - only 1 span.
                 1 REG   - span between LTU and REG is identified as 1.
                           span between REG and NTU is identified as 2.
                 2 REGs  - span between LTU and REG #1 is identified as 1.
                           span between REG #1 and REG #2 is identified as 2.
                           span between REG #2 and NTU is identified as 3.
             "
            ::= {hdslSpanAlarmSeverityEntry 2}

    hdslSpanLOSWAlarmSetting OBJECT-TYPE
        SYNTAX    PgAlarmSeverityProtectionSwitchMode
        ACCESS    read-write
        STATUS    mandatory
        DESCRIPTION
            "Sets the severity for Loss of Sync Word alarm."
        ::= {hdslSpanAlarmSeverityEntry 3}

    hdslSpanPFOAlarmSetting OBJECT-TYPE
        SYNTAX    PgAlarmSeverityMode
        ACCESS    read-write
        STATUS    mandatory
        DESCRIPTION
            "Sets the severity for Power Feed Open alarm."
        ::= {hdslSpanAlarmSeverityEntry 4}

    hdslSpanPFSAlarmSetting OBJECT-TYPE
        SYNTAX    PgAlarmSeverityMode
        ACCESS    read-write
        STATUS    mandatory
        DESCRIPTION
            "Sets the severity for Power Feed Short alarm."
        ::= {hdslSpanAlarmSeverityEntry 5}

    hdslSpanMarginThreshold  OBJECT-TYPE
        SYNTAX    Byte
        ACCESS    read-write
        STATUS    mandatory
        DESCRIPTION
            "Sets the HDSL Margin threshold value."
        ::= {hdslSpanAlarmSeverityEntry 6}

    hdslSpanMarginAlarmSetting OBJECT-TYPE
        SYNTAX    PgAlarmSeverityProtectionSwitchMode
        ACCESS    read-write
        STATUS    mandatory
        DESCRIPTION
            "Sets the severity for Margin threshold exceeded alarm."
        ::= {hdslSpanAlarmSeverityEntry 7}

    hdslSpanESThreshold OBJECT-TYPE
        SYNTAX    Byte
        ACCESS    read-write
        STATUS    mandatory
        DESCRIPTION
            "Sets the HDSL Errored Seconds threshold value."
        ::= {hdslSpanAlarmSeverityEntry 8}

    hdslSpanESAlarmSetting OBJECT-TYPE
        SYNTAX    PgAlarmSeverityProtectionSwitchMode
        ACCESS    read-write
        STATUS    mandatory
        DESCRIPTION
            "Sets the severity for Errored Seconds threshold exceeded alarm."
        ::= {hdslSpanAlarmSeverityEntry 9}

    hdslSpanUASThreshold OBJECT-TYPE
        SYNTAX    Byte
        ACCESS    read-write
        STATUS    mandatory
        DESCRIPTION
            "Sets the HDSL Unavailable Seconds threshold value."
        ::= {hdslSpanAlarmSeverityEntry 10}
 
    hdslSpanUASAlarmSetting OBJECT-TYPE
        SYNTAX    PgAlarmSeverityMode
        ACCESS    read-write
        STATUS    mandatory
        DESCRIPTION
            "Sets the severity for UAS threshold exceeded alarm."
        ::= {hdslSpanAlarmSeverityEntry 11}

    hdslSpanBERThreshold OBJECT-TYPE
            SYNTAX    PgBERThreshold 
            ACCESS    read-write
            STATUS    mandatory
            DESCRIPTION
                "Sets the HDSL BER threshold value."
            ::={hdslSpanAlarmSeverityEntry 12}
 
    hdslSpanBERAlarmSetting OBJECT-TYPE 
        SYNTAX    PgAlarmSeverityMode 
        ACCESS    read-write    
        STATUS    mandatory 
        DESCRIPTION 
            "Sets the severity for HDSL BER threshold exceeded alarm."
        ::= {hdslSpanAlarmSeverityEntry 13} 

END
