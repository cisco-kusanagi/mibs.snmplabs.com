CXVSHELL-MIB DEFINITIONS ::= BEGIN

--#CURRENT-VERSION 1


IMPORTS
	OBJECT-TYPE     FROM RFC-1212

-- Proprietary definitions:
	cxMc600         FROM CXProduct-SMI;

cxVShell OBJECT IDENTIFIER ::= { cxMc600 3 }


--  VCE CARD TO SLOT NUMBER ASSOCIATION.

voxCardsMapTable        OBJECT-TYPE
	SYNTAX  SEQUENCE  OF VoxCardsMapEntry
	ACCESS  not-accessible
	STATUS  mandatory
	DESCRIPTION
"Voice cards associations with I/O slots numbers.  The voice card number
corresponds to the slot number: voice card 1 is always associated with
slot number 1, voice card 2 is always associated with slot number 2 and
so on."
	::= { cxVShell 1 }

	voxCardsMapEntry        OBJECT-TYPE
		SYNTAX  VoxCardsMapEntry
		ACCESS  not-accessible
		STATUS  mandatory
		DESCRIPTION
"Each row associates a voice card number to an I/O slot number."
		INDEX { voxCardNo }
		::= { voxCardsMapTable 1 }

	VoxCardsMapEntry ::= 
		SEQUENCE {
			voxCardNo        INTEGER, 
			voxSlotNo        INTEGER,
			voxConnStatus    INTEGER,
			voxCardRowStatus INTEGER
		}

	voxCardNo               OBJECT-TYPE
		SYNTAX  INTEGER (1..8)
		ACCESS  read-only
		STATUS  mandatory
		DESCRIPTION
"Displays the voice I/O card number that is enabled.

Range of Values: a single digit from 1 to 8

Default Value: none"
		::= { voxCardsMapEntry 1 }

	voxSlotNo               OBJECT-TYPE
		SYNTAX  INTEGER (1..8)
		ACCESS  read-write
		STATUS  mandatory
		DESCRIPTION
"Determines the I/O slot number.

Range of Values: a single digit from 1 to 8

Default Value: none

Configuration Changed: administrative"
		::= { voxCardsMapEntry 2 }

	voxConnStatus   OBJECT-TYPE
		SYNTAX  INTEGER {
			    recorded-in-config(1),
			    failed(2),
			    connected(3)
			}
		ACCESS  read-only
		STATUS  mandatory
		DESCRIPTION

"Displays whether a voice I/O card-to-slot number association has been 
successful at the VCE layer.

Options:
recorded-in-config (1): configuration is correct but has not yet been 
implemeted. System reset required.

failed (2): configuration not performed correctly. The configuration may 
have the correct syntax but the change cannot be implemented at the VCE 
layer because there is no voice I/O card in the requested slot. If the 
requested slot is currently occupied by another kind of I/O card, for 
example an Ethernet card, the same result will occur.

connected (3): configuration performed properly and association made.

DefaultValue: none"
		::= { voxCardsMapEntry 3 }

	voxCardRowStatus        OBJECT-TYPE
		SYNTAX  INTEGER { invalid (1), valid (2) }
		ACCESS  read-write
		STATUS  mandatory
		DESCRIPTION
"Determines the status of the objects in a table row.

Options:
invalid (1): row is flagged; after the next reset the values will be 
disabled and the row will be deleted from the table.

valid (2): values are enabled.

DefaultValue: none

Configuration Changed: administrative"
		::= { voxCardsMapEntry 4 }


cxvshellMibLevel OBJECT-TYPE
   SYNTAX  INTEGER
   ACCESS  read-only
   STATUS  mandatory
   DESCRIPTION
"Used to determine current MIB module release supported
by the agent. Object is in decimal."
   DEFVAL { 0 }
   --#STARTING-VERSION 1
   ::= { cxVShell 2 }


END
