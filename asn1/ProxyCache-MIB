ProxyCache-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        proxyServer     OBJECT IDENTIFIER ::= { internetServer 11 }
        cacheStatistics OBJECT IDENTIFIER ::= { proxyServer 2 }

-- Proxy Cache Statistics
	urlsInCache OBJECT-TYPE
		SYNTAX	INTEGER
		ACCESS	read-only
		STATUS	mandatory
		DESCRIPTION 
			"The current number of URLs in the cache."
		::= { cacheStatistics 1 }

	totalMemoryBytesRetrieved OBJECT-TYPE
		SYNTAX	Counter
		ACCESS	read-only
		STATUS	mandatory
		DESCRIPTION 
			"The cumulative number of bytes that have been retrieved from the memory cache."
		::= { cacheStatistics 2 }

	totalDiskBytesRetrieved OBJECT-TYPE
		SYNTAX	Counter
		ACCESS	read-only
		STATUS	mandatory
		DESCRIPTION 
			"The cumulative number of bytes that have been retrieved from the disk cache."
		::= { cacheStatistics 3 }

	totalUrlsCached OBJECT-TYPE
		SYNTAX	Counter
		ACCESS	read-only
		STATUS	mandatory
		DESCRIPTION 
			"The cumulative number of URLs that have been stored in the cache."
		::= { cacheStatistics 4 }

	totalMemoryUrlsRetrieved OBJECT-TYPE
		SYNTAX	Counter
		ACCESS	read-only
		STATUS	mandatory
		DESCRIPTION 
			"The cumulative number of URLs that have been retrieved from the memory cache."
		::= { cacheStatistics 5 }

	totalDiskUrlsRetrieved OBJECT-TYPE
		SYNTAX	Counter
		ACCESS	read-only
		STATUS	mandatory
		DESCRIPTION 
			"The cumulative number of URLs that have been retrieved from the disk cache."
		::= { cacheStatistics 6 }

	maxUrlsCached OBJECT-TYPE
		SYNTAX	Counter
		ACCESS	read-only
		STATUS	mandatory
		DESCRIPTION 
			"The maximum number of URLs that have been stored in the cache."
		::= { cacheStatistics 7 }

	totalActiveRefreshes OBJECT-TYPE
		SYNTAX	Counter
		ACCESS	read-only
		STATUS	mandatory
		DESCRIPTION 
			"The cumulative number of popular URLs in the cache that have been actively refreshed from the Internet."
		::= { cacheStatistics 8 }

	totalActiveRefreshBytes OBJECT-TYPE
		SYNTAX	Counter
		ACCESS	read-only
		STATUS	mandatory
		DESCRIPTION 
			"The total bytes retrieved from the Internet to actively refresh popular URLs in the cache."
		::= { cacheStatistics 9 }

	totalDiskFailures OBJECT-TYPE
		SYNTAX	Counter
		ACCESS	read-only
		STATUS	mandatory
		DESCRIPTION 
			"The number of times that ISA Server failed to read from or write to disk cache, due to an I/O failure, since the Web Proxy service started."
		::= { cacheStatistics 10 }

	diskFailuresRate OBJECT-TYPE
		SYNTAX	Counter
		ACCESS	read-only
		STATUS	mandatory
		DESCRIPTION 
			"The number of I/O failures per second. An I/O failure occurs when ISA Server fails to read from or write to disk cache."
		::= { cacheStatistics 11 }

	memoryCacheAllocatedSpace OBJECT-TYPE
		SYNTAX	Counter
		ACCESS	read-only
		STATUS	mandatory
		DESCRIPTION 
			"The amount of space being used for the memory cache, from the memory allocated for memory caching."
		::= { cacheStatistics 12 }

	diskCacheAllocatedSpaceSum OBJECT-TYPE
		SYNTAX	Counter
		ACCESS	read-only
		STATUS	mandatory
		DESCRIPTION 
			"The amount of space being used for the disk cache, from the disk space allocated for disk caching."
		::= { cacheStatistics 13 }

	memoryUsageRatioPercent OBJECT-TYPE
		SYNTAX	Counter
		ACCESS	read-only
		STATUS	mandatory
		DESCRIPTION 
			"The amount of memory cache fetches, in proportion to total cache fetches."
		::= { cacheStatistics 14 }

	contentDiskWritesRate OBJECT-TYPE
		SYNTAX	Counter
		ACCESS	read-only
		STATUS	mandatory
		DESCRIPTION 
			"The amount of writes of content to the disk cache, per second."
		::= { cacheStatistics 15 }

	memoryRetrieves OBJECT-TYPE
		SYNTAX	Counter
		ACCESS	read-only
		STATUS	mandatory
		DESCRIPTION 
			"The rate at which URLs are retrieved from the memory cache."
		::= { cacheStatistics 16 }

	diskRetrieves OBJECT-TYPE
		SYNTAX	Counter
		ACCESS	read-only
		STATUS	mandatory
		DESCRIPTION 
			"The rate at which URLs are retrieved from the disk cache."
		::= { cacheStatistics 17 }

	memoryRetrieveBytes OBJECT-TYPE
		SYNTAX	Counter
		ACCESS	read-only
		STATUS	mandatory
		DESCRIPTION 
			"The rate at which bytes of data are retrieved from the memory cache."
		::= { cacheStatistics 18 }

	diskRetrieveBytes OBJECT-TYPE
		SYNTAX	Counter
		ACCESS	read-only
		STATUS	mandatory
		DESCRIPTION 
			"The rate at which bytes of data are retrieved from the disk cache."
		::= { cacheStatistics 19 }

	commits OBJECT-TYPE
		SYNTAX	Counter
		ACCESS	read-only
		STATUS	mandatory
		DESCRIPTION 
			"The rate at which URLs are committed to the cache."
		::= { cacheStatistics 20 }

	activeRefreshes OBJECT-TYPE
		SYNTAX	Counter
		ACCESS	read-only
		STATUS	mandatory
		DESCRIPTION 
			"The rate at which popular URLs in the cache are actively refreshed from the Internet."
		::= { cacheStatistics 21 }

	activeRefreshBytes OBJECT-TYPE
		SYNTAX	Counter
		ACCESS	read-only
		STATUS	mandatory
		DESCRIPTION 
			"The rate at which bytes of data are retrieved from the Internet to actively refresh popular URLs in the cache."
		::= { cacheStatistics 22 }


END
