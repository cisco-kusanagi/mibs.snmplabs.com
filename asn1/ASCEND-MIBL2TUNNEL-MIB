--			Ascend mibl2tunnel MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBL2TUNNEL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibtunnelServer  OBJECT IDENTIFIER ::= { configuration 91}
    mibl2TunnelGlobal  OBJECT IDENTIFIER ::= { configuration 90}

	-- The mibtunnelServer table
	--
	-- This table contains parameters for the mibtunnelServer profile
	--

    mibtunnelServerTable	OBJECT-TYPE
	SYNTAX		SEQUENCE OF MibtunnelServerEntry
	ACCESS		not-accessible
	STATUS		mandatory
	DESCRIPTION	"A list of mibtunnelServer profile entries."
	::= { mibtunnelServer 1 }

    mibtunnelServerEntry	OBJECT-TYPE
	SYNTAX		MibtunnelServerEntry
	ACCESS		not-accessible
	STATUS		mandatory
	DESCRIPTION	"A mibtunnelServer entry containing objects that
			 maps to the parameters of mibtunnelServer profile."
	INDEX		{ tunnelServer-ServerEndpoint }
	::= { mibtunnelServerTable 1 }

    MibtunnelServerEntry ::=
	SEQUENCE {
	    tunnelServer-ServerEndpoint
		DisplayString,
	    tunnelServer-Enabled
		INTEGER,
	    tunnelServer-SharedSecret
		DisplayString,
	    tunnelServer-MaxClients
		INTEGER,
	    tunnelServer-ValidCallTypes
		INTEGER,
	    tunnelServer-IpsecProfile
		DisplayString,
	    tunnelServer-ClientAuthId
		DisplayString,
	    tunnelServer-ServerAuthId
		DisplayString,
	    tunnelServer-DialoutOptions-Enabled
		INTEGER,
	    tunnelServer-DialoutOptions-DialNumberLookup
		INTEGER,
	    tunnelServer-DialoutOptions-LookupPrefix
		DisplayString,
	    tunnelServer-DialoutOptions-DialNumberPrefix
		DisplayString,
	    tunnelServer-Action-o
		INTEGER
	}

    tunnelServer-ServerEndpoint	OBJECT-TYPE
	SYNTAX	DisplayString
	ACCESS	read-only
	STATUS	mandatory
	DESCRIPTION	"The name of the remote tunnel endpoint. It should be the hostname or IP address that identifies the remote tunnel server, as required by the specific tunnel protocol. Usually, it matches the 'Tunnel-Server-Endpoint' RADIUS attribute but it may be different."
	::= { mibtunnelServerEntry 1 }

    tunnelServer-Enabled	OBJECT-TYPE
	SYNTAX	INTEGER {
		    no (1),
		    yes (2)
		}
	ACCESS	read-write
	STATUS	mandatory
	DESCRIPTION	"A tunnel server can be disabled by setting this field to 'no'."
	::= { mibtunnelServerEntry 2 }

    tunnelServer-SharedSecret	OBJECT-TYPE
	SYNTAX	DisplayString
	ACCESS	read-write
	STATUS	mandatory
	DESCRIPTION	"The shared secret (password) needed to bring up an L2TP Control Channel or an L2F tunnel with this server."
	::= { mibtunnelServerEntry 3 }

    tunnelServer-MaxClients	OBJECT-TYPE
	SYNTAX	INTEGER
	ACCESS	read-write
	STATUS	mandatory
	DESCRIPTION	"The maximum number of clients that this tunnel may carry."
	::= { mibtunnelServerEntry 4 }

    tunnelServer-ValidCallTypes	OBJECT-TYPE
	SYNTAX	INTEGER {
		    allCalls (1),
		    analogCalls (2),
		    digitalCalls (3)
		}
	ACCESS	read-write
	STATUS	mandatory
	DESCRIPTION	"The valid call types that can be carried on this tunnel."
	::= { mibtunnelServerEntry 5 }

    tunnelServer-IpsecProfile	OBJECT-TYPE
	SYNTAX	DisplayString
	ACCESS	read-write
	STATUS	mandatory
	DESCRIPTION	"Name of the ipsec profile which should be used to build the IPSec Scheme for the IP Packets sent and received from this server."
	::= { mibtunnelServerEntry 6 }

    tunnelServer-ClientAuthId	OBJECT-TYPE
	SYNTAX	DisplayString
	ACCESS	read-write
	STATUS	mandatory
	DESCRIPTION	"The system name used by the Tunnel Initiator during Tunnel establishment for the purposes of tunnel authentication. This is different and independent from user authentication. In L2TP, this name is sent on the SCCRQ command. Used on L2TP and L2F."
	::= { mibtunnelServerEntry 7 }

    tunnelServer-ServerAuthId	OBJECT-TYPE
	SYNTAX	DisplayString
	ACCESS	read-write
	STATUS	mandatory
	DESCRIPTION	"The system name used by the Tunnel Terminator during Tunnel establishment for the purposes of tunnel authentication. This is different and independent from user authentication. In L2TP, this name is sent on the SCCRP command. Used on L2TP and L2F."
	::= { mibtunnelServerEntry 8 }

    tunnelServer-DialoutOptions-Enabled	OBJECT-TYPE
	SYNTAX	INTEGER {
		    no (1),
		    yes (2)
		}
	ACCESS	read-write
	STATUS	mandatory
	DESCRIPTION	"Enables/Disables L2TP Dialout from this tunnel-server."
	::= { mibtunnelServerEntry 9 }

    tunnelServer-DialoutOptions-DialNumberLookup	OBJECT-TYPE
	SYNTAX	INTEGER {
		    no (1),
		    yes (2)
		}
	ACCESS	read-write
	STATUS	mandatory
	DESCRIPTION	"If enabled, uses the dial number passed by the LNS to lookup a connection profile."
	::= { mibtunnelServerEntry 17 }

    tunnelServer-DialoutOptions-LookupPrefix	OBJECT-TYPE
	SYNTAX	DisplayString
	ACCESS	read-write
	STATUS	mandatory
	DESCRIPTION	"A short text string prepended to the username portion of a RADIUS L2TP dial number lookup request. It is used to distinguish between DNIS and CLID authentication requests and L2TP lookup request."
	::= { mibtunnelServerEntry 18 }

    tunnelServer-DialoutOptions-DialNumberPrefix	OBJECT-TYPE
	SYNTAX	DisplayString
	ACCESS	read-write
	STATUS	mandatory
	DESCRIPTION	"A number to be prepended to the dialout number when placing the call. It can be used to provide locally required prefixes such as trunk numbers."
	::= { mibtunnelServerEntry 19 }

    tunnelServer-Action-o	OBJECT-TYPE
	SYNTAX	INTEGER {
		    noAction (1),
		    createProfile (2),
		    deleteProfile (3)
		}
	ACCESS	read-write
	STATUS	mandatory
	DESCRIPTION	""
	::= { mibtunnelServerEntry 16 }


	-- The mibtunnelServer__dialout_options__default_call_mapping table
	--
	-- This table contains parameters for the mibtunnelServer__dialout_options__default_call_mapping profile
	--

    mibtunnelServer-DialoutOptions-DefaultCallMappingTable	OBJECT-TYPE
	SYNTAX		SEQUENCE OF MibtunnelServer-DialoutOptions-DefaultCallMappingEntry
	ACCESS		not-accessible
	STATUS		mandatory
	DESCRIPTION	"A list of mibtunnelServer__dialout_options__default_call_mapping profile entries."
	::= { mibtunnelServer 2 }

    mibtunnelServer-DialoutOptions-DefaultCallMappingEntry	OBJECT-TYPE
	SYNTAX		MibtunnelServer-DialoutOptions-DefaultCallMappingEntry
	ACCESS		not-accessible
	STATUS		mandatory
	DESCRIPTION	"A mibtunnelServer__dialout_options__default_call_mapping entry containing objects that
			 maps to the parameters of mibtunnelServer__dialout_options__default_call_mapping profile."
	INDEX		{ tunnelServer-DialoutOptions-DefaultCallMapping-ServerEndpoint, tunnelServer-DialoutOptions-DefaultCallMapping-Index-o }
	::= { mibtunnelServer-DialoutOptions-DefaultCallMappingTable 1 }

    MibtunnelServer-DialoutOptions-DefaultCallMappingEntry ::=
	SEQUENCE {
	    tunnelServer-DialoutOptions-DefaultCallMapping-ServerEndpoint
		DisplayString,
	    tunnelServer-DialoutOptions-DefaultCallMapping-Index-o
		INTEGER,
	    tunnelServer-DialoutOptions-DefaultCallMapping-ValidEntry
		INTEGER,
	    tunnelServer-DialoutOptions-DefaultCallMapping-BearerType
		INTEGER,
	    tunnelServer-DialoutOptions-DefaultCallMapping-FramingType
		INTEGER,
	    tunnelServer-DialoutOptions-DefaultCallMapping-DataService
		INTEGER
	}

    tunnelServer-DialoutOptions-DefaultCallMapping-ServerEndpoint	OBJECT-TYPE
	SYNTAX	DisplayString
	ACCESS	read-only
	STATUS	mandatory
	DESCRIPTION	""
	::= { mibtunnelServer-DialoutOptions-DefaultCallMappingEntry 1 }

    tunnelServer-DialoutOptions-DefaultCallMapping-Index-o	OBJECT-TYPE
	SYNTAX	INTEGER
	ACCESS	read-only
	STATUS	mandatory
	DESCRIPTION	""
	::= { mibtunnelServer-DialoutOptions-DefaultCallMappingEntry 2 }

    tunnelServer-DialoutOptions-DefaultCallMapping-ValidEntry	OBJECT-TYPE
	SYNTAX	INTEGER {
		    no (1),
		    yes (2)
		}
	ACCESS	read-write
	STATUS	mandatory
	DESCRIPTION	"When FALSE, this entry should be skipped when mapping calls."
	::= { mibtunnelServer-DialoutOptions-DefaultCallMappingEntry 3 }

    tunnelServer-DialoutOptions-DefaultCallMapping-BearerType	OBJECT-TYPE
	SYNTAX	INTEGER {
		    any (4),
		    digital (2),
		    analog (3)
		}
	ACCESS	read-write
	STATUS	mandatory
	DESCRIPTION	"The bearer type used for the outgoing call."
	::= { mibtunnelServer-DialoutOptions-DefaultCallMappingEntry 4 }

    tunnelServer-DialoutOptions-DefaultCallMapping-FramingType	OBJECT-TYPE
	SYNTAX	INTEGER {
		    any (4),
		    sync (2),
		    async (3)
		}
	ACCESS	read-write
	STATUS	mandatory
	DESCRIPTION	"The framing type used for the outgoing call."
	::= { mibtunnelServer-DialoutOptions-DefaultCallMappingEntry 5 }

    tunnelServer-DialoutOptions-DefaultCallMapping-DataService	OBJECT-TYPE
	SYNTAX	INTEGER {
		    voice (1),
		    n-56kRestricted (2),
		    n-64kClear (3),
		    n-64kRestricted (4),
		    n-56kClear (5),
		    n-384kRestricted (6),
		    n-384kClear (7),
		    n-1536kClear (8),
		    n-1536kRestricted (9),
		    n-128kClear (10),
		    n-192kClear (11),
		    n-256kClear (12),
		    n-320kClear (13),
		    dws384Clear (14),
		    n-448Clear (15),
		    n-512Clear (16),
		    n-576Clear (17),
		    n-640Clear (18),
		    n-704Clear (19),
		    n-768Clear (20),
		    n-832Clear (21),
		    n-896Clear (22),
		    n-960Clear (23),
		    n-1024Clear (24),
		    n-1088Clear (25),
		    n-1152Clear (26),
		    n-1216Clear (27),
		    n-1280Clear (28),
		    n-1344Clear (29),
		    n-1408Clear (30),
		    n-1472Clear (31),
		    n-1600Clear (32),
		    n-1664Clear (33),
		    n-1728Clear (34),
		    n-1792Clear (35),
		    n-1856Clear (36),
		    n-1920Clear (37),
		    x30RestrictedBearer (39),
		    v110ClearBearer (40),
		    n-64kX30Restricted (41),
		    n-56kV110Clear (42),
		    modem (43),
		    atmodem (44),
		    n-2456kV110 (46),
		    n-4856kV110 (47),
		    n-9656kV110 (48),
		    n-19256kV110 (49),
		    n-38456kV110 (50),
		    n-2456krV110 (51),
		    n-4856krV110 (52),
		    n-9656krV110 (53),
		    n-19256krV110 (54),
		    n-38456krV110 (55),
		    n-2464kV110 (56),
		    n-4864kV110 (57),
		    n-9664kV110 (58),
		    n-19264kV110 (59),
		    n-38464kV110 (60),
		    n-2464krV110 (61),
		    n-4864krV110 (62),
		    n-9664krV110 (63),
		    n-19264krV110 (64),
		    n-38464krV110 (65),
		    v32 (66),
		    phs64k (67),
		    voiceOverIp (68),
		    atmSvc (70),
		    frameRelaySvc (71),
		    vpnTunnel (72),
		    wormarq (73),
		    n-14456kV110 (74),
		    n-28856kV110 (75),
		    n-14456krV110 (76),
		    n-28856krV110 (77),
		    n-14464kV110 (78),
		    n-28864kV110 (79),
		    n-14464krV110 (80),
		    n-28864krV110 (81),
		    modem31khzAudio (82),
		    x25Svc (83),
		    n-144kClear (255),
		    iptoip (263)
		}
	ACCESS	read-write
	STATUS	mandatory
	DESCRIPTION	"The type of data service used for outgoing call for this bearer and framing type combination."
	::= { mibtunnelServer-DialoutOptions-DefaultCallMappingEntry 6 }


	-- The mibl2TunnelGlobal table
	--
	-- This table contains parameters for the mibl2TunnelGlobal profile
	--

    mibl2TunnelGlobalTable	OBJECT-TYPE
	SYNTAX		SEQUENCE OF Mibl2TunnelGlobalEntry
	ACCESS		not-accessible
	STATUS		mandatory
	DESCRIPTION	"A list of mibl2TunnelGlobal profile entries."
	::= { mibl2TunnelGlobal 1 }

    mibl2TunnelGlobalEntry	OBJECT-TYPE
	SYNTAX		Mibl2TunnelGlobalEntry
	ACCESS		not-accessible
	STATUS		mandatory
	DESCRIPTION	"A mibl2TunnelGlobal entry containing objects that
			 maps to the parameters of mibl2TunnelGlobal profile."
	INDEX		{ l2TunnelGlobal-Index-o }
	::= { mibl2TunnelGlobalTable 1 }

    Mibl2TunnelGlobalEntry ::=
	SEQUENCE {
	    l2TunnelGlobal-Index-o
		INTEGER,
	    l2TunnelGlobal-PptpEnabled
		INTEGER,
	    l2TunnelGlobal-ServerProfileRequired
		INTEGER,
	    l2TunnelGlobal-L2tpMode
		INTEGER,
	    l2TunnelGlobal-L2tpAuthEnabled
		INTEGER,
	    l2TunnelGlobal-L2tpRxWindow
		INTEGER,
	    l2TunnelGlobal-MaxLnsClients
		INTEGER,
	    l2TunnelGlobal-L2tpSystemName
		DisplayString,
	    l2TunnelGlobal-L2tpConfig-RetryTimerMode
		INTEGER,
	    l2TunnelGlobal-L2tpConfig-FirstRetryTimer
		INTEGER,
	    l2TunnelGlobal-L2tpConfig-MaxRetryTimer
		INTEGER,
	    l2TunnelGlobal-L2tpConfig-RetryCount
		INTEGER,
	    l2TunnelGlobal-L2tpConfig-HelloTimer
		INTEGER,
	    l2TunnelGlobal-L2tpConfig-ControlConnectEstablishTimer
		INTEGER,
	    l2TunnelGlobal-L2tpConfig-LacIncomingCallTimer
		INTEGER,
	    l2TunnelGlobal-L2tpConfig-LnsIncomingCallTimer
		INTEGER,
	    l2TunnelGlobal-L2tpConfig-BaseUdpPort
		INTEGER,
	    l2TunnelGlobal-L2tpConfig-DataPktUdpCksum
		INTEGER,
	    l2TunnelGlobal-L2tpConfig-DialoutAuthLns
		INTEGER,
	    l2TunnelGlobal-L2tpConfig-DialoutSendProfileName
		INTEGER,
	    l2TunnelGlobal-L2tpConfig-VerifyRemoteHostName
		INTEGER,
	    l2TunnelGlobal-L2tpConfig-AcctTunnelConnectionEncoding
		INTEGER,
	    l2TunnelGlobal-L2tpConfig-DefaultTunnelServer
		DisplayString,
	    l2TunnelGlobal-L2tpConfig-TunnelServerPreSccrqLookup
		INTEGER,
	    l2TunnelGlobal-L2tpConfig-SuppressEndpointDiscriminator
		INTEGER,
	    l2TunnelGlobal-L2tpConfig-MaxCallsPerTunnel
		INTEGER,
	    l2TunnelGlobal-L2tpConfig-LnsNasPortType
		INTEGER,
	    l2TunnelGlobal-L2tpConfig-DigitalAsyncNasPortType
		INTEGER,
	    l2TunnelGlobal-L2fMode
		INTEGER,
	    l2TunnelGlobal-L2fSystemName
		DisplayString,
	    l2TunnelGlobal-L2fRetryCount
		INTEGER,
	    l2TunnelGlobal-L2fRetryInterval
		INTEGER,
	    l2TunnelGlobal-L2fTunnelSecret
		INTEGER,
	    l2TunnelGlobal-L2fIgnoreMidSequence
		INTEGER,
	    l2TunnelGlobal-Action-o
		INTEGER
	}

    l2TunnelGlobal-Index-o	OBJECT-TYPE
	SYNTAX	INTEGER
	ACCESS	read-only
	STATUS	mandatory
	DESCRIPTION	""
	::= { mibl2TunnelGlobalEntry 1 }

    l2TunnelGlobal-PptpEnabled	OBJECT-TYPE
	SYNTAX	INTEGER {
		    no (1),
		    yes (2)
		}
	ACCESS	read-write
	STATUS	mandatory
	DESCRIPTION	"Enables or disables support for the Point to Point Tunneling Protocol (PPTP)."
	::= { mibl2TunnelGlobalEntry 2 }

    l2TunnelGlobal-ServerProfileRequired	OBJECT-TYPE
	SYNTAX	INTEGER {
		    no (1),
		    yes (2)
		}
	ACCESS	read-write
	STATUS	mandatory
	DESCRIPTION	"When set to 'YES', it requires that an enabled TUNNEL-SERVER profile exists before a tunnel is created. When set to 'NO', if a matching profile can't be found, the server is assumed enabled and the tunnel can be created."
	::= { mibl2TunnelGlobalEntry 3 }

    l2TunnelGlobal-L2tpMode	OBJECT-TYPE
	SYNTAX	INTEGER {
		    disabled (1),
		    lac (2),
		    lns (3),
		    lacAndLns (4)
		}
	ACCESS	read-write
	STATUS	mandatory
	DESCRIPTION	"Layer 2 Tunneling Protocol operating mode."
	::= { mibl2TunnelGlobalEntry 4 }

    l2TunnelGlobal-L2tpAuthEnabled	OBJECT-TYPE
	SYNTAX	INTEGER {
		    no (1),
		    yes (2)
		}
	ACCESS	read-write
	STATUS	mandatory
	DESCRIPTION	"Enables or disables L2TP tunnel authentication."
	::= { mibl2TunnelGlobalEntry 5 }

    l2TunnelGlobal-L2tpRxWindow	OBJECT-TYPE
	SYNTAX	INTEGER
	ACCESS	read-write
	STATUS	mandatory
	DESCRIPTION	"This value is the advertised L2TP receive window size for the data channel. A value of zero indicates that this box will ask for no flow control for inbound L2TP payloads."
	::= { mibl2TunnelGlobalEntry 6 }

    l2TunnelGlobal-MaxLnsClients	OBJECT-TYPE
	SYNTAX	INTEGER
	ACCESS	read-write
	STATUS	mandatory
	DESCRIPTION	"The maximum number of clients that this box is allowed to support in LNS mode."
	::= { mibl2TunnelGlobalEntry 7 }

    l2TunnelGlobal-L2tpSystemName	OBJECT-TYPE
	SYNTAX	DisplayString
	ACCESS	read-write
	STATUS	mandatory
	DESCRIPTION	"Sent to the remote tunnel endpoint during L2TP session establishment. An empty string indicates that the actual system name plus domain name will be used."
	::= { mibl2TunnelGlobalEntry 8 }

    l2TunnelGlobal-L2tpConfig-RetryTimerMode	OBJECT-TYPE
	SYNTAX	INTEGER {
		    linear (1),
		    exponential (2)
		}
	ACCESS	read-write
	STATUS	mandatory
	DESCRIPTION	"The mode in which the L2TP Control Channel Transport Layer retry timer operates. The default is Linear."
	::= { mibl2TunnelGlobalEntry 33 }

    l2TunnelGlobal-L2tpConfig-FirstRetryTimer	OBJECT-TYPE
	SYNTAX	INTEGER
	ACCESS	read-write
	STATUS	mandatory
	DESCRIPTION	"The first interval before the L2TP Control Channel Transport Layer retransmits a control packet, in milliseconds. Subsequent retransmissions will increase the interval."
	::= { mibl2TunnelGlobalEntry 9 }

    l2TunnelGlobal-L2tpConfig-MaxRetryTimer	OBJECT-TYPE
	SYNTAX	INTEGER
	ACCESS	read-write
	STATUS	mandatory
	DESCRIPTION	"The maximum timeout interval used by the L2TP Control Channel Transport Layer before retransmitting a packet, in milliseconds. 0 indicates no limit."
	::= { mibl2TunnelGlobalEntry 34 }

    l2TunnelGlobal-L2tpConfig-RetryCount	OBJECT-TYPE
	SYNTAX	INTEGER
	ACCESS	read-write
	STATUS	mandatory
	DESCRIPTION	"The maximum number of times the L2TP Control Channel Transport Layer will retransmit a control packet."
	::= { mibl2TunnelGlobalEntry 10 }

    l2TunnelGlobal-L2tpConfig-HelloTimer	OBJECT-TYPE
	SYNTAX	INTEGER
	ACCESS	read-write
	STATUS	mandatory
	DESCRIPTION	"The number of seconds that an L2TP Control Channel will be idle before sending a HELLO packet. If set to 0, HELLO packets will not be sent."
	::= { mibl2TunnelGlobalEntry 11 }

    l2TunnelGlobal-L2tpConfig-ControlConnectEstablishTimer	OBJECT-TYPE
	SYNTAX	INTEGER
	ACCESS	read-write
	STATUS	mandatory
	DESCRIPTION	"The timeout interval for L2TP to establish a control connection session with its peer, in seconds."
	::= { mibl2TunnelGlobalEntry 12 }

    l2TunnelGlobal-L2tpConfig-LacIncomingCallTimer	OBJECT-TYPE
	SYNTAX	INTEGER
	ACCESS	read-write
	STATUS	mandatory
	DESCRIPTION	"The timeout interval for the LAC to setup an incoming call with the LNS, in seconds."
	::= { mibl2TunnelGlobalEntry 13 }

    l2TunnelGlobal-L2tpConfig-LnsIncomingCallTimer	OBJECT-TYPE
	SYNTAX	INTEGER
	ACCESS	read-write
	STATUS	mandatory
	DESCRIPTION	"The timeout interval for the LNS to setup an incoming call with the LAC, in seconds."
	::= { mibl2TunnelGlobalEntry 14 }

    l2TunnelGlobal-L2tpConfig-BaseUdpPort	OBJECT-TYPE
	SYNTAX	INTEGER
	ACCESS	read-write
	STATUS	mandatory
	DESCRIPTION	"This value defines the base L2TP udp port to use for a card. A value of zero (the default) means that a non private port will be allocated dynamically."
	::= { mibl2TunnelGlobalEntry 15 }

    l2TunnelGlobal-L2tpConfig-DataPktUdpCksum	OBJECT-TYPE
	SYNTAX	INTEGER {
		    no (1),
		    yes (2)
		}
	ACCESS	read-write
	STATUS	mandatory
	DESCRIPTION	"If IP-GLOBAL:udp-cksum is set to TRUE, setting this field to 'no' disables the locally originated UDP checksum calculation for L2TP data packets."
	::= { mibl2TunnelGlobalEntry 35 }

    l2TunnelGlobal-L2tpConfig-DialoutAuthLns	OBJECT-TYPE
	SYNTAX	INTEGER {
		    no (1),
		    yes (2)
		}
	ACCESS	read-write
	STATUS	mandatory
	DESCRIPTION	"Restricts the LAC to accept dialout requests only from the LNS which has authenticated during the tunnel setup."
	::= { mibl2TunnelGlobalEntry 16 }

    l2TunnelGlobal-L2tpConfig-DialoutSendProfileName	OBJECT-TYPE
	SYNTAX	INTEGER {
		    no (1),
		    yes (2)
		}
	ACCESS	read-write
	STATUS	mandatory
	DESCRIPTION	"Enables the LNS to send the Connection Profile Name VSA along with the Dialout Request."
	::= { mibl2TunnelGlobalEntry 17 }

    l2TunnelGlobal-L2tpConfig-VerifyRemoteHostName	OBJECT-TYPE
	SYNTAX	INTEGER {
		    no (1),
		    yes (2)
		}
	ACCESS	read-write
	STATUS	mandatory
	DESCRIPTION	"If Tunnel Authentication is enabled, also verify the remote peer HostName AVP."
	::= { mibl2TunnelGlobalEntry 27 }

    l2TunnelGlobal-L2tpConfig-AcctTunnelConnectionEncoding	OBJECT-TYPE
	SYNTAX	INTEGER {
		    normal (1),
		    decimalCallSerialNumber (2),
		    hexadecimalCallSerialNumber (3)
		}
	ACCESS	read-write
	STATUS	mandatory
	DESCRIPTION	"Encoding of the Acct-Tunnel-Connection radius attribute"
	::= { mibl2TunnelGlobalEntry 18 }

    l2TunnelGlobal-L2tpConfig-DefaultTunnelServer	OBJECT-TYPE
	SYNTAX	DisplayString
	ACCESS	read-write
	STATUS	mandatory
	DESCRIPTION	"Default tunnel server profile name. Used for dialout only."
	::= { mibl2TunnelGlobalEntry 28 }

    l2TunnelGlobal-L2tpConfig-TunnelServerPreSccrqLookup	OBJECT-TYPE
	SYNTAX	INTEGER {
		    no (1),
		    yes (2)
		}
	ACCESS	read-write
	STATUS	mandatory
	DESCRIPTION	"When Tunnel Authentication is enabled, this parameter controls whether a lookup is to be done for the Tunnel-Server profile before sending of the SCCRQ."
	::= { mibl2TunnelGlobalEntry 29 }

    l2TunnelGlobal-L2tpConfig-SuppressEndpointDiscriminator	OBJECT-TYPE
	SYNTAX	INTEGER {
		    no (1),
		    yes (2)
		}
	ACCESS	read-write
	STATUS	mandatory
	DESCRIPTION	"When set to 'yes', in the absence of a MRRU LCP option, the LAC will suppress the Endpoint Discriminator LCP option from the LCP AVPs sent to the LNS."
	::= { mibl2TunnelGlobalEntry 30 }

    l2TunnelGlobal-L2tpConfig-MaxCallsPerTunnel	OBJECT-TYPE
	SYNTAX	INTEGER
	ACCESS	read-write
	STATUS	mandatory
	DESCRIPTION	"This value restricts the maximum number of calls that a tunnel can have at a given instance of time. When set to 0 the limit is removed."
	::= { mibl2TunnelGlobalEntry 36 }

    l2TunnelGlobal-L2tpConfig-LnsNasPortType	OBJECT-TYPE
	SYNTAX	INTEGER {
		    virtual (1),
		    portTypeAvp (2)
		}
	ACCESS	read-write
	STATUS	mandatory
	DESCRIPTION	"LNS NAS Port Type reporting. If Virtual, report virtual. If PortTypeAvp, report as specified by LAC."
	::= { mibl2TunnelGlobalEntry 31 }

    l2TunnelGlobal-L2tpConfig-DigitalAsyncNasPortType	OBJECT-TYPE
	SYNTAX	INTEGER {
		    v120 (3),
		    v110 (4)
		}
	ACCESS	read-write
	STATUS	mandatory
	DESCRIPTION	"If LNS Acct NPT is set to PortTypeAvp but the LAC did not supply the NAS Port Type, report digital-async calls as specified here."
	::= { mibl2TunnelGlobalEntry 32 }

    l2TunnelGlobal-L2fMode	OBJECT-TYPE
	SYNTAX	INTEGER {
		    disabled (1),
		    nas (2),
		    gw (3),
		    nasAndGw (4)
		}
	ACCESS	read-write
	STATUS	mandatory
	DESCRIPTION	"Layer Two Forwarding operating mode."
	::= { mibl2TunnelGlobalEntry 20 }

    l2TunnelGlobal-L2fSystemName	OBJECT-TYPE
	SYNTAX	DisplayString
	ACCESS	read-write
	STATUS	mandatory
	DESCRIPTION	"Sent to the remote tunnel endpoint during L2F tunnel establishment. An empty string indicates that the actual system name plus domain name will be used."
	::= { mibl2TunnelGlobalEntry 21 }

    l2TunnelGlobal-L2fRetryCount	OBJECT-TYPE
	SYNTAX	INTEGER
	ACCESS	read-write
	STATUS	mandatory
	DESCRIPTION	"The number of times L2F will resend control packets. The standard value as outlined in RFC2341 is 4."
	::= { mibl2TunnelGlobalEntry 22 }

    l2TunnelGlobal-L2fRetryInterval	OBJECT-TYPE
	SYNTAX	INTEGER
	ACCESS	read-write
	STATUS	mandatory
	DESCRIPTION	"The interval between retries in seconds. A value of 0 (zero) means that an adaptative retry interval based on the retry number is used."
	::= { mibl2TunnelGlobalEntry 23 }

    l2TunnelGlobal-L2fTunnelSecret	OBJECT-TYPE
	SYNTAX	INTEGER {
		    sharedTunnelSecret (1),
		    distinctTunnelSecrets (2),
		    eitherSharedOrDistinctTunnelSecret (3)
		}
	ACCESS	read-write
	STATUS	mandatory
	DESCRIPTION	"The authentication method used on the NAS to authenticate the home Gateway during L2F Tunnel establishment."
	::= { mibl2TunnelGlobalEntry 24 }

    l2TunnelGlobal-L2fIgnoreMidSequence	OBJECT-TYPE
	SYNTAX	INTEGER {
		    no (1),
		    yes (2)
		}
	ACCESS	read-write
	STATUS	mandatory
	DESCRIPTION	"Determines whether a common sequence number is used for the L2F_PROTO PDUs for both the tunnel (MID=0) and the client connection."
	::= { mibl2TunnelGlobalEntry 25 }

    l2TunnelGlobal-Action-o	OBJECT-TYPE
	SYNTAX	INTEGER {
		    noAction (1),
		    createProfile (2),
		    deleteProfile (3)
		}
	ACCESS	read-write
	STATUS	mandatory
	DESCRIPTION	""
	::= { mibl2TunnelGlobalEntry 26 }

END
