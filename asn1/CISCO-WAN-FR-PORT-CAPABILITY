-- *****************************************************************
-- ciscoWanFrPortCapability MIB
--
-- AGENT-CAPABILITIES mib for Frame Relay Port MIB
-- in MGX8850 products.
--
-- March 2002, Subra.Hegde
--
-- Copyright(c) 2002 by Cisco Systems,Inc.
--
-- *****************************************************************

CISCO-WAN-FR-PORT-CAPABILITY DEFINITIONS ::= BEGIN
IMPORTS
        MODULE-IDENTITY
                FROM SNMPv2-SMI
        AGENT-CAPABILITIES
                FROM SNMPv2-CONF
        ciscoWanAgentCapability
                FROM CISCOWAN-SMI;   

ciscoWanFrPortCapability MODULE-IDENTITY
        LAST-UPDATED    "200203270000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
            "The Agent Capabilities for Frame Relay
            port mib objects.

            - The capability cwFrPortCapabilityFrsm12V3R00 is 
              for FRSM-12 module."
     
        REVISION "200203270000Z"
        DESCRIPTION
            "Initial version of this MIB Module."
        ::= { ciscoWanAgentCapability 359 }

cwFrPortCapabilityFrsm12V3R00 AGENT-CAPABILITIES
    PRODUCT-RELEASE      "MGX8850 Release 3.0.0."
    STATUS               current
    DESCRIPTION          "Frame Relay Port Agent capabilities for
                         Frame Relay Service Module(FRSM-12)."

-- The CISCO-WAN-AXIPOP-MIB is a SMIv1 MIB. This mib
-- contains the Frame Relay Port Related MIB objects.
--
-- The AGENT CAPABILITIES related clauses are within comments.
--  However this mib can be used as a reference
--  for limitations in supporting objects in CISCO MGX8850 Products.

-- To Make it more readable, the OBJECT-GROUP for the objects 
-- applicable for Frame Relay Ports are defined here with in comments.
--
--
-- ciscoWanFrPortConfGroup OBJECT-GROUP
--    OBJECTS {
--        portNum 	
--	      portLineNum 	
--     	  portRowStatus
--	      portDs0ConfigBitMap	 	
--        portDs0Speed
--        portFlagsBetweenFrames
--        portEqueueServiceRatio
--        portSpeed
--        portAdmin
--        portType
--	      portBERTEnable
--	      portEnhancedSIW
--	      portM32EgrQueueThresh
--	      portHeaderLen
--	      portFrameChkSumType
--	      portFileId
--	      portOverSubEnable
--    }
--  STATUS current
--    DESCRIPTION 
--       "The objects applicable to frame relay ports."

--
-- ciscoWanFrPortSvcGroup OBJECT-GROUP
--    OBJECTS {
--        portSvcStatus
--        portSvcInUse
--        portSvcShareLcn
--        portSvcLcnLow
--        portSvcLcnHigh
--        portSvcDlciLow
--        portSvcDlciHigh
--	      portDeleteSvcs
--	      portIngrSvcBandW
--	      portEgrSvcBandW
--    }
--  STATUS current
--    DESCRIPTION 
--       "The objects applicable to SVC characteristics
--       of frame relay ports."
--
-- ciscoWanFrPortMiscGroup OBJECT-GROUP
--    OBJECTS {
--        portsUsedLine1
--        portsUsedLine2
--        portsUsedLine3
--        portsUsedLine4
--        portsUsedLine5
--        portsUsedLine6
--        portsUsedLine7
--        portsUsedLine8
--        portNextAvailable
--    }
--  STATUS current
--    DESCRIPTION 
--       "The scalar objects applicable to frame relay ports."
--
--  ciscoWanFrPortSigLMIGroup  OBJECT-GROUP
--    OBJECTS {
--       lmiCnfPortNum
--       signallingProtocolType
--       asynchronousUpdates
--       t391LinkIntegrityTimer
--       t392PollingVerificationTimer
--       n391FullStatusPollingCounter
--       n392ErrorThreshold
--       n393MonitoredEventCount
--       enhancedLmi
--       portFRF1Dot2Support
--    }
--  STATUS current
--    DESCRIPTION
--       "The objects applicable to Frame Relay LMI 
--          Singalling"
--
-- ciscoWanFrPortSigCLLMGroup  OBJECT-GROUP
--    OBJECTS {
--       cllmCnfPortNum
--       cllmEnable
--       xmtCLLMStatusTimer
--       rcvCLLMStatusTimer
--    }
--  STATUS current
--    DESCRIPTION
--       "The objects applicable to Frame Relay CLLM
--          Protocol"
--
-- ciscoWanFrPortResPartGroup  OBJECT-GROUP
--    OBJECTS {
--       frResPartPortNum
--       frResPartCtrlrNum
--       frResPartRowStatus
--       frResPartNumOfLcnAvail
--       frResPartDlciLow
--       frResPartDlciHigh
--       frResPartIngrPctBW
--       frResPartEgrPctBW
--       frResPartCtrlrID
--    }
--  STATUS current
--    DESCRIPTION
--       "The objects applicable to Frame Relay 
--          Resource Partition"
--
-- ciscoWanFrPortStateGroup  OBJECT-GROUP
--    OBJECTS {
--       statePortNum
--       portState
--       portSignallingState
--       portOversubscribed
--       portIngrPercentUtil
--       portEgrPercentUtil
--    }
--  STATUS current
--    DESCRIPTION
--       "From Frame Relay Port State Table"
--
-- ciscoWanFrPortCntGroup  OBJECT-GROUP
--    OBJECTS {
--        cntPortNum
--        rcvPortFrames
--        rcvPortBytes
--        rcvPortFramesDE
--        rcvPortFramesFECN
--        rcvPortFramesBECN
--        rcvFramesDiscCRCError
--        rcvFramesDiscAlignmentError
--        rcvFramesDiscIllegalLen
--        rcvFramesDiscIllegalHeader
--        rcvFramesAbort
--        rcvFramesUnknownDLCI
--        rcvLastUnknownDLCI
--        rcvPortFramesTaggedFECN
--        rcvPortFramesTaggedBECN
--        rcvPortFramesTaggedDE
--        rcvPortFramesDiscXceedDEThresh
--        rcvPortKbpsAIR
--        rcvBufNotAvailable
--        xmtPortFrames
--        xmtPortBytes
--        xmtPortFramesFECN
--        xmtPortFramesBECN
--        xmtPortFramesDiscXceedQDepth
--        xmtPortBytesDiscXceedQDepth
--        xmtPortFramesDuringLMIAlarm
--        xmtPortBytesDuringLMIAlarm
--        xmtFramesAbort
--        xmtFramesUnderrun
--        xmtPortKbpsAIR
--        xmtBufNotAvailable
--        portClrButton
--        rcvFramesDiscNoChan
--        rcvFramesDiscOverrun
--    }
--  STATUS current
--    DESCRIPTION
--       "From Frame Relay Port Statistics Table"
--
-- ciscoWanFrPortLMICntGroup  OBJECT-GROUP
--    OBJECTS {
--        lmiSigPortNum
--        rcvStatusInquiry
--        rcvInvalidRequest
--        rcvUNISeqMismatch
--        xmtStatus
--        xmtAsynchUpdate
--        uniSignalingTimeout
--        xmtStatusInquiry
--        rcvStatus
--        rcvAsynchUpdate
--        rcvNNISeqMismatch
--        nniSignalingTimeout
--    }
--  STATUS current
--    DESCRIPTION
--       "From Frame Relay LMI Statistics Table"
--
-- ciscoWanFrPortCLLMCntGroup  OBJECT-GROUP
--    OBJECTS {
--        cllmSigPortNum
--        rcvFramesCLLM
--        rcvBytesCLLM
--        xmtFramesCLLM
--        xmtBytesCLLM
--        cllmFailures
--    }
--  STATUS current
--    DESCRIPTION
--       "From Frame Relay CLLM Statistics Table"
--
-- NOTE: FRSM-12 Does not support following groups:
--   ciscoWanFrPortSvcGroup 
--   ciscoWanFrPortMiscGroup
--   ciscoWanFrPortSigCLLMGroup
--   ciscoWanFrPortCLLMCntGroup
--
    SUPPORTS   CISCO-WAN-AXIPOP-MIB 
    INCLUDES   { ciscoWanFrPortConfGroup,
                 ciscoWanFrPortSigLMIGroup,
                 ciscoWanFrPortResPartGroup,
                 ciscoWanFrPortStateGroup,
                 ciscoWanFrPortCntGroup, 
                 ciscoWanFrPortLMICntGroup
               }

    VARIATION  portDs0Speed
    SYNTAX INTEGER {
               unUsed(3)
           }
    DESCRIPTION
        "Does not support speed56k(1),speed64k(2)."

    VARIATION   portFlagsBetweenFrames
    SYNTAX      INTEGER(1..8)
    DESCRIPTION
        "Supported with Restricted range."

    VARIATION   portAdmin
    SYNTAX      INTEGER { up(1), down(2) }
    DESCRIPTION
        "Does not support write-only(3)."

    VARIATION   portType
    SYNTAX      INTEGER { frame-relay(1), frame-forward(3) }
    DESCRIPTION
        "Does not support frFUNI(2)."

    VARIATION   portBERTEnable
    ACCESS      not-implemented
    DESCRIPTION
        "Not supported."

    VARIATION   portEnhancedSIW
    ACCESS      not-implemented
    DESCRIPTION
        "Not supported."

    VARIATION   portM32EgrQueueThresh
    ACCESS      not-implemented
    DESCRIPTION
        "Not supported."

    VARIATION   xmtPortFramesDiscXceedQDepth
    ACCESS      not-implemented
    DESCRIPTION
        "Not supported."

    VARIATION   xmtPortBytesDiscXceedQDepth
    ACCESS      not-implemented
    DESCRIPTION
        "Not supported."

    VARIATION   xmtFramesAbort
    ACCESS      not-implemented
    DESCRIPTION
        "Not supported."

    VARIATION   xmtBufNotAvailable
    ACCESS      not-implemented
    DESCRIPTION
        "Not supported."

   ::= { ciscoWanFrPortCapability 1 }

END
