--			Ascend mibswannet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSWANNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibswanNetworkProfile  OBJECT IDENTIFIER ::= { configuration 124}

	-- The mibswanNetworkProfile table
	--
	-- This table contains parameters for the mibswanNetworkProfile profile
	--

    mibswanNetworkProfileTable	OBJECT-TYPE
	SYNTAX		SEQUENCE OF MibswanNetworkProfileEntry
	ACCESS		not-accessible
	STATUS		mandatory
	DESCRIPTION	"A list of mibswanNetworkProfile profile entries."
	::= { mibswanNetworkProfile 1 }

    mibswanNetworkProfileEntry	OBJECT-TYPE
	SYNTAX		MibswanNetworkProfileEntry
	ACCESS		not-accessible
	STATUS		mandatory
	DESCRIPTION	"A mibswanNetworkProfile entry containing objects that
			 maps to the parameters of mibswanNetworkProfile profile."
	INDEX		{ swanNetworkProfile-Shelf-o, swanNetworkProfile-Slot-o, swanNetworkProfile-Item-o }
	::= { mibswanNetworkProfileTable 1 }

    MibswanNetworkProfileEntry ::=
	SEQUENCE {
	    swanNetworkProfile-Shelf-o
		INTEGER,
	    swanNetworkProfile-Slot-o
		INTEGER,
	    swanNetworkProfile-Item-o
		INTEGER,
	    swanNetworkProfile-Name
		DisplayString,
	    swanNetworkProfile-PhysicalAddress-Shelf
		INTEGER,
	    swanNetworkProfile-PhysicalAddress-Slot
		INTEGER,
	    swanNetworkProfile-PhysicalAddress-ItemNumber
		INTEGER,
	    swanNetworkProfile-Enabled
		INTEGER,
	    swanNetworkProfile-LineConfig-TrunkGroup
		INTEGER,
	    swanNetworkProfile-LineConfig-NailedGroup
		INTEGER,
	    swanNetworkProfile-LineConfig-RoutePort-SlotNumber-SlotNumber
		INTEGER,
	    swanNetworkProfile-LineConfig-RoutePort-SlotNumber-ShelfNumber
		INTEGER,
	    swanNetworkProfile-LineConfig-RoutePort-RelativePortNumber-RelativePortNumber
		INTEGER,
	    swanNetworkProfile-LineConfig-Activation
		INTEGER,
	    swanNetworkProfile-LineConfig-Clocking-ClockMode
		INTEGER,
	    swanNetworkProfile-LineConfig-Clocking-Divider
		INTEGER,
	    swanNetworkProfile-LineConfig-Clocking-Exp
		INTEGER,
	    swanNetworkProfile-LineConfig-Clocking-LineRate
		INTEGER,
	    swanNetworkProfile-Action-o
		INTEGER
	}

    swanNetworkProfile-Shelf-o	OBJECT-TYPE
	SYNTAX	INTEGER
	ACCESS	read-only
	STATUS	mandatory
	DESCRIPTION	""
	::= { mibswanNetworkProfileEntry 1 }

    swanNetworkProfile-Slot-o	OBJECT-TYPE
	SYNTAX	INTEGER
	ACCESS	read-only
	STATUS	mandatory
	DESCRIPTION	""
	::= { mibswanNetworkProfileEntry 2 }

    swanNetworkProfile-Item-o	OBJECT-TYPE
	SYNTAX	INTEGER
	ACCESS	read-only
	STATUS	mandatory
	DESCRIPTION	""
	::= { mibswanNetworkProfileEntry 3 }

    swanNetworkProfile-Name	OBJECT-TYPE
	SYNTAX	DisplayString
	ACCESS	read-write
	STATUS	mandatory
	DESCRIPTION	"Name of the Swan line for display purposes."
	::= { mibswanNetworkProfileEntry 4 }

    swanNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibswanNetworkProfileEntry 5 }

    swanNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibswanNetworkProfileEntry 6 }

    swanNetworkProfile-PhysicalAddress-ItemNumber	OBJECT-TYPE
	SYNTAX	INTEGER
	ACCESS	read-write
	STATUS	mandatory
	DESCRIPTION	"A number that specifies an addressable entity within the context of shelf and slot."
	::= { mibswanNetworkProfileEntry 7 }

    swanNetworkProfile-Enabled	OBJECT-TYPE
	SYNTAX	INTEGER {
		    no (1),
		    yes (2)
		}
	ACCESS	read-write
	STATUS	mandatory
	DESCRIPTION	"TRUE if the line is enabled, otherwise FALSE."
	::= { mibswanNetworkProfileEntry 8 }

    swanNetworkProfile-LineConfig-TrunkGroup	OBJECT-TYPE
	SYNTAX	INTEGER
	ACCESS	read-write
	STATUS	mandatory
	DESCRIPTION	"The trunk group to which this line is assigned. 0 means this line is not part of a trunk group."
	::= { mibswanNetworkProfileEntry 9 }

    swanNetworkProfile-LineConfig-NailedGroup	OBJECT-TYPE
	SYNTAX	INTEGER
	ACCESS	read-write
	STATUS	mandatory
	DESCRIPTION	"A number that identifies the set of lines that makes up a nailed group."
	::= { mibswanNetworkProfileEntry 10 }

    swanNetworkProfile-LineConfig-RoutePort-SlotNumber-SlotNumber	OBJECT-TYPE
	SYNTAX	INTEGER
	ACCESS	read-write
	STATUS	mandatory
	DESCRIPTION	""
	::= { mibswanNetworkProfileEntry 11 }

    swanNetworkProfile-LineConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibswanNetworkProfileEntry 12 }

    swanNetworkProfile-LineConfig-RoutePort-RelativePortNumber-RelativePortNumber	OBJECT-TYPE
	SYNTAX	INTEGER
	ACCESS	read-write
	STATUS	mandatory
	DESCRIPTION	""
	::= { mibswanNetworkProfileEntry 13 }

    swanNetworkProfile-LineConfig-Activation	OBJECT-TYPE
	SYNTAX	INTEGER {
		    static (1),
		    dsrActive (2),
		    dcdDsrActive (3)
		}
	ACCESS	read-write
	STATUS	mandatory
	DESCRIPTION	"Line activation mode (port control lead usage)."
	::= { mibswanNetworkProfileEntry 14 }

    swanNetworkProfile-LineConfig-Clocking-ClockMode	OBJECT-TYPE
	SYNTAX	INTEGER {
		    externalClock (1),
		    internalClock (2)
		}
	ACCESS	read-write
	STATUS	mandatory
	DESCRIPTION	"Line clocking mode, internal/external."
	::= { mibswanNetworkProfileEntry 18 }

    swanNetworkProfile-LineConfig-Clocking-Divider	OBJECT-TYPE
	SYNTAX	INTEGER
	ACCESS	read-write
	STATUS	mandatory
	DESCRIPTION	"The divider may be 1-256 and divides the 16.667 MHz source clock."
	::= { mibswanNetworkProfileEntry 19 }

    swanNetworkProfile-LineConfig-Clocking-Exp	OBJECT-TYPE
	SYNTAX	INTEGER
	ACCESS	read-write
	STATUS	mandatory
	DESCRIPTION	"The exp may be 0-9, the internal clock is further modified by dividing by 2 raised to the 'exp' power."
	::= { mibswanNetworkProfileEntry 20 }

    swanNetworkProfile-LineConfig-Clocking-LineRate	OBJECT-TYPE
	SYNTAX	INTEGER
	ACCESS	read-write
	STATUS	mandatory
	DESCRIPTION	"Line rate in bit-per-second."
	::= { mibswanNetworkProfileEntry 21 }

    swanNetworkProfile-Action-o	OBJECT-TYPE
	SYNTAX	INTEGER {
		    noAction (1),
		    createProfile (2),
		    deleteProfile (3)
		}
	ACCESS	read-write
	STATUS	mandatory
	DESCRIPTION	""
	::= { mibswanNetworkProfileEntry 22 }

END
