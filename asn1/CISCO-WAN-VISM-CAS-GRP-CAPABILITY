-- *****************************************************************
-- ciscoWanVismCasGrpCapabilities mib
--
-- AGENT-CAPABILITIES mib for vismCasGrp in VISM products. The 
--                    vismCasGrp.my mib objects are contained either 
--                    in the CISCO-WAN-AXIPOP-MIB.my file or the 
--                    finalMib.AXIPOPVISM1.5.my file
--
-- Copyright(c) 2000 by Cisco Systems,Inc.
--
-- Author: Mike.Manley
-- *****************************************************************

CISCO-WAN-VISM-CAS-GRP-CAPABILITY DEFINITIONS ::= BEGIN
IMPORTS
        MODULE-IDENTITY
                FROM SNMPv2-SMI
        AGENT-CAPABILITIES
                FROM SNMPv2-CONF
        ciscoWanAgentCapability
                FROM CISCOWAN-SMI;   

ciscoWanVismCasGrpCapability MODULE-IDENTITY
        LAST-UPDATED    "200012050000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
                "The Agent Capabilities for vismCasGrp.my ."
        ::= { ciscoWanAgentCapability 333 }

cwvismCasGrpCapability1  AGENT-CAPABILITIES
    PRODUCT-RELEASE      "VISM Release 2.1.0 and MGX-8850 Release 1.1.34"
    STATUS               current
    DESCRIPTION          "vismCasGrp.my Capabilities"

-- The vismCasGrp.my is a SNMP v1 MIB. 
-- The AGENT CAPABILITIES related clauses are within comments.
--  However this mib can be used as a reference
--  for limitations in supporting objects in vismCasGrp.my.
--
-- To Make it more readable, the OBJECT-GROUP for the objects in
-- vismCasGrp.my are defined here in comments.
--
--
--
--   vismCasVariantGroup OBJECT-GROUP
--   OBJECTS {
--        vismCasVariantName,     
--        vismCasFileName,     
--        vismCasTRinging,     
--        vismCasDigitMethod,    
--        vismCasInterdigitTpart,     
--        vismCasInterdigitTcrit,     
--        vismCasInterdigitTMF,     
--        vismCasVariantState,     
--        vismCasRowStatus,     
--        vismCasCountryCode     
--   }
--   STATUS current
--   DESCRIPTION
--       "Collection of objects implementing the vismCasVariantGroup Table."
--
--
--
--
--
--   vismCasXgcpVariantGroup OBJECT-GROUP
--   OBJECTS {
--        vismCasXgcpVariantName,
--        vismCasXgcpFileName,
--        vismCasXgcpMaxReXmitTime,
--        vismCasXgcpInitialReXmitTime,
--        vismCasXgcpMaxRetries
--   }
--   STATUS current
--   DESCRIPTION
--       "Collection of objects implementing the vismCasXgcpVariantGroup Table."
--
--
--
--
-- SUPPORTS clause uses the groups name defined above in
--  OBJECT-GROUP.
--
--   SUPPORTS vismCasGrp.my
--	INCLUDES {
--          vismCasVariantTable, 
--          vismCasXgcpVariantTable 
--      }
--
--	VARIATION   vismCasXgcpInitialReXmitTime
--      DESCRIPTION
--          "This object represents the initial timeout value in milli seconds."
--      DEFVAL      { 500 }
--
--	VARIATION   vismCasXgcpMaxRetries
--      DESCRIPTION
--          "This object specifies the number of retries for a message."
--      DEFVAL      { 3 }


    ::= { ciscoWanVismCasGrpCapability 1 }
END
