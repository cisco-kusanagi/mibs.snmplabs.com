ChrComPmDs3DS3FarEnd-Interval-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmDs3				FROM  Chromatis-MIB
	chrComIfifIndex					FROM  ChrComIfifTable-MIB
	TruthValue				FROM  ChrTyp-MIB
	Gauge32				FROM  SNMPv2-SMI;

-- chrComPmDs3DS3FarEnd-Interval Table

chrComPmDs3DS3FarEnd-IntervalTable		OBJECT-TYPE
	SYNTAX		SEQUENCE OF ChrComPmDs3DS3FarEnd-IntervalEntry
	MAX-ACCESS	not-accessible
	STATUS		current
	DESCRIPTION
	""
	::= { chrComPmDs3 15}

chrComPmDs3DS3FarEnd-IntervalEntry		OBJECT-TYPE
	SYNTAX		ChrComPmDs3DS3FarEnd-IntervalEntry
	MAX-ACCESS	not-accessible
	STATUS		current
	DESCRIPTION
	""
	INDEX  {  chrComIfifIndex, chrComPmDs3IntervalNumber }

--DEFAULT  get-function-async  MNIL_GetRoutine
--DEFAULT  set-function-async  MNIL_SetRoutine
--DEFAULT  next-function-async MNIL_NextRoutine
--DEFAULT  test-function-async MNIL_TestRoutine
--DEFAULT  cookie "DS3FarEnd-Interval"
	::= { chrComPmDs3DS3FarEnd-IntervalTable  1 }

ChrComPmDs3DS3FarEnd-IntervalEntry  ::=
	SEQUENCE  {
	chrComPmDs3IntervalNumber		Unsigned32	(1..32),
	chrComPmDs3SuspectedInterval	TruthValue,
	chrComPmDs3ElapsedTime		Unsigned32	(0..4294967295),
	chrComPmDs3SuppressedIntrvls	Gauge32			(0..4294967295),
	chrComPmDs3CCV			Gauge32			(0..4294967295),
	chrComPmDs3CES			Gauge32			(0..4294967295),
	chrComPmDs3CSES			Gauge32			(0..4294967295),
	chrComPmDs3SAS			Gauge32			(0..4294967295),
	chrComPmDs3UASCP			Gauge32			(0..4294967295),
	chrComPmDs3ESPLCP			Gauge32			(0..4294967295)
}

chrComPmDs3IntervalNumber 	OBJECT-TYPE
	SYNTAX		Unsigned32	(1..32)
	MAX-ACCESS 	read-only
	STATUS 		current
	DESCRIPTION
	""
	::= { chrComPmDs3DS3FarEnd-IntervalEntry  1 }

chrComPmDs3SuspectedInterval 	OBJECT-TYPE
	SYNTAX		TruthValue
	MAX-ACCESS 	read-only
	STATUS 		current
	DESCRIPTION
	""
	::= { chrComPmDs3DS3FarEnd-IntervalEntry  2 }

chrComPmDs3ElapsedTime 	OBJECT-TYPE
	SYNTAX		Unsigned32	(0..4294967295)
	MAX-ACCESS 	read-only
	STATUS 		current
	DESCRIPTION
	""
	::= { chrComPmDs3DS3FarEnd-IntervalEntry  3 }

chrComPmDs3SuppressedIntrvls 	OBJECT-TYPE
	SYNTAX		Gauge32			(0..4294967295)
	MAX-ACCESS 	read-only
	STATUS 		current
	DESCRIPTION
	""
	::= { chrComPmDs3DS3FarEnd-IntervalEntry  4 }

chrComPmDs3CCV 	OBJECT-TYPE
	SYNTAX		Gauge32			(0..4294967295)
	MAX-ACCESS 	read-only
	STATUS 		current
	DESCRIPTION
	""
	::= { chrComPmDs3DS3FarEnd-IntervalEntry  5 }

chrComPmDs3CES 	OBJECT-TYPE
	SYNTAX		Gauge32			(0..4294967295)
	MAX-ACCESS 	read-only
	STATUS 		current
	DESCRIPTION
	""
	::= { chrComPmDs3DS3FarEnd-IntervalEntry  6 }

chrComPmDs3CSES 	OBJECT-TYPE
	SYNTAX		Gauge32			(0..4294967295)
	MAX-ACCESS 	read-only
	STATUS 		current
	DESCRIPTION
	""
	::= { chrComPmDs3DS3FarEnd-IntervalEntry  7 }

chrComPmDs3SAS 	OBJECT-TYPE
	SYNTAX		Gauge32			(0..4294967295)
	MAX-ACCESS 	read-only
	STATUS 		current
	DESCRIPTION
	""
	::= { chrComPmDs3DS3FarEnd-IntervalEntry  8 }

chrComPmDs3UASCP 	OBJECT-TYPE
	SYNTAX		Gauge32			(0..4294967295)
	MAX-ACCESS 	read-only
	STATUS 		current
	DESCRIPTION
	""
	::= { chrComPmDs3DS3FarEnd-IntervalEntry  9 }

chrComPmDs3ESPLCP 	OBJECT-TYPE
	SYNTAX		Gauge32			(0..4294967295)
	MAX-ACCESS 	read-only
	STATUS 		current
	DESCRIPTION
	""
	::= { chrComPmDs3DS3FarEnd-IntervalEntry  10 }


END
