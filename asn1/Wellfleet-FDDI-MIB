Wellfleet-FDDI-MIB DEFINITIONS ::= BEGIN

-- Created by mdl2asn version 3.1
-- Creation date: Wed Aug 30 16:40:52 EDT 1995


    IMPORTS

      Counter, Gauge, TimeTicks
        FROM RFC1155-SMI
      OBJECT-TYPE
        FROM RFC-1212
      DisplayString
        FROM RFC1213-MIB
      wfLine, wfFddiGroup
        FROM Wellfleet-COMMON-MIB;


    wfFddiSmtGroup      OBJECT IDENTIFIER ::= { wfFddiGroup 1 }
    wfFddiMacGroup      OBJECT IDENTIFIER ::= { wfFddiGroup 2 }
    wfFddiPathGroup     OBJECT IDENTIFIER ::= { wfFddiGroup 3 }
    wfFddiPortGroup     OBJECT IDENTIFIER ::= { wfFddiGroup 4 }
    wfFddiXGroup        OBJECT IDENTIFIER ::= { wfFddiGroup 5 }


    wfFddiTable OBJECT-TYPE
        SYNTAX  SEQUENCE OF WfFddiEntry
        ACCESS  not-accessible
        STATUS  mandatory
        DESCRIPTION
                "FDDI line record"
        ::= { wfLine 4 }

    wfFddiEntry OBJECT-TYPE
        SYNTAX  WfFddiEntry
        ACCESS  not-accessible
        STATUS  mandatory
        DESCRIPTION
                "An entry in the FDDI table"
        INDEX   { wfFDDISlot,
                  wfFDDINode }
        ::= { wfFddiTable 1 }

    WfFddiEntry ::= SEQUENCE {
            wfFDDIDelete
                INTEGER,
            wfFDDIEnable
                INTEGER,
            wfFDDIState
                INTEGER,
            wfFDDISlot
                INTEGER,
            wfFDDINode
                INTEGER,
            wfFDDICct
                INTEGER,
            wfFDDIBofl
                INTEGER,
            wfFDDIBoflTmo
                INTEGER,
            wfFDDIMtu
                INTEGER,
            wfFDDIMadr
                OCTET STRING,
            wfFDDIOctetsRxOk
                Counter,
            wfFDDIFramesRxOk
                Counter,
            wfFDDIOctetsTxOk
                Counter,
            wfFDDIFramesTxOk
                Counter,
            wfFDDICrcErrRx
                Counter,
            wfFDDIOverrunRx
                Counter,
            wfFDDIParityErrRx
                Counter,
            wfFDDIMacErrRx
                Counter,
            wfFDDIRingErrRx
                Counter,
            wfFDDISmtRingErrRx
                Counter,
            wfFDDIRingOverrunRx
                Counter,
            wfFDDISmtRingOverrunRx
                Counter,
            wfFDDIAbortTx
                Counter,
            wfFDDIUnderrunTx
                Counter,
            wfFDDIParityErrTx
                Counter,
            wfFDDIRingErrTx
                Counter,
            wfFDDIPortOpErr
                Counter,
            wfFDDIInternOpErr
                Counter,
            wfFDDIHostErr
                Counter,
            wfFDDISmtConnectionPolicy
                INTEGER,
            wfFDDISmtTNotify
                INTEGER,
            wfFDDIMacTReq
                INTEGER,
            wfFDDIMacTMax
                INTEGER,
            wfFDDIMacTvxValue
                INTEGER,
            wfFDDIMacTMin
                INTEGER,
            wfFDDIHardwareFilter
                INTEGER,
            wfFDDISmtEnable
                INTEGER,
            wfFDDITxQueueLength
                INTEGER,
            wfFDDIRxQueueLength
                INTEGER,
            wfFDDITxClipFrames
                Counter,
            wfFDDIRxReplenMisses
                Counter,
            wfFDDICfgTxQueueLength
                INTEGER,
            wfFDDICfgRxQueueLength
                INTEGER,
            wfFDDILineNumber
                INTEGER,
            wfFDDIForcePeerTree
                INTEGER,
            wfFDDIInvalidFrameStatusRx
                Counter,
            wfFDDIRxOversizedFrames
                Counter,
            wfFDDIRxSmtOversizedFrames
                Counter,
            wfFDDIRxUndersizedFrames
                Counter,
            wfFDDIRxSmtUndersizedFrames
                Counter,
            wfFDDIModule
                INTEGER,
            wfFDDIActualNode
                INTEGER,
            wfFDDILastChange
                TimeTicks,
            wfFDDIOutQLen
                Gauge,
            wfFDDIRxSmtOctets
                Counter,
            wfFDDIRxSmtFrames
                Counter,
            wfFDDIIntProcessings
                Counter,
            wfFDDITxProcessings
                Counter,
            wfFDDIRxProcessings
                Counter,
            wfFDDITxRNRProcessings
                Counter,
            wfFDDISmtRxProcessings
                Counter,
            wfFDDIPhyALogPtr
                INTEGER,
            wfFDDIPhyBLogPtr
                INTEGER,
            wfFDDIPromiscuous
                INTEGER,
            wfFDDILLCFrameControl
                INTEGER,
            wfFDDITurboBofl
                INTEGER,
            wfFDDIBoflNum
                INTEGER,
            wfFDDIBoflLen
                INTEGER
        }

    wfFDDIDelete OBJECT-TYPE
        SYNTAX  INTEGER {
                    create(1),
                    delete(2)
                }
        ACCESS  read-write
        STATUS  mandatory
        DESCRIPTION
                "Create/delete parameter, default = create."
        DEFVAL  { create }
        ::= { wfFddiEntry 1 }

    wfFDDIEnable OBJECT-TYPE
        SYNTAX  INTEGER {
                    enable(1),
                    disable(2)
                }
        ACCESS  read-write
        STATUS  mandatory
        DESCRIPTION
                "Enable/disable parameter, default = enable."
        DEFVAL  { enable }
        ::= { wfFddiEntry 2 }

    wfFDDIState OBJECT-TYPE
        SYNTAX  INTEGER {
                    up(1),
                    down(2),
                    init(3),
                    notpresent(4)
                }
        ACCESS  read-only
        STATUS  mandatory
        DESCRIPTION
                "Line driver state variable, not present, init, down, up."
        DEFVAL  { notpresent }
        ::= { wfFddiEntry 3 }

    wfFDDISlot OBJECT-TYPE
        SYNTAX  INTEGER(1..14)
        ACCESS  read-only
        STATUS  mandatory
        DESCRIPTION
                "Instance ID slot - filled in by driver."
        ::= { wfFddiEntry 4 }

    wfFDDINode OBJECT-TYPE
        SYNTAX  INTEGER(1..44)
        ACCESS  read-only
        STATUS  mandatory
        DESCRIPTION
                "Instance ID node - filled in by driver. For the ASN
                this attribute is an encoded value and is equal to
                'module'*10 + 'node'. Where 'module' is defined in
                attribute 50 and 'node' is defined in attribute 51
                of this table. For non-ASN platforms this attribute
                indicates the physical node number on the slot"
        ::= { wfFddiEntry 5 }

    wfFDDICct OBJECT-TYPE
        SYNTAX  INTEGER(1..1023)
        ACCESS  read-write
        STATUS  mandatory
        DESCRIPTION
                "Cct number for this line instance."
        ::= { wfFddiEntry 6 }

    wfFDDIBofl OBJECT-TYPE
        SYNTAX  INTEGER {
                    enable(1),
                    disable(2)
                }
        ACCESS  read-write
        STATUS  mandatory
        DESCRIPTION
                "The Breath-Of-Life (BOFL) function, when enabled, will disable
                the LLC interface when the FDDI becomes non-operational
                (i.e., link unavailable) and the following conditions are true:

                1. The wfFddiMacMaUnitDataEnable attribute is enabled.
                2. The BOFL timer expired (specified by wfFDDIBoflTmo).

                If this attribute is disabled, the LLC interface will be
                terminated immediately after the link becomes unavailable. "
        DEFVAL  { enable }
        ::= { wfFddiEntry 7 }

    wfFDDIBoflTmo OBJECT-TYPE
        SYNTAX  INTEGER(0..3600)
        ACCESS  read-write
        STATUS  mandatory
        DESCRIPTION
                "Specifies the time value (in seconds) of the BOFL timer. The BOFL
                timer will be set to the value of this attribute when the following
                conditions are true:

                1. The wfFDDIBofl attribute is enabled.
                2. The link becomes unavailable.

                Upon expiration of the BOFL timer, the LLC interface will be
                disabled.

                Note also that the BOFL timer will be disabled if the link becomes
                operational (available) before the timer expires.."
        DEFVAL  { 3 }
        ::= { wfFddiEntry 8 }


    wfFDDIMtu OBJECT-TYPE
        SYNTAX  INTEGER {
                    default(4495)
                }
        ACCESS  read-only
        STATUS  mandatory
        DESCRIPTION
                "The MTU is the maximum allowed frame length on the wire, excluding
                frame delimiters (i.e. preamble, ending delimiter).

                The MTU of an FDDI frame includes:
                   FC (1 octet) + DA (6 octets) + SA (6 octets) +
                   INFO (<= 4478 octets) +
                   FCS (4 octets)  = 4495 octets"
        DEFVAL  { default }
        ::= { wfFddiEntry 9 }

    wfFDDIMadr OBJECT-TYPE
        SYNTAX  OCTET STRING
        ACCESS  read-only
        STATUS  mandatory
        DESCRIPTION
                "PROM-based MAC address, fixed - line driver fills in."
        ::= { wfFddiEntry 10 }

    wfFDDIOctetsRxOk OBJECT-TYPE
        SYNTAX  Counter
        ACCESS  read-only
        STATUS  mandatory
        DESCRIPTION
                "Number of bytes received without error. This byte count
                only includes LLC frames (i.e. no MAC and SMT frames)."
        ::= { wfFddiEntry 11 }

    wfFDDIFramesRxOk OBJECT-TYPE
        SYNTAX  Counter
        ACCESS  read-only
        STATUS  mandatory
        DESCRIPTION
                "Number of frames received without error. This frame count
                only includes LLC frames (i.e. no MAC and SMT frames)."
        ::= { wfFddiEntry 12 }

    wfFDDIOctetsTxOk OBJECT-TYPE
        SYNTAX  Counter
        ACCESS  read-only
        STATUS  mandatory
        DESCRIPTION
                "Number of bytes transmitted without error. This byte count
                only includes LLC and SMT frames (i.e. no MAC frames)."
        ::= { wfFddiEntry 13 }

    wfFDDIFramesTxOk OBJECT-TYPE
        SYNTAX  Counter
        ACCESS  read-only
        STATUS  mandatory
        DESCRIPTION
                "Number of frames transmitted without error. This frame count
                only includes LLC and SMT frames (i.e. no MAC frames )."
        ::= { wfFddiEntry 14 }

    wfFDDICrcErrRx OBJECT-TYPE
        SYNTAX  Counter
        ACCESS  read-only
        STATUS  mandatory
        DESCRIPTION
                "Number of frames received with CRC errors."
        ::= { wfFddiEntry 15 }

    wfFDDIOverrunRx OBJECT-TYPE
        SYNTAX  Counter
        ACCESS  read-only
        STATUS  mandatory
        DESCRIPTION
                "Number of frames received with internal overrun errors."
        ::= { wfFddiEntry 16 }

    wfFDDIParityErrRx OBJECT-TYPE
        SYNTAX  Counter
        ACCESS  read-only
        STATUS  mandatory
        DESCRIPTION
                "Number of frames received with parity errors."
        ::= { wfFddiEntry 17 }

    wfFDDIMacErrRx OBJECT-TYPE
        SYNTAX  Counter
        ACCESS  read-only
        STATUS  mandatory
        DESCRIPTION
                "Number of frames received with MAC errors."
        ::= { wfFddiEntry 18 }

    wfFDDIRingErrRx OBJECT-TYPE
        SYNTAX  Counter
        ACCESS  read-only
        STATUS  mandatory
        DESCRIPTION
                "Number of receive ring error events."
        ::= { wfFddiEntry 19 }

    wfFDDISmtRingErrRx OBJECT-TYPE
        SYNTAX  Counter
        ACCESS  read-only
        STATUS  mandatory
        DESCRIPTION
                "Number of SMT receive ring error events."
        ::= { wfFddiEntry 20 }

    wfFDDIRingOverrunRx OBJECT-TYPE
        SYNTAX  Counter
        ACCESS  read-only
        STATUS  mandatory
        DESCRIPTION
                "Number of LLC receive ring overrun events."
        ::= { wfFddiEntry 21 }

    wfFDDISmtRingOverrunRx OBJECT-TYPE
        SYNTAX  Counter
        ACCESS  read-only
        STATUS  mandatory
        DESCRIPTION
                "Number of SMT receive ring overrun events."
        ::= { wfFddiEntry 22 }

    wfFDDIAbortTx OBJECT-TYPE
        SYNTAX  Counter
        ACCESS  read-only
        STATUS  mandatory
        DESCRIPTION
                "Number of transmit frames with internal abort errors."
        ::= { wfFddiEntry 23 }

    wfFDDIUnderrunTx OBJECT-TYPE
        SYNTAX  Counter
        ACCESS  read-only
        STATUS  mandatory
        DESCRIPTION
                "Number of transmit frames aborted with underrun errors."
        ::= { wfFddiEntry 24 }

    wfFDDIParityErrTx OBJECT-TYPE
        SYNTAX  Counter
        ACCESS  read-only
        STATUS  mandatory
        DESCRIPTION
                "Number of transmit frames aborted with parity errors."
        ::= { wfFddiEntry 25 }

    wfFDDIRingErrTx OBJECT-TYPE
        SYNTAX  Counter
        ACCESS  read-only
        STATUS  mandatory
        DESCRIPTION
                "Number of LLC/SMT transmit ring error events."
        ::= { wfFddiEntry 26 }

    wfFDDIPortOpErr OBJECT-TYPE
        SYNTAX  Counter
        ACCESS  read-only
        STATUS  mandatory
        DESCRIPTION
                "Number of port operation error events."
        ::= { wfFddiEntry 27 }

    wfFDDIInternOpErr OBJECT-TYPE
        SYNTAX  Counter
        ACCESS  read-only
        STATUS  mandatory
        DESCRIPTION
                "Number of internal operation error events."
        ::= { wfFddiEntry 28 }

    wfFDDIHostErr OBJECT-TYPE
        SYNTAX  Counter
        ACCESS  read-only
        STATUS  mandatory
        DESCRIPTION
                "Number of host error events."
        ::= { wfFddiEntry 29 }

    wfFDDISmtConnectionPolicy OBJECT-TYPE
        SYNTAX  INTEGER {
                    default(65381)
                }
        ACCESS  read-write
        STATUS  mandatory
        DESCRIPTION
                "A value that indicates the connection policies
                enforced at the station. A station sets the
                corresponding policy for each of the connection
                types that it rejects. The letter designations, X
                and Y, in the 'rejectX-Y' names have the following
                significance: X represents the PC-Type of the
                local PORT and Y represents a PC-Neighbor in the
                evaluation of Connection-Policy (PC-Type, PC-
                Neighbor) that is done to determine the setting of
                T-Val(3) in the PC-Signaling sequence.

                The value is a sum. This value initially takes
                the value zero, then for each of the connection
                policies currently enforced on the node, 2 raised
                to a power is added to the sum. The powers are
                according to the following table:

                       Policy   Power
                    rejectA-A   0
                    rejectA-B   1
                    rejectA-S   2
                    rejectA-M   3
                    rejectB-A   4
                    rejectB-B   5
                    rejectB-S   6
                    rejectB-M   7
                    rejectS-A   8
                    rejectS-B   9
                    rejectS-S   10
                    rejectS-M   11
                    rejectM-A   12
                    rejectM-B   13
                    rejectM-S   14
                    rejectM-M   15"
        DEFVAL  { default }
        ::= { wfFddiEntry 30 }

    wfFDDISmtTNotify OBJECT-TYPE
        SYNTAX  INTEGER(2..30)
        ACCESS  read-write
        STATUS  mandatory
        DESCRIPTION
                "The timer used in the Neighbor Notification protocol, reported
                in seconds and ranging from 2 to 30 seconds."
        DEFVAL  { 22 }
        ::= { wfFddiEntry 31 }

    wfFDDIMacTReq OBJECT-TYPE
        SYNTAX  INTEGER {
                    default(2062500)
                }
        ACCESS  read-write
        STATUS  mandatory
        DESCRIPTION
                "Specifies the maximum time value of 'wfFddiPathMaxTReq' that
                shall be used by any MAC that is configured in this path. The
                operational value of 'wfFddiPathMaxTReq' is managed by setting
                this attribute. This attribute has the time value range of:

                     wfFddiPathTvxLowerBound < wfFddiMacTReq <=
                     wfFddiPathTMaxLowerBound.

                Time specified in octet units. The default value of this attribute
                is 165 msec. The name of this attribute in the IETF MIB is
                FddiMibPATHMaxTReq.

                To convert 165 milliseconds to octet units of 80 nanaseconds:

                T_Req Nanaoseconds =
                         ((165 * 1000 * 1000) / 80) = 2062500

                To convert 2062500 octet units of 80 nanoseconds to milliseconds:

                T_Req Milliseconds =
                         ((2062500 / 12.5) / 1000)  = 165"
        DEFVAL  { default }
        ::= { wfFddiEntry 32 }

    wfFDDIMacTMax OBJECT-TYPE
        SYNTAX  INTEGER
        ACCESS  read-only
        STATUS  mandatory
        DESCRIPTION
                "The requested maximum TTRT to be supported by a MAC represented
                in unsigned integer specifying time in octet units (80 nanoseconds)."
        ::= { wfFddiEntry 33 }

    wfFDDIMacTvxValue OBJECT-TYPE
        SYNTAX  INTEGER
        ACCESS  read-only
        STATUS  mandatory
        DESCRIPTION
                "The requested value of TvxValue represented in unsigned integer
                specifying time in octet units (80 nanoseconds)."
        ::= { wfFddiEntry 34 }

    wfFDDIMacTMin OBJECT-TYPE
        SYNTAX  INTEGER {
                    default(50000)
                }
        ACCESS  read-only
        STATUS  mandatory
        DESCRIPTION
                "The requested minimum TTRT to be requested by a MAC represented
                in unsigned integer specifying time in octet units (80 nanoseconds)."
        DEFVAL  { default }
        ::= { wfFddiEntry 35 }

    wfFDDIHardwareFilter OBJECT-TYPE
        SYNTAX  INTEGER {
                    enable(1),
                    disable(2)
                }
        ACCESS  read-write
        STATUS  mandatory
        DESCRIPTION
                "Hardware filter (CAM) parameter."
        DEFVAL  { disable }
        ::= { wfFddiEntry 36 }

    wfFDDISmtEnable OBJECT-TYPE
        SYNTAX  INTEGER {
                    enable(1),
                    disable(2)
                }
        ACCESS  read-write
        STATUS  mandatory
        DESCRIPTION
                "Enable Station Management periodic timer and NIF protocol."
        DEFVAL  { enable }
        ::= { wfFddiEntry 37 }

    wfFDDITxQueueLength OBJECT-TYPE
        SYNTAX  INTEGER
        ACCESS  read-only
        STATUS  mandatory
        DESCRIPTION
                "Current Transmit Queue Length"
        ::= { wfFddiEntry 38 }

    wfFDDIRxQueueLength OBJECT-TYPE
        SYNTAX  INTEGER
        ACCESS  read-only
        STATUS  mandatory
        DESCRIPTION
                "Current Receive Queue Length"
        ::= { wfFddiEntry 39 }

    wfFDDITxClipFrames OBJECT-TYPE
        SYNTAX  Counter
        ACCESS  read-only
        STATUS  mandatory
        DESCRIPTION
                "Number of frames clipped in driver's transmit routine due to transmit
                congestion."
        ::= { wfFddiEntry 40 }

    wfFDDIRxReplenMisses OBJECT-TYPE
        SYNTAX  Counter
        ACCESS  read-only
        STATUS  mandatory
        DESCRIPTION
                "Number of packet buffer misses while attempting to replenish driver
                receive ring."
        ::= { wfFddiEntry 41 }

    wfFDDICfgTxQueueLength OBJECT-TYPE
        SYNTAX  INTEGER(0..255)
        ACCESS  read-write
        STATUS  mandatory
        DESCRIPTION
                "Configured Transmit Queue Length. Values other than zero over-ride
                the router selected values. A value of zero has a special meaning.
                Zero causes router based default values to be used. Values larger
                than the compiled ring size are truncated to the compiled ring
                size."
        ::= { wfFddiEntry 42 }

    wfFDDICfgRxQueueLength OBJECT-TYPE
        SYNTAX  INTEGER(0..255)
        ACCESS  read-write
        STATUS  mandatory
        DESCRIPTION
                "Configured Receive Queue Length. Values other than zero over-ride
                the router selected values. A value of zero has a special meaning.
                Zero cuases router based default values to be used. Values larger
                than the compiled ring size are truncated to the compiled ring
                size."
        ::= { wfFddiEntry 43 }

    wfFDDILineNumber OBJECT-TYPE
        SYNTAX  INTEGER
        ACCESS  read-write
        STATUS  mandatory
        DESCRIPTION
                "Logical line number associated with this driver entity."
        ::= { wfFddiEntry 44 }

    wfFDDIForcePeerTree OBJECT-TYPE
        SYNTAX  INTEGER {
                    enable(1),
                    disable(2)
                }
        ACCESS  read-write
        STATUS  mandatory
        DESCRIPTION
                "This attribute allows all FDDI Peer/Tree connections
                to reach the 'Thru' state. This is done to give the
                user some flexibility and allow them to Daisy Chain
                their Phy connections, mixing Tree & Peer connections.
                This type of daisy chaining DOES NOT conform to the
                SMT standard and is NOT recommended as it may result in
                a less than optimum token path. Normally when we have a
                Peer/Tree connection mix, we will wrap the connection,
                favoring PHY B."
        DEFVAL  { disable }
        ::= { wfFddiEntry 45 }

    wfFDDIInvalidFrameStatusRx OBJECT-TYPE
        SYNTAX  Counter
        ACCESS  read-only
        STATUS  mandatory
        DESCRIPTION
                "A count of the number of badly formed frames received off
                of the FDDI ring. These are frames which do not contain a
                valid Frame Status field of at least 3 control indicator
                symbols (i.e. E, A, C, flags)."
        ::= { wfFddiEntry 46 }

    wfFDDIRxOversizedFrames OBJECT-TYPE
        SYNTAX  Counter
        ACCESS  read-only
        STATUS  mandatory
        DESCRIPTION
                "Number of LLC frames received whose length exceeded the MTU."
        ::= { wfFddiEntry 47 }

    wfFDDIRxSmtOversizedFrames OBJECT-TYPE
        SYNTAX  Counter
        ACCESS  read-only
        STATUS  mandatory
        DESCRIPTION
                "Number of SMT frames received whose length exceeded the MTU."
        ::= { wfFddiEntry 48 }

    wfFDDIRxUndersizedFrames OBJECT-TYPE
        SYNTAX  Counter
        ACCESS  read-only
        STATUS  mandatory
        DESCRIPTION
                "Number of LLC frames received whose length was less than 20 bytes
                including the FC byte and a 4 byte CRC."
        ::= { wfFddiEntry 49 }

    wfFDDIRxSmtUndersizedFrames OBJECT-TYPE
        SYNTAX  Counter
        ACCESS  read-only
        STATUS  mandatory
        DESCRIPTION
                "Number of SMT frames received whose length was less than 37 bytes
                including the FC byte and a 4 byte CRC."
        ::= { wfFddiEntry 50 }

    wfFDDIModule OBJECT-TYPE
        SYNTAX  INTEGER {
                    one(1),
                    two(2),
                    three(3),
                    four(4)
                }
        ACCESS  read-only
        STATUS  mandatory
        DESCRIPTION
                "Module number for ASN platform, filled in by driver. For non-ASN
                platforms this attribute will not be used."
        ::= { wfFddiEntry 51 }

    wfFDDIActualNode OBJECT-TYPE
        SYNTAX  INTEGER {
                    one(1),
                    two(2)
                }
        ACCESS  read-only
        STATUS  mandatory
        DESCRIPTION
                "Actual Node number for ASN platform, filled in by
                driver. For non-ASN platforms, this attribute will not
                be used."
        ::= { wfFddiEntry 52 }

    wfFDDILastChange OBJECT-TYPE
        SYNTAX  TimeTicks
        ACCESS  read-only
        STATUS  mandatory
        DESCRIPTION
                "The value of SysUpTime at the time the interface entered it's current
                operational state (UP state).  SysUpTime is defined as the time (in
                hundredths of a second) since the network management portion of the
                system was last re-initialized.  Usually the time since boot."
        ::= { wfFddiEntry 53 }

    wfFDDIOutQLen OBJECT-TYPE
        SYNTAX  Gauge
        ACCESS  read-only
        STATUS  mandatory
        DESCRIPTION
                "The instantaneous current length of the output packet queue (in packets)."
        ::= { wfFddiEntry 54 }

    wfFDDIRxSmtOctets OBJECT-TYPE
        SYNTAX  Counter
        ACCESS  read-only
        STATUS  mandatory
        DESCRIPTION
                "Number of bytes received without error. This byte count
                only includes SMT frames (i.e. no MAC and LLC frames)."
        ::= { wfFddiEntry 55 }

    wfFDDIRxSmtFrames OBJECT-TYPE
        SYNTAX  Counter
        ACCESS  read-only
        STATUS  mandatory
        DESCRIPTION
                "Number of frames received without error. This frame count
                only includes SMT frames (i.e. no MAC and LLC frames)."
        ::= { wfFddiEntry 56 }

    wfFDDIIntProcessings OBJECT-TYPE
        SYNTAX  Counter
        ACCESS  read-only
        STATUS  mandatory
        DESCRIPTION
                "Counts the number of times the interrupt service
                routine has been called "
        ::= { wfFddiEntry 57 }

    wfFDDITxProcessings OBJECT-TYPE
        SYNTAX  Counter
        ACCESS  read-only
        STATUS  mandatory
        DESCRIPTION
                "Counts the number of times the transmit routine
                fsi_xmt_oper_act(), has been called "
        ::= { wfFddiEntry 58 }

    wfFDDIRxProcessings OBJECT-TYPE
        SYNTAX  Counter
        ACCESS  read-only
        STATUS  mandatory
        DESCRIPTION
                "Counts the number of times RINT processing takes place
                in the interrupt service routine. "
        ::= { wfFddiEntry 59 }

    wfFDDITxRNRProcessings OBJECT-TYPE
        SYNTAX  Counter
        ACCESS  read-only
        STATUS  mandatory
        DESCRIPTION
                "Counts the number of times the transmit complete routine
                fsi_xmt_cmpl(), has been called "
        ::= { wfFddiEntry 60 }

    wfFDDISmtRxProcessings OBJECT-TYPE
        SYNTAX  Counter
        ACCESS  read-only
        STATUS  mandatory
        DESCRIPTION
                "Counts the number of time RINT was processing was performed on the
                SMT receive ring."
        ::= { wfFddiEntry 61 }

    wfFDDIPhyALogPtr OBJECT-TYPE
        SYNTAX  INTEGER
        ACCESS  read-only
        STATUS  mandatory
        DESCRIPTION
                "Address of the Debug Phy Event Buffer for Phy A. This
                attribute is strictly for diagnostic purposes. The size
                of the buffer is 1028 bytes."
        ::= { wfFddiEntry 62 }

    wfFDDIPhyBLogPtr OBJECT-TYPE
        SYNTAX  INTEGER
        ACCESS  read-only
        STATUS  mandatory
        DESCRIPTION
                "Address of the Debug Phy Event Buffer for Phy B. This
                attribute is strictly for diagnostic purposes. The size
                of the buffer is 1028 bytes."
        ::= { wfFddiEntry 63 }

    wfFDDIPromiscuous OBJECT-TYPE
        SYNTAX  INTEGER {
                    enable(1),
                    disable(2)
                }
        ACCESS  read-write
        STATUS  mandatory
        DESCRIPTION
                "For now this attribute is used only in BNX code !!!
                The promiscuous parameter allows address filtering based on the
                destination MAC addresses.  When enabled, all frames are received,
                disabled indicates only frames destined for this local address
                and any functional group address are received."
        DEFVAL  { enable }
        ::= { wfFddiEntry 64 }

    wfFDDILLCFrameControl OBJECT-TYPE
        SYNTAX INTEGER {
                   async(1),
                   sync(2)
               }
        ACCESS  read-write
        STATUS  mandatory
        DESCRIPTION
               "Frame control used for LLC frames, using synchronous frames
                for reserved priority traffic when specified."
        DEFVAL  { async }
        ::= { wfFddiEntry 65 }

    wfFDDITurboBofl OBJECT-TYPE
        SYNTAX  INTEGER {
                    enable(1),
                    disable(2)
                }
        ACCESS  read-write
        STATUS  mandatory
        DESCRIPTION
		"DEBUG parameter - Turbo bofl enabled or disabled, by adjusting
		BoflNum and BoflLen bofl packets can be made to fill the links
		available bandwith. This function is not a faster parallel of 
		the wfFDDIBofl feature it does not opperate on a disabled LLC
		interface"

        DEFVAL  { disable }
        ::= { wfFddiEntry 66 }

    wfFDDIBoflNum OBJECT-TYPE
        SYNTAX  INTEGER(1..127)
        ACCESS  read-write
        STATUS  mandatory
        DESCRIPTION
                "DEBUG parameter - Number of breath of life packets per breath
                of life"
        DEFVAL  { 1 }
        ::= { wfFddiEntry 67 }

    wfFDDIBoflLen OBJECT-TYPE
        SYNTAX  INTEGER(22..4450)
        ACCESS  read-write
        STATUS  mandatory
        DESCRIPTION
                "DEBUG parameter - breath of life packet length"
        DEFVAL  { 200 }
        ::= { wfFddiEntry 68 }

    wfFddiSmtTable OBJECT-TYPE
        SYNTAX  SEQUENCE OF WfFddiSmtEntry
        ACCESS  not-accessible
        STATUS  mandatory
        DESCRIPTION
                "A list of SMT entries."
        ::= { wfFddiSmtGroup 2 }

    wfFddiSmtEntry OBJECT-TYPE
        SYNTAX  WfFddiSmtEntry
        ACCESS  not-accessible
        STATUS  mandatory
        DESCRIPTION
                "A SMT entry containing information common to a given SMT."
        INDEX   { wfFddiSmtSlot,
                  wfFddiSmtNode }
        ::= { wfFddiSmtTable 1 }

    WfFddiSmtEntry ::= SEQUENCE {
            wfFddiSmtSlot
                INTEGER,
            wfFddiSmtNode
                INTEGER,
            wfFddiSmtCct
                INTEGER,
            wfFddiSmtStationId
                OCTET STRING,
            wfFddiSmtOpVersionId
                INTEGER,
            wfFddiSmtMacCt
                INTEGER,
            wfFddiSmtNonMasterCt
                INTEGER,
            wfFddiSmtEcmState
                INTEGER,
            wfFddiSmtCfState
                INTEGER,
            wfFddiSmtBypassPresent
                INTEGER,
            wfFddiSmtRemoteDisconnectFlag
                INTEGER,
            wfFddiSmtStationStatus
                INTEGER,
            wfFddiSmtPeerWrapFlag
                INTEGER
        }

    wfFddiSmtSlot OBJECT-TYPE
        SYNTAX  INTEGER
        ACCESS  read-only
        STATUS  mandatory
        DESCRIPTION
                "Slot number associated with an SMT entity."
        ::= { wfFddiSmtEntry 1 }

    wfFddiSmtNode OBJECT-TYPE
        SYNTAX  INTEGER
        ACCESS  read-only
        STATUS  mandatory
        DESCRIPTION
                "Node/connector number associated with an SMT entity."
        ::= { wfFddiSmtEntry 2 }

    wfFddiSmtCct OBJECT-TYPE
        SYNTAX  INTEGER
        ACCESS  read-only
        STATUS  mandatory
        DESCRIPTION
                "Circuit number associated with an SMT entity."
        ::= { wfFddiSmtEntry 3 }

    wfFddiSmtStationId OBJECT-TYPE
        SYNTAX  OCTET STRING
        ACCESS  read-only
        STATUS  mandatory
        DESCRIPTION
                "Unique identifier of an FDDI station."
        ::= { wfFddiSmtEntry 4 }

    wfFddiSmtOpVersionId OBJECT-TYPE
        SYNTAX  INTEGER
        ACCESS  read-only
        STATUS  mandatory
        DESCRIPTION
                "The version that this station is using for its operation."
        ::= { wfFddiSmtEntry 5 }

    wfFddiSmtMacCt OBJECT-TYPE
        SYNTAX  INTEGER
        ACCESS  read-only
        STATUS  mandatory
        DESCRIPTION
                "The number of MACs in a station."
        ::= { wfFddiSmtEntry 6 }

    wfFddiSmtNonMasterCt OBJECT-TYPE
        SYNTAX  INTEGER
        ACCESS  read-only
        STATUS  mandatory
        DESCRIPTION
                "The number of non master ports (A, B, or S PORTs) in a station."
        ::= { wfFddiSmtEntry 7 }

    wfFddiSmtEcmState OBJECT-TYPE
        SYNTAX  INTEGER {
                    out(1),
                    in(2),
                    trace(3),
                    leave(4),
                    pathtest(5),
                    insert(6),
                    check(7),
                    deinsert(8)
                }
        ACCESS  read-only
        STATUS  mandatory
        DESCRIPTION
                "Indicates the current state of the ECM state machine."
        ::= { wfFddiSmtEntry 8 }

    wfFddiSmtCfState OBJECT-TYPE
        SYNTAX  INTEGER {
                    isolated(1),
                    wraps(2),
                    wrapa(3),
                    wrapb(4),
                    wrapab(5),
                    thru(6),
                    locala(7),
                    localb(8),
                    localab(9),
                    locals(10),
                    cwrapa(11),
                    cwrapb(12),
                    cwraps(13)
                }
        ACCESS  read-only
        STATUS  mandatory
        DESCRIPTION
                "The attachment configuration for a station."
        ::= { wfFddiSmtEntry 9 }

    wfFddiSmtBypassPresent OBJECT-TYPE
        SYNTAX  INTEGER {
                    true(1),
                    false(2)
                }
        ACCESS  read-only
        STATUS  mandatory
        DESCRIPTION
                "A flag indicating if the station has an optical bypass on its
                A/B port pair."
        ::= { wfFddiSmtEntry 10 }

    wfFddiSmtRemoteDisconnectFlag OBJECT-TYPE
        SYNTAX  INTEGER {
                    true(1),
                    false(2)
                }
        ACCESS  read-only
        STATUS  mandatory
        DESCRIPTION
                "A flag indicating that the station was remotely disconnected
                from the network as a result of receiving an 'wfFddiSmtStationAction'
                disconnect in a Parameter Management Frame. A station requires
                a Connect Action to rejoin & clear the flag."
        ::= { wfFddiSmtEntry 11 }

    wfFddiSmtStationStatus OBJECT-TYPE
        SYNTAX  INTEGER {
                    concatenated(1),
                    seperated(2),
                    thru(3)
                }
        ACCESS  read-only
        STATUS  mandatory
        DESCRIPTION
                "This variable indicates the current state of the primary and
                secondary paths within this station."
        ::= { wfFddiSmtEntry 12 }

    wfFddiSmtPeerWrapFlag OBJECT-TYPE
        SYNTAX  INTEGER {
                    true(1),
                    false(2)
                }
        ACCESS  read-only
        STATUS  mandatory
        DESCRIPTION
                "This variable assumes the value of the 'PeerWrapFlag' in CFM."
        ::= { wfFddiSmtEntry 13 }

    wfFddiSmtExtTable OBJECT-TYPE
        SYNTAX  SEQUENCE OF WfFddiSmtExtEntry
        ACCESS  not-accessible
        STATUS  mandatory
        DESCRIPTION
                "A list of SMT extension entries."
        ::= { wfFddiSmtGroup 3 }

    wfFddiSmtExtEntry OBJECT-TYPE
        SYNTAX  WfFddiSmtExtEntry
        ACCESS  not-accessible
        STATUS  mandatory
        DESCRIPTION
                "A SMT entry containing information common to a given SMT."
        INDEX   { wfFddiSmtExtSlot,
                  wfFddiSmtExtNode }
        ::= { wfFddiSmtExtTable 1 }

    WfFddiSmtExtEntry ::= SEQUENCE {
            wfFddiSmtDelete
                INTEGER,
            wfFddiSmtExtSlot
                INTEGER,
            wfFddiSmtExtNode
                INTEGER,
            wfFddiSmtExtCct
                INTEGER,
            wfFddiSmtHiVersionId
                INTEGER,
            wfFddiSmtLoVersionId
                INTEGER,
            wfFddiSmtManufacturerData
                OCTET STRING,
            wfFddiSmtUserData
                DisplayString,
            wfFddiSmtMibVersionId
                INTEGER,
            wfFddiSmtMasterCts
                INTEGER,
            wfFddiSmtAvailablePaths
                INTEGER,
            wfFddiSmtConfigCapabilities
                INTEGER,
            wfFddiSmtConfigPolicy
                INTEGER,
            wfFddiSmtStatRptPolicy
                INTEGER,
            wfFddiSmtTraceMaxExpiration
                INTEGER,
            wfFddiSmtTimeStamp
                OCTET STRING,
            wfFddiSmtTransitionTimeStamp
                OCTET STRING,
            wfFddiSmtDatProtocol
                INTEGER
        }

    wfFddiSmtDelete OBJECT-TYPE
        SYNTAX  INTEGER {
                    created(1),
                    deleted(2)
                }
        ACCESS  read-write
        STATUS  mandatory
        DESCRIPTION
                "Create/delete parameter, default = create."
        DEFVAL  { created }
        ::= { wfFddiSmtExtEntry 1 }

    wfFddiSmtExtSlot OBJECT-TYPE
        SYNTAX  INTEGER
        ACCESS  read-only
        STATUS  mandatory
        DESCRIPTION
                "Slot number associated with an SMT entity."
        ::= { wfFddiSmtExtEntry 2 }

    wfFddiSmtExtNode OBJECT-TYPE
        SYNTAX  INTEGER
        ACCESS  read-only
        STATUS  mandatory
        DESCRIPTION
                "Node/connector number associated with an SMT entity."
        ::= { wfFddiSmtExtEntry 3 }

    wfFddiSmtExtCct OBJECT-TYPE
        SYNTAX  INTEGER
        ACCESS  read-only
        STATUS  mandatory
        DESCRIPTION
                "Circuit number associated with an SMT entity."
        ::= { wfFddiSmtExtEntry 4 }

    wfFddiSmtHiVersionId OBJECT-TYPE
        SYNTAX  INTEGER {
                    id(2)
                }
        ACCESS  read-only
        STATUS  mandatory
        DESCRIPTION
                "The highest version of SMT that this station supports."
        DEFVAL  { id }
        ::= { wfFddiSmtExtEntry 5 }

    wfFddiSmtLoVersionId OBJECT-TYPE
        SYNTAX  INTEGER {
                    id(2)
                }
        ACCESS  read-only
        STATUS  mandatory
        DESCRIPTION
                "The lowest version of SMT that this station supports."
        DEFVAL  { id }
        ::= { wfFddiSmtExtEntry 6 }

    wfFddiSmtManufacturerData OBJECT-TYPE
        SYNTAX  OCTET STRING
        ACCESS  read-only
        STATUS  mandatory
        DESCRIPTION
                "Contains 32 Octets of manufacturer data. The first component,
                manufacturing OUI, is the 3 octet Organizationally Unique
                Identifier (OUI) assigned by IEEE. The second component,
                ManufacturerData, is the manufacturers data (29 octets)."
        ::= { wfFddiSmtExtEntry 7 }

    wfFddiSmtUserData OBJECT-TYPE
        SYNTAX  DisplayString
        ACCESS  read-write
        STATUS  mandatory
        DESCRIPTION
                "Contains 32 Octets of user defined information in ascii format."
        ::= { wfFddiSmtExtEntry 8 }

    wfFddiSmtMibVersionId OBJECT-TYPE
        SYNTAX  INTEGER {
                    id(1)
                }
        ACCESS  read-only
        STATUS  mandatory
        DESCRIPTION
                "The version of the FDDI MIB of this station."
        DEFVAL  { id }
        ::= { wfFddiSmtExtEntry 9 }

    wfFddiSmtMasterCts OBJECT-TYPE
        SYNTAX  INTEGER
        ACCESS  read-only
        STATUS  mandatory
        DESCRIPTION
                "The number of M ports in a node."
        ::= { wfFddiSmtExtEntry 10 }

    wfFddiSmtAvailablePaths OBJECT-TYPE
        SYNTAX  INTEGER {
                    p(1),
                    s(2),
                    l(4)
                }
        ACCESS  read-only
        STATUS  mandatory
        DESCRIPTION
                "A bit string that indicates the path types that are available
                in the station.

                The value initially takes the value 0, then for each type of
                path that this node has available, 2 raised to a power is added
                to the sum. The powers are according to the following table:

                     Path    Power
                     ----    -----
                     Primary   0
                     Secondary 1
                     Local     2

                For example, a station having Primary and Local paths available
                would have a value of 5 (2**0 + 2**2)."
        DEFVAL  { p }
        ::= { wfFddiSmtExtEntry 11 }

    wfFddiSmtConfigCapabilities OBJECT-TYPE
        SYNTAX  INTEGER {
                    avail(1),
                    ab(2)
                }
        ACCESS  read-only
        STATUS  mandatory
        DESCRIPTION
                "A bit string which indicates the configuration capabilities of
                a node.

                The 'Hold Available' bit indicates the support of the optional
                Hold function, which is controlled by 'wfFddiSmtConfigPolicy'.
                The 'CF-Wrap-AB' bit indicates that the station has the capability
                of performing a wrab_ab.

                The value is a sum. This value initially takes the value 0, then
                for each of the configuration policies currently enforced on the
                node, 2 raised to a power is added to the sum. The powers are
                according to the following table:

                Policy          Power
                ------          -----
                HoldAvailable     0
                CF_Wrap-AB        1"
        ::= { wfFddiSmtExtEntry 12 }

    wfFddiSmtConfigPolicy OBJECT-TYPE
        SYNTAX  INTEGER
        ACCESS  read-only
        STATUS  mandatory
        DESCRIPTION
                "A bit string representing the configuration policies currently
                desired in a node. 'Hold' is one of the terms used for the
                'Hold' flag."
        ::= { wfFddiSmtExtEntry 13 }

    wfFddiSmtStatRptPolicy OBJECT-TYPE
        SYNTAX  INTEGER {
                    enable(1),
                    disable(2)
                }
        ACCESS  read-write
        STATUS  mandatory
        DESCRIPTION
                "If ENABLED, indicates that the node will generate Status Report Frames
                (SRF) for its implemented events."
        DEFVAL  { enable }
        ::= { wfFddiSmtExtEntry 14 }

    wfFddiSmtTraceMaxExpiration OBJECT-TYPE
        SYNTAX  INTEGER(6001..256000)
        ACCESS  read-write
        STATUS  mandatory
        DESCRIPTION
                "Maximum propogation time for a Trace on an FDDI topology. The
                value is stored in milliseconds."
        DEFVAL  { 7000 }
        ::= { wfFddiSmtExtEntry 15 }

    wfFddiSmtTimeStamp OBJECT-TYPE
        SYNTAX  OCTET STRING
        ACCESS  read-only
        STATUS  mandatory
        DESCRIPTION
                "Holds the time of creation of the last Status Report Frame (SRF)."
        ::= { wfFddiSmtExtEntry 16 }

    wfFddiSmtTransitionTimeStamp OBJECT-TYPE
        SYNTAX  OCTET STRING
        ACCESS  read-only
        STATUS  mandatory
        DESCRIPTION
                "Holds the time of occurrence of the last condition or event."
        ::= { wfFddiSmtExtEntry 17 }

    wfFddiSmtDatProtocol OBJECT-TYPE
        SYNTAX  INTEGER {
                    enable(1),
                    disable(2)
                }
        ACCESS  read-write
        STATUS  mandatory
        DESCRIPTION
                "SMT will implement an optional ANSI duplicate address test
                involving periodic transmission of NSA NIF frames addressed
                to itself if enabled by this attribute."
        DEFVAL  { enable }
        ::= { wfFddiSmtExtEntry 18 }

    wfFddiSmtActionTable OBJECT-TYPE
        SYNTAX  SEQUENCE OF WfFddiSmtActionEntry
        ACCESS  not-accessible
        STATUS  mandatory
        DESCRIPTION
                "A list of SMT action entries."
        ::= { wfFddiSmtGroup 4 }

    wfFddiSmtActionEntry OBJECT-TYPE
        SYNTAX  WfFddiSmtActionEntry
        ACCESS  not-accessible
        STATUS  mandatory
        DESCRIPTION
                "An SMT entry containing actions common to a given SMT."
        INDEX   { wfFddiSmtActionSlot,
                  wfFddiSmtActionNode }
        ::= { wfFddiSmtActionTable 1 }

    WfFddiSmtActionEntry ::= SEQUENCE {
            wfFddiSmtActionDelete
                INTEGER,
            wfFddiSmtActionSlot
                INTEGER,
            wfFddiSmtActionNode
                INTEGER,
            wfFddiSmtActionCct
                INTEGER,
            wfFddiSmtStationAction
                INTEGER
        }

    wfFddiSmtActionDelete OBJECT-TYPE
        SYNTAX  INTEGER {
                    created(1),
                    deleted(2)
                }
        ACCESS  read-write
        STATUS  mandatory
        DESCRIPTION
                "Create/delete parameter, default = create."
        DEFVAL  { created }
        ::= { wfFddiSmtActionEntry 1 }

    wfFddiSmtActionSlot OBJECT-TYPE
        SYNTAX  INTEGER
        ACCESS  read-only
        STATUS  mandatory
        DESCRIPTION
                "Slot number associated with an SMT action entity."
        ::= { wfFddiSmtActionEntry 2 }

    wfFddiSmtActionNode OBJECT-TYPE
        SYNTAX  INTEGER
        ACCESS  read-only
        STATUS  mandatory
        DESCRIPTION
                "Node/connector number associated with an SMT action entity."
        ::= { wfFddiSmtActionEntry 3 }

    wfFddiSmtActionCct OBJECT-TYPE
        SYNTAX  INTEGER
        ACCESS  read-only
        STATUS  mandatory
        DESCRIPTION
                "Circuit number associated with an SMT action entity."
        ::= { wfFddiSmtActionEntry 4 }

    wfFddiSmtStationAction OBJECT-TYPE
        SYNTAX  INTEGER {
                    other(1),
                    connect(2),
                    disconnect(3),
                    pathtest(4),
                    selftest(5),
                    disablea(6),
                    disableb(7),
                    disablem(8)
                }
        ACCESS  read-write
        STATUS  mandatory
        DESCRIPTION
                "This object when read, always returns a value of other(1).
                The behavior of setting this variable to each of the acceptable
                values is as follows:

                Other:       Results in a BadValue error

                Connect:     Generates a connect signal to ECM
                             to begin a connection sequence. The
                             'wfFddiSmtRemoteDisconnectFlag' is
                             cleared on the setting of this
                             variable to 1.

                Disconnect:  Generates a disconnect signal to
                             ECM and sets the
                             'wfFddiSmtRemoteDisconnectFlag'
                             to TRUE.

                Path_Test:   Initiates a station path test.
                             The 'PathTest' variable is set
                             to 'Testing'. The results of
                             this action are not specified
                             in the standard.

                Self_test:   Initiates a station self test.
                             The results of this action are
                             not specified in the standard.
                Disable_A:   Disable_A causes a PC_Disable on the
                             A port if the A port mode is peer.

                Disable_B:   Disable_B causes a PC_Disable on the
                             B port if the B port mode is peer.

                Disable_M:   Disable_M causes a PC_Disable on all
                             M ports.

                Attempts to set this object to all other values results in a
                BadValue error. Agents may elect to return a BadValue error on
                attempts to set this variable to PathTest or SelfTest."
        ::= { wfFddiSmtActionEntry 5 }

    wfFddiMacTable OBJECT-TYPE
        SYNTAX  SEQUENCE OF WfFddiMacEntry
        ACCESS  not-accessible
        STATUS  mandatory
        DESCRIPTION
                "A list of MAC entries."
        ::= { wfFddiMacGroup 2 }

    wfFddiMacEntry OBJECT-TYPE
        SYNTAX  WfFddiMacEntry
        ACCESS  not-accessible
        STATUS  mandatory
        DESCRIPTION
                "A MAC entry containing information common to a given MAC."
        INDEX   { wfFddiMacSlot,
                  wfFddiMacNode }
        ::= { wfFddiMacTable 1 }

    WfFddiMacEntry ::= SEQUENCE {
            wfFddiMacSlot
                INTEGER,
            wfFddiMacNode
                INTEGER,
            wfFddiMacCct
                INTEGER,
            wfFddiMacUpstreamNbr
                OCTET STRING,
            wfFddiMacDownstreamNbr
                OCTET STRING,
            wfFddiMacSmtAddress
                OCTET STRING,
            wfFddiMacTNeg
                INTEGER,
            wfFddiMacRmtState
                INTEGER,
            wfFddiMacOldUpstreamNbr
                OCTET STRING,
            wfFddiMacOldDownstreamNbr
                OCTET STRING,
            wfFddiMacTokenCts
                OCTET STRING,
            wfFddiMacErrorCts
                OCTET STRING,
            wfFddiMacLostCts
                OCTET STRING,
            wfFddiMacDaFlag
                INTEGER,
            wfFddiMacUnaDaFlag
                INTEGER,
            wfFddiMacFrameErrorFlag
                INTEGER,
            wfFddiMacMaUnitDataAvailable
                INTEGER,
            wfFddiMacDownstreamPortType
                INTEGER
        }

    wfFddiMacSlot OBJECT-TYPE
        SYNTAX  INTEGER
        ACCESS  read-only
        STATUS  mandatory
        DESCRIPTION
                "Slot number associated with a MAC entity."
        ::= { wfFddiMacEntry 1 }

    wfFddiMacNode OBJECT-TYPE
        SYNTAX  INTEGER
        ACCESS  read-only
        STATUS  mandatory
        DESCRIPTION
                "Node/connector number associated with a MAC entity."
        ::= { wfFddiMacEntry 2 }

    wfFddiMacCct OBJECT-TYPE
        SYNTAX  INTEGER
        ACCESS  read-only
        STATUS  mandatory
        DESCRIPTION
                "Circuit number associated with a MAC entity."
        ::= { wfFddiMacEntry 3 }

    wfFddiMacUpstreamNbr OBJECT-TYPE
        SYNTAX  OCTET STRING
        ACCESS  read-only
        STATUS  mandatory
        DESCRIPTION
                "The MAC's upstream neighbor's long individual MAC address. It
                may be determined by the Neighbor Information Frame protocol.
                The value shall be reported as '00 00 00 00 00 00' if it is
                unknown. SMT uses the MSB form for representation of 48-bit
                addresses."
        ::= { wfFddiMacEntry 4 }

    wfFddiMacDownstreamNbr OBJECT-TYPE
        SYNTAX  OCTET STRING
        ACCESS  read-only
        STATUS  mandatory
        DESCRIPTION
                "The MAC's downstream neighbor's long individual MAC address. It
                may be determined by the Neighbor Information Frame protocol.
                The value shall be reported as '00 00 00 00 00 00' if it is
                unknown. SMT uses the MSB form for representation of 48-bit
                addresses."
        ::= { wfFddiMacEntry 5 }

    wfFddiMacSmtAddress OBJECT-TYPE
        SYNTAX  OCTET STRING
        ACCESS  read-only
        STATUS  mandatory
        DESCRIPTION
                "The 48 bit individual address of the MAC used for SMT frames.
                SMT uses the MSB form for representation of 48-bit addresses."
        ::= { wfFddiMacEntry 6 }

    wfFddiMacTNeg OBJECT-TYPE
        SYNTAX  INTEGER
        ACCESS  read-only
        STATUS  mandatory
        DESCRIPTION
                "The negotiated TTRT during the claim process represented as an
                unsigned integer specifying time in nanoseconds."
        ::= { wfFddiMacEntry 7 }

    wfFddiMacRmtState OBJECT-TYPE
        SYNTAX  INTEGER {
                    isolated(1),
                    nonop(2),
                    ringop(3),
                    detect(4),
                    nonopdup(5),
                    ringopdup(6),
                    directed(7),
                    trace(8)
                }
        ACCESS  read-only
        STATUS  mandatory
        DESCRIPTION
                "Indicates the current state of the Ring Management state machine."
        ::= { wfFddiMacEntry 8 }

    wfFddiMacOldUpstreamNbr OBJECT-TYPE
        SYNTAX  OCTET STRING
        ACCESS  read-only
        STATUS  mandatory
        DESCRIPTION
                "The previous value of the MAC's upstream neighbor's long
                individual MAC address. It has an initial value of the
                SMT-Unknown-MAC Address and is only modified as specified by
                the Neighbor Information Frame protocol. SMT uses the MSB
                form for representation of 48-bit addresses."
        ::= { wfFddiMacEntry 9 }

    wfFddiMacOldDownstreamNbr OBJECT-TYPE
        SYNTAX  OCTET STRING
        ACCESS  read-only
        STATUS  mandatory
        DESCRIPTION
                "The previous value of the MAC's downstream neighbor's long
                individual MAC address. It has an initial value of the
                SMT-Unknown-MAC Address and is only modified as specified by
                the Neighbor Information Frame protocol. SMT uses the MSB
                form for representation of 48-bit addresses."
        ::= { wfFddiMacEntry 10 }

    wfFddiMacTokenCts OBJECT-TYPE
        SYNTAX  OCTET STRING
        ACCESS  read-only
        STATUS  mandatory
        DESCRIPTION
                "A count that should as closely as possible match the number
                of times the station has received a token (total of
                non-restricted and restricted) on this MAC. This count is
                valuable for determination of network load."
        ::= { wfFddiMacEntry 11 }

    wfFddiMacErrorCts OBJECT-TYPE
        SYNTAX  OCTET STRING
        ACCESS  read-only
        STATUS  mandatory
        DESCRIPTION
                "A count of the number of frames that were detected in error by
                this MAC that had not been detected in error by another MAC."
        ::= { wfFddiMacEntry 12 }

    wfFddiMacLostCts OBJECT-TYPE
        SYNTAX  OCTET STRING
        ACCESS  read-only
        STATUS  mandatory
        DESCRIPTION
                "A count of the number of instances that this MAC detected a
                format error during frame reception such that the frame was
                stripped."
        ::= { wfFddiMacEntry 13 }

    wfFddiMacDaFlag OBJECT-TYPE
        SYNTAX  INTEGER {
                    true(1),
                    false(2)
                }
        ACCESS  read-only
        STATUS  mandatory
        DESCRIPTION
                "Duplicate Address Flag. An RMT flag used to indicate that the
                MAC under control has the same address as another MAC on the FDDI."
        ::= { wfFddiMacEntry 14 }

    wfFddiMacUnaDaFlag OBJECT-TYPE
        SYNTAX  INTEGER {
                    true(1),
                    false(2)
                }
        ACCESS  read-only
        STATUS  mandatory
        DESCRIPTION
                "A flag, UNDA_Flag, set when the upstream neighbor reports a
                duplicate address condition. Cleared once the condition clears."
        ::= { wfFddiMacEntry 15 }

    wfFddiMacFrameErrorFlag OBJECT-TYPE
        SYNTAX  INTEGER {
                    true(1),
                    false(2)
                }
        ACCESS  read-only
        STATUS  mandatory
        DESCRIPTION
                "Indicates the MAC Frame Error Condition is present when set.
                Cleared when the condition clears and on station initialization."
        ::= { wfFddiMacEntry 16 }

    wfFddiMacMaUnitDataAvailable OBJECT-TYPE
        SYNTAX  INTEGER {
                    true(1),
                    false(2)
                }
        ACCESS  read-only
        STATUS  mandatory
        DESCRIPTION
                "A flag indicating that the MAC is available for the transmission
                and reception of Protocol Data Units (PDUs). The MAC and LLC
                interface will be established when the wfFddiMacMaUnitDataEnable
                attribute is enabled."
        ::= { wfFddiMacEntry 17 }

    wfFddiMacDownstreamPortType OBJECT-TYPE
        SYNTAX  INTEGER {
                    typea(1),
                    typeb(2),
                    types(3),
                    typem(4),
                    typenone(5)
                }
        ACCESS  read-only
        STATUS  mandatory
        DESCRIPTION
                "Indicates the PC-Type of the first port that is downstream of
                this MAC (the exit port)."
        ::= { wfFddiMacEntry 18 }

    wfFddiMacExtTable OBJECT-TYPE
        SYNTAX  SEQUENCE OF WfFddiMacExtEntry
        ACCESS  not-accessible
        STATUS  mandatory
        DESCRIPTION
                "A list of MAC extension entries."
        ::= { wfFddiMacGroup 3 }

    wfFddiMacExtEntry OBJECT-TYPE
        SYNTAX  WfFddiMacExtEntry
        ACCESS  not-accessible
        STATUS  mandatory
        DESCRIPTION
                "A MAC entry containing information common to a given MAC."
        INDEX   { wfFddiMacExtSlot,
                  wfFddiMacExtNode }
        ::= { wfFddiMacExtTable 1 }

    WfFddiMacExtEntry ::= SEQUENCE {
            wfFddiMacDelete
                INTEGER,
            wfFddiMacExtSlot
                INTEGER,
            wfFddiMacExtNode
                INTEGER,
            wfFddiMacExtCct
                INTEGER,
            wfFddiMacFrameStatusFunctions
                INTEGER,
            wfFddiMacBridgeFunctions
                INTEGER,
            wfFddiMacTMaxCapability
                INTEGER,
            wfFddiMacTvxCapability
                INTEGER,
            wfFddiMacAvailablePaths
                INTEGER,
            wfFddiMacCurrentPath
                INTEGER,
            wfFddiMacDupAddrTest
                INTEGER,
            wfFddiMacRequestedPaths
                INTEGER,
            wfFddiMacCopiedCts
                Counter,
            wfFddiMacFrameErrorThreshold
                INTEGER,
            wfFddiMacFrameErrorRatio
                INTEGER,
            wfFddiMacHardwarePresent
                INTEGER,
            wfFddiMacMaUnitDataEnable
                INTEGER,
            wfFddiMacTvxExpiredCts
                Counter,
            wfFddiMacLateCts
                Counter,
            wfFddiMacRingOpCts
                Counter,
            wfFddiMacDuplicateTokenCts
                Counter
        }

    wfFddiMacDelete OBJECT-TYPE
        SYNTAX  INTEGER {
                    created(1),
                    deleted(2)
                }
        ACCESS  read-write
        STATUS  mandatory
        DESCRIPTION
                "Create/delete parameter, default = create."
        DEFVAL  { created }
        ::= { wfFddiMacExtEntry 1 }

    wfFddiMacExtSlot OBJECT-TYPE
        SYNTAX  INTEGER
        ACCESS  read-only
        STATUS  mandatory
        DESCRIPTION
                "Slot number associated with a MAC entity."
        ::= { wfFddiMacExtEntry 2 }

    wfFddiMacExtNode OBJECT-TYPE
        SYNTAX  INTEGER
        ACCESS  read-only
        STATUS  mandatory
        DESCRIPTION
                "Node/connector number associated with a MAC entity."
        ::= { wfFddiMacExtEntry 3 }

    wfFddiMacExtCct OBJECT-TYPE
        SYNTAX  INTEGER
        ACCESS  read-only
        STATUS  mandatory
        DESCRIPTION
                "Circuit number associated with a MAC entity."
        ::= { wfFddiMacExtEntry 4 }

    wfFddiMacFrameStatusFunctions OBJECT-TYPE
        SYNTAX  INTEGER {
                    repeat(1),
                    set(2),
                    clear(4)
                }
        ACCESS  read-only
        STATUS  mandatory
        DESCRIPTION
                "Indicates the MAC's optional Frame Status processing functions.

                   The value is a sum. This value initially takes the value 0,
                   then for each function present, 2 raised to a power is added
                   to the sum. The powers are according to the following table:

                   function        power
                   --------        -----
                   fs-repeating      0
                   fs-setting        1
                   fs-clearing       2"
        ::= { wfFddiMacExtEntry 5 }

    wfFddiMacBridgeFunctions OBJECT-TYPE
        SYNTAX  INTEGER {
                    transparent(1),
                    srcroute(2),
                    srt(4)
                }
        ACCESS  read-only
        STATUS  mandatory
        DESCRIPTION
                "Indicates the MAC's optional bridging functions.

                   The value is a sum. This value initially takes the value zero,
                   then for each function present, 2 raised to a power is added to
                   the sum. The powers are according to the following table:

                        Function        Power
                        --------        ----
                           tb             0 -- Transparent bridging active
                           sr             1 -- Src routing active
                          srt             2 -- Src routing transparent active"
        ::= { wfFddiMacExtEntry 6 }

    wfFddiMacTMaxCapability OBJECT-TYPE
        SYNTAX  INTEGER {
                    default(1336934400)
                }
        ACCESS  read-only
        STATUS  mandatory
        DESCRIPTION
                "Indicates the maximum time value (in nanoseconds) of 'wfFddiMacTMax'
                that this MAC can support."
        DEFVAL  { default }
        ::= { wfFddiMacExtEntry 7 }

    wfFddiMacTvxCapability OBJECT-TYPE
        SYNTAX  INTEGER {
                    default(5222400)
                }
        ACCESS  read-only
        STATUS  mandatory
        DESCRIPTION
                "Indicates the maximum time value (in nanoseconds) of 'wfFddiMacTvxValue'
                that this MAC can support."
        DEFVAL  { default }
        ::= { wfFddiMacExtEntry 8 }

    wfFddiMacAvailablePaths OBJECT-TYPE
        SYNTAX  INTEGER {
                    p(1),
                    s(2),
                    l(4)
                }
        ACCESS  read-only
        STATUS  mandatory
        DESCRIPTION
                "Indicates the paths available for this MAC.

                   The value is a sum. This value initially takes the value 0, then
                   for each type of PATH that this MAC has available, 2 raised to a
                   power is added to the sum. The powers are according to the
                   following table:

                   Path        Power
                   ----        -----
                   Primary       0
                   Secondary     1
                   Local         2"
        DEFVAL  { p }
        ::= { wfFddiMacExtEntry 9 }

    wfFddiMacCurrentPath OBJECT-TYPE
        SYNTAX  INTEGER {
                    isolated(1),
                    local(2),
                    secondary(3),
                    primary(4),
                    concatenated(5),
                    thru(6)
                }
        ACCESS  read-only
        STATUS  mandatory
        DESCRIPTION
                "Indicates the Path into which this MAC is currently inserted."
        DEFVAL  { isolated }
        ::= { wfFddiMacExtEntry 10 }

    wfFddiMacDupAddrTest OBJECT-TYPE
        SYNTAX  INTEGER {
                    none(1),
                    pass(2),
                    fail(3)
                }
        ACCESS  read-only
        STATUS  mandatory
        DESCRIPTION
                "The Duplicate Address test flag."
        DEFVAL  { none }
        ::= { wfFddiMacExtEntry 11 }

    wfFddiMacRequestedPaths OBJECT-TYPE
        SYNTAX  INTEGER {
                    local(1),
                    salt(2),
                    palt(4),
                    calt(8),
                    spref(16),
                    ppref(32),
                    cpref(64),
                    thru(128)
                }
        ACCESS  read-only
        STATUS  mandatory
        DESCRIPTION
                "Contains a list of Permitted Paths which specifies the Path(s)
                into which the MAC may be inserted.

                The value is a sum which represents the individual paths that
                are desired. This value initially takes the value zero, then
                for each type of PATH that this node is, 2 raised to a power is
                added to the sum. The powers are according to the following table:

                                       Path  Power
                                       ----  -----
                                      local    0
                        secondary-alternate    1
                          primary-alternate    2
                     concatenated-alternate    3
                        secondary-preferred    4
                          primary-preferred    5
                     concatenated-preferred    6
                                       thru    7"
        DEFVAL  { palt }
        ::= { wfFddiMacExtEntry 12 }

    wfFddiMacCopiedCts OBJECT-TYPE
        SYNTAX  Counter
        ACCESS  read-only
        STATUS  mandatory
        DESCRIPTION
                "A count that should as closely as possible match the number of
                frames addressed to (A bit set) and successfully copied into
                the station's receive buffers (C bit set) by this MAC."
        ::= { wfFddiMacExtEntry 13 }

    wfFddiMacFrameErrorThreshold OBJECT-TYPE
        SYNTAX  INTEGER(1..65535)
        ACCESS  read-write
        STATUS  mandatory
        DESCRIPTION
                "Specifies the Mac Frame Error Threshold for determining when
                a MAC Frame Error Condition report will be generated (via an SRF
                Frame). If Mac Frame Error Ratio is greater than Mac Frame Error
                Threshold then the Mac Frame Error Condition exists. This Mac Frame
                Error Ratio is calculated periodically based on the attributes
                wfFddiMacErrorCts and wfFddiMacLostCts. A low value of Mac Frame
                Error Threshold will generate more frequent Mac Frame Error
                conditions if the wfFddiMacErrorCts and wfFddiMacLostCts counters
                are periodically increased. Therefore the user should set the Mac
                Frame Error Threshold (1..65535) in accordance with the volatility
                of the ring."
        DEFVAL  { 1 }
        ::= { wfFddiMacExtEntry 14 }

    wfFddiMacFrameErrorRatio OBJECT-TYPE
        SYNTAX  INTEGER
        ACCESS  read-only
        STATUS  mandatory
        DESCRIPTION
                "This variable is the value of the ratio:

                ((delta wfFddiMacLostCts + delta wfFddiMacErrorCts) /
                 (delta wfFddiMacFrameCts + delta wfFddiMacLostCts))
                  2**16)"
        ::= { wfFddiMacExtEntry 15 }

    wfFddiMacHardwarePresent OBJECT-TYPE
        SYNTAX  INTEGER {
                    notpresent(1),
                    present(2)
                }
        ACCESS  read-only
        STATUS  mandatory
        DESCRIPTION
                "This variable indicates the presence of underlying hardware
                support for this MAC object."
        DEFVAL  { present }
        ::= { wfFddiMacExtEntry 16 }

    wfFddiMacMaUnitDataEnable OBJECT-TYPE
        SYNTAX  INTEGER {
                    enable(1),
                    disable(2)
                }
        ACCESS  read-write
        STATUS  mandatory
        DESCRIPTION
                "A configurable attribute that specifies whether the MAC will be
                available for the transmission and reception of Protocol Data Units
                (PDUs). If enabled, the interface to the MAC entity will be available
                for the exchange of PDUs between the MAC and the local LLC entity
                when the ring becomes operational (i.e., LLC interface is established).
                Setting this attribute has no effect on the transfer and reception of
                MAC or SMT frames."
        DEFVAL  { enable }
        ::= { wfFddiMacExtEntry 17 }

    wfFddiMacTvxExpiredCts OBJECT-TYPE
        SYNTAX  Counter
        ACCESS  read-only
        STATUS  mandatory
        DESCRIPTION
                "A count that should as closely as possible match the number
                of times that TVX has expired."
        ::= { wfFddiMacExtEntry 18 }

    wfFddiMacLateCts OBJECT-TYPE
        SYNTAX  Counter
        ACCESS  read-only
        STATUS  mandatory
        DESCRIPTION
                "A count that should as closely as possible match the number of
                TRT expirations since this MAC was reset or a token was received."
        ::= { wfFddiMacExtEntry 19 }

    wfFddiMacRingOpCts OBJECT-TYPE
        SYNTAX  Counter
        ACCESS  read-only
        STATUS  mandatory
        DESCRIPTION
                "The count of the number of times the ring has entered the
                'Ring Operational' state from the `Ring Not Operational' state.
                This count is updated when a SM_MA_STATUS Indication of a change
                in the Ring_Operational state occurs. Because of implementatio
                considerations, this count may be less than the actual RingOp_Ct.
                It is not a requirement that this count be exact."
        ::= { wfFddiMacExtEntry 20 }

    wfFddiMacDuplicateTokenCts OBJECT-TYPE
        SYNTAX  Counter
        ACCESS  read-only
        STATUS  mandatory
        DESCRIPTION
                "The count of the number of times a Duplicate Token has been detected."
        ::= { wfFddiMacExtEntry 21 }

    wfFddiPathTable OBJECT-TYPE
        SYNTAX  SEQUENCE OF WfFddiPathEntry
        ACCESS  not-accessible
        STATUS  mandatory
        DESCRIPTION
                "A list of PATH entries."
        ::= { wfFddiPathGroup 2 }

    wfFddiPathEntry OBJECT-TYPE
        SYNTAX  WfFddiPathEntry
        ACCESS  not-accessible
        STATUS  mandatory
        DESCRIPTION
                "A PATH entry containing information common to a given PATH."
        INDEX   { wfFddiPathSlot,
                  wfFddiPathNode }
        ::= { wfFddiPathTable 1 }

    WfFddiPathEntry ::= SEQUENCE {
            wfFddiPathSlot
                INTEGER,
            wfFddiPathNode
                INTEGER,
            wfFddiPathCct
                INTEGER,
            wfFddiPathConfiguration
                OCTET STRING
        }

    wfFddiPathSlot OBJECT-TYPE
        SYNTAX  INTEGER
        ACCESS  read-only
        STATUS  mandatory
        DESCRIPTION
                "Slot number associated with a PATH entity."
        ::= { wfFddiPathEntry 1 }

    wfFddiPathNode OBJECT-TYPE
        SYNTAX  INTEGER
        ACCESS  read-only
        STATUS  mandatory
        DESCRIPTION
                "Node/connector number associated with a PATH entity."
        ::= { wfFddiPathEntry 2 }

    wfFddiPathCct OBJECT-TYPE
        SYNTAX  INTEGER
        ACCESS  read-only
        STATUS  mandatory
        DESCRIPTION
                "Circuit number associated with a PATH entity."
        ::= { wfFddiPathEntry 3 }

    wfFddiPathConfiguration OBJECT-TYPE
        SYNTAX  OCTET STRING
        ACCESS  read-only
        STATUS  mandatory
        DESCRIPTION
                "A circular list of resources on the path where each entry
                in the list consists of a resource type identifier (MAC
                or PORT), an index, and its CurrentPath. If the path is
                available to a resource in the node (as indicated by
                'wfFddiPortAvailablePaths' or 'wfFddiMacAvailablePaths')
                then that resource shall be included in the list. If the
                path is not available to a resource or the underlying
                hardware is not present, then that resource shall not be
                included in the list. Resources currently inserted in the
                Path shall appear in the list once in token order. Resources
                not currently inserted in the Path shall appear once in any
                position supported by the implementation."
        ::= { wfFddiPathEntry 4 }

    wfFddiPathExtTable OBJECT-TYPE
        SYNTAX  SEQUENCE OF WfFddiPathExtEntry
        ACCESS  not-accessible
        STATUS  mandatory
        DESCRIPTION
                "A list of PATH extension entries."
        ::= { wfFddiPathGroup 3 }

    wfFddiPathExtEntry OBJECT-TYPE
        SYNTAX  WfFddiPathExtEntry
        ACCESS  not-accessible
        STATUS  mandatory
        DESCRIPTION
                "A PATH entry containing information common to a given PATH."
        INDEX   { wfFddiPathExtSlot,
                  wfFddiPathExtNode }
        ::= { wfFddiPathExtTable 1 }

    WfFddiPathExtEntry ::= SEQUENCE {
            wfFddiPathDelete
                INTEGER,
            wfFddiPathExtSlot
                INTEGER,
            wfFddiPathExtNode
                INTEGER,
            wfFddiPathExtCct
                INTEGER,
            wfFddiPathTvxLowerBound
                INTEGER,
            wfFddiPathTMaxLowerBound
                INTEGER,
            wfFddiPathMaxTReq
                INTEGER
        }

    wfFddiPathDelete OBJECT-TYPE
        SYNTAX  INTEGER {
                    created(1),
                    deleted(2)
                }
        ACCESS  read-write
        STATUS  mandatory
        DESCRIPTION
                "Create/delete parameter, default = create."
        DEFVAL  { created }
        ::= { wfFddiPathExtEntry 1 }

    wfFddiPathExtSlot OBJECT-TYPE
        SYNTAX  INTEGER
        ACCESS  read-only
        STATUS  mandatory
        DESCRIPTION
                "Slot number associated with a Path entity."
        ::= { wfFddiPathExtEntry 2 }

    wfFddiPathExtNode OBJECT-TYPE
        SYNTAX  INTEGER
        ACCESS  read-only
        STATUS  mandatory
        DESCRIPTION
                "Node/connector number associated with a Path entity."
        ::= { wfFddiPathExtEntry 3 }

    wfFddiPathExtCct OBJECT-TYPE
        SYNTAX  INTEGER
        ACCESS  read-only
        STATUS  mandatory
        DESCRIPTION
                "Circuit number associated with a Path entity."
        ::= { wfFddiPathExtEntry 4 }

    wfFddiPathTvxLowerBound OBJECT-TYPE
        SYNTAX  INTEGER {
                    default(2500000)
                }
        ACCESS  read-write
        STATUS  mandatory
        DESCRIPTION
                "Specifies the minimum time value of 'wfFddiMacTvxValue'
                that shall be used  by any MAC that is configured in this
                path. The operational value of 'wfFddiMacTvxValue' is
                managed by setting this variable. This variable has the
                time value range of:
                     0 < wfFddiPathTvxLowerBound < wfFddiPathMaxTReq
                Changes to this attribute shall either satisfy the time
                value relationship:
                     wfFddiPathTvxLowerBound <= wfFddiMacTvxCapability
                of each of the MACS currently on the path, or be
                considered out of range. Time specified in nanoseconds.
                The initial value of wfFddiPathTvxLowerBound shall be
                2.500 msec."
        DEFVAL  { default }
        ::= { wfFddiPathExtEntry 5 }

    wfFddiPathTMaxLowerBound OBJECT-TYPE
        SYNTAX  INTEGER {
                    default(165000000)
                }
        ACCESS  read-write
        STATUS  mandatory
        DESCRIPTION
                "Specifies the minimum time value of 'wfFddiMACTMax' that
                shall be used by any MAC that is configured in this path.
                The operational value of 'wfFddiMacTMax' is managed by setting
                this attribute. This attribute has the time value range of:
                     wfFddiPathMaxTReq <= wfFddiPathTMaxLowerBound
                and an absolute time value range of
                     10msec <= wfFddiPathTMaxLowerBound.
                Changes to this aattribute shall either satisfy the time
                value relationship:
                     wfFddiPathTMaxLowerBound < wfFddiMacTMaxCapability
                of each of the MACs currently on the path, or be
                considered out of range. Time specified in nanoseconds.
                The initial value of wfFddiPathTMaxLowerBound shall be
                165 msec."
        DEFVAL  { default }
        ::= { wfFddiPathExtEntry 6 }

    wfFddiPathMaxTReq OBJECT-TYPE
        SYNTAX  INTEGER
        ACCESS  read-only
        STATUS  mandatory
        DESCRIPTION
                "This variable is the T_Req_value passed to the MAC. Without
                having detected a duplicate, the time value of this variable
                shall assume the maximum supported time value which is less
                than or equal to the time value of wfFDDIMacTReq. When a MAC
                has an address detected as a duplicate, it may use a time
                value for this variable greater than the time value of
                wfFddiPathTMaxLowerBound. A station shall cause claim when the
                new T_Req may cause the value of T_Neg to change in the claim
                process (i.e., time value new T_Req < T_Neg, or old T_Req =
                T_Neg). This value is encoded in nanoseconds. The name of
                this attribute in the IETF MIB is FddiMibMACTReq."
        ::= { wfFddiPathExtEntry 7 }

    wfFddiPortTable OBJECT-TYPE
        SYNTAX  SEQUENCE OF WfFddiPortEntry
        ACCESS  not-accessible
        STATUS  mandatory
        DESCRIPTION
                "A list of PORT entries."
        ::= { wfFddiPortGroup 2 }

    wfFddiPortEntry OBJECT-TYPE
        SYNTAX  WfFddiPortEntry
        ACCESS  not-accessible
        STATUS  mandatory
        DESCRIPTION
                "A PORT entry containing information common to a given PORT."
        INDEX   { wfFddiPortSlot,
                  wfFddiPortNode,
                  wfFddiPortIndex }
        ::= { wfFddiPortTable 1 }

    WfFddiPortEntry ::= SEQUENCE {
            wfFddiPortSlot
                INTEGER,
            wfFddiPortNode
                INTEGER,
            wfFddiPortCct
                INTEGER,
            wfFddiPortIndex
                INTEGER,
            wfFddiPortPcType
                INTEGER,
            wfFddiPortPcNeighbor
                INTEGER,
            wfFddiPortPcmState
                INTEGER,
            wfFddiPortRequestedPaths
                INTEGER,
            wfFddiPortBsFlag
                INTEGER,
            wfFddiPortLerFlag
                INTEGER,
            wfFddiPortConnectState
                INTEGER,
            wfFddiPortMacIndicated
                INTEGER
        }

    wfFddiPortSlot OBJECT-TYPE
        SYNTAX  INTEGER
        ACCESS  read-only
        STATUS  mandatory
        DESCRIPTION
                "Slot number associated with a PORT entity."
        ::= { wfFddiPortEntry 1 }

    wfFddiPortNode OBJECT-TYPE
        SYNTAX  INTEGER
        ACCESS  read-only
        STATUS  mandatory
        DESCRIPTION
                "Node/connector number associated with a PORT entity."
        ::= { wfFddiPortEntry 2 }

    wfFddiPortCct OBJECT-TYPE
        SYNTAX  INTEGER
        ACCESS  read-only
        STATUS  mandatory
        DESCRIPTION
                "Circuit number associated with a PORT entity."
        ::= { wfFddiPortEntry 3 }

    wfFddiPortIndex OBJECT-TYPE
        SYNTAX  INTEGER
        ACCESS  read-only
        STATUS  mandatory
        DESCRIPTION
                "A unique value for each PORT associated with each
                slot/connector pair."
        ::= { wfFddiPortEntry 4 }

    wfFddiPortPcType OBJECT-TYPE
        SYNTAX  INTEGER {
                    a(1),
                    b(2),
                    s(3),
                    m(4),
                    none(5)
                }
        ACCESS  read-only
        STATUS  mandatory
        DESCRIPTION
                "The physical connector type of the local PORT."
        ::= { wfFddiPortEntry 5 }

    wfFddiPortPcNeighbor OBJECT-TYPE
        SYNTAX  INTEGER {
                    a(1),
                    b(2),
                    s(3),
                    m(4),
                    unknown(5)
                }
        ACCESS  read-only
        STATUS  mandatory
        DESCRIPTION
                "The physical connector type of the remote PORT."
        ::= { wfFddiPortEntry 6 }

    wfFddiPortPcmState OBJECT-TYPE
        SYNTAX  INTEGER {
                    off(1),
                    break(2),
                    trace(3),
                    connect(4),
                    next(5),
                    signal(6),
                    join(7),
                    verify(8),
                    active(9),
                    maint(10)
                }
        ACCESS  read-only
        STATUS  mandatory
        DESCRIPTION
                "State of Physical State Machine."
        ::= { wfFddiPortEntry 7 }

    wfFddiPortRequestedPaths OBJECT-TYPE
        SYNTAX  INTEGER
        ACCESS  read-only
        STATUS  mandatory
        DESCRIPTION
                "This variable is a list of permitted paths where each list
                element defines the Port's permitted paths. The first octet
                corresponds to 'none', the second octet to 'tree' and the
                third octet to 'peer'."
        ::= { wfFddiPortEntry 8 }

    wfFddiPortBsFlag OBJECT-TYPE
        SYNTAX  INTEGER {
                    true(1),
                    false(2)
                }
        ACCESS  read-only
        STATUS  mandatory
        DESCRIPTION
                "Break State Flag - A PCM flag used to indicate that the PCM
                state Machine is not leaving the Break State in an expected
                time interval & a problem is suspected."
        ::= { wfFddiPortEntry 9 }

    wfFddiPortLerFlag OBJECT-TYPE
        SYNTAX  INTEGER {
                    true(1),
                    false(2)
                }
        ACCESS  read-only
        STATUS  mandatory
        DESCRIPTION
                "The condition becomes active when the value of
                'wfFddiPortLerEstimate' is <= 'wfFddiPortLerAlarm'. This will
                 be reported with Status Report Frames (SRF)."
        ::= { wfFddiPortEntry 10 }

    wfFddiPortConnectState OBJECT-TYPE
        SYNTAX  INTEGER {
                    disabled(1),
                    connecting(2),
                    standby(3),
                    active(4),
                    unknown(5)
                }
        ACCESS  read-only
        STATUS  mandatory
        DESCRIPTION
                "A variable from PCM to other management entities indicating
                the state of the connection."
        ::= { wfFddiPortEntry 11 }

    wfFddiPortMacIndicated OBJECT-TYPE
        SYNTAX  INTEGER {
                    ff(1),
                    ft(2),
                    tf(3),
                    tt(4)
                }
        ACCESS  read-only
        STATUS  mandatory
        DESCRIPTION
                "The indications (T_Val(9), R_Val(9)) in PC-Signalling, of the
                intent to place a MAC in the output token path to a PORT."
        ::= { wfFddiPortEntry 12 }

    wfFddiPortExtTable OBJECT-TYPE
        SYNTAX  SEQUENCE OF WfFddiPortExtEntry
        ACCESS  not-accessible
        STATUS  mandatory
        DESCRIPTION
                "A list of PORT extension entries."
        ::= { wfFddiPortGroup 3 }

    wfFddiPortExtEntry OBJECT-TYPE
        SYNTAX  WfFddiPortExtEntry
        ACCESS  not-accessible
        STATUS  mandatory
        DESCRIPTION
                "A PORT entry containing information common to a given PORT."
        INDEX   { wfFddiPortExtSlot,
                  wfFddiPortExtNode,
                  wfFddiPortExtIndex }
        ::= { wfFddiPortExtTable 1 }

    WfFddiPortExtEntry ::= SEQUENCE {
            wfFddiPortDelete
                INTEGER,
            wfFddiPortExtSlot
                INTEGER,
            wfFddiPortExtNode
                INTEGER,
            wfFddiPortExtCct
                INTEGER,
            wfFddiPortExtIndex
                INTEGER,
            wfFddiPortConnectionPolicies
                INTEGER,
            wfFddiPortCurrentPath
                INTEGER,
            wfFddiPortMacPlacement
                INTEGER,
            wfFddiPortAvailablePaths
                INTEGER,
            wfFddiPortPmdClass
                INTEGER,
            wfFddiPortConnectionCapabilities
                INTEGER,
            wfFddiPortEbErrorCts
                INTEGER,
            wfFddiPortLctFailCts
                Counter,
            wfFddiPortLerEstimate
                INTEGER,
            wfFddiPortLemRejectCts
                Counter,
            wfFddiPortLemCts
                Counter,
            wfFddiPortLerCutOff
                INTEGER,
            wfFddiPortLerAlarm
                INTEGER,
            wfFddiPortPcWithhold
                INTEGER,
            wfFddiPortHardwarePresent
                INTEGER
        }

    wfFddiPortDelete OBJECT-TYPE
        SYNTAX  INTEGER {
                    created(1),
                    deleted(2)
                }
        ACCESS  read-write
        STATUS  mandatory
        DESCRIPTION
                "Create/delete parameter, default = create."
        DEFVAL  { created }
        ::= { wfFddiPortExtEntry 1 }

    wfFddiPortExtSlot OBJECT-TYPE
        SYNTAX  INTEGER
        ACCESS  read-only
        STATUS  mandatory
        DESCRIPTION
                "Slot number associated with a Port entity."
        ::= { wfFddiPortExtEntry 2 }

    wfFddiPortExtNode OBJECT-TYPE
        SYNTAX  INTEGER
        ACCESS  read-only
        STATUS  mandatory
        DESCRIPTION
                "Node/connector number associated with a Port entity."
        ::= { wfFddiPortExtEntry 3 }

    wfFddiPortExtCct OBJECT-TYPE
        SYNTAX  INTEGER
        ACCESS  read-only
        STATUS  mandatory
        DESCRIPTION
                "Circuit number associated with a Port entity."
        ::= { wfFddiPortExtEntry 4 }

    wfFddiPortExtIndex OBJECT-TYPE
        SYNTAX  INTEGER
        ACCESS  read-only
        STATUS  mandatory
        DESCRIPTION
                "A unique value for each PORT associated with each
                slot/connector pair."
        ::= { wfFddiPortExtEntry 5 }

    wfFddiPortConnectionPolicies OBJECT-TYPE
        SYNTAX  INTEGER {
                    maclct(1),
                    macloop(2)
                }
        ACCESS  read-only
        STATUS  mandatory
        DESCRIPTION
                "A value representing the PORT's connection policies desired in
                the node. The value of 'pc-mac-lct' (i.e. PCM MAC LinkConfidence
                Test) is a term used in the PC_MAC_LCT Flag. The value of
                'pc-mac-loop' is a term used in the PC_MAC_LOOP flag.

                The value is a sum. This value initially takes the value zero,
                then for each PORT policy, 2 raised to a power is added to the
                sum. The powers are according to the following table:

                             Policy  Power
                             ------  -----
                         pc-mac-lct    0
                        pc-mac-loop    1"
        DEFVAL  { maclct }
        ::= { wfFddiPortExtEntry 6 }

    wfFddiPortCurrentPath OBJECT-TYPE
        SYNTAX  INTEGER {
                    isolated(1),
                    local(2),
                    secondary(3),
                    primary(4),
                    concatenated(5),
                    thru(6)
                }
        ACCESS  read-only
        STATUS  mandatory
        DESCRIPTION
                "Indicates the Path(s) into which this PORT is currently inserted."
        DEFVAL  { isolated }
        ::= { wfFddiPortExtEntry 7 }

    wfFddiPortMacPlacement OBJECT-TYPE
        SYNTAX  INTEGER
        ACCESS  read-only
        STATUS  mandatory
        DESCRIPTION
                "Indicates the MAC, if any, whose transmit path exits the station
                via this PORT. The value shall be zero if there is no MAC associated
                with the PORT."
        ::= { wfFddiPortExtEntry 8 }

    wfFddiPortAvailablePaths OBJECT-TYPE
        SYNTAX  INTEGER {
                    p(1),
                    s(2),
                    l(4)
                }
        ACCESS  read-only
        STATUS  mandatory
        DESCRIPTION
                "Indicates the Paths which are available to this Port. In the
                absence of faults, the A & B ports will always have both the
                Primary & Secondary paths available.

                The value is a sum. This value initially takes the value 0,
                then for each type of PATH that this port has available, 2
                raised to a power is added to the sum. The powers are according
                to the following table:

                      Path           Power
                      ----           -----
                     Primary           0
                   Secondary           1
                       Local           2"
        ::= { wfFddiPortExtEntry 9 }

    wfFddiPortPmdClass OBJECT-TYPE
        SYNTAX  INTEGER {
                    multimode(1),
                    mode1(2),
                    mode2(3),
                    sonet(4),
                    fiber(5),
                    twistedpair(6),
                    unknown(7),
                    unspecified(8)
                }
        ACCESS  read-only
        STATUS  mandatory
        DESCRIPTION
                "Indicates the Path(s) into which this PORT is currently inserted."
        ::= { wfFddiPortExtEntry 10 }

    wfFddiPortConnectionCapabilities OBJECT-TYPE
        SYNTAX  INTEGER {
                    maclct(1),
                    macloop(2)
                }
        ACCESS  read-only
        STATUS  mandatory
        DESCRIPTION
                "A value that indicates the connection capabilities of the port.
                The 'pc-mac-lct' bit indicates that the station has the capability
                of setting the PC_MAC_LCT Flag. The 'pc-mac-loop' bit indicates
                that the station has the capability of setting the PC_MAC_LOOP Flag.

                The value is a sum. This value initially takes the value zero,
                then for each PORT policy, 2 raised to a power is added to the
                sum. The powers are according to the following table:

                         Capability  Power
                         ----------  -----
                         pc-mac-lct    0
                        pc-mac-loop    1"
        DEFVAL  { maclct }
        ::= { wfFddiPortExtEntry 11 }

    wfFddiPortEbErrorCts OBJECT-TYPE
        SYNTAX  INTEGER
        ACCESS  read-only
        STATUS  mandatory
        DESCRIPTION
                "The count of the number of elasticity buffer errors for a
                particular PHY. The elasticity buffer is used to account for
                clock tolerances between stations"
        ::= { wfFddiPortExtEntry 12 }

    wfFddiPortLctFailCts OBJECT-TYPE
        SYNTAX  Counter
        ACCESS  read-only
        STATUS  mandatory
        DESCRIPTION
                "The count of the consecutive times the link confidence test
                (LCT) has failed during Connection Management."
        ::= { wfFddiPortExtEntry 13 }

    wfFddiPortLerEstimate OBJECT-TYPE
        SYNTAX  INTEGER(4..15)
        ACCESS  read-only
        STATUS  mandatory
        DESCRIPTION
                "A long term average of the link error rate. It ranges from
                10**-4 to 10**-15 and is reported as the absolute value of the
                base 10 logarithm."
        DEFVAL  { 15 }
        ::= { wfFddiPortExtEntry 14 }

    wfFddiPortLemRejectCts OBJECT-TYPE
        SYNTAX  Counter
        ACCESS  read-only
        STATUS  mandatory
        DESCRIPTION
                "A link error monitoring count of the times that a link has
                been rejected."
        ::= { wfFddiPortExtEntry 15 }

    wfFddiPortLemCts OBJECT-TYPE
        SYNTAX  Counter
        ACCESS  read-only
        STATUS  mandatory
        DESCRIPTION
                "The aggregate link error moniitor error count, set to 0 only
                on station initialization."
        ::= { wfFddiPortExtEntry 16 }

    wfFddiPortLerCutOff OBJECT-TYPE
        SYNTAX  INTEGER(4..15)
        ACCESS  read-write
        STATUS  mandatory
        DESCRIPTION
                "The link err rate estimate at which a link connection will be
                broken. It ranges from 10**-4 to 10**-15 and is reported as the
                absolute value of the base 10 logarithm."
        DEFVAL  { 7 }
        ::= { wfFddiPortExtEntry 17 }

    wfFddiPortLerAlarm OBJECT-TYPE
        SYNTAX  INTEGER(4..15)
        ACCESS  read-write
        STATUS  mandatory
        DESCRIPTION
                "The link err rate estimate at which a link connection will
                generate an alarm. It ranges from 10**-4 to 10**-15 and is
                reported as the absolute value of the base 10 logarithm of
                the estimate."
        DEFVAL  { 8 }
        ::= { wfFddiPortExtEntry 18 }

    wfFddiPortPcWithhold OBJECT-TYPE
        SYNTAX  INTEGER {
                    none(1),
                    mtom(2),
                    otherincompatible(3),
                    pathnotavailable(4)
                }
        ACCESS  read-only
        STATUS  mandatory
        DESCRIPTION
                "A variable from PCM to other management entities containing
                the reason for withholding a connection."
        DEFVAL  { none }
        ::= { wfFddiPortExtEntry 19 }

    wfFddiPortHardwarePresent OBJECT-TYPE
        SYNTAX  INTEGER {
                    notpresent(1),
                    present(2)
                }
        ACCESS  read-only
        STATUS  mandatory
        DESCRIPTION
                "This variable indicates the presence of underlying hardware
                support for this port object."
        DEFVAL  { present }
        ::= { wfFddiPortExtEntry 20 }

    wfFddiPortActionTable OBJECT-TYPE
        SYNTAX  SEQUENCE OF WfFddiPortActionEntry
        ACCESS  not-accessible
        STATUS  mandatory
        DESCRIPTION
                "A list of Port Action entries."
        ::= { wfFddiPortGroup 4 }

    wfFddiPortActionEntry OBJECT-TYPE
        SYNTAX  WfFddiPortActionEntry
        ACCESS  not-accessible
        STATUS  mandatory
        DESCRIPTION
                "A PORT entry containing actions common to a given PORT."
        INDEX   { wfFddiPortActionSlot,
                  wfFddiPortActionNode,
                  wfFddiPortActionIndex }
        ::= { wfFddiPortActionTable 1 }

    WfFddiPortActionEntry ::= SEQUENCE {
            wfFddiPortActionDelete
                INTEGER,
            wfFddiPortActionSlot
                INTEGER,
            wfFddiPortActionNode
                INTEGER,
            wfFddiPortActionCct
                INTEGER,
            wfFddiPortActionIndex
                INTEGER,
            wfFddiPortAction
                INTEGER
        }

    wfFddiPortActionDelete OBJECT-TYPE
        SYNTAX  INTEGER {
                    created(1),
                    deleted(2)
                }
        ACCESS  read-write
        STATUS  mandatory
        DESCRIPTION
                "Create/delete parameter, default = create."
        DEFVAL  { created }
        ::= { wfFddiPortActionEntry 1 }

    wfFddiPortActionSlot OBJECT-TYPE
        SYNTAX  INTEGER
        ACCESS  read-only
        STATUS  mandatory
        DESCRIPTION
                "Slot number associated with a PORT action entity."
        ::= { wfFddiPortActionEntry 2 }

    wfFddiPortActionNode OBJECT-TYPE
        SYNTAX  INTEGER
        ACCESS  read-only
        STATUS  mandatory
        DESCRIPTION
                "Node/connector number associated with a PORT action entity."
        ::= { wfFddiPortActionEntry 3 }

    wfFddiPortActionCct OBJECT-TYPE
        SYNTAX  INTEGER
        ACCESS  read-only
        STATUS  mandatory
        DESCRIPTION
                "Circuit number associated with a PORT action entity."
        ::= { wfFddiPortActionEntry 4 }

    wfFddiPortActionIndex OBJECT-TYPE
        SYNTAX  INTEGER
        ACCESS  read-only
        STATUS  mandatory
        DESCRIPTION
                "A unique value for each PORT associated with each
                slot/connector pair."
        ::= { wfFddiPortActionEntry 5 }

    wfFddiPortAction OBJECT-TYPE
        SYNTAX  INTEGER {
                    other(1),
                    maint(2),
                    enable(3),
                    disable(4),
                    start(5),
                    stop(6)
                }
        ACCESS  read-write
        STATUS  mandatory
        DESCRIPTION
                "Causes a control signal to be generated with a control_action
                of 'Signal' and the 'variable' parameter set with the
                appropriate value (i.e. PC_Maint, PC_Enable, PC_Disable, PC_Start,
                or PC_Stop). These signals are used to initiate a state change
                within Connection Management"
        ::= { wfFddiPortActionEntry 6 }


    wfFddiXLineCfgTable OBJECT-TYPE
        SYNTAX	SEQUENCE OF WfFddiXLineCfgEntry
        ACCESS	not-accessible
        STATUS	mandatory
        DESCRIPTION
                "FDDI switch configuration line record"
        ::= { wfFddiXGroup 1 }

    wfFddiXLineCfgEntry OBJECT-TYPE
        SYNTAX	WfFddiXLineCfgEntry
        ACCESS	not-accessible
        STATUS	mandatory
        DESCRIPTION
                "An FDDI entry containing configuration parameters about 
                 an FDDI interface."
        INDEX	{ wfFddiXLineCfgSlot,
    		  wfFddiXLineCfgNode }
        ::= { wfFddiXLineCfgTable 1 }

    WfFddiXLineCfgEntry ::= SEQUENCE {
    	    wfFddiXLineCfgDelete
    		INTEGER,
            wfFddiXLineCfgEnable
                INTEGER,
            wfFddiXLineCfgLossOfServiceTmo
                INTEGER,
            wfFddiXLineCfgSmtEnable
                INTEGER,
            wfFddiXLineCfgSmtDatProtocol
                INTEGER,
            wfFddiXLineCfgLineNumber
                INTEGER,
            wfFddiXLineCfgForcePeerTree
                INTEGER,
            wfFddiXLineCfgSlot
                INTEGER,
            wfFddiXLineCfgModule
                INTEGER,
            wfFddiXLineCfgActualNode
                INTEGER,
            wfFddiXLineCfgNode
                INTEGER,
            wfFddiXLineCfgSmtIndex
                INTEGER,
            wfFddiXLineCfgIfIndex
                INTEGER
        }


    wfFddiXLineCfgDelete OBJECT-TYPE
        SYNTAX	INTEGER {
    		    create(1),
    		    delete(2)
    		}
        ACCESS	read-write
        STATUS	mandatory
        DESCRIPTION
                "FDDI interface table create/delete object. The default 
                 setting is create."
        DEFVAL	{ create }
        ::= { wfFddiXLineCfgEntry 1 }

    wfFddiXLineCfgEnable OBJECT-TYPE
        SYNTAX	INTEGER {
    		    enable(1),
    		    disable(2)
    		}
        ACCESS	read-write
        STATUS	mandatory
        DESCRIPTION
                "FDDI interface enable/disable object. The  default 
                 setting is enable."
        DEFVAL	{ enable }
        ::= { wfFddiXLineCfgEntry 2 }

    wfFddiXLineCfgLossOfServiceTmo OBJECT-TYPE
        SYNTAX	INTEGER (0..2147483647)
        ACCESS	read-write
        STATUS	mandatory
        DESCRIPTION
                "This timer (in seconds) provides debounce functionality for 
                 an FDDI interface. 

                 When the FDDI ring becomes non-operational, the LLC
                 interface will be disabled if the following conditions
                 hold TRUE:

                        1. fddimibMACMAUnitdataEnable (contained in
                           fddimibMACTable of rfc1512.mib) is enabled
                        2. This FDDI interface has been unavailable for
                           wfFddiXLineCfgLossOfServiceTmo seconds.

                 If the FDDI interface becomes enabled before
                 wfFddiXLineCfgLossOfServiceTmo expires, then the 
                 timer is cancelled and nothing occurs. 

                 This debounce timer may be disabled by setting it
                 to 0. In this case, when the FDDI interface becomes
                 non-operational, the LLC interface will be notified 
                 right away."
        DEFVAL	{ 3 }
        ::= { wfFddiXLineCfgEntry 3 }

    wfFddiXLineCfgSmtEnable OBJECT-TYPE
        SYNTAX	INTEGER {
    		    enable(1),
    		    disable(2)
    		}
        ACCESS	read-write
        STATUS	mandatory
        DESCRIPTION
                "Enable Station Management periodic timers and NIF protocol."
        DEFVAL	{ enable }
        ::= { wfFddiXLineCfgEntry 4 }

    wfFddiXLineCfgSmtDatProtocol OBJECT-TYPE
        SYNTAX	INTEGER {
    		    enable(1),
    		    disable(2)
    		}
        ACCESS	read-write
        STATUS	mandatory
        DESCRIPTION
                "SMT will implement an optional ANSI duplicate address test
                involving periodic transmission of NSA NIF frames addressed
                to itself if enabled by this attribute."
        DEFVAL	{ enable }
        ::= { wfFddiXLineCfgEntry 5 }

    wfFddiXLineCfgLineNumber OBJECT-TYPE
        SYNTAX	INTEGER
        ACCESS	read-write
        STATUS	mandatory
        DESCRIPTION
                "Logical line number associated with this driver entity."
        ::= { wfFddiXLineCfgEntry 6 }

    wfFddiXLineCfgForcePeerTree OBJECT-TYPE
        SYNTAX	INTEGER {
    		    enable(1),
    		    disable(2)
    		}
        ACCESS	read-write
        STATUS	mandatory
        DESCRIPTION
                "This attribute allows all FDDI Peer/Tree connections
                to reach the 'Thru' state. This is done to give the
                user some flexibility and allow them to Daisy Chain
                their Phy connections, mixing Tree & Peer connections.
                This type of daisy chaining DOES NOT conform to the
                SMT standard and is NOT recommended as it may result in
                a less than optimum token path. Normally when we have a
                Peer/Tree connection mix, we will wrap the connection,
                favoring PHY B."
        DEFVAL	{ disable }
        ::= { wfFddiXLineCfgEntry 7 }


    wfFddiXLineCfgSlot OBJECT-TYPE
        SYNTAX	INTEGER(1..14)
        ACCESS	read-only
        STATUS	mandatory
        DESCRIPTION
                "Chassis slot number of FDDI interface."
        ::= { wfFddiXLineCfgEntry 8 }

    wfFddiXLineCfgModule OBJECT-TYPE
        SYNTAX	INTEGER {
    		    one(1),
    		    two(2),
    		    three(3),
    		    four(4)
    		}
        ACCESS	read-only
        STATUS	mandatory
        DESCRIPTION
                "Module number for Fiddlestix platform, filled in by driver."
        ::= { wfFddiXLineCfgEntry 9 }

    wfFddiXLineCfgActualNode OBJECT-TYPE
        SYNTAX	INTEGER {
    		    one(1),
    		    two(2)
    		}
        ACCESS	read-only
        STATUS	mandatory
        DESCRIPTION
                "Actual Node number for this FDDI interface, filled in
                 by the driver."
        ::= { wfFddiXLineCfgEntry 10 }

    wfFddiXLineCfgNode OBJECT-TYPE
        SYNTAX	INTEGER(1..44)
        ACCESS	read-only
        STATUS	mandatory
        DESCRIPTION
                "Instance ID node - filled in by driver. This attribute is 
                 an encoded value and is equal to 'module'*100 + 'node'. 
                 Where 'module' is defined in object 4 and 'node' is defined 
                 in object 5 of this table."
        ::= { wfFddiXLineCfgEntry 11 }

    wfFddiXLineCfgSmtIndex OBJECT-TYPE
        SYNTAX	INTEGER
        ACCESS	read-write
        STATUS	mandatory
        DESCRIPTION
                "Used for indexing into rfc1512 MIBS, this value is gotten 
                 from multiplying the 'slot*1000' and then adding the 
                 'wfFddiXLineCfgNode' attribute described above. Its 
                 purpose is to uniquely identify each SMT which exists."
        ::= { wfFddiXLineCfgEntry 12 }

    wfFddiXLineCfgIfIndex OBJECT-TYPE
        SYNTAX      INTEGER
        ACCESS      read-only
        STATUS      mandatory
        DESCRIPTION
                "An index value that uniquely identifies an
                interface to a FDDI-like medium.  The
                interface identified by a particular value of
                this index is the same interface as identified
                by the same value of ifIndex."
            ::= { wfFddiXLineCfgEntry 13 }


    wfFddiXLineTable OBJECT-TYPE
        SYNTAX	SEQUENCE OF WfFddiXLineEntry
        ACCESS	not-accessible
        STATUS	mandatory
        DESCRIPTION
                "FDDI switch statistic line record"
        ::= { wfFddiXGroup 2 }

    wfFddiXLineEntry OBJECT-TYPE
        SYNTAX	WfFddiXLineEntry
        ACCESS	not-accessible
        STATUS	mandatory
        DESCRIPTION
                "An FDDI entry containing information about an FDDI interface."
        INDEX	{ wfFddiXLineIfIndex }
        ::= { wfFddiXLineTable 1 }

    WfFddiXLineEntry ::= SEQUENCE {
            wfFddiXLineSlot
                INTEGER,
            wfFddiXLineModule
                INTEGER,
            wfFddiXLineActualNode
                INTEGER,
            wfFddiXLineNode
                INTEGER,
            wfFddiXLineSmtIndex
                INTEGER,
            wfFddiXLineIfIndex
                INTEGER,
            wfFddiXLineTxErrors
                Counter, 
            wfFddiXLineTxAborts
                Counter, 
            wfFddiXLineTxOverruns
                Counter,
            wfFddiXLineTxUnderruns
                Counter, 
            wfFddiXLineRxErrors
                Counter, 
            wfFddiXLineRxCrcErrors
                Counter, 
            wfFddiXLineRxSmtCrcErrors
                Counter, 
            wfFddiXLineRxInvalidFrameStatusErrors
                Counter,
            wfFddiXLineRxSmtInvalidFrameStatusErrors
                Counter,
            wfFddiXLineRxMacErrors
                Counter,
            wfFddiXLineRxSmtMacErrors
                Counter,
            wfFddiXLineRxFormatErrors
                Counter,
            wfFddiXLineRxSmtFormatErrors
                Counter,
            wfFddiXLineRxFragmentErrors
                Counter,
            wfFddiXLineRxSmtFragmentErrors
                Counter,
            wfFddiXLineRxInvalidLengthErrors
                Counter,
            wfFddiXLineRxSmtInvalidLengthErrors
                Counter,
            wfFddiXLineRxAbortErrors
                Counter,
            wfFddiXLineRxSmtAbortErrors
                Counter,
            wfFddiXLineRxEDataUnknownErrors
                Counter,
            wfFddiXLineRxSmtEDataUnknownErrors
                Counter,
            wfFddiXLineRxLastEDataFStatusErrorVal
                INTEGER,
            wfFddiXLineRxSmtLastEDataFStatusErrorVal
                INTEGER,
            wfFddiXLineRxOverruns
                Counter,
            wfFddiXLineRxUnderruns
                Counter, 
            wfFddiXLineRxOversizedFrames
                Counter, 
            wfFddiXLineRxSmtOversizedFrames
                Counter,
            wfFddiXLineRxUndersizedFrames
                Counter,
            wfFddiXLineRxSmtUndersizedFrames
                Counter,
            wfFddiXLineRxSmtSecondaryNsaFrames
                Counter,
            wfFddiXLineUnexpectedFrames
                Counter,
            wfFddiXLineRxSmtOctets
                Counter,
            wfFddiXLineRxSmtFrames
                Counter,
            wfFddiXLineTxSmtOctets
                Counter,
            wfFddiXLineTxSmtFrames
                Counter,
            wfFddiXLinePhyALogPtr
                INTEGER,
            wfFddiXLinePhyBLogPtr
                INTEGER
        }


    wfFddiXLineSlot OBJECT-TYPE
        SYNTAX	INTEGER(1..14)
        ACCESS	read-only
        STATUS	mandatory
        DESCRIPTION
                "Chassis slot number of FDDI interface."
        ::= { wfFddiXLineEntry 1 }

    wfFddiXLineModule OBJECT-TYPE
        SYNTAX	INTEGER {
    		    one(1),
    		    two(2),
    		    three(3),
    		    four(4)
    		}
        ACCESS	read-only
        STATUS	mandatory
        DESCRIPTION
                "Module number for Fiddlestix platform, filled in by driver."
        ::= { wfFddiXLineEntry 2 }

    wfFddiXLineActualNode OBJECT-TYPE
        SYNTAX	INTEGER {
    		    one(1),
    		    two(2)
    		}
        ACCESS	read-only
        STATUS	mandatory
        DESCRIPTION
                "Actual Node number for this FDDI interface, filled in
                 by the driver."
        ::= { wfFddiXLineEntry 3 }

    wfFddiXLineNode OBJECT-TYPE
        SYNTAX	INTEGER(1..44)
        ACCESS	read-only
        STATUS	mandatory
        DESCRIPTION
                "Instance ID node - filled in by driver. This attribute is 
                 an encoded value and is equal to 'module'*10 + 'node'. 
                 Where 'module' is defined in object 4 and 'node' is defined 
                 in object 5 of this table."
        ::= { wfFddiXLineEntry 4 }

    wfFddiXLineSmtIndex OBJECT-TYPE
        SYNTAX	INTEGER
        ACCESS	read-write
        STATUS	mandatory
        DESCRIPTION
                "Logical line number associated with this FDDI interface."
        ::= { wfFddiXLineEntry 5 }

    wfFddiXLineIfIndex OBJECT-TYPE
        SYNTAX      INTEGER
        ACCESS      read-only
        STATUS      mandatory
        DESCRIPTION
                "An index value that uniquely identifies an
                interface to a FDDI-like medium.  The
                interface identified by a particular value of
                this index is the same interface as identified
                by the same value of ifIndex."
            ::= { wfFddiXLineEntry 6 }

    wfFddiXLineTxErrors OBJECT-TYPE
        SYNTAX	Counter
        ACCESS	read-only
        STATUS	mandatory
        DESCRIPTION
                "An aggregate of the total number of transmit errors on this
                 FDDI interface."
        ::= { wfFddiXLineEntry 7 }

    wfFddiXLineTxAborts OBJECT-TYPE
        SYNTAX	Counter
        ACCESS	read-only
        STATUS	mandatory
        DESCRIPTION
                "Number of transmitted frames terminated (i.e. aborted)
                 abnormally by the MAC."
        ::= { wfFddiXLineEntry 8 }

    wfFddiXLineTxOverruns OBJECT-TYPE
        SYNTAX	Counter
        ACCESS	read-only
        STATUS	mandatory
        DESCRIPTION
                "Number of tranmitter overruns experienced by this interface.
                 May indicate a HW problem with regards to the DMAC feeding
                 the MAC."
        ::= { wfFddiXLineEntry 9 }
       
    wfFddiXLineTxUnderruns OBJECT-TYPE
        SYNTAX	Counter
        ACCESS	read-only
        STATUS	mandatory
        DESCRIPTION
                "Number of tranmitter underruns experienced by this interface.
                 May indicate a SW problem with regards to replenishing the
                 DMACs XMT descriptor."
        ::= { wfFddiXLineEntry 10 }

    wfFddiXLineRxErrors OBJECT-TYPE
        SYNTAX	Counter
        ACCESS	read-only
        STATUS	mandatory
        DESCRIPTION
                "An aggregate of the total number of receive errors on this
                 FDDI interface."
        ::= { wfFddiXLineEntry 11 }

    wfFddiXLineRxCrcErrors OBJECT-TYPE
        SYNTAX	Counter
        ACCESS	read-only
        STATUS	mandatory
        DESCRIPTION
                "Number of LLC frames received with CRC errors."
        ::= { wfFddiXLineEntry 12 }

    wfFddiXLineRxSmtCrcErrors OBJECT-TYPE
        SYNTAX	Counter
        ACCESS	read-only
        STATUS	mandatory
        DESCRIPTION
                "Number of SMT frames received with CRC errors."
        ::= { wfFddiXLineEntry 13 }

    wfFddiXLineRxInvalidFrameStatusErrors OBJECT-TYPE
        SYNTAX	Counter
        ACCESS	read-only
        STATUS	mandatory
        DESCRIPTION
                "A count of the number of badly formed LLC frames received off
                of the FDDI ring. These are frames which do not contain a
                valid Frame Status field of at least 3 control indicator
                symbols (i.e. E, A, C, flags)."
        ::= { wfFddiXLineEntry 14 }

    wfFddiXLineRxSmtInvalidFrameStatusErrors OBJECT-TYPE
        SYNTAX	Counter
        ACCESS	read-only
        STATUS	mandatory
        DESCRIPTION
                "A count of the number of badly formed SMT frames received off
                of the FDDI ring. These are frames which do not contain a
                valid Frame Status field of at least 3 control indicator
                symbols (i.e. E, A, C, flags)."
        ::= { wfFddiXLineEntry 15 }

    wfFddiXLineRxMacErrors OBJECT-TYPE 
        SYNTAX	Counter
        ACCESS	read-only
        STATUS	mandatory
        DESCRIPTION
                "Number of LLC frames received with MAC errors."
        ::= { wfFddiXLineEntry 16 }

    wfFddiXLineRxSmtMacErrors OBJECT-TYPE
        SYNTAX	Counter
        ACCESS	read-only
        STATUS	mandatory
        DESCRIPTION
                "Number of SMT frames received with MAC errors."
        ::= { wfFddiXLineEntry 17 }

    wfFddiXLineRxFormatErrors OBJECT-TYPE 
        SYNTAX	Counter
        ACCESS	read-only
        STATUS	mandatory
        DESCRIPTION
                "Number of LLC frames received with Format errors."
        ::= { wfFddiXLineEntry 18 }

    wfFddiXLineRxSmtFormatErrors OBJECT-TYPE
        SYNTAX	Counter
        ACCESS	read-only
        STATUS	mandatory
        DESCRIPTION
                "Number of SMT frames received with Format errors."
        ::= { wfFddiXLineEntry 19 }

    wfFddiXLineRxFragmentErrors OBJECT-TYPE
        SYNTAX	Counter
        ACCESS	read-only
        STATUS	mandatory
        DESCRIPTION
                "Number of LLC frame fragments received."
        ::= { wfFddiXLineEntry 20 }

    wfFddiXLineRxSmtFragmentErrors OBJECT-TYPE
        SYNTAX	Counter
        ACCESS	read-only
        STATUS	mandatory
        DESCRIPTION
                "Number of SMT frame fragments received."
        ::= { wfFddiXLineEntry 21 }

    wfFddiXLineRxInvalidLengthErrors OBJECT-TYPE
        SYNTAX	Counter
        ACCESS	read-only
        STATUS	mandatory
        DESCRIPTION
                "Number of LLC frames received with an ending T
                 symbol which are either too short or contain
                 an odd number of symbols."
        ::= { wfFddiXLineEntry 22 }

    wfFddiXLineRxSmtInvalidLengthErrors OBJECT-TYPE
        SYNTAX	Counter
        ACCESS	read-only
        STATUS	mandatory
        DESCRIPTION
                "Number of SMT frames received with an ending T
                 symbol which are either too short or contain
                 an odd number of symbols."
        ::= { wfFddiXLineEntry 23 }

    wfFddiXLineRxAbortErrors OBJECT-TYPE 
        SYNTAX	Counter
        ACCESS	read-only
        STATUS	mandatory
        DESCRIPTION
                "Number of LLC frames aborted during reception."
        ::= { wfFddiXLineEntry 24 }

    wfFddiXLineRxSmtAbortErrors OBJECT-TYPE
        SYNTAX	Counter
        ACCESS	read-only
        STATUS	mandatory
        DESCRIPTION
                "Number of LLC frames aborted during reception."
        ::= { wfFddiXLineEntry 25 }

    wfFddiXLineRxEDataUnknownErrors OBJECT-TYPE
        SYNTAX	Counter
        ACCESS	read-only
        STATUS	mandatory
        DESCRIPTION
                "Number of LLC frames received with the Error indication
                 set, that we couldn't decode as were unable to get the
                 END_DATA value from the frame."
        ::= { wfFddiXLineEntry 26 }

    wfFddiXLineRxSmtEDataUnknownErrors OBJECT-TYPE
        SYNTAX	Counter
        ACCESS	read-only
        STATUS	mandatory
        DESCRIPTION
                "Number of SMT frames received with the Error indication
                 set, that we couldn't decode as were unable to get the
                 END_DATA value from the frame."
        ::= { wfFddiXLineEntry 27 }

    wfFddiXLineRxLastEDataFStatusErrorVal OBJECT-TYPE
        SYNTAX	INTEGER
        ACCESS	read-only
        STATUS	mandatory
        DESCRIPTION
                "The value of END_DATA and FRAME_STATUS from the last 
                 LLC frame received containing an error."
        ::= { wfFddiXLineEntry 28 }

    wfFddiXLineRxSmtLastEDataFStatusErrorVal OBJECT-TYPE
        SYNTAX	INTEGER
        ACCESS	read-only
        STATUS	mandatory
        DESCRIPTION
                "The value of END_DATA and FRAME_STATUS from the last 
                 SMT frame received containing an error."
        ::= { wfFddiXLineEntry 29 }

    wfFddiXLineRxOverruns OBJECT-TYPE
        SYNTAX	Counter
        ACCESS	read-only
        STATUS	mandatory
        DESCRIPTION
                "Number of receiver overruns experienced by this interface.
                 May indicate a SW problem with regards to replenishing
                 the DMACs RCV descriptors."
        ::= { wfFddiXLineEntry 30 }

    wfFddiXLineRxUnderruns OBJECT-TYPE
        SYNTAX	Counter
        ACCESS	read-only
        STATUS	mandatory
        DESCRIPTION
                "Number of receiver underruns experienced by this interface.
                 May indicate a HW problem with regards to the DMAC feeding
                 the MAC."
        ::= { wfFddiXLineEntry 31 }

    wfFddiXLineRxOversizedFrames OBJECT-TYPE
        SYNTAX	Counter
        ACCESS	read-only
        STATUS	mandatory
        DESCRIPTION
                "Number of LLC frames received whose length exceeded the MTU.
                 (Note: The MTU is defined in rfc1573 in the ifMtu object.)"
        ::= { wfFddiXLineEntry 32 }

    wfFddiXLineRxSmtOversizedFrames OBJECT-TYPE
        SYNTAX	Counter
        ACCESS	read-only
        STATUS	mandatory
        DESCRIPTION
                "Number of SMT frames received whose length exceeded the MTU.
                 (Note: The MTU is defined in rfc1573 in the ifMtu object.)"
        ::= { wfFddiXLineEntry 33 }

    wfFddiXLineRxUndersizedFrames OBJECT-TYPE
        SYNTAX	Counter
        ACCESS	read-only
        STATUS	mandatory
        DESCRIPTION
                "Number of LLC frames received whose length was less than 20 
                 bytes, including the FC byte and a 4 byte CRC."
        ::= { wfFddiXLineEntry 34 }

    wfFddiXLineRxSmtUndersizedFrames OBJECT-TYPE
        SYNTAX	Counter
        ACCESS	read-only
        STATUS	mandatory
        DESCRIPTION
                "Number of SMT frames received whose length was less than 
                 37 bytes, including the FC byte and a 4 byte CRC."
        ::= { wfFddiXLineEntry 35 }

    wfFddiXLineRxSmtSecondaryNsaFrames OBJECT-TYPE
        SYNTAX	Counter
        ACCESS	read-only
        STATUS	mandatory
        DESCRIPTION
                "Number of Secondary NSA frames received by this interface
                 and dropped."
        ::= { wfFddiXLineEntry 36 }

    wfFddiXLineUnexpectedFrames OBJECT-TYPE
        SYNTAX	Counter
        ACCESS	read-only
        STATUS	mandatory
        DESCRIPTION
                "Number of non-LLC and non SMT frames received by this
                 interface. Does NOT include MAC frames or Void frames."
        ::= { wfFddiXLineEntry 37 }

    wfFddiXLineRxSmtOctets OBJECT-TYPE
        SYNTAX	Counter
        ACCESS	read-only
        STATUS	mandatory
        DESCRIPTION
                "Number of bytes received without error. This byte count
                 only includes SMT frames (i.e. no MAC and LLC frames)."
        ::= { wfFddiXLineEntry 38 }

    wfFddiXLineRxSmtFrames OBJECT-TYPE
        SYNTAX	Counter
        ACCESS	read-only
        STATUS	mandatory
        DESCRIPTION
                "Number of frames received without error. This frame count
                 only includes SMT frames (i.e. no MAC and LLC frames)."
        ::= { wfFddiXLineEntry 39 }

    wfFddiXLineTxSmtOctets OBJECT-TYPE
        SYNTAX	Counter
        ACCESS	read-only
        STATUS	mandatory
        DESCRIPTION
                "Number of bytes transmitted. This byte count only includes
                 SMT frames (i.e. no MAC and LLC frames). Also note that
                 this value is an approximation in that its assumed frames
                 queued for transmit ALWAYS make it onto the ring."
        ::= { wfFddiXLineEntry 40 }

    wfFddiXLineTxSmtFrames OBJECT-TYPE
        SYNTAX	Counter
        ACCESS	read-only
        STATUS	mandatory
        DESCRIPTION
                "Number of frames transmitted. This frame count only includes
                 SMT frames (i.e. no MAC and LLC frames). Also note that
                 this value is an approximation in that its assumed frames
                 queued for transmit ALWAYS make it onto the ring."
        ::= { wfFddiXLineEntry 41 }

    wfFddiXLinePhyALogPtr OBJECT-TYPE
        SYNTAX	INTEGER
        ACCESS	read-only
        STATUS	mandatory
        DESCRIPTION
                "Address of the Debug Phy Event Buffer for Phy A. This
                attribute is strictly for diagnostic purposes. The size
                of the buffer is 1028 bytes."
        ::= { wfFddiXLineEntry 42 }

    wfFddiXLinePhyBLogPtr OBJECT-TYPE
        SYNTAX	INTEGER
        ACCESS	read-only
        STATUS	mandatory
        DESCRIPTION
                "Address of the Debug Phy Event Buffer for Phy B. This
                attribute is strictly for diagnostic purposes. The size
                of the buffer is 1028 bytes."
        ::= { wfFddiXLineEntry 43 }


    wfFddiXSmtTable OBJECT-TYPE
        SYNTAX	SEQUENCE OF WfFddiXSmtEntry
        ACCESS	not-accessible
        STATUS	mandatory
        DESCRIPTION
                "A list of SMT entries."
        ::= { wfFddiXGroup 3 }

    wfFddiXSmtEntry OBJECT-TYPE
        SYNTAX	WfFddiXSmtEntry
        ACCESS	not-accessible
        STATUS	mandatory
        DESCRIPTION
                "An FDDI entry containing information about an FDDI interface."
        INDEX	{ wfFddiXSmtIndex }
        ::= { wfFddiXSmtTable 1 }

    WfFddiXSmtEntry ::= SEQUENCE {
            wfFddiXSmtIndex
                INTEGER,
    	    wfFddiXSmtManufacturerData
    		OCTET STRING
        }

    wfFddiXSmtIndex OBJECT-TYPE
        SYNTAX  INTEGER (1..65535)
        ACCESS  read-only
        STATUS  mandatory
        DESCRIPTION
                "A unique value for each SMT.  The value for each
                 SMT must remain constant at least from one re-
                 initialization of the entity's network management
                 system to the next re-initialization."
        ::= { wfFddiXSmtEntry 1 }

    wfFddiXSmtManufacturerData OBJECT-TYPE
        SYNTAX	OCTET STRING
        ACCESS	read-only
        STATUS	mandatory
        DESCRIPTION
                "Contains 32 Octets of manufacturer data. The first component,
                 manufacturing OUI, is the 3 octet Organizationally Unique
                 Identifier (OUI) assigned by IEEE. The second component,
                 ManufacturerData, is the manufacturers data (29 octets)."
        ::= { wfFddiXSmtEntry 2 }


    wfFddiXMacTable OBJECT-TYPE
        SYNTAX	SEQUENCE OF WfFddiXMacEntry
        ACCESS	not-accessible
        STATUS	mandatory
        DESCRIPTION
                "A list of MAC entries."
        ::= { wfFddiXGroup 4 }

    wfFddiXMacEntry OBJECT-TYPE
        SYNTAX	WfFddiXMacEntry
        ACCESS	not-accessible
        STATUS	mandatory
        DESCRIPTION
                "An FDDI entry containing information about an FDDI interface."
        INDEX	{ wfFddiXMacSmtIndex, wfFddiXMacIndex }
        ::= { wfFddiXMacTable 1 }

    WfFddiXMacEntry ::= SEQUENCE {
            wfFddiXMacSmtIndex
                INTEGER,
            wfFddiXMacIndex
                INTEGER,
            wfFddiXMacBridgeFunctions
                INTEGER,
            wfFddiXMacDuplicateTokenCts
                Counter
        }

    wfFddiXMacSmtIndex OBJECT-TYPE
        SYNTAX  INTEGER (1..65535)
        ACCESS  read-only
        STATUS  mandatory
        DESCRIPTION
                "The value of the SMT index associated with this
                 MAC."
        ::= { wfFddiXMacEntry 1 }
    
    wfFddiXMacIndex OBJECT-TYPE
        SYNTAX  INTEGER (1..65535)
        ACCESS  read-only
        STATUS  mandatory
        DESCRIPTION
                "Index variable for uniquely identifying the MAC
                 object instances, which is the same as the
                 corresponding resource index in SMT."
        ::= { wfFddiXMacEntry 2 }

    wfFddiXMacBridgeFunctions OBJECT-TYPE
        SYNTAX	INTEGER {
    		    transparent(1),
    		    srcroute(2),
    		    srt(4)
    		}
        ACCESS	read-only
        STATUS	mandatory
        DESCRIPTION
                "Indicates the MAC's optional bridging functions.

                   The value is a sum. This value initially takes the value 
                   zero, then for each function present, 2 raised to a power 
                   is added to the sum. The powers are according to the 
                   following table:

                        Function        Power
                        --------        ----
                           tb             0 -- Transparent bridging active
                           sr             1 -- Src routing active
                          srt             2 -- Src routing transparent active"
        ::= { wfFddiXMacEntry 3 }

    wfFddiXMacDuplicateTokenCts OBJECT-TYPE
        SYNTAX	Counter
        ACCESS	read-only
        STATUS	mandatory
        DESCRIPTION
                "The count of the number of times a Duplicate Token has 
                 been detected."
        ::= { wfFddiXMacEntry 4 }


    wfFddiXPortTable OBJECT-TYPE
        SYNTAX	SEQUENCE OF WfFddiXPortEntry
        ACCESS	not-accessible
        STATUS	mandatory
        DESCRIPTION
                "A list of PORT Entries."
        ::= { wfFddiXGroup 5 }

    wfFddiXPortEntry OBJECT-TYPE
        SYNTAX	WfFddiXPortEntry
        ACCESS	not-accessible
        STATUS	mandatory
        DESCRIPTION
                "An FDDI entry containing information about an FDDI interface."
        INDEX	{ wfFddiXPortSmtIndex, wfFddiXPortIndex }
        ::= { wfFddiXPortTable 1 }

    WfFddiXPortEntry ::= SEQUENCE {
            wfFddiXPortSmtIndex
                INTEGER,
            wfFddiXPortIndex
                INTEGER,
            wfFddiXPortEbErrors
                INTEGER
        }

    wfFddiXPortSmtIndex OBJECT-TYPE
        SYNTAX  INTEGER (1..65535)
        ACCESS  read-only
        STATUS  mandatory
        DESCRIPTION
                "The value of the SMT index associated with this
                 PORT."
        ::= { wfFddiXPortEntry 1 }
    
    wfFddiXPortIndex OBJECT-TYPE
        SYNTAX  INTEGER (1..65535)
        ACCESS  read-only
        STATUS  mandatory
        DESCRIPTION
                "A unique value for each PORT within a given SMT,
                 which is the same as the corresponding resource
                 index in SMT.  The value for each PORT must remain
                 constant at least from one re-initialization of
                 the entity's network management system to the next
                 re-initialization."
        ::= { wfFddiXPortEntry 2 }

    wfFddiXPortEbErrors OBJECT-TYPE
        SYNTAX	INTEGER
        ACCESS	read-only
        STATUS	mandatory
        DESCRIPTION
                "The count of the number of elasticity buffer errors for a
                 particular PHY. The elasticity buffer is used to account for
                 clock tolerances between stations."
        ::= { wfFddiXPortEntry 3 }


    END  -- Wellfleet-FDDI-MIB
