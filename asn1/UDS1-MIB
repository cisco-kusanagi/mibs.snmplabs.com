--******************************************************************
--*
--*         Copyright (c) 1993, 1999 by 3Com Corporation
--*                    All Rights Reserved
--*
--*    $Revision:   7.0  $
--*    $Date:   Jul 15 1999 11:39:40  $
--*
--*    3COM UDS1 MIB
--*
--******************************************************************


UDS1-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


-- This is the MIB module for USR's extended DS1 Objects.

usr OBJECT IDENTIFIER ::= { enterprises 429 }

nas OBJECT IDENTIFIER ::= { usr 1 }

uds1 OBJECT IDENTIFIER ::= { nas 4 }

-- The USR DS1 Configuration Group
-- Implementation of the USR DS1 Configuration group is
-- mandatory for all systems that provide management of
-- USR's Dual T1 Cards.

uds1ConfigTable OBJECT-TYPE
SYNTAX SEQUENCE OF Uds1ConfigEntry
ACCESS not-accessible
STATUS mandatory
DESCRIPTION
"This table is an extension of the ds1ConfigTable in the DS1 
MIB defined by RFC1232."
::= { uds1 1 }

uds1ConfigEntry OBJECT-TYPE
SYNTAX Uds1ConfigEntry
ACCESS not-accessible
STATUS mandatory
DESCRIPTION
"This table contains configurable parameters for a CSU that 
are not supported in the DS1 MIB defined by RFC1232.  Each 
entry in this table corresponds to an entry in the DS1 MIB. 
 There is a one-to-one correspondance between the value of 
uds1CSUIndex and ds1CSUIndex."
INDEX { uds1CfgIndex }
::= { uds1ConfigTable 1 }

Uds1ConfigEntry ::=
SEQUENCE {
uds1CfgIndex
    INTEGER,
uds1CfgRespToRemoteLoopbk
    INTEGER,
uds1CfgJitterAttenuation
    INTEGER,
uds1CfgXmitLineBuildOut
    INTEGER,
uds1CfgAutoBusyEnable
    INTEGER,
uds1CfgDialInAdr
    INTEGER,
uds1CfgZeroCoding
    INTEGER,
uds1CfgDialInOutTrunkSt
    INTEGER,
uds1CfgDialInAdrAckWinkEn
    INTEGER,
uds1CfgDialOutAdrDly
    INTEGER,
uds1CfgStuffByteValue
    INTEGER,
uds1CfgDialInOutTrunkType
    INTEGER,
uds1CfgPriSwitchType
    INTEGER,
uds1CfgIdleByte
    INTEGER,
uds1CfgAnlgBlockErrCode
    INTEGER,
uds1CfgDgtlBlockErrCode
    INTEGER,
uds1CfgNoMdmAvailErrCode
    INTEGER,
uds1CfgNoIgwsAvailErrCode
    INTEGER,
uds1CfgChanBlockErrCode
    INTEGER,
uds1CfgBlockCallType
    INTEGER,
uds1CfgNfasId
    INTEGER,
uds1CfgNfasDChannel
    INTEGER,
uds1CfgShrtHaulDist
    INTEGER,
uds1CfgCallProceedingRsp
    INTEGER,
uds1CfgAlertingRsp
    INTEGER,
uds1CfgServiceState
    INTEGER,
uds1CfgIcbKeyword
    DisplayString,
uds1CfgOverlapRxMode
    INTEGER,
uds1CfgEandMnoAddrTimer
    INTEGER,
uds1CfgSeizureWinkDly
    INTEGER
}

uds1CfgIndex OBJECT-TYPE
SYNTAX INTEGER
ACCESS read-only
STATUS mandatory
DESCRIPTION
"The index value which uniquely identifies the CSU to which 
this entry is applicable.  The value corresponds to 
ds1CSUIndex in the DS1 MIB defined in RFC1232.  The value 
of uds1CfgIndex matches the value of the index for the 
corresponding DS1 entity in the entity table of the chassis 
MIB."
::= { uds1ConfigEntry 1 }

uds1CfgRespToRemoteLoopbk OBJECT-TYPE
SYNTAX INTEGER{
  ignore(1),
  respond(2)
}
ACCESS read-write
STATUS mandatory
DESCRIPTION
"This object configures the specified CSU to either ignore 
or respond to remotely initiated loopback requests."
::= { uds1ConfigEntry 2 }

uds1CfgJitterAttenuation OBJECT-TYPE
SYNTAX INTEGER{
  attenJitterOnRcvr(1),
  attenJitterOnTxmtr(2),
  notApplicable(3)
}
ACCESS read-write
STATUS mandatory
DESCRIPTION
"This object is used to select how the jitter attenuation 
circuit on the CSU is to be used.  It can be used to 
attenuate jitter on the receiver, or the transmitter."
::= { uds1ConfigEntry 3 }

uds1CfgXmitLineBuildOut OBJECT-TYPE
SYNTAX INTEGER{
  dB0(1),
  dB7(2),
  dB15(3),
  dB22(4),
  notApplicable(5)
}
ACCESS read-write
STATUS mandatory
DESCRIPTION
"This object is used to configure the amount of attenuation 
that is to be applied to the transmit signal in order to 
control cross-talk, etc."
::= { uds1ConfigEntry 4 }

uds1CfgAutoBusyEnable OBJECT-TYPE
SYNTAX INTEGER{
  disabled(1),
  enabled(2)
}
ACCESS read-write
STATUS mandatory
DESCRIPTION
"This object is used to enable or disable the automatic busy 
out feature for all timeslots on the specified CSU.  If 
enabled, when a modem is considered idle and that modem is 
not sending the idle pattern to the T1 Card on the TDM bus, 
the timeslot will be busied out."
::= { uds1ConfigEntry 5 }

uds1CfgDialInAdr OBJECT-TYPE
SYNTAX INTEGER{
  noAddress(1),
  dnis(2),
  ani-dnis(3),
  ani(4)
}
ACCESS read-write
STATUS mandatory
DESCRIPTION
"This object identifies whether or not DNIS digits will be 
transferred as part of the call setup for the specified T1 
line."
::= { uds1ConfigEntry 6 }

uds1CfgZeroCoding OBJECT-TYPE
SYNTAX INTEGER{
  other(1),
  zcs(2),
  b8zs(3),
  ami(4),
  hdb3(5)
}
ACCESS read-write
STATUS mandatory
DESCRIPTION
"This object defines the type of zero coding used on the 
specified DS1.  It provides some values that are not 
present in the experimental DS1 MIB."
::= { uds1ConfigEntry 7 }

uds1CfgDialInOutTrunkSt OBJECT-TYPE
SYNTAX INTEGER{
  wink(1),
  immediate(2),
  dialTone(3)
}
ACCESS read-write
STATUS mandatory
DESCRIPTION
"This will set the Dial-in/Dial-out trunk start signal type. 
Default = wink(1)."
::= { uds1ConfigEntry 8 }

uds1CfgDialInAdrAckWinkEn OBJECT-TYPE
SYNTAX INTEGER{
  disabled(1),
  enabled(2)
}
ACCESS read-write
STATUS mandatory
DESCRIPTION
"Allows to enable/disable an acknowledgement wink after the 
dial-in address information has been received."
::= { uds1ConfigEntry 9 }

uds1CfgDialOutAdrDly OBJECT-TYPE
SYNTAX INTEGER (70..3000)
ACCESS read-write
STATUS mandatory
DESCRIPTION
"Allows an adjustable delay on sending out address 
information from the T1 NAC to the TELCO."
::= { uds1ConfigEntry 10 }

uds1CfgStuffByteValue OBJECT-TYPE
SYNTAX INTEGER (0..255)
ACCESS read-write
STATUS mandatory
DESCRIPTION
"The stuffed byte to send to TELCO for inactive DS0 in 
Fractional T1."
::= { uds1ConfigEntry 11 }

uds1CfgDialInOutTrunkType OBJECT-TYPE
SYNTAX INTEGER{
  eAndMTypeII(1),
  loopStart(2),
  groundStart(3)
}
ACCESS read-write
STATUS mandatory
DESCRIPTION
"This will set the Dial-In/Dial-out trunk type. Default = 
eAndMTypeII(1)."
::= { uds1ConfigEntry 12 }

uds1CfgPriSwitchType OBJECT-TYPE
SYNTAX INTEGER{
  priSw4ESS(1),
  priSw5ESS(2),
  priSwDMS100(3),
  priSwICTR4(4),
  priSwVn4(5),
  priSwNI2(6),
  priSwINS1500(7),
  priSwDASS2(8),
  priSwTSO14(9)
}
ACCESS read-write
STATUS mandatory
DESCRIPTION
"This sets the primary switch type for the T1-PRI ISDN NAC.  
The setting takes effect at NAC boot time.
Default = 
priSw5ESS(2)."
::= { uds1ConfigEntry 13 }

uds1CfgIdleByte OBJECT-TYPE
SYNTAX INTEGER (0..255)
ACCESS read-write
STATUS mandatory
DESCRIPTION
"This sets the idle byte pattern for the T1-PRI ISDN NAC.  
The setting takes effect at NAC boot time.
Default = 0xFE."
::= { uds1ConfigEntry 14 }

uds1CfgAnlgBlockErrCode OBJECT-TYPE
SYNTAX INTEGER (0..127)
ACCESS read-write
STATUS mandatory
DESCRIPTION
"This is the error code that will be returned to an ISDN 
switch when analog connections are being blocked.
Default = 
58."
::= { uds1ConfigEntry 15 }

uds1CfgDgtlBlockErrCode OBJECT-TYPE
SYNTAX INTEGER (0..127)
ACCESS read-write
STATUS mandatory
DESCRIPTION
"This is the error code that will be returned to an ISDN 
switch when digital connections are being blocked.
Default 
= 58."
::= { uds1ConfigEntry 16 }

uds1CfgNoMdmAvailErrCode OBJECT-TYPE
SYNTAX INTEGER (0..127)
ACCESS read-write
STATUS mandatory
DESCRIPTION
"This is the error code that will be returned to an ISDN 
switch when there are no modems available to accept the 
requested connection.
Default = 58."
::= { uds1ConfigEntry 17 }

uds1CfgNoIgwsAvailErrCode OBJECT-TYPE
SYNTAX INTEGER (0..127)
ACCESS read-write
STATUS mandatory
DESCRIPTION
"This is the error code that will be returned to an ISDN 
switch when no IGWS connections are available.
Default = 
58."
::= { uds1ConfigEntry 18 }

uds1CfgChanBlockErrCode OBJECT-TYPE
SYNTAX INTEGER (0..127)
ACCESS read-write
STATUS mandatory
DESCRIPTION
"This is the error code that will be returned to an ISDN 
switch when connections to a specific B channel are being 
blocked.
Default = 58."
::= { uds1ConfigEntry 19 }

uds1CfgBlockCallType OBJECT-TYPE
SYNTAX INTEGER{
  notSupported(1),
  blockNone(2),
  blockAnalog(3),
  blockDigital(4),
  blockAll(5)
}
ACCESS read-write
STATUS mandatory
DESCRIPTION
"This object determines if a PRI span line will block calls 
of a specific type.  This object does not apply to a NAC 
operating in Rob Bit T1 mode.
Default = blockNone(2)."
::= { uds1ConfigEntry 20 }

uds1CfgNfasId OBJECT-TYPE
SYNTAX INTEGER (0..127)
ACCESS read-write
STATUS mandatory
DESCRIPTION
"This defines the NFAS ID associated with a PRI span line.  
This object does not apply to Rob Bit T1 operation.
Default 
= 0."
::= { uds1ConfigEntry 21 }

uds1CfgNfasDChannel OBJECT-TYPE
SYNTAX INTEGER{
  notSupported(1),
  dchannel(2),
  extraBchannel(3)
}
ACCESS read-write
STATUS mandatory
DESCRIPTION
"This determines how a PRI span line will use the DS0 
normally assigned as a D channel when NFAS is being used.  
This object does not apply to Rob Bit T1 operation.
Default 
= dchannel(2)."
::= { uds1ConfigEntry 22 }

uds1CfgShrtHaulDist OBJECT-TYPE
SYNTAX INTEGER{
  notApplicable(1),
  len0thru133Ft(2),
  len133thru266Ft(3),
  len266thru399Ft(4),
  len399thru533Ft(5),
  len533thru655Ft(6)
}
ACCESS read-write
STATUS mandatory
DESCRIPTION
"Variuos distance ranges supported by Short Haul NIC 
Default=len0thru133Ft."
::= { uds1ConfigEntry 23 }

uds1CfgCallProceedingRsp OBJECT-TYPE
SYNTAX INTEGER{
  off(1),
  on(2)
}
ACCESS read-write
STATUS mandatory
DESCRIPTION
"This object determines to send CALL_PROCEEDING and CONNECT 
response, when a SETUP message is received from 
TELCO.
Default = ON."
::= { uds1ConfigEntry 24 }

uds1CfgAlertingRsp OBJECT-TYPE
SYNTAX INTEGER{
  off(1),
  on(2)
}
ACCESS read-write
STATUS mandatory
DESCRIPTION
"This object determines to send ALERTING response, when a 
SETUP message is received from TELCO.
Default = OFF."
::= { uds1ConfigEntry 25 }

uds1CfgServiceState OBJECT-TYPE
SYNTAX INTEGER{
  notSupported(1),
  inService(2),
  localOutOfService(3)
}
ACCESS read-write
STATUS mandatory
DESCRIPTION
"This objects configures the service state of the DS1 and 
will configure the state for power up if saved to NVRAM. 
Default= inService(2)."
::= { uds1ConfigEntry 26 }

uds1CfgIcbKeyword OBJECT-TYPE
SYNTAX DisplayString (SIZE(4..4))
ACCESS read-write
STATUS mandatory
DESCRIPTION
"This is the keyword used for DASS2 Incoming Call Barring 
control."
::= { uds1ConfigEntry 27 }

uds1CfgOverlapRxMode OBJECT-TYPE
SYNTAX INTEGER{
  enable(1),
  disable(2)
}
ACCESS read-write
STATUS mandatory
DESCRIPTION
"This object allows dialed digits to arrive in separate 
messages. Default = disabled(2) "
::= { uds1ConfigEntry 28 }

uds1CfgEandMnoAddrTimer OBJECT-TYPE
SYNTAX INTEGER (0..125)
ACCESS read-write
STATUS mandatory
DESCRIPTION
"This object is for E&M type II trunks with no DNIS address. 
If timer is >0, the ch T1 NAC will flush calls upon timer 
expiration, if the modem has not signalled the NAC to go 
ahead and answer the call. 2 seconds per unit. Default = 0 "
::= { uds1ConfigEntry 29 }

uds1CfgSeizureWinkDly OBJECT-TYPE
SYNTAX INTEGER (0..255)
ACCESS read-write
STATUS mandatory
DESCRIPTION
"Allows an adjustable delay on sending out address 
information from the T1 NAC to the TELCO. Default=18."
::= { uds1ConfigEntry 30 }

-- The USR DS1 Interval Group
-- Implementation of the USR DS1 Interval Group is mandatory
-- for all systems that provide management of
-- USR's Dual T1 Cards.

uds1IntervalTable OBJECT-TYPE
SYNTAX SEQUENCE OF Uds1IntervalEntry
ACCESS not-accessible
STATUS mandatory
DESCRIPTION
"An extension of the DS1 Interval table which provides 
status counters over 15 minute intervals."
::= { uds1 2 }

uds1IntervalEntry OBJECT-TYPE
SYNTAX Uds1IntervalEntry
ACCESS not-accessible
STATUS mandatory
DESCRIPTION
"An entry in the extended DS1 Interval table.  Every entry 
in the DS1 Interval table will have a corresponding entry 
in this table."
INDEX { uds1IntIndex, uds1IntNumber }
::= { uds1IntervalTable 1 }

Uds1IntervalEntry ::=
SEQUENCE {
uds1IntIndex
    INTEGER,
uds1IntNumber
    INTEGER,
uds1IntBurstyErrSeconds
    Counter,
uds1IntFrameBitErrors
    Counter,
uds1IntDeltaFrameAlligns
    Counter,
uds1IntExcessCRCErrors
    Counter
}

uds1IntIndex OBJECT-TYPE
SYNTAX INTEGER
ACCESS read-only
STATUS mandatory
DESCRIPTION
"This is the index value which uniquely identifies the CSU 
to which this entry is applicable.  The value of 
uds1IntIndex matches the value of the index for the 
corresponding DS1 entity in the entity table of the chassis 
MIB."
::= { uds1IntervalEntry 1 }

uds1IntNumber OBJECT-TYPE
SYNTAX INTEGER
ACCESS read-only
STATUS mandatory
DESCRIPTION
"A number between 1 and 96, where 1 is the most recently 
completed 15 minute interval and 96 is the least recently 
completed 15 minute interval (assuming that all 96 
intervals are valid)."
::= { uds1IntervalEntry 2 }

uds1IntBurstyErrSeconds OBJECT-TYPE
SYNTAX Counter
ACCESS read-only
STATUS mandatory
DESCRIPTION
"This object counts the number of seconds, over the 
specified interval, in which there were more than 2 and 
less than 320 CRC errors."
::= { uds1IntervalEntry 3 }

uds1IntFrameBitErrors OBJECT-TYPE
SYNTAX Counter
ACCESS read-only
STATUS mandatory
DESCRIPTION
"A specific bit pattern is used for the T1 receiver to 
determine frame allignment.  This object counts the number 
of incorrectly received framing bits in the specified 15 
minute interval."
::= { uds1IntervalEntry 4 }

uds1IntDeltaFrameAlligns OBJECT-TYPE
SYNTAX Counter
ACCESS read-only
STATUS mandatory
DESCRIPTION
"This object counts the number of times the specified T1 
receiver has reframed on a new framing pattern (ie. due to 
an OOF condition) in the specified 15 minute interval."
::= { uds1IntervalEntry 5 }

uds1IntExcessCRCErrors OBJECT-TYPE
SYNTAX Counter
ACCESS read-only
STATUS mandatory
DESCRIPTION
"This object counts each time 32 of any 33 consecutive CRCs 
are in error for the specified T1 line in the specified 15 
minute interval.  This counter is only valid in ESF format."
::= { uds1IntervalEntry 6 }

-- The USR DS1 Current Group
-- Implementation of the USR DS1 Current Group is
-- mandatory for all systems that provide management
-- of USR's Dual T1 Cards.

uds1CurrentTable OBJECT-TYPE
SYNTAX SEQUENCE OF Uds1CurrentEntry
ACCESS not-accessible
STATUS mandatory
DESCRIPTION
"An extension of the DS1 Current table that provides status 
counters over the present 15 minute interval."
::= { uds1 3 }

uds1CurrentEntry OBJECT-TYPE
SYNTAX Uds1CurrentEntry
ACCESS not-accessible
STATUS mandatory
DESCRIPTION
"An entry in the extended DS1 Current table.  Every entry in 
the DS1 Current table will have a corresponding entry in 
this table."
INDEX { uds1CurrIndex }
::= { uds1CurrentTable 1 }

Uds1CurrentEntry ::=
SEQUENCE {
uds1CurrIndex
    INTEGER,
uds1CurrBurstyErrSeconds
    Counter,
uds1CurrFrameBitErrors
    Counter,
uds1CurrDeltaFrameAlligns
    Counter,
uds1CurrExcessCRCErrors
    Counter
}

uds1CurrIndex OBJECT-TYPE
SYNTAX INTEGER
ACCESS read-only
STATUS mandatory
DESCRIPTION
"The index value which uniquely identifies the CSU to which 
this entry is applicable.  The value of uds1CurrIndex 
matches the value of the index for the corresponding DS1 
entity in the entity table of the chassis MIB."
::= { uds1CurrentEntry 1 }

uds1CurrBurstyErrSeconds OBJECT-TYPE
SYNTAX Counter
ACCESS read-only
STATUS mandatory
DESCRIPTION
"This object counts the number of seconds, in the current 15 
minute interval, during which there was more than two, and 
less than 320 CRC errors."
::= { uds1CurrentEntry 2 }

uds1CurrFrameBitErrors OBJECT-TYPE
SYNTAX Counter
ACCESS read-only
STATUS mandatory
DESCRIPTION
"A specific bit pattern is used for the receiver to 
determine frame allignment.  This object is a count of the 
number of incorrectly received framing bits in the current 
15 minute interval."
::= { uds1CurrentEntry 3 }

uds1CurrDeltaFrameAlligns OBJECT-TYPE
SYNTAX Counter
ACCESS read-only
STATUS mandatory
DESCRIPTION
"This object counts the number of times the specified T1 
receiver has reframed on a new framing pattern (ie. due to 
an OOF condition) in the current 15 minute interval."
::= { uds1CurrentEntry 4 }

uds1CurrExcessCRCErrors OBJECT-TYPE
SYNTAX Counter
ACCESS read-only
STATUS mandatory
DESCRIPTION
"This object counts each time 32 of any 33 consecutive CRCs 
are in error for the specified T1 line in the current 15 
minute interval.  This counter is only valid in ESF format."
::= { uds1CurrentEntry 5 }

-- The USR DS1 Total Group
-- Implementation of the USR DS1 Total Group is
-- mandatory for all systems that manage USR's Dual T1 Cards.

uds1TotalTable OBJECT-TYPE
SYNTAX SEQUENCE OF Uds1TotalEntry
ACCESS not-accessible
STATUS mandatory
DESCRIPTION
"An extension of the DS1 Total table that provides the 
cumulative sum of the various statistics for the 24 hour 
interval preceding the first valid interval in the 
uds1CurrentTable."
::= { uds1 4 }

uds1TotalEntry OBJECT-TYPE
SYNTAX Uds1TotalEntry
ACCESS not-accessible
STATUS mandatory
DESCRIPTION
"An entry in the extended DS1 Total table."
INDEX { uds1TotIndex }
::= { uds1TotalTable 1 }

Uds1TotalEntry ::=
SEQUENCE {
uds1TotIndex
    INTEGER,
uds1TotBurstyErrSeconds
    Counter,
uds1TotFrameBitErrors
    Counter,
uds1TotDeltaFrameAlligns
    Counter,
uds1TotExcessCRCErrors
    Counter
}

uds1TotIndex OBJECT-TYPE
SYNTAX INTEGER
ACCESS read-only
STATUS mandatory
DESCRIPTION
"The index value which uniquely identifies the CSU to which 
this entry is applicable.  The value of ds1TotalIndex 
matches the value of the index for the corresponding DS1 
entity in the entity table of the chassis MIB."
::= { uds1TotalEntry 1 }

uds1TotBurstyErrSeconds OBJECT-TYPE
SYNTAX Counter
ACCESS read-only
STATUS mandatory
DESCRIPTION
"This object counts the number of seconds, over the last 24 
hour period, in which there were more than 2 and less than 
320 CRC errors."
::= { uds1TotalEntry 2 }

uds1TotFrameBitErrors OBJECT-TYPE
SYNTAX Counter
ACCESS read-only
STATUS mandatory
DESCRIPTION
"A specific bit pattern is used so the T1 receiver can 
determine frame allignment.  This object counts the total 
number of incorrectly received framing bits in the last 24 
hour period."
::= { uds1TotalEntry 3 }

uds1TotDeltaFrameAlligns OBJECT-TYPE
SYNTAX Counter
ACCESS read-only
STATUS mandatory
DESCRIPTION
"This object counts the number of times the specified T1 
receiver has reframed on a new framing pattern (ie. due to 
an OOF condition) in the last 24 hour period."
::= { uds1TotalEntry 4 }

uds1TotExcessCRCErrors OBJECT-TYPE
SYNTAX Counter
ACCESS read-only
STATUS mandatory
DESCRIPTION
"This object indicates the total number of times there have 
been 32 of any 33 consecutive CRCs in error on the 
specified T1 line in the last 24 hour period.  This counter 
is only valid in ESF format."
::= { uds1TotalEntry 5 }

-- The USR DS1 Status Group
-- Implementation of the USR DS1 Status Group is mandatory
-- for all systems that provide management of
-- USR's Dual T1 Cards.

uds1StatTable OBJECT-TYPE
SYNTAX SEQUENCE OF Uds1StatEntry
ACCESS not-accessible
STATUS mandatory
DESCRIPTION
"USR's DS1 Status table contains various CSU status 
information.  There is no corresponding table in the DS1 
MIB defined by RFC1232."
::= { uds1 5 }

uds1StatEntry OBJECT-TYPE
SYNTAX Uds1StatEntry
ACCESS not-accessible
STATUS mandatory
DESCRIPTION
"There is one entry in the DS1 Status table for each CSU in 
the chassis."
INDEX { uds1StatIndex }
::= { uds1StatTable 1 }

Uds1StatEntry ::=
SEQUENCE {
uds1StatIndex
    INTEGER,
uds1StatReceiverGain
    INTEGER,
uds1StatOutOfFrame
    INTEGER,
uds1StatLossOfSignal
    INTEGER,
uds1StatReceivingAIS
    INTEGER,
uds1StatSwitchTypeActive
    INTEGER,
uds1StatDchanOperational
    INTEGER,
uds1StatE1ContCrc
    INTEGER,
uds1StatE1PhysicalState
    INTEGER,
uds1StatLoopBackInit
    INTEGER,
uds1StatNfasDChannel
    INTEGER,
uds1StatDChannel
    INTEGER,
uds1StatDs0SrvcChngLst
    DisplayString,
uds1StatMultiFrame
    INTEGER,
uds1StatRemMultiFrame
    INTEGER,
uds1StatServiceState
    INTEGER
}

uds1StatIndex OBJECT-TYPE
SYNTAX INTEGER
ACCESS read-only
STATUS mandatory
DESCRIPTION
"The index value which uniquely identifies the CSU to which 
this entry is applicable.  The value of this object matches 
the value of the index for the corresponding DS1 entity in 
the entity table of the chassis MIB."
::= { uds1StatEntry 1 }

uds1StatReceiverGain OBJECT-TYPE
SYNTAX INTEGER{
  dB0(1),
  dB7(2),
  dB15(3),
  dB22(4),
  notApplicable(5)
}
ACCESS read-only
STATUS mandatory
DESCRIPTION
"This object identifies the amount of gain applied to boost 
the receive signal level to an appropriate operating level."
::= { uds1StatEntry 2 }

uds1StatOutOfFrame OBJECT-TYPE
SYNTAX INTEGER{
  false(1),
  true(2)
}
ACCESS read-only
STATUS mandatory
DESCRIPTION
"This object indicates when the framing pattern for the 
specified T1 line has been lost and data connot be 
extracted properly.  This condition is also known as red 
alarm."
::= { uds1StatEntry 3 }

uds1StatLossOfSignal OBJECT-TYPE
SYNTAX INTEGER{
  false(1),
  true(2)
}
ACCESS read-only
STATUS mandatory
DESCRIPTION
"This object indicates when 175 consecutive 0's have been 
detected.  The signal is considered recovered if the 1's 
density reaches 12.5% (ie. four ones in a 32 bit period)."
::= { uds1StatEntry 4 }

uds1StatReceivingAIS OBJECT-TYPE
SYNTAX INTEGER{
  false(1),
  true(2)
}
ACCESS read-only
STATUS mandatory
DESCRIPTION
"This object identifies when the remote end of the specified 
T1 line has lost its receive signal and is transmitting a 
stream of all 1's to the local end.  This AIS condition is 
also known as blue alarm."
::= { uds1StatEntry 5 }

uds1StatSwitchTypeActive OBJECT-TYPE
SYNTAX INTEGER{
  priSw4ESS(1),
  priSw5ESS(2),
  priSwDMS100(3),
  priSwICTR4(4),
  priSwVn4(5),
  priSwNI2(6),
  priSwINS1500(7),
  priSwDASS2(8),
  priSwTSO14(9)
}
ACCESS read-only
STATUS mandatory
DESCRIPTION
"This object identifies the primary switch type that the 
T1-PRI ISDN NAC is currently connected to."
::= { uds1StatEntry 6 }

uds1StatDchanOperational OBJECT-TYPE
SYNTAX INTEGER{
  dChannelUp(1),
  dChannelDown(2),
  bChannel(3)
}
ACCESS read-only
STATUS mandatory
DESCRIPTION
"This object reflects the operational status of the D 
channel on the T1-PRI ISDN NAC."
::= { uds1StatEntry 7 }

uds1StatE1ContCrc OBJECT-TYPE
SYNTAX INTEGER{
  false(1),
  true(2)
}
ACCESS read-only
STATUS mandatory
DESCRIPTION
"This object indicates when continuous CRC errors are being 
received on the E1 DS1 span line on the T1-PRI ISDN NAC."
::= { uds1StatEntry 8 }

uds1StatE1PhysicalState OBJECT-TYPE
SYNTAX INTEGER{
  psF1Operational(1),
  psF2Fc1RaiTempCrcErrors(2),
  psF3Fc2LossOfSignal(3),
  psF4Fc3AlarmIndSignal(4),
  psF5Fc4RaiContCrcErrors(5),
  psF6PowerOn(6)
}
ACCESS read-only
STATUS mandatory
DESCRIPTION
"This object reflects the physical state of the E1 DS1 span 
line on the T1-PRI ISDN NAC."
::= { uds1StatEntry 9 }

uds1StatLoopBackInit OBJECT-TYPE
SYNTAX INTEGER{
  none(1),
  network(2),
  command(3)
}
ACCESS read-only
STATUS mandatory
DESCRIPTION
"This object tells if the loopback was initiated by the 
network or by command"
::= { uds1StatEntry 10 }

uds1StatNfasDChannel OBJECT-TYPE
SYNTAX INTEGER{
  notSupported(1),
  dchannel(2),
  extraBchannel(3)
}
ACCESS read-only
STATUS mandatory
DESCRIPTION
"This reflect how a PRI span line is using the DS0 normally 
assigned as a D channel when NFAS is being used.  This 
object does not apply to Rob Bit T1 operation.
Default = 
dchannel(2)."
::= { uds1StatEntry 11 }

uds1StatDChannel OBJECT-TYPE
SYNTAX INTEGER{
  notSupported(1),
  inService(2),
  bChannel(3)
}
ACCESS read-only
STATUS mandatory
DESCRIPTION
"This is the status of the D channel for this PRI span line. 
 A value of notSupported(1) means that this DS1 is not 
operating in ISDN mode or there is no D channel defined on 
this span line."
::= { uds1StatEntry 12 }

uds1StatDs0SrvcChngLst OBJECT-TYPE
SYNTAX DisplayString (SIZE(0..96))
ACCESS read-only
STATUS mandatory
DESCRIPTION
"This object contains the current list of DS0s that have 
changed their state from In Service to Out of Service or 
Vice versa.  The list is included in the corresponding SNMP 
trap."  
::= { uds1StatEntry 13 }

uds1StatMultiFrame OBJECT-TYPE
SYNTAX INTEGER{
  false(1),
  true(2)
}
ACCESS read-only
STATUS mandatory
DESCRIPTION
"This object identifies when the E1/PRI NAC line has lost 
synchronization with the Time-Slot 16 Multi-Frame alignment 
pattern. Only valid for E1/CAS NAC."  
::= { uds1StatEntry 14 }

uds1StatRemMultiFrame OBJECT-TYPE
SYNTAX INTEGER{
  false(1),
  true(2)
}
ACCESS read-only
STATUS mandatory
DESCRIPTION
"This object identifies when the remote end of the specified 
E1/PRI NAC line has lost synchronization with the Time-Slot 
16 Multi-Frame alignment pattern. Only valid for E1/CAS 
NAC."  
::= { uds1StatEntry 15 }

uds1StatServiceState OBJECT-TYPE
SYNTAX INTEGER{
  notSupported(1),
  inService(2),
  localOutOfService(3)
}
ACCESS read-only
STATUS mandatory
DESCRIPTION
"This object shows the current state of the DS1 Service. 
Default = inService(2)."
::= { uds1StatEntry 16 }

-- The USR DS1 Command Group
-- Implementation of the USR DS1 Command Group is
-- mandatory for all systems that provide management
-- of USR's Dual T1 Cards.

uds1CmdTable OBJECT-TYPE
SYNTAX SEQUENCE OF Uds1CmdEntry
ACCESS not-accessible
STATUS mandatory
DESCRIPTION
"The DS1 Command table contains an entry for each of the 
manageable CSUs in the chassis.  It provides a means 
through which to take specific actions on one or more CSUs 
in the chassis."
::= { uds1 6 }

uds1CmdEntry OBJECT-TYPE
SYNTAX Uds1CmdEntry
ACCESS not-accessible
STATUS mandatory
DESCRIPTION
"There is one entry in the DS1 Command table per CSU in the 
chassis."
INDEX { uds1CmdIndex }
::= { uds1CmdTable 1 }

Uds1CmdEntry ::=
SEQUENCE {
uds1CmdIndex
    INTEGER,
uds1CmdMgtStationId
    OCTET STRING,
uds1CmdReqId
    INTEGER,
uds1CmdFunction
    INTEGER,
uds1CmdForce
    INTEGER,
uds1CmdParam
    OCTET STRING,
uds1CmdResult
    INTEGER,
uds1CmdCode
    INTEGER
}

uds1CmdIndex OBJECT-TYPE
SYNTAX INTEGER
ACCESS read-only
STATUS mandatory
DESCRIPTION
"A unique value for each CSU in the chassis.  The value of 
uds1CmdIndex matches the value of the index for the 
corresponding DS1 entity in the entity table of the chassis 
MIB."
::= { uds1CmdEntry 1 }

uds1CmdMgtStationId OBJECT-TYPE
SYNTAX OCTET STRING (SIZE(0..8))
ACCESS read-write
STATUS mandatory
DESCRIPTION
"This object is a generic read-write variable that a 
Management Station (MS) can use to guarantee that the 
results from a given command are the result of that 
specific MS. Each MS must SET a unique value to this object 
when doing commands and GET the value of this object 
together with uds1CmdReqId and uds1CmdResult to detect 
interference from other MSs."
::= { uds1CmdEntry 2 }

uds1CmdReqId OBJECT-TYPE
SYNTAX INTEGER
ACCESS read-only
STATUS mandatory
DESCRIPTION
"This object contains the value of the request-id field in 
the SNMP PDU which invoked the current or most recent 
command on this DS1 interface.  If the request-id is 
unknown or undefined, this object contains the zero value."
::= { uds1CmdEntry 3 }

uds1CmdFunction OBJECT-TYPE
SYNTAX INTEGER{
  noCommand(1),
  forceReceiverReframe(2),
  enterLoopback(3),
  exitLoopback(4),
  inService(5),
  localOutOfService(6),
  blockAnalogCalls(7),
  blockDigitalCalls(8),
  blockAllCalls(9),
  blockNoCalls(10),
  redAlarmOverride(11),
  takeDownDChannel(12),
  bringUpDChannel(13)
}
ACCESS read-write
STATUS mandatory
DESCRIPTION
"This object identifies the command being requested."
::= { uds1CmdEntry 4 }

uds1CmdForce OBJECT-TYPE
SYNTAX INTEGER{
  force(1),
  noForce(2)
}
ACCESS read-write
STATUS mandatory
DESCRIPTION
"In some cases, the DS1 interface may be in a state such 
that certain commands could adversely affect connections.  
In such cases, a command request with uds1CmdForce not 
defined, or set to noForce will result in a warning.  If 
the operator elects to ignore such warnings, uds1CmdForce 
can be set to force in a re-issued request and the command 
will be carried out regardless of its potentially 
hazzardous effects."
::= { uds1CmdEntry 5 }

uds1CmdParam OBJECT-TYPE
SYNTAX OCTET STRING (SIZE(0..24))
ACCESS read-write
STATUS mandatory
DESCRIPTION
"This object contains parameters that are specific to the 
particular command being issued.  In some cases, there will 
be no additional parameters required."
::= { uds1CmdEntry 6 }

uds1CmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command, or the value none(1) if no commands have 
been requested since the last reset."
::= { uds1CmdEntry 7 }

uds1CmdCode OBJECT-TYPE
SYNTAX INTEGER{
  noError(1),
  unable(2),
  unrecognizedCommand(6),
  slotEmpty(8),
  noResponse(12),
  unsupportedCommand(20),
  deviceDisabled(22),
  pendingSoftwareDownload(73)
}
ACCESS read-only
STATUS mandatory
DESCRIPTION
"The value of this object upon command completion indicates 
a further description of what went wrong if the command was 
unsuccessful."
::= { uds1CmdEntry 8 }

uds1TrapEnaTable OBJECT-TYPE
SYNTAX SEQUENCE OF Uds1TrapEnaEntry
ACCESS not-accessible
STATUS mandatory
DESCRIPTION
"A trap enable table that defines a column for every trap 
that a DS1 entity can generate."
::= { uds1 7 }

uds1TrapEnaEntry OBJECT-TYPE
SYNTAX Uds1TrapEnaEntry
ACCESS not-accessible
STATUS mandatory
DESCRIPTION
"There is one entry in this table for every CSU that exists 
in the chassis."
INDEX { uds1TrapEnaIndex }
::= { uds1TrapEnaTable 1 }

Uds1TrapEnaEntry ::=
SEQUENCE {
uds1TrapEnaIndex
    INTEGER,
uds1TrapEnaYellowAlarm
    INTEGER,
uds1TrapEnaRedAlarm
    INTEGER,
uds1TrapEnaLossOfSignal
    INTEGER,
uds1TrapEnaAlarmIndSignal
    INTEGER,
uds1TrapEnaYellowAlarmClr
    INTEGER,
uds1TrapEnaRedAlarmClr
    INTEGER,
uds1TrapEnaLossOfSgnlClr
    INTEGER,
uds1TrapEnaAlrmIndSgnlClr
    INTEGER,
uds1TrapEnaContCrcAlrm
    INTEGER,
uds1TrapEnaContCrcAlrmClr
    INTEGER,
uds1TrapEnaPhysStateChng
    INTEGER,
uds1TrapEnaDchanInSrvc
    INTEGER,
uds1TrapEnaDchanOutOfSrvc
    INTEGER,
uds1TrapEnaDs0InSrvc
    INTEGER,
uds1TrapEnaDs0OutOfSrvc
    INTEGER,
uds1TrapEnaMultiFrame
    INTEGER,
uds1TrapEnaRemMultiFrame
    INTEGER,
uds1TrapEnaMultiFrmClr
    INTEGER,
uds1TrapEnaRemMultiFrmClr
    INTEGER
}

uds1TrapEnaIndex OBJECT-TYPE
SYNTAX INTEGER
ACCESS read-only
STATUS mandatory
DESCRIPTION
"A unique value for each CSU in the chassis.  The value of 
uds1TrapEnaIndex matches the value of the index for the 
corresponding DS1 entity in the entity table of the chassis 
MIB."
::= { uds1TrapEnaEntry 1 }

uds1TrapEnaYellowAlarm OBJECT-TYPE
SYNTAX INTEGER{
  enableTrap(1),
  disableAll(2),
  enableLog(3),
  enableAll(4)
}
ACCESS read-write
STATUS mandatory
DESCRIPTION
"Enable the generation of an SNMP trap upon detection of a 
yellow alarm condition on the specified DS1."
::= { uds1TrapEnaEntry 2 }

uds1TrapEnaRedAlarm OBJECT-TYPE
SYNTAX INTEGER{
  enableTrap(1),
  disableAll(2),
  enableLog(3),
  enableAll(4)
}
ACCESS read-write
STATUS mandatory
DESCRIPTION
"Enable the generation of an SNMP trap upon detection of a 
red alarm condition on the specified DS1."
::= { uds1TrapEnaEntry 3 }

uds1TrapEnaLossOfSignal OBJECT-TYPE
SYNTAX INTEGER{
  enableTrap(1),
  disableAll(2),
  enableLog(3),
  enableAll(4)
}
ACCESS read-write
STATUS mandatory
DESCRIPTION
"Enable the generation of an SNMP trap upon detection of 
loss of signal on the specified DS1."
::= { uds1TrapEnaEntry 4 }

uds1TrapEnaAlarmIndSignal OBJECT-TYPE
SYNTAX INTEGER{
  enableTrap(1),
  disableAll(2),
  enableLog(3),
  enableAll(4)
}
ACCESS read-write
STATUS mandatory
DESCRIPTION
"Enable the generation of an SNMP trap upon detection of an 
alarm indication signal (AIS) on the specified DS1."
::= { uds1TrapEnaEntry 5 }

uds1TrapEnaYellowAlarmClr OBJECT-TYPE
SYNTAX INTEGER{
  enableTrap(1),
  disableAll(2),
  enableLog(3),
  enableAll(4)
}
ACCESS read-write
STATUS mandatory
DESCRIPTION
"Enable the generation of an SNMP trap upon detection of a 
yellow alarm condition being cleared on the specified DS1."
::= { uds1TrapEnaEntry 6 }

uds1TrapEnaRedAlarmClr OBJECT-TYPE
SYNTAX INTEGER{
  enableTrap(1),
  disableAll(2),
  enableLog(3),
  enableAll(4)
}
ACCESS read-write
STATUS mandatory
DESCRIPTION
"Enable the generation of an SNMP trap upon detection of a 
red alarm condition being cleared on the specified DS1."
::= { uds1TrapEnaEntry 7 }

uds1TrapEnaLossOfSgnlClr OBJECT-TYPE
SYNTAX INTEGER{
  enableTrap(1),
  disableAll(2),
  enableLog(3),
  enableAll(4)
}
ACCESS read-write
STATUS mandatory
DESCRIPTION
"Enable the generation of an SNMP trap upon detection of 
loss of signal condition being cleared on the specified 
DS1."
::= { uds1TrapEnaEntry 8 }

uds1TrapEnaAlrmIndSgnlClr OBJECT-TYPE
SYNTAX INTEGER{
  enableTrap(1),
  disableAll(2),
  enableLog(3),
  enableAll(4)
}
ACCESS read-write
STATUS mandatory
DESCRIPTION
"Enable the generation of an SNMP trap upon detection of an 
alarm indication signal (AIS) being cleared on the 
specified DS1."
::= { uds1TrapEnaEntry 9 }

uds1TrapEnaContCrcAlrm OBJECT-TYPE
SYNTAX INTEGER{
  enableTrap(1),
  disableAll(2),
  enableLog(3),
  enableAll(4)
}
ACCESS read-write
STATUS mandatory
DESCRIPTION
"Enable the generation of an SNMP trap upon detection of a 
continuous CRC condition on the specified DS1."
::= { uds1TrapEnaEntry 10 }

uds1TrapEnaContCrcAlrmClr OBJECT-TYPE
SYNTAX INTEGER{
  enableTrap(1),
  disableAll(2),
  enableLog(3),
  enableAll(4)
}
ACCESS read-write
STATUS mandatory
DESCRIPTION
"Enable the generation of an SNMP trap upon detection of the 
clearing of a continuous CRC condition on the specified 
DS1."
::= { uds1TrapEnaEntry 11 }

uds1TrapEnaPhysStateChng OBJECT-TYPE
SYNTAX INTEGER{
  enableTrap(1),
  disableAll(2),
  enableLog(3),
  enableAll(4)
}
ACCESS read-write
STATUS mandatory
DESCRIPTION
"Enable the generation of an SNMP trap upon detection of a 
change in the physical state of the specified DS1."
::= { uds1TrapEnaEntry 12 }

uds1TrapEnaDchanInSrvc OBJECT-TYPE
SYNTAX INTEGER{
  enableTrap(1),
  disableAll(2),
  enableLog(3),
  enableAll(4)
}
ACCESS read-write
STATUS mandatory
DESCRIPTION
"Enable the generation of an SNMP trap upon detection of a 
change in the service state of a D channel on this span 
line from Out of Service, Maintenance or Standby to In 
Service.
Default = disableAll(2)."
::= { uds1TrapEnaEntry 13 }

uds1TrapEnaDchanOutOfSrvc OBJECT-TYPE
SYNTAX INTEGER{
  enableTrap(1),
  disableAll(2),
  enableLog(3),
  enableAll(4)
}
ACCESS read-write
STATUS mandatory
DESCRIPTION
"Enable the generation of an SNMP trap upon detection of a 
change in the service state of a D channel on this span 
line from In Service to Out of Service, Maintenance or 
Standby.
Default = disableAll(2)."
::= { uds1TrapEnaEntry 14 }

uds1TrapEnaDs0InSrvc OBJECT-TYPE
SYNTAX INTEGER{
  enableTrap(1),
  disableAll(2),
  enableLog(3),
  enableAll(4)
}
ACCESS read-write
STATUS mandatory
DESCRIPTION
"Enable the generation of an SNMP trap upon detection of a 
change in the service state of a DS0 on this span line from 
Out of Service to In Service.
Default = disableAll(2)."
::= { uds1TrapEnaEntry 15 }

uds1TrapEnaDs0OutOfSrvc OBJECT-TYPE
SYNTAX INTEGER{
  enableTrap(1),
  disableAll(2),
  enableLog(3),
  enableAll(4)
}
ACCESS read-write
STATUS mandatory
DESCRIPTION
"Enable the generation of an SNMP trap upon detection of a 
change in the service state of a DS0 on this span line from 
In Service to Out of Service.
Default = disableAll(2)."
::= { uds1TrapEnaEntry 16 }

uds1TrapEnaMultiFrame OBJECT-TYPE
SYNTAX INTEGER{
  enableTrap(1),
  disableAll(2),
  enableLog(3),
  enableAll(4)
}
ACCESS read-write
STATUS mandatory
DESCRIPTION
"Enable the generation of an SNMP trap upon detection of a 
Multi-Frame Alignment condition on the specified DS1. 
Default = disableAll(2)."
::= { uds1TrapEnaEntry 17 }

uds1TrapEnaRemMultiFrame OBJECT-TYPE
SYNTAX INTEGER{
  enableTrap(1),
  disableAll(2),
  enableLog(3),
  enableAll(4)
}
ACCESS read-write
STATUS mandatory
DESCRIPTION
"Enable the generation of an SNMP trap upon detection of a 
Remote Multi-Frame Alignment condition on the specified 
DS1. Default = disableAll(2)."
::= { uds1TrapEnaEntry 18 }

uds1TrapEnaMultiFrmClr OBJECT-TYPE
SYNTAX INTEGER{
  enableTrap(1),
  disableAll(2),
  enableLog(3),
  enableAll(4)
}
ACCESS read-write
STATUS mandatory
DESCRIPTION
"Enable the generation of an SNMP trap upon detection of 
clearing a Multi-Frame Alignment condition on the specified 
DS1. Default = disableAll(2)."
::= { uds1TrapEnaEntry 19 }

uds1TrapEnaRemMultiFrmClr OBJECT-TYPE
SYNTAX INTEGER{
  enableTrap(1),
  disableAll(2),
  enableLog(3),
  enableAll(4)
}
ACCESS read-write
STATUS mandatory
DESCRIPTION
"Enable the generation of an SNMP trap upon detection of 
clearing a Remote Multi-Frame Alignment condition on the 
specified DS1. Default = disableAll(2)."
::= { uds1TrapEnaEntry 20 }

END
