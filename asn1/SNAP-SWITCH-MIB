SNAP-SWITCH-MIB DEFINITIONS ::= BEGIN

-- Title:  SysKonnect SNAP-SWITCH-MIB Extension version 1.0
-- Date:   August, 1996
-- By:     Georg Klug <gklug@skd.de>

IMPORTS
    enterprises, OBJECT-TYPE, Counter,
    Gauge, TimeTicks, DisplayString,
    NetworkAddress			FROM RFC1155-SMI
    fddimibPORTSMTIndex, fddimibPORTIndex, fddimibPORTMyType,
    fddimibPORTConnectState		FROM RFC-1512
    OBJECT-TYPE				FROM RFC-1212
    TRAP-TYPE                           FROM RFC-1215
    MacAddress, BridgeId, Timeout	FROM RFC-1493;


--***********************************************************************
--*   Global Definition of the enterprise
--***********************************************************************

-- S&K private

	sk			OBJECT IDENTIFIER ::= { enterprises 179 }

	skSystems		OBJECT IDENTIFIER ::= { sk 1 }
	skMibs			OBJECT IDENTIFIER ::= { sk 2 }

--***********************************************************************
--*   Definition of the used sysObjectID
--***********************************************************************

skSnapSwitch6020	OBJECT IDENTIFIER ::= { skSystems 5 }

--***********************************************************************
--*   Definition of the private MIB base
--***********************************************************************

skSnapSwitchMib		OBJECT IDENTIFIER ::= { skMibs 2 }


--***********************************************************************
--*   Private Section
--***********************************************************************

sk602xSystemConfig	OBJECT IDENTIFIER ::= { skSnapSwitchMib 1 }
sk602xSwitch		OBJECT IDENTIFIER ::= { skSnapSwitchMib 3 }


-- sk602xSystemConfig stuff

sk602xSysSerialno OBJECT-TYPE
    SYNTAX DisplayString (SIZE (0..255))
    ACCESS read-only
    STATUS mandatory
    DESCRIPTION
    "Serial number."
    ::= { sk602xSystemConfig 1 }

sk602xSysTftpIPAddress OBJECT-TYPE
    SYNTAX NetworkAddress
    ACCESS read-write
    STATUS mandatory
    DESCRIPTION
    "TFTP Server IP address."  
    ::= { sk602xSystemConfig 2 }

sk602xSysTftpFilename OBJECT-TYPE
    SYNTAX DisplayString (SIZE (0..255))
    ACCESS read-write
    STATUS mandatory
    DESCRIPTION
    "TFTP file name."
    ::= { sk602xSystemConfig 3 }

sk602xSysPowerupCount OBJECT-TYPE
    SYNTAX INTEGER
    ACCESS read-only
    STATUS mandatory
    DESCRIPTION
    "Powerup Count."
    ::= { sk602xSystemConfig 4 }

sk602xSysBrcastCutoffRate OBJECT-TYPE
    SYNTAX INTEGER
    ACCESS read-write
    STATUS mandatory
    DESCRIPTION
    "Broadcast Cutoff Rate. (0..100000)"
    ::= { sk602xSystemConfig 5 }

sk602xSysGatewayIPAddress OBJECT-TYPE
    SYNTAX NetworkAddress
    ACCESS read-write
    STATUS mandatory
    DESCRIPTION
    "Gateway IP address."      
    ::= { sk602xSystemConfig 6 }

-- sk602x port table - indexed by port

sk602xPortTable OBJECT-TYPE
    SYNTAX SEQUENCE OF Sk602xPortEntry
    ACCESS not-accessible
    STATUS mandatory
    DESCRIPTION
    "The port setup table."
    ::= { skSnapSwitchMib 2 }

sk602xPortEntry OBJECT-TYPE
    SYNTAX Sk602xPortEntry
    ACCESS not-accessible
    STATUS mandatory
    DESCRIPTION
    "The port setup entry."
   INDEX { sk602xPort }
    ::= { sk602xPortTable 1 }

Sk602xPortEntry ::= SEQUENCE {
    sk602xPort
	INTEGER,
    sk602xPortStatus
	INTEGER,
    sk602xPortDuplexStatus
	INTEGER,		
    sk602xPortForwardedFrames
	Counter,		
    sk602xPortRcvdLocalFrames
	Counter
  }

sk602xPort OBJECT-TYPE
    SYNTAX INTEGER
    ACCESS read-only
    STATUS mandatory
    DESCRIPTION
    "A number from 1 to number of ports on the switch."
    ::= { sk602xPortEntry 1 }

sk602xPortStatus OBJECT-TYPE
    SYNTAX INTEGER {
	up (1),
	down (2)
      }
    ACCESS read-only
    STATUS mandatory
    DESCRIPTION
    "Port status."
    ::= { sk602xPortEntry 2 }

sk602xPortDuplexStatus OBJECT-TYPE
    SYNTAX INTEGER {
	half (1),
	full (2)
      }
    ACCESS read-only
    STATUS mandatory
    DESCRIPTION
    "Port duplex status."
    ::= { sk602xPortEntry 3 }

sk602xPortForwardedFrames OBJECT-TYPE
    SYNTAX Counter
    ACCESS read-only
    STATUS mandatory
    DESCRIPTION
    "Number of frames received on this port and forwarded to another
     port on the system module for processing."
    ::= { sk602xPortEntry 4 }

sk602xPortRcvdLocalFrames OBJECT-TYPE
    SYNTAX Counter
    ACCESS read-only
    STATUS mandatory
    DESCRIPTION
    "Number of frames received where the destination is on this port."
    ::= { sk602xPortEntry 5 }

-- sk602xSwitch stuff

sk602xSwitchIPAddress OBJECT-TYPE
    SYNTAX NetworkAddress
    ACCESS read-write
    STATUS mandatory
    DESCRIPTION
    "Since bridges can now be accessed without an IP address,
     there needs to be a way to find out there addresses."
    ::= { sk602xSwitch 1 }

sk602xSwitchSubnetMask OBJECT-TYPE
    SYNTAX NetworkAddress
    ACCESS read-write
    STATUS mandatory
    DESCRIPTION
    "The switch's submask."
    ::= { sk602xSwitch 2 }

sk602xActiveAgingTime OBJECT-TYPE
    SYNTAX INTEGER
    ACCESS read-write
    STATUS mandatory
    DESCRIPTION
    "Active Aging Time."
    ::= { sk602xSwitch 3 }

sk602xPurgeAgingTime OBJECT-TYPE
    SYNTAX INTEGER
    ACCESS read-write
    STATUS mandatory
    DESCRIPTION
    "Purge Aging Time."
    ::= { sk602xSwitch 4 }

sk602xSwitchSTPStatus OBJECT-TYPE
    SYNTAX INTEGER {
	on (1),
	off (2)
      }
    ACCESS read-write
    STATUS mandatory
    DESCRIPTION
    "The switch's Spanning Tree status, enter ON or OFF."
    ::= { sk602xSwitch 5 }

sk602xSwitchManager  OBJECT IDENTIFIER ::= { sk602xSwitch 6 }

sk602xSwitcTrapRcvr1 OBJECT-TYPE
    SYNTAX NetworkAddress
    ACCESS read-write
    STATUS mandatory
    DESCRIPTION
    "The 1th SNMP Trap Destination."
    ::= { sk602xSwitchManager 1 }

sk602xSwitcTrapRcvr2 OBJECT-TYPE
    SYNTAX NetworkAddress
    ACCESS read-write
    STATUS mandatory
    DESCRIPTION
    "The 2th SNMP Trap Destination."
    ::= { sk602xSwitchManager 2 }

sk602xSwitcTrapRcvr3 OBJECT-TYPE
    SYNTAX NetworkAddress
    ACCESS read-write
    STATUS mandatory
    DESCRIPTION
    "The 3th SNMP Trap Destination."
    ::= { sk602xSwitchManager 3 }

sk602xSwitcTrapRcvr4 OBJECT-TYPE
    SYNTAX NetworkAddress
    ACCESS read-write
    STATUS mandatory
    DESCRIPTION
    "The 4th SNMP Trap Destination."
    ::= { sk602xSwitchManager 4 }

END
