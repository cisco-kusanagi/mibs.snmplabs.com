-- *****************************************************************
-- ciscoWanFrX21LineMIB
--
-- September 2002, Subra Hegde
--
-- Copyright (c) 2002 by cisco Systems, Inc.
-- All rights reserved.
-- ****************************************************************

CISCO-WAN-FR-X21-MIB DEFINITIONS ::= BEGIN
IMPORTS
    MODULE-IDENTITY,
    OBJECT-TYPE,
    Integer32
                               FROM SNMPv2-SMI
    MODULE-COMPLIANCE,
    OBJECT-GROUP               FROM SNMPv2-CONF
    x21,
    frPortCnfX21PortGrp        
                               FROM BASIS-MIB
    ciscoWan                   FROM CISCOWAN-SMI;

ciscoWanFrX21MIB MODULE-IDENTITY
    LAST-UPDATED    "200209190000Z"
    ORGANIZATION    "Cisco Systems, Inc."
    CONTACT-INFO
            "       Cisco Systems
                        Customer Service

                Postal: 170 W Tasman Drive
                        San Jose, CA  95134
                        USA

                        Tel: +1 800 553-NETS

                E-mail: cs-wanatm@cisco.com"
    DESCRIPTION
        "The MIB module to configure X.21/HSSI physical
        and logical interfaces.
       This MIB module also contains alarm configuration
       of X.21 interfaces.

       Terminologies Used:
  
       HSSI : High Speed Serial Interface. The HSSI defines
              both electrical and physical interfaces on
              DTE and DCE devices. It operates at the physical
              layer of the OSI reference model. This provides
              high-speed data communication over WAN and LAN links."

    REVISION    "200209190000Z"
    DESCRIPTION
        "Initial version of the MIB.

        The content of this MIB was originally available
        in CISCO-WAN-AXIPOP-MIB defined using SMIv1.
        The applicable objects from CISCO-WAN-AXIPOP-MIB
        are defined using SMIv2 in this MIB."

    ::= { ciscoWan 49 }


x21CnfGrp	OBJECT IDENTIFIER ::= { x21 1 }
x21AlmCnfGrp	OBJECT IDENTIFIER ::= { x21 2 }
x21AlmGrp       OBJECT IDENTIFIER ::= { x21 3 }

-- **********************************************************************
-- X.21 Config Group
--
-- This group contains X.21 line configuration table
-- **********************************************************************

x21CnfGrpTable OBJECT-TYPE
	SYNTAX	   SEQUENCE OF X21CnfGrpEntry
	MAX-ACCESS not-accessible
	STATUS	   current
	DESCRIPTION
	    "The X21 Configuration table. The table size is
	    given by the value of x21LineNumofValidEntries."
	::= { x21CnfGrp 1 }

x21CnfGrpEntry OBJECT-TYPE
	SYNTAX	   X21CnfGrpEntry
	MAX-ACCESS not-accessible
	STATUS	   current
	DESCRIPTION
	    "An entry in the X21 Configuration table."
        INDEX	{ x21LineNum }

	::= { x21CnfGrpTable 1 }

X21CnfGrpEntry ::=
    SEQUENCE {
        x21LineNum                     Integer32,
        x21LineEnable                  INTEGER,
        x21LineType                    INTEGER,
        x21LineRate                    INTEGER,
        x21LineLoopbackCommand         INTEGER,
        x21LineSendCode                INTEGER,
        x21LineLoopbackCodeDetection   INTEGER,
        x21ConnectorType               INTEGER,
        x21InvertClock                 INTEGER,
        x21LineInterfaceType           INTEGER,
        x21ClkFrequencyThreshold       Integer32,
        serialLineRate                 Integer32,
        serialLineRateVariation        Integer32
}

x21LineNum OBJECT-TYPE
	SYNTAX	   Integer32 (1..8)
	MAX-ACCESS read-only
	STATUS	   current
	DESCRIPTION
            "This object is the identifier of a X.21 interface.
            FRSM-HS2/HS2B-HSSI supports a range from 1 to 2.
	    FRSM-HS2B-12IN1 supports a range from 1 to 8."
	::= { x21CnfGrpEntry 1 }

x21LineEnable  OBJECT-TYPE
	SYNTAX	INTEGER {
		    disable (1),
		    enable  (2),
		    modify  (3)
		}
	MAX-ACCESS read-write
	STATUS     current
	DESCRIPTION
		"This variable disables, enables or modifies a line
		 1 - disable
		 2 - enable
		 3 - modify
		Default is enable.
		"
	::= { x21CnfGrpEntry 2 }

x21LineType OBJECT-TYPE
	SYNTAX  INTEGER {
		    dte   (1),
	            dce   (2),
		    dteST (3)
   		}
	MAX-ACCESS read-write
	STATUS     current
	DESCRIPTION
		"This variable indicates the type X21 line type.
		 The line-type affects the clock -- the DCE device
		 always provides the clock and DTE accepts it.
		 dteST is only applicable to V.35 interfaces
		 Default is DTE.
		"
	::= { x21CnfGrpEntry 3 }


x21LineRate OBJECT-TYPE
  	SYNTAX  INTEGER {
		r48Kbps(1),
		r56Kbps(2),
		r64Kbps(3),
		r112Kbps(4),
		r128Kbps(5),
		r168Kbps(6),
		r192Kbps(7),
		r224Kbps(8),
		r256Kbps(9),
		r280Kbps(10),
		r320Kbps(11),
		r336Kbps(12),
		r384Kbps(13),
		r392Kbps(14),
		r448Kbps(15),
		r512Kbps(16),
		r768Kbps(17),
		r1024Kbps(18),
		r1536Kbps(19),
		r1544Kbps(20),
		r1792Kbps(21),
		r1920Kbps(22),
		r1984Kbps(23),
		r2048Kbps(24),
		r3097Kbps(25),
		r3157Kbps(26),
		r4096Kbps(27),
		r4645Kbps(28),
		r4736Kbps(29),
		r6195Kbps(30),
		r6315Kbps(31),
		r7744Kbps(32),
		r7899Kbps(33),
		r8192Kbps(34),
		r9289Kbps(35),
		r9472Kbps(36),
		r10240Kbps(37),
		r10890Kbps(38),
		r11060Kbps(39),
		r12390Kbps(40),
		r12630Kbps(41),
		r13900Kbps(42),
		r14220Kbps(43),
		r14340Kbps(44),
		r15490Kbps(45),
		r15800Kbps(46),
		r16380Kbps(47),
		r20030Kbps(48),
		r24990Kbps(49),
		r52Mbps(50),
-- FRSM_VHS added for frsm_vhs
		r17370Kbps(51),
		r18950Kbps(52),
		r20530Kbps(53),
		r22100Kbps(54),
		r23680Kbps(55),
--
-- n*T1 rates. Added for FRSM_VHS
-- note that 1.544Kbps is already enumerated above
--
		r3088Kbps(56),
		r4632Kbps(57),
		r6176Kbps(58),
		r7720Kbps(59),
		r9264Kbps(60),
		r10808Kbps(61),
		r12352Kbps(62),
		r13896Kbps(63),
		r15440Kbps(64),
		r16984Kbps(65),
		r18528Kbps(66),
		r20072Kbps(67),
		r21616Kbps(68),
		r23160Kbps(69),
		r24704Kbps(70),
		r26248Kbps(71),
		r27792Kbps(72),
		r29336Kbps(73),
		r30880Kbps(74),
		r32424Kbps(75),
		r33968Kbps(76),
		r35512Kbps(77),
		r37056Kbps(78),
		r38600Kbps(79),
		r40144Kbps(80),
		r41688Kbps(81),
		r43232Kbps(82),
		r44776Kbps(83),
		r46320Kbps(84),
		r47864Kbps(85),
		r49408Kbps(86),
		r50952Kbps(87),
--
-- n*E1 rates. Added for FRSM_VHS.		
--
		r6144Kbps(88),
		r12288Kbps(89),
		r14336Kbps(90),
		r16384Kbps(91),
		r18432Kbps(92),
		r20480Kbps(93),
		r22528Kbps(94),
		r24576Kbps(95),
		r26624Kbps(96),
		r28672Kbps(97),
		r30720Kbps(98),
		r32768Kbps(99),
		r34816Kbps(100),
		r36864Kbps(101),
		r38912Kbps(102),
		r40960Kbps(103),
		r43008Kbps(104),
		r45056Kbps(105),
		r47104Kbps(106),
		r49152Kbps(107),
		r51200Kbps(108)
	}
	MAX-ACCESS read-write
	STATUS     current
	DESCRIPTION
		"This variable configures the X.21/HSSI/V.35 line-rate.
		 Note that enumerations 51 through 108 are supported
		 only by FRSM-HS2/HS2B card.

		 default is r48Kbps on FRSM-HS2B-12IN1
		 default is r52Mbps on FRSM-HS2/HS2B-HSSI
		"
	::= { x21CnfGrpEntry 4 }

x21LineLoopbackCommand OBJECT-TYPE
	SYNTAX  INTEGER {
		    x21NoLoop                  (1),
		    x21DiagnosticMetallicLoop  (2),
		    x21DiagnosticFrontcardLoop (3),
		    x21RemoteLoop              (4),
		    v35MetallicLoop            (5)
   		}
         MAX-ACCESS read-write
         STATUS     current
         DESCRIPTION
		"This variable represents the  loopback  state
        	 x21NoLoop
			Not in the loopback state. Normal traffic can be sent
        	 x21DiagnosticMetallicLoop
			Loopbacks the line on the back-card towards the Network.
        	 x21DiagnosticFrontcardLoop
			Loopbacks the line on the frontcard toward the Network.
        	 x21RemoteLoop
             		The remote NTU is in the loop back mode.
			In this state, the FRSM-HS1 is sending the loopback 
			code to remote NTU.
	 	 Default is x21NoLoop.
		 Note: Before going into one of the loopbacks the state
		 should be x21NoLoop.
		"
	::= { x21CnfGrpEntry 5 }

x21LineSendCode OBJECT-TYPE
	SYNTAX  INTEGER {
		    x21NoCode             (1),
		    x21SendLoopACode      (2),
		    x21SendLoopBCode      (3),
		    x21SendLocalLoopCode  (4),
		    x21SendRemoteLoopCode (5),
		    x21SendUnLoopCode     (6)
   	}
	MAX-ACCESS read-write
	STATUS     current
	DESCRIPTION
        	"This variable indicates what type of  code  is
        	 being sent across the X.21/HSSI interface by the
		 device. The values mean:
		 
		x21NoCode: No loopback.

        	x21SendLoopACode:
             		Start sending Loop A code. Valid only if
			the backcard is HSSI and the line-type is DTE.
			This command loops the line module of the remote
			device.

        	x21SendLoopBCode:
             		Start sending Loop B code. Valid only if the
			backcard is HSSI and the line-type is DTE.
			This command loops the digital section of the
			remote device.

        	x21SendLocalLoopCode:
             		Start sending CCITT X.21 Loopback Type 3 code.
			This is valid only if the backcard is X.21 type.

        	x21SendRemoteLoopCode:
             		Start sending CCITT X.21 Loopback Type 2 code.
			This is valid only if the backcard is X.21 type.
		
	       	x21SendUnLoopCode:
             		Sending a loopback termination request.
			Valid for both HSSI and X.21 lines.

		To execute any of the loop-codes the x21LineLoopbackCommand
		should be set to x21RemoteLoop.
		Once the x21SendUnLoopCode succeeds the x21LineLoopbackCommand
		would transition back to x21NoLoop state.
	
		Default is x21NoCode."
	::= { x21CnfGrpEntry 6 }

x21LineLoopbackCodeDetection OBJECT-TYPE
	SYNTAX  INTEGER {
		    codeDetectDisabled (1),
		    codeDetectEnabled  (2)
		}
        MAX-ACCESS read-write
        STATUS     current
        DESCRIPTION
            "Enable detection of line Loopback Codes.
	    The loopback detection is implemented only in HSSI 
            DCE mode.
	    Default is codeDetectDisabled."
        ::= { x21CnfGrpEntry 7 }

x21ConnectorType OBJECT-TYPE
	SYNTAX  INTEGER {
		    x21Backcard  (1),
		    hssiBackcard (2),
		    v35Backcard  (3)
		}
        MAX-ACCESS read-only
        STATUS     current
        DESCRIPTION
		"back card type
		 This object is not used by FRSM-HS2/HS2B
		"
	::= { x21CnfGrpEntry 8 }

x21InvertClock OBJECT-TYPE
       SYNTAX INTEGER {
                  nonInvertedAndNotLooped (1),
                  invertedAndNotLooped    (2),
                  nonInvertedAndLooped    (3),
                  invertedAndLooped       (4)
       }
       MAX-ACCESS read-write
       STATUS     current
       DESCRIPTION
           "This object configures two options:
             a) To invert the clock sent by HS1/HS2B with the 
                TX data or not.
             b) If DCE,to expect the receive clock looped back 
                from DTE or not.

	    If DTE,to loop back the receive clock from DCE or not.
 
            nonInvertedAndNotLooped(1)- a)=dont invert,
                                        b)=dont expect rcv clock/
                                           dont loop rcv clock
            invertedAndNotLooped(2)   - a)=invert,
                                        b)=dont expect rcv clock/
					   dont loop rcv clock
            nonInvertedAndLooped(3)   - a)=dont invert,
                                        b)=expect rcv clock/
					   loop rcv clock
            invertedAndLooped(4)      - a)=invert,      
                                        b)=expect rcv clock/
					   loop rcv clock
 
	    Enums 1 and 2 are applicable for X.21/HSSI/V.35 interfaces.
	    Enums 3 and 4 are applicable only for V.35.

            Default for X.21/HSSI is nonInvertedAndNotLooped(1)
            Default for V.35 is nonInvertedAndLooped(3)
            This object is not used by FRSM-HS2/FRSM-HS2B-HSSI
            This object is used by FRSM-HS2B-12IN1 and default
            values are nonInvertedAndNotLooped(1) for X.21, 
            nonInvertedAndLooped(3) for V.35."
       ::= { x21CnfGrpEntry 9 }

x21LineInterfaceType OBJECT-TYPE
       SYNTAX INTEGER {
                  hssi(1),
                  x21 (2),
                  v35 (3)
       }
       MAX-ACCESS read-write
       STATUS     current
       DESCRIPTION
           "This object indicates serial interface type.
           Default is hssi(1).
		 
           This object is not is configurable in FRSM-HS2
	   and FRSM-HS2B-HSSI. It will be set to hssi(1) by
	   default for these cards
		 
	   This object is configurable in FRSM-H2B-12IN1.
	   Default is v35(3)."
       ::= { x21CnfGrpEntry 10}

x21ClkFrequencyThreshold OBJECT-TYPE
       SYNTAX     Integer32 (1..5)
       MAX-ACCESS read-write
       STATUS     current
       DESCRIPTION
           "This object indicates user configurable percentage of
          clock frequency, which is used by DTE clock monitoring
          to declare clock rate out of bound alarm. This object
          is valid only for X.21/v.35/HSSI DTE interfaces.
	  This object is supported by FRSM-HS2 and FRSM-HS2/B"
       DEFVAL { 3 }
         ::= { x21CnfGrpEntry 11}

serialLineRate OBJECT-TYPE
       SYNTAX     Integer32 (48000..51840000)
       MAX-ACCESS read-write
       STATUS     current
       DESCRIPTION
           "Line rate for X.21/HSSI/V.35 interfaces
	   in bps. This object is supported only by 
           FRSM-HS2/B card, only multiples of
	   1000 are accepted.
		 
	   Default is 48Kbps for X.21/V.35 interfaces
	   and 51840Kbps for HSSI interface."
         ::= { x21CnfGrpEntry 12}

serialLineRateVariation OBJECT-TYPE
       SYNTAX     Integer32 (0..2147483647)
       MAX-ACCESS read-only
       STATUS     current
       DESCRIPTION
           "This object indicates line rate variation of
           HSSI/X.21/V.35 DCE interfaces in ppm (parts
	   per million). i.e.  clock generated from DCE hardware 
           interface = (serialLineRate +/- (serialLineRateVariation
				        * 10^6)/ serialLineRate)

	   This object is supported only by FRSM-HS2/B card "
         ::= { x21CnfGrpEntry 13}


x21LineNumofValidEntries OBJECT-TYPE
	SYNTAX	   Integer32 (1..8)
	MAX-ACCESS read-only
	STATUS	   current
	DESCRIPTION
	    "The number of X.21/HSSI configuration entries
	    (regardless of their current configuration) in
	    the x21ConfigTable table."
	::= { x21CnfGrp 2 }

-- ******************************************************************
--
--
--		LOGICAL PORT CONFIG Group
--
--
-- ******************************************************************

frPortCnfX21PortGrpTable	OBJECT-TYPE
	SYNTAX	   SEQUENCE OF FrPortCnfX21PortGrpEntry
	MAX-ACCESS not-accessible
	STATUS     current
	DESCRIPTION
		"The config table is for X.21/HSSI logical port interface
		"
	::= { frPortCnfX21PortGrp 1 }


frPortCnfX21PortGrpEntry	OBJECT-TYPE
	SYNTAX	   FrPortCnfX21PortGrpEntry
	MAX-ACCESS not-accessible
	STATUS	   current
	DESCRIPTION
	    " An entry for logical port."
	INDEX	{ x21portNum }
    ::= { frPortCnfX21PortGrpTable 1 }

FrPortCnfX21PortGrpEntry ::=
	SEQUENCE {
	    x21portNum 	                 Integer32,
            x21portLineNum               Integer32,
      	    x21portRowStatus             INTEGER,
      	    x21portFlagsBetweenFrames    Integer32,
      	    x21portEqueueServiceRatio    Integer32,
	    x21portSpeed                 Integer32,
	    x21portAdmin                 INTEGER,
	    x21portType                  INTEGER,
	    x21portSvcStatus             INTEGER,
	    x21portSvcInUse              INTEGER,
	    x21portSvcShareLcn           INTEGER,
	    x21portSvcLcnLow             Integer32,
	    x21portSvcLcnHigh            Integer32,
	    x21portSvcDlciLow            Integer32,
	    x21portSvcDlciHigh           Integer32,
	    x21portDeleteSvcs            INTEGER,
	    x21portIngrSvcBandW          Integer32,
	    x21portEgrSvcBandW           Integer32
	}

x21portNum OBJECT-TYPE
	SYNTAX	   Integer32 (1..4) 
	MAX-ACCESS read-only
	STATUS     current
	DESCRIPTION
	    "This is logical port number.
	    The HSSI backcard can support upto 3 ports.
	    The X.21 back card can support 4 logical ports."
	::= { frPortCnfX21PortGrpEntry 1}

x21portLineNum	OBJECT-TYPE
	SYNTAX	   Integer32 (1..4) 
	MAX-ACCESS read-write
	STATUS	   current
	DESCRIPTION
	    "This represents the line number.
	    On FRSM-HS1 the HSSI can support 3 lines
	    and X.21 4 lines."
	::= { frPortCnfX21PortGrpEntry 2}

x21portRowStatus  OBJECT-TYPE		
	SYNTAX	INTEGER {
		add(1),
		del(2),
		mod(3)
		}
	MAX-ACCESS read-write
        STATUS  current
        DESCRIPTION
            "This variable adds, deletes, or modifies the port
	      1- add
	      2 - delete
	      3 - modify
	      Default is add."
        ::= { frPortCnfX21PortGrpEntry 3 }

x21portFlagsBetweenFrames OBJECT-TYPE
	SYNTAX	   Integer32 (1..10) 
	MAX-ACCESS read-write
	STATUS     current
	DESCRIPTION
	    "Number of flags transmitted between two consecutive
	    HDLC frames.
	    Default is 1 flag."
	::= { frPortCnfX21PortGrpEntry 4 }

x21portEqueueServiceRatio OBJECT-TYPE
	SYNTAX	   Integer32 (1..15) 
	MAX-ACCESS read-write
	STATUS	   current
	DESCRIPTION
	    "Number of times queue 1 is serviced 
	    for every time queue 2 is serviced.
	    Default is 1."
	::= { frPortCnfX21PortGrpEntry 5 }

x21portSpeed OBJECT-TYPE
        SYNTAX     Integer32 (0..2147483647)
	MAX-ACCESS read-only
        STATUS     current
        DESCRIPTION
            "Port speed in kbps. At present it is same
	    as line speed."
        ::= { frPortCnfX21PortGrpEntry 6 }

x21portAdmin OBJECT-TYPE
        SYNTAX	INTEGER {
		    up(1),
		    down(2),
		    write-Only(3)
                }
        MAX-ACCESS read-write
        STATUS     current
        DESCRIPTION
            "This object is used for administratively
            changing the status of the port.
            Up/down used to up and down the port.
            Default is the up state."
        ::= { frPortCnfX21PortGrpEntry 7 }

x21portType OBJECT-TYPE
	SYNTAX	INTEGER {
		    frame-relay   (1),
		    frFUNI        (2),
		    frame-forward (3)
            }
	MAX-ACCESS read-write
	STATUS	   current
	DESCRIPTION
	    "This represents port type. The processing of the
	    frames depends on the type of the port."
	::= { frPortCnfX21PortGrpEntry 8 }

x21portSvcStatus OBJECT-TYPE
	SYNTAX	INTEGER {
                    disable (1),
                    enable  (2)
            }
	MAX-ACCESS read-write
	STATUS	   current
	DESCRIPTION
            "This represents SVC status."
	::= { frPortCnfX21PortGrpEntry 9 }

x21portSvcInUse	OBJECT-TYPE
	SYNTAX	INTEGER {
                    not-use (1),
                    in-use  (2)
            }
	MAX-ACCESS read-write
	STATUS	   current
	DESCRIPTION
            "This represents port SVC in use."
	::= { frPortCnfX21PortGrpEntry 10 }

x21portSvcShareLcn	OBJECT-TYPE
	SYNTAX	INTEGER {
                    port-based(1),
                    card-based(2)
            }
	MAX-ACCESS read-only
	STATUS	   current
	DESCRIPTION
	    "This represents port type."
	::= { frPortCnfX21PortGrpEntry 11 }

x21portSvcLcnLow OBJECT-TYPE
	SYNTAX	   Integer32 (16..271)
	MAX-ACCESS read-only
	STATUS	   current
	DESCRIPTION
	    "This represents low end of reserved LCN for SVC."
	::= { frPortCnfX21PortGrpEntry 12 }

x21portSvcLcnHigh OBJECT-TYPE
	SYNTAX	   Integer32 (16..271)
	MAX-ACCESS read-only
	STATUS	   current
	DESCRIPTION
            "This represents high end of reserved LCN for SVC."
	::= { frPortCnfX21PortGrpEntry 13 }

x21portSvcDlciLow	OBJECT-TYPE
	SYNTAX	   Integer32 (0..1023)
	MAX-ACCESS read-only
	STATUS	   current
	DESCRIPTION
	    "This represents low end of reserved DLCI for SVC."
	::= { frPortCnfX21PortGrpEntry 14 }

x21portSvcDlciHigh	OBJECT-TYPE
	SYNTAX	   Integer32 (0..1023)
	MAX-ACCESS read-only
	STATUS	   current
	DESCRIPTION
	    "This represents high end of reserved DLCI for SVC."
	::= { frPortCnfX21PortGrpEntry 15 }

x21portDeleteSvcs OBJECT-TYPE
	SYNTAX	INTEGER {
		delete(1),
		other(2)
		}
	MAX-ACCESS read-write
        STATUS     current
        DESCRIPTION
            "Setting this object to 1 indicates that all the SVC
	    connections on the given port has to be deleted."
	::= { frPortCnfX21PortGrpEntry 16 }

x21portIngrSvcBandW	OBJECT-TYPE
	SYNTAX	   Integer32(0..2147483647)
	MAX-ACCESS read-only
	STATUS	   current
	DESCRIPTION
	    "This represents Ingress Bandwidth reserve for SVC."
	::= { frPortCnfX21PortGrpEntry 17 }

x21portEgrSvcBandW	OBJECT-TYPE
	SYNTAX     Integer32 (0..2147483647)
	MAX-ACCESS read-only
	STATUS	   current
	DESCRIPTION
	    "This represents Egress Bandwidth reserve for SVC."
	::= { frPortCnfX21PortGrpEntry 18 }


-- *********************************************************************
-- x21AlmConfig group
--
-- This group contains X.21/HSSI line alarm configuration table
--
-- *********************************************************************

x21AlmCnfGrpTable OBJECT-TYPE
	SYNTAX	   SEQUENCE OF X21AlmCnfGrpEntry
	MAX-ACCESS not-accessible
	STATUS	   current
	DESCRIPTION
	    "The FRSM-HS1/HS2 interface alarm configuration table."
	::= { x21AlmCnfGrp 1 }

x21AlmCnfGrpEntry OBJECT-TYPE
	SYNTAX	X21AlmCnfGrpEntry
	MAX-ACCESS  not-accessible
	STATUS  current
	DESCRIPTION
	    "An entry in the X.21/HSSI Alarm 
            Configuration table."
	INDEX	{ x21AlmCnfLineNum }
	::= { x21AlmCnfGrpTable 1 }

X21AlmCnfGrpEntry ::=
	SEQUENCE {
		x21AlmCnfLineNum	Integer32,
		x21Severity		INTEGER
      	}

x21AlmCnfLineNum OBJECT-TYPE
	SYNTAX	   Integer32 (1..8)
	MAX-ACCESS read-write
	STATUS	   current
	DESCRIPTION
	    "X.21/HSSI line number.

	     FRSM-HS2/HS2B-HSSI supports a range from 1 to 2.
	     FRSM-HS2B-12IN1 supports a range from 1 to 8."
	::= { x21AlmCnfGrpEntry 1 }

x21Severity	OBJECT-TYPE
	SYNTAX	INTEGER {
		minor(1),
		major(2),
		dontcare(3)
	}
	MAX-ACCESS read-write
	STATUS     current
	DESCRIPTION
	    "This variable is used to setup the severity of
            LOS(Loss of Signal) or clock mismatch alarm.
            Whenever the above condition arises, the
	    FRSM-HS1/HS2/HS2B will send the alarm with 
            appropriate status."
	::= { x21AlmCnfGrpEntry 2 }


-- *********************************************************************
--
-- X.21/HSSI Alarm Group
--
-- This group contains X.21/HSSI line alarm table
-- 
-- *********************************************************************

x21AlmGrpTable OBJECT-TYPE
	SYNTAX	   SEQUENCE OF X21AlmGrpEntry
	MAX-ACCESS not-accessible
	STATUS	   current
	DESCRIPTION
	    "The X.21/HSSI interface alarm configuration table."
	::= { x21AlmGrp 1 }

x21AlmGrpEntry OBJECT-TYPE
	SYNTAX	   X21AlmGrpEntry
	MAX-ACCESS not-accessible
	STATUS     current
	DESCRIPTION
		"An entry in the X21 Alarm table"
	INDEX	{ x21AlmLineNum }
	::= { x21AlmGrpTable 1 }

X21AlmGrpEntry ::=
	SEQUENCE {
		x21AlmLineNum		Integer32,
		x21LineAlarmState	Integer32,
		x21LineEIAStatus	Integer32,
		x21AlarmClrButton	INTEGER
	}

x21AlmLineNum OBJECT-TYPE
	SYNTAX	   Integer32 (1..8)
	MAX-ACCESS read-only
	STATUS     current
	DESCRIPTION
	    "This object is the identifier (line number) of a
            X.21/HSSI interface. The value for this object must
            be same as the value of x21LineNum."
	::= { x21AlmGrpEntry 1 }

x21LineAlarmState OBJECT-TYPE
	SYNTAX	   Integer32 (0..1023)
	MAX-ACCESS read-only
	STATUS     current
	DESCRIPTION
		"This variable is a bitmap of the X21 Line ALarms
		 on the FRSM-HS1. A value of zero indicates no alarms.
		 Itemized below are the individual bits:
		 BitPosition    Alarm
		 -----------    -----
		  0		C/I signal is OFF (also used to indicate LOS)
                  1             Clock rate mismatch (used in DTE mode)
		  2		Internal Loopback (diagnostic loopback)
		  3		HSSI Local LoopA (line is in loopback)
                  4             HSSI Local LoopB (line is in loopback)
		  5		Remote Loopback (line is transmitting loopcodes)
		  6             For V35 DTE mode, DCD and CTS both are inactive
                  7             For V35 DCE mode, RTS is inactive
                  8             No cable attached to V35 backcard
                  9             Wrong cable attached to V35 backcard
                 If all the bit-states are 0s:
                  - line is not in alarm, or
                  - line not in loopback, or
                  - line is transmitting any loopback codes.
		"
	::= { x21AlmGrpEntry 2 }

x21LineEIAStatus OBJECT-TYPE
	SYNTAX	   Integer32 (0..'10'h)
	MAX-ACCESS read-only
	STATUS	   current
	DESCRIPTION
            "Indicates the status of X.21/HSSI lines:
	      0x01 -- c-lead high
	      0x02 -- i-lead high
	      0x04 -- LC-lead high (valid only for HSSI DCE mode)."
	::= { x21AlmGrpEntry 3 }

x21AlarmClrButton OBJECT-TYPE
	SYNTAX  INTEGER {
		    noaction (1),
	            clear    (2)
	}
	MAX-ACCESS read-write
	STATUS     current
	DESCRIPTION
	    "This variable is used to clear all the 
            alarms for the line.
		 1 = No action
		 2 = Clear alarm."
	::= { x21AlmGrpEntry 4 }

-- conformance information

cwfX21MIBConformance  OBJECT IDENTIFIER ::= { ciscoWanFrX21MIB 2 }

cwfX21MIBGroups       OBJECT IDENTIFIER ::= { cwfX21MIBConformance 1 }

cwfX21MIBCompliances  OBJECT IDENTIFIER ::= { cwfX21MIBConformance 2 }

-- compliance statements

cwfX21Compliance MODULE-COMPLIANCE
    STATUS  current
    DESCRIPTION
        "The compliance statement for objects related
        to Frame Relay Ports."
    MODULE  
         MANDATORY-GROUPS {
             ciscoWanFrX21LineGroup,
             ciscoWanFrX21PortGroup,
             ciscoWanFrX21AlarmConfGroup,
             ciscoWanFrX21AlarmGroup
         }
     ::= { cwfX21MIBCompliances 1 }

ciscoWanFrX21PortGroup OBJECT-GROUP
     OBJECTS {
         x21portNum, 	
         x21portLineNum, 
         x21portRowStatus,
         x21portFlagsBetweenFrames,
         x21portEqueueServiceRatio,
         x21portSpeed,
         x21portAdmin,
         x21portType,
         x21portSvcStatus,
         x21portSvcInUse,
         x21portSvcShareLcn,
         x21portSvcLcnLow,
         x21portSvcLcnHigh,
         x21portSvcDlciLow,
         x21portSvcDlciHigh,
         x21portDeleteSvcs,
         x21portIngrSvcBandW,
         x21portEgrSvcBandW
     }
     STATUS current
     DESCRIPTION
         "The collection of objects which are applicable
         for X21 ports in frame relay."
       ::= { cwfX21MIBGroups 1 }

ciscoWanFrX21LineGroup OBJECT-GROUP
     OBJECTS {
         x21LineNum,
         x21LineEnable,
         x21LineType,
         x21LineRate,
         x21LineLoopbackCommand,
         x21LineSendCode,
         x21LineLoopbackCodeDetection,
         x21ConnectorType,
         x21InvertClock,
         x21LineInterfaceType,
         x21ClkFrequencyThreshold,
         serialLineRate,
         serialLineRateVariation,
         x21LineNumofValidEntries
       }
       STATUS current
       DESCRIPTION
           "The collection of objects which are related
           to x21 lines."
       ::= { cwfX21MIBGroups 2 }
 
ciscoWanFrX21AlarmConfGroup OBJECT-GROUP
     OBJECTS {
         x21AlmCnfLineNum,
         x21Severity
     }
     STATUS current
     DESCRIPTION
           "The collection of objects which are related
           to x21 lines."
       ::= { cwfX21MIBGroups 3 }
 
ciscoWanFrX21AlarmGroup OBJECT-GROUP
     OBJECTS {
         x21AlmLineNum,
         x21LineAlarmState,
         x21LineEIAStatus,
         x21AlarmClrButton
     }
     STATUS current
     DESCRIPTION
          "The collection of objects which are related
           to x21 lines."
       ::= { cwfX21MIBGroups 4 }
END
