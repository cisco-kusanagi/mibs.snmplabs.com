-- 
-- MANTRA-MIB module definition  
--
-- This mib is for controlling the various modules/processes in mantra
-- 
-- $Id: mantra.MIB.in,v 1.1 1999/06/30 16:12:56 avirmani Exp $
--
--

MANTRA-MIB DEFINITIONS ::= BEGIN
IMPORTS
    TimeTicks, enterprises, Counter
        FROM RFC1155-SMI
    OBJECT-TYPE
        FROM RFC-1212
    DisplayString
        FROM RFC1213-MIB
    MODULE-IDENTITY, ObjectName, Integer32, Counter32, snmpModules
        FROM SNMPv2-SMI
    TruthValue, DisplayString, TestAndIncr, TimeStamp, RowStatus
        FROM SNMPv2-TC;

	lucent		    OBJECT IDENTIFIER  ::=  {  enterprises  1751  }
	products	    OBJECT IDENTIFIER  ::=  {  lucent  1  }
	softSwitch  	OBJECT IDENTIFIER  ::=  {  products 1198  }

	mantraAdmin	MODULE-IDENTITY    
        LAST-UPDATED "310701"
        ORGANIZATION "Lucent Technologies"    
        CONTACT-INFO 
                ""    
        DESCRIPTION
                "The MIB module for entities implementing the xxxx
                protocol."  

::=  {  softSwitch 99 }

	--
	-- The various entries in this mib
	--

	moduleSummary OBJECT-TYPE
	    SYNTAX  DisplayString
	    MAX-ACCESS  read-only
	    STATUS  current
	    DESCRIPTION
		    "A short summary of the status of the mantra 
		    software modules.  This is provided as a
		    convenience variable to the administrator, so he
		    can see everything at a glance without polling each 
		    component separately.  
		    Processes can be in one of the four states:
			0 - not started,
			1 - in the process of starting up,
			2 - up, but inactive (only one process in a
			    fail-over group is active at a time)
			3 - up, and active
			4 - died (on its own)
			5 - stopped, i.e. by some command"

	    ::= { mantraAdmin 1 }

	mantraUpTime OBJECT-TYPE
	    SYNTAX  TimeTicks
	    MAX-ACCESS  read-only
	    STATUS  current
	    DESCRIPTION
		    "The time (in hundredths of a second) since the
		    mantra software was last re-initialized."

	    ::= { mantraAdmin 2 }

	mantraRetryCount  OBJECT-TYPE
	    SYNTAX  INTEGER (1..60 )
	    MAX-ACCESS  read-write
	    STATUS  current
	    DESCRIPTION
		    "The number of retry attempts to make when 
		    starting a software component managed by this mib."

	    ::= { mantraAdmin 3 }

	mantraRetryInterval  OBJECT-TYPE
	    SYNTAX  INTEGER ( 5..60 )
	    MAX-ACCESS  read-write
	    STATUS  current
	    DESCRIPTION
		    "The time in seconds between the above retry attempts."

	    ::= { mantraAdmin 4 }

	mantraReboot OBJECT-TYPE
	    SYNTAX  INTEGER ( 0..1 )
	    MAX-ACCESS  read-write
	    STATUS  current
	    DESCRIPTION
		    "Each time the user executes a set on this entry
		    with a value equal to 1, all components controlled
		    by this module in the softswitch are rebooted."

	    ::= { mantraAdmin 5 }

	mantraTurnoff OBJECT-TYPE
	    SYNTAX  INTEGER ( 0..1 )
	    MAX-ACCESS  read-write
	    STATUS  current
	    DESCRIPTION
		    "Each time the user executes a set on this entry
		    with a value equal to 1, all components controlled
		    by this module in the softswitch are turned off."

	    ::= { mantraAdmin 6 }

	startProcess OBJECT-TYPE
	    SYNTAX  DisplayString
	    MAX-ACCESS  read-write
	    STATUS  current
	    DESCRIPTION
		    "The user can set this entry to the name of the 
		    module that needs to be started, and it causes
		    that process to be restarted.  If the process is
		    already running, no action takes place.
		    The process name being set must be in the same format 
		    switch:group:pid, as returned in moduleSummary"

	    ::= { mantraAdmin 7 }

	stopProcess OBJECT-TYPE
	    SYNTAX  DisplayString
	    MAX-ACCESS  read-write
	    STATUS  current
	    DESCRIPTION
		    "The user can set this entry to the name of the 
		    module that needs to be stopped, and it causes
		    that process to be stopped.  If the process is
		    already stopped, no action takes place.
		    The process name being set must be in the same format 
		    switch:group:pid, as returned in moduleSummary"

	    ::= { mantraAdmin 8 }

	currentProcess OBJECT-TYPE
	    SYNTAX  DisplayString
	    MAX-ACCESS  read-write
	    STATUS  current
	    DESCRIPTION
		    "The user can set this entry to the name of the 
		    process he wants to interact with, and all future 
		    gets on processState variable return the health
		    information for that process"

	    ::= { mantraAdmin 9 }

	processState OBJECT-TYPE
	    SYNTAX  DisplayString
	    MAX-ACCESS  read-only
	    STATUS  current
	    DESCRIPTION
		    "A get on this variable returns the health of 
		    the process named in currentProcess variable."

	    ::= { mantraAdmin 10 }

	
END
