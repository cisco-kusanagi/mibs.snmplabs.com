--  Copyright 1996, Com21 Inc.  All Rights Reserved.
--
 
COM21-HCXOC3-MIB DEFINITIONS ::= BEGIN
  IMPORTS
        MODULE-IDENTITY, OBJECT-TYPE, NOTIFICATION-TYPE, Integer32,
        IpAddress, Gauge32, TimeTicks
            FROM SNMPv2-SMI
        DisplayString, MacAddress
            FROM SNMPv2-TC
        com21, com21Hcx
            FROM COM21-HCX-MIB
        com21Traps FROM COM21-HCX-MIB
		  hcxAlmSeverity, hcxEventLogTime
            FROM COM21-HCXALM-MIB;
 
 
        com21HcxOc3 MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"
 
                DESCRIPTION
                        "This is the Com21 ComController Oc3
                         MIB module. COM21 Part# 005-0025-00"
                ::= { com21Hcx 90 }
 
 
 

        com21HcxOc3UnitGroup      OBJECT IDENTIFIER ::= {com21Hcx 91}
        com21HcxOc3PortGroup      OBJECT IDENTIFIER ::= {com21Hcx 92}
        com21HcxOc3VccGroup       OBJECT IDENTIFIER ::= {com21Hcx 93}
        com21HcxOc3StatsGroup     OBJECT IDENTIFIER ::= {com21Hcx 94}

        PrimServiceState ::= INTEGER { is(1), oos(2) }
        Com21RowStatus   ::= INTEGER { active(1),
                                       create(2),
                                       destroy(3),
                                       deactive(4) }



        -- -- -- -- -- -- -- -- -- -- -- -- -- -- -- -- -- -- -- -- -- -- -- --
        -- -- -- -- -- -- -- -- -- -- -- -- -- -- -- -- -- -- -- -- -- -- -- --
        --
        -- com21HcxOc3UnitGroup
        --
        -- defines the attributes related to the management of the Oc3
        -- Unit. For the purposes of this MIB, all ethernet card types shall
        -- be managed by this group. The exact type and number of ports shall
        -- be defined within the group.
        --
        -- -- -- -- -- -- -- -- -- -- -- -- -- -- -- -- -- -- -- -- -- -- -- --
        -- -- -- -- -- -- -- -- -- -- -- -- -- -- -- -- -- -- -- -- -- -- -- --
 
        com21HcxOc3UnitTable OBJECT-TYPE
                SYNTAX  SEQUENCE OF HcxOc3UnitEntry
                MAX-ACCESS  not-accessible
                STATUS  current
                DESCRIPTION "."
                ::= { com21HcxOc3UnitGroup 1 }
 
        com21HcxOc3UnitEntry OBJECT-TYPE
                SYNTAX  HcxOc3UnitEntry
                MAX-ACCESS  not-accessible
                STATUS  current
                DESCRIPTION "."
                INDEX { hcxOc3UnitShelfId, hcxOc3UnitSlotId }
                ::= { com21HcxOc3UnitTable 1 }
 
        HcxOc3UnitEntry ::= SEQUENCE {
                hcxOc3UnitShelfId                 INTEGER,
                hcxOc3UnitSlotId                  Integer32,
                hcxOc3HardwareVersion         	  DisplayString,
                hcxOc3BootVersion                 DisplayString,
                hcxOc3UnitPrimServState           PrimServiceState,
                hcxOc3UnitSecServState            DisplayString,
                hcxOc3RestartAction               INTEGER,
                hcxOc3TestStatusLed               INTEGER,
                hcxOc3FaultStatusLed              INTEGER,
                hcxOc3SerialNumber                DisplayString,
                hcxOc3SyncClkConfigure            INTEGER }

        hcxOc3UnitShelfId OBJECT-TYPE
                SYNTAX INTEGER (1)
                MAX-ACCESS read-only
                STATUS current
                DESCRIPTION "
                        contains the associated shelf id."
                ::= { com21HcxOc3UnitEntry 1 }

        hcxOc3UnitSlotId OBJECT-TYPE
                SYNTAX Integer32
                MAX-ACCESS read-only
                STATUS current
                DESCRIPTION "
                        contains associated slot id."
                ::= { com21HcxOc3UnitEntry 2 }

        hcxOc3HardwareVersion OBJECT-TYPE
                SYNTAX DisplayString (SIZE (16))
                MAX-ACCESS read-only
                STATUS current
                DESCRIPTION "
                        contains the hardware version of the Oc3
                        card. Will contain empty string if card has not
                        been inserted in the slot."
                ::= { com21HcxOc3UnitEntry 3 }

        hcxOc3BootVersion OBJECT-TYPE
                SYNTAX DisplayString (SIZE (16))
                MAX-ACCESS read-only
                STATUS current
                DESCRIPTION "
                        contains the version of the Oc3 card boot ROM.
                        Will contain empty string if card has not been
                        inserted in the slot."
                ::= { com21HcxOc3UnitEntry 4 }

        hcxOc3UnitPrimServState OBJECT-TYPE
                SYNTAX PrimServiceState
                MAX-ACCESS read-only
                STATUS current
                DESCRIPTION "
                        contains primary service state of the Oc3
                        Unit."
                ::= { com21HcxOc3UnitEntry 5 }

 
        hcxOc3UnitPrimStateChange NOTIFICATION-TYPE
                OBJECTS { hcxAlmSeverity, hcxEventLogTime,
                            hcxOc3UnitShelfId, hcxOc3UnitSlotId,
                            hcxOc3UnitPrimServState }
                STATUS current
                DESCRIPTION "
                        This trap is generated whenever a change in the
                        the hcxOc3UnitPrimServState occurs. This an event
                        with no clear condition. Only severity is WARNING."
                ::= { com21Traps 150 }
 
        hcxOc3UnitSecServState OBJECT-TYPE
                SYNTAX DisplayString (SIZE (16))
                MAX-ACCESS read-only
                STATUS current
                DESCRIPTION "
                        contains a string defining the secondary service states
                        of the Oc3 Unit. The substrings supported by
                        the Oc3 Unit shall be: UNEQ - unequipped."
                ::= { com21HcxOc3UnitEntry 6 }
 
        hcxOc3UnitSecStateChange NOTIFICATION-TYPE
                OBJECTS { hcxAlmSeverity, hcxEventLogTime,
                            hcxOc3UnitShelfId, hcxOc3UnitSlotId,
                            hcxOc3UnitSecServState }
                STATUS current
                DESCRIPTION "
                        This trap is generated whenever a change in the
                        the hcxOc3UnitSecServState occurs. This an event
                        with no clear condition. Only severity is WARNING."
                ::= { com21Traps 151 }

 
        hcxOc3RestartAction OBJECT-TYPE
                SYNTAX INTEGER {
                                nil(1),
                                restart(2) }
                MAX-ACCESS read-write
                STATUS current
                DESCRIPTION "
                        The Oc3 Unit Restart Action is an active-value.
                        The setting of this attribute to restart(2) causes
                        the Oc3 card to reset and download a new image."
                ::= { com21HcxOc3UnitEntry 7 }

        hcxOc3TestStatusLed OBJECT-TYPE
                SYNTAX INTEGER { on (1), off (2) }
                MAX-ACCESS read-only
                STATUS current
                DESCRIPTION "
                        The Oc3 Test Status LED is a read-only
                        attribute which describes the condition of the
                        Oc3 Test Status light emitting diode
                        located on the Oc3 board. A value of on(1)
                        indicates that a service effecting test is in
                        progress and that the LED is illuminated. Will
                        be off if no card present."
                ::= { com21HcxOc3UnitEntry 8 }


        hcxOc3TestStatusLedChange NOTIFICATION-TYPE
                OBJECTS { hcxAlmSeverity, hcxEventLogTime,
                            hcxOc3UnitShelfId, hcxOc3UnitSlotId,
                            hcxOc3TestStatusLed }
                STATUS current
                DESCRIPTION "
                        generated whenever there is a change in test LED
                        status. This an event with no clear condition.
                        Only severity is WARNING."
                ::= { com21Traps 152 }


        hcxOc3FaultStatusLed OBJECT-TYPE
                SYNTAX INTEGER { on (1), off (2) }
                MAX-ACCESS read-only
                STATUS current
                DESCRIPTION "
                        The Oc3 Fault Status LED is a read-only
                        attribute which describes the condition of the
                        Oc3 Fault Status light emitting diode
                        located on the Oc3 board. A value of on(1)
                        indicates that an fault condition has been detected
                        (for which a trap will have been issued) and the
                        LED is illuminated. Will be off if no card present."
                ::= { com21HcxOc3UnitEntry 9}
 
        hcxOc3FaultStatusLedChange NOTIFICATION-TYPE
                OBJECTS { hcxAlmSeverity, hcxEventLogTime,
                            hcxOc3UnitShelfId, hcxOc3UnitSlotId,
                            hcxOc3FaultStatusLed }
                STATUS current
                DESCRIPTION "
                        generated whenever there is a change in the Fault
                        LED status. This an event with no clear condition.
                        Only severity is WARNING."
                ::= { com21Traps 153 }

        hcxOc3SerialNumber OBJECT-TYPE
                SYNTAX DisplayString (SIZE (16))
                MAX-ACCESS read-only
                STATUS current
                DESCRIPTION "
                        contains the serial number of the Oc3 card.
                        Will contain empty string if card has not been
                        inserted in the slot."
                ::= { com21HcxOc3UnitEntry 10 }

        hcxOc3SyncClkConfigure OBJECT-TYPE
                SYNTAX INTEGER { disable (1), priSrc (2), secSrc (3) }
                MAX-ACCESS read-write
                STATUS current
                DESCRIPTION "
                        This attribute allows to configure the
                        Oc3 card as the primary or secondary source
                        for network clock. This attribute is valid
                        only if networkClk is selected in hcxSyncClkConfigure
                        attribute. Only 1 Oc3 Card can be configured
                        as the priSrc and 1 Oc3 Card can be configured
                        as secSrc in the HCX system
                        Default: disable"
                ::= { com21HcxOc3UnitEntry 11 }

 
        -- -- -- -- -- -- -- -- -- -- -- -- -- -- -- -- -- -- -- -- -- -- -- --
        -- -- -- -- -- -- -- -- -- -- -- -- -- -- -- -- -- -- -- -- -- -- -- --
        --
        -- com21HcxOc3PortGroup
        --
        -- defines the attributes related to the management of a single
        -- Oc3 port.
        --
        -- -- -- -- -- -- -- -- -- -- -- -- -- -- -- -- -- -- -- -- -- -- -- --
        -- -- -- -- -- -- -- -- -- -- -- -- -- -- -- -- -- -- -- -- -- -- -- --
 
        com21HcxOc3PortTable OBJECT-TYPE
                SYNTAX  SEQUENCE OF HcxOc3PortEntry
                MAX-ACCESS  not-accessible
                STATUS  current
                DESCRIPTION "."
                ::= { com21HcxOc3PortGroup 1 }
 
        com21HcxOc3PortEntry OBJECT-TYPE
                SYNTAX  HcxOc3PortEntry
                MAX-ACCESS  not-accessible
                STATUS  current
                DESCRIPTION "."
                INDEX { hcxOc3PortShelfId, hcxOc3PortSlotId, hcxOc3PortId }
                ::= { com21HcxOc3PortTable 1 }


        HcxOc3PortEntry ::= SEQUENCE {
                hcxOc3PortShelfId             INTEGER,
                hcxOc3PortSlotId              Integer32,
                hcxOc3PortId                  INTEGER,
                hcxOc3PortPrimServState       PrimServiceState,
                hcxOc3PortSecServState        DisplayString,
                hcxOc3MaxBandwidth            INTEGER,
                hcxOc3AggrDnStrmCbrRate       Integer32,
                hcxOc3AggrDnStrmPcrRate       Integer32,
                hcxOc3AggrUpStrmCbrRate       Integer32,
                hcxOc3AggrUpStrmMinRate       Integer32,
                hcxOc3AggrUpStrmMaxRate       Integer32,
                hcxOc3AgeTime                 Integer32,
                hcxOc3PortConfigState         INTEGER,
                hcxOc3PortRestartAction       INTEGER,
                hcxOc3PortDiagTestAction      INTEGER,
                hcxOc3PortDiagTestResult      INTEGER,
                hcxOc3PortLOSLed       	      INTEGER,
                hcxOc3AggrActDnStrmCbrRate    Integer32,
                hcxOc3AggrActDnStrmPcrRate    Integer32,
                hcxOc3AggrActUpStrmCbrRate    Integer32,
                hcxOc3AggrActUpStrmMinRate    Integer32,
                hcxOc3AggrActUpStrmMaxRate    Integer32,
                hcxOc3PortIpAddr              IpAddress,
                hcxOc3PortIpMask              IpAddress,
                hcxOc3PortMacAddr             MacAddress,
		hcxOc3Port1483EncapEnbl	      INTEGER,
		hcxOc3PortSectionLOS	      INTEGER,	
		hcxOc3PortSectionLOF	      INTEGER,	
		hcxOc3PortLineAIS	      INTEGER,	
		hcxOc3PortLineRDI	      INTEGER,	
		hcxOc3PortPathRDI	      INTEGER,	
		hcxOc3PortAggrVoiceRate       Integer32,
		hcxOc3PortAggrActVoiceRate    Integer32,
		hcxOc3PortLOFLed              INTEGER }


       hcxOc3PortShelfId OBJECT-TYPE
                SYNTAX INTEGER (1)
                MAX-ACCESS read-only
                STATUS current
                DESCRIPTION "
                        contains shelf in which this Oc3 port is
                        located."
                ::= { com21HcxOc3PortEntry 1 }
 
        hcxOc3PortSlotId OBJECT-TYPE
                SYNTAX Integer32
                MAX-ACCESS read-only
                STATUS current
                DESCRIPTION "
                        contains slot in which this Oc3 port is
                        located."
                ::= { com21HcxOc3PortEntry 2 }
 
        hcxOc3PortId OBJECT-TYPE
                SYNTAX INTEGER (1)
                MAX-ACCESS read-only
                STATUS current
                DESCRIPTION "
                        contains port Id Oc3 port."
                ::= { com21HcxOc3PortEntry 3 }
 
        hcxOc3PortPrimServState OBJECT-TYPE
                SYNTAX PrimServiceState
                MAX-ACCESS read-only
                STATUS current
                DESCRIPTION "
                        contains primary service state of the Oc3
                        Unit. This state shall be effected by the
                        hcxOc3PortState attribute."
                ::= { com21HcxOc3PortEntry 4 }
 
        hcxOc3PortPrimStateChange NOTIFICATION-TYPE
                OBJECTS { hcxAlmSeverity, hcxEventLogTime,
                            hcxOc3PortShelfId, hcxOc3PortSlotId,
                            hcxOc3PortId, hcxOc3PortPrimServState }
                STATUS current
                DESCRIPTION "
                        This trap is generated whenever a change in the
                        the hcxOc3PortPrimServState occurs. This an event
                        with no clear condition. Only severity is WARNING."
                ::= { com21Traps 154 }
 
        hcxOc3PortSecServState OBJECT-TYPE
                SYNTAX DisplayString (SIZE (16))
                MAX-ACCESS read-only
                STATUS current
                DESCRIPTION "
                        contains a string defining the secondary service states
                        of the Oc3 Unit. The substrings supported by
                        the Oc3 Unit shall be: MT - offline, set by
                        hcxOc3, FAULT - hardware failure, TEST
                        - test, UNEQ - unequipped."
                ::= { com21HcxOc3PortEntry 5 }
 
        hcxOc3PortSecStateChange NOTIFICATION-TYPE
                OBJECTS { hcxAlmSeverity, hcxEventLogTime,
                            hcxOc3PortShelfId, hcxOc3PortSlotId,
                            hcxOc3PortId, hcxOc3PortSecServState }
                STATUS current

                DESCRIPTION "
                        This trap is generated whenever a change in the
                        the hcxOc3PortSecServState occurs. This an event
                        with no clear condition. Only severity is WARNING."
                ::= { com21Traps 155 }
 
        hcxOc3MaxBandwidth OBJECT-TYPE
                SYNTAX INTEGER (0..22222)
                MAX-ACCESS read-write
                STATUS current
                DESCRIPTION "
                        This attribute defines the maximum output payload
                        bandwidth associated with the Oc3 port. Defined
                        in thousands of bps. From 0 to 22222. This value shall
                        be checked by the CC which shall ensure that
                        the aggregate of the hcxOc3MaxBandwidth and
                        hcxEtherMaxBandwidth attributes
                        for each of the Oc3 and Ethernet ports does not exceed
                        the system maximum.
			If Voice Channels are configured on this Port,
			and if Voice channels are active, Ondemand
			Data bandwidth will get squeezed if Voice Channels
			are active.
                        Default: 7000 " 
                ::= { com21HcxOc3PortEntry 6 }

        hcxOc3AggrDnStrmCbrRate OBJECT-TYPE
                SYNTAX Integer32
                MAX-ACCESS read-only
                STATUS current
                DESCRIPTION "
                        This attribute specifies the aggregate of all ComPort
                        downstream CBR rates configured on the Oc3 port
                        This includes both acquired and unacquired
                        ComPorts. 
		        Defined in Kbps."
                ::= { com21HcxOc3PortEntry 7 }
 
        hcxOc3AggrDnStrmPcrRate OBJECT-TYPE
                SYNTAX Integer32
                MAX-ACCESS read-only
                STATUS current
                DESCRIPTION "
                        This attribute specifies the aggregate of all ComPort
                        downstream PCR rates configured on the Oc3 port
                        This includes both acquired and unacquired
                        ComPorts. Defined in Kbps."
                ::= { com21HcxOc3PortEntry 8 }
 
        hcxOc3AggrUpStrmCbrRate OBJECT-TYPE
                SYNTAX Integer32
                MAX-ACCESS read-only
                STATUS current
                DESCRIPTION "
                        This attribute specifies the aggregate of all ComPort
                        upstream CBR rates configured on the Oc3 port
                        This includes both acquired and unacquired
                        ComPorts. 
			Defined in Kbps."
                ::= { com21HcxOc3PortEntry 9 }
 
        hcxOc3AggrUpStrmMinRate OBJECT-TYPE
                SYNTAX Integer32
                MAX-ACCESS read-only
                STATUS current
                DESCRIPTION "
                        This attribute specifies the aggregate of all ComPort
                        upstream minimum PCR rates on the Oc3 port
                        This includes both acquired and unacquired ComPorts.
                        Defined in Kbps."
                ::= { com21HcxOc3PortEntry 10 }
 
        hcxOc3AggrUpStrmMaxRate OBJECT-TYPE
                SYNTAX Integer32
                MAX-ACCESS read-only
                STATUS current
                DESCRIPTION "
                        This attribute specifies the aggregate of all ComPort
                        upstream maximum cell rates on the Oc3 port
                        This includes both acquired and unacquired
                        ComPorts. Defined in Kbps."
                ::= { com21HcxOc3PortEntry 11 }
 
        hcxOc3AgeTime OBJECT-TYPE
                SYNTAX Integer32
                MAX-ACCESS read-write
                STATUS current
                DESCRIPTION "
                        This attribute defines, in seconds, the aging time
                        for non-accessed entries in the Bridge mapping table.
                        The default shall be 300secs. If this set to 0, then
                        aging is disabled."
                ::= { com21HcxOc3PortEntry 12 }
 
        hcxOc3PortConfigState OBJECT-TYPE
                SYNTAX INTEGER {
                        offline(2000),
                        online(2001),
                        test(2002) }
                MAX-ACCESS read-write
                STATUS current
                DESCRIPTION "
                        The Oc3 Port State is an active-value. The
                        Oc3 port will default to offline, in which
                        case no traffic shall be passed. Default offline."
                ::= { com21HcxOc3PortEntry 13 }

       hcxOc3PortRestartAction OBJECT-TYPE
                SYNTAX INTEGER {
                                nil(1),
                                restart(2) }
                MAX-ACCESS read-write
                STATUS current
                DESCRIPTION "
                        The Oc3 Port Restart Action is an active-value.
                        The setting of this attribute to restart(2) causes
                        the Oc3 port to reset and download a new image."
                ::= { com21HcxOc3PortEntry 14 }
 
        hcxOc3PortDiagTestAction OBJECT-TYPE
                SYNTAX INTEGER { nil(1), execute(2) }
                MAX-ACCESS read-write
                STATUS current
                DESCRIPTION "
                        This attribute is used to invoke the internal
                        Oc3 card diagnostic test. In order to activate
                        this test, the card must be placed in the test state."
                ::= { com21HcxOc3PortEntry 15 }
 
        hcxOc3PortDiagTestComplete NOTIFICATION-TYPE
                OBJECTS { hcxAlmSeverity, hcxEventLogTime,
                            hcxOc3PortShelfId, hcxOc3PortSlotId,
                            hcxOc3PortId, hcxOc3PortDiagTestResult }
                STATUS current
                DESCRIPTION "
                        This notification is generated whenever the Oc3
                        port internal diagnostic tests are completed. Event
                        only, no clear. Only severity allowed is WARNING."
                ::= { com21Traps 156 }

 
        hcxOc3PortDiagTestResult OBJECT-TYPE
                SYNTAX INTEGER {
                                inprogress(1),
                                success(2),
                                failure(3),
                                invalidState(4) }
                MAX-ACCESS read-only
                STATUS current
                DESCRIPTION "
                        This attribute contains the result of the last
                        Oc3 port diagnostic test."
                ::= { com21HcxOc3PortEntry 16 }
 
        hcxOc3OperationFailure NOTIFICATION-TYPE
                OBJECTS { hcxAlmSeverity, hcxEventLogTime,
                            hcxOc3PortShelfId, hcxOc3PortSlotId,
                            hcxOc3PortId }
                STATUS current
                DESCRIPTION "
                        This notification is generated by the CC whenever
                        an Oc3 port fails to respond correctly to a
                        request. This failure could indicate either a
                        resource problem or software failure. Note that
                        if an Oc3 card failures to respond completely
                        to a CC request, then a hcxInsertChange trap shall
                        be generated. This is an event without a
                        corresponding clear. Only severity allowed is
                        WARNING."
                ::= { com21Traps 157 }

 
        hcxOc3PortLOSLed OBJECT-TYPE
                SYNTAX INTEGER { on (1), off (2) }
                MAX-ACCESS read-only
                STATUS current
                DESCRIPTION "
                        The OC3 Loss Of Signal LED indicates whether
                        a Loss of Signal  is present on the
                        WAN side of the OC3 port."
                ::= { com21HcxOc3PortEntry 17 }
 
        hcxOc3PortLOSLedChange NOTIFICATION-TYPE
                OBJECTS { hcxAlmSeverity, hcxEventLogTime,
                            hcxOc3PortShelfId, hcxOc3PortSlotId, hcxOc3PortId,
                            hcxOc3PortLOSLed }
                STATUS current
                DESCRIPTION "
                        generated whenever there is a change in the LOS
                        LED status. This an event with no clear condition.
                        Only severity is WARNING."
                ::= { com21Traps 158 }

 
        hcxOc3AggrActDnStrmCbrRate OBJECT-TYPE
                SYNTAX Integer32
                MAX-ACCESS read-only
                STATUS current
                DESCRIPTION "
                        This attribute specifies the aggregate of all ComPort
                        downstream CBR rates active on the Oc3 port
                        (VLAN). This includes only acquired ComPorts. Defined
                        in Kbps."
                ::= { com21HcxOc3PortEntry 18 }
 
        hcxOc3AggrActDnStrmPcrRate OBJECT-TYPE
                SYNTAX Integer32
                MAX-ACCESS read-only
                STATUS current
                DESCRIPTION "
                        This attribute specifies the aggregate of all ComPort
                        downstream PCR rates active on the Oc3 port (VLAN).
                        This includes only acquired ComPorts. Defined in Kbps."
                ::= { com21HcxOc3PortEntry 19 }
 
        hcxOc3AggrActUpStrmCbrRate OBJECT-TYPE
                SYNTAX Integer32
                MAX-ACCESS read-only
                STATUS current
                DESCRIPTION "
                        This attribute specifies the aggregate of all ComPort
                        upstream CBR rates active on the Oc3 port (VLAN).
 
                        This includes only acquired ComPorts. Defined in bits
                        per second."
                ::= { com21HcxOc3PortEntry 20 }
 
        hcxOc3AggrActUpStrmMinRate OBJECT-TYPE
                SYNTAX Integer32
                MAX-ACCESS read-only
                STATUS current
                DESCRIPTION "
                        This attribute specifies the aggregate of all ComPort
                        upstream minimum PCR rates active on the Oc3 port
                        (VLAN). This includes only acquired ComPorts. Defined
                        in Kbps."
                ::= { com21HcxOc3PortEntry 21 }
 
        hcxOc3AggrActUpStrmMaxRate OBJECT-TYPE
                SYNTAX Integer32
                MAX-ACCESS read-only
                STATUS current
                DESCRIPTION "
                        This attribute specifies the aggregate of all ComPort
                        upstream maximum cell rates active on the Oc3 port
                        (VLAN). This includes only acquired ComPorts. Defined
                        in Kbps."
                ::= { com21HcxOc3PortEntry 22 }
 
        hcxOc3PortIpAddr OBJECT-TYPE
                SYNTAX IpAddress
                MAX-ACCESS read-write
                STATUS current
                DESCRIPTION "
                        IP Address associated with this ethernet port. This
                        is a future item for telephone return support."
                ::= { com21HcxOc3PortEntry 23 }
 
        hcxOc3PortIpMask OBJECT-TYPE
                SYNTAX IpAddress
                MAX-ACCESS read-write
                STATUS current
                DESCRIPTION "
                        IP mask associated with port. Default is ff.ff.ff.ff.
                        This is a future item for telephone return support."
                ::= { com21HcxOc3PortEntry 24 }
 
        hcxOc3PortMacAddr OBJECT-TYPE
                SYNTAX MacAddress
                MAX-ACCESS read-only
                STATUS current
                DESCRIPTION "
                        MAC address associated with port."
                ::= { com21HcxOc3PortEntry 25}

        hcxOc3Port1483EncapEnbl OBJECT-TYPE
                SYNTAX INTEGER { disable (1), enable (2) }
                MAX-ACCESS read-write
                STATUS current
                DESCRIPTION "
			This attribute is used to Enable/Disable
			1483 Encapsulation on the Oc3Port.
			If enabled, then all Ethernet packets
			received by the Oc3Port should be
			1483 Encapsulated and all Ethernet
			packets transmitted by the Oc3Port will
			be 1483 Encapsulated.	
			Default: enable."
                ::= { com21HcxOc3PortEntry 26}

        hcxOc3PortSectionLOS OBJECT-TYPE
                SYNTAX INTEGER { on (1), off (2) }
                MAX-ACCESS read-only
                STATUS current
                DESCRIPTION "
			This attribute indicates whether Section Loss of
			Signal is present at the OC3 Port. 
                        Default: off."
                ::= { com21HcxOc3PortEntry 27}

        hcxOc3PortSectionLOSDetected NOTIFICATION-TYPE
                OBJECTS { hcxAlmSeverity, hcxEventLogTime,
                            hcxOc3PortShelfId, hcxOc3PortSlotId, hcxOc3PortId }
                STATUS current
                DESCRIPTION "
                        generated whenever Loss of Signal is 
			detected at the OC3 Port.
			Alarm Severity: MAJOR"
                ::= { com21Traps 159 }

        hcxOc3PortSectionLOSClear NOTIFICATION-TYPE
                OBJECTS { hcxAlmSeverity, hcxEventLogTime,
                            hcxOc3PortShelfId, hcxOc3PortSlotId, hcxOc3PortId }
                STATUS current
                DESCRIPTION "
                        generated whenever Loss of Signal is
                        Cleared at the OC3 Port.
			Alarm Severity: CLEAR"
                ::= { com21Traps 160 }


        hcxOc3PortSectionLOF OBJECT-TYPE
                SYNTAX INTEGER { on (1), off (2) }
                MAX-ACCESS read-only
                STATUS current
                DESCRIPTION "
                        This attribute indicates whether Section Loss of 
                        Frame is present at the OC3 Port. 
                        Default: off."
                ::= { com21HcxOc3PortEntry 28}

        hcxOc3PortSectionLOFDetected NOTIFICATION-TYPE
                OBJECTS { hcxAlmSeverity, hcxEventLogTime,
                            hcxOc3PortShelfId, hcxOc3PortSlotId, hcxOc3PortId }
                STATUS current
                DESCRIPTION "
                        generated whenever Loss of Frame is detected
			 at the OC3 Port.
			Alarm Severity: MAJOR"
                ::= { com21Traps 161 }
 
        hcxOc3PortSectionLOFClear NOTIFICATION-TYPE
                OBJECTS { hcxAlmSeverity, hcxEventLogTime,
                            hcxOc3PortShelfId, hcxOc3PortSlotId, hcxOc3PortId }
                STATUS current
                DESCRIPTION "
                        generated whenever Loss of Frame is cleared
                         at the OC3 Port.
			Alarm Severity: CLEAR"
                ::= { com21Traps 162 }

        hcxOc3PortLineAIS OBJECT-TYPE
                SYNTAX INTEGER { on (1), off (2) }
                MAX-ACCESS read-only
                STATUS current
                DESCRIPTION "
                        This attribute indicates whether Line Alarm
			Indication Signal is detected by the OC3 Port
                        Default: off."
                ::= { com21HcxOc3PortEntry 29}

        hcxOc3PortLineAISDetected NOTIFICATION-TYPE
                OBJECTS { hcxAlmSeverity, hcxEventLogTime,
                            hcxOc3PortShelfId, hcxOc3PortSlotId, hcxOc3PortId }
                STATUS current
                DESCRIPTION "
                        generated whenever AIS is detected at the
                        OC3 Port. 
			Alarm Severity: MAJOR"
                ::= { com21Traps 163 }
 
        hcxOc3PortLineAISClear NOTIFICATION-TYPE
                OBJECTS { hcxAlmSeverity, hcxEventLogTime,
                            hcxOc3PortShelfId, hcxOc3PortSlotId, hcxOc3PortId }
                STATUS current
                DESCRIPTION "
                        generated whenever AIS is cleared at the
                        OC3 Port.
			Alarm Severity: CLEAR"
                ::= { com21Traps 164 }


        hcxOc3PortLineRDI OBJECT-TYPE
                SYNTAX INTEGER { on (1), off (2) }
                MAX-ACCESS read-only
                STATUS current
                DESCRIPTION "
                        This attribute indicates whether Line Remote
			Defect Indication is detected by the OC3 Port
                        Default: off."
                ::= { com21HcxOc3PortEntry 30}

        hcxOc3PortLineRDIDetected NOTIFICATION-TYPE
                OBJECTS { hcxAlmSeverity, hcxEventLogTime,
                            hcxOc3PortShelfId, hcxOc3PortSlotId, hcxOc3PortId }
                STATUS current
                DESCRIPTION "
                        generated whenever Line Remote Defect Indication is 
			detected at the OC3 Port.
			Alarm Severity: MAJOR"
                ::= { com21Traps 165 }

        hcxOc3PortLineRDIClear NOTIFICATION-TYPE
                OBJECTS { hcxAlmSeverity, hcxEventLogTime,
                            hcxOc3PortShelfId, hcxOc3PortSlotId, hcxOc3PortId }
                STATUS current
                DESCRIPTION "
                        generated whenever Line Remote Defect Indication is
                        cleared at the OC3 Port.
			Alarm Severity: CLEAR"
                ::= { com21Traps 166 }

 
        hcxOc3PortPathRDI OBJECT-TYPE
                SYNTAX INTEGER { on (1), off (2) }
                MAX-ACCESS read-only
                STATUS current
                DESCRIPTION "
                        This attribute indicates whether Path Remote
                        Defect Indication is detected by the OC3 Port
                        Default: off."
                ::= { com21HcxOc3PortEntry 31}

        hcxOc3PortPathRDIDetected NOTIFICATION-TYPE
                OBJECTS { hcxAlmSeverity, hcxEventLogTime,
                            hcxOc3PortShelfId, hcxOc3PortSlotId, hcxOc3PortId }
                STATUS current
                DESCRIPTION "
                        generated whenever Path Remote Defect Indication is 
                        detected at the OC3 Port.
			Alarm Severity: MAJOR"
                ::= { com21Traps 167 }

        hcxOc3PortPathRDIClear NOTIFICATION-TYPE
                OBJECTS { hcxAlmSeverity, hcxEventLogTime,
                            hcxOc3PortShelfId, hcxOc3PortSlotId, hcxOc3PortId }
                STATUS current
                DESCRIPTION "
                        generated whenever Path Remote Defect Indication is
                        cleared at the OC3 Port.
			Alarm Severity: CLEAR"
                ::= { com21Traps 168 }

 
        hcxOc3PortAggrVoiceRate OBJECT-TYPE
                SYNTAX Integer32
                MAX-ACCESS read-only
                STATUS current
                DESCRIPTION "
			This attribute specifies the aggregate Rate of
			all Voice Channels configured on this Port.
			A voice channel is considered configured on
			this Port if:
			 a ComPort is configured with Voice Channel and
			 the ComPort is configured on a Vlan which
			 is on this Port. 
			The rate specified here includes both
			acquired and unacquired ComPorts and
			is the same in both Upstream and Downstream
			Direction.
			Defined in Kbps."
                ::= { com21HcxOc3PortEntry 32 }

        hcxOc3PortAggrActVoiceRate OBJECT-TYPE
                SYNTAX Integer32
                MAX-ACCESS read-only
                STATUS current
                DESCRIPTION "
                        This attribute specifies the aggregate Rate of
                        all Voice Channels Active on this Port.
                        A voice channel is considered Active on
                        this Port if:
                         a ComPort is configured with Voice Channel and
                         the ComPort is configured on a Vlan which 
                         is on this Port and 
			 the Comport is acquired and
			 the Comport has a Voice Channel Active.

                        The rate specified here is the same in 
			both Upstream and Downstream Direction.
                        Defined in Kbps."
                ::= { com21HcxOc3PortEntry 33 }

        hcxOc3PortLOFLed OBJECT-TYPE
                SYNTAX INTEGER { on (1), off (2) }
                MAX-ACCESS read-only
                STATUS current
                DESCRIPTION "
                        The OC3 Loss Of Frame LED indicates whether
                        a Loss of Frame  is present on the
                        WAN side of the OC3 port."
                ::= { com21HcxOc3PortEntry 34 }

        hcxOc3PortLOFLedChange NOTIFICATION-TYPE
                OBJECTS { hcxAlmSeverity, hcxEventLogTime,
                            hcxOc3PortShelfId, hcxOc3PortSlotId, hcxOc3PortId,
                            hcxOc3PortLOFLed }
                STATUS current
                DESCRIPTION "
                        generated whenever there is a change in the LOF
                        LED status. This an event with no clear condition.
                        Only severity is WARNING."
                ::= { com21Traps 169 }



        -- -- -- -- -- -- -- -- -- -- -- -- -- -- -- -- -- -- -- -- -- -- -- --
        -- -- -- -- -- -- -- -- -- -- -- -- -- -- -- -- -- -- -- -- -- -- -- --
        --
        -- com21HcxOc3VccGroup
        --
	-- This table lists all configured VPI/VCI's in the system.
 	--	
        -- -- -- -- -- -- -- -- -- -- -- -- -- -- -- -- -- -- -- -- -- -- -- --
        -- -- -- -- -- -- -- -- -- -- -- -- -- -- -- -- -- -- -- -- -- -- -- --
 
 
        com21HcxOc3VccTable OBJECT-TYPE
                SYNTAX SEQUENCE OF HcxOc3VccEntry
                MAX-ACCESS not-accessible
                STATUS current
                DESCRIPTION "."
                ::= { com21HcxOc3VccGroup 1 }
 
 
        com21HcxOc3VccEntry OBJECT-TYPE
                SYNTAX HcxOc3VccEntry
                MAX-ACCESS not-accessible
                STATUS current
                DESCRIPTION "."
                INDEX { hcxOc3VccShelfId, hcxOc3VccSlotId, hcxOc3VccPortId, 
		        hcxOc3VccVpi, hcxOc3VccVci }
                ::= { com21HcxOc3VccTable 1 }
 
 
        HcxOc3VccEntry ::= SEQUENCE {
                hcxOc3VccShelfId                Integer32,
                hcxOc3VccSlotId                 Integer32,
                hcxOc3VccPortId                 Integer32,
                hcxOc3VccVpi                    Integer32,
                hcxOc3VccVci                    Integer32,
                hcxOc3VccType                   INTEGER }
 
        hcxOc3VccShelfId OBJECT-TYPE
                SYNTAX Integer32
                MAX-ACCESS read-only
                STATUS current
                DESCRIPTION "
                        Specifies the Shelf where this Entry exists. "
                ::= { com21HcxOc3VccEntry 1 }
 
        hcxOc3VccSlotId OBJECT-TYPE
                SYNTAX Integer32
                MAX-ACCESS read-only
                STATUS current
                DESCRIPTION "
                        Specifies the Slot where this Entry exists. "
                ::= { com21HcxOc3VccEntry 2 }
 
        hcxOc3VccPortId OBJECT-TYPE
                SYNTAX Integer32
                MAX-ACCESS read-only
                STATUS current
                DESCRIPTION "
                        Specifies the Port where this Entry exists. " 
                ::= { com21HcxOc3VccEntry 3 }

        hcxOc3VccVpi OBJECT-TYPE
                SYNTAX Integer32
                MAX-ACCESS read-only
                STATUS current
                DESCRIPTION "
                        Specifies the Vpi where this Entry exists. " 
                ::= { com21HcxOc3VccEntry 4 }

        hcxOc3VccVci OBJECT-TYPE
                SYNTAX Integer32
                MAX-ACCESS read-only
                STATUS current
                DESCRIPTION "
                        Specifies the Vci where this Entry exists. " 
                ::= { com21HcxOc3VccEntry 5 }

        hcxOc3VccType OBJECT-TYPE
                SYNTAX INTEGER { data (1), voice (2) }
                MAX-ACCESS read-only
                STATUS current
                DESCRIPTION "
                        Specifies whether this VCC is used to transport
			data or voice." 
                ::= { com21HcxOc3VccEntry 6 }
 
        -- -- -- -- -- -- -- -- -- -- -- -- -- -- -- -- -- -- -- -- -- -- -- --
        -- -- -- -- -- -- -- -- -- -- -- -- -- -- -- -- -- -- -- -- -- -- -- --
        --
        -- com21HcxOc3StatsGroup
        --
        -- This table lists all OC3 Port Related Stats.
        --
        -- -- -- -- -- -- -- -- -- -- -- -- -- -- -- -- -- -- -- -- -- -- -- --
        -- -- -- -- -- -- -- -- -- -- -- -- -- -- -- -- -- -- -- -- -- -- -- --
 
 
        com21HcxOc3StatsTable OBJECT-TYPE
                SYNTAX SEQUENCE OF HcxOc3StatsEntry
                MAX-ACCESS not-accessible
                STATUS current
                DESCRIPTION "."
                ::= { com21HcxOc3StatsGroup 1 }
 
 
        com21HcxOc3StatsEntry OBJECT-TYPE
                SYNTAX HcxOc3StatsEntry
                MAX-ACCESS not-accessible
                STATUS current
                DESCRIPTION "."
                INDEX { hcxOc3StatsShelfId, hcxOc3StatsSlotId, 
			hcxOc3StatsPortId }
                ::= { com21HcxOc3StatsTable 1 }

        HcxOc3StatsEntry ::= SEQUENCE {
                hcxOc3StatsShelfId                Integer32,
                hcxOc3StatsSlotId                 Integer32,
                hcxOc3StatsPortId                 Integer32,
                hcxOc3StatsCurrSectionBIPErr          Integer32,
                hcxOc3StatsCurrLineBIPErr             Integer32,
                hcxOc3StatsCurrPathBIPErr             Integer32,
                hcxOc3StatsCurrLineFEndBlockErr       Integer32,
                hcxOc3StatsCurrPathFEndBlockErr       Integer32,
                hcxOc3StatsPrevSectionBIPErr          Integer32,
                hcxOc3StatsPrevLineBIPErr             Integer32,
                hcxOc3StatsPrevPathBIPErr             Integer32,
                hcxOc3StatsPrevLineFEndBlockErr       Integer32,
                hcxOc3StatsPrevPathFEndBlockErr       Integer32,
		hcxOc3StatsClear		      INTEGER}


        hcxOc3StatsShelfId OBJECT-TYPE
                SYNTAX Integer32
                MAX-ACCESS read-only
                STATUS current
                DESCRIPTION "
                        Specifies the Shelf where this Entry exists. "
                ::= { com21HcxOc3StatsEntry 1 }

        hcxOc3StatsSlotId OBJECT-TYPE
                SYNTAX Integer32
                MAX-ACCESS read-only
                STATUS current
                DESCRIPTION "
                        Specifies the Slot where this Entry exists. "
                ::= { com21HcxOc3StatsEntry 2 }

        hcxOc3StatsPortId OBJECT-TYPE
                SYNTAX Integer32
                MAX-ACCESS read-only
                STATUS current
                DESCRIPTION "
                        Specifies the Port where this Entry exists. "
                ::= { com21HcxOc3StatsEntry 3 }

        hcxOc3StatsCurrSectionBIPErr OBJECT-TYPE
                SYNTAX Integer32
                MAX-ACCESS read-only
                STATUS current
                DESCRIPTION "
			This attributes displays the number of
			Section Byte Interleaved Parity Errors reported
			by the OC3 Port in the current 15-minute period. "
                ::= { com21HcxOc3StatsEntry 4 }

        hcxOc3StatsCurrLineBIPErr OBJECT-TYPE
                SYNTAX Integer32
                MAX-ACCESS read-only
                STATUS current
                DESCRIPTION "
                        This attributes displays the number of
                        Line Byte Interleaved Parity Errors reported
                        by the OC3 Port in the current 15-minute period. "
                ::= { com21HcxOc3StatsEntry 5 }

        hcxOc3StatsCurrPathBIPErr OBJECT-TYPE
                SYNTAX Integer32
                MAX-ACCESS read-only
                STATUS current
                DESCRIPTION "
                        This attributes displays the number of
                        Path Byte Interleaved Parity Errors reported
                        by the OC3 Port in the current 15-minute period."
                ::= { com21HcxOc3StatsEntry 6 }

        hcxOc3StatsCurrLineFEndBlockErr OBJECT-TYPE
                SYNTAX Integer32
                MAX-ACCESS read-only
                STATUS current
                DESCRIPTION "
                        This attributes displays the number of
                        Far End Line Block Errors reported
                        by the OC3 Port in the current 15-minute period." 
                ::= { com21HcxOc3StatsEntry 7 }

        hcxOc3StatsCurrPathFEndBlockErr OBJECT-TYPE
                SYNTAX Integer32
                MAX-ACCESS read-only
                STATUS current
                DESCRIPTION "
                        This attributes displays the number of
                        Far End Path Block Errors reported
                        by the OC3 Port in the current 15-minute period."
                ::= { com21HcxOc3StatsEntry 8 }

        hcxOc3StatsPrevSectionBIPErr OBJECT-TYPE
                SYNTAX Integer32
                MAX-ACCESS read-only
                STATUS current
                DESCRIPTION "
                        This attributes displays the number of
                        Section Byte Interleaved Parity Errors reported
                        by the OC3 Port in the current 15-minute period. "
                ::= { com21HcxOc3StatsEntry 9 }
 
        hcxOc3StatsPrevLineBIPErr OBJECT-TYPE
                SYNTAX Integer32
                MAX-ACCESS read-only
                STATUS current
                DESCRIPTION "
                        This attributes displays the number of
                        Line Byte Interleaved Parity Errors reported
                        by the OC3 Port in the current 15-minute period. "
                ::= { com21HcxOc3StatsEntry 10 }
 
        hcxOc3StatsPrevPathBIPErr OBJECT-TYPE
                SYNTAX Integer32
                MAX-ACCESS read-only
                STATUS current
                DESCRIPTION "
                        This attributes displays the number of
                        Path Byte Interleaved Parity Errors reported
                        by the OC3 Port in the current 15-minute period."
                ::= { com21HcxOc3StatsEntry 11 }
 
        hcxOc3StatsPrevLineFEndBlockErr OBJECT-TYPE
                SYNTAX Integer32
                MAX-ACCESS read-only
                STATUS current
                DESCRIPTION "
                        This attributes displays the number of
                        Far End Line Block Errors reported
                        by the OC3 Port in the current 15-minute period." 
                ::= { com21HcxOc3StatsEntry 12 }
 
        hcxOc3StatsPrevPathFEndBlockErr OBJECT-TYPE
                SYNTAX Integer32
                MAX-ACCESS read-only
                STATUS current
                DESCRIPTION "
                        This attributes displays the number of
                        Far End Path Block Errors reported
                        by the OC3 Port in the current 15-minute period."
                ::= { com21HcxOc3StatsEntry 13 }
 

        hcxOc3StatsClear OBJECT-TYPE
                SYNTAX INTEGER  { nil(1), clear(2) }
                MAX-ACCESS read-write
                STATUS current
                DESCRIPTION "
                        This attribute is used to clear the all OC3 Stats
                        statistics counters in this group. This operation
                        is only possible if the hcxStatsControl attribute
                        is set to wrapCurr."
                ::= { com21HcxOc3StatsEntry 14 }
 

END
