URQLEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE
			FROM SNMPv2-SMI
		DisplayString, RowStatus
			FROM SNMPv2-TC
		urqlExt
			FROM APENT-MIB;

--URQLEXT MIB

    apUrqlExtMib MODULE-IDENTITY
	   LAST-UPDATED "9906221000Z" -- Tue June 22 10:00:00 EST 1999
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	   (U)(R)L (Q)ualification (L)ists"
      ::= { urqlExt 1}


apUrqlTable OBJECT-TYPE
	SYNTAX          SEQUENCE OF APUrqlEntry
	MAX-ACCESS      not-accessible
	STATUS          current
	DESCRIPTION
		"A list of URL qualifier lists"
	::= { urqlExt 2 }

apUrqlEntry OBJECT-TYPE
	SYNTAX          APUrqlEntry
	MAX-ACCESS      not-accessible
	STATUS          current
	DESCRIPTION
		"A group of information uniquely identifying an URQL.  One entry 
         exists for each URQL"
	INDEX   { apUrqlName }
	::= { apUrqlTable 1 }

APUrqlEntry ::= SEQUENCE {
		apUrqlName                    DisplayString,
		apUrqlDescription             DisplayString,
		apUrqlCreateType              INTEGER,
		apUrqlStatus                  RowStatus,
		apUrqlEnable                  INTEGER,
		apUrqlDomain                  DisplayString
}

apUrqlName OBJECT-TYPE
	SYNTAX          DisplayString (SIZE(1..31))
	MAX-ACCESS      read-create
	STATUS          current
	DESCRIPTION     
			"The name of the URQL. This is a table index."
	::= {apUrqlEntry 1}

apUrqlDescription OBJECT-TYPE
	SYNTAX          DisplayString (SIZE(0..64))
	MAX-ACCESS      read-create
	STATUS          current
	DESCRIPTION     
			"An URQL description"
	::= {apUrqlEntry 2}

apUrqlCreateType OBJECT-TYPE
	SYNTAX          INTEGER {
                            static(1)                            ,
                            dynamic(2)                             
                            }
	MAX-ACCESS      read-only
	STATUS          current
	DESCRIPTION     
			"How the URQL entry was created"
	::= {apUrqlEntry 3}

apUrqlStatus OBJECT-TYPE
	SYNTAX          RowStatus
	MAX-ACCESS      read-create
	STATUS          current
	DESCRIPTION      
		"Status entry for this row"
	::= {apUrqlEntry 4}

apUrqlEnable  OBJECT-TYPE
	SYNTAX  INTEGER {
					disable(0),
					enable(1)
 					}
	MAX-ACCESS      read-create
	STATUS 			current
	DESCRIPTION     
		"The URQL is either enable or disabled"
	DEFVAL { disable }
	--DEFAULT ap-display-name	Status
	--DEFAULT apjam-popup-ref apCntInst, Properties
	--DEFAULT apjam-wizard-field	1, normal
	::= {apUrqlEntry  5}

apUrqlDomain OBJECT-TYPE
	SYNTAX          DisplayString (SIZE(0..63))
	MAX-ACCESS      read-create
	STATUS          current
	DESCRIPTION     
			"The domain name used for all table entries"
	::= {apUrqlEntry 6}


apUrqlExtTable OBJECT-TYPE
	SYNTAX          SEQUENCE OF APUrqlExtEntry
	MAX-ACCESS      not-accessible
	STATUS          current
	DESCRIPTION
		"A list of URLs associated with an URQL"
	::= { urqlExt 3 }

apUrqlExtEntry OBJECT-TYPE
	SYNTAX          APUrqlExtEntry
	MAX-ACCESS      not-accessible
	STATUS          current
	DESCRIPTION
		"Information uniquely identifying an URL within an URQL"
	INDEX   { apUrqlName, apUrqlExtUrlNumber }
	::= { apUrqlExtTable 1 }

APUrqlExtEntry ::= SEQUENCE {
		apUrqlExtUrlNumber               INTEGER,
		apUrqlExtUrlName                 DisplayString,
		apUrqlExtUrlDescription          DisplayString,
		apUrqlExtUrlCreateType           INTEGER,
		apUrqlExtUrlStatus               RowStatus
}

apUrqlExtUrlNumber OBJECT-TYPE
	SYNTAX          INTEGER ( 1..1000 )
	MAX-ACCESS      read-create
	STATUS          current
	DESCRIPTION     
			"The id number of the URL. This is a table index."
	::= {apUrqlExtEntry 1}

apUrqlExtUrlName OBJECT-TYPE
	SYNTAX          DisplayString (SIZE(0..251))
	MAX-ACCESS      read-create
	STATUS          current
	DESCRIPTION     
			"The URL"
	::= {apUrqlExtEntry 2}

apUrqlExtUrlDescription OBJECT-TYPE
	SYNTAX          DisplayString (SIZE(0..64))
	MAX-ACCESS      read-create
	STATUS          current
	DESCRIPTION     
			"A description of this URL"
	::= {apUrqlExtEntry 3}

apUrqlExtUrlCreateType OBJECT-TYPE
	SYNTAX          INTEGER {
                            static(1)                            ,
                            dynamic(2)                             
                            }
	MAX-ACCESS      read-only
	STATUS          current
	DESCRIPTION     
			"How the URL entry was created"
	::= {apUrqlExtEntry 4}

apUrqlExtUrlStatus OBJECT-TYPE
	SYNTAX          RowStatus
	MAX-ACCESS      read-create
	STATUS          current
	DESCRIPTION      
		"Status entry for this row"
	::= {apUrqlExtEntry 5}

END
