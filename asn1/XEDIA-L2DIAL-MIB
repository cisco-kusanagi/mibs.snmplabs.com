XEDIA-L2DIAL-MIB DEFINITIONS ::= BEGIN

IMPORTS 
    MODULE-IDENTITY, OBJECT-TYPE, IpAddress
        FROM SNMPv2-SMI
    TEXTUAL-CONVENTION, DisplayString, RowStatus        
        FROM SNMPv2-TC
    MODULE-COMPLIANCE, OBJECT-GROUP
        FROM SNMPv2-CONF
    xediaMibs
        FROM XEDIA-REG
    ;

xediaL2DialMIB MODULE-IDENTITY
    LAST-UPDATED "9902272155Z" -- February 27, 1999
    ORGANIZATION "Xedia Corp."
    CONTACT-INFO
        "support@xedia.com"
    DESCRIPTION
        "This module defines objects for management of Xedia's Layer
        2 Dial layer (l2Dial)."
    ::= { xediaMibs 30 }


-- ****************************************************************
-- Top-level organization of the MIB
-- ****************************************************************

l2DialObjects          OBJECT IDENTIFIER ::= { xediaL2DialMIB 1 }
l2DialConformance      OBJECT IDENTIFIER ::= { xediaL2DialMIB 2 }

-- ****************************************************************
-- Object Definitions
-- ****************************************************************

-- The L2Dial Address Status Table
--    show l2dial address-statuses
--    show l2dial address-status.xxxx

l2DialStatusTable   OBJECT-TYPE
    SYNTAX          SEQUENCE OF L2DialStatusEntry
    MAX-ACCESS      not-accessible
    STATUS          current
    DESCRIPTION
       "The L2Dial status table."
    ::= { l2DialObjects 1 }

l2DialStatusEntry   OBJECT-TYPE
    SYNTAX          L2DialStatusEntry
    MAX-ACCESS      not-accessible
    STATUS          current
    DESCRIPTION
       "An L2Dial status entry. An entry in this table
       corresponds to an ip addresses / sublayer mapping."
    INDEX { l2DialStatusIpAddress }
    ::= { l2DialStatusTable 1 }

L2DialStatusEntry ::=
    SEQUENCE {
        l2DialStatusIpAddress
            IpAddress,
        l2DialStatusSublayer
            INTEGER
    }

l2DialStatusIpAddress  OBJECT-TYPE
    SYNTAX          IpAddress
    MAX-ACCESS      not-accessible
    STATUS          current
    DESCRIPTION
       "An IP address."
    ::= { l2DialStatusEntry 1 }

l2DialStatusSublayer  OBJECT-TYPE
    SYNTAX          INTEGER
    MAX-ACCESS      read-only
    STATUS          current
    DESCRIPTION
       "A sublayer."
    ::= { l2DialStatusEntry 2 }


-- ****************************************************************
-- Conformance Statements
-- ****************************************************************

l2DialCompliances OBJECT IDENTIFIER ::= { l2DialConformance 1 }
l2DialGroups      OBJECT IDENTIFIER ::= { l2DialConformance 2 }

--
-- Compliance Statements
--

l2DialCompliance MODULE-COMPLIANCE
    STATUS      current
    DESCRIPTION
        "The compliance statement for all agents that support this
        MIB. A compliant agent implements all objects defined in this
        MIB."
    MODULE  -- this module
    MANDATORY-GROUPS {
        l2DialStatusGroup
    }
    ::= { l2DialCompliances 1 }

--
-- Object Groups
--

l2DialStatusGroup OBJECT-GROUP
    OBJECTS {
--        l2DialStatusIpAddress
        l2DialStatusSublayer
    }
    STATUS      current
    DESCRIPTION
        "A collection of objects providing addresses to sublayer mappings."
    ::= { l2DialGroups 1 }

END
