PANDATEL-GMH-MODEM-MIB DEFINITIONS ::= BEGIN

 -- This is the private mib group section for the GM-H modems.
 -- Because these modems must be installed in the PANDATEL modem rack
 -- the PANDATEL-MODEM-MIB also applies.

 -- Ver.1.05    Sep.13.1999

        IMPORTS
                enterprises
                        FROM RFC1155-SMI
                DisplayString
                        FROM RFC1213-MIB
                OBJECT-TYPE
                        FROM RFC-1212
                mdmSpecifics, device-id
                        FROM PANDATEL-MODEM-MIB;

-- ********************** THE MDM-GMH SUBTREE ******************************

-- the specific identifier is identical to the modem type integer
-- of the GM-H modem entries in the PANDATEL-MODEM-MIB mdmModemTable.

gmh-modem      OBJECT IDENTIFIER ::= { device-id 201 }     -- chassis-mib

gmh            OBJECT IDENTIFIER ::= { mdmSpecifics 201 }  -- this subtree

gmhModemTable OBJECT-TYPE
        SYNTAX  SEQUENCE OF GmhTableEntry
        ACCESS  not-accessible
        STATUS  mandatory
        DESCRIPTION
                "The table of all GM-H modems in this housing."
        ::= { gmh 1 }

gmhTableEntry OBJECT-TYPE
        SYNTAX  GmhTableEntry
        ACCESS  not-accessible
        STATUS  mandatory
        DESCRIPTION
                "The index of the table."
        INDEX   { mdmRack, mdmModem, mdmPosition }
        ::= { gmhModemTable 1 }

GmhTableEntry ::= SEQUENCE {
        mdmRack
                INTEGER,
        mdmModem
                INTEGER,
        mdmPosition
                INTEGER,
        mdmModemName
                DisplayString,
        mdmDataEquipmentEmulation
                INTEGER,
        mdmModemProperty
                INTEGER,
        mdmClockSystem
                INTEGER,
        mdmClockSource
                INTEGER,
        mdmDataRate
                INTEGER,
        mdmScrambler
                INTEGER,
        mdmRemoteAccessMode
                INTEGER,
        mdmForcedRemoteAccess
                INTEGER
        }

mdmRack OBJECT-TYPE
        SYNTAX  INTEGER
        ACCESS  read-only
        STATUS  mandatory
        DESCRIPTION
                "The index of the rack where the modem is installed."
        ::= { gmhTableEntry 1 }

mdmModem OBJECT-TYPE
        SYNTAX  INTEGER
        ACCESS  read-only
        STATUS  mandatory
        DESCRIPTION
                "This variable displays the slot number where the
                 corresponding modem is installed in the rack."
        ::= { gmhTableEntry 2 }

mdmPosition OBJECT-TYPE
        SYNTAX  INTEGER {
                local       (1),
                remote      (2)
                }
        ACCESS  read-only
        STATUS  mandatory
        DESCRIPTION
                "This variable displays the location of the corresponding
                 modem: 'local' or 'remote'.
                 The modem which is plugged into a managed rack is 'local',
                 the counterpart is 'remote'."
        ::= { gmhTableEntry 3 }

mdmModemName OBJECT-TYPE
        SYNTAX  DisplayString
        ACCESS  read-only
        STATUS  mandatory
        DESCRIPTION
                "A verbal name of this modem."
        ::= { gmhTableEntry 5 }

mdmDataEquipmentEmulation OBJECT-TYPE
        SYNTAX  INTEGER {
                other       (1),
                dte         (2),
                dce         (3),
                unknown     (99)
        }
        ACCESS  read-only
        STATUS  mandatory
        DESCRIPTION
                "Interface mode of the unit: DTE or DCE."
        ::= { gmhTableEntry 6 }

mdmModemProperty OBJECT-TYPE
        SYNTAX  INTEGER {
                other           (1),
                e1              (2),
                t1              (3),
                unknown         (99)
        }
        ACCESS  read-only
        STATUS  mandatory
        DESCRIPTION
                "Type of link: 'E1' with 2048 kbps or 'T1' with 1544 kbps."
        ::= { gmhTableEntry 7 }

mdmClockSystem OBJECT-TYPE
        SYNTAX  INTEGER {
                other       (1),
                dual        (2),
                single      (3)
        }
        ACCESS  read-write
        STATUS  mandatory
        DESCRIPTION
                "The clock system at the interface: 'single' or 'dual'."
        ::= { gmhTableEntry 23 }

mdmClockSource OBJECT-TYPE
        SYNTAX  INTEGER {
                other       (1),
                internal    (2),
                remote      (3),
                external    (4)
        }
        ACCESS  read-write
        STATUS  mandatory
        DESCRIPTION
                "The clock source at the interface: 'internal, 'remote'
                 or 'external'."
        ::= { gmhTableEntry 24 }

mdmDataRate OBJECT-TYPE
        SYNTAX  INTEGER {
                other       (1)
        }
        ACCESS  read-write
        STATUS  mandatory
        DESCRIPTION
                "The data rate at the interface in bits per seconds. The data
                 rate at the remote counterpart changes simultaneously."
        ::= { gmhTableEntry 25 }


mdmScrambler OBJECT-TYPE
        SYNTAX  INTEGER {
                other       (1),
                disable     (2),
                enable      (3)
        }
        ACCESS  read-write
        STATUS  mandatory
        DESCRIPTION
                "The scrambler activation status of the modem: 'enabled'
                 or 'disabled'."
        ::= { gmhTableEntry 63 }

mdmRemoteAccessMode OBJECT-TYPE
        SYNTAX  INTEGER {
                other       (1),
                disable     (2),
                enable      (5)
        }
        ACCESS  read-write
        STATUS  mandatory
        DESCRIPTION
                "The possibility of remote management: 'enabled' or 'disabled'.
                 Once disabled remote management, it is not possible to enable
                 it at the remote unit."
        ::= { gmhTableEntry 64 }

mdmForcedRemoteAccess OBJECT-TYPE
        SYNTAX  INTEGER {
                off         (1),
                on          (2)
        }
        ACCESS  read-write
        STATUS  mandatory
        DESCRIPTION
                "Activation of remote management: 'on' or 'off'.
                 Status 'on' enables management of remote unit. During this
                 process the link is restricted to management data. The
                 transmission of user data is interrupted.
                 Status 'off' disables management of remote unit. The link
                 transmits user data."
        ::= { gmhTableEntry 65 }

END
