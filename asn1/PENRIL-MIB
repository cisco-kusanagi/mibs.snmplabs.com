PENRIL-MIB { iso org(3) dod(6) internet(1) private(4) enterprises(1) }

DEFINITIONS ::= BEGIN

IMPORTS 
	Gauge, NetworkAddress, Counter
		FROM RFC1155-SMI
	enterprises, OBJECT-TYPE, IpAddress, TimeTicks
		FROM SNMPv2-SMI
;

                  dot3       OBJECT IDENTIFIER ::= { experimental 3 }
                  ppp        OBJECT IDENTIFIER ::= { experimental 18 }
                  fddi       OBJECT IDENTIFIER ::= { experimental 8 }


			pppLinkControlTable	OBJECT IDENTIFIER ::= { ppp 1 }
			pppLinkStatusTable	OBJECT IDENTIFIER ::= { ppp 2 }
			pppLinkErrorsTable	OBJECT IDENTIFIER ::= { ppp 3 }
			pppLinkQualityTable	OBJECT IDENTIFIER ::= { ppp 4 }
			pppProtocolTables	OBJECT IDENTIFIER ::= { ppp 5 }

			sfSMT			OBJECT IDENTIFIER ::= { fddi 1 }
			sfMAC			OBJECT IDENTIFIER ::= { fddi 2 }
			sfPATH		OBJECT IDENTIFIER ::= { fddi 3 }
			sfPORT		OBJECT IDENTIFIER ::= { fddi 4 }
			sfATTACH	OBJECT IDENTIFIER ::= { fddi 5 }

	 cmu OBJECT IDENTIFIER ::= { enterprises 3 }
	 sigma OBJECT IDENTIFIER ::= { enterprises 97 }
	 sys OBJECT IDENTIFIER ::= { sigma 1 }
	 trojan OBJECT IDENTIFIER ::= { sigma 2 }
	 hw OBJECT IDENTIFIER ::= { trojan 1 }
	 sw OBJECT IDENTIFIER ::= { trojan 2 }
	 admin OBJECT IDENTIFIER ::= { trojan 3 }
	 config OBJECT IDENTIFIER ::= { admin 1 }
	 lma OBJECT IDENTIFIER ::= { admin 2 }
	 ppe OBJECT IDENTIFIER ::= { admin 3 }
	 st OBJECT IDENTIFIER ::= { admin 4 }
	 mesh OBJECT IDENTIFIER ::= { admin 5 }
	 swdis OBJECT IDENTIFIER ::= { trojan 4 }
	 addr OBJECT IDENTIFIER ::= { trojan 5 }
	 snmpsmt OBJECT IDENTIFIER ::= { trojan 6 }
	 sinterfaces OBJECT IDENTIFIER ::= { trojan 7 }
	 sfddi OBJECT IDENTIFIER ::= { trojan 8 }
	 suart OBJECT IDENTIFIER ::= { trojan 9 }
	 filter OBJECT IDENTIFIER ::= { trojan 10 }
	 reboot OBJECT IDENTIFIER ::= { trojan 11 }
	 debug OBJECT IDENTIFIER ::= { trojan 12 }
	 lpbk OBJECT IDENTIFIER ::= { trojan 13 }
	 swan OBJECT IDENTIFIER ::= { trojan 14 }
	 systems OBJECT IDENTIFIER ::= { cmu 1 }
	 mibs OBJECT IDENTIFIER ::= { cmu 2 }
	 cmuSNMP OBJECT IDENTIFIER ::= { systems 1 }
	 cmuKip OBJECT IDENTIFIER ::= { systems 2 }
	 cmuRouter OBJECT IDENTIFIER ::= { systems 3 }

	-- Sigma MIB
	-- System group

	sysID	OBJECT-TYPE
		SYNTAX  INTEGER
		ACCESS	read-only
		STATUS	mandatory
		::= { sys 1 }

	sysReset	OBJECT-TYPE
		SYNTAX  TimeTicks
		ACCESS	read-write
		STATUS	mandatory
		::= { sys 2 }

	sysTrapAck	OBJECT-TYPE
		SYNTAX  INTEGER
		ACCESS	read-write
		STATUS	mandatory
		::= { sys 3 }

	sysTrapTime	OBJECT-TYPE
		SYNTAX  TimeTicks
		ACCESS	read-write
		STATUS	mandatory
		::= { sys 4 }

	sysTrapRetry OBJECT-TYPE
		SYNTAX  TimeTicks
		ACCESS	read-write
		STATUS	mandatory
		::= { sys 5 }

	-- Trojan HW Configuration Group


	-- Trojan HW Configuration Group


	hwNumber	OBJECT-TYPE
		SYNTAX	INTEGER
		ACCESS	read-only
		STATUS	mandatory
		::= { hw 1 }

	hwSlotTable	OBJECT-TYPE
		SYNTAX	SEQUENCE OF HwEntry
		ACCESS	not-accessible
		STATUS	mandatory
		::= { hw 2 }

	hwEntry	OBJECT-TYPE
		SYNTAX	HwEntry
		ACCESS  not-accessible
		STATUS	mandatory
		::= { hwSlotTable 1 }

	HwEntry ::= SEQUENCE {
			hwIndex
				INTEGER,
			hwType
				INTEGER,
			hwUseMod
				INTEGER,
			hwDefType
				INTEGER,
			hwDiagStatus
				INTEGER,
			hwInuse
				INTEGER,
			hwDiagCode
				INTEGER,
			hwManufData
				OCTET STRING,
			hwPortType
				OCTET STRING,
			hwPortStatus
				OCTET STRING,
			hwUsePort
				OCTET STRING,
			hwDefPortType
				OCTET STRING,
			hwAddr1
				OCTET STRING,
			hwAddr2
				OCTET STRING,
			hwAddr3
				OCTET STRING,
			hwAddr4
				OCTET STRING,
			hwTempOK
				INTEGER,
			hwFirstPort
				INTEGER,
			hwFatalErr
				OCTET STRING
			}

	hwIndex	OBJECT-TYPE
		SYNTAX	INTEGER
		ACCESS	read-only
		STATUS	mandatory
		::= { hwEntry 1 }

	hwType	OBJECT-TYPE
		SYNTAX	INTEGER
		ACCESS	read-only
		STATUS	mandatory
		::= { hwEntry 2 }

	hwUseMod	OBJECT-TYPE
		SYNTAX	INTEGER
		ACCESS	read-write
		STATUS	mandatory
		::= { hwEntry 3 }

	hwDefType	OBJECT-TYPE
		SYNTAX	INTEGER
		ACCESS	read-only
		STATUS	mandatory
		::= { hwEntry 4 }

	hwDiagStatus	OBJECT-TYPE
		SYNTAX	INTEGER
		ACCESS	read-only
		STATUS	mandatory
		::= { hwEntry 5 }

	hwInuse	OBJECT-TYPE
		SYNTAX	INTEGER
		ACCESS	read-only
		STATUS	mandatory
		::= { hwEntry 6 }

	hwDiagCode	OBJECT-TYPE
		SYNTAX	INTEGER
		ACCESS	read-only
		STATUS	mandatory
		::= { hwEntry 7 }

	hwManufData	OBJECT-TYPE
		SYNTAX	OCTET STRING
		ACCESS	read-only
		STATUS	mandatory
		::= { hwEntry 8 }

	hwPortType	OBJECT-TYPE
		SYNTAX	OCTET STRING
		ACCESS	read-only
		STATUS	mandatory
		::= { hwEntry 9 }

	hwPortStatus	OBJECT-TYPE
		SYNTAX	OCTET STRING
		ACCESS	read-only
		STATUS	mandatory
		::= { hwEntry 10 }

	hwUsePort	OBJECT-TYPE
		SYNTAX	OCTET STRING
		ACCESS	read-write
		STATUS	mandatory
		::= { hwEntry 11 }

	hwDefPortType	OBJECT-TYPE
		SYNTAX	OCTET STRING
		ACCESS	read-only
		STATUS	mandatory
		::= { hwEntry 12 }

	hwAddr1	OBJECT-TYPE
		SYNTAX	OCTET STRING
		ACCESS	read-only
		STATUS	mandatory
		::= { hwEntry 13 }

	hwAddr2	OBJECT-TYPE
		SYNTAX	OCTET STRING
		ACCESS	read-only
		STATUS	mandatory
		::= { hwEntry 14 }

	hwAddr3	OBJECT-TYPE
		SYNTAX	OCTET STRING
		ACCESS	read-only
		STATUS	mandatory
		::= { hwEntry 15 }

	hwAddr4	OBJECT-TYPE
		SYNTAX	OCTET STRING
		ACCESS	read-only
		STATUS	mandatory
		::= { hwEntry 16 }

	hwTempOK	OBJECT-TYPE
		SYNTAX	INTEGER
		ACCESS	read-only
		STATUS	mandatory
		::= { hwEntry 17 }

	hwFirstPort	OBJECT-TYPE
		SYNTAX	INTEGER
		ACCESS	read-only
		STATUS	mandatory
		::= { hwEntry 18 }

	hwFatalErr	OBJECT-TYPE
		SYNTAX	OCTET STRING
		ACCESS	read-only
		STATUS	mandatory
		::= { hwEntry 19 }

	-- Trojan SW Configuration Group




	-- Trojan SW Configuration Group

	swNumber	OBJECT-TYPE
		SYNTAX	INTEGER
		ACCESS	read-only
		STATUS	mandatory
		::= { sw 1 }

	swFilesetTable	OBJECT-TYPE
		SYNTAX	SEQUENCE OF SwFileset
		ACCESS	not-accessible
		STATUS	mandatory
		::= { sw 2 }

	swFileset	OBJECT-TYPE
		SYNTAX	SwFileset
		ACCESS	not-accessible
		STATUS	mandatory
		::= { swFilesetTable 1 }

	SwFileset ::= SEQUENCE {
			swIndex
				INTEGER,
			swValid
				INTEGER,
			swDesc
				OCTET STRING,
			swCount
				INTEGER,
			swTypes
				OCTET STRING,
			swSizes
				OCTET STRING,
			swStarts
				OCTET STRING,
			swBases
				OCTET STRING
			}

	swIndex	OBJECT-TYPE
		SYNTAX	INTEGER
		ACCESS	read-only
		STATUS	mandatory
		::= { swFileset 1 }

	swValid	OBJECT-TYPE
		SYNTAX	INTEGER
		ACCESS	read-only
		STATUS	mandatory
		::= { swFileset 2 }

	swDesc	OBJECT-TYPE
		SYNTAX	OCTET STRING
		ACCESS	read-only
		STATUS	mandatory
		::= { swFileset 3 }

	swCount	OBJECT-TYPE
		SYNTAX	INTEGER
		ACCESS	read-only
		STATUS	mandatory
		::= { swFileset 4 }

	swTypes	OBJECT-TYPE
		SYNTAX	OCTET STRING
		ACCESS	read-only
		STATUS	mandatory
		::= { swFileset 5 }

	swSizes	OBJECT-TYPE
		SYNTAX	OCTET STRING
		ACCESS	read-only
		STATUS	mandatory
		::= { swFileset 6 }

	swStarts	OBJECT-TYPE
		SYNTAX	OCTET STRING
		ACCESS	read-only
		STATUS	mandatory
		::= { swFileset 7 }

	swBases	OBJECT-TYPE
		SYNTAX	OCTET STRING
		ACCESS	read-only
		STATUS	mandatory
		::= { swFileset 8 }

	-- Configuration Status Group



	-- Configuration Status Group

	configFatalErr	OBJECT-TYPE	
		SYNTAX	OCTET STRING
		ACCESS	read-only
		STATUS	mandatory
		::= { config 1 }

	configAnyPass	OBJECT-TYPE	
		SYNTAX	OCTET STRING
		ACCESS	read-write
		STATUS	mandatory
		::= { config 2 }

	configGetPass	OBJECT-TYPE	
		SYNTAX	OCTET STRING
		ACCESS	read-write
		STATUS	mandatory
		::= { config 3 }

	configNMSAddress	OBJECT-TYPE	
		SYNTAX	IpAddress
		ACCESS	read-write
		STATUS	mandatory
		::= { config 4 }

	configFunctions	OBJECT-TYPE	
		SYNTAX	INTEGER
		ACCESS	read-only
		STATUS	mandatory
		::= { config 5 }

	configPowerAc1	OBJECT-TYPE	
		SYNTAX	INTEGER
		ACCESS	read-only
		STATUS	mandatory
		::= { config 6 }

	configPowerAc2	OBJECT-TYPE	
		SYNTAX	INTEGER
		ACCESS	read-only
		STATUS	mandatory
		::= { config 7 }

	configPowerDc1	OBJECT-TYPE	
		SYNTAX	INTEGER
		ACCESS	read-only
		STATUS	mandatory
		::= { config 8 }

	configPowerDc2	OBJECT-TYPE	
		SYNTAX	INTEGER
		ACCESS	read-only
		STATUS	mandatory
		::= { config 9 }

	configPowerPresent1	OBJECT-TYPE	
		SYNTAX	INTEGER
		ACCESS	read-only
		STATUS	mandatory
		::= { config 10 }

	configPowerPresent2	OBJECT-TYPE	
		SYNTAX	INTEGER
		ACCESS	read-only
		STATUS	mandatory
		::= { config 11 }

	configAlarmDynamic	OBJECT-TYPE	
		SYNTAX	INTEGER
		ACCESS	read-write
		STATUS	mandatory
		::= { config 12 }

	configAlarmAddresses	OBJECT-TYPE	
		SYNTAX	INTEGER
		ACCESS	read-write
		STATUS	mandatory
		::= { config 13 }

	configStorageFailure	OBJECT-TYPE	
		SYNTAX	INTEGER
		ACCESS	read-only
		STATUS	mandatory
		::= { config 14 }

	configAuthenticationFailure	OBJECT-TYPE	
		SYNTAX	IpAddress
		ACCESS	read-only
		STATUS	mandatory
		::= { config 15 }

	configFddiPriority	OBJECT-TYPE	
		SYNTAX	INTEGER
		ACCESS	read-write
		STATUS	mandatory
		::= { config 16 }

	configTprPriority	OBJECT-TYPE	
		SYNTAX	INTEGER
		ACCESS	read-write
		STATUS	mandatory
		::= { config 17 }

	-- LMA Configuration Group



	lmaAllAddr	OBJECT-TYPE
		SYNTAX	OCTET STRING
		ACCESS	read-write
		STATUS	mandatory
		::= { lma 1 }
	
	lmaAnyAddr	OBJECT-TYPE
		SYNTAX	OCTET STRING
		ACCESS	read-write
		STATUS	mandatory
		::= { lma 2 }
	

	-- PPE Configuration Group

	ppeLrgUxRxCnt	OBJECT-TYPE
		SYNTAX	INTEGER
		ACCESS	read-write
		STATUS	mandatory
		::= { ppe 1 }
	
	ppeSmlUxRxCnt	OBJECT-TYPE
		SYNTAX	INTEGER
		ACCESS	read-write
		STATUS	mandatory
		::= { ppe 2 }
	
	ppeUxTxCnt	OBJECT-TYPE
		SYNTAX	INTEGER
		ACCESS	read-write
		STATUS	mandatory
		::= { ppe 3 }
	
	ppeSmlBuffSize	OBJECT-TYPE
		SYNTAX	INTEGER
		ACCESS	read-write
		STATUS	mandatory
		::= { ppe 4 }
	
	ppeLrgBuffSize	OBJECT-TYPE
		SYNTAX	INTEGER
		ACCESS	read-write
		STATUS	mandatory
		::= { ppe 5 }
	
	ppeExtendStats	OBJECT-TYPE
		SYNTAX	INTEGER
		ACCESS	read-write
		STATUS	mandatory
		::= { ppe 6 }
	
	ppeBAddrLimit	OBJECT-TYPE
		SYNTAX	INTEGER
		ACCESS	read-write
		STATUS	mandatory
		::= { ppe 7 }
	
	ppeTxCongests	OBJECT-TYPE
		SYNTAX	Counter
		ACCESS	read-only
		STATUS	mandatory
		::= { ppe 8 }
	
	ppeArpEntries	OBJECT-TYPE
		SYNTAX	Counter
		ACCESS	read-only
		STATUS	mandatory
		::= { ppe 9 }
	
	ppeArpStatics	OBJECT-TYPE
		SYNTAX	Counter
		ACCESS	read-only
		STATUS	mandatory
		::= { ppe 10 }
	
	ppeArpOverflows	OBJECT-TYPE
		SYNTAX	Counter
		ACCESS	read-only
		STATUS	mandatory
		::= { ppe 11 }
	
	ppeIpEntries	OBJECT-TYPE
		SYNTAX	Counter
		ACCESS	read-only
		STATUS	mandatory
		::= { ppe 12 }
	
	ppeIpStatics	OBJECT-TYPE
		SYNTAX	Counter
		ACCESS	read-only
		STATUS	mandatory
		::= { ppe 13 }
	

	-- Spanning Tree Group

	stGroupAddr	OBJECT-TYPE
		SYNTAX	OCTET STRING
		ACCESS	read-write
		STATUS	mandatory
		::= { st 1 }
	
	stResAddr	OBJECT-TYPE
		SYNTAX	OCTET STRING
		ACCESS	read-write
		STATUS	mandatory
		::= { st 2 }
	
	stBridgeId	OBJECT-TYPE
		SYNTAX	OCTET STRING
		ACCESS	read-write
		STATUS	mandatory
		::= { st 3 }
	
	stRootMaxAge	OBJECT-TYPE
		SYNTAX	TimeTicks
		ACCESS	read-write
		STATUS	mandatory
		::= { st 4 }
	
	stRootHello	OBJECT-TYPE
		SYNTAX	TimeTicks
		ACCESS	read-write
		STATUS	mandatory
		::= { st 5 }
	
	stRootDelay	OBJECT-TYPE
		SYNTAX	TimeTicks
		ACCESS	read-write
		STATUS	mandatory
		::= { st 6 }
	
	stRootID	OBJECT-TYPE
		SYNTAX	OCTET STRING
		ACCESS	read-only
		STATUS	mandatory
		::= { st 7 }
	
	stRootCost	OBJECT-TYPE
		SYNTAX	INTEGER
		ACCESS	read-only
		STATUS	mandatory
		::= { st 8 }
	
	stRootPort	OBJECT-TYPE
		SYNTAX	INTEGER
		ACCESS	read-only
		STATUS	mandatory
		::= { st 9 }
	
	stTopChange	OBJECT-TYPE
		SYNTAX	INTEGER
		ACCESS	read-only
		STATUS	mandatory
		::= { st 10 }
	
	stActMaxAge	OBJECT-TYPE
		SYNTAX	TimeTicks
		ACCESS	read-only
		STATUS	mandatory
		::= { st 11 }
	
	stActHello	OBJECT-TYPE
		SYNTAX	TimeTicks
		ACCESS	read-only
		STATUS	mandatory
		::= { st 12 }
	
	stActDelay	OBJECT-TYPE
		SYNTAX	TimeTicks
		ACCESS	read-only
		STATUS	mandatory
		::= { st 13 }
	
	stTopChangeCount	OBJECT-TYPE
		SYNTAX	INTEGER
		ACCESS	read-write
		STATUS	mandatory
		::= { st 14 }
	
	stTopChangeTime	OBJECT-TYPE
		SYNTAX	TimeTicks
		ACCESS	read-only
		STATUS	mandatory
		::= { st 15 }
	
	stAgeTime	OBJECT-TYPE
		SYNTAX	INTEGER
		ACCESS	read-write
		STATUS	mandatory
		::= { st 16 }
	
	-- Mesh Group

	meshCostPercent	OBJECT-TYPE
		SYNTAX INTEGER
		ACCESS	read-write
		STATUS	mandatory
		::= { mesh 1 }

	meshCost	OBJECT-TYPE
		SYNTAX INTEGER
		ACCESS	read-write
		STATUS	mandatory
		::= { mesh 2 }

	meshCostChange	OBJECT-TYPE
		SYNTAX 	INTEGER
		ACCESS	read-only
		STATUS	mandatory
		::= { mesh 3 }

	meshCostChangeCount	OBJECT-TYPE
		SYNTAX 	INTEGER
		ACCESS	read-write
		STATUS	mandatory
		::= { mesh 4 }

	meshCostChangeTime	OBJECT-TYPE
		SYNTAX 	TimeTicks
		ACCESS	read-only
		STATUS	mandatory
		::= { mesh 5 }

	meshSubnet	OBJECT-TYPE
		SYNTAX 	OCTET STRING
		ACCESS	read-only
		STATUS	mandatory
		::= { mesh 6 }

	-- Software Distribution Group

	swdisDesc 	OBJECT-TYPE
		SYNTAX 	OCTET STRING
		ACCESS	read-write
		STATUS	mandatory
		::= { swdis 1 }

	swdisNewSet	OBJECT-TYPE
		SYNTAX INTEGER
		ACCESS	read-write
		STATUS	mandatory
		::= { swdis 2 }

	swdisWriteStatus	OBJECT-TYPE
		SYNTAX INTEGER
		ACCESS	read-write
		STATUS	mandatory
		::= { swdis 3 }

	swdisFileNumber	OBJECT-TYPE
		SYNTAX INTEGER
		ACCESS	read-write
		STATUS	mandatory
		::= { swdis 4 }

	swdisFileType	OBJECT-TYPE
		SYNTAX INTEGER
		ACCESS	read-write
		STATUS	mandatory
		::= { swdis 5 }

	swdisFileLength	OBJECT-TYPE
		SYNTAX INTEGER
		ACCESS	read-write
		STATUS	mandatory
		::= { swdis 6 }

	swdisBlockOffset	OBJECT-TYPE
		SYNTAX INTEGER
		ACCESS	read-write
		STATUS	mandatory
		::= { swdis 7 }

	swdisFileStart	OBJECT-TYPE
		SYNTAX INTEGER
		ACCESS	read-write
		STATUS	mandatory
		::= { swdis 8 }

	swdisFileBase	OBJECT-TYPE
		SYNTAX INTEGER
		ACCESS	read-write
		STATUS	mandatory
		::= { swdis 9 }

	swdisBlockSize	OBJECT-TYPE
		SYNTAX INTEGER
		ACCESS	read-write
		STATUS	mandatory
		::= { swdis 10 }

	swdisBlockData	OBJECT-TYPE
		SYNTAX 	OCTET STRING
		ACCESS	read-write
		STATUS	mandatory
		::= { swdis 11 }

	-- Address Configuration

	addrStatics	OBJECT-TYPE
		SYNTAX	 Counter
		ACCESS	read-only
		STATUS	mandatory
		::= { addr 1 }

	addrDynamics	OBJECT-TYPE
		SYNTAX	Counter
		ACCESS	read-only
		STATUS	mandatory
		::= { addr 2 }

	addrDynamicMax	OBJECT-TYPE
		SYNTAX	Gauge
		ACCESS	read-write
		STATUS	mandatory
		::= { addr 3 }

	addrMeshs	OBJECT-TYPE
		SYNTAX	 Counter
		ACCESS	read-only
		STATUS	mandatory
		::= { addr 4 }

	addrDynamicOverflows	OBJECT-TYPE
		SYNTAX	Counter
		ACCESS	read-only
		STATUS	mandatory
		::= { addr 5 }


	addrMeshOverflows	OBJECT-TYPE
		SYNTAX	Counter
		ACCESS	read-only
		STATUS	mandatory
		::= { addr 6 }

	addrFlags	OBJECT-TYPE
		SYNTAX	INTEGER
		ACCESS	read-write
		STATUS	mandatory
		::= { addr 7 }

	addrMAC	OBJECT-TYPE
		SYNTAX	OCTET STRING
		ACCESS	read-write
		STATUS	mandatory
		::= { addr 8 }

	addrPort	OBJECT-TYPE
		SYNTAX	INTEGER
		ACCESS	write-only
		STATUS	mandatory
		::= { addr 9 }

	addrPortMap	OBJECT-TYPE
		SYNTAX	OCTET STRING
		ACCESS	read-write
		STATUS	mandatory
		::= { addr 10 }

	addrBridgeMap	OBJECT-TYPE
		SYNTAX	OCTET STRING
		ACCESS	read-write
		STATUS	mandatory
		::= { addr 11 }

	addrLeastCount	OBJECT-TYPE
		SYNTAX	INTEGER
		ACCESS	write-only
		STATUS	mandatory
		::= { addr 12 }

	addrTotalCount	OBJECT-TYPE
		SYNTAX	INTEGER
		ACCESS	write-only
		STATUS	mandatory
		::= { addr 13 }

	addrCost1	OBJECT-TYPE
		SYNTAX	INTEGER
		ACCESS	write-only
		STATUS	mandatory
		::= { addr 14 }

	addrCost2	OBJECT-TYPE
		SYNTAX	INTEGER
		ACCESS	write-only
		STATUS	mandatory
		::= { addr 15 }

	addrCost3	OBJECT-TYPE
		SYNTAX	INTEGER
		ACCESS	write-only
		STATUS	mandatory
		::= { addr 16 }

	addrCost4	OBJECT-TYPE
		SYNTAX	INTEGER
		ACCESS	write-only
		STATUS	mandatory
		::= { addr 17 }

	addrSource1	OBJECT-TYPE
		SYNTAX	INTEGER
		ACCESS	write-only
		STATUS	mandatory
		::= { addr 18 }

	addrSource2	OBJECT-TYPE
		SYNTAX	INTEGER
		ACCESS	write-only
		STATUS	mandatory
		::= { addr 19 }

	addrSource3	OBJECT-TYPE
		SYNTAX	INTEGER
		ACCESS	write-only
		STATUS	mandatory
		::= { addr 20 }

	addrSource4	OBJECT-TYPE
		SYNTAX	INTEGER
		ACCESS	write-only
		STATUS	mandatory
		::= { addr 21 }

	addrDest1	OBJECT-TYPE
		SYNTAX	INTEGER
		ACCESS	write-only
		STATUS	mandatory
		::= { addr 22 }

	addrDest2	OBJECT-TYPE
		SYNTAX	INTEGER
		ACCESS	write-only
		STATUS	mandatory
		::= { addr 23 }

	addrDest3	OBJECT-TYPE
		SYNTAX	INTEGER
		ACCESS	write-only
		STATUS	mandatory
		::= { addr 24 }

	addrDest4	OBJECT-TYPE
		SYNTAX	INTEGER
		ACCESS	write-only
		STATUS	mandatory
		::= { addr 25 }

	addrStabile	OBJECT-TYPE
		SYNTAX	TimeTicks
		ACCESS	write-only
		STATUS	mandatory
		::= { addr 26 }

	addrTxSource	OBJECT-TYPE
		SYNTAX	INTEGER
		ACCESS	read-write
		STATUS	mandatory
		::= { addr 27 }

	addrTxDestination	OBJECT-TYPE
		SYNTAX	INTEGER
		ACCESS	read-write
		STATUS	mandatory
		::= { addr 28 }

	addrOldLeast	OBJECT-TYPE
		SYNTAX	INTEGER
		ACCESS	write-only
		STATUS	mandatory
		::= { addr 29 }

	addrOldTotal	OBJECT-TYPE
		SYNTAX	INTEGER
		ACCESS	write-only
		STATUS	mandatory
		::= { addr 30 }

	addrOldSource1	OBJECT-TYPE
		SYNTAX	INTEGER
		ACCESS	write-only
		STATUS	mandatory
		::= { addr 31 }

	addrOldSource2	OBJECT-TYPE
		SYNTAX	INTEGER
		ACCESS	write-only
		STATUS	mandatory
		::= { addr 32 }

	addrOldSource3	OBJECT-TYPE
		SYNTAX	INTEGER
		ACCESS	write-only
		STATUS	mandatory
		::= { addr 33 }

	addrOldSource4	OBJECT-TYPE
		SYNTAX	INTEGER
		ACCESS	write-only
		STATUS	mandatory
		::= { addr 34 }

	addrOldDestination1	OBJECT-TYPE
		SYNTAX	INTEGER
		ACCESS	write-only
		STATUS	mandatory
		::= { addr 35 }

	addrOldDestination2	OBJECT-TYPE
		SYNTAX	INTEGER
		ACCESS	write-only
		STATUS	mandatory
		::= { addr 36 }

	addrOldDestination3	OBJECT-TYPE
		SYNTAX	INTEGER
		ACCESS	write-only
		STATUS	mandatory
		::= { addr 37 }

	addrOldDestination4	OBJECT-TYPE
		SYNTAX	INTEGER
		ACCESS	write-only
		STATUS	mandatory
		::= { addr 38 }

	addrOldTxSource	OBJECT-TYPE
		SYNTAX	INTEGER
		ACCESS	write-only
		STATUS	mandatory
		::= { addr 39 }

	addrOldTxDestination	OBJECT-TYPE
		SYNTAX	INTEGER
		ACCESS	write-only
		STATUS	mandatory
		::= { addr 40 }

	addrOperation	OBJECT-TYPE
		SYNTAX	INTEGER
		ACCESS	read-write
		STATUS	mandatory
		::= { addr 41 }

	addrIndex	OBJECT-TYPE
		SYNTAX	INTEGER
		ACCESS	read-write
		STATUS	mandatory
		::= { addr 42 }

	addrIndexMesh	OBJECT-TYPE
		SYNTAX	INTEGER
		ACCESS	read-write
		STATUS	mandatory
		::= { addr 43 }

	addrNext	OBJECT-TYPE
		SYNTAX	INTEGER
		ACCESS	write-only
		STATUS	mandatory
		::= { addr 44 }

	addrAge	OBJECT-TYPE
		SYNTAX	TimeTicks
		ACCESS	write-only
		STATUS	mandatory
		::= { addr 45 }

	addrRxPkts	OBJECT-TYPE
		SYNTAX	Counter
		ACCESS	write-only
		STATUS	mandatory
		::= { addr 46 }

	addrRxChars	OBJECT-TYPE
		SYNTAX	Counter
		ACCESS	write-only
		STATUS	mandatory
		::= { addr 47 }

	addrRxMultiPkts	OBJECT-TYPE
		SYNTAX	Counter
		ACCESS	write-only
		STATUS	mandatory
		::= { addr 48 }

	addrRxFwdPkts	OBJECT-TYPE
		SYNTAX	Counter
		ACCESS	write-only
		STATUS	mandatory
		::= { addr 49 }

	addrTxPkts	OBJECT-TYPE
		SYNTAX	Counter
		ACCESS	write-only
		STATUS	mandatory
		::= { addr 50 }

	addrTxChars	OBJECT-TYPE
		SYNTAX	Counter
		ACCESS	write-only
		STATUS	mandatory
		::= { addr 51 }

	addrBlockSize	OBJECT-TYPE
		SYNTAX	INTEGER
		ACCESS	write-only
		STATUS	mandatory
		::= { addr 52 }

	addrBlock	OBJECT-TYPE
		SYNTAX	OCTET STRING
		ACCESS	write-only
		STATUS	mandatory
		::= { addr 53 }

	addrAlarmMAC	OBJECT-TYPE
		SYNTAX	OCTET STRING
		ACCESS	read-only
		STATUS	mandatory
		::= { addr 54 }

	-- SNMP/SMT Support Group

	snmpsmtUpstreamReq	OBJECT-TYPE
		SYNTAX	OCTET STRING
		ACCESS	read-write
		STATUS	mandatory
		::= { snmpsmt 1 }

	snmpsmtUpstreamRsp	OBJECT-TYPE
		SYNTAX	OCTET STRING
		ACCESS	read-only
		STATUS	mandatory
		::= { snmpsmt 2 }

	snmpsmtUpstreamDescriptor	OBJECT-TYPE
		SYNTAX	OCTET STRING
		ACCESS	read-only
		STATUS	mandatory
		::= { snmpsmt 3 }

	snmpsmtUpstreamState	OBJECT-TYPE
		SYNTAX	OCTET STRING
		ACCESS	read-only
		STATUS	mandatory
		::= { snmpsmt 4 }

	-- Sigma Interfaces Group

	sifUX	OBJECT-TYPE
		SYNTAX	INTEGER
		ACCESS	read-only
		STATUS	mandatory
		::= { sinterfaces 1 }

	sifBuffSpace	OBJECT-TYPE
		SYNTAX	INTEGER
		ACCESS	read-only
		STATUS	mandatory
		::= { sinterfaces 2 }

	sifTable	OBJECT-TYPE
		SYNTAX	SEQUENCE OF SifEntry
		ACCESS	not-accessible
		STATUS	mandatory
		::= { sinterfaces 3 }

	sifEntry	OBJECT-TYPE
		SYNTAX	SifEntry
		ACCESS	not-accessible
		STATUS	mandatory
		::= { sifTable 1 }

	SifEntry ::= SEQUENCE {
			sifIndex
				INTEGER,
			sifSmlRxCnt
				INTEGER,
			sifLrgRxCnt
				INTEGER,
			sifSmlBuffSize
				INTEGER,
			sifLrgBuffSize
				INTEGER,
			sifUxTxCnt
				INTEGER,
			sifThreshold
				INTEGER,
			sifThresholdTime
				TimeTicks,
			sifRxQueueThresh
				INTEGER,
			sifRxQueueThreshTime
				TimeTicks,
			sifTxStormCnt
				INTEGER,
			sifTxStormTime
				TimeTicks,
			sifMinPacketSize
				INTEGER,
			sifFilterFlags
				INTEGER,
			sifCongestTime
				TimeTicks,
			sifQueueTime
				TimeTicks,
			sifPortCost
				INTEGER,
			sifStPriority
				INTEGER,
			sifFunctions
				INTEGER,
			sifCongested
				INTEGER,
			sifState
				INTEGER,
			sifDesigCost
				INTEGER,
			sifDesigRoot
				OCTET STRING,
			sifDesigBridge
				OCTET STRING,
			sifDesigPort
				OCTET STRING,
			sifRxPackets
				OCTET STRING,
			sifRxChar0s
				Counter,
			sifRxChar1s
				Counter,
			sifRxSizeErrors
				Counter,
			sifRxHwFCSs
				Counter,
			sifRxQueues
				Counter,
			sifRxFFcnts
				Counter,
			sifTxPackets
				OCTET STRING,
			sifTxCongests
				Counter,
			sifTxStorms
				Counter,
			sifTxDests
				Counter,
			sifErrorsFlag
				INTEGER,
			sifRxQueueFlag
				INTEGER,
			sifTxStormFlag
				INTEGER,
			sifTxSizes
				Counter,
			sifTxAddr
				OCTET STRING,
			sifLan
				INTEGER,
			sifStatisticsTime
				TimeTicks,
			sifIpAddress
				IpAddress,
			sifIpGroupAddress
				IpAddress,
			sifMaxPacketSize
				INTEGER,
			sifExpectSqe
				INTEGER,
			sifExtraIpAddress1
				IpAddress,
			sifExtraIpAddress2
				IpAddress,
			sifExtraIpAddress3
				IpAddress
			}

	sifIndex	OBJECT-TYPE
		SYNTAX	INTEGER
		ACCESS	read-only
		STATUS	mandatory
		::= { sifEntry 1 }

	sifSmlRxCnt	OBJECT-TYPE
		SYNTAX	INTEGER
		ACCESS	read-write
		STATUS	mandatory
		::= { sifEntry 2 }

	sifLrgRxCnt	OBJECT-TYPE
		SYNTAX	INTEGER
		ACCESS	read-write
		STATUS	mandatory
		::= { sifEntry 3 }

	sifSmlBuffSize	OBJECT-TYPE
		SYNTAX	INTEGER
		ACCESS	read-write
		STATUS	mandatory
		::= { sifEntry 4 }

	sifLrgBuffSize	OBJECT-TYPE
		SYNTAX	INTEGER
		ACCESS	read-write
		STATUS	mandatory
		::= { sifEntry 5 }

	sifUxTxCnt	OBJECT-TYPE
		SYNTAX	INTEGER
		ACCESS	read-write
		STATUS	mandatory
		::= { sifEntry 6 }

	sifThreshold	OBJECT-TYPE
		SYNTAX	INTEGER
		ACCESS	read-write
		STATUS	mandatory
		::= { sifEntry 7 }

	sifThresholdTime	OBJECT-TYPE
		SYNTAX	INTEGER
		ACCESS	read-write
		STATUS	mandatory
		::= { sifEntry 8 }

	sifRxQueueThresh	OBJECT-TYPE
		SYNTAX	INTEGER
		ACCESS	read-write
		STATUS	mandatory
		::= { sifEntry 9 }

	sifRxQueueThreshTime	OBJECT-TYPE
		SYNTAX	INTEGER
		ACCESS	read-write
		STATUS	mandatory
		::= { sifEntry 10 }

	sifTxStormCnt	OBJECT-TYPE
		SYNTAX	INTEGER
		ACCESS	read-write
		STATUS	mandatory
		::= { sifEntry 11 }

	sifTxStormTime	OBJECT-TYPE
		SYNTAX	TimeTicks
		ACCESS	read-write
		STATUS	mandatory
		::= { sifEntry 12 }

	sifMinPacketSize	OBJECT-TYPE
		SYNTAX	INTEGER
		ACCESS	read-write
		STATUS	mandatory
		::= { sifEntry 13 }

	sifFilterFlags	OBJECT-TYPE
		SYNTAX	INTEGER
		ACCESS	read-write
		STATUS	mandatory
		::= { sifEntry 14 }

	sifCongestTime	OBJECT-TYPE
		SYNTAX	TimeTicks
		ACCESS	read-write
		STATUS	mandatory
		::= { sifEntry 15 }

	sifQueueTime	OBJECT-TYPE
		SYNTAX	TimeTicks
		ACCESS	read-write
		STATUS	mandatory
		::= { sifEntry 16 }

	sifPortCost	OBJECT-TYPE
		SYNTAX	INTEGER
		ACCESS	read-write
		STATUS	mandatory
		::= { sifEntry 17 }

	sifStPriority	OBJECT-TYPE
		SYNTAX	INTEGER
		ACCESS	read-write
		STATUS	mandatory
		::= { sifEntry 18 }

	sifFunctions	OBJECT-TYPE
		SYNTAX	INTEGER
		ACCESS	read-only
		STATUS	mandatory
		::= { sifEntry 19 }

	sifCongested	OBJECT-TYPE
		SYNTAX	INTEGER
		ACCESS	read-only
		STATUS	mandatory
		::= { sifEntry 20 }

	sifState	OBJECT-TYPE
        SYNTAX  INTEGER {
                    disabled(0),
                    listening(1),
                    learning(2),
                    forwarding(3),
                    blocking(4)
                }
		ACCESS	read-only
		STATUS	mandatory
		::= { sifEntry 21 }

	sifDesigCost	OBJECT-TYPE
		SYNTAX	INTEGER
		ACCESS	read-only
		STATUS	mandatory
		::= { sifEntry 22 }

	sifDesigRoot	OBJECT-TYPE
		SYNTAX	OCTET STRING
		ACCESS	read-only
		STATUS	mandatory
		::= { sifEntry 23 }

	sifDesigBridge	OBJECT-TYPE
		SYNTAX	OCTET STRING
		ACCESS	read-only
		STATUS	mandatory
		::= { sifEntry 24 }

	sifDesigPort	OBJECT-TYPE
		SYNTAX	OCTET STRING
		ACCESS	read-only
		STATUS	mandatory
		::= { sifEntry 25 }

	sifRxPackets	OBJECT-TYPE
		SYNTAX	OCTET STRING
		ACCESS	read-only
		STATUS	mandatory
		::= { sifEntry 26 }

	sifRxChar0s	OBJECT-TYPE
		SYNTAX	Counter
		ACCESS	read-only
		STATUS	mandatory
		::= { sifEntry 27 }

	sifRxChar1s	OBJECT-TYPE
		SYNTAX	Counter
		ACCESS	read-only
		STATUS	mandatory
		::= { sifEntry 28 }

	sifRxSizeErrors	OBJECT-TYPE
		SYNTAX	Counter
		ACCESS	read-only
		STATUS	mandatory
		::= { sifEntry 29 }

	sifRxHwFCSs	OBJECT-TYPE
		SYNTAX	Counter
		ACCESS	read-only
		STATUS	mandatory
		::= { sifEntry 30 }

	sifRxQueues	OBJECT-TYPE
		SYNTAX	Counter
		ACCESS	read-only
		STATUS	mandatory
		::= { sifEntry 31 }

	sifRxFFcnts	OBJECT-TYPE
		SYNTAX	Counter
		ACCESS	read-only
		STATUS	mandatory
		::= { sifEntry 32 }

	sifTxPackets	OBJECT-TYPE
		SYNTAX	OCTET STRING
		ACCESS	read-only
		STATUS	mandatory
		::= { sifEntry 33 }

	sifTxCongests	OBJECT-TYPE
		SYNTAX	Counter
		ACCESS	read-only
		STATUS	mandatory
		::= { sifEntry 34 }

	sifTxStorms	OBJECT-TYPE
		SYNTAX	Counter
		ACCESS	read-only
		STATUS	mandatory
		::= { sifEntry 35 }

	sifTxDests	OBJECT-TYPE
		SYNTAX	Counter
		ACCESS	read-only
		STATUS	mandatory
		::= { sifEntry 36 }

	sifErrorsFlag	OBJECT-TYPE
		SYNTAX	INTEGER
		ACCESS	read-only
		STATUS	mandatory
		::= { sifEntry 37 }

	sifRxQueueFlag	OBJECT-TYPE
		SYNTAX	INTEGER
		ACCESS	read-only
		STATUS	mandatory
		::= { sifEntry 38 }

	sifTxStormFlag	OBJECT-TYPE
		SYNTAX	INTEGER
		ACCESS	read-only
		STATUS	mandatory
		::= { sifEntry 39 }

	sifTxSizes	OBJECT-TYPE
		SYNTAX	Counter
		ACCESS	read-only
		STATUS	mandatory
		::= { sifEntry 40 }

	sifTxAddr	OBJECT-TYPE
		SYNTAX	OCTET STRING
		ACCESS	read-only
		STATUS	mandatory
		::= { sifEntry 41 }

	sifLan	OBJECT-TYPE
		SYNTAX	INTEGER
		ACCESS	read-write
		STATUS	mandatory
		::= { sifEntry 42 }

	sifStatisticsTime	OBJECT-TYPE
		SYNTAX	TimeTicks
		ACCESS	read-only
		STATUS	mandatory
		::= { sifEntry 43 }

	sifIpAddress	OBJECT-TYPE
		SYNTAX	IpAddress
		ACCESS	read-write
		STATUS	mandatory
		::= { sifEntry 44 }

	sifIpGroupAddress	OBJECT-TYPE
		SYNTAX	IpAddress
		ACCESS	read-write
		STATUS	mandatory
		::= { sifEntry 45 }

	sifMaxPacketSize	OBJECT-TYPE
		SYNTAX	INTEGER
		ACCESS	read-write
		STATUS	mandatory
		::= { sifEntry 46 }

	sifExpectSqe	OBJECT-TYPE
		SYNTAX	INTEGER
		ACCESS	read-write
		STATUS	mandatory
		::= { sifEntry 47 }

	sifExtraIpAddress1	OBJECT-TYPE
		SYNTAX	IpAddress
		ACCESS	read-write
		STATUS	mandatory
		::= { sifEntry 48 }

	sifExtraIpAddress2	OBJECT-TYPE
		SYNTAX	IpAddress
		ACCESS	read-write
		STATUS	mandatory
		::= { sifEntry 49 }

	sifExtraIpAddress3	OBJECT-TYPE
		SYNTAX	IpAddress
		ACCESS	read-write
		STATUS	mandatory
		::= { sifEntry 50 }

	-- Sigma FDDI Interfaces Group

	sfddiTable	OBJECT-TYPE
		SYNTAX	SEQUENCE OF SfddiEntry
		ACCESS	not-accessible
		STATUS	mandatory
		::= { sfddi 1 }

	sfddiEntry	OBJECT-TYPE
		SYNTAX	SfddiEntry
		ACCESS	not-accessible
		STATUS	mandatory
		::= { sfddiTable 1 }

	SfddiEntry ::= SEQUENCE {
				sfddiIndex
					INTEGER,
				sfddiRxHwAborts
					Counter,
				sfddiRxParitys
					Counter,
				sfddiRxShorts
					Counter,
				sfddiDpcErrCnts
					Counter,
				sfddiDpcErrValue
					INTEGER,
				sfddiRbcErrCnts
					Counter,
				sfddiRbcErrValue
					INTEGER,
				sfddiTxAsync
					INTEGER,
				sfddiShortAddressing
					INTEGER,
				sfddiSmtConditions
					INTEGER,
				sfddiSrfConditions
					INTEGER,
				sfddiSmtConditionsStatus
					INTEGER,
				sfddiSrfConditionsStatus
					INTEGER,
				sfddiSrfReportLimit
					INTEGER,
				sfddiFrameErrorThreshold
					INTEGER,
				sfddiNotCopiedThreshold
					INTEGER,
				sfddiSBFlag
					INTEGER,
				sfddiRxEbits
					INTEGER,
				sfddiOBSFuseBad
					INTEGER,
				sfddiThruB
					INTEGER,
				sfddiStationDescriptor
					OCTET STRING,
				sfddiStationState
					OCTET STRING,
				sfddiDownstreamNbr
					OCTET STRING
				}
	sfddiIndex	OBJECT-TYPE
		SYNTAX	INTEGER
		ACCESS	read-only
		STATUS	mandatory
		::= { sfddiEntry 1 }

	sfddiRxHwAborts	OBJECT-TYPE
		SYNTAX	Counter
		ACCESS	read-write
		STATUS	mandatory
		::= { sfddiEntry 2 }

	sfddiRxParitys	OBJECT-TYPE
		SYNTAX	Counter
		ACCESS	read-write
		STATUS	mandatory
		::= { sfddiEntry 3 }

	sfddiRxShorts	OBJECT-TYPE
		SYNTAX	Counter
		ACCESS	read-write
		STATUS	mandatory
		::= { sfddiEntry 4 }

	sfddiDpcErrCnts	OBJECT-TYPE
		SYNTAX	Counter
		ACCESS	read-write
		STATUS	mandatory
		::= { sfddiEntry 5 }

	sfddiDpcErrValue	OBJECT-TYPE
		SYNTAX	INTEGER
		ACCESS	read-write
		STATUS	mandatory
		::= { sfddiEntry 6 }

	sfddiRbcErrCnts	OBJECT-TYPE
		SYNTAX	Counter
		ACCESS	read-write
		STATUS	mandatory
		::= { sfddiEntry 7 }

	sfddiRbcErrValue	OBJECT-TYPE
		SYNTAX	INTEGER
		ACCESS	read-write
		STATUS	mandatory
		::= { sfddiEntry 8 }

	sfddiTxAsync	OBJECT-TYPE
		SYNTAX	INTEGER
		ACCESS	read-write
		STATUS	mandatory
		::= { sfddiEntry 9 }

	sfddiShortAddressing	OBJECT-TYPE
		SYNTAX	INTEGER
		ACCESS	read-only
		STATUS	mandatory
		::= { sfddiEntry 10 }

	sfddiSmtConditions	OBJECT-TYPE
		SYNTAX	INTEGER
		ACCESS	read-write
		STATUS	mandatory
		::= { sfddiEntry 11 }

	sfddiSrfConditions	OBJECT-TYPE
		SYNTAX	INTEGER
		ACCESS	read-write
		STATUS	mandatory
		::= { sfddiEntry 12 }

	sfddiSmtConditionsStatus	OBJECT-TYPE
		SYNTAX	INTEGER
		ACCESS	read-write
		STATUS	mandatory
		::= { sfddiEntry 13 }

	sfddiSrfConditionsStatus	OBJECT-TYPE
		SYNTAX	INTEGER
		ACCESS	read-write
		STATUS	mandatory
		::= { sfddiEntry 14 }

	sfddiSrfReportLimit	OBJECT-TYPE
		SYNTAX	INTEGER
		ACCESS	read-write
		STATUS	mandatory
		::= { sfddiEntry 15 }

	sfddiFrameErrorThreshold	OBJECT-TYPE
		SYNTAX	INTEGER
		ACCESS	read-write
		STATUS	mandatory
		::= { sfddiEntry 16 }

	sfddiNotCopiedThreshold	OBJECT-TYPE
		SYNTAX	INTEGER
		ACCESS	read-write
		STATUS	mandatory
		::= { sfddiEntry 17 }

	sfddiSBFlag	OBJECT-TYPE
		SYNTAX	INTEGER
		ACCESS	read-only
		STATUS	mandatory
		::= { sfddiEntry 18 }

	sfddiRxEbits OBJECT-TYPE
		SYNTAX	INTEGER
		ACCESS	read-only
		STATUS	mandatory
		::= { sfddiEntry 19 }

	sfddiOBSFuseBad OBJECT-TYPE
		SYNTAX	INTEGER
		ACCESS	read-only
		STATUS	mandatory
		::= { sfddiEntry 20 }

	sfddiThruB OBJECT-TYPE
		SYNTAX	INTEGER
		ACCESS	read-write
		STATUS	mandatory
		::= { sfddiEntry 21 }

	sfddiStationDescriptor OBJECT-TYPE
		SYNTAX	OCTET STRING
		ACCESS	read-only
		STATUS	mandatory
		::= { sfddiEntry 22 }

	sfddiStationState OBJECT-TYPE
		SYNTAX	OCTET STRING
		ACCESS	read-only
		STATUS	mandatory
		::= { sfddiEntry 23 }

	sfddiDownstreamNbr OBJECT-TYPE
		SYNTAX	OCTET STRING
		ACCESS	read-only
		STATUS	mandatory
		::= { sfddiEntry 24 }

	-- Sigma UART Interface Group

	suartTable	OBJECT-TYPE
		SYNTAX	SEQUENCE OF SuartEntry
		ACCESS 	not-accessible
		STATUS	mandatory
		::= { suart 1 }

	suartEntry	OBJECT-TYPE
		SYNTAX	SuartEntry
		ACCESS	not-accessible
		STATUS	mandatory
		::= { suartTable 1 }

	SuartEntry ::= SEQUENCE {
				suartIndex
					INTEGER,
				suartBaud
					INTEGER,
				suartModem
					INTEGER,
				suartIpNeighborAddress
					IpAddress,
				suartPPPActive
					INTEGER,
				suartAlignmentErrors
					Counter,
				suartOverrunErrors
					Counter
				}

	suartIndex	OBJECT-TYPE
		SYNTAX	INTEGER
		ACCESS	read-only
		STATUS	mandatory
		::= { suartEntry 1 }

	suartBaud	OBJECT-TYPE
		SYNTAX	INTEGER
		ACCESS	read-write
		STATUS	mandatory
		::= { suartEntry 2 }

	suartModem	OBJECT-TYPE
		SYNTAX	INTEGER
		ACCESS	read-write
		STATUS	mandatory
		::= { suartEntry 3 }

	suartIpNeighborAddress	OBJECT-TYPE
		SYNTAX	IpAddress
		ACCESS	read-write
		STATUS	mandatory
		::= { suartEntry 4 }

	suartPPPActive	OBJECT-TYPE
		SYNTAX	INTEGER
		ACCESS	read-write
		STATUS	mandatory
		::= { suartEntry 5 }

	suartAlignmentErrors	OBJECT-TYPE
		SYNTAX	Counter
		ACCESS	read-only
		STATUS	mandatory
		::= { suartEntry 6 }

	suartOverrunErrors	OBJECT-TYPE
		SYNTAX	Counter
		ACCESS	read-only
		STATUS	mandatory
		::= { suartEntry 7 }

	-- Filter Group

	filterMaxCount	OBJECT-TYPE
		SYNTAX	INTEGER
		ACCESS	read-only
		STATUS	mandatory
		::= { filter 1 }

	filterCurrentCount	OBJECT-TYPE
		SYNTAX	INTEGER
		ACCESS	read-only
		STATUS	mandatory
		::= { filter 2 }

	filterDeleteID	OBJECT-TYPE
		SYNTAX	INTEGER
		ACCESS	read-write
		STATUS	mandatory
		::= { filter 3 }

	filterNextID	OBJECT-TYPE
		SYNTAX	INTEGER
		ACCESS	read-only
		STATUS	mandatory
		::= { filter 4 }

	filterAddID	OBJECT-TYPE
		SYNTAX	INTEGER
		ACCESS	read-write
		STATUS	mandatory
		::= { filter 5 }

	filterAddIndex	OBJECT-TYPE
		SYNTAX	INTEGER
		ACCESS	read-write
		STATUS	mandatory
		::= { filter 6 }

	filterTable	OBJECT-TYPE
		SYNTAX	SEQUENCE OF FilterEntry
		ACCESS	not-accessible
		STATUS	mandatory
		::= { filter 7 }

	filterEntry	OBJECT-TYPE
		SYNTAX	FilterEntry
		ACCESS	not-accessible
		STATUS	mandatory
		::= { filterTable 1 }

	FilterEntry ::= SEQUENCE {
			filterIndex
				INTEGER,
			filterID
				INTEGER,
			filterPortNo
				INTEGER,
			filterComboType
				INTEGER,
			filterFlags
				INTEGER,
			filterframe
				INTEGER,
			filterSource
				INTEGER,
			filterSourceEnd
				OCTET STRING,
			filterDest
				OCTET STRING,
			filterDestEnd
				OCTET STRING,
			filterSourceMask
				OCTET STRING,
			filterDestMask
				OCTET STRING,
			filterSrcLan
				INTEGER,
			filterOffset
				INTEGER,
			filterField
				OCTET STRING,
			filterMask
				OCTET STRING,
			filterThreshold
				INTEGER,
			filterThreshTime
				INTEGER,
			filterThreshFlag
				INTEGER,
			filterPktCnts
				Counter,
			filterLastSrc
				OCTET STRING,
			filterFast
				INTEGER
			}

	filterIndex	OBJECT-TYPE
		SYNTAX	INTEGER
		ACCESS	read-only
		STATUS	mandatory
		::= { filterEntry 1 }

	filterID	OBJECT-TYPE
		SYNTAX	INTEGER
		ACCESS	read-only
		STATUS	mandatory
		::= { filterEntry 2 }

	filterPortNo	OBJECT-TYPE
		SYNTAX	INTEGER
		ACCESS	read-write
		STATUS	mandatory
		::= { filterEntry 3 }

	filterComboType	OBJECT-TYPE
		SYNTAX	INTEGER
		ACCESS	read-write
		STATUS	mandatory
		::= { filterEntry 4 }

	filterFlags	OBJECT-TYPE
		SYNTAX	INTEGER
		ACCESS	read-write
		STATUS	mandatory
		::= { filterEntry 5 }

	filterFrame	OBJECT-TYPE
		SYNTAX	INTEGER
		ACCESS	read-write
		STATUS	mandatory
		::= { filterEntry 6 }

	filterSource	OBJECT-TYPE
		SYNTAX	OCTET STRING
		ACCESS	read-write
		STATUS	mandatory
		::= { filterEntry 7 }

	filterSourceEnd	OBJECT-TYPE
		SYNTAX	OCTET STRING
		ACCESS	read-write
		STATUS	mandatory
		::= { filterEntry 8 }

	filterDest	OBJECT-TYPE
		SYNTAX	OCTET STRING
		ACCESS	read-write
		STATUS	mandatory
		::= { filterEntry 9 }

	filterDestEnd	OBJECT-TYPE
		SYNTAX	OCTET STRING
		ACCESS	read-write
		STATUS	mandatory
		::= { filterEntry 10 }

	filterSourceMask	OBJECT-TYPE
		SYNTAX	OCTET STRING
		ACCESS	read-write
		STATUS	mandatory
		::= { filterEntry 11 }

	filterDestMask	OBJECT-TYPE
		SYNTAX	OCTET STRING
		ACCESS	read-write
		STATUS	mandatory
		::= { filterEntry 12 }

	filterSrcLan	OBJECT-TYPE
		SYNTAX	INTEGER
		ACCESS	read-write
		STATUS	mandatory
		::= { filterEntry 13 }

	filterOffset	OBJECT-TYPE
		SYNTAX	INTEGER
		ACCESS	read-write
		STATUS	mandatory
		::= { filterEntry 14 }

	filterField	OBJECT-TYPE
		SYNTAX	OCTET STRING
		ACCESS	read-write
		STATUS	mandatory
		::= { filterEntry 15 }

	filterMask	OBJECT-TYPE
		SYNTAX	OCTET STRING
		ACCESS	read-write
		STATUS	mandatory
		::= { filterEntry 16 }

	filterThreshold	OBJECT-TYPE
		SYNTAX	INTEGER
		ACCESS	read-write
		STATUS	mandatory
		::= { filterEntry 17 }

	filterThreshTime	OBJECT-TYPE
		SYNTAX	INTEGER
		ACCESS	read-write
		STATUS	mandatory
		::= { filterEntry 18 }

	filterThreshFlag	OBJECT-TYPE
		SYNTAX	INTEGER
		ACCESS	read-only
		STATUS	mandatory
		::= { filterEntry 19 }

	filterPktCnts	OBJECT-TYPE
		SYNTAX	Counter
		ACCESS	read-only
		STATUS	mandatory
		::= { filterEntry 20 }

	filterLastSrc	OBJECT-TYPE
		SYNTAX	OCTET STRING
		ACCESS	read-only
		STATUS	mandatory
		::= { filterEntry 21 }

	filterFast	OBJECT-TYPE
		SYNTAX	INTEGER
		ACCESS	read-only
		STATUS	mandatory
		::= { filterEntry 22 }

	-- Change Reboot Characteristics Command Group

	rebootFddiBuff	OBJECT-TYPE
		SYNTAX	INTEGER
		ACCESS	read-write
		STATUS	mandatory
		::= { reboot 1 }

	rebootSlotTable	OBJECT-TYPE
		SYNTAX	SEQUENCE OF RebootEntry
		ACCESS	not-accessible
		STATUS	mandatory
		::= { reboot 2 }

	rebootEntry	OBJECT-TYPE
		SYNTAX	RebootEntry
		ACCESS	not-accessible
		STATUS	mandatory
		::= { rebootSlotTable 1 }

	RebootEntry ::= SEQUENCE {
			rebootIndex
				INTEGER,
			rebootType
				INTEGER,
			rebootUseMod
				INTEGER,
			rebootPortType
				OCTET STRING
			}
	rebootIndex	OBJECT-TYPE
		SYNTAX	INTEGER
		ACCESS	read-only
		STATUS	mandatory
		::= { rebootEntry 1 }

	rebootType	OBJECT-TYPE
		SYNTAX	INTEGER
		ACCESS	read-write
		STATUS	mandatory
		::= { rebootEntry 2 }

	rebootUseMod	OBJECT-TYPE
		SYNTAX	INTEGER
		ACCESS	read-write
		STATUS	mandatory
		::= { rebootEntry 3 }

	rebootPortType	OBJECT-TYPE
		SYNTAX	OCTET STRING
		ACCESS	read-write
		STATUS	mandatory
		::= { rebootEntry 4 }

	-- Debug Command Group

	debugStringID	OBJECT-TYPE
		SYNTAX	INTEGER
		ACCESS	read-only
		STATUS	mandatory
		::= { debug 1 }

	debugString	OBJECT-TYPE
		SYNTAX	OCTET STRING
		ACCESS	read-only
		STATUS	mandatory
		::= { debug 2 }

	debugTable	OBJECT-TYPE
		SYNTAX	SEQUENCE OF DebugEntry
		ACCESS	not-accessible
		STATUS	mandatory
		::= { debug 3 }

	debugEntry	OBJECT-TYPE
		SYNTAX	DebugEntry
		ACCESS	not-accessible
		STATUS	mandatory
		::= { debugTable 1 }

	DebugEntry ::= SEQUENCE {
			debugIndex
				INTEGER,
			debugOperation
				INTEGER,
			debugBase
				INTEGER,
			debugLength
				INTEGER,
			debugData
				OCTET STRING
			}

	debugIndex	OBJECT-TYPE
		SYNTAX	INTEGER
		ACCESS	read-only
		STATUS	mandatory
		::= { debugEntry 1 }

	debugOperation	OBJECT-TYPE
		SYNTAX	INTEGER
		ACCESS	read-write
		STATUS	mandatory
		::= { debugEntry 2 }

	debugBase	OBJECT-TYPE
		SYNTAX	INTEGER
		ACCESS	read-write
		STATUS	mandatory
		::= { debugEntry 3 }

	debugLength	OBJECT-TYPE
		SYNTAX	INTEGER
		ACCESS	read-write
		STATUS	mandatory
		::= { debugEntry 4 }

	debugData	OBJECT-TYPE
		SYNTAX	OCTET STRING
		ACCESS	read-write
		STATUS	mandatory
		::= { debugEntry 5 }

	-- Loopback Comand Group

	lpbkTable	OBJECT-TYPE
		SYNTAX	SEQUENCE OF LpbkEntry
		ACCESS	not-accessible
		STATUS	mandatory
		::= { lpbk 1 }

	lpbkEntry	OBJECT-TYPE
		SYNTAX	LpbkEntry
		ACCESS	not-accessible
		STATUS	mandatory
		::= { lpbkTable 1 }

	LpbkEntry ::= SEQUENCE {
			lpbkIndex
				INTEGER,
			lpbkOperation
				INTEGER,
			lpbkDestAddr
				OCTET STRING,
			lpbkPktNum
				INTEGER,
			lpbkInterval
				TimeTicks,
			lpbkPktLength
				INTEGER,
			lpbkINcrements
				INTEGER,
			lpbkGoods
				Counter,
			lpbkErrorNoReceives
				Counter,
			lpbkErrorBadReceives
				Counter,
			lpbkErrorSize
				INTEGER,
			lpbkErrorSent
				OCTET STRING,
			lpbkErrorReceived
				OCTET STRING,
			lpbkErrorOffset
				INTEGER
			}

	lpbkIndex	OBJECT-TYPE
		SYNTAX	INTEGER
		ACCESS	read-only
		STATUS	mandatory
		::= { lpbkEntry 1 }

	lpbkOperation	OBJECT-TYPE
		SYNTAX	INTEGER
		ACCESS	read-write
		STATUS	mandatory
		::= { lpbkEntry 2 }

	lpbkDestAddr	OBJECT-TYPE
		SYNTAX	OCTET STRING
		ACCESS	read-write
		STATUS	mandatory
		::= { lpbkEntry 3 }

	lpbkPktNum	OBJECT-TYPE
		SYNTAX	INTEGER
		ACCESS	read-write
		STATUS	mandatory
		::= { lpbkEntry 4 }

	lpbkInterval	OBJECT-TYPE
		SYNTAX	TimeTicks
		ACCESS	read-write
		STATUS	mandatory
		::= { lpbkEntry 5 }

	lpbkPktLength	OBJECT-TYPE
		SYNTAX	INTEGER
		ACCESS	read-write
		STATUS	mandatory
		::= { lpbkEntry 6 }

	lpbkIncrements	OBJECT-TYPE
		SYNTAX	INTEGER
		ACCESS	read-write
		STATUS	mandatory
		::= { lpbkEntry 7 }

	lpbkGoods	OBJECT-TYPE
		SYNTAX	Counter
		ACCESS	read-only
		STATUS	mandatory
		::= { lpbkEntry 8 }

	lpbkErrorNoReceives	OBJECT-TYPE
		SYNTAX	Counter
		ACCESS	read-only
		STATUS	mandatory
		::= { lpbkEntry 9 }

	lpbkErrorBadReceives	OBJECT-TYPE
		SYNTAX	Counter
		ACCESS	read-only
		STATUS	mandatory
		::= { lpbkEntry 10 }

	lpbkErrorSize	OBJECT-TYPE
		SYNTAX	INTEGER
		ACCESS	read-only
		STATUS	mandatory
		::= { lpbkEntry 11 }

	lpbkErrorSent	OBJECT-TYPE
		SYNTAX	OCTET STRING
		ACCESS	read-only
		STATUS	mandatory
		::= { lpbkEntry 12 }

	lpbkErrorReceived	OBJECT-TYPE
		SYNTAX	OCTET STRING
		ACCESS	read-only
		STATUS	mandatory
		::= { lpbkEntry 13 }

	lpbkErrorOffset	OBJECT-TYPE
		SYNTAX	INTEGER
		ACCESS	read-only
		STATUS	mandatory
		::= { lpbkEntry 14 }

	-- Sigma WAN Interface Group

	swanTable	OBJECT-TYPE
		SYNTAX	SEQUENCE OF SwanEntry
		ACCESS 	not-accessible
		STATUS	mandatory
		::= { swan 1 }

	swanEntry	OBJECT-TYPE
		SYNTAX	SwanEntry
		ACCESS	not-accessible
		STATUS	mandatory
		::= { swanTable 1 }

	SwanEntry ::= SEQUENCE {
				swanIndex
					INTEGER,
				swanDesiredSpeed
					INTEGER,
				swanActualSpeed
					INTEGER,
				swanIpNeighborAddress
					IpAddress,
				swanPPPActive
					INTEGER,
				swanAlignmentErrors
					Counter,
				swanOverrunErrors
					Counter,
				swanPortType
					INTEGER,
				swanLinkCost
					INTEGER,
				swanMeshState
					INTEGER,
				swanLinkSubnet
					OCTET STRING,
				swanLinkBridge
					OCTET STRING,
				swanLinkPort
					INTEGER,
				swanNegotiate
					INTEGER
				}

	swanIndex	OBJECT-TYPE
		SYNTAX	INTEGER
		ACCESS	read-only
		STATUS	mandatory
		::= { swanEntry 1 }

	swanDesiredSpeed	OBJECT-TYPE
		SYNTAX	INTEGER
		ACCESS	read-write
		STATUS	mandatory
		::= { swanEntry 2 }

	swanActualSpeed	OBJECT-TYPE
		SYNTAX	INTEGER
		ACCESS	read-only
		STATUS	mandatory
		::= { swanEntry 3 }

	swanIpNeighborAddress	OBJECT-TYPE
		SYNTAX	IpAddress
		ACCESS	read-write
		STATUS	mandatory
		::= { swanEntry 4 }

	swanPPPActive	OBJECT-TYPE
		SYNTAX	INTEGER
		ACCESS	read-write
		STATUS	mandatory
		::= { swanEntry 5 }

	swanAlignmentErrors	OBJECT-TYPE
		SYNTAX	Counter
		ACCESS	read-only
		STATUS	mandatory
		::= { swanEntry 6 }

	swanOverrunErrors	OBJECT-TYPE
		SYNTAX	Counter
		ACCESS	read-only
		STATUS	mandatory
		::= { swanEntry 7 }

	swanPortType	OBJECT-TYPE
		SYNTAX	INTEGER
		ACCESS	read-only
		STATUS	mandatory
		::= { swanEntry 8 }

	swanLinkCost	OBJECT-TYPE
		SYNTAX	INTEGER
		ACCESS	read-only
		STATUS	mandatory
		::= { swanEntry 9 }

	swanMeshState	OBJECT-TYPE
		SYNTAX	INTEGER
		ACCESS	read-only
		STATUS	mandatory
		::= { swanEntry 10 }

	swanLinkSubnet	OBJECT-TYPE
		SYNTAX	OCTET STRING
		ACCESS	read-only
		STATUS	mandatory
		::= { swanEntry 11 }

	swanLinkBridge	OBJECT-TYPE
		SYNTAX	OCTET STRING
		ACCESS	read-only
		STATUS	mandatory
		::= { swanEntry 12 }

	swanLinkPort	OBJECT-TYPE
		SYNTAX	INTEGER
		ACCESS	read-only
		STATUS	mandatory
		::= { swanEntry 13 }

	swanNegotiate	OBJECT-TYPE
		SYNTAX	INTEGER
		ACCESS	read-write
		STATUS	mandatory
		::= { swanEntry 14 }

  END
