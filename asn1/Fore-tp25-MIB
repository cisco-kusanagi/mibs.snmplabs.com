-- 
-- Copyright 1999 by Fore Systems, Inc. 
-- Converted to SMIv2 rfc 2578,2579,2580 - STD 58
--
-- Copyright 1994 by Fore Systems, Inc.

Fore-tp25-MIB DEFINITIONS ::= BEGIN

IMPORTS
	Integer32, Counter32,
	OBJECT-TYPE,
	MODULE-IDENTITY				FROM SNMPv2-SMI
	asx					FROM Fore-Common-MIB;
	
------------------------------------------------------------------------
-- The implementation of the foreTP25 tables is mandatory
-- for all switches that have 25.6Mbps UTP/STP port module.

foreTP25Module  MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "
	      The foreTP25 Module supports all switchs that have
	      the 25.6Mbps UTP/STP port module."
    ::= { asx 9 }

tp25ConfGroup		OBJECT IDENTIFIER ::= { foreTP25Module 1 }
tp25StatsGroup		OBJECT IDENTIFIER ::= { foreTP25Module 2 }


------------------------------------------------------------------------
-- The TP25 configuration Group

tp25ConfTable OBJECT-TYPE
	SYNTAX	SEQUENCE OF Tp25ConfEntry
	MAX-ACCESS	not-accessible
	STATUS	current
	DESCRIPTION
		"A table of TP25(25.6Mbps UTP/STP switch port configuration 
		 information."
	::= { tp25ConfGroup 1 }

tp25ConfEntry OBJECT-TYPE
	SYNTAX	Tp25ConfEntry
	MAX-ACCESS	not-accessible
	STATUS	current
	DESCRIPTION
		"A table entry containing TP25 configuration information
		 for each port."
	INDEX	{ tp25ConfBoard, tp25ConfModule, tp25ConfPort }
	::= { tp25ConfTable 1 }

Tp25ConfEntry ::=
	SEQUENCE {
		tp25ConfBoard		Integer32,
		tp25ConfModule		Integer32,
		tp25ConfPort		Integer32,
		tp25MediaType		INTEGER,
		tp25LoopbackConfig	INTEGER,
		tp25RxTiming		INTEGER
	}		

tp25ConfBoard OBJECT-TYPE
	SYNTAX	Integer32
	MAX-ACCESS	read-only
	STATUS	current
	DESCRIPTION
		"The index of this port's switch board."
	::= { tp25ConfEntry 1 }

tp25ConfModule OBJECT-TYPE
	SYNTAX	Integer32
	MAX-ACCESS	read-only
	STATUS	current
	DESCRIPTION
		"The network module of this port."
	::= { tp25ConfEntry 2 }

tp25ConfPort OBJECT-TYPE
	SYNTAX	Integer32
	MAX-ACCESS	read-only
	STATUS	current
	DESCRIPTION
		"The number of this port."
	::= { tp25ConfEntry 3 }

tp25MediaType OBJECT-TYPE
	SYNTAX	INTEGER {
		tp25UTP (1),
		tp25STP (2),
		tp25FTP (3)
		}
	MAX-ACCESS	read-only
	STATUS	current
	DESCRIPTION
		"This variable represents the type of the physical medium
	 	 connected to the TP25 interface:
		tp25UTP (1) means physical media is UTP  
		tp25STP (2) means physical media is STP
		tp25FTP (3) means physical media is FTP."
	::= { tp25ConfEntry 4 }

tp25LoopbackConfig OBJECT-TYPE
	SYNTAX	INTEGER {
		tp25NoLoop (1), 
		tp25DiagLoop (2),
		tp25LineLoop (3)
		}
	MAX-ACCESS	read-write
	STATUS	current
	DESCRIPTION
		"This variable represents the loopback configuration of the
		  TP25 interface.
		tp25NoLoop (1) means that the interface is not in a loopback
 	    	  state.
		tp25DiagLoop (2) means that the transmit data stream is looped
		  back to the receiver.
		tp25LineLoop (3) also known as remote loopback, in this state
	          received data is transfered to upstream system as well as
	          looped back to the transmitter."
	DEFVAL { tp25NoLoop }
	::= { tp25ConfEntry 5 }

tp25RxTiming OBJECT-TYPE
	SYNTAX	INTEGER {
		tp25NoTimingPresent (1),
		tp25TimingPresent (2)
		}
	MAX-ACCESS	read-only
	STATUS	current
	DESCRIPTION
		"This variable represents the type of the physical medium
	 	 connected to the TP25 interface:
		tp25NoTimingPresent (1) means port is not receiving sync pulses.
		tp25TimingPresent (2) means port is receiving sync pulses."
	::= { tp25ConfEntry 6 }

------------------------------------------------------------------------
-- The TP25 Statistics Group

tp25ErrorTable OBJECT-TYPE
	SYNTAX	SEQUENCE OF Tp25ErrorEntry
	MAX-ACCESS	not-accessible
	STATUS	current
	DESCRIPTION
		"A table of TP25 error counters."
	::= { tp25StatsGroup 1 }

tp25ErrorEntry OBJECT-TYPE
	SYNTAX	Tp25ErrorEntry
	MAX-ACCESS	not-accessible
	STATUS	current
	DESCRIPTION
		"A table entry containing TP25 error counters."
	INDEX	{ tp25ErrorBoard, tp25ErrorModule, tp25ErrorPort }
	::= { tp25ErrorTable 1 }

Tp25ErrorEntry ::=
	SEQUENCE {
		tp25ErrorBoard		Integer32,
		tp25ErrorModule		Integer32,
		tp25ErrorPort		Integer32,
		tp25ErrorSymbol		Counter32
	}

tp25ErrorBoard OBJECT-TYPE
	SYNTAX	Integer32
	MAX-ACCESS	read-only
	STATUS	current
	DESCRIPTION
		"The index of this port's switch board."
	::= { tp25ErrorEntry 1 }

tp25ErrorModule OBJECT-TYPE
	SYNTAX	Integer32
	MAX-ACCESS	read-only
	STATUS	current
	DESCRIPTION
		"The network module of this port."
	::= { tp25ErrorEntry 2 }

tp25ErrorPort OBJECT-TYPE
	SYNTAX	Integer32
	MAX-ACCESS	read-only
	STATUS	current
	DESCRIPTION
		"The number of this port."
	::= { tp25ErrorEntry 3 }

tp25ErrorSymbol OBJECT-TYPE
	SYNTAX	Counter32
	MAX-ACCESS	read-only
	STATUS	current
	DESCRIPTION
		"The number of all undefined 5 bit symbols received."
	::= { tp25ErrorEntry 4 }

------------------------------------------------------------------------

tp25AtmTable OBJECT-TYPE
	SYNTAX	SEQUENCE OF Tp25AtmEntry
	MAX-ACCESS	not-accessible
	STATUS	current
	DESCRIPTION
		"A table of TP25 ATM statistics information."
	::= { tp25StatsGroup 2 }

tp25AtmEntry OBJECT-TYPE
	SYNTAX	Tp25AtmEntry
	MAX-ACCESS	not-accessible
	STATUS	current
	DESCRIPTION
		"A table entry containing TP25 ATM statistics information."
	INDEX	{ tp25AtmBoard, tp25AtmModule, tp25AtmPort }
	::= { tp25AtmTable 1 }

Tp25AtmEntry ::=
	SEQUENCE {
		tp25AtmBoard		Integer32,
		tp25AtmModule		Integer32,
		tp25AtmPort		Integer32,
		tp25AtmHCSs		Counter32,
		tp25AtmRxCells		Counter32,
		tp25AtmTxCells		Counter32
	}

tp25AtmBoard OBJECT-TYPE
	SYNTAX	Integer32
	MAX-ACCESS	read-only
	STATUS	current
	DESCRIPTION
		"The index of this port's switch board."
	::= { tp25AtmEntry 1 }

tp25AtmModule OBJECT-TYPE
	SYNTAX	Integer32
	MAX-ACCESS	read-only
	STATUS	current
	DESCRIPTION
		"The network module of this port."
	::= { tp25AtmEntry 2 }

tp25AtmPort OBJECT-TYPE
	SYNTAX	Integer32
	MAX-ACCESS	read-only
	STATUS	current
	DESCRIPTION
		"The number of this port."
	::= { tp25AtmEntry 3 }

tp25AtmHCSs OBJECT-TYPE
	SYNTAX	Counter32
	MAX-ACCESS	read-only
	STATUS	current
	DESCRIPTION
		"Number of header check sequence (HCS) error events.
		 The HCS is a CRC-8 calculation over the first 4 octets
		 of the ATM cell header."
	::= { tp25AtmEntry 4 }

tp25AtmRxCells OBJECT-TYPE
	SYNTAX	Counter32
	MAX-ACCESS	read-only
	STATUS	current
	DESCRIPTION
		"Number of ATM cells that were received."
	::= { tp25AtmEntry 5 }

tp25AtmTxCells OBJECT-TYPE
	SYNTAX	Counter32
	MAX-ACCESS	read-only
	STATUS	current
	DESCRIPTION
		"Number of non-null ATM cells that were transmitted."
	::= { tp25AtmEntry 6 }

END
