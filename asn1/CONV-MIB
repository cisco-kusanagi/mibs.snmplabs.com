-- Definition of the cx1000 LAN Convergence Group
-- April 8, 1994
-- Draft 2
-- Fred Mruzek
-- The Convergence element is used to convert the LAN connectionless 
-- data to WAN Connection Oriented data stream.
-- The Conv. is divided into three logical subcomponents:
-- Convergence Attributes Table which controls the convergence 
-- attributes such as connection setup, compression etc.
-- WAN interface table which defines attributes of used WAN service
-- Statistics Table - mostly error statistics
-- The tables are now indexed by the convergence port instead of ifIndex
-- which should be a simplification. 
-- The usual interface statistics on the interface are again covered by the 
-- cxInterfaces group.   

-- Modifications: Hien Quang Le    June 7, 1994
--
--    cxFwkServiceName, cxFwkServiceCardId, cxFwkServiceSapId: changed 
--         from read-write to read-only objects
--    cxFwkServiceVcAttributes: removed
--    cxFwkConnectOptions:      removed
--    cxConvRowStatus:                  added
--         cxFwkCircuitRowStatus:       added
--    cxFwkCircuitState:        replaced closing(4) by openFailed(4)
--
-- Modifications: Hien Quang Le    August 10, 1994
--
--    Modified descriptions of cxConvTearDownTimer,cxFwkServiceType,
--         cxFwkServiceCircuitMdu, cxFwkServiceCost
--    Modified cxFwkServiceType object values to "notSpecified" & 
--   "frameRelay" only
--      FM - revision 1.01
--    Setup and TearDown Timers were removed
--     cxConvEncapsulation was removed - 1294 is always on
--     cxCompression was removed - it is not available
--     cxCompression was reinstated 

-- Modifications: Claude Rocray    April 1, 1996
--
--    cxConvCompCompatibility was added
--    cxFwkServiceRouteRef was added
--    cleaned up unused objects (cxFwkServiceVcAttributes, 
--    cxFwkConnectOptions).
--    removed reference to software header files.
--

CONV-MIB                
DEFINITIONS ::= BEGIN

IMPORTS 
   OBJECT-TYPE    FROM RFC-1212
   Counter        FROM RFC1155-SMI
   cxConv, Alias  FROM CXProduct-SMI;


-- Convergence Attributes Table 
-------------------------------
-- Carries basic information on the lifespan and characteristics 
-- of a convergence element

cxConvTable  OBJECT-TYPE
   SYNTAX  SEQUENCE OF CxConvEntry
    ACCESS  not-accessible
    STATUS  mandatory
    DESCRIPTION 
"Provides configuration information and attributes of each of the module's 
convergence ports.

The table contains two rows of default entries; some of these entries can be 
modified. If required, you can add additional entries."
    ::= { cxConv 1 }

cxConvEntry  OBJECT-TYPE
   SYNTAX  CxConvEntry
    ACCESS  not-accessible
    STATUS  mandatory
	  		 DESCRIPTION ""
    INDEX   { cxConvPort }
    ::= { cxConvTable 1 }

CxConvEntry
   ::= SEQUENCE {
      cxConvPort
         INTEGER,
      cxConvPortAlias
         Alias,
      cxConvRowStatus
         INTEGER,
      cxConvIfIndex
         INTEGER,
      cxConvState
         INTEGER,
      cxConvCompression
         INTEGER,
      cxConvCompCompatibility
         INTEGER
   }


cxConvPort  OBJECT-TYPE
    SYNTAX  INTEGER (1..65535)
    ACCESS  read-only
    STATUS  mandatory
    DESCRIPTION 
"Identifies the number of a specific convergence port. This number acts as an 
index to this and the cxFwkCircuitTable.

Range of Values: 1 - 32 

Default Value: None

Note:
The system defines two default entries; their respective values 
are 1 and 2."
    ::= { cxConvEntry 1 }

cxConvPortAlias  OBJECT-TYPE
    SYNTAX  Alias
    ACCESS  read-write
    STATUS  mandatory
    DESCRIPTION 
"Determines a textual name (alias), assigned by the network administrator, 
which identifies a particular convergence port. The alias is used by the 
routing and bridging protocols when they bind to this port.

Range of Values: 0-16 alphanumeric characters. (Note that the first 
character must be a letter, and spaces are not allowed). 

Default Value: none

Note: The system defines two default entries; their respective 
values are CNV_PORT1 and CNV_PORT2.

Configuration Changed: administrative"
    ::= { cxConvEntry 2 }

cxConvRowStatus  OBJECT-TYPE
   SYNTAX  INTEGER {
            invalid (1),
            valid   (2)
         }
   ACCESS  read-write
   STATUS  mandatory
   DESCRIPTION
"Determines the status of the objects in a table row.

Options:
valid (1): values are enabled

invalid (2) row is flagged, after next reset values will be disabled and the 
row will be deleted from the table).

Default Value: valid

Configuration Changed:  administrative"
    DEFVAL { valid }
    ::= { cxConvEntry 3 }

cxConvIfIndex  OBJECT-TYPE
   SYNTAX  INTEGER
    ACCESS  read-only
    STATUS  mandatory
    DESCRIPTION
"Identifies the table row that contains configuration or monitoring objects 
for a specific type of physical interface.

Range of Values: 1 to the number of entries in the interface table. 

Default Value: None"
    ::= { cxConvEntry 4 }

cxConvState  OBJECT-TYPE
   
SYNTAX  INTEGER {
             on(1),
             off(2)
      } 
    ACCESS  read-write
    STATUS  mandatory
    DESCRIPTION
"Determines whether the convergence port is active (on).  When the object is 
set to on, transmission can begin over the port; when the object is set to 
off transmission will be stopped.

Options:
on (1)

off (2)

Default Value: on

Configuration Changed: administrative"
    DEFVAL { on }
    ::= { cxConvEntry 5 }

cxConvCompression  OBJECT-TYPE
   SYNTAX  INTEGER
    ACCESS  read-write
    STATUS  mandatory
    DESCRIPTION
"Determines whether the port is linked to a compression port. If the port is  
not linked to a compression port the value is 0. If the port is linked to a 
compression port, then the object identifies the compression port number 
(CompressPortNumber on CompressTable.) 

Range of Values: 0 to 64.

Default Value: 0.

Configuration Changed: administrative"
    ::= { cxConvEntry 6 }

cxConvCompCompatibility  OBJECT-TYPE
   SYNTAX  INTEGER {
            compatibleMemotec (1),
            compatibleACC (2)
         }
    ACCESS  read-write
    STATUS  mandatory
    DESCRIPTION
"Determines the data compression synchronization algorithm. 

When the CX1000 interfaces with Memotec models CL2800, CL5050, CL5200, 
CL5300, or CL5500, this object must be set to compatibleACC; when it 
interfaces with any other product the object must be set to 
compatibleMemotec.

The CX900 must always be set to 
compatibleMemotec.

Options:
compatibleMemotec (1)

compatibleACC (2)

Default Value: compatibleMemotec (1)

Configuration Changed:  administrative "
    ::= { cxConvEntry 7 }


-- Convergence WAN circuit table
-----------------------------------
-- contains description of WAN circuits used by the convergence element
-- the attributes such as explicit address can be filled by the MANAGER
-- or can be learned via the directory services of the FRAMEWORK

cxFwkCircuitTable  OBJECT-TYPE
   SYNTAX  SEQUENCE OF CxFwkCircuitEntry
   ACCESS  not-accessible
   STATUS  mandatory
   DESCRIPTION
"Provides the attributes of the WAN service(s) used and the circuits 
established by each convergence port. It also identifies statistical 
information about the WAN circuits.

The table contains two rows of default entries; some of these entries can be 
modified. If required, you can add additional entries."
   ::= { cxConv 2 }

cxFwkCircuitEntry  OBJECT-TYPE
   SYNTAX  CxFwkCircuitEntry
   ACCESS  not-accessible
   STATUS  mandatory
	  		 DESCRIPTION ""
   INDEX   { cxFwkCircuitPort }
   ::= { cxFwkCircuitTable 1 }

CxFwkCircuitEntry
   ::= SEQUENCE {
      cxFwkCircuitPort
         INTEGER,
      cxFwkCircuitState
         INTEGER,
      cxFwkCircuitRowStatus
         INTEGER,
         
      -- service identification or selection

      cxFwkServiceType            -- PSAP, field2
         INTEGER,
      cxFwkServiceProtocol      
         INTEGER,
      cxFwkServiceName
         OCTET STRING (SIZE (16)),

      -- destination WAN address 

      cxFwkDestAddress
         OCTET STRING (SIZE (20)),
      cxFwkDestAlias
         Alias,

      cxFwkServiceCircuitMdu
         INTEGER,
      cxFwkServiceCost
         INTEGER,

      -- service provider location within the system

      cxFwkServiceCardId      -- PSAP, field1
         INTEGER,
      cxFwkServiceSapId         -- PSAP, field3
         INTEGER,

      -- service provider multiplexing information
      
       cxFwkServiceRouteRef
           INTEGER,

      -- WAN Interface error stats.

       cxFwkStatsInternalErrors
            Counter,
       cxFwkStatsRegistrationErrors
           Counter,
       cxFwkStatsQueryErrors
           Counter,
       cxFwkStatsOpenErrors
           Counter,
       cxFwkStatsResets
           Counter

        }


cxFwkCircuitPort  OBJECT-TYPE
   SYNTAX  INTEGER
   ACCESS  read-only
   STATUS  mandatory
   DESCRIPTION
"Identifies the convergence port by a unique index number. This number acts 
as an index for this and the cxConvTable.

Range of Values: 1 to the number of convergence ports

Default Values: none

Note that the system defines two default entries; their respective values 
are 1 and 2."
   ::= { cxFwkCircuitEntry 1 }

cxFwkCircuitState  OBJECT-TYPE
   SYNTAX  INTEGER {
         idle(256),
         opened(1),
         closed(2),
         opening(3),
         openFailed(4)
          }
   ACCESS  read-only
    STATUS  mandatory
    DESCRIPTION
"Identifies the current state of the circuit between the convergence port and 
the destination port.

Options:
opened (1): The circuit is active

closed (2): The circuit is not active

opening (3): The circuit is being activated

openFailed (4): The circuit could not be opened. 

idle (256): There is no activity over the circuit.

Default Value: None

Configuration Changed: administrative"
   ::= { cxFwkCircuitEntry 2 }


cxFwkCircuitRowStatus OBJECT-TYPE
   SYNTAX  INTEGER {
            invalid (1),
            valid   (2)
         }
   ACCESS  read-write
   STATUS  mandatory
   DESCRIPTION
"Determines the status of the objects in a table row.

Options:

invalid (1): row is flagged, after next reset the values will be disabled and
the row will be deleted from the table.

valid (2): values are enabled

Default Value: valid

Configuration Changed:  administrative"
    DEFVAL { valid }
   ::= { cxFwkCircuitEntry 3 }

cxFwkServiceType  OBJECT-TYPE
   SYNTAX  INTEGER {
    frameRelay (1),
    notSpecified (256)
         }
   ACCESS  read-write
    STATUS  mandatory
    DESCRIPTION 
"Determines the WAN service used. At the present time, frame relay is the 
only WAN service available.

Options:
frameRelay (1)

notSpecified (256)

Default Value: frameRelay (1)

Configuration Changed:  administrative "
    ::= { cxFwkCircuitEntry 4 }

cxFwkServiceProtocol  OBJECT-TYPE
   SYNTAX  INTEGER {
            cls(1),
            pvc(2),
            svc(3),
            char(4)
              }
   ACCESS  read-write
    STATUS  mandatory
    DESCRIPTION
"Identifies the type of connection the WAN service uses. At the present time, 
Permanent Virtual Circuit (PVC) is the only type of connection available.

Options
cls (1)

pvc (2)

svc (3)

char (4)

Default Value: pvc (2)

Configuration Changed:  administrative "
   REFERENCE "FRAMEWORK REQ. SPEC."                
    ::= { cxFwkCircuitEntry 5 }

cxFwkServiceName  OBJECT-TYPE
   SYNTAX  OCTET STRING (SIZE (16))
    ACCESS  read-only
    STATUS  mandatory
    DESCRIPTION
"Identifies the textual name of the WAN service used. The system updates the 
name automatically when it selects a WAN service for transmission. 
Frame Relay is the only WAN service currently available.

Range of Values: 1 to 16 alphanumeric characters

Default Value: None" 
    
::= { cxFwkCircuitEntry 6 }


cxFwkDestAddress  OBJECT-TYPE
   SYNTAX  OCTET STRING (SIZE (20))
    ACCESS  read-only
    STATUS  mandatory
    DESCRIPTION
"Identifies the address used to reach the WAN service provider.

Range of Values: 20 octets, each octet ranging from 00 to FF.

Default Value:  None"
    ::= { cxFwkCircuitEntry 7 }


cxFwkDestAlias  OBJECT-TYPE
   SYNTAX  Alias
    ACCESS  read-write
    STATUS  mandatory
    DESCRIPTION
"Determines a unique textual name (assigned by a network administrator) 
identifying the destination frame relay circuit. 

Range of Values: 0-16 alphanumeric characters. (Note that the first character 
must be a letter; spaces are not allowed).

Default Value: none

Note: The system defines two default entries; their respective values are 
PRIMARY_DEST and BACKUP_DEST. 
                   
Related Parameter:
The name must equal a destination alias defined using the 
object frpCircuitAlias in the FrameRelayCicuitCfgTable.

Configuration Changed:  administrative  "
    ::= { cxFwkCircuitEntry 8 }

cxFwkServiceCircuitMdu  OBJECT-TYPE
   SYNTAX  INTEGER (0..8192)
    ACCESS  read-write
    STATUS  mandatory
    DESCRIPTION
"Determines the maximum size of the data unit (in octets) that may be 
transmitted over the WAN circuit.

Range of Values: 0 to 8192

Default Value: 1600

Configuration Changed:  administrative"
   REFERENCE "FRAMEWORK REQ. SPEC." 
   DEFVAL { 1600 }               
    ::= { cxFwkCircuitEntry 9 }


cxFwkServiceCost  OBJECT-TYPE
   SYNTAX  INTEGER (0..1000000)
    ACCESS  read-write
    STATUS  mandatory
    DESCRIPTION
"Determines the cost of the WAN service. Cost is typically inverse to the 
throughput. The smaller the number, the greater the throughput on the port. 
A value of 0 indicates that the cost is not known.

Range of Values: 0 to 1000000 

Default Value: 0

Configuration Changed:  administrative "
   REFERENCE "FRAMEWORK REQ. SPEC."                
   DEFVAL { 0 }
    ::= { cxFwkCircuitEntry 10 }

cxFwkServiceCardId  OBJECT-TYPE
   SYNTAX  INTEGER (1..16)
    ACCESS  read-only
    STATUS  mandatory
    DESCRIPTION
"Identifies the number of the chassis slot that contains the WAN service 
(FR600). This object is not applicable in the CX900 architecture.

Range of Values: 1-16

Default Value: None"
    ::= { cxFwkCircuitEntry 11 }

cxFwkServiceSapId  OBJECT-TYPE
   SYNTAX  INTEGER 
    ACCESS  read-only
    STATUS  mandatory
    DESCRIPTION
"Identifies the ID of the WAN service's SAP (service access point) that the 
convergence port uses to establish the circuit. This object is not used if 
there is only one SAP on the WAN service.

Range of Values:  0 to 65535 


Default Value: None"
   ::= { cxFwkCircuitEntry 12 }

cxFwkServiceRouteRef OBJECT-TYPE
   SYNTAX  INTEGER (0..255)
    ACCESS  read-write
    STATUS  mandatory
    DESCRIPTION
"Determines a routing reference number. This number provides a reference for 
WAN service providers that offer multiplexing (it is required in situations 
where multiple convergence ports are multiplexed over the same DLCI).

If the WAN provider doesn't provide multiplexing, then the object should be 
set to 0. 

If the WAN provider does provide multiplexing, a value of 0 instructs the 
provider not to multiplex other LAN traffic over the same circuit and the 
frame must be sent as received (regular RFC 1490 encapsulation in the case of 
frame relay service provider). If the value is set to other than 0 (1-255), 
the provider will use this number as a reference in its multiplexing 
encapsulation header. Each reference within the same WAN circuit must be 
unique.

Range of Values: 0-255

Default Value: None

Configuration Changed:  administrative "
    ::= { cxFwkCircuitEntry 13 }

--   Fwk Error Statistics
--------------------------

cxFwkStatsInternalErrors OBJECT-TYPE
   SYNTAX  Counter
    ACCESS  read-only
    STATUS  mandatory
    DESCRIPTION
"Identifies the number of internal errors recognized by the convergence port. 


Range of Values: 1 to 4, 294, 967, 295

Default Value: 0"
    ::= { cxFwkCircuitEntry 15 }

cxFwkStatsRegistrationErrors OBJECT-TYPE
   SYNTAX  Counter
    ACCESS  read-only
    STATUS  mandatory
    DESCRIPTION
"Identifies the number of errors that occurred when the convergence port 
attempted to register itself to the framework. 

Range of Values: 1 to 4, 294, 967, 295

Default Value: 0"
    ::= { cxFwkCircuitEntry 16 }

cxFwkStatsQueryErrors OBJECT-TYPE
   SYNTAX  Counter
    ACCESS  read-only
    STATUS  mandatory
    DESCRIPTION
"Identifies the number of times the convergence port requested a service that 
was not available. 

Range of Values: 1 to 4, 294, 967, 295

Default Value: 0"
 
   ::= { cxFwkCircuitEntry 17 }

cxFwkStatsOpenErrors OBJECT-TYPE
   SYNTAX  Counter
    ACCESS  read-only
    STATUS  mandatory
    DESCRIPTION
"Identifies the number of errors that occurred when the convergence port 
attempted to establish a connection with a WAN service. A value here may 
indicate congestion at the WAN service, or a configuration problem.

Range of Values: 1 to 4, 294, 967, 295

Default Value: 0"
    ::= { cxFwkCircuitEntry 18 }

cxFwkStatsResets OBJECT-TYPE
   SYNTAX  Counter
    ACCESS  read-only
    STATUS  mandatory
    DESCRIPTION
"Identifies the number of resets received from the WAN service. A large value 
here may signify a breakdown on the bus or the WAN circuit.

Range of Values: 1 to 4, 294, 967, 295 

Default Value: 0"
    ::= { cxFwkCircuitEntry 19 }

END
