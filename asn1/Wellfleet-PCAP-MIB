Wellfleet-PCAP-MIB DEFINITIONS ::= BEGIN

-- Created by mdl2asn version 3.1
-- Creation date: Wed Aug 30 16:46:23 EDT 1995


    IMPORTS

      Gauge
        FROM RFC1155-SMI
      OBJECT-TYPE
        FROM RFC-1212
      DisplayString
        FROM RFC1213-MIB
      wfPktCaptureGroup
        FROM Wellfleet-COMMON-MIB;


    wfPktCaptureTable OBJECT-TYPE
        SYNTAX	SEQUENCE OF WfPktCaptureEntry
        ACCESS	not-accessible
        STATUS	mandatory
        DESCRIPTION
                "PCAP line record"
        ::= { wfPktCaptureGroup 1 }

    wfPktCaptureEntry OBJECT-TYPE
        SYNTAX	WfPktCaptureEntry
        ACCESS	not-accessible
        STATUS	mandatory
        DESCRIPTION
                "An entry in the pcap table"
        INDEX	{ wfPktCaptureLineNumber }
        ::= { wfPktCaptureTable 1 }

    WfPktCaptureEntry ::= SEQUENCE {
    	    wfPktCaptureDelete
    		INTEGER,
    	    wfPktCaptureDisable
    		INTEGER,
    	    wfPktCaptureState
    		INTEGER,
    	    wfPktCaptureFname
    		DisplayString,
    	    wfPktCaptureControl
    		INTEGER,
    	    wfPktCaptureCapture
    		INTEGER,
    	    wfPktCaptureLineNumber
    		INTEGER,
    	    wfPktCaptureBufSize
    		INTEGER,
    	    wfPktCapturePktSize
    		INTEGER,
    	    wfPktCaptureDirection
    		INTEGER,
    	    wfPktCaptureCount
    		Gauge,
    	    wfPktCaptureRxTrigger
    		INTEGER,
    	    wfPktCaptureTxTrigger
    		INTEGER,
    	    wfPktCaptureRxFltr1Type
    		INTEGER,
    	    wfPktCaptureRxFltr1Offset
    		INTEGER,
    	    wfPktCaptureRxFltr1Ref
    		INTEGER,
    	    wfPktCaptureRxFltr1Size
    		INTEGER,
    	    wfPktCaptureRxFltr1Match
    		OCTET STRING,
    	    wfPktCaptureTxFltr1Type
    		INTEGER,
    	    wfPktCaptureTxFltr1Offset
    		INTEGER,
    	    wfPktCaptureTxFltr1Ref
    		INTEGER,
    	    wfPktCaptureTxFltr1Size
    		INTEGER,
    	    wfPktCaptureTxFltr1Match
    		OCTET STRING,
    	    wfPktCaptureRxFltr2Type
    		INTEGER,
    	    wfPktCaptureRxFltr2Offset
    		INTEGER,
    	    wfPktCaptureRxFltr2Ref
    		INTEGER,
    	    wfPktCaptureRxFltr2Size
    		INTEGER,
    	    wfPktCaptureRxFltr2Match
    		OCTET STRING,
    	    wfPktCaptureRxFltr2Group
    		INTEGER,
    	    wfPktCaptureTxFltr2Type
    		INTEGER,
    	    wfPktCaptureTxFltr2Offset
    		INTEGER,
    	    wfPktCaptureTxFltr2Ref
    		INTEGER,
    	    wfPktCaptureTxFltr2Size
    		INTEGER,
    	    wfPktCaptureTxFltr2Match
    		OCTET STRING,
    	    wfPktCaptureTxFltr2Group
    		INTEGER,
            wfPktCaptureAtmVpi
                INTEGER,
            wfPktCaptureAtmVci
                INTEGER
        }

    wfPktCaptureDelete OBJECT-TYPE
        SYNTAX	INTEGER {
    		    created(1),
    		    deleted(2)
    		}
        ACCESS	read-write
        STATUS	mandatory
        DESCRIPTION
                "Delete parameter, created or deleted"
        DEFVAL	{ created }
        ::= { wfPktCaptureEntry 1 }

    wfPktCaptureDisable OBJECT-TYPE
        SYNTAX	INTEGER {
    		    enabled(1),
    		    disabled(2)
    		}
        ACCESS	read-write
        STATUS	mandatory
        DESCRIPTION
                "Enable parameter, enabled or disabled"
        DEFVAL	{ enabled }
        ::= { wfPktCaptureEntry 2 }

    wfPktCaptureState OBJECT-TYPE
        SYNTAX	INTEGER {
    		    up(1),
    		    down(2),
    		    init(3),
    		    notpresent(4)
    		}
        ACCESS	read-only
        STATUS	mandatory
        DESCRIPTION
                "Interface Gate State"
        DEFVAL	{ notpresent }
        ::= { wfPktCaptureEntry 3 }

    wfPktCaptureFname OBJECT-TYPE
        SYNTAX	DisplayString
        ACCESS	read-only
        STATUS	mandatory
        DESCRIPTION
                "Filename used to retrieve capture buffer"
        ::= { wfPktCaptureEntry 4 }

    wfPktCaptureControl OBJECT-TYPE
        SYNTAX	INTEGER {
    		    start(1),
    		    stop(2)
    		}
        ACCESS	read-write
        STATUS	mandatory
        DESCRIPTION
                "Swapping the value in this field causes the capture
                code to do the opposite of what is set in the Capture
                field."
        DEFVAL	{ stop }
        ::= { wfPktCaptureEntry 5 }

    wfPktCaptureCapture OBJECT-TYPE
        SYNTAX	INTEGER {
    		    started(1),
    		    stopped(2)
    		}
        ACCESS	read-only
        STATUS	mandatory
        DESCRIPTION
                "Capture state, STARTed or STOPed"
        DEFVAL	{ stopped }
        ::= { wfPktCaptureEntry 6 }

    wfPktCaptureLineNumber OBJECT-TYPE
        SYNTAX	INTEGER
        ACCESS	read-only
        STATUS	mandatory
        DESCRIPTION
                "Instance ID LineNumber, filled in by capture gate"
        ::= { wfPktCaptureEntry 7 }

    wfPktCaptureBufSize OBJECT-TYPE
        SYNTAX	INTEGER
        ACCESS	read-write
        STATUS	mandatory
        DESCRIPTION
                "Size of capture buffer in 1024 byte increments"
        ::= { wfPktCaptureEntry 8 }

    wfPktCapturePktSize OBJECT-TYPE
        SYNTAX	INTEGER
        ACCESS	read-write
        STATUS	mandatory
        DESCRIPTION
                "Number of bytes to save from packet in 32 byte increments"
        ::= { wfPktCaptureEntry 9 }

    wfPktCaptureDirection OBJECT-TYPE
        SYNTAX	INTEGER {
    		    rx(1),
    		    tx(2),
    		    both(3)
    		}
        ACCESS	read-write
        STATUS	mandatory
        DESCRIPTION
                "Direction of packet flow to capture, Rx, Tx or Both"
        DEFVAL	{ rx }
        ::= { wfPktCaptureEntry 10 }

    wfPktCaptureCount OBJECT-TYPE
        SYNTAX	Gauge
        ACCESS	read-only
        STATUS	mandatory
        DESCRIPTION
                "Number of packets in capture buffer"
        ::= { wfPktCaptureEntry 11 }

    wfPktCaptureRxTrigger OBJECT-TYPE
        SYNTAX	INTEGER {
    		    full(1),
    		    match1(2),
    		    match2(3),
    		    notused(4)
    		}
        ACCESS	read-write
        STATUS	mandatory
        DESCRIPTION
                "Rx trigger, Not used, buffer full or match on filter"
        DEFVAL	{ notused }
        ::= { wfPktCaptureEntry 12 }

    wfPktCaptureTxTrigger OBJECT-TYPE
        SYNTAX	INTEGER {
    		    full(1),
    		    match1(2),
    		    match2(3),
    		    notused(4)
    		}
        ACCESS	read-write
        STATUS	mandatory
        DESCRIPTION
                "Tx trigger, Not used, buffer full or match on filter"
        DEFVAL	{ notused }
        ::= { wfPktCaptureEntry 13 }

    wfPktCaptureRxFltr1Type OBJECT-TYPE
        SYNTAX	INTEGER {
    		    capture(1),
    		    trigger(2),
    		    notused(3)
    		}
        ACCESS	read-write
        STATUS	mandatory
        DESCRIPTION
                "Rx filter 1 type, Capture, Trigger, or Not used"
        DEFVAL	{ notused }
        ::= { wfPktCaptureEntry 14 }

    wfPktCaptureRxFltr1Offset OBJECT-TYPE
        SYNTAX	INTEGER
        ACCESS	read-write
        STATUS	mandatory
        DESCRIPTION
                "Rx filter 1 offset in bytes"
        ::= { wfPktCaptureEntry 15 }

    wfPktCaptureRxFltr1Ref OBJECT-TYPE
        SYNTAX	INTEGER {
    		    mac(1),
    		    dl(2),
    		    mcast(3)
    		}
        ACCESS	read-write
        STATUS	mandatory
        DESCRIPTION
                "Rx filter 1 Reference point, MAC, DATA LINK, MULTICAST"
        DEFVAL	{ mac }
        ::= { wfPktCaptureEntry 16 }

    wfPktCaptureRxFltr1Size OBJECT-TYPE
        SYNTAX	INTEGER
        ACCESS	read-write
        STATUS	mandatory
        DESCRIPTION
                "Rx filter 1 field size to match in bytes"
        ::= { wfPktCaptureEntry 17 }

    wfPktCaptureRxFltr1Match OBJECT-TYPE
        SYNTAX	OCTET STRING
        ACCESS	read-write
        STATUS	mandatory
        DESCRIPTION
                "Rx filter 1 data to match with packet"
        ::= { wfPktCaptureEntry 18 }

    wfPktCaptureTxFltr1Type OBJECT-TYPE
        SYNTAX	INTEGER {
    		    capture(1),
    		    trigger(2),
    		    notused(3)
    		}
        ACCESS	read-write
        STATUS	mandatory
        DESCRIPTION
                "Tx filter 1 type, Capture, Trigger or Not used"
        DEFVAL	{ notused }
        ::= { wfPktCaptureEntry 19 }

    wfPktCaptureTxFltr1Offset OBJECT-TYPE
        SYNTAX	INTEGER
        ACCESS	read-write
        STATUS	mandatory
        DESCRIPTION
                "Tx filter 1 offset in bytes"
        ::= { wfPktCaptureEntry 20 }

    wfPktCaptureTxFltr1Ref OBJECT-TYPE
        SYNTAX	INTEGER {
    		    mac(1),
    		    dl(2),
    		    mcast(3)
    		}
        ACCESS	read-write
        STATUS	mandatory
        DESCRIPTION
                "Tx filter 1 Reference point, MAC, DATA LINK, MULTICAST"
        DEFVAL	{ mac }
        ::= { wfPktCaptureEntry 21 }

    wfPktCaptureTxFltr1Size OBJECT-TYPE
        SYNTAX	INTEGER
        ACCESS	read-write
        STATUS	mandatory
        DESCRIPTION
                "Tx filter 1 field size to match in bytes"
        ::= { wfPktCaptureEntry 22 }

    wfPktCaptureTxFltr1Match OBJECT-TYPE
        SYNTAX	OCTET STRING
        ACCESS	read-write
        STATUS	mandatory
        DESCRIPTION
                "Tx filter 1 data to match with packet"
        ::= { wfPktCaptureEntry 23 }

    wfPktCaptureRxFltr2Type OBJECT-TYPE
        SYNTAX	INTEGER {
    		    capture(1),
    		    trigger(2),
    		    notused(3)
    		}
        ACCESS	read-write
        STATUS	mandatory
        DESCRIPTION
                "Rx filter 2 type, Capture, Trigger or Not used"
        DEFVAL	{ notused }
        ::= { wfPktCaptureEntry 24 }

    wfPktCaptureRxFltr2Offset OBJECT-TYPE
        SYNTAX	INTEGER
        ACCESS	read-write
        STATUS	mandatory
        DESCRIPTION
                "Rx filter 2 offset in bytes"
        ::= { wfPktCaptureEntry 25 }

    wfPktCaptureRxFltr2Ref OBJECT-TYPE
        SYNTAX	INTEGER {
    		    mac(1),
    		    dl(2),
    		    mcast(3)
    		}
        ACCESS	read-write
        STATUS	mandatory
        DESCRIPTION
                "Rx filter 2 Reference point, MAC, DATA LINK, MULTICAST"
        DEFVAL	{ mac }
        ::= { wfPktCaptureEntry 26 }

    wfPktCaptureRxFltr2Size OBJECT-TYPE
        SYNTAX	INTEGER
        ACCESS	read-write
        STATUS	mandatory
        DESCRIPTION
                "Rx filter 2 field size to match in bytes"
        ::= { wfPktCaptureEntry 27 }

    wfPktCaptureRxFltr2Match OBJECT-TYPE
        SYNTAX	OCTET STRING
        ACCESS	read-write
        STATUS	mandatory
        DESCRIPTION
                "Rx filter 2 data to match with packet"
        ::= { wfPktCaptureEntry 28 }

    wfPktCaptureRxFltr2Group OBJECT-TYPE
        SYNTAX	INTEGER {
    		    or(1),
    		    and(2)
    		}
        ACCESS	read-write
        STATUS	mandatory
        DESCRIPTION
                "Rx filter 2 grouping attribute, AND or OR"
        DEFVAL	{ or }
        ::= { wfPktCaptureEntry 29 }

    wfPktCaptureTxFltr2Type OBJECT-TYPE
        SYNTAX	INTEGER {
    		    capture(1),
    		    trigger(2),
    		    notused(3)
    		}
        ACCESS	read-write
        STATUS	mandatory
        DESCRIPTION
                "Tx filter 2 type, Capture, Trigger or Not used"
        DEFVAL	{ notused }
        ::= { wfPktCaptureEntry 30 }

    wfPktCaptureTxFltr2Offset OBJECT-TYPE
        SYNTAX	INTEGER
        ACCESS	read-write
        STATUS	mandatory
        DESCRIPTION
                "Tx filter 2 offset in bytes"
        ::= { wfPktCaptureEntry 31 }

    wfPktCaptureTxFltr2Ref OBJECT-TYPE
        SYNTAX	INTEGER {
    		    mac(1),
    		    dl(2),
    		    mcast(3)
    		}
        ACCESS	read-write
        STATUS	mandatory
        DESCRIPTION
                "Tx filter 2 Reference point, MAC, DATA LINK, MULTICAST"
        DEFVAL	{ mac }
        ::= { wfPktCaptureEntry 32 }

    wfPktCaptureTxFltr2Size OBJECT-TYPE
        SYNTAX	INTEGER
        ACCESS	read-write
        STATUS	mandatory
        DESCRIPTION
                "Tx filter 2 field size to match in bytes"
        ::= { wfPktCaptureEntry 33 }

    wfPktCaptureTxFltr2Match OBJECT-TYPE
        SYNTAX	OCTET STRING
        ACCESS	read-write
        STATUS	mandatory
        DESCRIPTION
                "Tx filter 2 data to match with packet"
        ::= { wfPktCaptureEntry 34 }

    wfPktCaptureTxFltr2Group OBJECT-TYPE
        SYNTAX	INTEGER {
    		    or(1),
    		    and(2)
    		}
        ACCESS	read-write
        STATUS	mandatory
        DESCRIPTION
                "Tx filter 2 grouping attribute, AND or OR"
        DEFVAL	{ or }
        ::= { wfPktCaptureEntry 35 }


    wfPktCaptureAtmVpi OBJECT-TYPE
        SYNTAX  INTEGER
        ACCESS  read-write
        STATUS  mandatory
        DESCRIPTION
                "ATM VPI"
        ::= { wfPktCaptureEntry 36 }

    wfPktCaptureAtmVci OBJECT-TYPE
        SYNTAX  INTEGER
        ACCESS  read-write
        STATUS  mandatory
        DESCRIPTION
                "ATM VCI"
        ::= { wfPktCaptureEntry 37 }

    END  -- Wellfleet-PCAP-MIB
