--
-- ****************************************************************************
-- Title:    	Symbol Technologie's PRIVATE MIB for Spectrum24 Ethernet Access
--		Point Device 
--
-- This MIB file works with Spectrun24 AP Firmware version 03.10-26 and above.
--
-- Copyright 1995 - 1997 Symbol Technologies, Inc.
-- All rights reserved.
-- This Symbol Technologies's SNMP Management Information Base Specification
-- embodies Symbols' confidential and proprietary intellectual property.
-- Symbol Technologies Inc., retains all title and ownership in the 
-- Specification, including any revisions.
--
-- This Specification is supplied "AS IS," and Symbol makes no warranty, either
-- express or implied, as to the use, operation, condition, or performance of 
-- the Specification.
-- ****************************************************************************
--
--
-- ************************************
-- Symbol Access Point MIB at a glance
-- ************************************
--
-- symbol (388)
--	spectrum24(1)
--		apProduct(1)
--			apConfigMgmt(1)
--				apManufactureInfo(1) 
--					apModelnumber(1)      DisplayString  R
--					apSerialnumber(2)     DisplayString  R
--					apHardwareRev(3)      DisplayString  R
--                                      apMyMacAddr(4)        PhysAddress    R
--					apAPFirmwareRev(5)    DisplayString  R
--					apRFFirmwareRev(6)    DisplayString  R
--
--				apSystemConfig(2)
--					apSystemName(1)	      DisplayString  R/W
--					apMyIPAddr(2)	      IpAddress	     R/W
--					apSubnetMask(3)	      INTEGER	     R/W
--					apGatewayIPAddr(4)    INTEGER        R/W
--					apDefaultInterface(5) INTEGER        R/W
--					apEnetPortState(6)    INTEGER        R/W
--					apEthernetTimeOut(7)  INTEGER        R/W
--					apTelnetEnable(8)     INTEGER        R/W
--					apAccCtrlEnable(9)    INTEGER        R/W
--					apTypeFilterEnable(10)INTEGER        R/W
--					apMUAutoCfgEnable(11) INTEGER  	     R/W
--					apAutoCfgEnable(12)   INTEGER        R/W
--					apWNMPEnable(13)      INTEGER 	     R/W
--					apAPStateXchgEnable(14)INTEGER 	     R/W
--
--
--				apSNMPInfo(3)
--					apSNMPMode(1)  	      INTEGER        R/W
--					apROCommunityName(2)  DisplayString  R/W
--					apRWCommunityName(3)  DisplayString  R/W
--					apTrapRcvrIpAdr(4)    IpAddress      R/W
--					apAllTrapsEnable(5)   INTEGER        R/W
--					apColdBootTrapEnable(6) INTEGER      R/W
--					apAuthenFailureTrapEnable(7) INTEGER R/W
--					apRFTrapEnable(8)     INTEGER        R/W
--					apACLTrapEnable(9)    INTEGER        R/W
--					apMUStateChngTrapEnable(10) INTEGER  R/W
--					apAPIdConflictTrapEnable(11) INTEGER R/W
--					apWLAPConnChngTrapEnable(12) INTEGER R/W
--
--				apRFConfig(4)
--					apRFPortState(1)      INTEGER        R/W
--					apNetId(2)	      OctetString    R/W
--					apApId(3)	      OctetString    R/W
--					apHopSequence(4)      INTEGER        R/W
--					apCountryName(5)      DisplayString  R
--					apHopSet(6)	      INTEGER        R  
--					apAntennaSelect(7)    INTEGER        R/W
--					apDTIMInterval(8)     INTEGER        R/W
--					apBCMCQMax(9)         INTEGER        R/W
--					apReassemblyTimeOut(10)INTEGER       R/W
--					apMaxRetries(11)      INTEGER        R/W
--					apMulticastMask(12)   OctetString    R/W
--					apEncryptCoeff(13)    OctetString    R/W
--					apEncryptPhase(14)    OctetString    R/W
--					apWLAPMode(15)        INTEGER 	     R/W
--					apWLAPPriority(16)    OctetString    R/W
--					apWLAPManualAPID(17)  OctetString    R/W
--					apWLAPEncryption(18 ) INTEGER 	     R/W
--					apWLAPHelloTime(19)   INTEGER 	     R/W
--					apWLAPMaxAge(20)      INTEGER 	     R/W
--					apWLAPFwdDelay(21)    INTEGER 	     R/W
--
--				apSerialPortConfig(5)
--					apPPPState(1)	      INTEGER        R/W
--					apSerialPortUse(2)    INTEGER        R/W
--					apModemConnected(3)   INTEGER        R/W
--					apConnectMode(4)      INTEGER	     R/W
--					apDialOutNumber(5)    OctetString    R/W
--                           		apDialOutMode(6)      INTEGER        R/W
--                           		apAnswerWaitTime(7)   INTEGER        R/W
--                           		apModemSpeaker(8)     INTEGER        R/W
--                           		apInactivityTimeout(9)INTEGER        R/W
--                           		apPPPTimeOut(10)      INTEGER        R/W
--                           		apPPPTerminates(11)   Counter        R/W
--
--                           	apAddrFilterTable(6)
--                                   	apAddrFilterEntry(1)
--                                             disallowedMUIndex(1)INTEGER Index
--                                             disallowedMU(2) PhysAddress  R/W
--
--                           	apTypeFilteringTable(7)
--                                  apTypeEntry(1)
--                                      typeIndex(1)  	      INTEGER      Index
--                                      etherType(2)          INTEGER        R/W
--
--
--			apPerformMgmt(2)
--				apTrafficMatrixTable(1)
--				    apTrafficMatrixEntry(1)
--					apTMTableIndex(1)     INTEGER	   Index
--					apProtoItfName(2)     DisplayString  R
--					apNPktsToEnets(3)     Counter        R
--					apNPktsToPpps(4)      Counter        R
--					apNPktsToRfs(5)       Counter        R
--					apNPktsToAPStks(6)    Counter        R
--                     
--				apItfStatTable(2)
--				    apItfStatEntry(1)
--					apItfStatIndex(1)     INTEGER	   Index
--					apInterfaceName(2)    DisplayString  R
--					apPacketsIns(3)       Counter        R
--					apPacketsOuts(4)      Counter        R
--					apOctetsIns(5)        Counter        R
--					apOctetsOuts(6)       Counter        R
--					apPktsInPerSec(7)     Gauge          R
--					apPktsOutPerSec(8)    Gauge          R
--					apOctInPerSec(9)      Gauge          R
--					apOctOutPerSec(10)    Gauge          R
--
--				apEthernetStatistics(3)
--					apEPktsSeens(1)       Counter        R
--					apEPktsForwardeds(2)  Counter        R
--					apEPktsDiscNoMatchs(3)Counter        R
--					apEPktsDiscForceds(4) Counter        R
--					apEPktsDiscBuffers(5) Counter        R
--                                     	apEPktsDiscCRCs(6)    Counter        R
--                                     	apEPktsSents(7)       Counter        R
--                                     	apEAnyCollisions(8)   Counter        R
--                                     	apE1orMoreColls(9)    Counter        R
--                                     	apEMaxCollisions(10)  Counter        R
--                                     	apELateCollisions(11) Counter        R
--                                     	apEPktsDefers(12)     Counter        R
--	
--                   		apRFStatistics(4)
--                                 	rfBcMcPktsSents(1)    Counter        R
--                                     	rfBcMcPktsRcvds(2)    Counter        R
--                                     	rfBcMcOctetsSents(3)  Counter        R
--                                     	rfBcMcOctetsRcvds(4)  Counter        R
--                                     	rfSystemPktsSents(5)  Counter        R
--                                     	rfSystemPktsRcvds(6)  Counter        R
--                                     	rfSBcMcPktsSents(7)   Counter        R
--                                     	rfSBcMcPktsRcvds(8)   Counter        R
--                                     	rfSuccFragPkts(9)     Counter        R
--                                     	rfUnsuccFragPkts(10)  Counter        R
--                                     	rfTotalFragSents(11)  Counter        R
--                                     	rfTotalFragRcvds(12)  Counter        R
--                                     	rfSuccReassPkts(13)   Counter        R
--                                     	rfUnsuccReassPkts(14) Counter        R
--                                     	rfAssoMUs(15)         Counter        R
--                                     	rfRcvdCRCErrors(16)   Counter        R
--                                     	rfRcvdDupliPkts(17)   Counter        R
--                                     	rfTotalCollisions(18) Counter        R
--                                     	rfPktsWithoutColls(19)Counter        R
--                                     	rfPktsWithMaxColls(20)Counter        R
--                                     	rfPktsWithColls(21)   Counter        R
--	
--				apPerFreqStatTable(5)
--            			    apPerFreqStatEntry(1)
--					rfPerFqChannel(1)     INTEGER	     R
--                                     	rfPerFqPktsSents(2)   Counter        R
--                                     	rfPerFqPktsRcvds(3)   Counter        R
--                                     	rfPerFqRetries(4)     Counter        R
--
--                   		apSerialPortStatistics(6)
--                                 	apNbrOfDialouts(1)    Counter        R
--                                     	apDialoutFailures(2)  Counter        R
--                                     	apNbrOfAnswers(3)     Counter        R
--                                     	apCurrCallTime(4)     TimeTicks      R
--                                     	apLastCallTime(5)     TimeTicks      R
--
--                   		apWNMPStatistics(7)
--                                 	apWNMPCfgPkts(1)      Counter        R
--                                     	WEchoRequests(2)      Counter        R
--                                     	WPingRequests(3)      Counter        R
--                                     	WPktsFromNVs(4)       Counter        R
--                                     	WPktsToNVs(5)         Counter        R
--                                     	WPassThruEcs(6)       Counter        R
--
--                   		apMUInfo(8)
--                          		apCurrentMUs(1)       Counter        R
--                             		apMaxMUs(2)           Counter	     R
--                             		apTotalAssocs(3)      Counter        R
--                             		apMUTable(4)
--                             		    apMUEntry(1)
--					 	muIndex(1)       INTEGER   Index
--                                      	muMacAddr(2)     PhysAddress  R
--						muInterface(3)   INTEGER      R
--                                         	muState(4)       INTEGER      R
--                                             	muPowerMode(5)   INTEGER      R
--						muStationID(6)   INTEGER      R
--                                             	muLastAPAddr(7)  PhysAddress  R
--						muTotalAssoc(8)  INTEGER      R
--                                             	muAssocStart(9)  TimeTicks    R
--                                             	muLstAssStrt(10) TimeTicks    R
--                                             	muLastAssEnd(11) TimeTicks    R
--                                             	muNPktsSents(12) Counter      R
--                                             	muNPktsRcvds(13) Counter      R
--                                             	muNBytesSents(14)Counter      R
--                                             	muNByteRcvds(15) Counter      R
--						muNDiscdPkts(16) Counter      R
--                                             	muTmLastData(17) TimeTicks    R
--
--                   		apKnownAPsTable(9)
--                           	    apKnownAPsEntry(1)
--                              	apAPMacAddr(1)        PhysAddress    R
--                                 	apAPIpAddr(2)         IpAddress      R
--                                     	apNetID(3)            OctetString    R
--                                     	apAPID(4)             OctetString    R
--                                     	apHoppingSeq(5)       INTEGER        R
--                                     	apMUs(6)              INTEGER        R
--                                     	apKBOS(7)             INTEGER        R
--                                     	apKBIS(8)             INTEGER        R
--                                     	apLastRcvd(9)         TimeTicks      R
--
--                           	apFilterStatistics(10)
--                                     	apAdrViolations(1)    Counter        R
--                                     	apTypeViolations(2)   Counter        R
--
--                           	apWLAPInfo(11)
--				    apNbrOfWLAPItfs(1)	      Counter	     R
--				    apWLAPState(2)	      INTEGER	     R
--				    apWLAPHopSequence(3)      INTEGER	     R
--				    apRootInterface(4)	      OctetString    R
--				    apRootWLAPID(5)	      OctetString    R
--				    apRootPathCost(6)	      INTEGER	     R
--				    apWLAPID(7)		      OctetString    R
--				    apWLAPItfTable(8)
--				      apWLAPItfEntry(1)
--					apWLAPItfID(1)	      OctetString    R
--					apWLAPItfAddr(2)      PhysAddress    R	
--					apWLAPItfState(3)     INTEGER	     R
--					apWLAPPathCost(4)     INTEGER	     R
--					apDsgnatedRoot(5)     OctetString    R	
--					apDsgnatedCost(6)     INTEGER	     R
--					apDsgnatedWLAP(7)     OctetString    R
--					apDsgnatedItf(8)      OctetString    R
--
--			apFaultManagement(3)
--                           	apClrAllStatistics(1)         INTEGER        R/W
--                           	apClrMUTable(2)               INTEGER        R/W
-- 				apClrACL(3)		      INTEGER	     R/W
--				apClrACLRangeTable(4)	      INTEGER	     R/W
--				apClrAddrFilterTbl(5)	      INTEGER	     R/W
--				apLdACLFrMUList(6)	      INTEGER	     R/W
--                           	apModemDialOut(7)             INTEGER        R/W
--                           	apModemHangUp(8)              INTEGER        R/W
--                           	apUpdateFirmware(9)           INTEGER        R/W
--                           	apDnLdFileName(10)            DisplayString  R/W
--                           	apTFTPServer(11)              IpAddress      R/W
--				apResetAP(12)		      INTEGER        R/W
--
--
--			apSecurityMgmt(4)
--                              apACLViolations(1)            Counter        R
--				apSaveConfig(2)		      INTEGER	     R/W
--                           	apAccCtrlTable(3)
--                                  apACLEntry(1)
--                          		allowedMUIdx(1)       INTEGER        R
--                                      allowedMU(2)          PhysAddress    R/W
--				apACLRangeTable(4)	
--				    apACLRTEntry(1)
--					apACLRangeIdx(1)      INTEGER	     R
--                                      minMacAddr(2)         PhysAddress    R/W
--                                      maxMacAddr(3)         PhysAddress    R/W
--


SYMBOL-ENTERPRISE-PRIVATE-MIB  DEFINITIONS ::= BEGIN 

        IMPORTS
		enterprises, IpAddress, Counter, Gauge, TimeTicks   
							FROM RFC1155-SMI
                OBJECT-TYPE 				FROM RFC-1212 
		snmp, DisplayString, PhysAddress	FROM RFC1213-MIB
                TRAP-TYPE 				FROM RFC-1215;
		
     		symbol          OBJECT IDENTIFIER ::= { enterprises 388 }

      		spectrum24      OBJECT IDENTIFIER ::= { symbol 1 }

       		apProduct       OBJECT IDENTIFIER ::= { spectrum24 1 }

		apConfigMgmt    OBJECT IDENTIFIER ::= { apProduct 1 }
		apPerformMgmt   OBJECT IDENTIFIER ::= { apProduct 2 }
		apFaultMgmt     OBJECT IDENTIFIER ::= { apProduct 3 }
		apSecurityMgmt  OBJECT IDENTIFIER ::= { apProduct 4 }

  		apManufactureInfo      OBJECT IDENTIFIER ::= { apConfigMgmt 1 }
  		apSystemConfig         OBJECT IDENTIFIER ::= { apConfigMgmt 2 }
  		apSNMPInfo             OBJECT IDENTIFIER ::= { apConfigMgmt 3 }
  		apRFConfig             OBJECT IDENTIFIER ::= { apConfigMgmt 4 }
  		apSerialPortConfig     OBJECT IDENTIFIER ::= { apConfigMgmt 5 }
--		apAddrFilterTable      OBJECT IDENTIFIER ::= { apConfigMgmt 6 }
--		apTypeFilteringTable   OBJECT IDENTIFIER ::= { apConfigMgmt 7 }

--      	apTrafficMatrixTable   OBJECT IDENTIFIER ::= { apPerformMgmt 1 }
--      	apItfStatTable         OBJECT IDENTIFIER ::= { apPerformMgmt 2 }
      		apEthernetStatistics   OBJECT IDENTIFIER ::= { apPerformMgmt 3 }
      		apRFStatistics         OBJECT IDENTIFIER ::= { apPerformMgmt 4 }
--      	apPerFreqStatTable     OBJECT IDENTIFIER ::= { apPerformMgmt 5 }
                apSerialPortStatistics OBJECT IDENTIFIER ::= { apPerformMgmt 6 }
       		apWNMPStatistics       OBJECT IDENTIFIER ::= { apPerformMgmt 7 }
 		apMUInfo               OBJECT IDENTIFIER ::= { apPerformMgmt 8 }
--       	apKnownAPsTable        OBJECT IDENTIFIER ::= { apPerformMgmt 9 }
 		apFilterStatistics     OBJECT IDENTIFIER ::= { apPerformMgmt 10}
         	apWLAPInfo             OBJECT IDENTIFIER ::= { apPerformMgmt 11}

--              apClrAllStatistics     OBJECT IDENTIFIER ::= { apFaultMgmt 1 }
--              apClrMUTable	       OBJECT IDENTIFIER ::= { apFaultMgmt 2 }
-- 		apClrACL	       OBJECT IDENTIFIER ::= { apFaultMgmt 3 }
--              apClrACLRangeTable     OBJECT IDENTIFIER ::= { apFaultMgmt 4 }
--		apClrAddrFilterTbl     OBJECT IDENTIFIER ::= { apFaultMgmt 5 }
--		apLdACLFrMUList	       OBJECT IDENTIFIER ::= { apFaultMgmt 6 }
--              apModemDialOut	       OBJECT IDENTIFIER ::= { apFaultMgmt 7 }
--              apModemHangUp	       OBJECT IDENTIFIER ::= { apFaultMgmt 8 }
--              apUpdateFirmware       OBJECT IDENTIFIER ::= { apFaultMgmt 9 }
--              apDnLdFileName	       OBJECT IDENTIFIER ::= { apFaultMgmt 10 }
--              apTFTPServer	       OBJECT IDENTIFIER ::= { apFaultMgmt 11 }
--		apResetAP	       OBJECT IDENTIFIER ::= { apFaultMgmt 12 }
--

--              apACLViolation	       OBJECT IDENTIFIER ::= { apSecurityMgmt 1}
--		apSaveConfig	       OBJECT IDENTIFIER ::= { apSecurityMgmt 2}
--              apAccCtrlTable	       OBJECT IDENTIFIER ::= { apSecurityMgmt 3}
--              apACLRangeTable	       OBJECT IDENTIFIER ::= { apSecurityMgmt 4}


 	coldStart		TRAP-TYPE
		ENTERPRISE snmp
		VARIABLES  { apMyMacAddr }
		DESCRIPTION
			"Access Point cold boot. 
			 - apMyMacAddr is the MAC address of the Access Point 
			   sending this trap message."
		::= 0

 	authenticationFailure	TRAP-TYPE
		ENTERPRISE snmp
		VARIABLES  { apMyMacAddr, apAPMacAddr }
		DESCRIPTION
			"Invalid SNMP Community string.
			 - apMyMacAddr is the MAC address of the Access Point 
			   sending this trap message.
			 - apAPMacAddr is the MAC address of the remote host 
			   sending SNMP packet with invalid community."
		::= 4

 	apRFStartUpTrap		TRAP-TYPE
		ENTERPRISE apProduct
		VARIABLES  { apMyMacAddr }
		DESCRIPTION
			"RF Driver is up.
			 - apMyMacAddr is the MAC address of the Access Point 
			   sending this trap message."
		::= 101

 	apACLViolationTrap	TRAP-TYPE
		ENTERPRISE apProduct
		VARIABLES  { apMyMacAddr, muMacAddr }
		DESCRIPTION
			"Mobile Unit MAC address not in the Access control 
			 Table.
			 - apMyMacAddr is the MAC address of the Access Point 
			   sending this trap message.
			 - muMacAddr is the MAC address of the Mobile Unit 
			   not in the Access Control Table."
		::= 102

 	apAPIdConflictTrap	TRAP-TYPE
		ENTERPRISE apProduct
		VARIABLES  { apMyMacAddr }
		DESCRIPTION
			"An Access Point with the same AP-ID with this Access
			 Point is found.
			 - apMyMacAddr is the MAC address of the Access Point 
			   sending this trap message."
		::= 103

 	apMUAssocTrap	TRAP-TYPE
		ENTERPRISE apProduct
		VARIABLES  { apMyMacAddr, muMacAddr, apCurrentMUs }
		DESCRIPTION
			"Indicates that there is one Mobile Unit associating
			 with this Access Point.
			 - apMyMacAddr is the MAC address of the Access Point 
			   sending this trap message.
			 - muMacAddr is the MAC address of the Mobile Unit.
			   Note : If two or more Mobile Units associate with the
				  Access Point at the same time, muMacAddr 
				  belongs to the last Mobile Unit.
			 - apCurrentMUs is the number of Mobile Units currently 
			   associating with this Access Point."
		::= 111

 	apMUUnAssocTrap	TRAP-TYPE
		ENTERPRISE apProduct
		VARIABLES  { apMyMacAddr, muMacAddr, apCurrentMUs }
		DESCRIPTION
			"Indicates that there is one Mobile Unit no longer 
			 associating with this Access Point anymore.
			 - apMyMacAddr is the MAC address of the Access Point 
			   sending this trap message.
			 - muMacAddr is the MAC address of the Mobile Unit.
			   Note : If two or more Mobile Units un-associate with
				  the Access Point at the same time, muMacAddr 
				  belongs to the last Mobile Unit.
			 - apCurrentMUs is the number of Mobile Units currently 
			   associating with this Access Point."
		::= 112

 	apMUToCAMTrap	TRAP-TYPE
		ENTERPRISE apProduct
		VARIABLES  { apMyMacAddr, muMacAddr, apCurrentMUs }
		DESCRIPTION
			"Indicates that the Mobile Unit changes from PSP mode
			 to CAM mode.
			 - apMyMacAddr is the MAC address of the Access Point 
			   sending this trap message.
			 - muMacAddr is the MAC address of the Mobile Unit.
			   Note : If two or more Mobile Units change their mode
				  at the same time, muMacAddr belongs to the 
				  last Mobile Unit.
			 - apCurrentMUs is the number of Mobile Units currently 
			   associating with this Access Point."
		::= 113

 	apMUToPSPTrap	TRAP-TYPE
		ENTERPRISE apProduct
		VARIABLES  { apMyMacAddr, muMacAddr, apCurrentMUs }
		DESCRIPTION
			"Indicates that the Mobile Unit changes from CAM mode
			 to PSP mode.
			 - apMyMacAddr is the MAC address of the Access Point 
			   sending this trap message.
			 - muMacAddr is the MAC address of the Mobile Unit.
			   Note : If two or more Mobile Units change their mode
				  at the same time, muMacAddr belongs to the 
				  last Mobile Unit.
			 - apCurrentMUs is the number of Mobile Units currently 
			   associating with this Access Point."
		::= 114

 	apRootWLAPUpTrap	TRAP-TYPE
		ENTERPRISE apProduct
		VARIABLES  { apMyMacAddr, apAPMacAddr, apNbrOfWLAPItfs }
		DESCRIPTION
			"Indicates that the Root AP connection is setup and
			 is ready to forward data.
			 - apMyMacAddr is the MAC address of the Access Point 
			   sending this trap message.
			 - apAPMacAddr is the MAC address of the Root AP.
			 - apNbrOfWLAPItfs is the number of current WLAP 
			   Interfaces established."
		::= 121

 	apRootWLAPLostTrap	TRAP-TYPE
		ENTERPRISE apProduct
		VARIABLES  { apMyMacAddr, apAPMacAddr, apNbrOfWLAPItfs }
		DESCRIPTION
			"If the current wireless AP  does not receive Beacon 
			 packet from its Root AP within one second, it will 
			 consider the Root AP is lost. The wireless AP  will 
			 eventually reset itself to re-establish the network 
			 topology.
			 - apMyMacAddr is the MAC address of the Access Point 
			   sending this trap message.
			 - apAPMacAddr is the MAC address of the Root AP.
			 - apNbrOfWLAPItfs is the number of current WLAP 
			   Interfaces established."
		::= 122

 	apDsgntedWLAPUpTrap	TRAP-TYPE
		ENTERPRISE apProduct
		VARIABLES  { apMyMacAddr, apAPMacAddr, apNbrOfWLAPItfs }
		DESCRIPTION
			"Indicates that the Designated WLAP connection is setup
			 and is ready to forward data.
			 - apMyMacAddr is the MAC address of the Access Point 
			   sending this trap message.
			 - apAPMacAddr is the MAC address of the Designated 
			   WLAP. 
			 - apNbrOfWLAPItfs is the number of current WLAP 
			   Interfaces established."
		::= 123

 	apDsgnatedWLAPLostTrap	TRAP-TYPE
		ENTERPRISE apProduct
		VARIABLES  { apMyMacAddr, apAPMacAddr, apNbrOfWLAPItfs }
		DESCRIPTION
			"If the current wireless AP does not receive Config BPDU
			 (Bridge Protocol Data Unit) packet from its Designated
			 WLAP for MAX AGE time, it will consider that the 
			 Designated WLAP is lost. 
			 - apMyMacAddr is the MAC address of the Access Point 
			   sending this trap message.
			 - apAPMacAddr is the MAC address of the Designated 
			   WLAP.
			 - apNbrOfWLAPItfs is the number of current WLAP 
			   Interfaces established."
		::= 124


--
--  Access Point Configuration Management (1)
--
	-- Access Point Manufacturer Information Group (1.1)
	--
	-- This group specifies the manufacturer information on the Access
	-- Point for identification only. These data may not be altered by 
	-- users.
	--     

        apModelnumber OBJECT-TYPE
        	SYNTAX  DisplayString (SIZE (1..32))
           	ACCESS  read-only
               	STATUS  mandatory
               	DESCRIPTION
                	"The Model Number of the Access Point device."
            	::= { apManufactureInfo 1 }

     	apSerialnumber OBJECT-TYPE
         	SYNTAX  DisplayString (SIZE (1..16))
           	ACCESS  read-only
               STATUS  mandatory
               	DESCRIPTION
                     	"The Serial Number of the Access Point system."
           	::= { apManufactureInfo 2 }

     	apHardwareRev OBJECT-TYPE
               	SYNTAX DisplayString (SIZE (1..8))
            	ACCESS  read-only
               	STATUS  mandatory
               	DESCRIPTION
                     	"The current revision of the Access Point hardware."
               	::= { apManufactureInfo 3 }

      	apMyMacAddr OBJECT-TYPE
         	SYNTAX  PhysAddress
             	ACCESS  read-only
               	STATUS  mandatory
               	DESCRIPTION
                     	"The MAC address of the AP."
               	::= { apManufactureInfo 4 }
 
     	apAPFirmwareRev OBJECT-TYPE
            	SYNTAX  DisplayString (SIZE (1..16))
           	ACCESS  read-only
               	STATUS  mandatory
               	DESCRIPTION
                     	"The current revision of the Access Point firmware."
            	::= { apManufactureInfo 5 }

     	apRFFirmwareRev OBJECT-TYPE
             	SYNTAX  DisplayString (SIZE (1..16))
           	ACCESS  read-only
               	STATUS  mandatory
               	DESCRIPTION
                     	"The current revision of the Access Point radio 
			 firmware."
          	::= { apManufactureInfo 6 }

	--
	-- Access Point System Configuration Information Group (1.2)
	--
	-- This group contains the Access Point System Configuration Information
	-- which is used for controlling the Access Point system operations.
	--

 	apSystemName	OBJECT-TYPE
             	SYNTAX  DisplayString (SIZE (1..31))
         	ACCESS  read-write
              	STATUS  mandatory
               	DESCRIPTION
                     	"An ASCII string to identify this Access Point (up to 
			 31 characters)."

          	::= { apSystemConfig  1 }

 	apMyIPAddr	OBJECT-TYPE
             	SYNTAX  IpAddress
         	ACCESS  read-write
              	STATUS  mandatory
               	DESCRIPTION
                     	"The IP address for the AP."
          	::= { apSystemConfig  2 }

 	apSubnetMask	OBJECT-TYPE
             	SYNTAX  IpAddress
         	ACCESS  read-write
              	STATUS  mandatory
               	DESCRIPTION
                     	"The IP subnet mask for the AP."
          	::= { apSystemConfig  3 }

 	apGatewayIPAddr	OBJECT-TYPE
             	SYNTAX  IpAddress
         	ACCESS  read-write
              	STATUS  mandatory
               	DESCRIPTION
                     	"The IP address for the default gateway."
          	::= { apSystemConfig  4 }

 	apDefaultInterface 	OBJECT-TYPE
                SYNTAX  INTEGER {
                    	ppp(1),      
                	ethernet(2)  
                }
               	ACCESS  read-write
              	STATUS  mandatory
               	DESCRIPTION
                     	"Specifies the default interface (Ethernet or PPP) for 
			 the Access Point to forward an unknown packet. Default
			 is ethernet(2)."
             	::= { apSystemConfig  5 } 

   	apEnetPortState	OBJECT-TYPE
            	SYNTAX  INTEGER {
                 	up(1),     
                	down(2)    
              	}
               	ACCESS  read-write
              	STATUS  mandatory
               	DESCRIPTION
                     	"Specifies the state of the Ethernet interface.
			 Default is up(1)." 
               	::= { apSystemConfig  6 }
 
   	apEthernetTimeOut OBJECT-TYPE
            	SYNTAX  INTEGER 
               	ACCESS  read-write
              	STATUS  mandatory
               	DESCRIPTION
			"The Ethernet time out value ranges from 30 to 255 
			 seconds. If the value is:
			 - 0: the Ethernet Time Out function is disabled.
			 - 1: detect Ethernet timeout by hardware circuitry.
			 - 2: send WLAP Alive BPDU on Ethernet interface to let
			      other WLAP on the same Ethernet segment to detect
			      it's existence.
			 - 3: keep track of WLAP Alive BPDU on Ethernet inter-
			      face. If the BPDU is missing for 'WLAP Hello Time'
			      seconds, both Ethernet Attached and Activity LEDs
			      will flash and the RF interface is disabled until
			      the WLAP Alive BPDU is received again, then the
			      AP will reset itself. 
			 When the Ethernet connection is broken: 
			 - if WLAP Mode is disabled, the AP will clear the MU 
			   table and disable the RF interface until the Ethernet
			   connection is up.
			 - if WLAP Mode is enabled, the AP will set the timeout
			   value to zero and reset itself. 
			 The default value is 0." 
               	::= { apSystemConfig  7 }
 
        apTelnetEnable	OBJECT-TYPE
              	SYNTAX  INTEGER {
                       	enabled(1),    
                       	disabled(2)    
              	}
               	ACCESS  read-write
              	STATUS  mandatory
               	DESCRIPTION
                     	"Enables/Disables Telnet access to the AP. Default is 
			 enabled(1)."
           	::= { apSystemConfig  8 }

	apAccCtrlEnable	OBJECT-TYPE
             	SYNTAX  INTEGER {
  			enabled(1), 
      			disabled(2) 
              	}
               	ACCESS  read-write
              	STATUS  mandatory
               	DESCRIPTION
                     	"Enables/Disables the Access Control function. 
			 When it is enabled, a Mobile Unit can associate with 
			 the Access Point only if its MAC address is in the 
			 Access Control Table. Default is disabled(2)."
          	::= { apSystemConfig 9 }
 
 	apTypeFilterEnable	OBJECT-TYPE
             	SYNTAX  INTEGER { 
                      	disabled(1),  
                       	forward(2),    
                        discard(3)    	
              	}
               	ACCESS  read-write
              	STATUS  mandatory
               	DESCRIPTION
                     	"Specifies the type of Access Point Type Filtering 
			 operation, i.e.  Disabled/Forward/Discard. Default is 
			 disabled(1)."
              	::= { apSystemConfig 10 }
 
 	apMUAutoCfgEnable	OBJECT-TYPE
             	SYNTAX  INTEGER {
	            	enabled(1),      
                       	disabled(2)   
              	}
               	ACCESS  read-write
              	STATUS  mandatory
               	DESCRIPTION
                     	"Enables/Disables Autoconfiguration of Mobile Units.
			 When enabled, the Net ID is automatically downloaded
			 to Mobile Units. Default is disabled(2)."
              	::= { apSystemConfig 11 }

 	apAutoCfgEnable	OBJECT-TYPE
          	SYNTAX  INTEGER {
                  	enabled(1),     
                       	disabled(2)  
              	}
               	ACCESS  read-write
              	STATUS  mandatory
               	DESCRIPTION
                     	"Enables/Disables Access Point auto configuration. When
			 enabled, the Access Point will automatically select 
			 unique BSSs and hopping sequences by negotiating with 
			 one another. Default is enabled(1)."
         	::= { apSystemConfig 12 }

        apWNMPEnable    OBJECT-TYPE
             	SYNTAX  INTEGER {
                   	enabled(1),    
         		disabled(2)   
              	}
               	ACCESS  read-write
              	STATUS  mandatory
               	DESCRIPTION
                	"Enables/Disables Use of the WNMP agent. Default is 
			 enabled(1)."
            	::= { apSystemConfig  13 }

        apAPStateXchgEnable    OBJECT-TYPE
             	SYNTAX  INTEGER {
                   	enabled(1),    
         		disabled(2)   
              	}
               	ACCESS  read-write
              	STATUS  mandatory
               	DESCRIPTION
                	"Enables/Disables exchanging Access Point to Access 
			 Point state information by using WNMP protocol. Default
			 is enabled(1)."
            	::= { apSystemConfig  14 }


	-- 
	--  The Access Point SNMP Configuration Information Group (1.3) 
	--
	--  This group contains the SNMP configuration information which is
	--  used for SNMP operations on the AP. A trap receiver table 
	--  allows users to set the Network Manager addresses for receiving
	--  the traps (i.e. Alert/Alarm/Event) from Access Point devices.
	-- 
 
    	apSNMPMode      OBJECT-TYPE
             	SYNTAX  INTEGER {
                      	disabled(1),  
                     	readonly(2),
                   	readwrite(3)   
          	}
               	ACCESS  read-write
              	STATUS  mandatory
               	DESCRIPTION
                     	"Specifies the mode of the SNMP Agent operation, i.e.
			 Disabled/Readonly/ReadWrite. Default is readwrite(3)."
            	::= { apSNMPInfo 1 }

    	apROCommunityName OBJECT-TYPE
                SYNTAX  DisplayString (SIZE (1..31))
            	ACCESS  read-write
              	STATUS  mandatory
               	DESCRIPTION
                     	"The Read-Only community name of the SNMP command for 
			 management station accessing this Access Point (up to 
			 31 characters)."
             	::= { apSNMPInfo 2 }
 
    	apRWCommunityName OBJECT-TYPE
                SYNTAX  DisplayString (SIZE (1..13))
            	ACCESS  read-write
              	STATUS  mandatory
               	DESCRIPTION
                     	"The Read-Write community name of the SNMP command for 
			 management station accessing this Access Point (up to 
			 13 characters). This community name is same as the
			 System Password or Telnet Password. For security 
			 purpose, if the management station uses the READ-ONLY 
			 community name to access this object, a string of 
			 'xxxxx' will be returned."
             	::= { apSNMPInfo 3 }
 
       	apTrapRcvrIpAdr OBJECT-TYPE
              	SYNTAX  IpAddress
              	ACCESS  read-write
              	STATUS  mandatory
               	DESCRIPTION
                     	"Trap receiver's (i.e. Network Manager's) IP address."
          	::= { apSNMPInfo 4 }
 
   	apAllTrapsEnable OBJECT-TYPE
            	SYNTAX  INTEGER {
                    	enabled(1),   
	              	disabled(2)  
              	}
               	ACCESS  read-write
              	STATUS  mandatory
               	DESCRIPTION
                     	"Enables/Disables all SNMP traps. Default is disable(2)."
               	::= { apSNMPInfo 5 }
 
 	apColdBootTrapEnable OBJECT-TYPE
                SYNTAX  INTEGER {
                  	enabled(1),     
                       	disabled(2)     
              	}
               	ACCESS  read-write
              	STATUS  mandatory
               	DESCRIPTION
                     	"Enables/Disables Access Point Cold Boot trap. Default 
			 is disable(2). This is a generic-trap and the trap 
			 code is 0.
			 The enabled/disabled state of this trap depends on the
			 state of apAllTrapsEnable."
              	::= { apSNMPInfo 6 }

 	apAuthenFailureTrapEnable OBJECT-TYPE
                SYNTAX  INTEGER {
                  	enabled(1),      
                       	disabled(2)     
              	}
               	ACCESS  read-write
              	STATUS  mandatory
               	DESCRIPTION
                     	"Enables/Disables authentication failure trap. Default 
			 is disable(2). This is a generic-trap and the trap code
			 is 4.
			 The enabled/disabled state of this trap depends on the
			 state of apAllTrapsEnable."
              	::= { apSNMPInfo 7 }

   	apRFTrapEnable OBJECT-TYPE
          	SYNTAX  INTEGER {
                     	enabled(1),    
                     	disabled(2)   
              	}
              	ACCESS  read-write
              	STATUS  mandatory
               	DESCRIPTION
                     	"Enables/Disables Access Point RF driver startup trap. 
			 Default is disable(2). This is an enterprise-specific 
			 trap and the trap code is 101.
			 The enabled/disabled state of this trap depends on the
			 state of apAllTrapsEnable."
              	::= { apSNMPInfo 8 }

   	apACLTrapEnable OBJECT-TYPE
         	SYNTAX  INTEGER {
                    	enabled(1),  
                      	disabled(2) 
              	}
               	ACCESS  read-write
              	STATUS  mandatory
               	DESCRIPTION
                     	"Enables/Disables Access Control violation trap. Default
			 is disable(2). This is an enterprise-specific trap and
			 the trap code is 102.
			 The enabled/disabled state of this trap depends on the
			 state of apAllTrapsEnable."
            	::= { apSNMPInfo 9 }
 
  	apMUStateChngTrapEnable  OBJECT-TYPE
            	SYNTAX  INTEGER {
                        enabled(1),  
                       	disabled(2) 
              	}
               	ACCESS  read-write
              	STATUS  mandatory
               	DESCRIPTION
                     	"Enables/Disables Mobile Unit State Change trap. Default
			 is disable(2). Once enabled, the following 4 
			 enterprise- specific traps will be generated :
			 - MU Association Trap, the trap code is 111.
			 - MU Un-association Trap, the trap code is 112.
			 - MU To CAM Trap, the trap code is 113.
			 - MU To PSP Trap, the trap code is 114.
			 The enabled/disabled state of this trap depends on the
			 state of apAllTrapsEnable."
              	::= { apSNMPInfo 10 }
 
  	apAPIdConflictTrapEnable  OBJECT-TYPE
            	SYNTAX  INTEGER {
                        enabled(1),      
                       	disabled(2)     
              	}
               	ACCESS  read-write
              	STATUS  mandatory
               	DESCRIPTION
                     	"Enables/Disables AP-Id conflict trap. Default is 
			 disable(2). This is an enterprise-specific trap and the
			 trap code is 103.
			 The enabled/disabled state of this trap depends on the
			 state of apAllTrapsEnable."
              	::= { apSNMPInfo 11 }
 
  	apWLAPConnChngTrapEnable  OBJECT-TYPE
            	SYNTAX  INTEGER {
                        enabled(1),      
                       	disabled(2)     

              	}
               	ACCESS  read-write
              	STATUS  mandatory
               	DESCRIPTION
                     	"Enables/Disables WLAP Connection Change trap. Default 
			 is disable(2). Once enabled, the following 4 
			 enterprise-specific traps will be generated :
			 - Root AP Up Trap, the trap code is 121. 
			 - Root AP Lost Trap, the trap code is 122. 
			 - Designated WLAP Up Trap, the trap code is 123.
			 - Designated WLAP Lost Trap, the trap code is 124.
			 The enabled/disabled state of this trap depends on the
			 state of apAllTrapsEnable."
              	::= { apSNMPInfo 12 }
 

	--
	--  The Access Point RF Configuration Information Group (1.4)
	--
	--  This group contains AP Radio Frequency interface configuration 
	--  information.
	--

   	apRFPortState OBJECT-TYPE
              	SYNTAX  INTEGER {
                      	up(1),  
                       	down(2) 
              	}
               	ACCESS  read-write
              	STATUS  mandatory
               	DESCRIPTION
                     	"Specifies the state of the RF Interface. Default is 
			 up(1)."
              	::= { apRFConfig 1 }

   	apNetId OBJECT-TYPE
             	SYNTAX  OCTET STRING (SIZE(1..2))
             	ACCESS  read-write
              	STATUS  mandatory 
              	DESCRIPTION
                     	"The current Net ID (i.e. operational ESS ID) for the 
			 AP. This value determines which APs are on the same
			 network and ranges from 1 - 0x1fe."
            	::= { apRFConfig 2 }
 
    	apApId OBJECT-TYPE
             	SYNTAX  OCTET STRING (SIZE(1..2))
               	ACCESS  read-write
             	STATUS  mandatory
               	DESCRIPTION
                     	"The current AP-ID (i.e. BSS ID) for this Access Point.
			 This value ranges from 0 - 0x79.
			 Writing a value will force this Access Point to use 
			 that value as AP-ID, unless it conflicts with that used
			 by another Access Point. In that case this Access Point
			 will select its own value. The Access Point will always
			 insure that the AP-ID is unique." 
               	::= { apRFConfig 3 }
 
   	apHopSequence OBJECT-TYPE
               	SYNTAX  INTEGER
         	ACCESS  read-write
              	STATUS  mandatory
               	DESCRIPTION
                     	"The hopping sequence defined in the system configura-
			 tion table for this AP. If WLAP mode is enabled, this 
			 Access Point will follow the hopping sequence 
			 (defined as apWLAPHopSequence) of the Root AP. 
			 Writing a value will force this Access Point to use 
			 that value as hopping sequence, unless it conflicts 
			 with that used by another AP. In that case this Access
			 Point will select its own value. The Access Point will
			 always insure that the hopping sequence is unique 
			 (given that there are fewer Access Points than the 
			 maximum number of hopping sequences). For the United 
			 States, this value ranges from 1-22, for Japan 0-3, 
			 ... TBD."
          	::= { apRFConfig 4 }
 
 	apCountryName	OBJECT-TYPE
             	SYNTAX  DisplayString (SIZE (1..36))
               	ACCESS  read-only
               	STATUS  mandatory
               	DESCRIPTION
                     	"The country for which the Access Point radio is 
			 configured. It is set at the factory and may not be 
			 altered."
                ::= { apRFConfig 5 }

    	apHopSet OBJECT-TYPE
            	SYNTAX  INTEGER
               	ACCESS  read-only
              	STATUS  mandatory
               	DESCRIPTION
                     	"The current hopping sequence set used by this AP."
              	::= { apRFConfig 6 }

   	apAntennaSelect	 OBJECT-TYPE
              	SYNTAX  INTEGER {
                      	primary-and-secondary(1),  
                       	primary-only(2) 
              	}
               	ACCESS  read-write
              	STATUS  mandatory
               	DESCRIPTION
                     	"Select either Primary antenna only (i.e. Disable 
			 antenna diversity) or both Primary and Secondary 
			 antennas (i.e. Enable antenna diversity). Default is 
			 primary-only(2)."
              	::= { apRFConfig 7 }

    	apDTIMInterval OBJECT-TYPE
            	SYNTAX  INTEGER
               	ACCESS  read-write
              	STATUS  mandatory
               	DESCRIPTION
                     	"The frequency of DTIM packets as a multiple of TIM 
			 packets. Default is 10."
              	::= { apRFConfig 8 }

    	apBCMCQMax OBJECT-TYPE
            	SYNTAX  INTEGER
               	ACCESS  read-write
              	STATUS  mandatory
               	DESCRIPTION
                     	"The maximum size of broadcast/multicast queue.
			 Default is 10."
              	::= { apRFConfig 9 }

    	apReassemblyTimeOut OBJECT-TYPE
            	SYNTAX  INTEGER
               	ACCESS  read-write
              	STATUS  mandatory
               	DESCRIPTION
                     	"The re-assembly timeout (in .5 ms units).
			 Default is 9000."
              	::= { apRFConfig 10 }

    	apMaxRetries OBJECT-TYPE
            	SYNTAX  INTEGER
               	ACCESS  read-write
              	STATUS  mandatory
               	DESCRIPTION
                     	"The maximum number of allowed retries before aborting a
			 transmission. Default is 15."
              	::= { apRFConfig 11 }

    	apMulticastMask OBJECT-TYPE
             	SYNTAX  OCTET STRING (SIZE(1..4))
               	ACCESS  read-write
              	STATUS  mandatory
               	DESCRIPTION
                     	"RF multicast packets with these upper 32 bits are sent
			 out immediately."
              	::= { apRFConfig 12 }

    	apEncryptCoeff OBJECT-TYPE
             	SYNTAX  OCTET STRING (SIZE(1..2))
               	ACCESS  read-write
              	STATUS  mandatory
               	DESCRIPTION
                     	"The encrytion coefficient value in hexadecimal."
              	::= { apRFConfig 13 }

    	apEncryptPhase OBJECT-TYPE
             	SYNTAX  OCTET STRING (SIZE(1..2))
               	ACCESS  read-write
              	STATUS  mandatory
               	DESCRIPTION
                     	"The encrytion phase value in hexadecimal."
              	::= { apRFConfig 14 }

        apWLAPMode    OBJECT-TYPE
             	SYNTAX  INTEGER {
                   	enabled(1),    
         		disabled(2)   
              	}
               	ACCESS  read-write
              	STATUS  mandatory
               	DESCRIPTION
                	"Enables/Disables Wireless AP capability. Default is 
			 disabled(2)."
            	::= { apRFConfig 15 }

        apWLAPPriority    OBJECT-TYPE
             	SYNTAX  OCTET STRING (SIZE(1..2))
               	ACCESS  read-write
              	STATUS  mandatory
               	DESCRIPTION
			"Provides a user with the influence to determine the 
			 Root AP in wireless operation. The priority value is
			 added as the most significant portion of the MAC 
			 address to form the WLAP ID. A WLAP with a lower 
			 numerical value for priority is more likely to become 
			 the Root AP. Default is 8000 hex from the 0 - 0xFFFF 
			 range. Reset the Access Point for value to 
			 take effect."
            	::= { apRFConfig 16 }

        apWLAPManualAPID    OBJECT-TYPE
             	SYNTAX  OCTET STRING (SIZE(1..2))
               	ACCESS  read-write
              	STATUS  mandatory
               	DESCRIPTION
			"Specifies the AP-ID of a particular WLAP and forces 
			 the current WLAP to associate only with that WLAP. 
			 When WLAP Manaul AP ID is set to the current AP-ID,
			 the current AP jumps into Functional state immediately 
			 and waits for an Association Request from the other 
			 WLAP. Reset AP for value to take effect."

            	::= { apRFConfig 17 }

        apWLAPEncryption OBJECT-TYPE
             	SYNTAX  INTEGER {
                   	enabled(1),    
         		disabled(2)   
              	}
               	ACCESS  read-write
              	STATUS  mandatory
               	DESCRIPTION
                	"Enables/Disables Wireless AP encryption capability. 
			 Default is disabled(2)."
            	::= { apRFConfig 18 }

        apWLAPHelloTime    OBJECT-TYPE
             	SYNTAX  INTEGER 
               	ACCESS  read-write
              	STATUS  mandatory
               	DESCRIPTION
			"Sets the time lapse, in seconds, between Configuration
			 BPDUs (Bridge Protocol Data Unit) generated by a Root 
			 AP. Default is 20 seconds. Reset AP for value to take 
			 effect."
            	::= { apRFConfig 19 }

        apWLAPMaxAge    OBJECT-TYPE
             	SYNTAX  INTEGER 
               	ACCESS  read-write
              	STATUS  mandatory
               	DESCRIPTION
			"Specifies how long, in seconds, a Configuration BPDU
			 (Bridge Protocol Data Unit) is kept before it is 
			 judged too old and discarded. Consequently, the 
			 interface is considered to be disconnected. Default
			 is 100 seconds. Recommended value is multiple of the 
			 WLAP Hello Time. Reset AP for value to take effect."
            	::= { apRFConfig 20 }

        apWLAPFwdDelay    OBJECT-TYPE
             	SYNTAX  INTEGER 
               	ACCESS  read-write
              	STATUS  mandatory
               	DESCRIPTION
			"Specifies how long, in seconds, an WLAP is prevented 
			 from forwarding data packets to an interface.
			 This delay is to allow the spread of news of a topology
			 change to all parts of a network. Default is 10 secs. 
			 Reset AP for value to take effect."
            	::= { apRFConfig 21 }


	--
	--  AP Serial Port Configuration Information Group (1.5)
	--  This group contains the Serial Port configuration information.
	--

        apPPPState OBJECT-TYPE
       		SYNTAX  INTEGER {
                    	up(1),    
	              	down(2)  
	              	}
               	ACCESS  read-write
              	STATUS  mandatory
               	DESCRIPTION
                     	"Indicates the current state of the PPP connection
			 machine. Default is down(2)."
                ::= { apSerialPortConfig 1 }
 
     	apSerialPortUse OBJECT-TYPE
        	SYNTAX  INTEGER {
                    	ppp(1),    	
               		ui(2)  
         	}
               	ACCESS  read-write
              	STATUS  mandatory
               	DESCRIPTION
			"Specifies whether the Serial Interface is to be used 
			 as User Interface(UI) or PPP. Default is ui(2)."
             	::= { apSerialPortConfig  2 }
 
    	apModemConnected OBJECT-TYPE
            	SYNTAX  INTEGER {
             		yes(1),  
                        no(2)     
            	}
               	ACCESS  read-write
              	STATUS  mandatory
               	DESCRIPTION
			"Specifies whether the Serial Interface has a modem 
			 attached to it. Default is no(2)."
            	::= { apSerialPortConfig  3 }
 
    	apConnectMode OBJECT-TYPE
               SYNTAX  INTEGER {
                    	originate(1), 	
              		answer(2)      
             	}
        	ACCESS  read-write
      	        STATUS  mandatory
               	DESCRIPTION
			"Specifies the Modem connection mode:
			 - originate(1): AP sends dial-out information.
			 - answer(2):    AP waits for dial-in information.
			 Default is answer(2)."
         	::= { apSerialPortConfig  4 }
 
    	apDialOutNumber OBJECT-TYPE
             	SYNTAX  DisplayString (SIZE (1..32))
              	ACCESS  read-write
              	STATUS  mandatory
               	DESCRIPTION
			"Specifies the number to be dialed by the modem."
              	::= { apSerialPortConfig  5  }
 
   	apDialOutMode OBJECT-TYPE
              SYNTAX  INTEGER {
                 	auto(1),
                  	manual(2)
	      	}
               	ACCESS  read-write
              	STATUS  mandatory
               	DESCRIPTION
			"Specifies the dialout mode:
			 - auto(1):   Modem dial out during startup time.
			 - manual(2): Modem dial out by manned intervention.
			 Dedault is auto(1)." 
 	        ::= { apSerialPortConfig  6 }
 
    	apAnswerWaitTime OBJECT-TYPE
		SYNTAX  INTEGER
               	ACCESS  read-write
              	STATUS  mandatory
               	DESCRIPTION
			"Specifies the period (in seconds) the AP will wait for 
			 the remote unit to answer the call. Default is 60 sec."
	        ::= { apSerialPortConfig  7 }
 
    	apModemSpeaker OBJECT-TYPE
              SYNTAX  INTEGER {
                      	on(1),    
            		off(2)   
             	}
               	ACCESS  read-write
              	STATUS  mandatory
               	DESCRIPTION
                     	"Specifies if modem speaker is turned on(1) or off(2).
			 Default is on(1)."
               	::= { apSerialPortConfig  8 }
 
   	apInactivityTimeout OBJECT-TYPE
         	SYNTAX  INTEGER
               	ACCESS  read-write
              	STATUS  mandatory
               	DESCRIPTION
                     	"Specifies the User Interface Inactivity timeout in 
			 minutes. 0 means no timeout. Default is 5 minutes."
              	::= { apSerialPortConfig  9 }

   	apPPPTimeout OBJECT-TYPE
          	SYNTAX  INTEGER
               	ACCESS  read-write
              	STATUS  mandatory
               	DESCRIPTION
                     	"Specifies the PPP event timeout in seconds. Default is
			 3 seconds. "
              	::= { apSerialPortConfig  10 }

    	apPPPTerminates OBJECT-TYPE
             	SYNTAX  Counter
        	ACCESS  read-write
              	STATUS  mandatory
               	DESCRIPTION
                     	"Specifies the maximum number of PPP terminate 
			 requests. Default is 10."
	        ::= { apSerialPortConfig  11 }


	--
        --  Access Point Address Filtering Table (1.6)
  	--  This group defines the MU MAC address list which is not allowed to
	--  get access to the AP.

       	apAddrFilterTable OBJECT-TYPE
            	SYNTAX  SEQUENCE OF ApAddrFilterEntry
         	ACCESS  not-accessible
          	STATUS  mandatory
               	DESCRIPTION
			"A table of MAC addresses not allowed to associate with
			 the Access Point.
			 The maximum number of entries in the table is 128."
               	::= { apConfigMgmt 6 }

       	apAddrFilterEntry OBJECT-TYPE
              	SYNTAX  ApAddrFilterEntry
             	ACCESS  not-accessible
          	STATUS  mandatory
               	DESCRIPTION
                     	"An entry in the table of Address Filter. 
			 A row in this table is created by setting the value of
			 disallowedMU to the MAC address of the MU not allowed 
			 to associate with the Access Point. 
			 A row in this table is deleted by setting the value of
			 disallowedMU to '000000000000'."
              	INDEX { disallowedIndex }
          	::= { apAddrFilterTable 1 }

      	ApAddrFilterEntry ::= SEQUENCE {
		disallowedIndex
			INTEGER,
              	disallowedMU
                    	PhysAddress
             	}

       	disallowedIndex  OBJECT-TYPE
          	SYNTAX  INTEGER (1..128)
              	ACCESS  read-only
              	STATUS  mandatory
               	DESCRIPTION
                     	"Address Filter Table index."
                ::= { apAddrFilterEntry 1 }
 
       	disallowedMU  OBJECT-TYPE
               	SYNTAX  PhysAddress
              	ACCESS  read-write
             	STATUS  mandatory
               	DESCRIPTION
                     	"MU MAC address which is not allowed to be associated 
			 with this Access Point." 
            	::= { apAddrFilterEntry 2 }

       
	--
        --  Access Point Type Filter Table (1.7)
  	--  This group defines the AP filter type list which is limited to
       	--  1. A packet level filter function only, no filter rules are applied.
       	--  2. Only inbound filter is supported; no "outbound" or "inbound & 
	--     outbound" direction are supported.
        --  3. No TCP/UDP source port is selected for filter criteria.
 	--

      	apTypeFilterTable  OBJECT-TYPE
           	SYNTAX  SEQUENCE OF ApTypeFilterEntry
           	ACCESS  not-accessible
          	STATUS  mandatory
               	DESCRIPTION
			"A table of Ethernet types (i.e. 16-bit DIX Ethernet
			 type), which are entered by the user and supported for
			 the type filtering function.
			 The maximum number of entries in the table is 16."
             	::= { apConfigMgmt 7 }

       	apTypeFilterEntry OBJECT-TYPE
           	SYNTAX  ApTypeFilterEntry
               	ACCESS  not-accessible
          	STATUS  mandatory
               	DESCRIPTION
                        "An entry in the table of Type Filter. 
			 A row in this table is created by setting the value of
			 etherType to Ethernet packet type in hexadecimal.
			 A row in this table is deleted by setting the value of
			 etherType to 00"
            	INDEX { typeIndex }
             	::= { apTypeFilterTable 1 }

      	ApTypeFilterEntry ::= SEQUENCE {
                typeIndex
                       	INTEGER,
                etherType
                    	OCTET STRING 
         	}

       	typeIndex OBJECT-TYPE
           	SYNTAX INTEGER (1..16)
          	ACCESS read-only
                STATUS mandatory
                DESCRIPTION
                     	"Filter Type Table index."
             	::= { apTypeFilterEntry 1 }     
 
       	etherType  OBJECT-TYPE
		SYNTAX	OCTET STRING (SIZE(1..2))
               	ACCESS  read-write
              	STATUS  mandatory
               	DESCRIPTION
                     	"A 16-bit Ethernet Protocol Type in hexadecimal." 
                ::= { apTypeFilterEntry 2 }

--
--  Access Point Performance Management (2)
--
	--  Access Point Traffic Matrix Table Group (2.1)
	--
	--  This group counts the number of packets from all protocol interfaces
	--  to a certain port interface (i.e. Ethernet, PPP, RF, AP Stack).
	--
 
       apTrafficMatrixTable OBJECT-TYPE
       		SYNTAX  SEQUENCE OF ApTrafficMatrixEntry
       		ACCESS  not-accessible
      		STATUS  mandatory
               	DESCRIPTION
               		"A table of Access Point Traffic Matrix which provides 
			 information on packets transmitted from one interface 
			 to another (Ethernet, PPP, radio, AP). The table also 
			 displays the number of broadcast packets transmitted 
			 from the Access Point.
			 The current number of entries is 5."
              	::= { apPerformMgmt 1 }

    	apTrafficMatrixEntry OBJECT-TYPE
           	SYNTAX  ApTrafficMatrixEntry
           	ACCESS  not-accessible
         	STATUS  mandatory
               	DESCRIPTION
                     	"An entry in the table of Access Point Traffic Matrix.
			 A row in this table cannot be created or deleted by
			 SNMP operations on columns of the table."
	        INDEX { apTMTableIndex }
              	::= { apTrafficMatrixTable 1}

   	ApTrafficMatrixEntry ::= SEQUENCE {
		apTMTableIndex
			INTEGER,
             	apProtoItfName
                	DisplayString,
           	apNPktsToEnets
                    	Counter,
           	apNPktsToPpps
                     	Counter,
          	apNPktsToRfs
                        Counter,
           	apNPktsToAPStks
                   	Counter
        	}

	apTMTableIndex OBJECT-TYPE
		SYNTAX	INTEGER (1..5)
              	ACCESS  read-only
               	STATUS  mandatory
               	DESCRIPTION
               	"Access Point Traffic Matrix Table index."
           	::= { apTrafficMatrixEntry 1 }

       apProtoItfName OBJECT-TYPE
       		SYNTAX  DisplayString (SIZE (1..12))
              	ACCESS  read-only
               	STATUS  mandatory
               	DESCRIPTION
               	"Access Point Protocol Interface Name (i.e. Ethernet, PPP, 
		 Radio, AP)."
           	::= { apTrafficMatrixEntry 2 }

     	apNPktsToEnets OBJECT-TYPE
        	SYNTAX  Counter
       		ACCESS  read-only
               	STATUS  mandatory
               	DESCRIPTION
                     	"Indicates the number of packets sent from the Access 
			 Point Protocol Interface to the Ethernet Interface.
			 This field should always be zero if the Access Point 
			 Protocol Interface is Ethernet."
           	::= { apTrafficMatrixEntry 3 }
 
    	apNPktsToPpps OBJECT-TYPE
         	SYNTAX  Counter
        	ACCESS  read-only
               	STATUS  mandatory
               	DESCRIPTION
                     	"Indicates the number of packets sent from the Access 
			 Point Protocol Interface to the PPP Interface. 
			 This field is meaningful only if the PPP interface is 
			 enabled. "
               ::= { apTrafficMatrixEntry 4 }

     	apNPktsToRfs OBJECT-TYPE
          	SYNTAX  Counter
        	ACCESS  read-only
             	STATUS  mandatory
               	DESCRIPTION
                     	"Indicates the number of packets sent from the Access 
			 Point Protocol Interface to the RF Interface. If the 
			 Access Point Protocol Interface is RF, these are 
			 frames from one MU to another."
            	::= { apTrafficMatrixEntry  5 }
 
   	apNPktsToAPStks OBJECT-TYPE
                SYNTAX  Counter
        	ACCESS  read-only
             	STATUS  mandatory
               	DESCRIPTION
               		"Indicates the number of packets sent from the Access 
			 Point Protocol Interface to the internal Access Point 
			 stack.  This field should always be zero if the Access
			 Point Protocol Interface is Access Point Stack."
                ::= { apTrafficMatrixEntry  6 }


	--
	--  Access Point Basic Interface Statistics/Counters Group (2.2)
	--
	--  This group contains the statistics/counters common to the four
 	--  interfaces on the Access Point (i.e. Ethernet, PPP, RF, AP Stack.)
	--

  	apItfStatTable OBJECT-TYPE
           	SYNTAX  SEQUENCE OF ApItfStatEntry
              	ACCESS  not-accessible
          	STATUS  mandatory
               	DESCRIPTION
               		"A table of Access Point Interfaces Statistics, which 
			 provides packets forwarding statistics for each inter-
			 face (Ethernet, PPP, RF, AP stack). 
			 Interface statistics also provide performance informa-
			 tion for each interface in Packets-per-second (PPS) and
			 Bytes- per-second (BPS).
			 The AP interface indicates packets sent to the AP stack
			 (e.g. configuration requests, SNMP, Telnet etc.).
			 The current number of entries is 4."
         	::= { apPerformMgmt 2 }
 
   	apItfStatEntry OBJECT-TYPE
              	SYNTAX  ApItfStatEntry
          	ACCESS  not-accessible
          	STATUS  mandatory
               	DESCRIPTION
               		"An entry in the table of Access Point Interface 
			 Statistics.
			 A row in this table cannot be created or deleted by
			 SNMP operations on columns of the table."
             	INDEX { apItfStatIndex }
               	::= { apItfStatTable 1 }

     	ApItfStatEntry ::= SEQUENCE { 
		apItfStatIndex
			INTEGER,
          	apInterfaceName
                 	DisplayString,
           	apPacketsIns
                     	Counter,
                apPacketsOuts
                    	Counter,
                apOctetsIns
                      	Counter,
                apOctetsOuts
                     	Counter,
                apPktsInPerSec
                    	Gauge,
          	apPktsOutPerSec
                   	Gauge,
          	apOctInPerSec
                     	Gauge,
          	apOctOutPerSec
                    	Gauge
   	}
 
      	apItfStatIndex OBJECT-TYPE
             	SYNTAX  INTEGER (1..4) 
                ACCESS  read-only
               	STATUS  mandatory
               	DESCRIPTION
                     	"Access Point Interface Statistics Table index."
           	::= { apItfStatEntry 1 }
 
      	apInterfaceName OBJECT-TYPE
             	SYNTAX  DisplayString (SIZE (1..12))
                ACCESS  read-only
               	STATUS  mandatory
               	DESCRIPTION
                     	"Access Point Interface Name (Ethernet, PPP, RF, 
			 AP)."
           	::= { apItfStatEntry 2 }
 
       	apPacketsIns OBJECT-TYPE
         	SYNTAX  Counter
          	ACCESS  read-only
               	STATUS  mandatory
               	DESCRIPTION
                     	"Indicates the number of good packets received on the 
			 specified interface."
          	::= { apItfStatEntry 3 }

        apPacketsOuts OBJECT-TYPE
                SYNTAX  Counter
          	ACCESS  read-only
               	STATUS  mandatory
               	DESCRIPTION
                     	"Indicates the number of packets successfully 
			 transmitted on the specified interface."
          	::= { apItfStatEntry 4 }

        apOctetsIns OBJECT-TYPE
          	SYNTAX  Counter
          	ACCESS  read-only
               	STATUS  mandatory
               	DESCRIPTION
                     	"Indicates the number of good bytes received on the 
			 specified interface."
           	::= { apItfStatEntry 5 }

        apOctetsOuts OBJECT-TYPE
         	SYNTAX  Counter
          	ACCESS  read-only
               	STATUS  mandatory
               	DESCRIPTION
                     	"Indicates the number of bytes successfully transmitted
			 on the specified interface."
           	::= { apItfStatEntry 6 }
 
       	apPktsInPerSec OBJECT-TYPE
              	SYNTAX  Gauge
            	ACCESS  read-only
               	STATUS  mandatory
               	DESCRIPTION
                     	"Indicates the number of good packets per second 
			 received on the specified Interface."
                ::= { apItfStatEntry 7 }

        apPktsOutPerSec OBJECT-TYPE
             	SYNTAX  Gauge
            	ACCESS  read-only
               	STATUS  mandatory
               	DESCRIPTION
                     	"Indicates the number of packets per second successfully
			 transmitted on the specified interface."
          	::= { apItfStatEntry 8 }
 
       	apOctInPerSec OBJECT-TYPE
               	SYNTAX  Gauge
            	ACCESS  read-only
               	STATUS  mandatory
               	DESCRIPTION
                     	"Indicates the number of good bytes per second 
			 received on the specified Interface."
           	::= { apItfStatEntry 9 }
 
       	apOctOutPerSec OBJECT-TYPE
              	SYNTAX  Gauge
            	ACCESS  read-only
               	STATUS  mandatory
               	DESCRIPTION
                     	"Indicates the number of bytes per second successfully
			 transmitted on the specified interface."
           	::= { apItfStatEntry 10 }


	--
	--  Access Point Ethernet Port Interface Statistics Group (2.3)
	-- 
	--  This group contains statistics/counters information specific to
 	--  the Access Point Ethernet Interface.
	-- 

  	apEPktsSeens OBJECT-TYPE
       		SYNTAX  Counter
         	ACCESS  read-only
               	STATUS  mandatory
               	DESCRIPTION
                     	"Indicates the number of packets that have been seen on
			 the Ethernet interface. Most of these packets are for
			 stations other than those associated with this AP."
          	::= { apEthernetStatistics 1 }
 
  	apEPktsForwardeds OBJECT-TYPE
           	SYNTAX  Counter
         	ACCESS  read-only
               	STATUS  mandatory
               	DESCRIPTION
                     	"Indicates the number of Ethernet packets forwarded
			 from the Ethernet interface to other interfaces."
         	::= { apEthernetStatistics 2 }

   	apEPktsDiscNoMatchs OBJECT-TYPE
         	SYNTAX  Counter
         	ACCESS  read-only
               	STATUS  mandatory
               	DESCRIPTION
                     	"Indicates the number of packets discarded due to 
			 unknown destination (i.e. no database entry)."
             	::= { apEthernetStatistics 3 }

   	apEPktsDiscForceds OBJECT-TYPE
          	SYNTAX  Counter
         	ACCESS  read-only
               	STATUS  mandatory
               	DESCRIPTION
                     	"Indicates the number of packets discarded due to Type
			 or Address filters applied."
         	::= { apEthernetStatistics 4 }
 
  	apEPktsDiscBuffers OBJECT-TYPE
          	SYNTAX  Counter
         	ACCESS  read-only
               	STATUS  mandatory
               	DESCRIPTION
                   	"Indicates the number of packets discarded due to lack 
			 of available buffers in AP."
          	::= { apEthernetStatistics 5 }
 
  	apEPktsDiscCRCs OBJECT-TYPE
             	SYNTAX  Counter
         	ACCESS  read-only
               	STATUS  mandatory
               	DESCRIPTION
                     	"Indicates the number of packets discarded due to CRC 
			 errors."
                ::= { apEthernetStatistics 6 }
 
  	apEPktsSents OBJECT-TYPE
                SYNTAX  Counter
         	ACCESS  read-only
               	STATUS  mandatory
               	DESCRIPTION
                     	"Indicates the number of packets sent by this Ethernet 
			 Port."
         	::= { apEthernetStatistics 7 }
 
  	apEAnyCollisions OBJECT-TYPE
            	SYNTAX  Counter
         	ACCESS  read-only
               	STATUS  mandatory
               	DESCRIPTION
                     	"Indicates the number of packets that suffer at least 
			 one collision."
             	::= { apEthernetStatistics 8 }

   	apE1orMoreColls OBJECT-TYPE
             	SYNTAX  Counter
         	ACCESS  read-only
               	STATUS  mandatory
               	DESCRIPTION
                     	"Indicates the number of packets that suffer more than
			 one collision."
           	::= { apEthernetStatistics 9 }
 
 	apEMaxCollisions OBJECT-TYPE
            	SYNTAX  Counter
         	ACCESS  read-only
               	STATUS  mandatory
               	DESCRIPTION
                     	"Indicates the number of packets that suffer more than
			 the maximum number of collisions."
            	::= { apEthernetStatistics 10 }
 
 	apELateCollisions OBJECT-TYPE
           	SYNTAX  Counter
         	ACCESS  read-only 
              	STATUS  mandatory
               	DESCRIPTION
                     	"Indicates the number of packets that suffer late 
			 collisions."
         	::= { apEthernetStatistics 11 }
 
 	apEPktsDefers OBJECT-TYPE
              	SYNTAX  Counter
         	ACCESS  read-only
               	STATUS  mandatory
               	DESCRIPTION
                     	"Indicates the times AP had to defer transmit requests
			 on Ethernet due to busy medium."
                ::= { apEthernetStatistics 12 }
 

	--       
	--  Radio Frequency Interface Statistics Group (2.4)
	--
	--  This group contains statistics/counters information specific to
	--  the Access Point Radio Frequency Interface.
	--

     	rfBcMcPktsSents OBJECT-TYPE
             	SYNTAX  Counter
          	ACCESS  read-only
               	STATUS  mandatory
               	DESCRIPTION
                     	"Indicates the number of broadcast/multicast packets 
			 that have been successfully transmitted."
                ::= { apRFStatistics 1 }

    	rfBcMcPktsRcvds OBJECT-TYPE
             	SYNTAX  Counter
          	ACCESS  read-only
               	STATUS  mandatory
               	DESCRIPTION
                     	"Indicates the number of broadcast/multicast packets 
			 that have been successfully received."
           	::= { apRFStatistics 2 }
 
     	rfBcMcOctSents OBJECT-TYPE
           	SYNTAX Counter
          	ACCESS  read-only
               	STATUS  mandatory
               	DESCRIPTION
                     	"Indicates the number of broadcast/multicast bytes that
			  have been successfully transmitted."
                ::= { apRFStatistics 3 }
 
    	rfBcMcOctRcvds OBJECT-TYPE
           	SYNTAX Counter
          	ACCESS  read-only
               	STATUS  mandatory
               	DESCRIPTION
                     	"Indicates the number of broadcast/multicast bytes that
			 have been successfully received."
           	::= { apRFStatistics 4 }
 
    	rfSysPktsSents OBJECT-TYPE
            	SYNTAX  Counter
         	ACCESS  read-only
               	STATUS  mandatory
               	DESCRIPTION
                     	"Indicates the number of system packets (includes probe
			 operations packets) that have been successfully 
			 transmitted."
           	::= { apRFStatistics 5 }
 
     	rfSysPktsRcvds OBJECT-TYPE
            	SYNTAX  Counter
         	ACCESS  read-only
               	STATUS  mandatory
               	DESCRIPTION
                     	"Indicates the number of system packets (includes probes
			 /associate packets) that have been successfully 
			 received."
              	::= { apRFStatistics 6 }

    	rfSBcMcPktsSents OBJECT-TYPE
            	SYNTAX  Counter
          	ACCESS  read-only 
              	STATUS  mandatory
               	DESCRIPTION
                     	"Indicates the number of system broadcast/multicast 
			 packets (includes beacons) that have been successfully 
			 transmitted."
                ::= { apRFStatistics 7 }

     	rfSBcMcPktsRcvds OBJECT-TYPE
            	SYNTAX  Counter
          	ACCESS  read-only
               	STATUS  mandatory
               	DESCRIPTION
                     	"Indicates the number of system broadcast/multicast 
			 iincludes beacons) packets that have been successfully
			 received."
            	::= { apRFStatistics 8 }

     	rfSuccFragPkts OBJECT-TYPE
              	SYNTAX Counter
          	ACCESS  read-only
               	STATUS  mandatory
               	DESCRIPTION
                	"Indicates the number of packets that were fragmented 
			 and for which all fragments were acked."
             	::= { apRFStatistics 9 }
 
   	rfUnsuccFragPkts OBJECT-TYPE
            	SYNTAX Counter
          	ACCESS  read-only
               	STATUS  mandatory
               	DESCRIPTION 
                    	"Indicates the number of packets that were fragmented 
			 but for which one or more fragments were not acked."
         	::= {apRFStatistics 10 }
 
    	rfTotalFragSents  OBJECT-TYPE
            	SYNTAX  Counter
          	ACCESS  read-only
               	STATUS  mandatory
               	DESCRIPTION
                     	"Indicates the number of packets fragments that have 
			 been sent."
             	::= { apRFStatistics 11 }

    	rfTotalFragRcvds OBJECT-TYPE
             	SYNTAX  Counter
          	ACCESS  read-only
               	STATUS  mandatory
               	DESCRIPTION
                     	"Indicates the number of packets fragments that have 
			 been received."
         	::= { apRFStatistics 12 }
 
   	rfSuccReassPkts OBJECT-TYPE
            	SYNTAX  Counter
          	ACCESS  read-only
               	STATUS  mandatory
               	DESCRIPTION
                     	"Indicates the number of packets that were reassigned 
			 and successfully reassembled."
              	::= { apRFStatistics 13 }
 
   	rfUnsuccReassPkts OBJECT-TYPE
           	SYNTAX  Counter
          	ACCESS  read-only
               	STATUS  mandatory
               	DESCRIPTION
                     	"Indicates the number of packets that were 
			 unsuccessfully reassembled."
           	::= { apRFStatistics 14 }
 
   	rfAssocMUs OBJECT-TYPE
           	SYNTAX  Counter
          	ACCESS  read-only
               	STATUS  mandatory
               	DESCRIPTION
                     	"Indicates the number of MUs currently associated with 
			 this AP."
          	::= { apRFStatistics 15 }
 
   	rfRcvdCRCErrors OBJECT-TYPE
             	SYNTAX  Counter
          	ACCESS  read-only
               	STATUS  mandatory
               	DESCRIPTION
                     	"Indicates the number of packets that were received but
			 had the CRC errors."
          	::= { apRFStatistics 16 }
 
   	rfRcvdDupPkts	OBJECT-TYPE
             	SYNTAX  Counter
          	ACCESS  read-only
               	STATUS  mandatory
               	DESCRIPTION
                     	"Indicates the number of packets that were received but
			 were duplicates of previously received. This is usually
			 an indication that an ACK was not received by the 
			 sending unit."
                ::= { apRFStatistics 17 }
 
   	rfTotalCollisions	OBJECT-TYPE
             	SYNTAX  Counter
          	ACCESS  read-only
               	STATUS  mandatory
               	DESCRIPTION
                     	"Indicates the number of collisions that have occured on
			 the interface. A collision on the RF interface means 
			 that an ack was not received or that a RTS was not 
			 answered by a CTS." 
          	::= { apRFStatistics 18 }
 
   	rfPktsWithoutColls OBJECT-TYPE
           	SYNTAX  Counter
          	ACCESS  read-only
               	STATUS  mandatory
               	DESCRIPTION
                     	"Indicates the number of packets without any collision."
            	::= { apRFStatistics 19 }
 
   	rfPktsWithMaxColls  OBJECT-TYPE
          	SYNTAX  Counter
          	ACCESS  read-only
               	STATUS  mandatory
               	DESCRIPTION
                     	"Indicates the number of packets that suffered the 
			 maximum number of collisions."
           	::= { apRFStatistics 20 }
 
   	rfPktsWithColls OBJECT-TYPE
              	SYNTAX  Counter
          	ACCESS  read-only
               	STATUS  mandatory
               	DESCRIPTION
                     	"Indicates the number of packets that suffered at least
			 one collision."
              	::= { apRFStatistics 21 }


	--
	--  Access Point RF Per Frequency Statistics Table Groupt (2.5)
	--
	--  This group contains the Access Point Radio Frequency Per 
	--  Frequency statistics/counters information based on the 
	--  historical frequency records used by this Access Point.
	--

      	apPerFreqStatTable OBJECT-TYPE
          	SYNTAX SEQUENCE OF ApPerFreqStatEntry
           	ACCESS not-accessible
           	STATUS mandatory
                DESCRIPTION
                     	"A table of Radio Per Frequency statistics, which is 
			 based on the historical frequency records used by this
			 Access Point.
			 The current number of entries is 78."
                ::= { apPerformMgmt 5 }
 
  	apPerFreqStatEntry OBJECT-TYPE
            	SYNTAX ApPerFreqStatEntry
               	ACCESS not-accessible
           	STATUS mandatory
                DESCRIPTION
                     	"An entry in the table of Radio per frequency 
			 statistics.
			 A row in this table cannot be created or deleted by
			 SNMP operations on columns of the table."
                INDEX { rfPerFqChannel}
                ::= { apPerFreqStatTable 1 }
 
   	ApPerFreqStatEntry ::= SEQUENCE {
               	rfPerFqChannel         
			INTEGER,
              	rfPerFqPktsSents      
			Counter,
                rfPerFqPktsRcvds      
			Counter,
                rfPerFqRetries       
			Counter
   	}
 
      	rfPerFqChannel OBJECT-TYPE
               	SYNTAX  INTEGER (2..79)
          	ACCESS  read-only
                STATUS  mandatory
                DESCRIPTION
                     	"Radio Frequency channel number."
                ::= { apPerFreqStatEntry 1 }

      	rfPerFqPktsSents OBJECT-TYPE
                SYNTAX  Counter
          	ACCESS  read-only
                STATUS  mandatory
                DESCRIPTION
                     	"Counter for the packets sent per frequency." 
             	::= { apPerFreqStatEntry 2 }

      	rfPerFqPktsRcvds OBJECT-TYPE
                SYNTAX  Counter
          	ACCESS  read-only
                STATUS  mandatory
                DESCRIPTION
                     	"Counter for the packets received per frequency." 
             	::= { apPerFreqStatEntry 3 }

      	rfPerFqRetries OBJECT-TYPE
                SYNTAX  Counter
          	ACCESS  read-only
                STATUS  mandatory
                DESCRIPTION
                     	"Counter for the retries per frequency." 
             	::= { apPerFreqStatEntry 4 }


	--
	--  Access Point Serial Port Statistics Group (2.6)
	--
	--  This group contains Serial Port interface statistics/counters
	--  information.
	--

  	apNbrOfDialouts OBJECT-TYPE
             	SYNTAX  Counter
          	ACCESS  read-only
               	STATUS  mandatory
               	DESCRIPTION 
                    	"Indicates the number of dialout attempts by the AP."
           	::= { apSerialPortStatistics 1 }

   	apDialoutFailures  OBJECT-TYPE
               	SYNTAX  Counter
          	ACCESS  read-only
               	STATUS  mandatory
               	DESCRIPTION
                     	"Indicates the number of dialout failures by the AP."
         	::= { apSerialPortStatistics 2 }

   	apNbrOfAnswers  OBJECT-TYPE
            	SYNTAX  Counter
          	ACCESS  read-only
               	STATUS  mandatory
               	DESCRIPTION
                     	"Indicates the number of answer attempts by the AP."
           	::= { apSerialPortStatistics 3 }
 
   	apCurrCallTime  OBJECT-TYPE
             	SYNTAX  TimeTicks
                ACCESS  read-only
               	STATUS  mandatory
               	DESCRIPTION
                     	"Indicates the length in seconds of current connection
			 session. Note: the time is relative to the boot time 
			 of this AP."
            	::= { apSerialPortStatistics 4 }

   	apLastCallTime  OBJECT-TYPE
             	SYNTAX  TimeTicks
                ACCESS  read-only
               	STATUS  mandatory
               	DESCRIPTION
                     	"Indicates the length in seconds of last connection 
			 session. Note: the time is relative to the boot time 
			 of this AP."
            	::= { apSerialPortStatistics 5 }
 

	--
	--  WNMP Statistics Table Group (2.7)
	--
	--  This group contains statistic/counter information for the WNMP 
	--  interface to AP.
	--

 	apWNMPCfgPkts OBJECT-TYPE
                SYNTAX  Counter
          	ACCESS  read-only
               	STATUS  mandatory
               	DESCRIPTION
               		"Indicates the number of WNMP configuration requests 
			 received from NetVision."
            	::= { apWNMPStatistics 1 }
 
        wEchoRequests OBJECT-TYPE
           	SYNTAX  Counter
          	ACCESS  read-only
               	STATUS  mandatory
               	DESCRIPTION
                     	"Indicates the number of WNMP Echo Requests received 
			 by this AP."
               	::= { apWNMPStatistics 2 }
 
        wPingRequests OBJECT-TYPE 
          	SYNTAX  Counter
          	ACCESS  read-only
               	STATUS  mandatory
               	DESCRIPTION
                     	"Indicates the number of WNMP ping requests received by
			 this AP."
                ::= { apWNMPStatistics 3 }
 
        wPktsFromNVs OBJECT-TYPE
              	SYNTAX  Counter
          	ACCESS  read-only
               	STATUS  mandatory
               	DESCRIPTION
                     	"Indicates the number of WNMP packets that were received
			 from NetVision via this AP."
          	::= { apWNMPStatistics 4 }
 
        wPPktsToNVs OBJECT-TYPE
                SYNTAX  Counter
          	ACCESS  read-only
               	STATUS  mandatory
               	DESCRIPTION
                     	"Indicates the number of WNMP packets that were sent to
			 the NetVision via this AP."
               	::= { apWNMPStatistics 5 }
 
        wPassThruEchoes  OBJECT-TYPE
             	SYNTAX  Counter
          	ACCESS  read-only
               	STATUS  mandatory
               	DESCRIPTION 
                     	"Indicates the number of WNMP packets for other stations
			 that passed through this AP."
               	::= { apWNMPStatistics 6 }

 
	--
	--  The Access Point MU Information Group (2.8)
	--
   	--  This group contains the Global Statistics/Counter information for 
	--  All MUs which has/had been associated with this AP.
     	--

      	apCurrentMUs  OBJECT-TYPE
               	SYNTAX  Counter
         	ACCESS  read-only
               	STATUS  mandatory
               	DESCRIPTION
                     	"Indicates the number of MUs currently associated with 
			 this AP."
            	::= { apMUInfo 1 }

      	apMaxMUs  OBJECT-TYPE
           	SYNTAX  Counter
         	ACCESS  read-only
               	STATUS  mandatory
               	DESCRIPTION
                     	"Indicates the highest number of MUs ever associated 
			 with this AP."
            	::= { apMUInfo 2 }
 
     	apTotalAssocs  OBJECT-TYPE
               	SYNTAX  Counter
         	ACCESS  read-only
               	STATUS  mandatory
               	DESCRIPTION
                     	"Indicates the total number of associations by all MUs 
			 with this AP."
            	::= { apMUInfo 3 }
 
   	apMUTable OBJECT-TYPE
              	SYNTAX  SEQUENCE OF ApMUEntry
             	ACCESS  not-accessible
          	STATUS  mandatory
               	DESCRIPTION
                     	"A table of information for a specific MU associated 
			 with this Access Point.
			 The current number of entries is 128."
         	::= { apMUInfo 4 }
 
     	apMUEntry OBJECT-TYPE
              	SYNTAX  ApMUEntry
         	ACCESS  not-accessible
          	STATUS  mandatory
               	DESCRIPTION
                     	"An entry in the table of information for a specific MU
			 associated with this Access Point.
			 A row in this table cannot be created or deleted by
			 SNMP operations on columns of the table."
          	INDEX { muIndex }
           	::= { apMUTable 1}
 
        ApMUEntry ::= SEQUENCE {
		muIndex
			INTEGER,
          	muMacAddr
                     	PhysAddress,
                muInterface
                 	INTEGER,
            	muState
                 	INTEGER,
                muPowerMode
                 	INTEGER,
                muStationID
                 	INTEGER,
              	muLastAPAddr
                   	PhysAddress,
                muTotalAssoc
                 	INTEGER,
                muAssocStart
                        TimeTicks,
            	muLstAssStrt
                    	TimeTicks,
              	muLastAssEnd
                      	TimeTicks,
                muNPktsSents
                  	Counter,
                muNPktsRcvds
                  	Counter,
                muNBytesSents
                 	Counter,
                muNBytesRcvds
                 	Counter,
		muNDiscdPkts
			Counter,
                muTmLastData
                     	TimeTicks
       	}
 
      	muIndex OBJECT-TYPE
             	SYNTAX  INTEGER (1..128) 
                ACCESS  read-only
               	STATUS  mandatory
               	DESCRIPTION
                     	"Specific MU information Table index."
           	::= { apMUEntry 1 }
 
      	muMacAddr OBJECT-TYPE
         	SYNTAX  PhysAddress
             	ACCESS  read-only
               	STATUS  mandatory
               	DESCRIPTION
                     	"The MAC address of the MU associated with this AP."
              	::= { apMUEntry 2 }
 
   	muInterface OBJECT-TYPE
             	SYNTAX  INTEGER {
                       	ethernet(1),    -- MU is located in Ethernet Interface.
                 	ppp(2),         -- MU is located in PPP Interface.
                      	rf(3),          -- MU is located in RF Interface.
                       	apstack(4)      -- MU is located in AP internal stack 
					-- interface.
             	}
               	ACCESS  read-only
               	STATUS  mandatory
               	DESCRIPTION
                     	"Indicates the interface on which this MU is located.
                   	 Note: The AP may learn of an MU via the RF network
                       	 or from the wired networks such as Ethernet or PPP.
                     	 In this release, the AP does not keep track of those 
			 MUs reachable via the Ethernet, but that will change 
			 in future releases."
            	::= { apMUEntry 3 }

  	muState OBJECT-TYPE
             	SYNTAX  INTEGER {
                      	associated(3),		-- used for an associated MU
                      	not-associated(4)	-- Not associated, roamed to 
						-- another AP.
               	}
               	ACCESS  read-only
               	STATUS  mandatory
               	DESCRIPTION
                     	"Indicates the state of this MU."
         	::= { apMUEntry 4 }

        muPowerMode	OBJECT-TYPE
             	SYNTAX  INTEGER {
                 	cam(1),			-- continue active mode
			psp(2)			-- power save mode
		}
               	ACCESS  read-only
               	STATUS  mandatory
               	DESCRIPTION
                     	"Indicates the MU power mode (Power Save Protocol mode
			 or Continue Active Mode.)"
         	::= { apMUEntry 5 }

        muStationID	OBJECT-TYPE
             	SYNTAX  INTEGER 
               	ACCESS  read-only
               	STATUS  mandatory
               	DESCRIPTION
                     	"Indicates the MU station ID."
         	::= { apMUEntry 6 }

        muLastAPAddr	 OBJECT-TYPE
               	SYNTAX  PhysAddress
             	ACCESS  read-only
               	STATUS  mandatory
               	DESCRIPTION
                     	"Indicates the MAC address of the last AP with which 
			 this MU had an association."
              	::= { apMUEntry 7 }

	muTotalAssoc	OBJECT-TYPE
             	SYNTAX  INTEGER 
               	ACCESS  read-only
               	STATUS  mandatory
               	DESCRIPTION
			"Indicates the total associations for this MU."
              	::= { apMUEntry 8 }

        muAssocStart	OBJECT-TYPE
            	SYNTAX  TimeTicks
               	ACCESS  read-only
               	STATUS  mandatory
               	DESCRIPTION
                     	"Indicates when the MU began its current association 
			 with this AP. 
			 Note: Time is represented in seconds and the time
                     	 is relative to the boot time of this AP.
                 	 This is also true for all the association objects 
			 listed below."
                ::= { apMUEntry 9 }
 
      	muLstAssStrt	 OBJECT-TYPE
                SYNTAX  TimeTicks
               	ACCESS  read-only
               	STATUS  mandatory
               	DESCRIPTION
                     	"Indicates when the MU began its prior association 
			 with this AP. 
                 	 If this is the first association with this AP, this 
			 value is zero. "
            	::= { apMUEntry 10 }
 
  	muLastAssEnd	OBJECT-TYPE
          	SYNTAX  TimeTicks
               	ACCESS  read-only
               	STATUS  mandatory
               	DESCRIPTION
                     	"Indicates when the MU ended its previous association 
			 with this AP. 
                 	 If this is the first association with this AP, this 
			 value is zero. "
            	::= { apMUEntry 11 }
 
  	muNPktsSents  OBJECT-TYPE
             	SYNTAX  Counter
         	ACCESS  read-only
               	STATUS  mandatory
               	DESCRIPTION
                     	"Indicates the number of packets successfully 
			 transmitted to this MU."
            	::= { apMUEntry 12 }
 
  	muNPktsRcvds  OBJECT-TYPE
             	SYNTAX  Counter
         	ACCESS  read-only
               	STATUS  mandatory
               	DESCRIPTION
                     	"Indicates the number of Good Packets received from this
			 MU."
              	::= { apMUEntry 13 }
 
  	muNBytesSents  OBJECT-TYPE
            	SYNTAX  Counter
         	ACCESS  read-only
               	STATUS  mandatory
               	DESCRIPTION
                     	"Indicates the number of bytes successfully transmitted
			 to this MU."
              	::= { apMUEntry 14 }
 
  	muNBytesRcvds  OBJECT-TYPE
            	SYNTAX  Counter
         	ACCESS  read-only
               	STATUS  mandatory
               	DESCRIPTION
                     	"Indicates the number of Good Bytes received from this 
			 MU."
               	::= { apMUEntry 15 }

	muNDiscdPkts	OBJECT-TYPE
            	SYNTAX  Counter
         	ACCESS  read-only
               	STATUS  mandatory
               	DESCRIPTION
                     	"Indicates the number of received packets discarded 
			 because no buffers."
               	::= { apMUEntry 16 }

        muTmLastData	 OBJECT-TYPE
                SYNTAX  TimeTicks
               	ACCESS  read-only
               	STATUS  mandatory
               	DESCRIPTION
                     	"Indicates the time when the last good packet was 
			 received from this MU. 
                 	 The packet may be either an ACK, Data, or Poll. "
         	::= { apMUEntry 17 }


	--
	--  Known APs Information Table Group (2.9)
	--  (Remote AP configuration)
	--
	--  This group contains informations about the other Access Points known
	--  by this Access Point.
	--        
 
       	apKnownAPsTable OBJECT-TYPE
       		SYNTAX SEQUENCE OF ApKnownAPsEntry
           	ACCESS not-accessible
              	STATUS mandatory
                DESCRIPTION
               		"A table of information on other Access Points known by 
			 this Access Point. 
			 The current number of entries is 32."
            	::= { apPerformMgmt  9 }

  	apKnownAPsEntry OBJECT-TYPE
              	SYNTAX ApKnownAPsEntry
            	ACCESS not-accessible
               	STATUS mandatory
                DESCRIPTION
                	"An entry in the table of information on the Known 
			 Access Points.
			 A row in this table cannot be created or deleted by
			 SNMP operations on columns of the table."
               	INDEX { apAPMacAddr }
           	::= { apKnownAPsTable 1 }

       	ApKnownAPsEntry ::= SEQUENCE {
          	apAPMacAddr     
			PhysAddress,
            	apAPIpAddr      
			IpAddress,
              	apNetID         
			OCTET STRING,
                apAPID          
			OCTET STRING,
                apHoppingSeq    
			INTEGER,
                apMUs           
			INTEGER,
                apKBOS  	
			INTEGER,
                apKBIS          
			INTEGER,
                apLastRcvd      
			TimeTicks
       	}

       	apAPMacAddr OBJECT-TYPE
               	SYNTAX PhysAddress
        	ACCESS read-only
                STATUS mandatory
                DESCRIPTION
                     	"Mac Address of Known AP."
              	::= { apKnownAPsEntry 1 }

       	apAPIpAddr  OBJECT-TYPE
             	SYNTAX IpAddress 
               	ACCESS read-only
                STATUS mandatory
                DESCRIPTION
                     	"IP Address of Known AP."
               	::= { apKnownAPsEntry 2 }

       	apNetID OBJECT-TYPE
             	SYNTAX  OCTET STRING (SIZE(1..2))
              	ACCESS read-only
                STATUS mandatory
                DESCRIPTION
                     	"Network ID (i.e. ESS ID) of the Known AP in 
			 hexadecimal."
            	::= { apKnownAPsEntry 3 }

       	apAPID  OBJECT-TYPE
             	SYNTAX  OCTET STRING (SIZE(1..2))
               	ACCESS read-only
                STATUS mandatory
                DESCRIPTION
                	"AP ID (i.e. BSS ID) of the Known AP in hexadecimal."
         	::= { apKnownAPsEntry 4 }
 
      	apHoppingSeq OBJECT-TYPE
           	SYNTAX INTEGER
             	ACCESS read-only
                STATUS mandatory
                DESCRIPTION
               		"Hopping Sequence of Known AP."
         	::= { apKnownAPsEntry 5 }
 
      	apMUs OBJECT-TYPE
               	SYNTAX INTEGER
         	ACCESS read-only
                STATUS mandatory
                DESCRIPTION
                     "Indicates the number of MUs currently associated with AP."
              	::= { apKnownAPsEntry 6 }
 
      	apKBOS OBJECT-TYPE
             	SYNTAX INTEGER
              	ACCESS read-only
                STATUS mandatory
                DESCRIPTION
                     "Kilobytes sent per second by AP on the radio interface."
              	::= { apKnownAPsEntry 7 }
 
      	apKBIS OBJECT-TYPE
            	SYNTAX INTEGER
              	ACCESS read-only
                STATUS mandatory
                DESCRIPTION
                     "Kilobytes received per second by AP on the radio 
		      interface."
              	::= { apKnownAPsEntry 8 }
 
      	apLastRcvd OBJECT-TYPE
             	SYNTAX TimeTicks
                ACCESS read-only
                STATUS mandatory
                DESCRIPTION
                     "Last communication in seconds with AP. Consistent values
		      greater than 12 may indicate a communication failure with
		      AP."
              	::= { apKnownAPsEntry 9 }


	--
       	--  Access Point Mobile Unit MAC Address Filtering and Packet Type 
	--  Filtering Statistics Group (2.10)
	--

 	apAdrViolations  OBJECT-TYPE
            	SYNTAX  Counter
          	ACCESS  read-only
               	STATUS  mandatory
               	DESCRIPTION
                     	"Indicates the number of Mobile Unit MAC address 
			 violations counted."
            	::= { apFilterStatistics 1 }
 
 	apTypeViolations  OBJECT-TYPE
            	SYNTAX  Counter
          	ACCESS  read-only
               	STATUS  mandatory
               	DESCRIPTION
                     	"Indicates the number of Ethernet packet type violations
			 counted."
               	::= { apFilterStatistics 2 }

      
	--
       	-- Wireless AP Statistics Group (2.11)
	--

 	apNbrOfWLAPItfs  OBJECT-TYPE
            	SYNTAX  Counter
          	ACCESS  read-only
               	STATUS  mandatory
               	DESCRIPTION
                     	"Indicates number of WLAP interfaces established."
               	::= { apWLAPInfo 1 }

 	apWLAPState  OBJECT-TYPE
            	SYNTAX  INTEGER {
                    	initializing(1),    
	              	sending-probe(2),  
                    	send-assoc-req(3),    
                    	send-cfg-bpdu(4),    
                    	wait-for-probe(5),    
                    	send-Probe-rsp(6),    
                    	send-assoc-rsp(7),    
                    	send-cfg-rsp(8),    
                    	received-root-rsp(10),    
                    	root-wlap-lost(12),    
                    	disabled(14),
                    	functional(15)    
	              	}
          	ACCESS  read-only
               	STATUS  mandatory
               	DESCRIPTION
                     	"Indicates the current WLAP state. The state values and
			 meanings are as follows :
			 - During power-up initialization :
                    		Initializing(1)    
	              		SendingProbe(2)  
                    		SendAssocReq(3)    
                    		SendCfgBPDU(4)    
                    		WaitForProbe(5)    
                    		SendProbeRsp(6)    
                    		SendAssocRsp(7)    
                    		SendCfgRsp(8)
                    		ReceivedRootRsp(10)    
			 - During WLAP operation :
                    		RootWLAPLost(12)
                    		Disabled(14)
                    		Functional(15)    
			"
               	::= { apWLAPInfo 2 }

	apWLAPHopSequence OBJECT-TYPE
            	SYNTAX  INTEGER
          	ACCESS  read-only
               	STATUS  mandatory
               	DESCRIPTION
                     	"Indicates the hop sequence of the Root AP followed by
			 this WLAP."
               	::= { apWLAPInfo 3 }

 	apRootInterface  OBJECT-TYPE
            	SYNTAX  INTEGER
          	ACCESS  read-only
               	STATUS  mandatory
               	DESCRIPTION
                     	"Indicates the WLAP interface leading to the Root AP."
               	::= { apWLAPInfo 4 }

 	apRootWLAPID  OBJECT-TYPE
             	SYNTAX  OCTET STRING (SIZE(1..8))
          	ACCESS  read-only
               	STATUS  mandatory
               	DESCRIPTION
                     	"Indicates the WLAP ID of the Root AP. It consists of
			 2 bytes of priority (default is 0x8000) and 6 bytes of
			 MAC address of the Root AP"
               	::= { apWLAPInfo 5 }

 	apRootPathCost  OBJECT-TYPE
            	SYNTAX  INTEGER
          	ACCESS  read-only
               	STATUS  mandatory
               	DESCRIPTION
                     	"Indicates how many hops away the current WLAP is from
			 the Root AP."
               	::= { apWLAPInfo 6 }

 	apWLAPID  OBJECT-TYPE
             	SYNTAX  OCTET STRING (SIZE(1..8))
          	ACCESS  read-only
               	STATUS  mandatory
               	DESCRIPTION
                     	"Indicates the WLAP ID of the current WLAP. It consists 
			 of 2 bytes of priority (default is 0x8000) and 6 bytes 
			 MAC address of the current WLAP"
               	::= { apWLAPInfo 7 }

	apWLAPItfTable	OBJECT-TYPE
       		SYNTAX SEQUENCE OF ApWLAPItfEntry
           	ACCESS not-accessible
              	STATUS mandatory
                DESCRIPTION
               		"A table of wireless AP interfaces information, which 
			 contains four (4) interfaces : Ethernet and three 
			 AP-to-AP interfaces or just all four AP-to-AP 
			 interfaces.
			 The current number of entries is 4."
            	::= { apWLAPInfo  8 }

	apWLAPItfEntry	 OBJECT-TYPE
              	SYNTAX ApWLAPItfEntry
            	ACCESS not-accessible
               	STATUS mandatory
                DESCRIPTION
                	"An entry in the table of wireless AP interfaces 
			 information.
			 A row in this table cannot be created or deleted by
			 SNMP operations on columns of the table."
               	INDEX { apWLAPItfID }
           	::= { apWLAPItfTable 1 }

	ApWLAPItfEntry ::= SEQUENCE {
		apWLAPItfID	      
			OCTET STRING,
		apWLAPItfAddr   
			PhysAddress,
		apWLAPItfState	      
			INTEGER,
		apWLAPPathCost	      
			INTEGER,
		apDsgnatedRoot   
			OCTET STRING,
		apDsgnatedCost   
			INTEGER,
		apDsgnatedWLAP 
			OCTET STRING,
		apDsgnatedItf    
			OCTET STRING
	}

      	apWLAPItfID OBJECT-TYPE
             	SYNTAX  OCTET STRING (SIZE(1..2))
              	ACCESS read-only
                STATUS mandatory
                DESCRIPTION
                     	"WLAP interface ID. It consists of 1 byte of priority 
			 (default is 0x80) and 1 byte of interface ID."
              	::= { apWLAPItfEntry 1 }
 
       	apWLAPItfAddr  OBJECT-TYPE
             	SYNTAX  PhysAddress 
               	ACCESS read-only
                STATUS mandatory
                DESCRIPTION
                	"The MAC address of the associated WLAP on this 
			 interface.
			 For Ethernet, this is the Bridge Group Address :
			 	01-80-C2-00-00-00. 
			 For AP-to-AP, this is the associated WLAP MAC address."
         	::= { apWLAPItfEntry 2 }
 
      	apWLAPItfState OBJECT-TYPE
            	SYNTAX INTEGER {
			disabled(1),
			listening(2),
			learning(3),
			forwarding(4),
			blocking(5)
		}
              	ACCESS read-only
                STATUS mandatory
                DESCRIPTION
                     "The current state of the Wireless AP interface, ie :
		      Disabled(1), Listening(2), Learning(3), Forwarding(4), or
		      Blocking(5)."
              	::= { apWLAPItfEntry 3 }
 
      	apWLAPPathCost OBJECT-TYPE
            	SYNTAX INTEGER
              	ACCESS read-only
                STATUS mandatory
                DESCRIPTION
                     "The cost to be added to the root path cost field in the 
		      config BPDU (Bridge Protocol Data Unit) received on this 
		      interface in order to determine the cost of the path to 
		      the Root AP."
              	::= { apWLAPItfEntry 4 }
 
       	apDsgnatedRoot  OBJECT-TYPE
             	SYNTAX  OCTET STRING (SIZE(1..8))
               	ACCESS read-only
                STATUS mandatory
                DESCRIPTION
			"The unique Root AP ID designated by the Root AP."
         	::= { apWLAPItfEntry 5 }
 
      	apDsgnatedCost OBJECT-TYPE
            	SYNTAX INTEGER
              	ACCESS read-only
                STATUS mandatory
                DESCRIPTION
                     	"The cost of the path to the Root AP designated by the
			 Root AP."
              	::= { apWLAPItfEntry 6 }
 
       	apDsgnatedWLAP  OBJECT-TYPE
             	SYNTAX  OCTET STRING (SIZE(1..8))
               	ACCESS read-only
                STATUS mandatory
                DESCRIPTION
			"The unique WLAP ID designated by the Root AP."
         	::= { apWLAPItfEntry 7 }
 
      	apDsgnatedItf OBJECT-TYPE
             	SYNTAX  OCTET STRING (SIZE(1..2))
              	ACCESS read-only
                STATUS mandatory
                DESCRIPTION
			"The WLAP interface ID designated by the Root AP."
              	::= { apWLAPItfEntry 8 }
 
--	
--  Access Point Fault Management (3)
--
	apClrAllStatistics	OBJECT-TYPE
              	SYNTAX  INTEGER {
			yes (1),
			no (2)
			}
              	ACCESS  read-write
              	STATUS  mandatory
               	DESCRIPTION
                     	"Clear all the interface statistics (yes = 1, no = 2)."
          	::= { apFaultMgmt 1 }

	apClrMUTable	OBJECT-TYPE
              	SYNTAX  INTEGER {
			yes (1),
			no (2)
			}
              	ACCESS  read-write
              	STATUS  mandatory
               	DESCRIPTION
                     	"Clear the MU Table (yes = 1, no = 2)."
          	::= { apFaultMgmt 2 }
 
	apClrACL	OBJECT-TYPE
              	SYNTAX  INTEGER {
			yes (1),
			no (2)
			}
              	ACCESS  read-write
              	STATUS  mandatory
               	DESCRIPTION
                     	"Clear the Access Control Table (yes = 1, no = 2)."
          	::= { apFaultMgmt 3 }
 
       	apClrACLRangeTable  OBJECT-TYPE
             	SYNTAX  INTEGER {
			yes (1),
			no (2)
			}
          	ACCESS  read-write
               	STATUS  mandatory
               	DESCRIPTION
                     	"Clear the Access Control Range Table (yes = 1, no = 2)."
          	::= { apFaultMgmt 4 }
 
	apClrAddrFilterTbl	OBJECT-TYPE
              	SYNTAX  INTEGER {
			yes (1),
			no (2)
			}
              	ACCESS  read-write
              	STATUS  mandatory
               	DESCRIPTION
                     	"Clear the Address Filtering Table (yes = 1, no = 2)."
          	::= { apFaultMgmt 5 }
 
	apLdACLFrMUList	OBJECT-TYPE
              	SYNTAX  INTEGER {
			yes (1),
			no (2)
			}
              	ACCESS  read-write
              	STATUS  mandatory
               	DESCRIPTION
                     	"Load the Access Control Table from MU Table (yes = 1, 
			 no = 2)."
          	::= { apFaultMgmt 6 }
 
	apModemDialOut	OBJECT-TYPE
              	SYNTAX  INTEGER {
			yes (1),
			no (2)
			}
              	ACCESS  read-write
              	STATUS  mandatory
               	DESCRIPTION
                     	"Commands the modem to dialout (yes = 1, no = 2)."
          	::= { apFaultMgmt 7 }
 
	apModemHangUp	OBJECT-TYPE
              	SYNTAX  INTEGER {
			yes (1),
			no (2)
			}
              	ACCESS  read-write
              	STATUS  mandatory
               	DESCRIPTION
                     	"Forces the AP to issue a 'hangup' string to the modem
			 attached to the serial port (yes = 1, no = 2). 
			 This command is meaningful only if the AP is configured
			 for a modem connection on the serial port. If there is
			 no modem or there is no connection, the command will be
			 ignored."
          	::= { apFaultMgmt 8 }
 
	apUpdateFirmware OBJECT-TYPE
              	SYNTAX  INTEGER {
			yes (1),
			no (2)
			}
              	ACCESS  read-write
              	STATUS  mandatory
               	DESCRIPTION
                     	"Update the AP firmware through TFTP server. The AP
			 firmware will be saved in NVRAM (yes = 1, no = 2). 
			 Before issuing this command, set 'apDnLdFileName', 
			 and 'apTFTPServer' to the proper values "
          	::= { apFaultMgmt 9 }
 
	apDnLdFileName	OBJECT-TYPE
             	SYNTAX  DisplayString (SIZE (1..50))
              	ACCESS  read-write
              	STATUS  mandatory
               	DESCRIPTION
                     	"The name of the file to be downloaded to the AP. 
			 (Including path name and total up to 49 characters.)
			 Note: IF BOOTP is responded to, that name will take
			 precedence and overwrite this name."
          	::= { apFaultMgmt 10 }
 
	apTFTPServer	OBJECT-TYPE
              	SYNTAX  IpAddress
              	ACCESS  read-write
              	STATUS  mandatory
               	DESCRIPTION
                     	"The IP address for the TFTP Server."
          	::= { apFaultMgmt 11 }
 
	apResetAP	OBJECT-TYPE
              	SYNTAX  INTEGER {
			yes (1),
			no (2)
			}
              	ACCESS  read-write
              	STATUS  mandatory
               	DESCRIPTION
			"Forces a reset of the AP (yes = 1, no = 2).
			 Upon reset, the AP clears all the statistics and 
			 restores the last saved configuration information. If 
			 changes are made without being saved, the AP clears 
			 those changes upon reset." 
          	::= { apFaultMgmt 12 }
 

--
--  Access Point Security Management (4)
--

       	apACLViolations  OBJECT-TYPE
             	SYNTAX  Counter
          	ACCESS  read-only
               	STATUS  mandatory
               	DESCRIPTION
                     	"Indicates the number of Access Control violations 
			 occurred."
                ::= { apSecurityMgmt 1 }
 
       	apSaveConfig  OBJECT-TYPE
             	SYNTAX  INTEGER {
			yes (1),
			no (2)
			}
          	ACCESS  read-write
               	STATUS  mandatory
               	DESCRIPTION
                     	"Saves the current configuration to NVRAM (yes = 1, 
			 no = 2)." 
                ::= { apSecurityMgmt 2 }
 
     	--  Access Point Access Control Table
       	--  The Access Point Access Control Table is currently supported under 
	--  the MAC addresses of the MUs only. No other control criteria is 
	--  defined at this time.
 	--
 
     	apAccCtrlTable  OBJECT-TYPE
           	SYNTAX  SEQUENCE OF ApAccCtrlEntry
         	ACCESS  not-accessible
          	STATUS  mandatory
               	DESCRIPTION
			"A table of MAC addresses allowed to associate with the 
			 Access Point.
			 The maximum number of entries in the table is 128."
          	::= { apSecurityMgmt 3 }

       	apAccCtrlEntry OBJECT-TYPE
              	SYNTAX  ApAccCtrlEntry
             	ACCESS  not-accessible
          	STATUS  mandatory
               	DESCRIPTION
                     	"An entry in the table of MAC address Access Control. 
			 A row in this table is created by setting the value of
			 allowedMU to the MAC address of the MU allowed to 
			 associate with this Access Point. 
			 A row in this table is deleted by setting the value of
			 allowedMU to '000000000000'."
         	INDEX { allowedIndex }
             	::= { apAccCtrlTable 1 }

      	ApAccCtrlEntry ::= SEQUENCE {
		allowedIndex
			INTEGER,
              	allowedMU
                       	PhysAddress
             	}

       	allowedIndex  OBJECT-TYPE
          	SYNTAX	INTEGER (1..128)
              	ACCESS  read-only
              	STATUS  mandatory
               	DESCRIPTION
                     	"Access Control Table index."
                ::= { apAccCtrlEntry 1 }
 
       	allowedMU  OBJECT-TYPE
          	SYNTAX  PhysAddress
              	ACCESS  read-write
              	STATUS  mandatory
               	DESCRIPTION
                     	"MU MAC address which is allowed to associate with 
			 this AP." 
                ::= { apAccCtrlEntry 2 }

     	apACLRangeTable  OBJECT-TYPE
           	SYNTAX  SEQUENCE OF ApACLRangeEntry
         	ACCESS  not-accessible
          	STATUS  mandatory
               	DESCRIPTION
                     	"A table of Access Control Range, which consists of 
			 eight (8) pairs of low and high MAC addresses. 
			 Any Mobile Unit with the MAC address within the range 
			 is allowed to associate with the Access Point.
			 The maximum number of entries in the table is 8."
          	::= { apSecurityMgmt 4 }

       	apACLRangeEntry OBJECT-TYPE
              	SYNTAX  ApACLRangeEntry
             	ACCESS  not-accessible
          	STATUS  mandatory
               	DESCRIPTION
                     	"An entry in the table of MAC address Access Control
			 Range. 
			 A row in this table is created by first setting the 
			 value of lowMacAddr to the lowest MAC address and then
			 the value of highMacAddr to the highest MAC address of
			 a group of Mobile Units allowed to associate with this
			 Access Point. This sequence of setting is very 
			 important, otherwise a wrong result will occur.
			 A row in this table is deleted by setting the value of
			 either lowMacAddr or highMacAddr  to '000000000000'."
         	INDEX { apACLRangeIndex }
             	::= { apACLRangeTable 1 }

      	ApACLRangeEntry ::= SEQUENCE {
		apACLRangeIndex
			INTEGER,
              	lowMacAddr
                       	PhysAddress,
              	highMacAddr
                       	PhysAddress
             	}

       	apACLRangeIndex  OBJECT-TYPE
          	SYNTAX	INTEGER (1..8)
              	ACCESS  read-only
              	STATUS  mandatory
               	DESCRIPTION
                     	"Access Control Range Table index."
                ::= { apACLRangeEntry 1 }
 
       	lowMacAddr  OBJECT-TYPE
          	SYNTAX  PhysAddress
              	ACCESS  read-write
              	STATUS  mandatory
               	DESCRIPTION
                     	"The lowest Mobile Unit MAC address in the range which 
			 is allowed to be associated with this AP." 
                ::= { apACLRangeEntry 2 }
 
       	highMacAddr  OBJECT-TYPE
          	SYNTAX  PhysAddress
              	ACCESS  read-write
              	STATUS  mandatory
               	DESCRIPTION
                     	"The highest Mobile Unit MAC address in the range which
			 is allowed to be associated with this AP." 
                ::= { apACLRangeEntry 3 }
 
END
