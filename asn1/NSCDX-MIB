NSCDX-MIB DEFINITIONS ::= BEGIN

-- Title:	NSC DX MIB version 1.2 in concise format
-- Date:	11 January 1995
-- By:		John Lyman <john.lyman@nsco.network.com>

IMPORTS
	OBJECT-TYPE
	    FROM RFC1155-SMI
	DisplayString
	    FROM RFC1213-MIB
        nscDx 
            FROM NSC-MIB;

-- 
-- nscDX Configuration
--

nscDxConfig OBJECT IDENTIFIER ::= { nscDx 1 }

nscDxConfigSecondsToReset OBJECT-TYPE
	SYNTAX	INTEGER
	ACCESS	read-write
	STATUS	mandatory
	DESCRIPTION
		"Seconds to reset the DX unit.  If this value is SET non-zero,
		it will get decremented once per second.  When the count
		reaches zero the DX unit is reset.  If the value is reSET to
		zero before it counts down to zero, then the DX unit will
		not be reset."
	::= { nscDxConfig 1 }

nscDxConfigFirmwareRevTab OBJECT-TYPE
	SYNTAX	DisplayString (SIZE(1..7))
	ACCESS	read-only
	STATUS	mandatory
	DESCRIPTION
		"Nucleus firmware revision and tab number.  This is a string
		of the form 'x.y'; where x is the major version number and y
		is the minor version number."
	::= { nscDxConfig 2 }

nscDxConfigBufferMemorySize OBJECT-TYPE
	SYNTAX	INTEGER
	ACCESS	read-only
	STATUS	mandatory
	DESCRIPTION
		"Buffer memory size (k)."
	::= { nscDxConfig 3 }

nscDxConfigSecondsSinceMc OBJECT-TYPE
	SYNTAX	INTEGER
	ACCESS	read-only
	STATUS	mandatory
	DESCRIPTION
		"Seconds since master clear."
	::= { nscDxConfig 4 }

nscDxConfigProcessorMask OBJECT-TYPE
	SYNTAX	DisplayString (SIZE(16))
	ACCESS	read-only
	STATUS	mandatory
	DESCRIPTION
		"Bit mask of available processors.  This is a string where each
		character represents the availability of a processor.  The
		leftmost character coresponds to processor 0 and the rightmost
		character corresponds to processor 15.  Each character will be
		a hex digit 0..F if the processor is active, else it is a '.'."
	::= { nscDxConfig 5 }

nscDxConfigControlAddr OBJECT-TYPE
	SYNTAX	OCTET STRING (SIZE(4))
	ACCESS	read-only
	STATUS	mandatory
	DESCRIPTION
		"The DX unit's HYPERchannel address."
	::= { nscDxConfig 6 }

nscDxConfigLargePageSize OBJECT-TYPE
	SYNTAX	INTEGER
	ACCESS	read-only
	STATUS	mandatory
	DESCRIPTION
		"Size in bytes of large pages."
	::= { nscDxConfig 7 }

nscDxConfigBoardInfoTable OBJECT-TYPE
	SYNTAX	SEQUENCE OF NscDxConfigBoardInfoEntry
	ACCESS	not-accessible
	STATUS	mandatory
	DESCRIPTION
		"Board configuration information."
	::= { nscDxConfig 8 }

nscDxConfigBoardInfoEntry OBJECT-TYPE
	SYNTAX	NscDxConfigBoardInfoEntry
	ACCESS	not-accessible
	STATUS	mandatory
	DESCRIPTION
		"Board configuration entry."
	INDEX	{ nscDxConfigBoardInfoEntSlotNum }
	::= { nscDxConfigBoardInfoTable 1 }

NscDxConfigBoardInfoEntry ::= SEQUENCE {
	nscDxConfigBoardInfoEntSlotNum
		INTEGER,
	nscDxConfigBoardInfoEntBoardPart
		DisplayString
}

nscDxConfigBoardInfoEntSlotNum OBJECT-TYPE
	SYNTAX	INTEGER
	ACCESS	read-only
	STATUS	mandatory
	DESCRIPTION
		"Slot number the board is in."
	::= { nscDxConfigBoardInfoEntry 1 }

nscDxConfigBoardInfoEntBoardPart OBJECT-TYPE
	SYNTAX	DisplayString (SIZE(9))
	ACCESS	read-only
	STATUS	mandatory
	DESCRIPTION
		"Board part number.  This string represents the partnumber
		of the hardware; the format is xxxxxx-tt.  Where xxxxxx is the
		partnumber and tt is the tab."
	::= { nscDxConfigBoardInfoEntry 2 }

nscDxConfigTime OBJECT-TYPE
	SYNTAX	DisplayString (SIZE(8))
	ACCESS	read-only
	STATUS	mandatory
	DESCRIPTION
		"Current time.  The time is returned as a string with the format
		of hh:mm:ss.  Where hh is hours, mm is minutes, and ss is seconds."
	::= { nscDxConfig 9 }

nscDxConfigDate OBJECT-TYPE
	SYNTAX	DisplayString (SIZE(10))
	ACCESS	read-only
	STATUS	mandatory
	DESCRIPTION
		"Current date.  The date is returned as a string with the format
		of mm/dd/yyyy.  Where mm is the month, dd is the day, and yyyy
		is the year."
	::= { nscDxConfig 10 }

nscDxConfigStartType OBJECT-TYPE
	SYNTAX	INTEGER {
		    reset(1),
		    powerup(2)
		}
	ACCESS	read-only
	STATUS	mandatory
	DESCRIPTION
		"Method of startup."
	::= { nscDxConfig 11 }

nscDxConfigMemoryDivision OBJECT-TYPE
	SYNTAX	INTEGER
	ACCESS	read-only
	STATUS	mandatory
	DESCRIPTION
		"Beginning of big buffers."
	::= { nscDxConfig 12 }

--
-- nscDX Processor Table
--

nscDxProcTable OBJECT-TYPE
	SYNTAX	SEQUENCE OF NscDxProcTableEntry
	ACCESS	not-accessible
	STATUS	mandatory
	DESCRIPTION
		"List of processor entries."
	::= { nscDx 2 }

nscDxProcTableEntry OBJECT-TYPE
	SYNTAX	NscDxProcTableEntry
	ACCESS	not-accessible
	STATUS	mandatory
	DESCRIPTION
		"Processor entry."
	INDEX	{ nscDxProcTableEntKeyId }
	::= { nscDxProcTable 1 }

NscDxProcTableEntry ::= SEQUENCE {
	nscDxProcTableEntKeyId
		INTEGER,
	nscDxProcTableEntType
		DisplayString,
	nscDxProcTableEntFirmwareNum
		DisplayString,
	nscDxProcTableEntHardwareNum
		DisplayString,
	nscDxProcTableEntBaseAddr
		OCTET STRING,
	nscDxProcTableEntPost
		DisplayString
}

nscDxProcTableEntKeyId OBJECT-TYPE
	SYNTAX	INTEGER (0..'F'h)
	ACCESS	read-only
	STATUS	mandatory
	DESCRIPTION
		"Processor Key ID (KID). This is a unique
		value for each interface."
	::= { nscDxProcTableEntry 1 }

nscDxProcTableEntType OBJECT-TYPE
	SYNTAX	DisplayString (SIZE(4))
	ACCESS	read-only
	STATUS	mandatory
	DESCRIPTION
		"Processor type code.  See appendix A of the
		Nucleus Reference Manual (460456)."
	::= { nscDxProcTableEntry 2 }

nscDxProcTableEntFirmwareNum OBJECT-TYPE
	SYNTAX	DisplayString (SIZE(9))
	ACCESS	read-only
	STATUS	mandatory
	DESCRIPTION
		"Firmware part number.  This string represents the partnumber
		of the firmware; the format is xxxxxx-tt.  Where xxxxxx is the
		partnumber and tt is the tab."
	::= { nscDxProcTableEntry 3 }

nscDxProcTableEntHardwareNum OBJECT-TYPE
	SYNTAX	DisplayString (SIZE(9))
	ACCESS	read-only
	STATUS	mandatory
	DESCRIPTION
		"Hardware part number.  This string represents the partnumber
		of the hardware; the format is xxxxxx-tt.  Where xxxxxx is the
		partnumber and tt is the tab."
	::= { nscDxProcTableEntry 4 }

nscDxProcTableEntBaseAddr OBJECT-TYPE
	SYNTAX	OCTET STRING (SIZE(4))
	ACCESS	read-only
	STATUS	mandatory
	DESCRIPTION
		"The base HYPERchannel address of the processor."
	::= { nscDxProcTableEntry 5 }

nscDxProcTableEntPost OBJECT-TYPE
	SYNTAX	DisplayString (SIZE(4))
	ACCESS	read-only
	STATUS	mandatory
	DESCRIPTION
		"POST completion code. 0 = POST completed successfully."
	::= { nscDxProcTableEntry 6 }

END
