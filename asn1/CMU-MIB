CMU-MIB DEFINITIONS ::= BEGIN
	IMPORTS enterprises FROM SNMPv2-SMI
	;
	
		proteon OBJECT IDENTIFIER ::= { enterprises 1 }
		ibm OBJECT IDENTIFIER ::= { enterprises 2 }
		cmu OBJECT IDENTIFIER ::= { enterprises 3 }
		unix OBJECT IDENTIFIER ::= { enterprises 4 }
		acc OBJECT IDENTIFIER ::= { enterprises 5 }
		twg OBJECT IDENTIFIER ::= { enterprises 6 }
		cayman OBJECT IDENTIFIER ::= { enterprises 7 }
		psi OBJECT IDENTIFIER ::= { enterprises 8 }
		cisco OBJECT IDENTIFIER ::= { enterprises 9 }
		nsc OBJECT IDENTIFIER ::= { enterprises 10 }
		hp OBJECT IDENTIFIER ::= { enterprises 11 }
		epilogue OBJECT IDENTIFIER ::= { enterprises 12 }
		utk OBJECT IDENTIFIER ::= { enterprises 13 }
		bbn OBJECT IDENTIFIER ::= { enterprises 14 }
		xylogics OBJECT IDENTIFIER ::= { enterprises 15 }
		timeplex OBJECT IDENTIFIER ::= { enterprises 16 }
		canstar OBJECT IDENTIFIER ::= { enterprises 17 }
		wellfleet OBJECT IDENTIFIER ::= { enterprises 18 }
		trw OBJECT IDENTIFIER ::= { enterprises 19 }
		mit OBJECT IDENTIFIER ::= { enterprises 20 }
		eon OBJECT IDENTIFIER ::= { enterprises 21 }
		spartacus OBJECT IDENTIFIER ::= { enterprises 22 }
		excelan OBJECT IDENTIFIER ::= { enterprises 23 }
		spider OBJECT IDENTIFIER ::= { enterprises 24 }
		nsfnet OBJECT IDENTIFIER ::= { enterprises 25 }
		hls OBJECT IDENTIFIER ::= { enterprises 26 }
		xyplex OBJECT IDENTIFIER ::= { enterprises 33 }
		cray OBJECT IDENTIFIER ::= { enterprises 34 }
		sun OBJECT IDENTIFIER ::= { enterprises 42 }
		synoptics OBJECT IDENTIFIER ::= { enterprises 45 }
		dec OBJECT IDENTIFIER ::= { enterprises 36 }
		tgv OBJECT IDENTIFIER ::= { enterprises 58 }
		apple OBJECT IDENTIFIER ::= { enterprises 63 }
		nat OBJECT IDENTIFIER ::= { enterprises 86 }
		snmp-research OBJECT IDENTIFIER ::= { enterprises 99 }
		ftp OBJECT IDENTIFIER ::= { enterprises 121 }
		shiva OBJECT IDENTIFIER ::= { enterprises 166 }
		transarc OBJECT IDENTIFIER ::= { enterprises 257 }
		lexcel OBJECT IDENTIFIER ::= { enterprises 379 }

END
