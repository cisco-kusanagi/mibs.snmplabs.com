--
-- MIB ASN.1 for 3Com LinkBuilder MSH 4 port Ethernet Bridge 3C18600
--                    Version 1 13th May 1994.
--
-- Standard groups and tables that are not implemented
-- are in here, but commented out.
--
-- This is for software release 1.x of the 3C18600
--


 	LBHUB-MSH4PTBRDG-MIB DEFINITIONS ::= BEGIN
    IMPORTS
            Counter, Gauge, TimeTicks, enterprises, internet,
            IpAddress, mgmt, NetworkAddress, experimental
        FROM RFC1155-SMI

            OBJECT-TYPE
        FROM RFC-1212
		  TRAP-TYPE FROM RFC-1215
        ;


    private         OBJECT IDENTIFIER ::= { internet 4 }
    enterprises     OBJECT IDENTIFIER ::= { private 1 }

    mib-2           OBJECT IDENTIFIER ::= { mgmt 1 }

    system          OBJECT IDENTIFIER ::= { mib-2 1 }
    interfaces      OBJECT IDENTIFIER ::= { mib-2 2 }
    ip              OBJECT IDENTIFIER ::= { mib-2 4 }
    icmp            OBJECT IDENTIFIER ::= { mib-2 5 }
    tcp             OBJECT IDENTIFIER ::= { mib-2 6 }
    udp             OBJECT IDENTIFIER ::= { mib-2 7 }
    egp             OBJECT IDENTIFIER ::= { mib-2 8 }

    transmission    OBJECT IDENTIFIER ::= { mib-2 10 }
    dot3            OBJECT IDENTIFIER ::= { --! POINTER Dot3_OID
                                                transmission 7 }

    snmp            OBJECT IDENTIFIER ::= { mib-2 11 }
    ifExtensions    OBJECT IDENTIFIER ::= { mib-2 12 }
    dot1dBridge     OBJECT IDENTIFIER ::= { --! POINTER Dot1d_OID
                                                mib-2 17 }


    -- Our private tree space.

    constellation   OBJECT IDENTIFIER ::= { enterprises 187 }

    -- Put Internet Experimental MIBS under cExper

    cExper          OBJECT IDENTIFIER ::= { constellation 1 }



--
-- From RFC 1271, RMON
--
       --       EntryStatus ::= INTEGER
       --                  { valid(1),
       --                    createRequest(2),
       --                    underCreation(3),
       --                    invalid(4)
       --                  }

              -- The status of a table entry.
              --
              -- Setting this object to the value invalid(4) has the
              -- effect of invalidating the corresponding entry.
              -- That is, it effectively disassociates the mapping
              -- identified with said entry.
              -- It is an implementation-specific matter as to whether
              -- the agent removes an invalidated entry from the table.
              -- Accordingly, management stations must be prepared to
              -- receive tabular information from agents that corresponds
              -- to entries currently not in use.  Proper
              -- interpretation of such entries requires examination
              -- of the relevant EntryStatus object.
              --
              -- An existing instance of this object cannot be set to
              -- createRequest(2).  This object may only be set to
              -- createRequest(2) when this instance is created.  When
              -- this object is created, the agent may wish to create
              -- supplemental object instances to complete a conceptual
              -- row in this table.  Immediately after completing the
              -- create operation, the agent must set this object to
              -- underCreation(3).
              --
              -- Entries shall exist in the underCreation(3) state until
              -- the management station is finished configuring the
              -- entry and sets this object to valid(1) or aborts,
              -- setting this object to invalid(4).  If the agent
              -- determines that an entry has been in the
              -- underCreation(3) state for an abnormally long time,
              -- it may decide that the management station has
              -- crashed.  If the agent makes this decision,
              -- it may set this object to invalid(4) to reclaim the
              -- entry.  A prudent agent will understand that the
              -- management station may need to wait for human input
              -- and will allow for that possibility in its
              -- determination of this abnormally long period.

-- RFC 1213 defines MIB-II


          -- textual conventions

          DisplayString ::= OCTET STRING
          -- This data type is used to model textual information taken
          -- from the NVT ASCII character set.  By convention, objects
          -- with this syntax are declared as having
          --
          --      SIZE (0..255)

          PhysAddress ::= OCTET STRING
          -- This data type is used to model media addresses.  For many
          -- types of media, this will be in a binary representation.
          -- For example, an ethernet address would be represented as
          -- a string of 6 octets.

          Timeout ::= INTEGER

          -- groups in MIB-II




    --
    -- Product Registration Hierarchy
    --
    cProducts       OBJECT IDENTIFIER ::= { constellation 2 }

    cLittleDipper   OBJECT IDENTIFIER ::= { --! POINTER Dipper_OID
                                                cProducts 1 }
    cAuriga         OBJECT IDENTIFIER ::= { --! POINTER Auriga_OID
                                                cProducts 3 }

    cCarina         OBJECT IDENTIFIER ::= { cProducts 4 }
    cCarinaAui      OBJECT IDENTIFIER ::= { --! POINTER CarinaAui_OID
                                                cCarina 1 }
    cCarinaBnc      OBJECT IDENTIFIER ::= { --! POINTER CarinaBnc_OID
                                                cCarina 2 }
    --
    -- This subtree is allocated for the use of the dupont
    -- product family.
    --

    cDuPont         OBJECT IDENTIFIER ::= { cProducts 5 }
    cDuPontAui      OBJECT IDENTIFIER ::= { --! POINTER DuPontAui_OID
                                                cDuPont 1 }
    --
    -- This subtree is allocated for the use of the datability
    -- product family.
    --

    cDatabil        OBJECT IDENTIFIER ::= { cProducts 6 }
    cDatability     OBJECT IDENTIFIER ::= { --! POINTER Datability_OID
                                                cDatabil 1 }

    --
    --
    -- This subtree is allocated for the use of the penril
    -- product family.
    --

    cPenr           OBJECT IDENTIFIER ::= { cProducts 7 }
    cPenril         OBJECT IDENTIFIER ::= { --! POINTER Penril_OID
                                                cPenr 1 }
    --
    --
    -- This subtree is allocated for the use of the 3com
    -- product family.
    --
       cThreeCom      OBJECT IDENTIFIER ::= { cProducts 8 }
       cThreeComMSH   OBJECT IDENTIFIER ::= { --! POINTER ThreeComMSH_OID
	                                       cThreeCom 1 }





    --
    -- Subtree to contain proprietary extensions to the standard MIB-II
    -- Groups. In theory, these extensions are in ALL constellation
    -- products
    --

    cStdExtensions  OBJECT IDENTIFIER ::= { constellation 3 }

    -- Each extension subtree's OID is similar to the OID of the
    -- related group in MIB-II in that if the MIB-II group's OID
    -- is defined as { mib-2 n } then the extension subtree's
    -- OID is defined as { cStdExtensions n }.
    --
    -- These subtrees contain extensions to the standard mibs that
    -- are common across all Constellation Products.
    --

    cSystem         OBJECT IDENTIFIER ::= { cStdExtensions 1 }
    cInterfaces     OBJECT IDENTIFIER ::= { cStdExtensions 2 }
    cIp             OBJECT IDENTIFIER ::= { cStdExtensions 4 }
    cIcmp           OBJECT IDENTIFIER ::= { cStdExtensions 5 }
    cTcp            OBJECT IDENTIFIER ::= { cStdExtensions 6 }
    cUdp            OBJECT IDENTIFIER ::= { cStdExtensions 7 }

    cTransmission   OBJECT IDENTIFIER ::= { cStdExtensions 10 }
    cDot3           OBJECT IDENTIFIER ::= { cTransmission 7 }

    cSnmp           OBJECT IDENTIFIER ::= { cStdExtensions 11 }

    --
    -- This subtree contains MIB Objects that are specific to the
    -- Little Dipper and Leech-I (carina/auriga/pyxis) products.
    --

    cConstellation  OBJECT IDENTIFIER ::= { constellation 4 }


    --
    -- This branch of our subtree defines the internal party
    -- proxy goop. This is also our Transport Domain.
    --
    cProxys         OBJECT IDENTIFIER ::= { --! POINTER CP_TDomain_OID
                                                constellation 5 }

    --
    -- Proxys for bridgelets are identified under the cProxyLb
    -- subtree. In general, a proxy for logical bridge "n" is
    -- defined as:
    --     cProxyLbN  OBJECT IDENTIFIER ::= { cProxyLb N+1 }
    --

    cProxyLb        OBJECT IDENTIFIER ::= { cProxys 1 }
    cProxyLb0       OBJECT IDENTIFIER ::= { --! POINTER Proxy_LB0_OID
                                                cProxyLb 1 }
    cProxyLb1       OBJECT IDENTIFIER ::= { --! POINTER Proxy_LB1_OID
                                                cProxyLb 2 }
    cProxyLb2       OBJECT IDENTIFIER ::= { --! POINTER Proxy_LB2_OID
                                                cProxyLb 3 }
    cProxyLb3       OBJECT IDENTIFIER ::= { --! POINTER Proxy_LB3_OID
                                                cProxyLb 4 }

    --
    -- Proxys for logical routers are identified under the cProxyLr
    -- subtree. In general, a proxy for logical router "n" is
    -- defined as:
    --     cProxyLrN  OBJECT IDENTIFIER ::= { cProxyLr N+1 }
    --

    cProxyLr        OBJECT IDENTIFIER ::= { cProxys 2 }
    cProxyLr0       OBJECT IDENTIFIER ::= { --! POINTER Proxy_LR0_OID
                                                cProxyLr 1 }


    --
    -- Constellation IP extensions. A couple of counters
    -- that are extensions on the ipInHdrErrors object.
    -- All of these counters are included within the
    -- ipInHdrErrors object.
    --
    cIpInLenErrors OBJECT-TYPE
        SYNTAX  Counter
        ACCESS  read-only

        STATUS  mandatory
        DESCRIPTION
            "Number of packets received with an inconsistant
            Header/Packet length"
        ::= { cIp 1 }

    cIpInVersionErrors OBJECT-TYPE
        SYNTAX  Counter
        ACCESS  read-only

        STATUS  mandatory
        DESCRIPTION
            "Number of packets received with an incorrect
            IP version number."
        ::= { cIp 2 }

    cIpInCSErrors OBJECT-TYPE
        SYNTAX  Counter
        ACCESS  read-only

        STATUS  mandatory
        DESCRIPTION
            "Number of packets received with an incorrect
            IP checksum."
        ::= { cIp 3 }

    cIpTTLZero OBJECT-TYPE
        SYNTAX  Counter
        ACCESS  read-only

        STATUS  mandatory
        DESCRIPTION
            "Number of packets that would have been forwarded
            but their TTL went to 0."
        ::= { cIp 4 }

    cIpReasmTimeOuts OBJECT-TYPE
        SYNTAX  Counter
        ACCESS  read-only
        STATUS  mandatory

        DESCRIPTION
            "Number of reassmebly timeouts. This is included inthe
            ipReasmFails object."
        ::= { cIp 5 }

    --
    -- Extensions to arp MIB that belong to US!!!!!
    --
    cIpNetToMedia   OBJECT IDENTIFIER ::= { cIp 7 }

    cIpNetToMediaTableSize OBJECT-TYPE
        SYNTAX  INTEGER
        ACCESS  read-only
        STATUS  mandatory

        DESCRIPTION
            "The maximum number of entries that can be in the
            cIpNetToMediaTable/ipNetToMediaTable."
        ::= { cIpNetToMedia 1 }

    cIpNetToMediaCompleteTimeOut OBJECT-TYPE
        SYNTAX  INTEGER
        ACCESS  read-write
        STATUS  mandatory

        DESCRIPTION
            "The maximum age, in minutes, that a completed entry
            may remain in the table before it is timed out and discarded."
        ::= { cIpNetToMedia 2 }

    cIpNetToMediaInCompleteTimeOut OBJECT-TYPE
        SYNTAX  INTEGER
        ACCESS  read-write
        STATUS  mandatory

        DESCRIPTION
            "The maximum age, in minutes, that an incomplete entry
            may remain in the table before it is timed out and discarded."
        ::= { cIpNetToMedia 3 }

    cIpNetToMediaIns    OBJECT-TYPE
        SYNTAX  Counter
        ACCESS  read-only
        STATUS  mandatory

        DESCRIPTION
            "Total number of arp packets received."
        ::= { cIpNetToMedia 4 }

    cIpNetToMediaInLenErrs  OBJECT-TYPE
        SYNTAX  Counter
        ACCESS  read-only
        STATUS  mandatory

        DESCRIPTION
            "Total number of arp packets received which had
            inconsistant or incorrect lengths. These packets are
            ignored."
        ::= { cIpNetToMedia 5 }

    cIpNetToMediaInNotEther OBJECT-TYPE
        SYNTAX  Counter
        ACCESS  read-only
        STATUS  mandatory

        DESCRIPTION
            "Total number of arp packets received which specified
            a hardware type other than Ethernet. These packets are
            ignored."
        ::= { cIpNetToMedia 6 }

    cIpNetToMediaInNoArpOnIf    OBJECT-TYPE
        SYNTAX  Counter
        ACCESS  read-only
        STATUS  mandatory

        DESCRIPTION
            "Number of ARP packets received in an interface for which
            ARP is disabled."
        ::= { cIpNetToMedia 7 }

    cIpNetToMediaInIp   OBJECT-TYPE
        SYNTAX  Counter
        ACCESS  read-only
        STATUS  mandatory

        DESCRIPTION
            "Number of ARP packets received specifying IP."
        ::= { cIpNetToMedia 8 }

    cIpNetToMediaInIpTrailers   OBJECT-TYPE
        SYNTAX  Counter
        ACCESS  read-only
        STATUS  mandatory

        DESCRIPTION
            "Number of ARP packets received specifying IP Trailers."
        ::= { cIpNetToMedia 9 }

    cIpNetToMediaInUnkProtos    OBJECT-TYPE
        SYNTAX  Counter
        ACCESS  read-only
        STATUS  mandatory

        DESCRIPTION
            "Number of ARP packets received specifying an unknown
            protocol."
        ::= { cIpNetToMedia 10 }

    cIpNetToMediaInSourceBcast  OBJECT-TYPE
        SYNTAX  Counter
        ACCESS  read-only
        STATUS  mandatory

        DESCRIPTION
            "Number of ARP packets received with a broadcast or multicast
            source hardware address."
        ::= { cIpNetToMedia 11 }

    cIpNetToMediaInDups OBJECT-TYPE
        SYNTAX  Counter
        ACCESS  read-only
        STATUS  mandatory

        DESCRIPTION
            "Number of ARP packets received that originated from another
            node but had the IP address of this node in the packet's
            source protocol address field."
        ::= { cIpNetToMedia 12 }

    cIpNetToMediaInRequests OBJECT-TYPE
        SYNTAX  Counter
        ACCESS  read-only
        STATUS  mandatory

        DESCRIPTION
            "Number of ARP Requests received."
        ::= { cIpNetToMedia 13 }

    cIpNetToMediaInResponses    OBJECT-TYPE
        SYNTAX  Counter
        ACCESS  read-only
        STATUS  mandatory

        DESCRIPTION
            "Number of ARP Responses received."
        ::= { cIpNetToMedia 14 }

    cIpNetToMediaInProxyOks OBJECT-TYPE
        SYNTAX  Counter
        ACCESS  read-only
        STATUS  mandatory

        DESCRIPTION
            "Number of proxy ARP requests that we received and
            have answered."
        ::= { cIpNetToMedia 15 }

    cIpNetToMediaOutReplys  OBJECT-TYPE
        SYNTAX  Counter
        ACCESS  read-only
        STATUS  mandatory

        DESCRIPTION
            "Number of ARP replys sent."
        ::= { cIpNetToMedia 16 }

    cIpNetToMediaOutRequests    OBJECT-TYPE
        SYNTAX  Counter
        ACCESS  read-only
        STATUS  mandatory

        DESCRIPTION
            "Number of ARP requests sent."
        ::= { cIpNetToMedia 17 }

    cIpNetToMediaReqBadAddrs    OBJECT-TYPE
        SYNTAX  Counter
        ACCESS  read-only
        STATUS  mandatory

        DESCRIPTION
            "Number of times that a request was for an incorrect
            IP address (such as the broadcast)."
        ::= { cIpNetToMedia 18 }

    cIpNetToMediaNoResponses    OBJECT-TYPE
        SYNTAX  Counter
        ACCESS  read-only
        STATUS  mandatory

        DESCRIPTION
            "Number of times that a request timed out."
        ::= { cIpNetToMedia 19 }

    cIpNetToMediaAgeOuts    OBJECT-TYPE
        SYNTAX  Counter
        ACCESS  read-only
        STATUS  mandatory

        DESCRIPTION
            "Number of times that an entry was aged out of the arp
            cache because it had not been referenced recently."
        ::= { cIpNetToMedia 20 }

    cIpNetToMediaTable OBJECT-TYPE
        SYNTAX  SEQUENCE OF CIpNetToMediaEntry
        ACCESS  not-accessible
        STATUS  mandatory
        DESCRIPTION
            "Table containing Constellation extensions to the
            IP Address Translation (IpNetToMedia) table defined above."
        ::= { cIpNetToMedia 21 }

    cIpNetToMediaEntry OBJECT-TYPE
        SYNTAX  CIpNetToMediaEntry
        ACCESS  not-accessible
        STATUS  mandatory
        DESCRIPTION
            "Each entry contains Constellation extensions for one
             IpAddress to `physical' address equivalence."
        INDEX   { cIpNetToMediaIfIndex, cIpNetToMediaNetAddress }
        ::= { cIpNetToMediaTable 1 }

    CIpNetToMediaEntry ::= SEQUENCE {
        cIpNetToMediaIfIndex
            INTEGER,
        cIpNetToMediaNetAddress
            IpAddress,
        cIpNetToMediaRefTime
            TimeTicks,
        cIpNetToMediaProxyRespond
            INTEGER,
        cIpNetToMediaComplete
            INTEGER,
        cIpNetToMediaUseTrailers
            INTEGER
    }

    cIpNetToMediaIfIndex OBJECT-TYPE
        SYNTAX  INTEGER
        ACCESS  read-write
        STATUS  mandatory

        DESCRIPTION
            "The interface on which this entry's equivalence is
            effective.  The interface identified by a particular value
            of this index is the same interface as identified by the
            same value of ifIndex."
        ::= { cIpNetToMediaEntry 1 }

    cIpNetToMediaNetAddress OBJECT-TYPE
        SYNTAX  IpAddress
        ACCESS  read-write
        STATUS  mandatory

        DESCRIPTION
            "The IpAddress corresponding to the media- dependent
            `physical' address."
        ::= { cIpNetToMediaEntry 2 }

    cIpNetToMediaRefTime OBJECT-TYPE
        SYNTAX  TimeTicks
        ACCESS  read-only
        STATUS  mandatory

        DESCRIPTION
            "The value of sysUpTime when this entry was last referenced."
        ::= { cIpNetToMediaEntry 3 }

    cIpNetToMediaProxyRespond OBJECT-TYPE
        SYNTAX  INTEGER { true(1), false(2) }
        ACCESS  read-only
        STATUS  mandatory

        DESCRIPTION
            "Is true(1) if this node willrespond to this IP Address
            following the rules of proxy arp. Otherwise this object
            is false(2).

            Setting this object to false(2) will have the effect of
            preventing this node from responding to this address. Setting
            this object to true(1) will cause this node to begin
            responding to this address."
--        DEFVAL { false }
        ::= { cIpNetToMediaEntry 4 }

    cIpNetToMediaComplete OBJECT-TYPE
        SYNTAX  INTEGER { true(1), false(2) }
        ACCESS  read-only
        STATUS  mandatory

        DESCRIPTION
            "Is true(1) if the table entry is complete -- that is to say,
            the ipNetToMediaPhysAddress contains a valid value. If this
            object is false then the physical address may not be correct.
            Typically, a 0 length octet string is returned if the
            entry is not complete."
        ::= { cIpNetToMediaEntry 5 }

    cIpNetToMediaUseTrailers OBJECT-TYPE
        SYNTAX  INTEGER { true(1), false(2) }
        ACCESS  read-only
        STATUS  mandatory

        DESCRIPTION
            "Is true(1) if this entry will use ARP trailers. Otherwise
            this object is false(2)."
--        DEFVAL { false }
        ::= { cIpNetToMediaEntry 6 }




    -- Constellation Extensions to the icmp group. Primarily, these are
    -- more detailed error indications and detailed breakdowns
    -- for the individual message codes for destination unreachable,
    -- time exceeded, and redirect messages.

    -- Breakdowns of the individual codes for the Redirect Message.
    -- The total of these objects should match the value of
    -- icmpInRedirects. Any discrepancy indicates that some redirects
    -- came in with unknown codes.
    cIcmpInRedirectNet      OBJECT-TYPE
        SYNTAX  Counter
        ACCESS  read-only
        STATUS  mandatory

        DESCRIPTION
            "Number of ICMP Destination Unreachable, Network
            Unreachable messages received."
        ::= { cIcmp 1 }

    cIcmpInRedirectHost     OBJECT-TYPE
        SYNTAX  Counter
        ACCESS  read-only
        STATUS  mandatory

        DESCRIPTION
            "Number of ICMP Destination Unreachable, Host
            Unreachable messages received."
        ::= { cIcmp 2 }

    cIcmpInRedirectNetTos   OBJECT-TYPE
        SYNTAX  Counter
        ACCESS  read-only
        STATUS  mandatory

        DESCRIPTION
            "Number of ICMP Destination Unreachable, Network/TOS
            Unreachable messages received."
        ::= { cIcmp 3 }

    cIcmpInRedirectHostTos  OBJECT-TYPE
        SYNTAX  Counter
        ACCESS  read-only
        STATUS  mandatory

        DESCRIPTION
            "Number of ICMP Destination Unreachable, Host/TOS
            Unreachable messages received."
        ::= { cIcmp 4 }

    -- Breakdowns of the individual codes for the Time Exceeded Message.
    -- The total of these objects should match the value of
    -- icmpInTimeExcds. Any discrepancy indicates that some redirects
    -- came in with unknown codes.

    cIcmpInTimeExcTTL       OBJECT-TYPE
        SYNTAX  Counter
        ACCESS  read-only
        STATUS  mandatory

        DESCRIPTION
            "Number of ICMP Time Exceeded, TTL Exceeded in
            Transit messages received."
        ::= { cIcmp 5 }

    cIcmpInTimeExcReAsm     OBJECT-TYPE
        SYNTAX  Counter
        ACCESS  read-only
        STATUS  mandatory

        DESCRIPTION
            "Number of ICMP Time Exceeded, Reassembly Time
            Exceeded messages received."
        ::= { cIcmp 6 }

    -- Breakdowns of the individual codes for the Destination UnReachable Message.
    -- The total of these objects should match the value of
    -- icmpInDestUnreachs. Any discrepancy indicates that some redirects
    -- came in with unknown codes.

    cIcmpInDestUnNet        OBJECT-TYPE
        SYNTAX  Counter
        ACCESS  read-only
        STATUS  mandatory

        DESCRIPTION
            "Number of ICMP Network Destination Unreachable
            messages received."
        ::= { cIcmp 7 }

    cIcmpInDestUnHost       OBJECT-TYPE
        SYNTAX  Counter
        ACCESS  read-only
        STATUS  mandatory

        DESCRIPTION
            "Number of ICMP Host Destination Unreachable
            messages received."
        ::= { cIcmp 8 }

    cIcmpInDestUnProtocol   OBJECT-TYPE
        SYNTAX  Counter
        ACCESS  read-only
        STATUS  mandatory

        DESCRIPTION
            "Number of ICMP Protocol Destination Unreachable
            messages received."
        ::= { cIcmp 9 }

    cIcmpInDestUnPort       OBJECT-TYPE
        SYNTAX  Counter
        ACCESS  read-only
        STATUS  mandatory

        DESCRIPTION
            "Number of ICMP Port Destination Unreachable
            messages received."
        ::= { cIcmp 10 }

    cIcmpInDestUnFragNeeded OBJECT-TYPE
        SYNTAX  Counter
        ACCESS  read-only
        STATUS  mandatory

        DESCRIPTION
            "Number of ICMP Fragmentation Needed and DF Set
            Destination Unreachable messages received."
        ::= { cIcmp 11 }

    cIcmpInDestUnSourceRoute    OBJECT-TYPE
        SYNTAX  Counter
        ACCESS  read-only
        STATUS  mandatory

        DESCRIPTION
            "Number of ICMP Source Route Failed
            Destination Unreachable messages received."
        ::= { cIcmp 12 }

    -- Breakdowns of the individual codes for the Redirect Message.
    -- The total of these objects should match the value of
    -- icmpOutRedirects. Any discrepancy indicates that some redirects
    -- were sent with unknown codes (which really should not happen sinc
    -- our code is perfect :-).

    cIcmpOutRedirectNet     OBJECT-TYPE
        SYNTAX  Counter
        ACCESS  read-only
        STATUS  mandatory

        DESCRIPTION
            "Number of ICMP Destination Unreachable, Network
            Unreachable messages sent."
        ::= { cIcmp 13 }

    cIcmpOutRedirectHost        OBJECT-TYPE
        SYNTAX  Counter
        ACCESS  read-only
        STATUS  mandatory

        DESCRIPTION
            "Number of ICMP Destination Unreachable, Host
            Unreachable messages sent."
        ::= { cIcmp 14 }

    cIcmpOutRedirectNetTos  OBJECT-TYPE
        SYNTAX  Counter
        ACCESS  read-only
        STATUS  mandatory

        DESCRIPTION
            "Number of ICMP Destination Unreachable, Network/TOS
            Unreachable messages sent."
        ::= { cIcmp 15 }

    cIcmpOutRedirectHostTos OBJECT-TYPE
        SYNTAX  Counter
        ACCESS  read-only
        STATUS  mandatory

        DESCRIPTION
            "Number of ICMP Destination Unreachable, Host/TOS
            Unreachable messages sent."
        ::= { cIcmp 16 }

    -- Breakdowns of the individual codes for the Time Exceeded Message.
    -- The total of these objects should match the value of
    -- icmpOutTimeExcds. Any discrepancy indicates that some redirects
    -- were sent with unknown codes (which really should not happen sinc
    -- our code is perfect :-).

    cIcmpOutTimeExcTTL      OBJECT-TYPE
        SYNTAX  Counter
        ACCESS  read-only
        STATUS  mandatory

        DESCRIPTION
            "Number of ICMP Time Exceeded, TTL Exceeded in
            Transit messages sent."
        ::= { cIcmp 17 }

    cIcmpOutTimeExcReAsm        OBJECT-TYPE
        SYNTAX  Counter
        ACCESS  read-only
        STATUS  mandatory

        DESCRIPTION
            "Number of ICMP Time Exceeded, Reassembly Time
            Exceeded messages sent."
        ::= { cIcmp 18 }

    -- Breakdowns of the individual codes for the Destination UnReachable Message.
    -- The total of these objects should match the value of
    -- icmpOutDestUnreachs. Any discrepancy indicates that some redirects
    -- were sent with unknown codes (which really should not happen sinc
    -- our code is perfect :-).
    cIcmpOutDestUnNet       OBJECT-TYPE
        SYNTAX  Counter
        ACCESS  read-only
        STATUS  mandatory

        DESCRIPTION
            "Number of ICMP Network Destination Unreachable
            messages sent."
        ::= { cIcmp 19 }

    cIcmpOutDestUnHost      OBJECT-TYPE
        SYNTAX  Counter
        ACCESS  read-only
        STATUS  mandatory

        DESCRIPTION
            "Number of ICMP Host Destination Unreachable
            messages sent."
        ::= { cIcmp 20 }

    cIcmpOutDestUnProtocol  OBJECT-TYPE
        SYNTAX  Counter
        ACCESS  read-only
        STATUS  mandatory

        DESCRIPTION
            "Number of ICMP Protocol Destination Unreachable
            messages sent."
        ::= { cIcmp 21 }

    cIcmpOutDestUnPort      OBJECT-TYPE
        SYNTAX  Counter
        ACCESS  read-only
        STATUS  mandatory

        DESCRIPTION
            "Number of ICMP Port Destination Unreachable
            messages sent."
        ::= { cIcmp 22 }

    cIcmpOutDestUnFragNeeded    OBJECT-TYPE
        SYNTAX  Counter
        ACCESS  read-only
        STATUS  mandatory

        DESCRIPTION
            "Number of ICMP Fragmentation Needed and DF Set
            Destination Unreachable messages sent."
        ::= { cIcmp 23 }

    cIcmpOutDestUnSourceRoute   OBJECT-TYPE
        SYNTAX  Counter
        ACCESS  read-only
        STATUS  mandatory

        DESCRIPTION
            "Number of ICMP Source Route Failed
            Destination Unreachable messages sent."
        ::= { cIcmp 24 }

    --
    -- Extended breakdown of the ICMP errors that
    -- can be detected. These counts are all components
    -- of icmpInErrors. If the sum of these counts does
    -- not equal icmpInErrors, then there were other,
    -- unspecified, receive errors.
    --

    cIcmpInLengthErrors OBJECT-TYPE
        SYNTAX  Counter
        ACCESS  read-only
        STATUS  mandatory

        DESCRIPTION
            "Number of alleged ICMP packets that were not
            long enough."
        ::= { cIcmp 25 }

    cIcmpInChecksumErrors   OBJECT-TYPE
        SYNTAX  Counter
        ACCESS  read-only
        STATUS  mandatory

        DESCRIPTION
            "Number of alleged ICMP packets that had
            a bad checksum."
        ::= { cIcmp 26 }

    cIcmpInUnkTypes OBJECT-TYPE
        SYNTAX  Counter
        ACCESS  read-only
        STATUS  mandatory

        DESCRIPTION
            "Number of Received ICMP packets with an
            unknown type field value."
        ::= { cIcmp 27 }

    --
    -- Additional destination unreachable types defined in host requirements.
    --

    cIcmpInDestUnNetUnknown OBJECT-TYPE
        SYNTAX  Counter
        ACCESS  read-only
        STATUS  mandatory

        DESCRIPTION
            "Number of ICMP Destination Network Unknown
            Destination Unreachable messages received."
        ::= { cIcmp  28 }

    cIcmpInDestUnHostUnknown    OBJECT-TYPE
        SYNTAX  Counter
        ACCESS  read-only
        STATUS  mandatory

        DESCRIPTION
            "Number of ICMP Destination Host Unknown
            Destination Unreachable messages received."
        ::= { cIcmp  29 }

    cIcmpInDestUnSrcIsolated    OBJECT-TYPE
        SYNTAX  Counter
        ACCESS  read-only
        STATUS  mandatory

        DESCRIPTION
            "Number of ICMP Source Isolated
            Destination Unreachable messages received."
        ::= { cIcmp  30 }

    cIcmpInDestUnHostProhib OBJECT-TYPE
        SYNTAX  Counter
        ACCESS  read-only
        STATUS  mandatory

        DESCRIPTION
            "Number of ICMP Communication with Host
            Administratively Prohibited Destination
            Unreachable messages received."
        ::= { cIcmp  31 }

    cIcmpInDestUnNetProhib  OBJECT-TYPE
        SYNTAX  Counter
        ACCESS  read-only
        STATUS  mandatory

        DESCRIPTION
            "Number of ICMP Communication with Net
            Administratively Prohibited Destination
            Unreachable messages received."
        ::= { cIcmp  32 }

    cIcmpInDestUnNetTos OBJECT-TYPE
        SYNTAX  Counter
        ACCESS  read-only
        STATUS  mandatory

        DESCRIPTION
            "Number of ICMP Network Unreachable with
            TOS messages received."
        ::= { cIcmp  33 }

    cIcmpInDestUnHostTos    OBJECT-TYPE
        SYNTAX  Counter
        ACCESS  read-only
        STATUS  mandatory

        DESCRIPTION
            "Number of ICMP Host Unreachable with
            TOS messages received."
        ::= { cIcmp  34 }

    cIcmpOutDestUnNetUnknown    OBJECT-TYPE
        SYNTAX  Counter
        ACCESS  read-only
        STATUS  mandatory

        DESCRIPTION
            "Number of ICMP Destination Network Unknown
            Destination Unreachable messages sent."
        ::= { cIcmp 35 }

    cIcmpOutDestUnHostUnknown   OBJECT-TYPE
        SYNTAX  Counter
        ACCESS  read-only
        STATUS  mandatory

        DESCRIPTION
            "Number of ICMP Destination Host Unknown
            Destination Unreachable messages sent."
        ::= { cIcmp 36 }

    cIcmpOutDestUnSrcIsolated   OBJECT-TYPE
        SYNTAX  Counter
        ACCESS  read-only
        STATUS  mandatory

        DESCRIPTION
            "Number of ICMP Source Isolated
            Destination Unreachable messages sent."
        ::= { cIcmp 37 }

    cIcmpOutDestUnHostProhib    OBJECT-TYPE
        SYNTAX  Counter
        ACCESS  read-only
        STATUS  mandatory

        DESCRIPTION
            "Number of ICMP Communication with Host
            Administratively Prohibited Destination
            Unreachable messages sent."
        ::= { cIcmp 38 }

    cIcmpOutDestUnNetProhib OBJECT-TYPE
        SYNTAX  Counter
        ACCESS  read-only
        STATUS  mandatory

        DESCRIPTION
            "Number of ICMP Communication with Net
            Administratively Prohibited Destination
            Unreachable messages sent."
        ::= { cIcmp 39 }

    cIcmpOutDestUnNetTos    OBJECT-TYPE
        SYNTAX  Counter
        ACCESS  read-only
        STATUS  mandatory

        DESCRIPTION
            "Number of ICMP Network Unreachable with
            TOS messages sent."
        ::= { cIcmp 40 }

    cIcmpOutDestUnHostTos   OBJECT-TYPE
        SYNTAX  Counter
        ACCESS  read-only
        STATUS  mandatory

        DESCRIPTION
            "Number of ICMP Host Unreachable with
            TOS messages sent."
        ::= { cIcmp 41 }

    cIcmpInParmProbMissingOpt   OBJECT-TYPE
        SYNTAX  Counter
        ACCESS  read-only
        STATUS  mandatory

        DESCRIPTION
            "Number of received Parameter Problem messages
            with the Missing Option code."
        ::= { cIcmp 42 }

    cIcmpOutParmProbMissingOpt  OBJECT-TYPE
        SYNTAX  Counter
        ACCESS  read-only
        STATUS  mandatory

        DESCRIPTION
            "Number of sent Parameter Problem messages
            with the Missing Option code."
        ::= { cIcmp 43 }

    --
    -- Here are a few exteneded UDP statistics for the UDP
    -- These are in constellation proprietary space.
    --

    cUdpHdrDrops    OBJECT-TYPE
        SYNTAX  Counter
        ACCESS  read-only
        STATUS  mandatory

        DESCRIPTION
            "Nr of packets dropped because of internal
            consistancy problems. This counter is a component
            of the udpInErrors Count."
        ::= { cUdp 1 }

    cUdpBadCheckSum OBJECT-TYPE
        SYNTAX  Counter
        ACCESS  read-only
        STATUS  mandatory

        DESCRIPTION
            "Nr of packets dropped because of an incorrect
            checksum. This counter is a component
            of the udpInErrors Count."
        ::= { cUdp 2 }

    cUdpBadLength   OBJECT-TYPE
        SYNTAX  Counter
        ACCESS  read-only
        STATUS  mandatory

        DESCRIPTION
            "Nr of packets dropped because of an incorrect
            length. This counter is a component
            of the udpInErrors Count."
        ::= { cUdp 3 }

    cUdpOtherErrors OBJECT-TYPE
        SYNTAX  Counter
        ACCESS  read-only
        STATUS  mandatory

        DESCRIPTION
            "Nr of packets dropped because of some error other
            than one of the above. This counter is a component
            of the udpInErrors Count.

            The most likely cause of these errors is a problem
            in the internal IPC mechanism. Probably because some
            process that was supposed to be receiving packets
            is not."
        ::= { cUdp 4 }

    cUdpNoChecksum  OBJECT-TYPE
        SYNTAX  Counter
        ACCESS  read-only
        STATUS  mandatory

        DESCRIPTION
            "Nr of packets received with a checksum of 0. This
            is not an error condition but indicates that there
            are mentally retarded hosts on the network."
        ::= { cUdp 5 }

-- *************************************************************
--
-- Constellation extensions to the SNMP MIB. These extensions
-- are to
--  A) Support more error statistics for parsing the packets
--     and reasons for declaring the packet as non-authentic.
--  B) Configuration of the community table.
--  C) More party counters, etc.
--
--  This area also contains extensions to the snmpParty
--  mib subtree, even though this subtree is NOT in the
--  Standard snmp mib group.
--
-- *************************************************************

    cSnmpCommunities OBJECT IDENTIFIER ::= { cSnmp 1 }

    cSnmpInCommunityMessages OBJECT-TYPE
        SYNTAX  Counter
        ACCESS  read-only
        STATUS  mandatory

        DESCRIPTION
            "Number of messages received that use the community-
            based authentication scheme."
        ::= { cSnmpCommunities 1 }

-- *************************************************************
--
-- Here are the extensions to MIB-II.
--
-- First, the Generic Interface Extensions MIB
--
-- *************************************************************


--   Generic Interface Extension Table
--
--  This group of objects is mandatory for all types of
--  subnetwork interface.

    ifExtnsTable  OBJECT-TYPE
        SYNTAX SEQUENCE OF IfExtnsEntry
        ACCESS not-accessible
        STATUS mandatory
        DESCRIPTION
            "A list of interfaces extension entries.
            The number of entries is given by the value
            of ifNumber, defined in [4,6]."
        ::= { ifExtensions 1 }

    ifExtnsEntry  OBJECT-TYPE
        SYNTAX IfExtnsEntry
        ACCESS not-accessible
        STATUS mandatory
        DESCRIPTION
            "An extension to the interfaces entry,
            defined in [4,6], containing additional
            objects at the subnetwork layer and below
            for a particular interface."
        INDEX  { ifExtnsIfIndex }

        ::= { ifExtnsTable 1 }

    IfExtnsEntry ::= SEQUENCE {
            ifExtnsIfIndex
                INTEGER,
            ifExtnsChipSet
                OBJECT IDENTIFIER,
            ifExtnsRevWare
                DisplayString,
            ifExtnsMulticastsTransmittedOks
                Counter,
            ifExtnsBroadcastsTransmittedOks
                Counter,
            ifExtnsMulticastsReceivedOks
                Counter,
            ifExtnsBroadcastsReceivedOks
                Counter,
            ifExtnsPromiscuous
                INTEGER
        }

    ifExtnsIfIndex  OBJECT-TYPE
        SYNTAX INTEGER
        ACCESS read-only
        STATUS mandatory

        DESCRIPTION
            "The value of this object identifies the
            interface for which this entry contains
            extended management information.  The value
            of this object for a particular interface
            has the same value as the ifIndex object,
            defined in [4,6], for the same interface."
        ::= { ifExtnsEntry 1 }

    ifExtnsChipSet  OBJECT-TYPE
        SYNTAX  OBJECT IDENTIFIER
        ACCESS  read-only
        STATUS  mandatory

        DESCRIPTION
            "This object identifies the hardware chip
            set being used in the interface.  The
            assignment of OBJECT IDENTIFIERs to various
            types of hardware chip sets is defined
            elsewhere.  This document assigns only the
            value: unknownChipSet for use if the chip
            set in use is unknown.
                Note that unknownChipSet is a
            syntactically valid object identifier, and
            any conformant implementation of ASN.1 and
            the BER must be able to generate and
            recognize this value."
        ::= { ifExtnsEntry 2 }

-- for unknown hardware chip set
--      unknownChipSet  OBJECT IDENTIFIER ::= { 0 0 }

    ifExtnsRevWare  OBJECT-TYPE
        SYNTAX DisplayString (SIZE (0..255))
        ACCESS read-only
        STATUS mandatory

        DESCRIPTION
            "An arbitrary octet string that describes
            the firmware version of this interface.
            It is intended that this should be human
            readable.  It must only contain ASCII
            printable characters.  Typically this
            will be the firmware version of the main
            interface software."
        ::= { ifExtnsEntry 3 }

    ifExtnsMulticastsTransmittedOks OBJECT-TYPE
        SYNTAX Counter
        ACCESS read-only
        STATUS mandatory

        DESCRIPTION
            "The count of frames successfully
            transmitted to a subnetwork or link-layer
            multicast destination address other than a
            broadcast address.  For a MAC layer protocol,
            this includes both Group and Functional
            addresses."
        ::= { ifExtnsEntry 4 }

    ifExtnsBroadcastsTransmittedOks OBJECT-TYPE
        SYNTAX Counter
        ACCESS read-only
        STATUS mandatory

        DESCRIPTION
            "The count of frames successfully
            transmitted to a subnetwork or link-layer
            broadcast addresses.  It does not include
            frames sent to a multicast address."
        ::= { ifExtnsEntry 5 }

    ifExtnsMulticastsReceivedOks OBJECT-TYPE
        SYNTAX  Counter
        ACCESS  read-only
        STATUS  mandatory

        DESCRIPTION
            "The count of frames successfully received
            that are directed to an active subnetwork
            or link-layer multicast address (for a MAC
            layer protocol, this includes both Group and
            Functional addresses). This does not include
            frames directed to a broadcast address, nor
            frames received with errors."
        ::= { ifExtnsEntry 6 }

    ifExtnsBroadcastsReceivedOks OBJECT-TYPE
        SYNTAX Counter
        ACCESS read-only
        STATUS mandatory

        DESCRIPTION
            "The count of frames successfully received
            that are directed to a subnetwork or
            link-layer broadcast address."
        ::= { ifExtnsEntry 7 }

    ifExtnsPromiscuous  OBJECT-TYPE
        SYNTAX INTEGER {
                        true(1),
                        false(2)
                    }
        ACCESS read-only    -- Note: agent implementors are
                            -- encouraged to extend this
                            -- access to read-write if that
                            -- makes sense in their agent.
        STATUS mandatory

        DESCRIPTION
            "This object has a value of false(2) if
            this interface only accepts packets/frames
            that are addressed to this station. This
            object has a value of true(1) when the
            station accepts all packets/frames
            transmitted on the media.  The value
            true(1) is only legal on certain types of
            media.  If legal, setting this object to a
            value of true(1) may require the interface
            to be reset before becoming effective."
        ::= { ifExtnsEntry 8 }

--
--    Generic Interface Test Table
--
-- This group of objects is optional, but if the table is
-- implemented, all objects in the table must be implemented.
-- Not implemented in the little dipper.
--
--
--   Generic Receive Address Table
--
-- This group of objects is mandatory for all types of
-- interfaces which can receive packets/frames addressed to
-- more than one address.
--

    ifExtnsRcvAddrTable  OBJECT-TYPE
        SYNTAX SEQUENCE OF IfExtnsRcvAddrEntry
        ACCESS not-accessible
        STATUS mandatory
        DESCRIPTION
            "This table contains an entry for each
            address (broadcast, multicast, or uni-cast)
            for which the system will receive packets/
            frames on a particular interface.  When an
            interface is operating in promiscuous mode,
            entries are only required for those
            addresses for which the system would receive
            frames were it not operating in promiscuous
            mode."
        ::= { ifExtensions 3 }

    ifExtnsRcvAddrEntry  OBJECT-TYPE
        SYNTAX IfExtnsRcvAddrEntry
        ACCESS not-accessible
        STATUS mandatory
        DESCRIPTION
            "A list of objects identifying an address
            for which the system will accept packets/
            frames on a particular interface."
        INDEX  { ifExtnsRcvAddrIfIndex, ifExtnsRcvAddress }

        ::= { ifExtnsRcvAddrTable 1 }

    IfExtnsRcvAddrEntry ::= SEQUENCE {
        ifExtnsRcvAddrIfIndex
            INTEGER,
        ifExtnsRcvAddress
            PhysAddress,
        ifExtnsRcvAddrStatus
            INTEGER
        }

    ifExtnsRcvAddrIfIndex  OBJECT-TYPE
        SYNTAX  INTEGER
        ACCESS  read-only
        STATUS  mandatory

        DESCRIPTION
            "The value of ifIndex, defined in [4,6],
            of an interface which recognizes this
            entry's address."
        ::= { ifExtnsRcvAddrEntry 1 }

    ifExtnsRcvAddress OBJECT-TYPE
        SYNTAX  PhysAddress
        ACCESS  read-only
        STATUS  mandatory

        DESCRIPTION
            "An address for which the system will
            accept packets/frames on this entry's
            interface."
        ::= { ifExtnsRcvAddrEntry 2 }

    ifExtnsRcvAddrStatus OBJECT-TYPE
        SYNTAX  INTEGER {
                    other(1),
                    invalid(2),
                    volatile(3),
                    nonVolatile(4)
                }
        ACCESS  read-write
        STATUS  mandatory

        DESCRIPTION
            "This object has the value nonVolatile(4)
            for those entries in the table which are
            valid and will not be deleted by the next
            restart of the managed system.  Entries
            having the value volatile(3) are valid
            and exist, but have not been saved, so
            that will not exist after the next
            restart of the managed system.  Entries
            having the value other(1) are valid and
            exist but are not classified as to whether
            they will continue to exist after the next
            restart.  Entries having the value invalid(2)
            are invalid and do not represent an address
            for which an interface accepts frames.
                Setting an object instance to one of
            the values other(1), volatile(3), or
            nonVolatile(4) causes the corresponding
            entry to exist or continue to exist, and
            to take on the respective status as regards
            the next restart of the managed system.
                Setting an object instance to the value
            invalid(2) causes the corresponding entry
            to become invalid or cease to exist.
                It is an implementation-specific matter
            as to whether the agent removes an
            invalidated entry from the table.
            Accordingly, management stations must be
            prepared to receive tabular information
            from agents that corresponds to entries not
            currently in use.  Proper interpretation of
            such entries requires examination of the
            relevant ifExtnsRcvAddrStatus object
            instance."
--      DEFVAL  { volatile }
        ::= { ifExtnsRcvAddrEntry 3 }


-- *************************************************************
--
-- Now, the ethernet like interface stuff.
--
-- *************************************************************

-- the Generic Ethernet-like group

-- Implementation of this group is mandatory for all systems
-- that attach to an ethernet-like medium.

    dot3Table OBJECT-TYPE
        SYNTAX  SEQUENCE OF Dot3Entry
        ACCESS  not-accessible
        STATUS  mandatory
        DESCRIPTION
            "Status information and control variables for a
            collection of ethernet-like interfaces attached to
            a particular system."
        ::= { dot3 1 }

    dot3Entry OBJECT-TYPE
        SYNTAX  Dot3Entry
        ACCESS  not-accessible
        STATUS  mandatory
        DESCRIPTION
            "Status information and control variables for a
            particular interface to an ethernet-like medium."
        INDEX   { dot3Index }

        ::= { dot3Table 1 }

    Dot3Entry ::= SEQUENCE {
        dot3Index
            INTEGER,
        dot3InitializeMac
            INTEGER,
        dot3MacSubLayerStatus
            INTEGER,
        dot3MulticastReceiveStatus
            INTEGER,
        dot3TxEnabled
            INTEGER,
        dot3TestTdrValue
            Gauge
    }

    dot3Index OBJECT-TYPE
        SYNTAX  INTEGER
        ACCESS  read-only
        STATUS  mandatory

        DESCRIPTION
            "An index value that uniquely identifies an
            interface to an ethernet-like medium.  The
            interface identified by a particular value of this
            index is the same interface as identified by the
            same value of ifIndex."
        ::= { dot3Entry 1 }

    dot3InitializeMac OBJECT-TYPE
        SYNTAX  INTEGER { initialized(1), uninitialized(2) }
        ACCESS  read-write
        STATUS  mandatory

        DESCRIPTION
            "The initialization status of the MAC and PLS
            (Physical Layer Signalling) subsystems for a
            particular interface. The value initialized(1)
            signifies that the subsystems for a particular
            interface have been previously initialized; the
            value uninitialized(2) signifies that they have
            not been previously initialized.

            Each alteration of an instance of this object to
            either of the values initialized(1) or
            uninitialized(2) is analogous to an invocation of
            the initializeMAC action defined in [9] and has
            the effect of (re-)initializing the MAC and PLS
            subsystems for the associated interface. In
            particular,

                all management counters pertaining to the MAC
                and PLS subsystems for said interface are
                reset to zero;

                the receive and transmit layer management
                state variables (receiveEnabled and
                transmitEnabled in [9]) are set to enable
                reception and transmission of frames;

                the promiscuous receive function is disabled;
                and

                multicast reception is disabled."
        ::= { dot3Entry 2 }

    dot3MacSubLayerStatus OBJECT-TYPE
        SYNTAX  INTEGER { enabled(1), disabled(2) }
        ACCESS  read-write
        STATUS  mandatory

        DESCRIPTION
            "The operational status of the MAC sublayer for a
            particular interface.  The value enabled(1)
            signifies that the MAC sublayer for said interface
            is operational for both transmitting and receiving
            frames -- that is, that the value of both the
            receive and transmit layer management state
            variables (receiveEnabled and transmitEnabled in
            [9]) for said interface are true.  The value
            disabled(2) signifies that the MAC sublayer for
            said interface is not operational for either
            transmitting or receiving frames. In particular,
            the value of an instance of this object is
            disabled(2) whenever the value of the
            corresponding instance of the dot3Enabled object
            is false(2).

            Each alteration of an instance of this object to
            the value enabled(1) is analogous to an invocation
            of the enableMACSublayer action defined in [9] and
            has the effect of starting normal transmit and
            receive operations (from the ``idle'' state) on
            the associated interface. In particular, such an
            alteration has the effect of resetting the PLS for
            said interface and of setting the receive and
            transmit layer management state variables
            (receiveEnabled and transmitEnabled in [9]) to be
            true.

            Each alteration of an instance of this object to
            the value disabled(2) is analogous to an
            invocation of the disableMACSublayer action
            defined in [9] and has the effect of terminating
            transmit and receive operations on the associated
            interface. In particular, such an alteration has
            the effect of setting the receive and transmit
            layer management state variables (receiveEnabled
            and transmitEnabled in [9]) to be false. Any
            transmissions/receptions in progress are completed
            before operation is terminated."
        ::= { dot3Entry 3 }

    dot3MulticastReceiveStatus OBJECT-TYPE
        SYNTAX  INTEGER { enabled(1), disabled(2) }
        ACCESS  read-write
        STATUS  mandatory

        DESCRIPTION
            "The multicast receive status for a particular
            interface.  The value enabled(1) signifies that
            reception of multicast frames by the MAC sublayer
            is enabled on said interface. The value
            disabled(2) signifies that reception of multicast
            frames by the MAC sublayer is not enabled on said
            interface.

            Each alteration of an instance of this object to
            the value enabled(1) is analogous to an invocation
            of the enableMulticastReceive action defined in
            [9] and has the effect of enabling multicast frame
            reception on the associated interface. Actual
            reception of multicast frames is only possible on
            an interface when the values for the associated
            instances of the dot3MulticastReceiveStatus and
            dot3MacSubLayerStatus objects are enabled(1) and
            enabled(1), respectively.

            Each alteration of an instance of this object to
            the value disabled(2) is analogous to an
            invocation of the disableMulticastReceive action
            defined in [9] and has the effect of inhibiting
            multicast frame reception on the associated
            interface."
        ::= { dot3Entry 4 }

    dot3TxEnabled OBJECT-TYPE
        SYNTAX  INTEGER { true(1), false(2)  }
        ACCESS  read-write
        STATUS  mandatory

        DESCRIPTION
            "The transmit layer management state variable
            (transmitEnabled as defined in [9]) for a
            particular interface.  The value true(1) signifies
            that the MAC frame transmission is enabled on said
            interface. The value false(2) signifies that the
            MAC frame transmission is inhibited on said
            interface. In particular, the value of an instance
            of this object is false(2) whenever the value of
            the corresponding instance of the
            dot3MacSubLayerStatus object is disabled(2).

            Each alteration of an instance of this object to
            the value true(1) is analogous to an invocation of
            the enableTransmit action defined in [9] and has
            the effect of enabling MAC sublayer frame
            transmission on the associated interface. In
            particular, such an alteration has the effect of
            setting the transmit layer management state
            variable (transmitEnabled in [9]) for said
            interface to be true.

            Each alteration of an instance of this object to
            the value false(2) is analogous to an invocation
            of the disableTransmit action defined in [9] and
            has the effect of inhibiting MAC sublayer frame
            transmission on the associated interface. In
            particular, such an alteration has the effect of
            setting the transmit layer management state
            variable (transmitEnabled in [9]) for said
            interface to be false. Any transmissions in
            progress are completed before transmission is
            inhibited."
        ::= { dot3Entry 5 }

    dot3TestTdrValue OBJECT-TYPE
        SYNTAX  Gauge
        ACCESS  read-only
        STATUS  mandatory

        DESCRIPTION
            "The number of 10 MHz ticks which elapsed between
            the beginning of a TDR measurement and the
            collision which ended it, for the most recently
            executed TDR test.  If no TDR test has been
            executed, or the last TDR value is not available,
            this object has the value 0."
        ::= { dot3Entry 6 }

-- the Ethernet-like Statistics group

-- Implementation of this group is mandatory

-- Due to implementation restrictions (e.g. in the instrumentation
-- provided by a chipset, or a device driver), some of the counters
-- in this group may be difficult or impossible to implement.
-- In such cases, an implementator should apply reasonable best
-- effort to detect as many occurrences as possible.  In any case,
-- the value of a counter will be the number actually detected,
-- which will always be less or equal to the number of actual
-- occurrences.  In the extreme case of a total inability to
-- detect occurrences, the counter will always be zero.

-- Vendors are strongly encouraged to document in user guides and
-- other appropriate documentation the conditions under which the
-- values of the counters in this group may represent an
-- underestimate of the true count.

    dot3StatsTable OBJECT-TYPE
        SYNTAX  SEQUENCE OF Dot3StatsEntry
        ACCESS  not-accessible
        STATUS  mandatory
        DESCRIPTION
            "Statistics for a collection of ethernet-like
            interfaces attached to a particular system."
        ::= { dot3 2 }

    dot3StatsEntry OBJECT-TYPE
        SYNTAX  Dot3StatsEntry
        ACCESS  not-accessible
        STATUS  mandatory
        DESCRIPTION
            "Statistics for a particular interface to an
            ethernet-like medium."
        INDEX   { dot3StatsIndex }

        ::= { dot3StatsTable 1 }

    Dot3StatsEntry ::= SEQUENCE {
        dot3StatsIndex
            INTEGER,
        dot3StatsAlignmentErrors
            Counter,
        dot3StatsFCSErrors
            Counter,
        dot3StatsSingleCollisionFrames
            Counter,
        dot3StatsMultipleCollisionFrames
            Counter,
        dot3StatsSQETestErrors
            Counter,
        dot3StatsDeferredTransmissions
            Counter,
        dot3StatsLateCollisions
            Counter,
        dot3StatsExcessiveCollisions
            Counter,
        dot3StatsInternalMacTransmitErrors
            Counter,
        dot3StatsCarrierSenseErrors
            Counter,
        dot3StatsExcessiveDeferrals
            Counter,
        dot3StatsFrameTooLongs
            Counter,
        dot3StatsInRangeLengthErrors
            Counter,
        dot3StatsOutOfRangeLengthFields
            Counter,
        dot3StatsInternalMacReceiveErrors
            Counter
    }

    dot3StatsIndex OBJECT-TYPE
        SYNTAX  INTEGER
        ACCESS  read-only
        STATUS  mandatory

        DESCRIPTION
            "An index value that uniquely identifies an
            interface to an ethernet-like medium.  The
            interface identified by a particular value of this
            index is the same interface as identified by the
            same value of ifIndex."
        ::= { dot3StatsEntry 1 }

    dot3StatsAlignmentErrors OBJECT-TYPE
        SYNTAX  Counter
        ACCESS  read-only
        STATUS  mandatory

        DESCRIPTION
            "A count of frames received on a particular
            interface that are not an integral number of
            octets in length and do not pass the FCS check.

            The count represented by an instance of this
            object is incremented when the alignmentError
            status is returned by the MAC service to the LLC
            (or other MAC user). Received frames for which
            multiple error conditions obtain are, according to
            the conventions of [9], counted exclusively
            according to the error status presented to the
            LLC."
        ::= { dot3StatsEntry 2 }

    dot3StatsFCSErrors OBJECT-TYPE
        SYNTAX  Counter
        ACCESS  read-only
        STATUS  mandatory

        DESCRIPTION
            "A count of frames received on a particular
            interface that are an integral number of octets in
            length but do not pass the FCS check.

            The count represented by an instance of this
            object is incremented when the frameCheckError
            status is returned by the MAC service to the LLC
            (or other MAC user). Received frames for which
            multiple error conditions obtain are, according to
            the conventions of [9], counted exclusively
            according to the error status presented to the
            LLC."
        ::= { dot3StatsEntry 3 }

    dot3StatsSingleCollisionFrames OBJECT-TYPE
        SYNTAX  Counter
        ACCESS  read-only
        STATUS  mandatory

        DESCRIPTION
            "A count of successfully transmitted frames on a
            particular interface for which transmission is
            inhibited by exactly one collision.

            A frame that is counted by an instance of this
            object is also counted by the corresponding
            instance of either the ifOutUcastPkts or
            ifOutNUcastPkts object and is not counted by the
            corresponding instance of the
            dot3StatsMultipleCollisionFrames object."
        ::= { dot3StatsEntry 4 }

    dot3StatsMultipleCollisionFrames OBJECT-TYPE
        SYNTAX  Counter
        ACCESS  read-only
        STATUS  mandatory

        DESCRIPTION
            "A count of successfully transmitted frames on a
            particular interface for which transmission is
            inhibited by more than one collision.

            A frame that is counted by an instance of this
            object is also counted by the corresponding
            instance of either the ifOutUcastPkts or
            ifOutNUcastPkts object and is not counted by the
            corresponding instance of the
            dot3StatsSingleCollisionFrames object."
    ::= { dot3StatsEntry 5 }

    dot3StatsSQETestErrors OBJECT-TYPE
        SYNTAX  Counter
        ACCESS  read-only
        STATUS  mandatory

        DESCRIPTION
            "A count of times that the SQE TEST ERROR message
            is generated by the PLS sublayer for a particular
            interface. The SQE TEST ERROR message is defined
            in section 7.2.2.2.4 of [12] and its generation is
            described in section 7.2.4.6 of the same
            document."
        ::= { dot3StatsEntry 6 }

    dot3StatsDeferredTransmissions OBJECT-TYPE
        SYNTAX  Counter
        ACCESS  read-only
        STATUS  mandatory

        DESCRIPTION
            "A count of frames for which the first
            transmission attempt on a particular interface is
            delayed because the medium is busy.
            The count represented by an instance of this
            object does not include frames involved in
            collisions."
        ::= { dot3StatsEntry 7 }

    dot3StatsLateCollisions OBJECT-TYPE
        SYNTAX  Counter
        ACCESS  read-only
        STATUS  mandatory

        DESCRIPTION
            "The number of times that a collision is detected
            on a particular interface later than 512 bit-times
            into the transmission of a packet.

            Five hundred and twelve bit-times corresponds to
            51.2 microseconds on a 10 Mbit/s system. A (late)
            collision included in a count represented by an
            instance of this object is also considered as a
            (generic) collision for purposes of other
            collision-related statistics."
        ::= { dot3StatsEntry 8 }

    dot3StatsExcessiveCollisions OBJECT-TYPE
        SYNTAX  Counter
        ACCESS  read-only
        STATUS  mandatory

        DESCRIPTION
            "A count of frames for which transmission on a
            particular interface fails due to excessive
            collisions."
        ::= { dot3StatsEntry 9 }

    dot3StatsInternalMacTransmitErrors OBJECT-TYPE
        SYNTAX  Counter
        ACCESS  read-only
        STATUS  mandatory

        DESCRIPTION
            "A count of frames for which transmission on a
            particular interface fails due to an internal MAC
            sublayer transmit error. A frame is only counted
            by an instance of this object if it is not counted
            by the corresponding instance of either the
            dot3StatsLateCollisions object, the
            dot3StatsExcessiveCollisions object, the
            dot3StatsCarrierSenseErrors object, or the
            dot3StatsExcessiveDeferrals object.

            The precise meaning of the count represented by an
            instance of this object is implementation-
            specific.  In particular, an instance of this
            object may represent a count of transmission
            errors on a particular interface that are not
            otherwise counted."
        ::= { dot3StatsEntry 10 }

    dot3StatsCarrierSenseErrors OBJECT-TYPE
        SYNTAX  Counter
        ACCESS  read-only
        STATUS  mandatory

        DESCRIPTION
            "The number of times that the carrier sense
            condition was lost or never asserted when
            attempting to transmit a frame on a particular
            interface.

            The count represented by an instance of this
            object is incremented at most once per
            transmission attempt, even if the carrier sense
            condition fluctuates during a transmission
            attempt."
        ::= { dot3StatsEntry 11 }

    dot3StatsExcessiveDeferrals OBJECT-TYPE
        SYNTAX  Counter
        ACCESS  read-only
        STATUS  mandatory

        DESCRIPTION
            "A count of frames for which transmission on a
            particular interface is deferred for an excessive
            period of time."
        ::= { dot3StatsEntry 12 }

    dot3StatsFrameTooLongs OBJECT-TYPE
        SYNTAX  Counter
        ACCESS  read-only
        STATUS  mandatory

        DESCRIPTION
            "A count of frames received on a particular
            interface that exceed the maximum permitted frame
            size.

            The count represented by an instance of this
            object is incremented when the frameTooLong status
            is returned by the MAC service to the LLC (or
            other MAC user). Received frames for which
            multiple error conditions obtain are, according to
            the conventions of [9], counted exclusively
            according to the error status presented to the
            LLC."
        ::= { dot3StatsEntry 13 }

    dot3StatsInRangeLengthErrors OBJECT-TYPE
        SYNTAX  Counter
        ACCESS  read-only
        STATUS  mandatory

        DESCRIPTION
            "A count of frames received on a particular
            interface with a length field value that falls
            between the minimum unpadded LLC data size and the
            maximum allowed LLC data size inclusive and that
            does not match the number of LLC data octets
            received.

            The count represented by an instance of this
            object also includes frames for which the length
            field value is less than the minimum unpadded LLC
            data size."
        ::= { dot3StatsEntry 14 }

    dot3StatsOutOfRangeLengthFields OBJECT-TYPE
        SYNTAX  Counter
        ACCESS  read-only
        STATUS  mandatory

        DESCRIPTION
            "A count of frames received on a particular
            interface for which the length field value exceeds
            the maximum allowed LLC data size.

            The count represented by an instance of this
            object is not incremented in implementations that
            observe Ethernet encapsulation conventions (by
            which the IEEE 802.3 length field is interpreted
            as the Ethernet Type field)."
        ::= { dot3StatsEntry 15 }

    dot3StatsInternalMacReceiveErrors OBJECT-TYPE
        SYNTAX  Counter
        ACCESS  read-only
        STATUS  mandatory

        DESCRIPTION
            "A count of frames for which reception on a
            particular interface fails due to an internal MAC
            sublayer receive error. A frame is only counted by
            an instance of this object if it is not counted by
            the corresponding instance of either the
            dot3StatsFrameTooLongs object, the
            dot3StatsAlignmentErrors object, the
            dot3StatsFCSErrors object, the
            dot3StatsInRangeLengthErrors object, or the
            dot3StatsOutOfRangeLengthFields object.

            The precise meaning of the count represented by an
            instance of this object is implementation-
            specific.  In particular, an instance of this
            object may represent a count of receive errors on
            a particular interface that are not otherwise
            counted."
        ::= { dot3StatsEntry 16 }

--
-- The Ethernet-like Collision Statistics group (dot3CollTable)
-- is not implemented in the Little Dipper since the necessary
-- instrumentation is not present in the IF chipset.
--

--  802.3 Hardware Chipsets

-- The object ifExtnsChipSet is provided in [11] to identify the
-- MAC hardware used to communcate on an interface.  The following
-- hardware chipsets are provided for 802.3:

dot3ChipSets        OBJECT IDENTIFIER ::= { dot3 8 }
dot3ChipSetAMD      OBJECT IDENTIFIER ::= { dot3ChipSets 1 }

dot3ChipSetAMD7990  OBJECT IDENTIFIER ::= { --! POINTER Lance_OID
                        dot3ChipSetAMD 1 }
dot3ChipSetAMD79900 OBJECT IDENTIFIER ::= {--! POINTER Ilacc_OID
                        dot3ChipSetAMD 2 }
--
-- Following chips are not used on the Constellation  Series so
-- I commented out their OID definitions. Saves some space.
--
-- dot3ChipSetIntel      OBJECT IDENTIFIER ::= { dot3ChipSets 2 }
-- dot3ChipSetIntel82586 OBJECT IDENTIFIER ::= { dot3ChipSetIntel 1 }
-- dot3ChipSetIntel82596 OBJECT IDENTIFIER ::= { dot3ChipSetIntel 2 }

-- dot3ChipSetSeeq       OBJECT IDENTIFIER ::= { dot3ChipSets 3 }
-- dot3ChipSetSeeq8003   OBJECT IDENTIFIER ::= { dot3ChipSetSeeq 1 }

-- dot3ChipSetNational      OBJECT IDENTIFIER ::= { dot3ChipSets 4 }
-- dot3ChipSetNational8390  OBJECT IDENTIFIER ::= { dot3ChipSetNational 1 }
-- dot3ChipSetNationalSonic OBJECT IDENTIFIER ::= { dot3ChipSetNational 2 }

-- For those chipsets not represented above, OBJECT IDENTIFIER
-- assignment is required in other documentation, e.g., assignment
-- within that part of the registration tree delegated to
-- individual enterprises (see [4]).

-- Traps for use by Bridges

--        newRoot TRAP-TYPE
--            ENTERPRISE  dot1d
--            DESCRIPTION
--                    "The newRoot trap indicates that the sending agent
--                    has become the new root of the Spanning Tree; the
--                    trap is sent by a bridge on the first occurrence
--                    of one of its ports transitioning to the
--                    Forwarding state after becoming root."
--            ::= 1

--        topologyChange TRAP-TYPE
--            ENTERPRISE  dot1d
--            DESCRIPTION
--                    "A topologyChange trap is sent by a bridge when
--                    any of its configured ports transitions into or
--                    out of the Forwarding state.  The trap is not sent
--                    if a newRoot trap is sent for the same
--                    transition."
--            ::= 2

    --
    -- cDipper subtree. This subtree contains constellation
    -- specific objects i.e. objects for the little dipper,
    -- carina, pyxis and/or auriga.
    --

    cConstellationAvailableBuffers OBJECT-TYPE
        SYNTAX  Gauge
        ACCESS  read-only
        STATUS  mandatory

        DESCRIPTION
            "Count of available data buffers"
        ::= { cConstellation 1 }

    cConstellationInitialBuffers OBJECT-TYPE
        SYNTAX  INTEGER
        ACCESS  read-only
        STATUS  mandatory

        DESCRIPTION
            "Initial amount of buffers available at system startup."
        ::= { cConstellation 2 }

    cConstallationBufferDataLength OBJECT-TYPE
        SYNTAX  INTEGER(64..65535)
        ACCESS  read-only
        STATUS  mandatory

        DESCRIPTION
            "Number of data bytes that can be stored in each buffer."
        ::= { cConstellation 3 }

    cConstellationInstructionRam OBJECT-TYPE
        SYNTAX  INTEGER
        ACCESS  read-only
        STATUS  mandatory

        DESCRIPTION
            "Number of bytes of system instruction ram available.
            This is fast, zero-wait-state RAM."
        ::= { cConstellation 4 }

    cConstellationGlobalDataRam OBJECT-TYPE
        SYNTAX  INTEGER
        ACCESS  read-only
        STATUS  mandatory

        DESCRIPTION
            "Number of bytes of global data ram available.
            This is RAM contains I/O buffers and other
            data structures for which zero-wait-state access
            is not required by the CPU."
        ::= { cConstellation 5 }

    cConstellationFastDataRam OBJECT-TYPE
        SYNTAX  INTEGER
        ACCESS  read-only
        STATUS  mandatory

        DESCRIPTION
            "Number of bytes of fast data ram available.
            This is RAM contains data structures for which
            the CPU requires zero-wait-state access, such as
            the bridge forwarding database."
        ::= { cConstellation 6 }

    --
    -- Extensions for the dot3 group for our own
    -- driver, etc, counters.
    --

    cDot3Table OBJECT-TYPE
        SYNTAX  SEQUENCE OF CDot3Entry
        ACCESS  not-accessible
        STATUS  mandatory
        DESCRIPTION
            "Extended status information for the Constellation
            specific LANCE and ILACC drivers."
        ::= { cDot3 1 }

    cDot3Entry OBJECT-TYPE
        SYNTAX  CDot3Entry
        ACCESS  not-accessible
        STATUS  mandatory
        DESCRIPTION
            "Proprietary status information for a particular
            interface"
        INDEX   { cDot3Index }

        ::= { cDot3Table 1 }

    CDot3Entry ::= SEQUENCE {
        cDot3Index          INTEGER,
        cDot3Disables       Counter,
        cDot3MauDisconnect  Counter,
        cDot3Babbles        Counter,
        cDot3MerrDisconnect Counter,
        cDot3TxonDisconnect Counter,
        cDot3RxonDisconnect Counter,
        cDot3XmitFailure    Counter,
        cDot3XmitBuffErr    Counter,
        cDot3XmitUflo       Counter,
        cDot3RcvBuffErr     Counter,
        cDot3RcvOflo        Counter,
        cDot3Startless      Counter,
        cDot3Endless        Counter
    }

    cDot3Index OBJECT-TYPE
        SYNTAX  INTEGER
        ACCESS  read-only
        STATUS  mandatory

        DESCRIPTION
            "An index value that uniquely identifies an
            interface to an ethernet-like medium.  The
            interface identified by a particular value of this
            index is the same interface as identified by the
            same value of ifIndex."
        ::= { cDot3Entry 1 }

    cDot3Disables OBJECT-TYPE
        SYNTAX  Counter
        ACCESS  read-only
        STATUS  mandatory

        DESCRIPTION
            "Number of LANCE/ILLAC disconnects that occured
            because the interface was disabled"
        ::= { cDot3Entry 2 }

    cDot3MauDisconnect OBJECT-TYPE
        SYNTAX  Counter
        ACCESS  read-only
        STATUS  mandatory

        DESCRIPTION
            "Number of LANCE/ILLAC disconnects that occured
            because m_lance_cs_mau_connected was 0."
        ::= { cDot3Entry 3 }

    cDot3Babbles OBJECT-TYPE
        SYNTAX  Counter
        ACCESS  read-only
        STATUS  mandatory

        DESCRIPTION
            "Number of times the LANCE/ILACC Babble bit
            was set."
        ::= { cDot3Entry 4 }

    cDot3MerrDisconnect OBJECT-TYPE
        SYNTAX  Counter
        ACCESS  read-only
        STATUS  mandatory

        DESCRIPTION
            "Number of LANCE/ILLAC disconnects that occured
            because the memory error bit was set."
        ::= { cDot3Entry 5 }

    cDot3TxonDisconnect OBJECT-TYPE
        SYNTAX  Counter
        ACCESS  read-only
        STATUS  mandatory

        DESCRIPTION
            "Number of LANCE/ILLAC disconnects that occured
            because the txon bit was off."
        ::= { cDot3Entry 6 }

    cDot3RxonDisconnect OBJECT-TYPE
        SYNTAX  Counter
        ACCESS  read-only
        STATUS  mandatory

        DESCRIPTION
            "Number of LANCE/ILLAC disconnects that occured
            because the rxon bit was off."
        ::= { cDot3Entry 7 }

    cDot3XmitFailure OBJECT-TYPE
        SYNTAX  Counter
        ACCESS  read-only
        STATUS  mandatory

        DESCRIPTION
            "Number of LANCE/ILLAC disconnects that occured
            because no packets were received and every transmit
            attempt resulted in a failure."
        ::= { cDot3Entry 8 }

    cDot3XmitBuffErr OBJECT-TYPE
        SYNTAX  Counter
        ACCESS  read-only
        STATUS  mandatory

        DESCRIPTION
            "Number of LANCE/ILLAC transmit buffer errors that occured."
        ::= { cDot3Entry 9 }

    cDot3XmitUflo OBJECT-TYPE
        SYNTAX  Counter
        ACCESS  read-only
        STATUS  mandatory

        DESCRIPTION
            "Number of LANCE/ILLAC transmit underflo errors that occured."
        ::= { cDot3Entry 10 }

    cDot3RcvBuffErr OBJECT-TYPE
        SYNTAX  Counter
        ACCESS  read-only
        STATUS  mandatory

        DESCRIPTION
            "Number of LANCE/ILLAC receive buffer errors that occured."
        ::= { cDot3Entry 11 }

    cDot3RcvOflo OBJECT-TYPE
        SYNTAX  Counter
        ACCESS  read-only
        STATUS  mandatory

        DESCRIPTION
            "Number of LANCE/ILLAC receive overflo errors that occured."
        ::= { cDot3Entry 12 }

    cDot3Startless OBJECT-TYPE
        SYNTAX  Counter
        ACCESS  read-only
        STATUS  mandatory

        DESCRIPTION
            "Number of times that the driver did not get a
            start-of-message when one was expected. This if
            for reception."
        ::= { cDot3Entry 13 }

    cDot3Endless OBJECT-TYPE
        SYNTAX  Counter
        ACCESS  read-only
        STATUS  mandatory

        DESCRIPTION
            "Number of times that the driver detected the
            start of one packet without detecting the end of
            the previous packet. This is for reception."
        ::= { cDot3Entry 14 }


--
-- Here starts the constellation rewritten part of the MIB
--
-- mad - 22 Jun 93
--

--
-- textual conventions
--

--    YesNo ::= INTEGER {
--                      yes(1),
--                      no(2)
--                      }

--    RowStatus ::= INTEGER {
--                          valid(1),
--                          underCreation(2),
--                          delete(3),
 --                         invalid(4)
--                          }

--
-- our OIDs
--

    cConfig                  OBJECT IDENTIFIER ::= { constellation 6 }
    cMonitor                 OBJECT IDENTIFIER ::= { constellation 7 }

    cConfigSystem            OBJECT IDENTIFIER ::= { cConfig 1 }
    cConfSysInfo             OBJECT IDENTIFIER ::= { cConfigSystem 1 }
    cConfOperAcct            OBJECT IDENTIFIER ::= { cConfigSystem 2 }

    cConfigLan               OBJECT IDENTIFIER ::= { cConfig 2 }
    cConfigEther             OBJECT IDENTIFIER ::= { cConfigLan 1 }
    cConfigTwp               OBJECT IDENTIFIER ::= { cConfigLan 2 }

    cConfigWan               OBJECT IDENTIFIER ::= { cConfig 3 }
    cConfigSerChan           OBJECT IDENTIFIER ::= { cConfigWan 1 }
--  cConfigVCTable           OBJECT IDENTIFIER ::= { cConfigWan 2 }
    cConfigWideAreaGroups    OBJECT IDENTIFIER ::= { cConfigWan 3 }
--  cConfigX25Interface      OBJECT IDENTIFIER ::= { cConfigWan 4 }
--  cConfigX25PacketCircuit  OBJECT IDENTIFIER ::= { cConfigWan 5 }
--  cConfigFrameRelayInt     OBJECT IDENTIFIER ::= { cConfigWan 6 }
--  cConfigFrameRelayCircuit OBJECT IDENTIFIER ::= { cConfigWan 7 }
--  cConfigPppInterface      OBJECT IDENTIFIER ::= { cConfigWan 8 }
--  cConfigLine              OBJECT IDENTIFIER ::= { cConfigWan 9 }

--  cConfigVls               OBJECT IDENTIFIER ::= { cConfig 4 }

    cConfigBridge            OBJECT IDENTIFIER ::= { cConfig 5 }
    cConfigLogicalBridge     OBJECT IDENTIFIER ::= { cConfigBridge 1 }
--  cConfigBridgeFilters     OBJECT IDENTIFIER ::= { cConfigBridge 2 }
--  cConfigSpanningTree      OBJECT IDENTIFIER ::= { cConfigBridge 3 }
--  cConfigSpanninPort       OBJECT IDENTIFIER ::= { cConfigBridge 4 }

    cIpAddress               OBJECT IDENTIFIER ::= { cConfig 6 }

    cConfigIpRouter          OBJECT IDENTIFIER ::= { cConfig 7 }
--  cConfigIpRouterIf        OBJECT IDENTIFIER ::= { cConfigIpRouter 1 }
--  cConfigGatewayList       OBJECT IDENTIFIER ::= { cConfigIpRouter 2 }
--  cConfigProtocols         OBJECT IDENTIFIER ::= { cConfigIpRouter 3 }
--  cConfigEgpGroups         OBJECT IDENTIFIER ::= { cConfigIpRouter 4 }
    cConfigAcceptLists       OBJECT IDENTIFIER ::= { cConfigIpRouter 5 }
    cConfigPropagateLists    OBJECT IDENTIFIER ::= { cConfigIpRouter 6 }
--  cConfigStaticRoutes      OBJECT IDENTIFIER ::= { cConfigIpRouter 7 }
--  cConfigMartianNetworks   OBJECT IDENTIFIER ::= { cConfigIpRouter 8 }
    cIpFilters               OBJECT IDENTIFIER ::= { cConfigIpRouter 9 }
--    cResetIpRouter           OBJECT IDENTIFIER ::= { cConfigIpRouter 10 }

    cConfigIpxRouter         OBJECT IDENTIFIER ::= { cConfig 8 }
    cConfigIpxBridgeIf       OBJECT IDENTIFIER ::= { cConfigIpxRouter 1 }
    cConfigIpxRouterFilters  OBJECT IDENTIFIER ::= { cConfigIpxRouter 2 }
--  cResetIpxRouter          OBJECT IDENTIFIER ::= { cConfigIpxRouter 3 }

    cConfigAppleTalk         OBJECT IDENTIFIER ::= { cConfig 9 }
    cConfigAtIf              OBJECT IDENTIFIER ::= { cConfigAppleTalk 1 }

    cConfigNetProtocol       OBJECT IDENTIFIER ::= { cConfig 10 }
    cConfigSnmp              OBJECT IDENTIFIER ::= { cConfigNetProtocol 1 }
    cConfigArp               OBJECT IDENTIFIER ::= { cConfigNetProtocol 2 }
    cConfigTcp               OBJECT IDENTIFIER ::= { cConfigNetProtocol 3 }
    cConfigTelnet            OBJECT IDENTIFIER ::= { cConfigNetProtocol 4 }
    cConfigHostTable         OBJECT IDENTIFIER ::= { cConfigNetProtocol 5 }

    cConfigSoftwareQueues    OBJECT IDENTIFIER ::= { cConfig 11 }

    cConfigFlashDnld         OBJECT IDENTIFIER ::= { cConfig 14 }

    cMonitorSystem           OBJECT IDENTIFIER ::= { cMonitor 1 }
    cMonitorSystemInfo       OBJECT IDENTIFIER ::= { cMonitorSystem 1 }
    cMonitorHeapStats        OBJECT IDENTIFIER ::= { cMonitorSystem 2 }
    cMonitorLoginHistory     OBJECT IDENTIFIER ::= { cMonitorSystem 3 }

    cMonitorBridges          OBJECT IDENTIFIER ::= { cMonitor 2 }

    cMonitorPhysInterfaces   OBJECT IDENTIFIER ::= { cMonitor 3 }

    cMonitorProto            OBJECT IDENTIFIER ::= { cMonitor 4 }
    cTcpStats                OBJECT IDENTIFIER ::= { cMonitorProto 3 }
    cIpStats                 OBJECT IDENTIFIER ::= { cMonitorProto 4 }
    cIcmpStats               OBJECT IDENTIFIER ::= { cMonitorProto 5 }
    cWanStats                OBJECT IDENTIFIER ::= { cMonitorProto 9 }

    cMonitorIpRouter         OBJECT IDENTIFIER ::= { cMonitor 5 }
    cIpRoutingStats          OBJECT IDENTIFIER ::= { cMonitorIpRouter 1 }
--  cIpRoutingTables         OBJECT IDENTIFIER ::= { cMonitorIpRouter 2 }
    cEgpStats                OBJECT IDENTIFIER ::= { cMonitorIpRouter 3 }
--  cEgpNeighborStats        OBJECT IDENTIFIER ::= { cMonitorIpRouter 4 }
    cRipStats                OBJECT IDENTIFIER ::= { cMonitorIpRouter 5 }
    cHelloStats              OBJECT IDENTIFIER ::= { cMonitorIpRouter 6 }

    cMonitorIpxRouter        OBJECT IDENTIFIER ::= { cMonitor 6 }
    cIpxStats                OBJECT IDENTIFIER ::= { cMonitorIpxRouter 1 }
--  cIpxRoutingTables        OBJECT IDENTIFIER ::= { cMonitorIpxRouter 2 }
--  cIpxServerTables         OBJECT IDENTIFIER ::= { cMonitorIpxRouter 3 }

    cMonitorAtRouter         OBJECT IDENTIFIER ::= { cMonitor 7 }
    cAtRouterStats           OBJECT IDENTIFIER ::= { cMonitorAtRouter 1 }
--  cMoniterAtRoutesZones    OBJECT IDENTIFIER ::= { cMonitorAtRouter 2 }

    cDiagnostics             OBJECT IDENTIFIER ::= { cMonitor 8 }
--  cErrorLog                OBJECT IDENTIFIER ::= { cDiagnostics 1 }

--
-- Menu path B. Configure
--              A. System
--                 A. System Information
--
-- These variable allow the control of various system data.
--

    cLocalTime OBJECT-TYPE
        SYNTAX  OCTET STRING
        ACCESS  read-write
        STATUS  mandatory

        DESCRIPTION
            "This entity is a string in the format hh:mm [am|pm]
            representing the local time on the device."
        ::= { cConfSysInfo 1 }

    cLocalDate OBJECT-TYPE
        SYNTAX  OCTET STRING
        ACCESS  read-write
        STATUS  mandatory

        DESCRIPTION
            "This entity is a string in the format mm/dd/yy or
            dd-mm-yy representing the local date on the device."
        ::= { cConfSysInfo 2 }

--    cLocalTimeZone OBJECT-TYPE
--        SYNTAX  OCTET STRING
--        ACCESS  read-write
--        STATUS  mandatory
--
--        DESCRIPTION
--            "This entity is a string representing the local timezone
--            on the device.  The following are valid strings:
--
--            [+|-]hh:mm  Hour:minute offset from UTC ('+' west, '-'
--            east)
--
--            GMT            Canada/Newfoundland         Brazil/East
--            US/Eastern     Canada/Atlantic             Brazil/West
--            US/Indiana     Canada/Eastern              Brazil/Acre
--            US/Central     Canada/Central              Brazil/DeNoronha
--            US/Mountain    Canada/East-Saskatchewan    Chile/Continental
--            US/Arizona     Canada/Mountain             Chile/EasterIsland
--            US/Pacific     Canada/Pacific              Cuba
--            US/Alaska      Canada/Yukon                GB-Erie
--            US/Hawaii      Mexico/BajaNorte            Europe/Eastern
--            US/Samoa       Mexico/BajaSur              Europe/Middle
--            US/Aleutian    Mexico/General              Europe/Western
--            Australia/NSW  New Zealand                 Japan
--            Australia/Yancowinna      Israel           Korea
--            Australia/Tasmania        Turkey           Singapore
--            Australia/Victoria        Egypt            China/PRC
--            Australia/Queensland      Iran             China/ROC
--            Australia/North           Libya            China/Hong Kong
--            Australia/West
--            Australia/South"
--        ::= { cConfSysInfo 3 }

    cLocalCtpMode OBJECT-TYPE
        SYNTAX  INTEGER {
                        standard(1),
                        extended(2)
                        }
        ACCESS  read-write
        STATUS  mandatory

        DESCRIPTION
            "This entity determines whether the local console is using
            standard vt100 key mappings or extended key mappings."
        ::= { cConfSysInfo 4 }

    cRemoteCtpMode OBJECT-TYPE
        SYNTAX  INTEGER {
                        standard(1),
                        extended(2)
                        }
        ACCESS  read-write
        STATUS  mandatory

        DESCRIPTION
            "This entity determines whether remotely logged in
            consoles use standard vt100 key mappings or extended key
            mappings."
        ::= { cConfSysInfo 5 }

    cBridgeStatsAveraging OBJECT-TYPE
        SYNTAX  INTEGER {
                        off(1),
                        on(2)
                        }
        ACCESS  read-write
        STATUS  mandatory

        DESCRIPTION
            "This entity determines whether the bridge statistics
            screens use time averaged or absolute values"
        ::= { cConfSysInfo 6 }

    cBranchTargetCache OBJECT-TYPE
        SYNTAX  INTEGER {
                        disabled(1),
                        enabled(2)
                        }
        ACCESS  read-write
        STATUS  mandatory

        DESCRIPTION
            "This entity determines whether the CPU's branch target
            cache is enabled or not."
        ::= { cConfSysInfo 7 }

--
-- Menu path B. Configure
--              A. System
--                 B. Operator Accounts
--
-- This MIB table allows you to configure Operator Accounts
--

	cOperAcctTable	OBJECT-TYPE
		SYNTAX	SEQUENCE OF OperAcctEntry
		ACCESS	not-accessible
		STATUS	mandatory
		DESCRIPTION
			"This table allows an administrator to configure the
            operar accounts which grant access to the system.  There
            are up to 60 accounts in the system."
		::= { cConfOperAcct 1 }

	cOperAcctEntry	OBJECT-TYPE
		SYNTAX	OperAcctEntry
		ACCESS	not-accessible
		STATUS	mandatory
		DESCRIPTION
			"Information on one entry in the operator accounts
            database."
		INDEX	{ cOperIndex }
		::= { cOperAcctTable 1 }

	OperAcctEntry ::= SEQUENCE {
		cOperIndex				INTEGER,
		cOperID					OCTET STRING,
		cOperPriv				INTEGER,
		cOperPasswd				OCTET STRING,
		cOperStatus				INTEGER
	}

	cOperIndex OBJECT-TYPE
		SYNTAX  INTEGER (1..60)
		ACCESS	read-write
		STATUS	mandatory

		DESCRIPTION
			"This variable indexes the table of operator accounts."
		::= { cOperAcctEntry 1 }

	cOperID OBJECT-TYPE
		SYNTAX  OCTET STRING (SIZE(1..8))
		ACCESS	read-write
		STATUS	mandatory

		DESCRIPTION
			"The name of the account"
		::= { cOperAcctEntry 2 }

	cOperPriv OBJECT-TYPE
		SYNTAX  INTEGER
				{
				privNone(1),
				privOper(2),
				privAdmin(3)
				}
		ACCESS	read-write
		STATUS	mandatory

		DESCRIPTION
			"This variable gives the privileges associated with a
            particular account.  Valid values for the field are:

			privNone  delete account,
            privOper  operator privileges,
			privAdmin administrator privileges.  Administrators are
                      allowed to configure security."
		::= { cOperAcctEntry 3 }

	cOperPasswd OBJECT-TYPE
		SYNTAX  OCTET STRING (SIZE(1..8))
		ACCESS	read-write
		STATUS	mandatory

		DESCRIPTION
			"This is the password assocated with the given account.  A
            get on this variable will return an empty string."
		::= { cOperAcctEntry 4 }

	cOperStatus OBJECT-TYPE
		SYNTAX  INTEGER
                         {
		            	valid(1),
                           createRequest(2),
                           underCreation(3),
                           invalid(4)
                         }
		ACCESS	read-write
		STATUS	mandatory

		DESCRIPTION
			"This is the current status of the row.  The only valid
            values for a manager to set this value to are
            createRequest(2) or invalid(4). The agent may return any
            of valid(1), underCreation(3) or invalid(4)."
		::= { cOperAcctEntry 5 }

--
-- Menu path B. Configure
--              J. Network Protocol
--                 A. SNMP
--                    A. Communities
--                          (and)
--                    B. Community Traps
--

    cSnmpCommunityTable	OBJECT-TYPE
		SYNTAX	SEQUENCE OF SnmpCommunityEntry
		ACCESS	not-accessible
		STATUS	mandatory
		DESCRIPTION
			"Constellation proprietary information about configured
			SNMP communities.

            Managers can configure communities, but at least one
			community must be configured via the console for the
			manager to be able to communicate with the agent in the
			first place."
		::= { cConfigSnmp 1 }

	cSnmpCommunityEntry	OBJECT-TYPE
		SYNTAX	SnmpCommunityEntry
		ACCESS	not-accessible
		STATUS	mandatory
		DESCRIPTION
			"Each entry contains information about the name of a
			community, the destination to which to send traps, the
			interface to report on, and the access allowed by this
			community."
		INDEX	{ cSnmpCommunityIndex }
		::= { cSnmpCommunityTable 1 }

	SnmpCommunityEntry ::= SEQUENCE {
		cSnmpCommunityIndex				INTEGER,
		cSnmpCommunity					OCTET STRING (SIZE(1..32)),
		cSnmpCommunityIf				INTEGER,
		cSnmpCommunityAccess			INTEGER,
		cSnmpCommunityTrapAddress		IpAddress,
		cSnmpCommunityTrapPort			INTEGER,
		cSnmpCommunityTrapEnabled		INTEGER
	}

	cSnmpCommunityIndex OBJECT-TYPE
		SYNTAX  INTEGER
		ACCESS	read-only
		STATUS	mandatory

		DESCRIPTION
			"This variable is a unique index into the snmp community table."
		::= { cSnmpCommunityEntry 1 }

	cSnmpCommunity OBJECT-TYPE
		SYNTAX  OCTET STRING (SIZE(1..32))
		ACCESS	read-write
		STATUS	mandatory

		DESCRIPTION
			"This variable represents the name of a community which
			the agent recognizes.  Each community must have a unique
			name."
		::= { cSnmpCommunityEntry 2 }

	cSnmpCommunityIf OBJECT-TYPE
		SYNTAX  INTEGER {
						lb0(1),
						lb1(2),
						lb2(3),
						lb3(4),
						wa0(5),
						wa1(6),
						router(1024)
						}
		ACCESS	read-write
		STATUS	mandatory

		DESCRIPTION
			"This variable associates an interface with the given
			community.  Each community is associated with exactly one
			interface."
--        DEFVAL { router }
		::= { cSnmpCommunityEntry 3 }

	cSnmpCommunityAccess OBJECT-TYPE
		SYNTAX  INTEGER {
						readOnly(1),
						readWrite(2)
						}
		ACCESS	read-write
		STATUS	mandatory

		DESCRIPTION
			"This variable determines whether the agent using this
			community may set or only get variables in the MIB."
--		DEFVAL { readOnly }
		::= { cSnmpCommunityEntry 4 }

	cSnmpCommunityTrapAddress OBJECT-TYPE
		SYNTAX  IpAddress
		ACCESS	read-write
		STATUS	mandatory

		DESCRIPTION
			"This variable represents the address to which the
			agent will send traps on behalf of the given community."
--		DEFVAL { 0.0.0.0 }
		::= { cSnmpCommunityEntry 5 }

	cSnmpCommunityTrapPort OBJECT-TYPE
		SYNTAX  INTEGER
		ACCESS	read-write
		STATUS	mandatory

		DESCRIPTION
			"This variable represents the port to which the agent will
			send traps on behalf of the given community."
--		DEFVAL { 162 }
		::= { cSnmpCommunityEntry 6 }

	cSnmpCommunityTrapEnabled OBJECT-TYPE
		SYNTAX  INTEGER {
	                      yes(1),
      	                no(2)
             	   }

		ACCESS	read-write
		STATUS	mandatory

		DESCRIPTION
			"This variable determines whether the agent will send
			traps on behalf of the given community."
--		DEFVAL { No }
		::= { cSnmpCommunityEntry 7 }

--
-- Menu path B. Configure
--              J. Network Protocol
--                 C. TCP
--

	cTcpKeepalive OBJECT-TYPE
		SYNTAX  INTEGER
		ACCESS	read-write
		STATUS	mandatory

		DESCRIPTION
			"This variable describes, in minutes, how long the TCP
            waits between keepalive probes."
		::= { cConfigTcp 1 }

--
-- Menu path B. Configure
--              J. Network Protocol
--                 D. Telnet
--

	cTelnetPort OBJECT-TYPE
		SYNTAX  INTEGER
		ACCESS	read-write
		STATUS	mandatory

		DESCRIPTION
			"This parameter tells the TELNET protocol on which to
            listen for incoming calls."
		::= { cConfigTelnet 1 }

	cTelnetNegotiate OBJECT-TYPE
		SYNTAX  INTEGER {
	                      yes(1),
      	                no(2)
             	         }

		ACCESS	read-write
		STATUS	mandatory

		DESCRIPTION
			"This parameter tells the TELNET protocol whether to
            negotiate negotiable parameters."
		::= { cConfigTelnet 2 }

--
-- Menu path B. Configure
--              K. Software Queues
--

--
-- A table for ethernet queues
--

    cEtherSWQTable	OBJECT-TYPE
		SYNTAX	SEQUENCE OF EtherSWQEntry
		ACCESS	not-accessible
		STATUS	mandatory
		DESCRIPTION
			"This table allows contains information about the maximum
            size and maximum lifetime of each of the packet queues on
            the LAN ports."
		::= { cConfigSoftwareQueues 1 }

	cEtherSWQEntry	OBJECT-TYPE
		SYNTAX	EtherSWQEntry
		ACCESS	not-accessible
		STATUS	mandatory
		DESCRIPTION
			"Each entry contains software queue information for one
            interface."
		INDEX	{ cEtherSWQIndex }
		::= { cEtherSWQTable 1 }

	EtherSWQEntry ::= SEQUENCE {
		cEtherSWQIndex			INTEGER (1..16),
		cEtherSWQMaxSize		INTEGER (0..512),
		cEtherSWQMaxTtl			INTEGER (5..500)
	}

	cEtherSWQIndex OBJECT-TYPE
		SYNTAX  INTEGER (1..16)
		ACCESS	read-only
		STATUS	mandatory

		DESCRIPTION
			"This index is the number of one of the ethernet
            interfaces.  The port names are mapped to integers thusly:
            e1a - e8a are entries 1-8;  e1b - e8b are entries 9-16."
		::= { cEtherSWQEntry 1 }

	cEtherSWQMaxSize OBJECT-TYPE
		SYNTAX  INTEGER (0..512)
		ACCESS	read-write
		STATUS	mandatory

		DESCRIPTION
			"The maximum number of packets that may be in the queue at
            one time for this interface."
		::= { cEtherSWQEntry 2 }

	cEtherSWQMaxTtl OBJECT-TYPE
		SYNTAX  INTEGER (5..500)
		ACCESS	read-write
		STATUS	mandatory

		DESCRIPTION
			"The maximum time in milliseconds that a packet may remain
            in the queue for this interface."
		::= { cEtherSWQEntry 3 }

--
-- Menu path B. Configure
--              L. Novram
--
-- Unlike the screen oriented control, you don't get to second guess.
-- Once you set the variable, you've reset novram
--

    cResetNovram OBJECT-TYPE
        SYNTAX  INTEGER
        ACCESS  read-write
        STATUS  mandatory

        DESCRIPTION
            "When this entity is set, novram is cleared."
        ::= { cConfig 12 }

--
-- Menu path B. Configure
--              M. System Reset
--
-- Unlike the screen oriented control, you don't get to second guess.
-- Once you set the variable, you're rebooting.
--

    cRestartSystem OBJECT-TYPE
        SYNTAX  INTEGER
        ACCESS  read-write
        STATUS  mandatory

        DESCRIPTION
            "When this entity is set, the system is restarted."
        ::= { cConfig 13 }

--
-- Menu path ?. Configure
--              N. Flash Download
--
-- Information for flash download.
--

	cFlashIpAddress OBJECT-TYPE
	SYNTAX  IpAddress
	ACCESS  read-write
	STATUS  mandatory

	DESCRIPTION
	"IP address of server with flash download file."
											    ::= { cConfigFlashDnld 1 }

	cFlashFileName OBJECT-TYPE
	SYNTAX  OCTET STRING (SIZE (0..40))
	ACCESS  read-write
	STATUS  mandatory

	DESCRIPTION
	"Name of flash download file."
	::= { cConfigFlashDnld 2 }
	cFlashBootFlag OBJECT-TYPE
	SYNTAX  INTEGER {
                      yes(1),
                      no(2)
                      }

	ACCESS  read-write
	STATUS  mandatory

	DESCRIPTION
	"Flag to determine whether or not to load new flash code."
	::= { cConfigFlashDnld 3 }
	cFlashGatewayIpAddr OBJECT-TYPE
	SYNTAX  IpAddress

        ACCESS  read-write
	STATUS  mandatory

	DESCRIPTION
	"IP address of nearest gateway.  This variable should only
	be set if the TFTP server is not on the same network as the
	bridge."
	::= { cConfigFlashDnld 4 }





--
-- Menu path C. Monitoring
--              A. System
--                 C. Login History
--

    cLoginTable	OBJECT-TYPE
		SYNTAX	SEQUENCE OF LoginEntry
		ACCESS	not-accessible
		STATUS	mandatory
		DESCRIPTION
			"This table gives a record of recent logins to the system."
		::= { cMonitorLoginHistory 1 }

	cLoginEntry	OBJECT-TYPE
		SYNTAX	LoginEntry
		ACCESS	not-accessible
		STATUS	mandatory
		DESCRIPTION
			"Each entry describes one login to the system, either
            remote or local."
		INDEX	{ cLoginIndex }
		::= { cLoginTable 1 }

	LoginEntry ::= SEQUENCE {
		cLoginIndex				INTEGER,
		cLoginUser				OCTET STRING (SIZE(1..8)),
		cLoginLocal				INTEGER,
		cLoginRemote			IpAddress
	}

	cLoginIndex OBJECT-TYPE
		SYNTAX  INTEGER
		ACCESS	read-only
		STATUS	mandatory

		DESCRIPTION
			"This variable indexes the entries in the Login History
            Table."
		::= { cLoginEntry 1 }

	cLoginUser OBJECT-TYPE
		SYNTAX  OCTET STRING (SIZE(1..8))
		ACCESS	read-only
		STATUS	mandatory

		DESCRIPTION
			"This variable contains the login name of the user for
            the current row in the table."
		::= { cLoginEntry 2 }

	cLoginLocal OBJECT-TYPE
		SYNTAX   INTEGER {
                      yes(1),
                      no(2)
                      }

		ACCESS	read-only
		STATUS	mandatory

		DESCRIPTION
			"This variable describes whether the entry specified in
            this row of the table represents a login from the local
            console (yes(1)) or remotely (no(2))."
		::= { cLoginEntry 3 }

	cLoginRemote OBJECT-TYPE
		SYNTAX  IpAddress
		ACCESS	read-only
		STATUS	mandatory

		DESCRIPTION
			"This entry gives the remote IP address of a remote login."
		::= { cLoginEntry 4 }

    cLoginFails	OBJECT-TYPE
		SYNTAX	Counter
		ACCESS	read-only
		STATUS	mandatory

		DESCRIPTION
			"This variable returns the number of attempted logins
            which have failed."
		::= { cMonitorLoginHistory 2 }

--
-- Menu path C. Monitoring
--              B. Bridges
--                 C. Node Table/Address
--

    cNodeByAddressTable	OBJECT-TYPE
		SYNTAX	SEQUENCE OF NodeByAddressEntry
		ACCESS	not-accessible
		STATUS	mandatory
		DESCRIPTION
			"This Table allows the manager to map MAC addresses to
            hash buckets and ports in the router."
		::= { cMonitorBridges 3 }

	cNodeByAddressEntry	OBJECT-TYPE
		SYNTAX	NodeByAddressEntry
		ACCESS	not-accessible
		STATUS	mandatory
		DESCRIPTION
			"Each entry contains the entry for one MAC address."
		INDEX	{ cNodeByAddressAddr }
		::= { cNodeByAddressTable 1 }

	NodeByAddressEntry ::= SEQUENCE {
		cNodeByAddressAddr		OCTET STRING (SIZE(6)),
		cNodeByAddressBridge	INTEGER,
		cNodeByAddressPort		INTEGER,
		cNodeByAddressStatus	INTEGER
	}

	cNodeByAddressAddr OBJECT-TYPE
		SYNTAX  OCTET STRING (SIZE(6))
		ACCESS	read-only
		STATUS	mandatory

		DESCRIPTION
			"This variable is the MAC address for which the manager
            wishes to find the hash bucket and port."
		::= { cNodeByAddressEntry 1 }

	cNodeByAddressBridge OBJECT-TYPE
		SYNTAX  INTEGER {
						lb0(1),
						lb1(2),
						lb2(3),
						lb3(4)
						}
		ACCESS	read-only
		STATUS	mandatory

		DESCRIPTION
			"This variable is the bridge on which the given MAC
            address is reached."
		::= { cNodeByAddressEntry 2 }

	cNodeByAddressPort OBJECT-TYPE
		SYNTAX  INTEGER
		ACCESS	read-only
		STATUS	mandatory

		DESCRIPTION
			"This variable is the port through which the given MAC
            address is reached."
		::= { cNodeByAddressEntry 3 }

	cNodeByAddressStatus OBJECT-TYPE
		SYNTAX  INTEGER {
				permanent(1),	-- a permanent entry in the given
                                -- logical bridge
				port(2),		-- MAC address of the port itself
				appeared(3),	-- a MAC address which has appeared in
                                -- the current ageing interval on the
                                -- port.
				notAppeared(4)  -- a MAC address which has appeared,
                                -- but not in the current interval.
				}
		ACCESS	read-only
		STATUS	mandatory

		DESCRIPTION
			"This variable gives the status of the given MAC address.
            If the status is 'permanent,' the contents of
            cNodeByAddressPort have no meaning."
		::= { cNodeByAddressEntry 4 }

--
-- Menu path C. Monitoring
--              B. Bridges
--                 D. Node Table/Hash
--

    cNodeByHashTable	OBJECT-TYPE
		SYNTAX	SEQUENCE OF NodeByHashEntry
		ACCESS	not-accessible
		STATUS	mandatory
		DESCRIPTION
            "This table may be used by the manager to read the
            contents of the node table, in the order in which entries
            appear in the hash table."
		::= { cMonitorBridges 4 }

	cNodeByHashEntry	OBJECT-TYPE
		SYNTAX	NodeByHashEntry
		ACCESS	not-accessible
		STATUS	mandatory
		DESCRIPTION
            "Each entry in this table represents one mapping of a MAC
            address to a bridge."
		INDEX	{ cNodeByHashIndex }
		::= { cNodeByHashTable 1 }

	NodeByHashEntry ::= SEQUENCE {
		cNodeByHashIndex		INTEGER,
		cNodeByHashBucket		INTEGER (0..511),
		cNodeByHashBridge	INTEGER,
		cNodeByHashAddress		OCTET STRING (SIZE(6)),
		cNodeByHashPort			INTEGER,
		cNodeByHashStatus		INTEGER
	}

	cNodeByHashIndex OBJECT-TYPE
		SYNTAX  INTEGER
		ACCESS	read-only
		STATUS	mandatory

		DESCRIPTION
			"This variable is an abstract index into the hash table.
            The first entry in bucket 0 is entry 1, the second entry
            in bucket 0 is 2, the first entry in bucket 1 is 3, etc."
		::= { cNodeByHashEntry 1 }

	cNodeByHashBucket OBJECT-TYPE
		SYNTAX  INTEGER (0..511)
		ACCESS	read-only
		STATUS	mandatory

		DESCRIPTION
			"This entry describes in which bucket in the hash table
            the given entry appears."
		::= { cNodeByHashEntry 2 }

	cNodeByHashAddress OBJECT-TYPE
		SYNTAX  OCTET STRING (SIZE(6))
		ACCESS	read-only
		STATUS	mandatory

		DESCRIPTION
			"This entry describes the MAC address of the given entry."
		::= { cNodeByHashEntry 3 }

	cNodeByHashBridge OBJECT-TYPE
		SYNTAX  INTEGER {
						lb0(1),
						lb1(2),
						lb2(3),
						lb3(4)
						}
		ACCESS	read-only
		STATUS	mandatory

		DESCRIPTION
			"This variable is the bridge on which the given MAC
            address is reached."
		::= { cNodeByHashEntry 4 }

	cNodeByHashPort OBJECT-TYPE
		SYNTAX  INTEGER
		ACCESS	read-only
		STATUS	mandatory

		DESCRIPTION
			"This variable describes the port through which the
            corresponding cNodeByHashAddress is accessed."
		::= { cNodeByHashEntry 5 }

	cNodeByHashStatus OBJECT-TYPE
		SYNTAX  INTEGER {
				permanent(1),	-- a permanent entry in the given
                                -- logical bridge
				port(2),		-- MAC address of the port itself
				appeared(3),	-- a MAC address which has appeared in
                                -- the current ageing interval on the
                                -- port.
				notAppeared(4)  -- a MAC address which has appeared,
                                -- but not in the current interval.
				}
		ACCESS	read-only
		STATUS	mandatory

		DESCRIPTION
			"This variable gives the status of the given MAC address.
            If the status is 'permanent,' the contents of
            cNodeByHashPort have no meaning."
		::= { cNodeByHashEntry 6 }

--
-- Menu path C. Monitoring
--              C. Phys Interfaces
--                 A. Hardware Status
--

    cHardwareStatusTable	OBJECT-TYPE
		SYNTAX	SEQUENCE OF HardwareStatusEntry
		ACCESS	not-accessible
		STATUS	mandatory
		DESCRIPTION
			"This table provides a brief description of of the
            contents and status of each hardware slot."
		::= { cMonitorPhysInterfaces 1 }

	cHardwareStatusEntry	OBJECT-TYPE
		SYNTAX	HardwareStatusEntry
		ACCESS	not-accessible
		STATUS	mandatory
		DESCRIPTION
			"Each entry in this table provides information about one
            LAN or WAN hardware slot."
		INDEX	{ cHardwareStatusIndex }
		::= { cHardwareStatusTable 1 }

	HardwareStatusEntry ::= SEQUENCE {
		cHardwareStatusIndex			INTEGER (1..31),
		cHardwareStatusSlot				INTEGER (1..11),
		cHardwareStatusContents			DisplayString,
		cHardwareStatusMacAddr			OCTET STRING (SIZE(6)),
		cHardwareStatusSerialNo			OCTET STRING,
		cHardwareStatusRevision			OCTET STRING,
		cHardwareStatusStatus			DisplayString
	}

	cHardwareStatusIndex OBJECT-TYPE
		SYNTAX  INTEGER (1..31)
		ACCESS	read-only
		STATUS	mandatory

		DESCRIPTION
            "This variable is the index into the table of values."
		::= { cHardwareStatusEntry 1 }

	cHardwareStatusSlot OBJECT-TYPE
		SYNTAX  INTEGER (1..11)
		ACCESS	read-only
		STATUS	mandatory

		DESCRIPTION
			"This variable provides the slot number as it would
            appear on the 'Hardware Configuration' screen of the
            console interface."
		::= { cHardwareStatusEntry 2 }

	cHardwareStatusContents OBJECT-TYPE
		SYNTAX  DisplayString
		ACCESS	read-only
		STATUS	mandatory

		DESCRIPTION
			"This variable describes the hardware associated with a
            given slot."
		::= { cHardwareStatusEntry 3 }

	cHardwareStatusMacAddr OBJECT-TYPE
		SYNTAX  OCTET STRING (SIZE(6))
		ACCESS	read-only
		STATUS	mandatory

		DESCRIPTION
			"This variable contains the MAC address of the hardware in
            the given slot."
		::= { cHardwareStatusEntry 4 }

	cHardwareStatusSerialNo OBJECT-TYPE
		SYNTAX  OCTET STRING
		ACCESS	read-only
		STATUS	mandatory

		DESCRIPTION
			"This variable returns the constellation serial number for
            the part in the accessed slot."
		::= { cHardwareStatusEntry 5 }

	cHardwareStatusRevision OBJECT-TYPE
		SYNTAX  OCTET STRING
		ACCESS	read-only
		STATUS	mandatory

		DESCRIPTION
			"This variable describes the revision of the hardware in
            the accessed slot."
		::= { cHardwareStatusEntry 6 }

	cHardwareStatusStatus OBJECT-TYPE
		SYNTAX  DisplayString
		ACCESS	read-only
		STATUS	mandatory

		DESCRIPTION
			"This variable gives the status of the hardware."
		::= { cHardwareStatusEntry 7 }

--
-- Menu path C. Monitoring
--              H. Diagnostics
--                 A. Error Log
--                      (AND)
--                 C. Clear Error Log
--

	cClearErrorLog OBJECT-TYPE
		SYNTAX  INTEGER
		ACCESS	read-write
		STATUS	mandatory

		DESCRIPTION
			"Setting this variable erases the accumulated error log
            from NOVRAM.  Reading it is meaningless."
		::= { cDiagnostics 1 }

    cErrorLogTable	OBJECT-TYPE
		SYNTAX	SEQUENCE OF ErrorLogEntry
		ACCESS	not-accessible
		STATUS	mandatory
		DESCRIPTION
			"This table contains the text of errors detected.  Errors
            are stored in nonvolatile memory, and hence preserved
            across reboots of the box."
		::= { cDiagnostics 2 }

	cErrorLogEntry	OBJECT-TYPE
		SYNTAX	ErrorLogEntry
		ACCESS	not-accessible
		STATUS	mandatory
		DESCRIPTION
			"Each entry contains the text of one error message."
		INDEX	{ cErrorLogIndex }
		::= { cErrorLogTable 1 }

	ErrorLogEntry ::= SEQUENCE {
		cErrorLogIndex			INTEGER,
		cErrorLogMessage		OCTET STRING (SIZE(1..80))
	}

	cErrorLogIndex OBJECT-TYPE
		SYNTAX  INTEGER
		ACCESS	read-only
		STATUS	mandatory

		DESCRIPTION
			"This is the index of an error message, with higher
            indices indicating more recent messages."
		::= { cErrorLogEntry 1 }

	cErrorLogMessage OBJECT-TYPE
		SYNTAX  OCTET STRING (SIZE(1..80))
		ACCESS	read-only
		STATUS	mandatory

		DESCRIPTION
			"This is the text of an error message."
		::= { cErrorLogEntry 2 }

-- Trap definition after RFC 1215 Conentions for defining Traps


-- generic traps for use with snmp

--    coldStart TRAP-TYPE
--	ENTERPRISE snmp
--        DESCRIPTION "A coldStart trap signifies that the sending
--                     protocol entity is reinitializing itself such
--                     that the agent's configuration or the protocol
--                     entity implementation may be altered."
--	::= 0
--
--
--   warmStart TRAP-TYPE
--   	ENTERPRISE snmp
--        DESCRIPTION "A warmStart trap signifies that the sending
--                     protocol entity is reinitializing itself such
--                     that neither the agent configuration nor the
--                     protocol entity implementation is altered."
--	::= 1
--
--   linkDown TRAP-TYPE
--   	ENTERPRISE snmp
--        DESCRIPTION "A linkDown trap signifies that the sending
--                     protocol entity recognizes a failure in one of
--                     the communication links represented in the
--                     agent's configuration."
--	::= 2
--
--   linkUp TRAP-TYPE
--   	ENTERPRISE snmp
--        DESCRIPTION "A linkUp trap signifies that the sending
--                     protocol entity recognizes that one of the
--                     communication links represented in the agent's
--                     configuration has come up."
--	::= 3
--
--   authenticationFailure TRAP-TYPE
--        ENTERPRISE snmp
--        DESCRIPTION "An authenticationFailure trap signifies that
--                     the sending protocol entity is the addressee
--                     of a protocol message that is not properly
--                     authenticated.  While implementations of the
--                     SNMP must be capable of generating this trap,
--                     they must also be capable of suppressing the
--                     emission of such traps via an implementation-
--                     specific mechanism."
--        ::= 4

          -- Traps for use by Bridges

          -- Traps for the Spanning Tree Protocol

          newRoot TRAP-TYPE
               ENTERPRISE  dot1dBridge
               DESCRIPTION
                       "The newRoot trap indicates that the sending agent
                       has become the new root of the Spanning Tree; the
                       trap is sent by a bridge soon after its election
                       as the new root, e.g., upon expiration of the
                       Topology Change Timer immediately subsequent to
                       its election."
               ::= 1

           topologyChange TRAP-TYPE
               ENTERPRISE  dot1dBridge
               DESCRIPTION
                       "A topologyChange trap is sent by a bridge when
                       any of its configured ports transitions from the
                       Learning state to the Forwarding state, or from
                       the Forwarding state to the Blocking state.  The
                       trap is not sent if a newRoot trap is sent for the
                       same transition."
               ::= 2


END
