-- ****************************************************************************
--                             AP553Liu.mib
-- ****************************************************************************

-- INNOVX Access Probe - Line Interface Unit MIB


-- Copyright 1998 General DataComm Inc., All Rights Reserved.

-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.

-- This Specification is supplied "AS IS," and GDC makes no warranty,
-- either expressed or implied, as to the use operation, condition, or
-- performance of the Specification.


-- Objects in this mib may be controlled or influenced by objects
-- in the Innovx Access Probe Core mib: InnovxCore.mib



--
-- ****************************************************************************
--                        Revision History
-- ****************************************************************************

-- Version   Date	Name/Comments

-- 1.00A     19-Nov-98  S. Veillette
--                      1) Initial Revision
--
-- 1.00B      6-Jan-99  S. Veillette
--                      1) change ap553NetIntfRcvLevel to
--                         ap553NetDS1IntfRcvLevel and add
--                         enum (6) invalidDSX1intf, same for cascade
--
-- 1.00C     27-Jan-99  S. Veillette
--                      1) remove object ap553DiagStopTest
--                      2) rename t1NoTest (4) enum  => t1StopTest (4)
--                         under ap553DiagT1Test object
--
-- 1.00D      1-Feb-99  S. Veillette
--                      1) remove Controlled Slip Seconds support objects:
--                         ap553CurrentControlledSlipSeconds
--                         ap553TotalControlledSlipSeconds
--                         ap553ControlledSlipSecondsData
--
-- 1.00E      4-Feb-99  S. Veillette
--                      1) Add WEBFLAG/WEBEND tokens to description text of
--                         enumerated objects for web page support.
--
-- 1.00F     24-Feb-99	S. Veillette
--			1) removed liuChanAlarmCfg:
--                         Channel Alarm Mask Configuration Group,
--			   moved to new InnovxDte.mib

--			2) modified Status Group objects: remove support for
--                         all interfaces except Network.  DTE status moved
--                         to InnovxDte.mib, ETX and PPP moved to
--                         InnovxCore.mib, and Cascade interface moved to
--                         InnovxCascadeLiu.mib.

-- 1.00G     25-Feb-99  S. Veillette
--                      1) Fix ap553LedStatus object:remove  SD EQP & RD EQP
--                      2) Fix ap553PortFrameCounts object: remove cascade.
--                      3) Fix ap553PortStatus object size: SIZE(2) => SIZE(1)


-- 1.00H     03-Mar-99  S. Veillette
--                      1) add BipolarViolationsErrors and LossOfSignalErrors
--                         objects to the liuCurrentStats, liuTotalStats,
--                         and liuHistoryStats groups.

-- 1.00I     03-Mar-99  A. Limoncelli
--                      1) changed BPV, CRC, and LAD window's to one minute,
--                         15 minutes, and one hour.
--			2) added a threshold of one to BPV, CRC, and LAD 
--			   threshold's  

-- 1.00J     20-Apr-99  A. Limoncelli
--			1) added ap553SystemStatus OBJECT-TYPE
--			2) added ap553CircuitAssurance OBJECT-TYPE
--			3) deleted t1NetworkInterface option from the 
--			   ap553DiagT1Test  OBJECT-TYPE
--			4) removed statT1NetworkInterface option
--			   from the ap553DiagTestStatus OBJECT-TYPE
 
-- 1.00K      5-May-99  A. Limoncelli
--			1) added ap553InbandLoop OBJECT-TYPE

-- 1.00L     21-May-99  S. Veillette
--                      1) Rename ap553DS0Format => ap553DS0Fmt
--                      2) Rename ap553NumberOfDS0s => ap553NumDS0s
--                      3) Old objects ap553DS0Format & ap553NumberOfDS0s
--                         moved as readOnly to InnovxCore.mib for common
--                         access by Repoint to all Innovx products.

-- 1.00M     21-May-99  K. Nell
--                      1) Added option to WEB stuff for LIU recveive level

-- 1.00N     21-May-99  A. Limoncelli
--                      1) added comments for stats. to represent E1

-- ****************************************************************************




--
-- ****************************************************************************
--                       mib definitions begin
-- ****************************************************************************


AP553LIU-MIB DEFINITIONS ::= BEGIN

IMPORTS	
Gauge			FROM RFC1155-SMI
OBJECT-TYPE		FROM RFC-1212
DisplayString		FROM RFC1213-MIB
liuGroup		FROM INNOVX-CORE-MIB;


liuAdmin        	OBJECT IDENTIFIER ::= { liuGroup  1 }

liuCsuNetCfg     	OBJECT IDENTIFIER ::= { liuGroup  2 }
liuDsuCfg         	OBJECT IDENTIFIER ::= { liuGroup  3 }

liuNetAlarmCfg	 	OBJECT IDENTIFIER ::= { liuGroup  4 }

liuDiagnostics		OBJECT IDENTIFIER ::= { liuGroup  5 }

liuStatus               OBJECT IDENTIFIER ::= { liuGroup  6 }

liuCurrentStats  	OBJECT IDENTIFIER ::= { liuGroup  7 }
liuTotalStats	  	OBJECT IDENTIFIER ::= { liuGroup  8 }
liuHistoryStats  	OBJECT IDENTIFIER ::= { liuGroup  9 }



--
-- ****************************************************************************
--                            Administrative Group
-- ****************************************************************************


ap553MIBversion OBJECT-TYPE
    SYNTAX DisplayString (SIZE (5))
    ACCESS read-only
    STATUS mandatory
    DESCRIPTION
    "Identifies the version of the MIB as `X.YZT' where:

	X: Major Revision         (1-9)
	Y: Minor Revision         (0-9)
	Z: Typographical Revision (0-9)
	T: Test Revision          (A-Z)

    Upon formal release, the test revision will not be present."

    ::= { liuAdmin 1 }



--
-- ****************************************************************************
--                CSU Configuration - Network Interface Group
-- ****************************************************************************


 ap553NetSetFrameType OBJECT-TYPE
    SYNTAX INTEGER
    {
        esf   (1),  -- extended superframe format
	d4    (2),  -- D4 framing format
        auto  (3)   -- the unit will determine framing format
    }
    ACCESS  read-write
    STATUS  mandatory
    DESCRIPTION
    "Defines the line interface framing type as follows:
    `esf'  sets extended superframe format,
    `d4'   sets D4 framing format,
    `auto' instructs the unit to determine framing
    WEBFLAG
    ESF
    D4
    Automatic
    WEBEND"

    ::= { liuCsuNetCfg 1 }


ap553NetOperFrameType OBJECT-TYPE
    SYNTAX INTEGER
    {
        esf   (1),  -- extended superframe format
        d4    (2),  -- D4 framing format
        auto  (3)   -- the unit is `acquiring', frame type is indeterminate
    }
    ACCESS  read-only
    STATUS  mandatory
    DESCRIPTION
    "Identifies the line interface framing type acquired by the unit as
    defined by the `ap553NetSetFrameType' object as follows:
    `esf'  indicates extended superframe format,
    `d4'   indicates D4 framing format,
    `auto' indicates the unit is still `acquiring', frame type
    is indeterminate at this time.
    WEBFLAG
    ESF
    D4
    Automatic
    WEBEND"

    ::= { liuCsuNetCfg 2 }


ap553NetEsfMode OBJECT-TYPE
    SYNTAX  INTEGER
    {
        ansi-T1-403  (1),  -- FDL exchange per ANSI specs
        tr-54016     (2)   -- FDL exchange as ESF
    }
    ACCESS  read-write
    STATUS  mandatory
    DESCRIPTION
    "Defines the use of the Facilities Data Link as follows:
    `ansi_T1_403' defines the FDL exchange per ANSI specification,
    `tr-54016' defines the FDL exchange as ESF.
    Selections of `ansi_T1_403' and `tr-54016' are only valid
    when ap553NetOperFrameType is `esf'.
    WEBFLAG
    ANSI T1.403
    TR-54016
    WEBEND"

    ::= { liuCsuNetCfg 3 }


ap553NetLineCoding OBJECT-TYPE
    SYNTAX  INTEGER
    {
        b8zs  (1),  -- binary eight zero substitution
        ami   (2)   -- alternate mark inversion
    }
    ACCESS  read-write
    STATUS  mandatory
    DESCRIPTION
    "Defines the Zero Code Suppression mechanism for the interface.

    `b8zs' defines the use of a specified  pattern  of  normal bits and
    bipolar violations used to replace a sequence of eight zero bits.

    `ami' (alternate mark inversion) defines a mode wherein no zero code
    suppression is provided. Therefore ami line encoding does not protect
    against inadequate ones density.

    The DSU will enforce an 8x(N+1) minimum ones density requirement when
    ap553NetLineCoding == `ami' and ap553DS0Fmt == `nx64k' and
    ap553DS0AllocationScheme == `consecutive'.
    WEBFLAG
    B8ZS
    AMI
    WEBEND"

    ::= { liuCsuNetCfg 4 }


ap553NetIntfType OBJECT-TYPE
    SYNTAX INTEGER
    {
	ds1-auto-lbo      (1),  -- ds1, automatic line buildout
	ds1-zero-dB       (2),  -- ds1,line buildout of   0.0 dB
	ds1-neg7pt5-dB    (3),  -- ds1,line buildout of -07.5 dB
        ds1-neg15pt0-dB   (4),  -- ds1,line buildout of -15.0 dB
        ds1-neg22pt5-dB   (5),  -- ds1,line buildout of -22.5 dB
        dsx1-preeq133-ft  (6),  -- dsx1, transmitter gain for   0 < 133 feet
        dsx1-preeq266-ft  (7),  -- dsx1, transmitter gain for 133 < 266 feet
        dsx1-preeq399-ft  (8),  -- dsx1, transmitter gain for 266 < 399 feet
        dsx1-preeq533-ft  (9),  -- dsx1, transmitter gain for 399 < 533 feet
        dsx1-preeq655-ft (10)   -- dsx1, transmitter gain for 533 < 655 feet
    }
    ACCESS read-write
    STATUS mandatory
    DESCRIPTION
    "Defines the operating mode of the interface, and the attenuation or gain.

    The following values specify operation as a standard DS1 interface, with
    the specified attenuation:
    `ds1-auto-lbo' allows the unit to determine the interface buildout value.
    `ds1-zero-dB' sets the transmit buildout to 0.0 dB.
    `ds1-neg7pt5-dB' sets the transmit buildout to -7.5dB.
    `ds1-neg15pt0-dB' sets the transmit buildout to -15.0dB.
    `ds1-neg22pt5-dB' sets the transmit buildout to -22.5dB.

    The following values specify operation as a standard cross-connect DSX-1
    interface, with the specified transmitter gain:
    `dsx1-preeq133_ft'  -- transmitter gain for 0 < 133 feet
    `dsx1-preeq266_ft'  -- transmitter gain for 133 < 266 feet
    `dsx1-preeq399_ft'  -- transmitter gain for 266 < 399 feet
    `dsx1-preeq533_ft'  -- transmitter gain for 399 < 533 feet
    `dsx1-preeq655_ft'  -- transmitter gain for 533 < 655 feet
    WEBFLAG
    DS1     Auto Line Buildout
    DS1    0.0dB Line Buildout
    DS1   -7.5dB Line Buildout    
    DS1  -15.0dB Line Buildout
    DS1  -22.5dB Line Buildout
    DSX1   0 - 133 ft Pre-equalization
    DSX1 133 - 266 ft Pre-equalization
    DSX1 266 - 399 ft Pre-equalization
    DSX1 399 - 533 ft Pre-equalization
    DSX1 533 - 655 ft Pre-equalization
    WEBEND"

    ::= { liuCsuNetCfg 5 }


ap553NetDS1IntfRcvLevel OBJECT-TYPE
    SYNTAX INTEGER 
    {
	noSignal             (1),  --  no T1 signal detected
	pos2toNeg7pt5-dB     (2),  --  + 2.0dB  to  - 7.5dB
	neg7pt5toNeg15-dB    (3),  --  - 7.5dB  to  -15.0dB
	neg15toNeg22pt5-dB   (4),  --  -15.0dB  to  -22.5dB
	lessThanNeg22pt5-dB  (5),  --  less than -22.5dB
        invalidDSX1intf      (6)   --  invalid, interface is DSX1
     }
    ACCESS read-only
    STATUS mandatory
    DESCRIPTION
    "Identifies the Network Interface Receive level for a DS1 type interface.
    `noSignal' indicates that no T1 signal is detected on the interface, (the
    `NS' LED on the unit's front panel will be on.
    `pos2toNeg7pt5-dB'=> + 2.0dB  to  - 7.5dB DS1 interface receive level
    `neg7pt5toNeg15-dB'=> - 7.5dB  to  -15.0dB DS1 interface receive level
    `neg15toNeg22pt5-dB'=> -15.0dB  to  -22.5dB DS1 interface receive level
    `lessThanNeg22pt5-dB'=> less than -22.5dB DS1 interface receive level
    `invalidDSX1intf=> invalid object, interface type is DSX1
    WEBFLAG
    no signal	
    + 2.0dB  to - 7.5dB
    - 7.5dB  to -15.0dB
    -15.0dB  to -22.5dB
    less than -22.5dB
    invalid dsx selected
    WEBEND"

    ::= { liuCsuNetCfg 6 }


--
-- ****************************************************************************
--                          DSU Configuration Group
-- ****************************************************************************


ap553DS0AllocationScheme OBJECT-TYPE
    SYNTAX INTEGER 
    {
        consecutive  (1),  -- DSU data passed in contiguous DS0 cells
        alternate    (2)   -- DSU data passed in every other DS0 cell
    }
    ACCESS read-write
    STATUS mandatory
    DESCRIPTION
    "Defines the DSU DS0 allocation scheme.
    `consecutive' specifies DSU data passed in contiguous DS0 cell assignments
    as specified by the ap553StartingDS0 and ap553NumDS0s objects.
    `alternate' specifies DSU data passed in every other DS0 cell, with each
    data cell a corresponding adjacent cell is forced to marks (ones), this
    scheme ensures that a minimum ones density requirement is met to maintain
    frame synchronization. This scheme provides a maximum throughput
    of 12x56K or 12x64K, as specified by the ap552DS0Format and 
    ap553NumDS0s objects.

    The DSU will enforce an 8x(N+1) minimum ones density requirement when
    ap553NetLineCoding == `ami' and ap553DS0Fmt == `nx64k' and
    ap553DS0AllocationScheme == `consecutive'.
    WEBFLAG
    Consecutive
    Alternate
    WEBEND"
    
    ::= { liuDsuCfg 1 }


ap553DS0Fmt OBJECT-TYPE
    SYNTAX INTEGER
    {
        nx56k  (1),  -- N X 56K rate
        nx64k  (2)   -- N X 64K rate
    }
    ACCESS read-write
    STATUS mandatory
    DESCRIPTION
    "Defines the DS0 base rate as either 56K or 64K bits per second.
    This object value, in conjunction with the ap553NumDS0s object
    value determines the LIU aggregate bandwidth.
    `nx64k' defines a DS0 data format as clear channel in which all 8 bits
    of the DS0 are used for data. 
    `nx56k defines a DS0 data format as 7 bits for data, and 1 bit used for
    signalling information or unused and forced to marks.

    The DSU will enforce an 8x(N+1) minimum ones density requirement when
    ap553NetLineCoding == `ami' and ap553DS0Fmt == `nx64k' and
    ap553DS0AllocationScheme == `consecutive'.
    WEBFLAG
    N x 56K
    N x 64K
    WEBEND"

    ::= { liuDsuCfg 2 }


ap553StartingDS0 OBJECT-TYPE
    SYNTAX INTEGER (1..24)
    ACCESS read-write
    STATUS mandatory
    DESCRIPTION
    "Defines the starting DS0 number for the bundle of DS0s used for the LIU
    aggregate bandwidth.

    Values of 1-24 are valid when ap553DS0AllocationScheme is consecutive.
    Values of 1-23 are valid when ap553DS0AllocationScheme is alternate."

    ::= { liuDsuCfg 3 }


ap553NumDS0s OBJECT-TYPE
    SYNTAX INTEGER (1..24)
    ACCESS read-write
    STATUS mandatory
    DESCRIPTION
    "Defines the number of DS0 cells used for passing DSU data. 
    When ap553DS0AllocationScheme is consecutive, valid values are 1 - N
    where N <= (25 - ap553StartingDS0).
    When ap553DS0AllocationScheme is alternate, valid values are 1 - N
    where N <= (25 - ap553StartingDS0)/2."

    ::= { liuDsuCfg 4 }


ap553LIUAggregateRate OBJECT-TYPE
    SYNTAX DisplayString (SIZE(11))
    ACCESS read-only
    STATUS mandatory
    DESCRIPTION
    "Displays the current aggregate LIU data rate as:

    ` aggRate Kbps ' with values ranging from ` 56 Kbps ' to ` 1536 Kbps ',
    where aggregate rate is calculated as follows: 

       aggRate = ap553NumDS0s * (ap553DS0Fmt == `nx56k') ? 56 : 64;"
		    
    ::= { liuDsuCfg 5 }


ap553SystemStatus OBJECT-TYPE
    SYNTAX INTEGER 
    {
       	disable  (1),
        enable   (2)
    }
    ACCESS read-write
    STATUS mandatory
    DESCRIPTION
    "The System Status option.  When enabled, allows the DSU to clamp DSR
    upon receiving the following Network codes:

     	1. Out of Service Code (OOS)
	2. Abnormal Station Code (ASC)
	3. No Signal(not a network code)
	4. other inactive channel codes (ICC)

    WEBFLAG
    Disable
    Enable
    WEBEND"

    ::= { liuDsuCfg 6 }


ap553CircuitAssurance OBJECT-TYPE
    SYNTAX INTEGER 
    {
    	disable  (1),
        enable   (2)
    }
    ACCESS read-write
    STATUS mandatory
    DESCRIPTION
    "The Circuit Assurance option. When enabled, allows the DSU to clamp
    CTS upon receiving the following Network codes:

	 1. IDLE(no DCD)
    	 2. Out of Service Code (OOS)
	 3. Abnormal Station Code (ASC)
	 4. No Signal(not a network code)
	 5. other inactive channel codes (ICC)

    WEBFLAG
    Disable
    Enable
    WEBEND"

    ::= { liuDsuCfg 7 }


ap553InbandLoop OBJECT-TYPE
    SYNTAX INTEGER 
    {
    	inhibit  	(1),
        payloadloop	(2),
        lineloop	(3)
    }
    ACCESS read-write
    STATUS mandatory
    DESCRIPTION
    "The Inband Loop Control option. Defines the DSU response to Inband Line
    Loopback codes as follows:

         inhibit     - the DSU does not respond to in-band T1 loop codes
         payloadloop - the DSU starts or stops a payload loop test
         lineloop    - the DSU starts or stops a line loop test

    WEBFLAG
    Inhibit
    Start/Stop Payload Loop
    Start/Stop Line Loop
    WEBEND"

    ::= { liuDsuCfg 8 }



--
-- ****************************************************************************
--          Network Alarm Mask, Window & Threshold Configuration Group
-- ****************************************************************************


ap553NetBpvTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Network Bipolar
    Violations Alarm when this event occurs and meets the window & threshold
    requirements for reporting as specified by the associated window and
    threshold object values below.
    WEBFLAG
    Inhibit
    Critical
    Major
    Minor
    Warning
    Info
    WEBEND"

    ::= { liuNetAlarmCfg 1 }


ap553NetBpvWindow OBJECT-TYPE
    SYNTAX INTEGER
    {
        oneMinute   	(1), -- 1 minute sampling window, report one event only
        fifteenMinutes  (2), -- 15 minutes sampling window, report one event
        oneHour    	(3)  -- 1 hour sampling window, report one event only

    }
    ACCESS read-write
    STATUS mandatory
    DESCRIPTION
    "Specifies the sampling window in which to report the Network Bipolar
    Violations alarm condition as active.

    All other values specify the size of the sampling window in which the 
    event may be reported one time as active, as controlled by the associated
    mask object value, when the associated obj's threshold condition is met.
    WEBFLAG
    One Minute
    Fifteen Minutes
    One Hour
    WEBEND"

    ::= { liuNetAlarmCfg 2 }


ap553NetBpvThresh OBJECT-TYPE
    SYNTAX INTEGER
    {
	thr1      (1),
	thr10     (2),
	thr100    (3),
	thr1000   (4),
	thr10000  (5)
    }
    ACCESS read-write
    STATUS mandatory
    DESCRIPTION
    "Specifies the threshold of events to be exceeded for reporting the
    Network Bipolar Violations alarm condition.
    WEBFLAG
    1
    10
    100
    1,000
    10,000
    WEBEND"

    ::= { liuNetAlarmCfg 3 }


ap553NetCrcTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Network Cyclical
    Redundancy Check Alarm when this event occurs and meets the window and
    threshold requirements for reporting as specified by the associated 
    window and threshold object values below.
    WEBFLAG
    Inhibit
    Critical
    Major
    Minor
    Warning
    Info
    WEBEND"

    ::= { liuNetAlarmCfg 4 }


ap553NetCrcWindow OBJECT-TYPE
    SYNTAX INTEGER
    {
        oneMinute   	(1), -- 1 minute sampling window, report one event only
        fifteenMinutes  (2), -- 15 minutes sampling window, report one event
        oneHour    	(3)  -- 1 hour sampling window, report one event only
    }
    ACCESS read-write
    STATUS mandatory
    DESCRIPTION
    "Specifies the sampling window in which to report the Network Cyclical
    Redundancy Check alarm condition as active.


    All other values specify the size of the sampling window in which the 
    event may be reported one time as active, as controlled by the associated
    mask object value, when the associated obj's threshold condition is met.
    WEBFLAG
    One Minute
    Fifteen Minutes
    One Hour
    WEBEND"

    ::= { liuNetAlarmCfg 5 }


ap553NetCrcThresh OBJECT-TYPE
    SYNTAX INTEGER
    {
	thr1      (1),
	thr10     (2),
	thr100    (3),
	thr1000   (4),
	thr10000  (5)
    }
    ACCESS read-write
    STATUS mandatory
    DESCRIPTION
    "Specifies the threshold of events to be exceeded for reporting the 
    Network Cyclical Redundancy Check alarm condition.
    WEBFLAG
    1
    10
    100
    1,000
    10,000
    WEBEND"

    ::= { liuNetAlarmCfg 6 }


ap553NetLadTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Network Low
    Average Density Alarm when this event occurs and meets the window and
    threshold requirements for reporting as specified by the associated 
    window and threshold object values below.
    WEBFLAG
    Inhibit
    Critical
    Major
    Minor
    Warning
    Info
    WEBEND"

    ::= { liuNetAlarmCfg 7 }


ap553NetLadWindow OBJECT-TYPE
    SYNTAX INTEGER
    {
        oneMinute   	(1), -- 1 minute sampling window, report one event only
        fifteenMinutes  (2), -- 15 minutes sampling window, report one event
        oneHour    	(3)  -- 1 hour sampling window, report one event only
    }
    ACCESS read-write
    STATUS mandatory
    DESCRIPTION
    "Specifies the sampling window in which to report the Network Low Average
    Density alarm condition as active.

    All other values specify the size of the sampling window in which the 
    event may be reported one time as active, as controlled by the associated
    mask object value, when the associated obj's threshold condition is met.
    WEBFLAG
    One Minute
    Fifteen Minutes
    One Hour
    WEBEND"

    ::= { liuNetAlarmCfg 8 }


ap553NetLadThresh OBJECT-TYPE
    SYNTAX INTEGER
    {
	thr1      (1),
	thr10     (2),
	thr100    (3),
	thr1000   (4),
	thr10000  (5)
    }
    ACCESS read-write
    STATUS mandatory
    DESCRIPTION
    "Specifies the threshold of events to be exceeded for reporting the
    Network Low Average Density alarm condition. 
    WEBFLAG
    1
    10
    100
    1,000
    10,000
    WEBEND"

    ::= { liuNetAlarmCfg 9 }


ap553NetAisTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Network Alarm
    Indication Signal Alarm when this event occurs.
    WEBFLAG
    Inhibit
    Critical
    Major
    Minor
    Warning
    Info
    WEBEND"

    ::= { liuNetAlarmCfg 10 }


ap553NetLosTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Network Loss of
    Signal Alarm when this event occurs.
    WEBFLAG
    Inhibit
    Critical
    Major
    Minor
    Warning
    Info
    WEBEND"

    ::= { liuNetAlarmCfg 11 }


ap553NetOofTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Network Out of
    Frame Alarm when this event occurs.
    WEBFLAG
    Inhibit
    Critical
    Major
    Minor
    Warning
    Info
    WEBEND"

    ::= { liuNetAlarmCfg 12 }


ap553NetRcdYelTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Network Received
    Yellow Alarm when this event occurs.
    WEBFLAG
    Inhibit
    Critical
    Major
    Minor
    Warning
    Info
    WEBEND"

    ::= { liuNetAlarmCfg 13 }


ap553NetUssTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Network
    Unavailable Signal State Alarm when this event occurs.
    WEBFLAG
    Inhibit
    Critical
    Major
    Minor
    Warning
    Info
    WEBEND"

    ::= { liuNetAlarmCfg 14 }




--
-- ****************************************************************************
--                        Diagnostics Group
-- ****************************************************************************


ap553DiagT1Test OBJECT-TYPE
    SYNTAX INTEGER 
    {
	t1LineLoopback        (1),
	t1PayLoadLoopback     (2),
	t1StopTest            (3)
    }
    ACCESS read-write
    STATUS mandatory
    DESCRIPTION 
    "Specifies the test to be executed, or stops the current test."

    ::= { liuDiagnostics 1 }


ap553DiagTestDuration OBJECT-TYPE
    SYNTAX INTEGER
    {
        testTime1Min    (1),
        testTime5Mins   (2),
        testTime10Mins  (3),
        testTime20Mins  (4)
    }
    ACCESS read-write
    STATUS mandatory
    DESCRIPTION
    "Defines the length of all LIU diagnostic tests."

    ::= { liuDiagnostics 2 }


ap553DiagTestStatus OBJECT-TYPE
    SYNTAX INTEGER
    {

	statT1LineLoopback        (1),
	statT1PayLoadLoopback     (2),
	statNoTestinProgress      (3)
    }
    ACCESS read-only
    STATUS mandatory
    DESCRIPTION
    "Displays the test in progress, if any."

    ::= { liuDiagnostics 3 }


--
-- ****************************************************************************
--                             Status Group
-- ****************************************************************************


ap553LedStatus OBJECT-TYPE
    SYNTAX OCTET STRING (SIZE(1))
    ACCESS read-only
    STATUS mandatory
    DESCRIPTION
    "A bitwise snapshot of the front panel LED states, 
    where 0 = LED off and 1 = LED on, as follows:

                        LED       description
 
    Octet 1     bit 7 - n/u
		bit 6 - n/u
		bit 5 - n/u
		bit 4 - DCE LMI   LMI traffic on DCE
		bit 3 - SD NTWK   send data - network traffic
		bit 2 - RD NTWK   receive data - network traffic
		bit 1 - NS        No Signal on T1 interface
		bit 0 - OOF       Out of Frame condition on T1 Interface"

    ::= { liuStatus 1 }


ap553PortStatus OBJECT-TYPE
    SYNTAX  OCTET STRING (SIZE(1))
    ACCESS  read-only
    STATUS  mandatory
    DESCRIPTION
    "A bitwise snapshot of interface port status conditions and EIA signals,
    where 0 = condition not present, and 1 = condition present, as follows:

    Octet 1 - NETWORK Interface Port Status
 		bit 7 - n/u
               	bit 6 - n/u
                bit 5 - n/u
                bit 4 - n/u
                bit 3 - Alarm Indication Signal
                bit 2 - Out Of Frame Alarm
                bit 1 - Loss Of Signal Alarm
                bit 0 - Remote Alarm"

    ::= { liuStatus 2 }


ap553PortFrameCounts OBJECT-TYPE
    SYNTAX  OCTET STRING (SIZE(4))
    ACCESS  read-only
    STATUS  mandatory
    DESCRIPTION
    "The total number of frames transmitted and received on each interface
    port.  This object will be reset to zero after a read, and after power up,
    soft reset, or factory defaults reset.

    Octet 1 - NETWORK Interface Transmit Frame Count	Octet 2
 		bit 7 - 2^15 				bit 7 - 2^7
               	bit 6 - 2^14				bit 6 - 2^6	
                bit 5 - 2^13				bit 5 - 2^5
                bit 4 - 2^12				bit 4 - 2^4	
                bit 3 - 2^11				bit 3 - 2^3
                bit 2 - 2^10				bit 2 - 2^2
                bit 1 - 2^9				bit 1 - 2^1
                bit 0 - 2^8				bit 0 - 2^0

    Octet 3 - NETWORK Interface Receive Frame Count	Octet 4
 		bit 7 - 2^15 				bit 7 - 2^7
               	bit 6 - 2^14				bit 6 - 2^6	
                bit 5 - 2^13				bit 5 - 2^5
                bit 4 - 2^12				bit 4 - 2^4	
                bit 3 - 2^11				bit 3 - 2^3
                bit 2 - 2^10				bit 2 - 2^2
                bit 1 - 2^9				bit 1 - 2^1
                bit 0 - 2^8				bit 0 - 2^0"

::= { liuStatus 3 }
    


--
-- ****************************************************************************
--                   Current Interval Statistics Group
-- ****************************************************************************



ap553CurrentIntervalCompletion OBJECT-TYPE
    SYNTAX INTEGER (0..100)
    ACCESS read-only
    STATUS mandatory
    DESCRIPTION
    "The elapsed time into the current interval expressed as a percent of
    completion from 0 to 100%.  When the current Line Stats interval
    is complete (15 minutes), the collected data is moved into the first
    historical interval (#1), and collection begins again in this object.
    This object will be reset to zero after a read, and after power up,
    soft reset, or factory defaults reset."

    ::= { liuCurrentStats 1 }


ap553CurrentErroredSeconds OBJECT-TYPE
    SYNTAX Gauge
    ACCESS read-only
    STATUS mandatory
    DESCRIPTION
    "The Line statistics for the current 15 minute interval, also specifies
    the percent completion of this interval.  When the current Line Stats
    interval time is complete (15 minutes), this data is moved into the first
    historical interval (#1), and collection begins again in this object.
    This object will be reset to zero after a read, and after power up,
    soft reset, or factory defaults reset."

    ::= { liuCurrentStats 2 }


ap553CurrentSeverelyErroredSeconds OBJECT-TYPE
    SYNTAX Gauge
    ACCESS read-only
    STATUS mandatory
    DESCRIPTION
    "The Line statistics for the current 15 minute interval, also specifies
    the percent completion of this interval.  When the current Line Stats
    interval time is complete (15 minutes), this data is moved into the first
    historical interval (#1), and collection begins again in this object.
    This object will be reset to zero after a read, and after power up,
    soft reset, or factory defaults reset."

    ::= { liuCurrentStats 3 }


ap553CurrentBurstyErroredSeconds OBJECT-TYPE
    SYNTAX Gauge
    ACCESS read-only
    STATUS mandatory
    DESCRIPTION
    "The Line statistics for the current 15 minute interval, also specifies
    the percent completion of this interval.  When the current Line Stats
    interval time is complete (15 minutes), this data is moved into the first
    historical interval (#1), and collection begins again in this object.
    This object will be reset to zero after a read, and after power up,
    soft reset, or factory defaults reset.
    For a E1 product this statistic is Frame Alignment Signal Errors"

    ::= { liuCurrentStats 4 }


ap553CurrentCrcErrors OBJECT-TYPE
    SYNTAX Gauge
    ACCESS read-only
    STATUS mandatory
    DESCRIPTION
    "The Line statistics for the current 15 minute interval, also specifies
    the percent completion of this interval.  When the current Line Stats
    interval time is complete (15 minutes), this data is moved into the first
    historical interval (#1), and collection begins again in this object.
    This object will be reset to zero after a read, and after power up,
    soft reset, or factory defaults reset.
    For a E1 product this statistic is CRC4"

    ::= { liuCurrentStats 5 }


ap553CurrentUnavailableSeconds OBJECT-TYPE
    SYNTAX Gauge
    ACCESS read-only
    STATUS mandatory
    DESCRIPTION
    "The Line statistics for the current 15 minute interval, also specifies
    the percent completion of this interval.  When the current Line Stats
    interval time is complete (15 minutes), this data is moved into the first
    historical interval (#1), and collection begins again in this object.
    This object will be reset to zero after a read, and after power up,
    soft reset, or factory defaults reset."

    ::= { liuCurrentStats 6 }


ap553CurrentLossOfFrameErrors OBJECT-TYPE
    SYNTAX Gauge
    ACCESS read-only
    STATUS mandatory
    DESCRIPTION
    "The Line statistics for the current 15 minute interval, also specifies
    the percent completion of this interval.  When the current Line Stats
    interval time is complete (15 minutes), this data is moved into the first
    historical interval (#1), and collection begins again in this object.
    This object will be reset to zero after a read, and after power up,
    soft reset, or factory defaults reset.
    For a E1 product this statistic is Far End Block Errors"

    ::= { liuCurrentStats 7 }


ap553CurrentBipolarViolationsErrors OBJECT-TYPE
    SYNTAX Gauge
    ACCESS read-only
    STATUS mandatory
    DESCRIPTION
    "The Line statistics for the current 15 minute interval, also specifies
    the percent completion of this interval.  When the current Line Stats
    interval time is complete (15 minutes), this data is moved into the first
    historical interval (#1), and collection begins again in this object.
    This object will be reset to zero after a read, and after power up,
    soft reset, or factory defaults reset.
    For a E1 product this statistic is LCV"

    ::= { liuCurrentStats 8 }


ap553CurrentLossOfSignalErrors OBJECT-TYPE
    SYNTAX Gauge
    ACCESS read-only
    STATUS mandatory
    DESCRIPTION
    "The Line statistics for the current 15 minute interval, also specifies
    the percent completion of this interval.  When the current Line Stats
    interval time is complete (15 minutes), this data is moved into the first
    historical interval (#1), and collection begins again in this object.
    This object will be reset to zero after a read, and after power up,
    soft reset, or factory defaults reset.
    For a E1 product this statistic is not used"

    ::= { liuCurrentStats 9 }


--
-- ********************************************************************
--                  24 Hour Totals Statistics Group
-- ********************************************************************

ap553TotalErroredSeconds OBJECT-TYPE
    SYNTAX Gauge
    ACCESS read-only
    STATUS mandatory
    DESCRIPTION
    "The line statistics totals of the valid Line Statistics Interval
    objects as specified by the ap553ValidHistoryIntervals object value.
    This object will be reset to zero after a read, and after power up,
    soft reset, or factory defaults reset."

    ::= { liuTotalStats 1 }
 

ap553TotalSeverelyErroredSeconds OBJECT-TYPE
    SYNTAX Gauge
    ACCESS read-only
    STATUS mandatory
    DESCRIPTION
    "The line statistics totals of the valid Line Statistics Interval
    objects as specified by the ap553ValidHistoryIntervals object value.
    This object will be reset to zero after a read, and after power up,
    soft reset, or factory defaults reset."

    ::= { liuTotalStats 2 }
 

ap553TotalBurstyErroredSeconds OBJECT-TYPE
    SYNTAX Gauge
    ACCESS read-only
    STATUS mandatory
    DESCRIPTION
    "The line statistics totals of the valid Line Statistics Interval
    objects as specified by the ap553ValidHistoryIntervals object value.
    This object will be reset to zero after a read, and after power up,
    soft reset, or factory defaults reset.
    For a E1 product this statistic is Frame Alignment Signal Errors."

    ::= { liuTotalStats 3 }
 

ap553TotalCrcErrors OBJECT-TYPE
    SYNTAX Gauge
    ACCESS read-only
    STATUS mandatory
    DESCRIPTION
    "The line statistics totals of the valid Line Statistics Interval
    objects as specified by the ap553ValidHistoryIntervals object value.
    This object will be reset to zero after a read, and after power up,
    soft reset, or factory defaults reset.
    For a E1 product this statistic is CRC4"

    ::= { liuTotalStats 4 }
 

ap553TotalUnavailableSeconds OBJECT-TYPE
    SYNTAX Gauge
    ACCESS read-only
    STATUS mandatory
    DESCRIPTION
    "The line statistics totals of the valid Line Statistics Interval
    objects as specified by the ap553ValidHistoryIntervals object value.
    This object will be reset to zero after a read, and after power up,
    soft reset, or factory defaults reset."

    ::= { liuTotalStats 5 }
 

ap553TotalLossOfFrameErrors OBJECT-TYPE
    SYNTAX Gauge
    ACCESS read-only
    STATUS mandatory
    DESCRIPTION
    "The line statistics totals of the valid Line Statistics Interval
    objects as specified by the ap553ValidHistoryIntervals object value.
    This object will be reset to zero after a read, and after power up,
    soft reset, or factory defaults reset.
    For a E1 product this statistic is Far End Block Errors"

    ::= { liuTotalStats 6 }

 
ap553TotalBipolarViolationsErrors OBJECT-TYPE
    SYNTAX Gauge
    ACCESS read-only
    STATUS mandatory
    DESCRIPTION
    "The line statistics totals of the valid Line Statistics Interval
    objects as specified by the ap553ValidHistoryIntervals object value.
    This object will be reset to zero after a read, and after power up,
    soft reset, or factory defaults reset.
    For a E1 product this statistic is LCV"

    ::= { liuTotalStats 7 }

 
ap553TotalLossOfSignalErrors OBJECT-TYPE
    SYNTAX Gauge
    ACCESS read-only
    STATUS mandatory
    DESCRIPTION
    "The line statistics totals of the valid Line Statistics Interval
    objects as specified by the ap553ValidHistoryIntervals object value.
    This object will be reset to zero after a read, and after power up,
    soft reset, or factory defaults reset.
    For a E1 product this statistic is not used."

    ::= { liuTotalStats 8 }

 


--
-- ********************************************************************
--                24 Hour History Statistics Table
-- ********************************************************************

ap553ValidHistoryIntervals OBJECT-TYPE
    SYNTAX  INTEGER (0..96)
    ACCESS  read-only
    STATUS  mandatory
    DESCRIPTION
    "The number of 15 minute intervals for which line statistics data has
    been collected.  The value will be 96 unless the interface was brought
    on-line within the last 24 hours, in which case the value will be the
    number of complete 15 minute intervals the interface has been online.
    This object will be reset to zero after a read, and after power up,
    soft reset, or factory defaults reset."

    ::= { liuHistoryStats 1 }


ap553LineStats24hrHistoryTable 	OBJECT-TYPE
    SYNTAX  SEQUENCE OF Ap553HistoryEntry
    ACCESS  not-accessible
    STATUS  mandatory
    DESCRIPTION
    "The ap553 Line Statistics 24 hour history table. This table is comprised
    of 96 objects, each of which hold T1 Line statistics data for a 15 minute
    time period.  Upon power up or after a reset, data is collected in the
    current interval object: ap553CurrentLineStats.  After 15 minutes this
    data is moved into the first of 96 historical objects.  After each sub- 
    sequent 15 minute period completes, data is moved downstream, data from
    interval #1 is moved into interval #2, etc.  The number of valid history
    intervals contained in ap553ValidLineStatsIntervals is incremented. The
    ap553TotalLineStats object is recalculated after each 15 minute interval
    completes, summing all valid interval data into this object.  When all
    96 objects have been filled, containing 24 hours of data, the oldest
    object, #96, will be overwritten by object #95, at the completion of the
    next 15 minute interval.  In this fashion, the unit is able to maintain
    a current 24 hour history of Line Statistics data."

    ::= { liuHistoryStats 2 }

ap553HistoryEntry OBJECT-TYPE
    SYNTAX  Ap553HistoryEntry
    ACCESS  not-accessible
    STATUS  mandatory
    DESCRIPTION
    "An entry in the Line Statistics 24 hour history table."
    INDEX
    { 
        ap553HistoryInterval
    }

    ::= { ap553LineStats24hrHistoryTable 1 }


Ap553HistoryEntry ::=
    SEQUENCE
    {
        ap553HistoryInterval			INTEGER,
        ap553ErroredSecondsData			Gauge,
        ap553SeverelyErroredSecondsData		Gauge,
        ap553BurstyErroredSecondsData		Gauge,
        ap553CrcErrorsData			Gauge,
        ap553UnavailableSecondsData		Gauge,
        ap553LossOfFrameErrorsData  		Gauge,
        ap553BipolarViolationsErrorsData	Gauge,
        ap553LossOfSignalErrorsData		Gauge
    }

 
ap553HistoryInterval 	OBJECT-TYPE
    SYNTAX  INTEGER (1..96)
    ACCESS  read-only
    STATUS  mandatory
    DESCRIPTION
    "Identifies the relative time period of this data. Interval #1 is the most
    recent historical 15 minute period.  Interval #96 is the oldest 15 minute
    time period in the current 24 hour history."

    ::= { ap553HistoryEntry 1 }


ap553ErroredSecondsData OBJECT-TYPE
    SYNTAX Gauge
    ACCESS read-only
    STATUS mandatory
    DESCRIPTION
    "The Line Statistics Data for a 15 minute historical period
    within the last 24 hours, as specified by the ap553HistoryInterval.
    This object will be reset to zero after a read, and after power up,
    soft reset, or factory defaults reset."

    ::= { ap553HistoryEntry 2 }


ap553SeverelyErroredSecondsData OBJECT-TYPE
    SYNTAX Gauge
    ACCESS read-only
    STATUS mandatory
    DESCRIPTION
    "The Line Statistics Data for a 15 minute historical period
    within the last 24 hours, as specified by the ap553HistoryInterval.
    This object will be reset to zero after a read, and after power up,
    soft reset, or factory defaults reset."

    ::= { ap553HistoryEntry 3 }


ap553BurstyErroredSecondsData OBJECT-TYPE
    SYNTAX Gauge
    ACCESS read-only
    STATUS mandatory
    DESCRIPTION
    "The Line Statistics Data for a 15 minute historical period
    within the last 24 hours, as specified by the ap553HistoryInterval.
    This object will be reset to zero after a read, and after power up,
    soft reset, or factory defaults reset.
    For a E1 product this statistic is Frame Alignment Signal Errors"

    ::= { ap553HistoryEntry 4 }


ap553CrcErrorsData OBJECT-TYPE
    SYNTAX Gauge
    ACCESS read-only
    STATUS mandatory
    DESCRIPTION
    "The Line Statistics Data for a 15 minute historical period
    within the last 24 hours, as specified by the ap553HistoryInterval.
    This object will be reset to zero after a read, and after power up,
    soft reset, or factory defaults reset.
    For a E1 product this statistic is CRC4"

    ::= { ap553HistoryEntry 5 }


ap553UnavailableSecondsData OBJECT-TYPE
    SYNTAX Gauge
    ACCESS read-only
    STATUS mandatory
    DESCRIPTION
    "The Line Statistics Data for a 15 minute historical period
    within the last 24 hours, as specified by the ap553HistoryInterval.
    This object will be reset to zero after a read, and after power up,
    soft reset, or factory defaults reset."

    ::= { ap553HistoryEntry 6 }


ap553LossOfFrameErrorsData OBJECT-TYPE
    SYNTAX Gauge
    ACCESS read-only
    STATUS mandatory
    DESCRIPTION
    "The Line Statistics Data for a 15 minute historical period
    within the last 24 hours, as specified by the ap553HistoryInterval.
    This object will be reset to zero after a read, and after power up,
    soft reset, or factory defaults reset.
    For a E1 product this statistic is Far End Block Errors"

    ::= { ap553HistoryEntry 7 }


ap553BipolarViolationsErrorsData OBJECT-TYPE
    SYNTAX Gauge
    ACCESS read-only
    STATUS mandatory
    DESCRIPTION
    "The Line Statistics Data for a 15 minute historical period
    within the last 24 hours, as specified by the ap553HistoryInterval.
    This object will be reset to zero after a read, and after power up,
    soft reset, or factory defaults reset.
    For a E1 product this statistic is LCV"

    ::= { ap553HistoryEntry 8 }


ap553LossOfSignalErrorsData OBJECT-TYPE
    SYNTAX Gauge
    ACCESS read-only
    STATUS mandatory
    DESCRIPTION
    "The Line Statistics Data for a 15 minute historical period
    within the last 24 hours, as specified by the ap553HistoryInterval.
    This object will be reset to zero after a read, and after power up,
    soft reset, or factory defaults reset.
    For a E1 product this statistic is not used."

    ::= { ap553HistoryEntry 9 }



-- ****************************************************************************
--                       mib definitions end
-- ****************************************************************************

END
