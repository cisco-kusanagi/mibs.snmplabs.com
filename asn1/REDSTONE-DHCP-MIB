-- *****************************************************************
-- REDSTONE-DHCP-MIB
--
-- Redstone Communications Inc. Enterprise MIB
-- DHCP MIB
--
-- Copyright 1999 Redstone Communications, Incorporated.
-- All Rights Reserved.
-- *****************************************************************

REDSTONE-DHCP-MIB DEFINITIONS ::= BEGIN

IMPORTS
    MODULE-IDENTITY, 
    OBJECT-TYPE, 
    IpAddress
        FROM SNMPv2-SMI

    RowStatus
        FROM SNMPv2-TC

    MODULE-COMPLIANCE, 
    OBJECT-GROUP  
        FROM SNMPv2-CONF

    rsMgmt
		FROM REDSTONE-SMI

    RsEnable
        FROM REDSTONE-TC;


rsDhcpMIB MODULE-IDENTITY
    LAST-UPDATED "9906010000Z"
    ORGANIZATION "Redstone Communications Inc."
	CONTACT-INFO
        "
        Redstone Communications, Inc.
		5 Carlisle Road
        Westford MA 01886
        USA
        Tel:    +1-978-692-1999
		Email:  mib@redstonecom.com
        "
	DESCRIPTION
		"The DHCP MIB for the
		Redstone Communications Inc. enterprise."
	REVISION      "9906010000Z"
	DESCRIPTION
		"Initial version of this MIB module."
    ::= { rsMgmt 22 }


-- ++++++++++++++++++++++++++++++++++++++++++++++++++++++++++++++++++++++
-- Textual conventions
-- ++++++++++++++++++++++++++++++++++++++++++++++++++++++++++++++++++++++

-- No textual conventions are defined in this MIB



-- ++++++++++++++++++++++++++++++++++++++++++++++++++++++++++++++++++++++
-- Managed object groups
-- ++++++++++++++++++++++++++++++++++++++++++++++++++++++++++++++++++++++


rsDhcpObjects       OBJECT IDENTIFIER ::= {rsDhcpMIB 1}
rsDhcpRelay         OBJECT IDENTIFIER ::= {rsDhcpObjects 1}
rsDhcpProxy         OBJECT IDENTIFIER ::= {rsDhcpObjects 2}

-- ++++++++++++++++++++++++++++++++++++++++++++++++++++++++++++++++++++++
-- Managed objects for DHCP Relay
-- ++++++++++++++++++++++++++++++++++++++++++++++++++++++++++++++++++++++

--
-- DHCP Relay Scalars
-- 
rsDhcpRelayScalars  OBJECT IDENTIFIER ::= {rsDhcpRelay 1}

rsDhcpRelayAgentInfoEnable OBJECT-TYPE
    SYNTAX      RsEnable
    MAX-ACCESS  read-write
    STATUS      current
    DESCRIPTION
        "Enable/disable use of the DHCP Relay Agent Info option."
    ::= { rsDhcpRelayScalars 1 }


--
-- DHCP Relay Server Table
--

rsDhcpRelayServerTable OBJECT-TYPE
    SYNTAX      SEQUENCE OF RsDhcpRelayServerEntry
    MAX-ACCESS  not-accessible
    STATUS      current
    DESCRIPTION
        "The (conceptual) table listing the DHCP Relay servers."
    ::= { rsDhcpRelay 2 }

rsDhcpRelayServerEntry OBJECT-TYPE
    SYNTAX      RsDhcpRelayServerEntry
    MAX-ACCESS  not-accessible
    STATUS      current
    DESCRIPTION
        "An entry (conceptual row) representing a DHCP Relay server."
    INDEX      { rsDhcpRelayServerAddress }
    ::= { rsDhcpRelayServerTable 1 }

RsDhcpRelayServerEntry ::= SEQUENCE {
    rsDhcpRelayServerAddress                IpAddress,
    rsDhcpRelayServerRowStatus              RowStatus
}

rsDhcpRelayServerAddress OBJECT-TYPE
    SYNTAX      IpAddress
    MAX-ACCESS  not-accessible
    STATUS      current
    DESCRIPTION
        "The IP address of the DHCP server to which DHCP
        requests received from attached DHCP clients are
        forwarded."
    ::= { rsDhcpRelayServerEntry 1 }

rsDhcpRelayServerRowStatus OBJECT-TYPE
    SYNTAX      RowStatus
    MAX-ACCESS  read-create
    STATUS      current
    DESCRIPTION
        "Supports 'createAndGo' and 'destroy' only."
    ::= { rsDhcpRelayServerEntry 2 }


-- ++++++++++++++++++++++++++++++++++++++++++++++++++++++++++++++++++++++
-- Managed objects for DHCP Proxy
-- ++++++++++++++++++++++++++++++++++++++++++++++++++++++++++++++++++++++

-- No objects defined yet.


-- ++++++++++++++++++++++++++++++++++++++++++++++++++++++++++++++++++++++
-- Notification control objects
-- ++++++++++++++++++++++++++++++++++++++++++++++++++++++++++++++++++++++

-- No notifications are defined in this MIB. Placeholder follows.

-- rsDhcpTrapControl      OBJECT IDENTIFIER ::= { rsDhcpMIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- rsDhcpTraps            OBJECT IDENTIFIER ::= { rsDhcpMIB 3 }
-- rsDhcpTrapPrefix       OBJECT IDENTIFIER ::= { rsDhcpTraps 0 }



-- ++++++++++++++++++++++++++++++++++++++++++++++++++++++++++++++++++++++
-- Conformance information
-- ++++++++++++++++++++++++++++++++++++++++++++++++++++++++++++++++++++++

rsDhcpMIBConformance
             OBJECT IDENTIFIER ::= { rsDhcpMIB 4 }
rsDhcpMIBCompliances
             OBJECT IDENTIFIER ::= { rsDhcpMIBConformance 1 }
rsDhcpMIBGroups
             OBJECT IDENTIFIER ::= { rsDhcpMIBConformance 2 }


-- compliance statements

rsDhcpRelayCompliance MODULE-COMPLIANCE
    STATUS      current
    DESCRIPTION
        "The compliance statement for systems supporting DHCP Relay."
    MODULE  -- this module
    MANDATORY-GROUPS { rsDhcpRelayGroup }
    ::= { rsDhcpMIBCompliances 1 }


-- units of conformance

rsDhcpRelayGroup OBJECT-GROUP
    OBJECTS {
        rsDhcpRelayAgentInfoEnable,

        rsDhcpRelayServerRowStatus
    }
    STATUS      current
    DESCRIPTION
        "The basic collection of objects providing management
        of DHCP Relay functionality."
    ::= { rsDhcpMIBGroups 1 }

END
