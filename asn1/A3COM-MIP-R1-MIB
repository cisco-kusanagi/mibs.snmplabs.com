A3COM-MIP-R1-MIB DEFINITIONS ::= BEGIN

          IMPORTS
                  enterprises, IpAddress
                      FROM RFC1155-SMI
                  OBJECT-TYPE
                          FROM RFC-1212;

--
-- This MIB is for Multicast IP
--

a3Com           OBJECT IDENTIFIER ::= { enterprises 43 }
brouterMIB      OBJECT IDENTIFIER ::= { a3Com 2 }
a3ComMIP    	OBJECT IDENTIFIER ::= { brouterMIB 27 }
a3ComMipSConfig	OBJECT IDENTIFIER ::= { a3ComMIP 1 }
a3ComMipCConfig	OBJECT IDENTIFIER ::= { a3ComMIP 2 }
a3ComMipData	OBJECT IDENTIFIER ::= { a3ComMIP 3 }



      RowStatus ::= INTEGER {
                         active(1),
                         notInService(2),
                         notReady(3),                               
                         createAndGo(4),
                         createAndWait(5),
                         destroy(6)
      }

      --This data type, which has the same semantics as the rowStatus
      --textual convention used in SNMPv2, is used to add and 
      --delete entries from a table.

      --The tables in this MIB allow a subset of the functionality
      --provided by the rowStatus textual convention.  In particular
      --row creation is allowed using only the createAndGo method.

      --That is, when adding entries to this table, this object
      --must be set to createAndGo(4).  The instance identifier
      --for this object will define the values of the columns 
      --that make up the index.  

      --In the same PDU, the appropriate remaining columns
      --of that row must be set as well.  The agent
      --will immediately set the value of this object to
      --active(1) if the row is correct.  If not, the agent
      --will refuse the SET request and return an
      --error code.

      --To modify an existing entry, it must be removed
      --and another entry with the desired changes added. 
                   
      --To remove an entry, set the value of this object
      --to destroy(6).

--
-- The following objects contain parameters applied to the whole system
--

a3ComMipControl	OBJECT-TYPE
    SYNTAX  INTEGER {
    	    	enabled (1),
    	    	disabled (2)
    }
    ACCESS  read-write
    STATUS  mandatory
    DESCRIPTION
    	"If this object is set to enabled(1), then multicast IP routing is in
    	service. If it is set to disabled(2), then multicast IP routing is
    	turned off."
    DEFVAL  { disabled }
    ::= { a3ComMipSConfig 1 }

--
-- The following table contain parameters applied to a specific port or tunnel.
--

a3ComMipPortTable   OBJECT-TYPE
    SYNTAX  SEQUENCE OF A3ComMipPortEntry
    ACCESS  not-accessible
    STATUS  mandatory
    DESCRIPTION
    	"This table contains entries of parameters associated with every port
    	or tunnel."
    ::= { a3ComMipCConfig 1 }

a3ComMipPortEntry   OBJECT-TYPE
    SYNTAX  A3ComMipPortEntry
    ACCESS  not-accessible
    STATUS  mandatory
    DESCRIPTION
    	"Each entry contains information for a spcified port or tunnel."
    INDEX   { a3ComMipPortIndex }
    ::= { a3ComMipPortTable 1 }

A3ComMipPortEntry ::=
    SEQUENCE {
    	a3ComMipPortIndex   	    INTEGER,
    	a3ComMipPortQueryInterval   INTEGER,
    	a3ComMipPortThreshold       INTEGER,
    	a3ComMipPortQuerier	    INTEGER,
    	a3ComMipPortPaceMode	    INTEGER
    }

    a3ComMipPortIndex	OBJECT-TYPE
    	SYNTAX	INTEGER
    	ACCESS	read-only
    	STATUS	mandatory
    	DESCRIPTION
    	    "The port number or tunnel ID of which this entry applies. The
    	    tunnel ID starts with 1025 and end with 1056, i.e. total tunnel
    	    number is limited to 32."
    	::= { a3ComMipPortEntry 1 }

    a3ComMipPortQueryInterval	OBJECT-TYPE
    	SYNTAX	INTEGER (5 .. 5400)
    	ACCESS	read-write
    	STATUS	mandatory
    	DESCRIPTION
    	    "This object specifies the time interval in seconds that a Host
    	    Query message is sent to the attached subnet to request for the
    	    local group membership. It also derives the Membership Expiration
    	    time which is set to two times value of this object plus 20
    	    seconds. This object cannot be applied on tunnel port."
    	DEFVAL	{ 120 }
    	::= { a3ComMipPortEntry 2 }

    a3ComMipPortThreshold   OBJECT-TYPE
    	SYNTAX	INTEGER (1 .. 255)
    	ACCESS	read-write
    	STATUS	mandatory
    	DESCRIPTION
    	    "This object specifies the minimum IP TTL required for a multicast
    	    datagram to be forwarded to the given port or tunnel."
    	DEFVAL	{ 1 }
    	::= { a3ComMipPortEntry 3 }

    a3ComMipPortQuerier	OBJECT-TYPE
    	SYNTAX	INTEGER {
    	    	    yes (1),
    	    	    no (2)
    	}
    	ACCESS	read-only
    	STATUS	mandatory
    	DESCRIPTION
    	    "This object specifies if the system is responsible for sending out
    	    Host Query messages on this port. If the value is yes(1) then the
    	    system is the designated router on the subnet this port connects to
    	    and the system is sending out Host Query messages periodically on
    	    that port. This object must be set to value no(2) for tunnel port."
    	::= { a3ComMipPortEntry 4 }

    a3ComMipPortPaceMode    OBJECT-TYPE
    	SYNTAX	INTEGER {
    	    	    enabled (1),
    	    	    disabled (2)
    	}
    	ACCESS	read-write
    	STATUS	mandatory
    	DESCRIPTION
    	    "This object is used to control PACE mode. If set to enabled(1),
    	    the multicast packets will be sent out with the Universal/Local bit
    	    set, or Priority MAC. If set to disabled(2) the Universal/Local bit
    	    is clear, or Interactive MAC."
    	DEFVAL	{ disabled }
    	::= { a3ComMipPortEntry 5 }

--
-- The following table contains local group information.
--

a3ComMipLocalGroupTable	OBJECT-TYPE
    SYNTAX  SEQUENCE OF A3ComMipLocalGroupEntry
    ACCESS  not-accessible
    STATUS  mandatory
    DESCRIPTION
    	"This table contains group membership information of each attached
    	subnet."
    ::= { a3ComMipCConfig 2 }

a3ComMipLocalGroupEntry	OBJECT-TYPE
    SYNTAX  A3ComMipLocalGroupEntry
    ACCESS  not-accessible
    STATUS  mandatory
    DESCRIPTION
    	"Each entry contains a group membership information associated with
    	a specific port."
    INDEX   { a3ComMipLocalGroupPort, a3ComMipLocalGroupIpAddr }
    ::= { a3ComMipLocalGroupTable 1 }

A3ComMipLocalGroupEntry ::=
    SEQUENCE {
    	a3ComMipLocalGroupPort	    INTEGER,
    	a3ComMipLocalGroupIpAddr    IpAddress,
    	a3ComMipLocalGroupType	    INTEGER,
    	a3ComMipLocalGroupStatus    RowStatus
    }

    a3ComMipLocalGroupPort  OBJECT-TYPE
    	SYNTAX	INTEGER
    	ACCESS	read-only
    	STATUS	mandatory
    	DESCRIPTION
    	    "This object specifies the port number to which this entry applies."
    	::= { a3ComMipLocalGroupEntry 1 }

    a3ComMipLocalGroupIpAddr	OBJECT-TYPE
    	SYNTAX	IpAddress
    	ACCESS	read-only
    	STATUS	mandatory
    	DESCRIPTION
    	    "This object specifies group's address presents on the specified
    	    port. If the port is configured as a tunnel, there will be no group
    	    address associated with it."
    	::= { a3ComMipLocalGroupEntry 2 }

    a3ComMipLocalGroupType  OBJECT-TYPE
    	SYNTAX	INTEGER {
    	    	    static (1),
    	    	    igmp (2)
    	    	}
    	ACCESS	read-only
    	STATUS	mandatory
    	DESCRIPTION
    	    "This object specifies the type of local group. This object can only
    	    be set to 'static' by SET command, and if the local group is learned
    	    from IGMP, it is set to 'igmp'."
    	::= { a3ComMipLocalGroupEntry 3 }

    a3ComMipLocalGroupStatus	OBJECT-TYPE
    	SYNTAX	RowStatus
    	ACCESS	read-write
    	STATUS	mandatory
    	DESCRIPTION
    	    "This object is used to add and delete entries in this table. See
    	    the definition of RowStatus for detail."
    	::= { a3ComMipLocalGroupEntry 4 }

--
-- The following table provides the mapping between IP network addresses and
-- SMDS group address
--

a3ComMipSmdsGroupTable	OBJECT-TYPE
    SYNTAX  SEQUENCE OF A3ComMipSmdsGroupEntry
    ACCESS  not-accessible
    STATUS  mandatory
    DESCRIPTION
    	"This table contains a set of IP network address and SMDS group address
    	mapping."
    ::= { a3ComMipCConfig 3 }

a3ComMipSmdsGroupEntry	OBJECT-TYPE
    SYNTAX  A3ComMipSmdsGroupEntry
    ACCESS  not-accessible
    STATUS  mandatory
    DESCRIPTION
    	"Each entry contains an IP network address to SMDS group address mapping."
    INDEX   { a3ComMipSmdsGroupIpAddr }
    ::= { a3ComMipSmdsGroupTable 1 }

A3ComMipSmdsGroupEntry ::=
    SEQUENCE {
    	a3ComMipSmdsGroupIpAddr	    IpAddress,
    	a3ComMipSmdsGroupMediaAddr  OCTET STRING,
    	a3ComMipSmdsGroupStatus	    RowStatus
    }

    a3ComMipSmdsGroupIpAddr OBJECT-TYPE
    	SYNTAX	IpAddress
    	ACCESS	read-only
    	STATUS	mandatory
    	DESCRIPTION
    	    "This is an IP network address for which there is a corresponding
    	    SMDS group address."
    	::= { a3ComMipSmdsGroupEntry 1 }

    a3ComMipSmdsGroupMediaAddr	OBJECT-TYPE
    	SYNTAX	OCTET STRING ( SIZE(8) )
    	ACCESS	read-write
    	STATUS	mandatory
    	DESCRIPTION
    	    "This is the SMDS group address that corresponds to the IP network
    	    address identified by a3ComMipSmdsGroupIpAddr."
    	::= { a3ComMipSmdsGroupEntry 2 }

    a3ComMipSmdsGroupStatus OBJECT-TYPE
    	SYNTAX	RowStatus
    	ACCESS	read-write
    	STATUS	mandatory
    	DESCRIPTION
    	    "This object is used to add and delete entries in this table. See
    	    the definition of RowStatus for detail."
    	::= { a3ComMipSmdsGroupEntry 3 }

END
