Wellfleet-VRRP-MIB DEFINITIONS ::= BEGIN

    IMPORTS

      IpAddress, Counter             FROM RFC1155-SMI
      OBJECT-TYPE                    FROM RFC-1212
      PhysAddress                    FROM RFC1213-MIB
      wfVrrpGroup                    FROM Wellfleet-COMMON-MIB;
 
    wfVrrpAdminTable OBJECT-TYPE
        SYNTAX   SEQUENCE OF WfVrrpAdminEntry
        ACCESS   not-accessible
        STATUS   mandatory
        DESCRIPTION
            "Configuration information."
        ::= { wfVrrpGroup 1 }

    wfVrrpAdminEntry OBJECT-TYPE
        SYNTAX  WfVrrpAdminEntry
        ACCESS  not-accessible
        STATUS  mandatory
        DESCRIPTION
            " VRRP the operational characteristics of a virtual router."
        INDEX    { wfVrrpAdminPrimaryIpAddr, wfVrrpAdminVrId }
        ::= { wfVrrpAdminTable 1 }

    WfVrrpAdminEntry ::=
        SEQUENCE {
            wfVrrpAdminDelete
                INTEGER,
            wfVrrpAdminDisable
                INTEGER,
            wfVrrpAdminState
                INTEGER,
            wfVrrpAdminPrimaryIpAddr
                IpAddress,
            wfVrrpAdminVrId
                INTEGER,
            wfVrrpAdminIpAddr
                IpAddress,
            wfVrrpAdminVirtualMacAddr
                PhysAddress,
            wfVrrpAdminPriority
                INTEGER,
            wfVrrpAdminAdvertisementInterval
                INTEGER,
            wfVrrpAdminCriticalIpInterface
                IpAddress,
            wfVrrpAdminIPXBackup
                INTEGER,
            wfVrrpAdminIGMPBackup
                INTEGER,
            wfVrrpAdminTokenRingAddress
                OCTET STRING,
            wfVrrpAdminPreemptMode
                INTEGER,
            wfVrrpAdminMasterPingEnable
                INTEGER
    }
    wfVrrpAdminDelete OBJECT-TYPE
        SYNTAX  INTEGER {
                    created(1),
                    deleted(2)
                }
        ACCESS  read-write
        STATUS  mandatory
        DESCRIPTION
                "Delete/Create parameter."
        DEFVAL  { created }
        ::= { wfVrrpAdminEntry 1 }

    wfVrrpAdminDisable OBJECT-TYPE
        SYNTAX  INTEGER {
                    enabled(1),
                    disabled(2)
                }
        ACCESS  read-write
        STATUS  mandatory
        DESCRIPTION
                "Enable/Disable parameter."
        DEFVAL  { enabled }
        ::= { wfVrrpAdminEntry 2 }

    wfVrrpAdminState OBJECT-TYPE
        SYNTAX   INTEGER {
            initialize(1),  -- Waiting for a startup event
            backup(2),      -- Monitoring the Master
            master(3),      -- Forwarding for its IP addresses
            down(4)
        } 
        ACCESS   read-only
        STATUS   mandatory
        DESCRIPTION
            "The current state of the VRRP router with respect
             to this virtual router."
        DEFVAL         { initialize }
        ::= { wfVrrpAdminEntry 3 }

    wfVrrpAdminPrimaryIpAddr OBJECT-TYPE
        SYNTAX   IpAddress
        ACCESS   read-only
        STATUS   mandatory
        DESCRIPTION
            "The master router's real (primary) IP address. This is
            the IP address listed as the source in VRRP advertisements
            received by this virtual router."
        ::= { wfVrrpAdminEntry 4 }

    wfVrrpAdminVrId OBJECT-TYPE
        SYNTAX   INTEGER (1..255)
        ACCESS   read-only
        STATUS   mandatory
        DESCRIPTION
            "This object contains the Virtual Router Identifier (VRID).
             In addition to being part of the index for this table, it
             is used to calculate the MAC address."
        ::= { wfVrrpAdminEntry 5 }

    wfVrrpAdminIpAddr OBJECT-TYPE
        SYNTAX   IpAddress
        ACCESS   read-write
        STATUS   mandatory
        DESCRIPTION
            "The IP address that is associated with this virtual router."
        ::= { wfVrrpAdminEntry 6 }

    wfVrrpAdminVirtualMacAddr OBJECT-TYPE
        SYNTAX   PhysAddress
        ACCESS   read-only
        STATUS   mandatory
        DESCRIPTION
            "The virtual MAC address of the virtual router. This is derived
            as follows: 00-00-5E-00-01-<VRID>.
            Where the first three octets consist of the IANA's OUI, the
            next two octets indicate the address block of the VRRP protocol,
            and the remaining octets consist of the VRID.
            Although this object can be derived from the 'wfVrrpAdminVrId'
            object, it is included here, for completeness."
        ::= { wfVrrpAdminEntry 7 }

    wfVrrpAdminPriority OBJECT-TYPE
        SYNTAX   INTEGER (1..255)
        ACCESS   read-write
        STATUS   mandatory
        DESCRIPTION
            "This object specifies the priority for the virtual 
            router with respect to other virtual routers that are
            backing up a set of IP addresses. Higher values imply
            higher priority. 
            A priority of 255 is used for the router that owns the
            associated IP address(es), i.e., is backing up IP
            addresses which are primary."
        DEFVAL       { 100 }
        ::= { wfVrrpAdminEntry 8 }

    wfVrrpAdminAdvertisementInterval OBJECT-TYPE
        SYNTAX   INTEGER (1..255)
        ACCESS   read-write
        STATUS   mandatory
        DESCRIPTION
            "This is the time interval, in seconds, between sending 
            advertisement. Only the Master sends VRRP advertisements."
        DEFVAL       { 1 }
        ::= { wfVrrpAdminEntry 9 }

    wfVrrpAdminCriticalIpInterface OBJECT-TYPE
        SYNTAX   IpAddress
        ACCESS   read-write
        STATUS   mandatory
        DESCRIPTION
            "The IP address of an interface on the Router that will
            cauase the shutdown event."
        ::= { wfVrrpAdminEntry 10 }

    wfVrrpAdminIPXBackup OBJECT-TYPE
        SYNTAX  INTEGER {
                    enabled(1),
                    disabled(2)
                }
        ACCESS  read-write
        STATUS  mandatory
        DESCRIPTION
                "Enable/Disable IPX backup."
        DEFVAL  { disabled }
        ::= { wfVrrpAdminEntry 11 }

    wfVrrpAdminIGMPBackup OBJECT-TYPE
        SYNTAX  INTEGER {
                    enabled(1),
                    disabled(2)
                }
        ACCESS  read-write
        STATUS  mandatory
        DESCRIPTION
                "Enable/Disable IGMP backup."
        DEFVAL  { disabled }
        ::= { wfVrrpAdminEntry 12 }

    wfVrrpAdminTokenRingAddress OBJECT-TYPE
        SYNTAX  OCTET STRING
        ACCESS  read-write
        STATUS  mandatory
        DESCRIPTION
                "Source MAC Address for VRRP when running over Token Ring."
        ::= { wfVrrpAdminEntry 13 }

    wfVrrpAdminPreemptMode OBJECT-TYPE
        SYNTAX  INTEGER {
                    enabled(1),
                    disabled(2)
                }
        ACCESS  read-write
        STATUS  mandatory
        DESCRIPTION
                "Preempt Mode."
        DEFVAL  { enabled }
        ::= { wfVrrpAdminEntry 14 }

    wfVrrpAdminMasterPingEnable OBJECT-TYPE
        SYNTAX  INTEGER {
                    enabled(1),
                    disabled(2)
                }
        ACCESS  read-write
        STATUS  mandatory
        DESCRIPTION
                "a VRRP router is called Owner if it has the virtual
                 IP address configured as one of its real interface 
                 address(es). According to the RFC 2338, if the Master
                 is not the Owner of the virtual IP address, it must 
                 not accept packets addressed to the virtual IP address.
                 This mib is added to make the virtual IP address
                 pingable even if the Master is not the Owner.It
                 defines whether Non-Owner Master responds to the 
                 virtual IP address ping or not."
        DEFVAL  { disabled }
        ::= { wfVrrpAdminEntry 15 }

    wfVrrpRouterStatsTable OBJECT-TYPE
        SYNTAX   SEQUENCE OF WfVrrpRouterStatsEntry
        ACCESS   not-accessible
        STATUS   mandatory
        DESCRIPTION
            "Table of virtual router statistics."
        ::= { wfVrrpGroup 2 }

    wfVrrpRouterStatsEntry OBJECT-TYPE
        SYNTAX   WfVrrpRouterStatsEntry
        ACCESS   not-accessible
        STATUS   mandatory
        DESCRIPTION
            "An entry in the table, containing statistics information
            about a given virtual router."
        INDEX    { wfVrrpStatsPrimaryIpAddr, wfVrrpStatsVrId }
        ::= { wfVrrpRouterStatsTable 1 }

    WfVrrpRouterStatsEntry ::=
        SEQUENCE {
            wfVrrpStatsPrimaryIpAddr
                IpAddress,
            wfVrrpStatsVrId
                INTEGER,
            wfVrrpStatsMasterTransitions
                Counter,
            wfVrrpStatsInAdvertisements
                Counter,
            wfVrrpStatsChecksumErrors
                Counter,
            wfVrrpStatsVersionErrors
                Counter,
            wfVrrpStatsVrIdErrors
                Counter,
            wfVrrpStatsAdvertiseIntervalErrors
                Counter,
            wfVrrpStatsIpTtlErrors
                Counter,
            wfVrrpStatsInPriorityZeroAdvertisements
                Counter,
            wfVrrpStatsOutPriorityZeroAdvertisements
                Counter,
            wfVrrpStatsInInvalidTypeAdvertisements
                Counter,
            wfVrrpStatsUnknownTypeAdvertisements
                Counter
    }

    wfVrrpStatsPrimaryIpAddr OBJECT-TYPE
        SYNTAX   IpAddress
        ACCESS   read-only
        STATUS   mandatory
        DESCRIPTION
            "The master router's real (primary) IP address. This is
            the IP address listed as the source in VRRP advertisements
            received by this virtual router."
        ::= { wfVrrpRouterStatsEntry 1 }

    wfVrrpStatsVrId OBJECT-TYPE
        SYNTAX   INTEGER (1..255)
        ACCESS   read-only
        STATUS   mandatory
        DESCRIPTION
            "This object contains the Virtual Router Identifier (VRID).
             In addition to being part of the index for this table, it
             is used to calculate the MAC address."
        ::= { wfVrrpRouterStatsEntry 2 }

    wfVrrpStatsMasterTransitions OBJECT-TYPE
        SYNTAX   Counter
        ACCESS   read-only
        STATUS   mandatory
        DESCRIPTION
            "The total number of times that this virtual router's state
            has transitioned from BACKUP to MASTER."
        ::= { wfVrrpRouterStatsEntry 3 }

    wfVrrpStatsInAdvertisements OBJECT-TYPE
        SYNTAX   Counter
        ACCESS   read-only

        STATUS   mandatory
        DESCRIPTION
            "The total number of VRRP advertisements received by this
            virtual router."
        ::= { wfVrrpRouterStatsEntry 4 }

    wfVrrpStatsChecksumErrors OBJECT-TYPE
        SYNTAX   Counter
        ACCESS   read-only
        STATUS   mandatory
        DESCRIPTION
            "The total number of VRRP packets received with an invalid
            checksum value."
        ::= { wfVrrpRouterStatsEntry 5 }

    wfVrrpStatsVersionErrors OBJECT-TYPE
        SYNTAX   Counter
        ACCESS   read-only
        STATUS   mandatory
        DESCRIPTION
            "The total number of VRRP packets received with an invalid 
            version number."
        ::= { wfVrrpRouterStatsEntry 6 }

    wfVrrpStatsVrIdErrors OBJECT-TYPE
        SYNTAX   Counter
        ACCESS   read-only
        STATUS   mandatory
        DESCRIPTION
            "The total number of VRRP packets received with an invalid
            VRID for this virtual router."
        ::= { wfVrrpRouterStatsEntry 7 }

    wfVrrpStatsAdvertiseIntervalErrors OBJECT-TYPE
        SYNTAX   Counter
        ACCESS   read-only
        STATUS   mandatory
        DESCRIPTION
            "The total number of VRRP advertisement packets received
            for which the advertisement interval is different than the
            one configured for the local virtual router."
        ::= { wfVrrpRouterStatsEntry 8 }

    wfVrrpStatsIpTtlErrors OBJECT-TYPE
        SYNTAX   Counter
        ACCESS   read-only
        STATUS   mandatory
        DESCRIPTION
            "The total number of VRRP packets received by the router
            with IP TTL (Time-To-Live) not equal to 255."
        ::= { wfVrrpRouterStatsEntry 9 }

    wfVrrpStatsInPriorityZeroAdvertisements OBJECT-TYPE
        SYNTAX   Counter
        ACCESS   read-only
        STATUS   mandatory
        DESCRIPTION
            "The total number of VRRP packets received by the virtual 
            router with a priority of '0'."
        ::= { wfVrrpRouterStatsEntry 10 }

    wfVrrpStatsOutPriorityZeroAdvertisements OBJECT-TYPE
        SYNTAX   Counter
        ACCESS   read-only
        STATUS   mandatory
        DESCRIPTION
            "The total number of VRRP packets sent by the virtual router
            with a priority of '0'."
        ::= { wfVrrpRouterStatsEntry 11 }

    wfVrrpStatsInInvalidTypeAdvertisements OBJECT-TYPE
        SYNTAX   Counter
        ACCESS   read-only
        STATUS   mandatory
        DESCRIPTION
            "The total number of VRRP packets received by the virtual   
            router with an invalid value in the 'type' field."
        ::= { wfVrrpRouterStatsEntry 12 }

    wfVrrpStatsUnknownTypeAdvertisements OBJECT-TYPE
        SYNTAX   Counter
        ACCESS   read-only
        STATUS   mandatory
        DESCRIPTION
            "The total number of VRRP packets received by the router
            with an invalid value in the VRRP type field."
        ::= { wfVrrpRouterStatsEntry 13 }

    END -- Wellfleet-VRRP-MIB
