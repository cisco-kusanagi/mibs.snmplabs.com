Wellfleet-RARP-MIB DEFINITIONS ::= BEGIN

-- Created by mdl2asn version 3.1
-- Creation date: Wed Aug 30 16:46:46 EDT 1995


    IMPORTS

      IpAddress, Counter
        FROM RFC1155-SMI
      OBJECT-TYPE
        FROM RFC-1212
      wfRarpGroup
        FROM Wellfleet-COMMON-MIB;


    wfRarp		OBJECT IDENTIFIER ::= { wfRarpGroup 1 }

    wfRarpDelete OBJECT-TYPE
        SYNTAX	INTEGER {
    		    created(1),
    		    deleted(2)
    		}
        ACCESS	read-write
        STATUS	mandatory
        DESCRIPTION
                "Create/Delete parameter. Default is created.
                Users perform a set operation on this
                object in order to create/delete RARP."
        DEFVAL	{ created }
        ::= { wfRarp 1 }

    wfRarpDisable OBJECT-TYPE
        SYNTAX	INTEGER {
    		    enabled(1),
    		    disabled(2)
    		}
        ACCESS	read-write
        STATUS	mandatory
        DESCRIPTION
                "Enable/Disable Parameter indicates whether
                this RARP record is enabled or disabled."
        DEFVAL	{ enabled }
        ::= { wfRarp 2 }

    wfRarpNumNoMatches OBJECT-TYPE
        SYNTAX	Counter
        ACCESS	read-only
        STATUS	mandatory
        DESCRIPTION
                "The number of RARP Requests dropped that failed Table Look UP"
        ::= { wfRarp 3 }

    wfRarpMapTable OBJECT-TYPE
        SYNTAX	SEQUENCE OF WfRarpMapEntry
        ACCESS	not-accessible
        STATUS	mandatory
        DESCRIPTION
                "List of configured RARP MAP Table entries"
        ::= { wfRarpGroup 2 }

    wfRarpMapEntry OBJECT-TYPE
        SYNTAX	WfRarpMapEntry
        ACCESS	not-accessible
        STATUS	mandatory
        DESCRIPTION
                "A description of an RARP map"
        INDEX	{ wfRarpMapMadr }
        ::= { wfRarpMapTable 1 }

    WfRarpMapEntry ::= SEQUENCE {
    	    wfRarpMapDelete
    		INTEGER,
    	    wfRarpMapMadr
    		OCTET STRING,
    	    wfRarpMapIpAddr
    		IpAddress
        }

    wfRarpMapDelete OBJECT-TYPE
        SYNTAX	INTEGER {
    		    created(1),
    		    deleted(2)
    		}
        ACCESS	read-write
        STATUS	mandatory
        DESCRIPTION
                "Indicates whether this RARP Map record is to be deleted or created"
        DEFVAL	{ created }
        ::= { wfRarpMapEntry 1 }

    wfRarpMapMadr OBJECT-TYPE
        SYNTAX	OCTET STRING (SIZE (6))
        ACCESS	read-only
        STATUS	mandatory
        DESCRIPTION
                "Mac Address in RARP Request pkts"
        ::= { wfRarpMapEntry 2 }

    wfRarpMapIpAddr OBJECT-TYPE
        SYNTAX	IpAddress
        ACCESS	read-write
        STATUS	mandatory
        DESCRIPTION
                "IP Address of Requesting Station"
        ::= { wfRarpMapEntry 3 }

    wfRarpIntfTable OBJECT-TYPE
        SYNTAX	SEQUENCE OF WfRarpIntfEntry
        ACCESS	not-accessible
        STATUS	mandatory
        DESCRIPTION
                "List of configured RARP interfaces"
        ::= { wfRarpGroup 3 }

    wfRarpIntfEntry OBJECT-TYPE
        SYNTAX	WfRarpIntfEntry
        ACCESS	not-accessible
        STATUS	mandatory
        DESCRIPTION
                "A description of an RARP interface"
        INDEX	{ wfRarpIntfCctno }
        ::= { wfRarpIntfTable 1 }

    WfRarpIntfEntry ::= SEQUENCE {
    	    wfRarpIntfDelete
    		INTEGER,
    	    wfRarpIntfDisable
    		INTEGER,
    	    wfRarpIntfCctno
    		INTEGER,
    	    wfRarpIntfIpAddr
    		IpAddress
        }

    wfRarpIntfDelete OBJECT-TYPE
        SYNTAX	INTEGER {
    		    created(1),
    		    deleted(2)
    		}
        ACCESS	read-write
        STATUS	mandatory
        DESCRIPTION
                "Indicates whether this RARP intf record is to be deleted or created"
        DEFVAL	{ created }
        ::= { wfRarpIntfEntry 1 }

    wfRarpIntfDisable OBJECT-TYPE
        SYNTAX	INTEGER {
    		    enabled(1),
    		    disabled(2)
    		}
        ACCESS	read-write
        STATUS	mandatory
        DESCRIPTION
                "Indicates whether this RARP intf record is to be enabled or disabled"
        DEFVAL	{ enabled }
        ::= { wfRarpIntfEntry 2 }

    wfRarpIntfCctno OBJECT-TYPE
        SYNTAX	INTEGER
        ACCESS	read-only
        STATUS	mandatory
        DESCRIPTION
                "Which Circuit rarp should run on"
        ::= { wfRarpIntfEntry 3 }

    wfRarpIntfIpAddr OBJECT-TYPE
        SYNTAX	IpAddress
        ACCESS	read-write
        STATUS	mandatory
        DESCRIPTION
                "RARP Server's IP Address on this circuit"
        ::= { wfRarpIntfEntry 4 }

    END  -- Wellfleet-RARP-MIB
