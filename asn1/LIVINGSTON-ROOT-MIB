--++++++++++++++++++++++++++++++++++++++++++++++++++++++++++++++++++++++++++++++++++
-- Lucent PortMaster 4 Root MIB
-- ++++++++++++++++++++++++++++++++++++++++++++++++++++++++++++++++++++++++++++++++++
LIVINGSTON-ROOT-MIB DEFINITIONS ::= BEGIN

IMPORTS
	enterprises
		FROM RFC1155-SMI;

lucent      OBJECT IDENTIFIER ::= { enterprises 307 }
product 	OBJECT IDENTIFIER ::= { lucent 1 }

-- Lucent PortMaster MIB
lucentPMProduct 	OBJECT IDENTIFIER ::= { product 1 }
lucentPMMib		OBJECT IDENTIFIER ::= { product 2 }
lucentPM3		OBJECT IDENTIFIER ::= { lucentPMProduct 1 }
lucentPM4		OBJECT IDENTIFIER ::= { lucentPMProduct 2 }

END

-- ++++++++++++++++++++++++++++++++++++++++++++++++++++++++++++++++++
-- Lucent (RABU) Generic Global Configuration MIB at a glance
-- ++++++++++++++++++++++++++++++++++++++++++++++++++++++++++++++++++
-- pmglobal.mib	Rev. 1.0
-- Copyright 1998 Lucent Technologies
--
--	lucent
--		products
--			lucentPMProducts
--				lucentPM3
--				lucentPM4
--			lucentPMMib
--				lucentPMGlobal
--					lucentPMGenGlobParams
--						lucentPMGenPriNameSrvr
--						lucentPMGenAltNameSrvr
--						lucentPMGenSyslogHost
--						lucentPMGenAssignedAddr
--						lucentPMGenReportedAddr
--						lucentPMGenNetMask
--						lucentPMGenNameSvc
--						lucentPMGenDomainName
--						lucentPMGenTelnetPortNum
--						lucentPMGenMaxConsConn
--						lucentPMGenOSPF
--						lucentPMGenBGP
--						lucentPMGenIPX
--						lucentPMGenNetBIOS
--						lucentPMGenCallCheck
--					lucentPMRadiusMgmt
--						lucentPMRadiusIP
--						lucentPMRadiusAltIP
--						lucentPMRadiusAcctIP
--						lucentPMRadiusAcctAltIP
--						lucentPMRadiusPriPort
--						lucentPMRadiusAltPort
--						lucentPMRadiusAcctPriPort
--						lucentPMRadiusAcctAltPort
--						lucentPMRadiusAuthFails
--						lucentPMRadiusRetrans
--						lucentPMRadiusTimeout
--						lucentPMRadiusAuth
--						lucentPMRadiusSecret
--					lucentPMChoiceNetMgmt
--						lucentPMChoiceNetPriIP
--						lucentPMChoiceNetAltIP
--						lucentPMChoiceNetPriPort
--						lucentPMChoiceNetAltPort
--						lucentPMChoiceNetSecret
--
-- Modification History
-- --------------------
--
-- Pavan Kumar	11/06/98	Initial Creation
--
-- ++++++++++++++++++++++++++++++++++++++++++++++++++++++++++++++++++
