Wellfleet-ST2-MIB DEFINITIONS ::= BEGIN

-- Created by mdl2asn version 3.1
-- Creation date: Wed Aug 30 16:48:03 EDT 1995


    IMPORTS

      IpAddress, Counter
        FROM RFC1155-SMI
      OBJECT-TYPE
        FROM RFC-1212
      DisplayString
        FROM RFC1213-MIB
      wfReservationProtocolGroup 
        FROM Wellfleet-COMMON-MIB;


    wfSt2Group      OBJECT IDENTIFIER ::= { wfReservationProtocolGroup 2 }
    wfSt2BaseGroup	OBJECT IDENTIFIER ::= { wfSt2Group 1 }


    wfSt2BaseDelete OBJECT-TYPE
        SYNTAX	INTEGER {
    		    create(1),
    		    delete(2)
    		}
        ACCESS	read-write
        STATUS	mandatory
        DESCRIPTION
                "This value determines whether ST2 is configured on this slot."
        DEFVAL	{ create }
        ::= { wfSt2BaseGroup 1 }

    wfSt2BaseDisable OBJECT-TYPE
        SYNTAX	INTEGER {
    		    enable(1),
    		    disable(2)
    		}
        ACCESS	read-write
        STATUS	mandatory
        DESCRIPTION
                "This value determines whether ST2 is to startup."
        DEFVAL	{ enable }
        ::= { wfSt2BaseGroup 2 }

    wfSt2BaseState OBJECT-TYPE
        SYNTAX	INTEGER {
    		    notpresent(4),
    		    initializing(3),
    		    down(2),
    		    up(1)
    		}
        ACCESS	read-only
        STATUS	mandatory
        DESCRIPTION
                "This value records the current state of ST2."
        DEFVAL	{ notpresent }
        ::= { wfSt2BaseGroup 3 }

    wfSt2BaseRoutingVers OBJECT-TYPE
        SYNTAX	DisplayString
        ACCESS	read-only
        STATUS	mandatory
        DESCRIPTION
                "'This read-only parameter identifies the executor node's
                Routing version number. The format is the same as for the
                Network Management version number.'"
        ::= { wfSt2BaseGroup 4 }

    wfSt2BaseTunnelCapability OBJECT-TYPE
        SYNTAX	INTEGER {
    		    yes(1),
    		    no(2)
    		}
        ACCESS	read-write
        STATUS	mandatory
        DESCRIPTION
                "This is the tunnelling capability flag for the router."
        DEFVAL	{ no }
        ::= { wfSt2BaseGroup 5 }

    wfSt2BaseTunnelDisable OBJECT-TYPE
        SYNTAX	INTEGER {
    		    enable(1),
    		    disable(2)
    		}
        ACCESS	read-write
        STATUS	mandatory
        DESCRIPTION
                "This is the tunnelling enabled flag for the router."
        DEFVAL	{ disable }
        ::= { wfSt2BaseGroup 6 }

    wfSt2BaseAgentDBGMask OBJECT-TYPE
        SYNTAX	INTEGER
        ACCESS	read-write
        STATUS	mandatory
        DESCRIPTION
                "This is the ST2 base agent debug mask."
        ::= { wfSt2BaseGroup 7 }

    wfSt2BaseReservedParameter1 OBJECT-TYPE
        SYNTAX	INTEGER
        ACCESS	read-write
        STATUS	mandatory
        DESCRIPTION
                "This is the ST2 base reserved parameter."
        ::= { wfSt2BaseGroup 8 }

    wfSt2BaseReservedParameter2 OBJECT-TYPE
        SYNTAX	INTEGER
        ACCESS	read-write
        STATUS	mandatory
        DESCRIPTION
                "This is the ST2 base reserved parameter."
        ::= { wfSt2BaseGroup 9 }

    wfSt2CircuitTable OBJECT-TYPE
        SYNTAX	SEQUENCE OF WfSt2CircuitEntry
        ACCESS	not-accessible
        STATUS	mandatory
        DESCRIPTION
                "' Table of ST2 Circuit Configuration and Counter Records'"
        ::= { wfSt2Group 2 }

    wfSt2CircuitEntry OBJECT-TYPE
        SYNTAX	WfSt2CircuitEntry
        ACCESS	not-accessible
        STATUS	mandatory
        DESCRIPTION
                "'Parameters information about all circuits currently known.
                NOTE: depending on the type of object being querried (e.g., a
                level 1 vs. a level 2 router or end system) some variables may
                not be present.'"
        INDEX	{ wfSt2CircuitID }
        ::= { wfSt2CircuitTable 1 }

    WfSt2CircuitEntry ::= SEQUENCE {
    	    wfSt2CircuitDelete
    		INTEGER,
    	    wfSt2CircuitDisable
    		INTEGER,
    	    wfSt2CircuitCommonState
    		INTEGER,
    	    wfSt2CircuitID
    		INTEGER,
    	    wfSt2CircuitCommonType
    		INTEGER,
    	    wfSt2CircuitIPAddress
    		IpAddress,
    	    wfSt2CircuitTmoAccept
    		INTEGER,
    	    wfSt2CircuitRetryAccept
    		INTEGER,
    	    wfSt2CircuitTmoConnect
    		INTEGER,
    	    wfSt2CircuitRetryConnect
    		INTEGER,
    	    wfSt2CircuitTmoDisconnect
    		INTEGER,
    	    wfSt2CircuitRetryDisconnect
    		INTEGER,
    	    wfSt2CircuitTmoHidChange
    		INTEGER,
    	    wfSt2CircuitRetryHidChange
    		INTEGER,
    	    wfSt2CircuitTmoRefuse
    		INTEGER,
    	    wfSt2CircuitRetryRefuse
    		INTEGER,
    	    wfSt2CircuitTmoHello
    		INTEGER,
    	    wfSt2CircuitRetryHello
    		INTEGER,
    	    wfSt2CircuitMTU
    		INTEGER,
    	    wfSt2CircuitDBGMask
    		INTEGER,
    	    wfSt2CircuitHelloFailure
    		INTEGER,
    	    wfSt2CircuitHidProposed
    		INTEGER,
    	    wfSt2CircuitBadStCksum
    		Counter,
    	    wfSt2CircuitEncodeBadParm
    		Counter,
    	    wfSt2CircuitEncodeWrongParms
    		Counter,
    	    wfSt2CircuitMsgInHidColl
    		Counter,
    	    wfSt2CircuitMsgInNoCon
    		Counter,
    	    wfSt2CircuitNotSt2
    		Counter,
    	    wfSt2CircuitParmMissing
    		Counter,
    	    wfSt2CircuitScmpRefNum
    		Counter,
    	    wfSt2CircuitScmp0rVlid
    		Counter,
    	    wfSt2CircuitScmp0sVlid
    		Counter,
    	    wfSt2CircuitScmpBadVlid
    		Counter,
    	    wfSt2CircuitScmpCksum
    		Counter,
    	    wfSt2CircuitScmpFailedResources
    		Counter,
    	    wfSt2CircuitScmpFailedRoute
    		Counter,
    	    wfSt2CircuitScmpLenInconsist
    		Counter,
    	    wfSt2CircuitScmpRxTimeOut
    		Counter,
    	    wfSt2CircuitScmpXmtCnt
    		Counter,
    	    wfSt2CircuitScmpRcvCnt
    		Counter,
    	    wfSt2CircuitDataXmtCnt
    		Counter,
    	    wfSt2CircuitDataRcvCnt
    		Counter,
    	    wfSt2CircuitSt2StreamCnt
    		Counter,
    	    wfSt2CircuitHelloXmtCnt
    		Counter,
    	    wfSt2CircuitHelloRcvCnt
    		Counter,
    	    wfSt2CircuitHelloRAckCnt
    		Counter,
    	    wfSt2CircuitLbPoliceDrop
    		Counter,
    	    wfSt2CircuitPbsDropCnt
    		Counter,
    	    wfSt2CircuitOverDrop2Cnt
    		Counter,
    	    wfSt2CircuitPktCnt
    		Counter,
    	    wfSt2CircuitScmpXmt
    		Counter,
    	    wfSt2CircuitScmpRcv
    		Counter,
    	    wfSt2CircuitBWAlloc
    		Counter,
    	    wfSt2CircuitRsvdParameter1
    		INTEGER,
    	    wfSt2CircuitRsvdParameter2
    		INTEGER
        }

    wfSt2CircuitDelete OBJECT-TYPE
        SYNTAX	INTEGER {
    		    create(1),
    		    delete(2)
    		}
        ACCESS	read-write
        STATUS	mandatory
        DESCRIPTION
                "This value determines whether the circuit is configured"
        DEFVAL	{ create }
        ::= { wfSt2CircuitEntry 1 }

    wfSt2CircuitDisable OBJECT-TYPE
        SYNTAX	INTEGER {
    		    enable(1),
    		    disable(2)
    		}
        ACCESS	read-write
        STATUS	mandatory
        DESCRIPTION
                "'This value represents the circuit's Network Management
                operational state. NOTE: These values are incremented by one
                compared to the standard St2 values in order to maintain
                compliance with RFC 1155.'"
        DEFVAL	{ enable }
        ::= { wfSt2CircuitEntry 2 }

    wfSt2CircuitCommonState OBJECT-TYPE
        SYNTAX	INTEGER {
    		    notpresent(4),
    		    initializing(3),
    		    down(2),
    		    up(1)
    		}
        ACCESS	read-only
        STATUS	mandatory
        DESCRIPTION
                "This value represents the circuit's operational state."
        DEFVAL	{ down }
        ::= { wfSt2CircuitEntry 3 }

    wfSt2CircuitID OBJECT-TYPE
        SYNTAX	INTEGER
        ACCESS	read-only
        STATUS	mandatory
        DESCRIPTION
                "A unique value for each known circuit."
        ::= { wfSt2CircuitEntry 4 }

    wfSt2CircuitCommonType OBJECT-TYPE
        SYNTAX	INTEGER {
    		    sync(1),
    		    ethernet(6),
    		    fddi(15),
    		    smds(100),
    		    fr(101),
    		    atm(102),
    		    ring(103),
    		    ppp(104)
    		}
        ACCESS	read-only
        STATUS	mandatory
        DESCRIPTION
                "'Represents the type of the circuit.'"
        ::= { wfSt2CircuitEntry 5 }

    wfSt2CircuitIPAddress OBJECT-TYPE
        SYNTAX	IpAddress
        ACCESS	read-write
        STATUS	mandatory
        DESCRIPTION
                "Network Interface IP address of this ST2 circuit"
        ::= { wfSt2CircuitEntry 6 }

    wfSt2CircuitTmoAccept OBJECT-TYPE
        SYNTAX	INTEGER {
    		    taccdef(10)
    		}
        ACCESS	read-write
        STATUS	mandatory
        DESCRIPTION
                "Transmit accept ..."
        DEFVAL	{ taccdef }
        ::= { wfSt2CircuitEntry 7 }

    wfSt2CircuitRetryAccept OBJECT-TYPE
        SYNTAX	INTEGER {
    		    raccdef(3)
    		}
        ACCESS	read-write
        STATUS	mandatory
        DESCRIPTION
                "Receive accept ..."
        DEFVAL	{ raccdef }
        ::= { wfSt2CircuitEntry 8 }

    wfSt2CircuitTmoConnect OBJECT-TYPE
        SYNTAX	INTEGER {
    		    tcondef(10)
    		}
        ACCESS	read-write
        STATUS	mandatory
        DESCRIPTION
                "Transmit connect ..."
        DEFVAL	{ tcondef }
        ::= { wfSt2CircuitEntry 9 }

    wfSt2CircuitRetryConnect OBJECT-TYPE
        SYNTAX	INTEGER {
    		    rcondef(5)
    		}
        ACCESS	read-write
        STATUS	mandatory
        DESCRIPTION
                "Receive connect ..."
        DEFVAL	{ rcondef }
        ::= { wfSt2CircuitEntry 10 }

    wfSt2CircuitTmoDisconnect OBJECT-TYPE
        SYNTAX	INTEGER {
    		    tdiscondef(10)
    		}
        ACCESS	read-write
        STATUS	mandatory
        DESCRIPTION
                "Transmit disconnect ..."
        DEFVAL	{ tdiscondef }
        ::= { wfSt2CircuitEntry 11 }

    wfSt2CircuitRetryDisconnect OBJECT-TYPE
        SYNTAX	INTEGER {
    		    rdiscondef(3)
    		}
        ACCESS	read-write
        STATUS	mandatory
        DESCRIPTION
                "Receive disconnect ..."
        DEFVAL	{ rdiscondef }
        ::= { wfSt2CircuitEntry 12 }

    wfSt2CircuitTmoHidChange OBJECT-TYPE
        SYNTAX	INTEGER {
    		    thidchgdef(10)
    		}
        ACCESS	read-write
        STATUS	mandatory
        DESCRIPTION
                "Transmit hid change ..."
        DEFVAL	{ thidchgdef }
        ::= { wfSt2CircuitEntry 13 }

    wfSt2CircuitRetryHidChange OBJECT-TYPE
        SYNTAX	INTEGER {
    		    rhidchgdef(3)
    		}
        ACCESS	read-write
        STATUS	mandatory
        DESCRIPTION
                "Receive Hid Change ..."
        DEFVAL	{ rhidchgdef }
        ::= { wfSt2CircuitEntry 14 }

    wfSt2CircuitTmoRefuse OBJECT-TYPE
        SYNTAX	INTEGER {
    		    trefusedef(10)
    		}
        ACCESS	read-write
        STATUS	mandatory
        DESCRIPTION
                "Transmit refuse ..."
        DEFVAL	{ trefusedef }
        ::= { wfSt2CircuitEntry 15 }

    wfSt2CircuitRetryRefuse OBJECT-TYPE
        SYNTAX	INTEGER {
    		    rrefusedef(3)
    		}
        ACCESS	read-write
        STATUS	mandatory
        DESCRIPTION
                "Receive refuse ..."
        DEFVAL	{ rrefusedef }
        ::= { wfSt2CircuitEntry 16 }

    wfSt2CircuitTmoHello OBJECT-TYPE
        SYNTAX	INTEGER {
    		    thellodef(10)
    		}
        ACCESS	read-write
        STATUS	mandatory
        DESCRIPTION
                "Transmit hello ..."
        DEFVAL	{ thellodef }
        ::= { wfSt2CircuitEntry 17 }

    wfSt2CircuitRetryHello OBJECT-TYPE
        SYNTAX	INTEGER {
    		    rhellodef(5)
    		}
        ACCESS	read-write
        STATUS	mandatory
        DESCRIPTION
                "Receive hello ..."
        DEFVAL	{ rhellodef }
        ::= { wfSt2CircuitEntry 18 }

    wfSt2CircuitMTU OBJECT-TYPE
        SYNTAX	INTEGER
        ACCESS	read-write
        STATUS	mandatory
        DESCRIPTION
                "Maximum transmission unit ..."
        ::= { wfSt2CircuitEntry 19 }

    wfSt2CircuitDBGMask OBJECT-TYPE
        SYNTAX	INTEGER
        ACCESS	read-write
        STATUS	mandatory
        DESCRIPTION
                "Debug mask ..."
        ::= { wfSt2CircuitEntry 20 }

    wfSt2CircuitHelloFailure OBJECT-TYPE
        SYNTAX	INTEGER {
    		    preserve(1),
    		    down(2)
    		}
        ACCESS	read-write
        STATUS	mandatory
        DESCRIPTION
                "The stream is to be preserved even though
                helloing fails."
        DEFVAL	{ down }
        ::= { wfSt2CircuitEntry 21 }

    wfSt2CircuitHidProposed OBJECT-TYPE
        SYNTAX	INTEGER {
    		    locally(1),
    		    remotely(2)
    		}
        ACCESS	read-write
        STATUS	mandatory
        DESCRIPTION
                "Hid proposed flag ..."
        DEFVAL	{ locally }
        ::= { wfSt2CircuitEntry 22 }

    wfSt2CircuitBadStCksum OBJECT-TYPE
        SYNTAX	Counter
        ACCESS	read-only
        STATUS	mandatory
        DESCRIPTION
                "Bad St2 checksum ..."
        ::= { wfSt2CircuitEntry 23 }

    wfSt2CircuitEncodeBadParm OBJECT-TYPE
        SYNTAX	Counter
        ACCESS	read-only
        STATUS	mandatory
        DESCRIPTION
                "Bad parameter encoding ..."
        ::= { wfSt2CircuitEntry 24 }

    wfSt2CircuitEncodeWrongParms OBJECT-TYPE
        SYNTAX	Counter
        ACCESS	read-only
        STATUS	mandatory
        DESCRIPTION
                "Wrong parameter encoded ..."
        ::= { wfSt2CircuitEntry 25 }

    wfSt2CircuitMsgInHidColl OBJECT-TYPE
        SYNTAX	Counter
        ACCESS	read-only
        STATUS	mandatory
        DESCRIPTION
                "Message in Hid ..."
        ::= { wfSt2CircuitEntry 26 }

    wfSt2CircuitMsgInNoCon OBJECT-TYPE
        SYNTAX	Counter
        ACCESS	read-only
        STATUS	mandatory
        DESCRIPTION
                "Message in No ..."
        ::= { wfSt2CircuitEntry 27 }

    wfSt2CircuitNotSt2 OBJECT-TYPE
        SYNTAX	Counter
        ACCESS	read-only
        STATUS	mandatory
        DESCRIPTION
                "Not an St2 packet ..."
        ::= { wfSt2CircuitEntry 28 }

    wfSt2CircuitParmMissing OBJECT-TYPE
        SYNTAX	Counter
        ACCESS	read-only
        STATUS	mandatory
        DESCRIPTION
                "Circuit parameter missing ..."
        ::= { wfSt2CircuitEntry 29 }

    wfSt2CircuitScmpRefNum OBJECT-TYPE
        SYNTAX	Counter
        ACCESS	read-only
        STATUS	mandatory
        DESCRIPTION
                "Number of Scmp refuses ..."
        ::= { wfSt2CircuitEntry 30 }

    wfSt2CircuitScmp0rVlid OBJECT-TYPE
        SYNTAX	Counter
        ACCESS	read-only
        STATUS	mandatory
        DESCRIPTION
                "Scmp Or Vlid ..."
        ::= { wfSt2CircuitEntry 31 }

    wfSt2CircuitScmp0sVlid OBJECT-TYPE
        SYNTAX	Counter
        ACCESS	read-only
        STATUS	mandatory
        DESCRIPTION
                "Scmp Os Vlid ..."
        ::= { wfSt2CircuitEntry 32 }

    wfSt2CircuitScmpBadVlid OBJECT-TYPE
        SYNTAX	Counter
        ACCESS	read-only
        STATUS	mandatory
        DESCRIPTION
                "Bad Scmp Vlid ..."
        ::= { wfSt2CircuitEntry 33 }

    wfSt2CircuitScmpCksum OBJECT-TYPE
        SYNTAX	Counter
        ACCESS	read-only
        STATUS	mandatory
        DESCRIPTION
                "Scmp checksun ..."
        ::= { wfSt2CircuitEntry 34 }

    wfSt2CircuitScmpFailedResources OBJECT-TYPE
        SYNTAX	Counter
        ACCESS	read-only
        STATUS	mandatory
        DESCRIPTION
                "Scmp recources failed ..."
        ::= { wfSt2CircuitEntry 35 }

    wfSt2CircuitScmpFailedRoute OBJECT-TYPE
        SYNTAX	Counter
        ACCESS	read-only
        STATUS	mandatory
        DESCRIPTION
                "Scmp routed failed ..."
        ::= { wfSt2CircuitEntry 36 }

    wfSt2CircuitScmpLenInconsist OBJECT-TYPE
        SYNTAX	Counter
        ACCESS	read-only
        STATUS	mandatory
        DESCRIPTION
                "Scmp packet length inconsistent ..."
        ::= { wfSt2CircuitEntry 37 }

    wfSt2CircuitScmpRxTimeOut OBJECT-TYPE
        SYNTAX	Counter
        ACCESS	read-only
        STATUS	mandatory
        DESCRIPTION
                "Scmp receive time outs ..."
        ::= { wfSt2CircuitEntry 38 }

    wfSt2CircuitScmpXmtCnt OBJECT-TYPE
        SYNTAX	Counter
        ACCESS	read-only
        STATUS	mandatory
        DESCRIPTION
                "Scmp transmit count ..."
        ::= { wfSt2CircuitEntry 39 }

    wfSt2CircuitScmpRcvCnt OBJECT-TYPE
        SYNTAX	Counter
        ACCESS	read-only
        STATUS	mandatory
        DESCRIPTION
                "Scmp receive count ..."
        ::= { wfSt2CircuitEntry 40 }

    wfSt2CircuitDataXmtCnt OBJECT-TYPE
        SYNTAX	Counter
        ACCESS	read-only
        STATUS	mandatory
        DESCRIPTION
                "Transmited data count ..."
        ::= { wfSt2CircuitEntry 41 }

    wfSt2CircuitDataRcvCnt OBJECT-TYPE
        SYNTAX	Counter
        ACCESS	read-only
        STATUS	mandatory
        DESCRIPTION
                "received data count ..."
        ::= { wfSt2CircuitEntry 42 }

    wfSt2CircuitSt2StreamCnt OBJECT-TYPE
        SYNTAX	Counter
        ACCESS	read-only
        STATUS	mandatory
        DESCRIPTION
                "St2 stream count ..."
        ::= { wfSt2CircuitEntry 43 }

    wfSt2CircuitHelloXmtCnt OBJECT-TYPE
        SYNTAX	Counter
        ACCESS	read-only
        STATUS	mandatory
        DESCRIPTION
                "Hellos transmitted count ..."
        ::= { wfSt2CircuitEntry 44 }

    wfSt2CircuitHelloRcvCnt OBJECT-TYPE
        SYNTAX	Counter
        ACCESS	read-only
        STATUS	mandatory
        DESCRIPTION
                "Hellos received count ..."
        ::= { wfSt2CircuitEntry 45 }

    wfSt2CircuitHelloRAckCnt OBJECT-TYPE
        SYNTAX	Counter
        ACCESS	read-only
        STATUS	mandatory
        DESCRIPTION
                "Hellos received acknowledged coubt ..."
        ::= { wfSt2CircuitEntry 46 }

    wfSt2CircuitLbPoliceDrop OBJECT-TYPE
        SYNTAX	Counter
        ACCESS	read-only
        STATUS	mandatory
        DESCRIPTION
                "Learning bridge police drop count ..."
        ::= { wfSt2CircuitEntry 47 }

    wfSt2CircuitPbsDropCnt OBJECT-TYPE
        SYNTAX	Counter
        ACCESS	read-only
        STATUS	mandatory
        DESCRIPTION
                "Pbs drop count ..."
        ::= { wfSt2CircuitEntry 48 }

    wfSt2CircuitOverDrop2Cnt OBJECT-TYPE
        SYNTAX	Counter
        ACCESS	read-only
        STATUS	mandatory
        DESCRIPTION
                "Over drop ? count ..."
        ::= { wfSt2CircuitEntry 49 }

    wfSt2CircuitPktCnt OBJECT-TYPE
        SYNTAX	Counter
        ACCESS	read-only
        STATUS	mandatory
        DESCRIPTION
                "Circuit packet count ..."
        ::= { wfSt2CircuitEntry 50 }

    wfSt2CircuitScmpXmt OBJECT-TYPE
        SYNTAX	Counter
        ACCESS	read-only
        STATUS	mandatory
        DESCRIPTION
                "Scmp packets transmitted ..."
        ::= { wfSt2CircuitEntry 51 }

    wfSt2CircuitScmpRcv OBJECT-TYPE
        SYNTAX	Counter
        ACCESS	read-only
        STATUS	mandatory
        DESCRIPTION
                "Scmp packets received ..."
        ::= { wfSt2CircuitEntry 52 }

    wfSt2CircuitBWAlloc OBJECT-TYPE
        SYNTAX	Counter
        ACCESS	read-only
        STATUS	mandatory
        DESCRIPTION
                "Circuit bandwith allocated ..."
        ::= { wfSt2CircuitEntry 53 }

    wfSt2CircuitRsvdParameter1 OBJECT-TYPE
        SYNTAX	INTEGER
        ACCESS	read-write
        STATUS	mandatory
        DESCRIPTION
                "Circuit reserved parameter"
        ::= { wfSt2CircuitEntry 54 }

    wfSt2CircuitRsvdParameter2 OBJECT-TYPE
        SYNTAX	INTEGER
        ACCESS	read-write
        STATUS	mandatory
        DESCRIPTION
                "Circuit reserved parameter"
        ::= { wfSt2CircuitEntry 55 }

    wfSt2NeighborTable OBJECT-TYPE
        SYNTAX	SEQUENCE OF WfSt2NeighborEntry
        ACCESS	not-accessible
        STATUS	mandatory
        DESCRIPTION
                "The ST2 neighbor routing table"
        ::= { wfSt2Group 3 }

    wfSt2NeighborEntry OBJECT-TYPE
        SYNTAX	WfSt2NeighborEntry
        ACCESS	not-accessible
        STATUS	mandatory
        DESCRIPTION
                "Neighbor Table"
        INDEX	{ wfSt2NeighborNxtHopIPAddr }
        ::= { wfSt2NeighborTable 1 }

    WfSt2NeighborEntry ::= SEQUENCE {
    	    wfSt2NeighborDelete
    		INTEGER,
    	    wfSt2NeighborDisable
    		INTEGER,
    	    wfSt2NeighborNxtHopIPAddr
    		IpAddress,
    	    wfSt2NeighborRteExplr
    		INTEGER,
    	    wfSt2NeighborHelloProtocol
    		INTEGER,
    	    wfSt2NeighborType
    		INTEGER,
    	    wfSt2NeighborPriorityLevel
    		INTEGER,
    	    wfSt2NeighborRsvdParameter1
    		INTEGER,
    	    wfSt2NeighborRsvdParameter2
    		INTEGER,
    	    wfSt2NeighborLocalIPAddress
    		IpAddress,
    	    wfSt2NeighborTmoAccept
    		INTEGER,
    	    wfSt2NeighborRetryAccept
    		INTEGER,
    	    wfSt2NeighborTmoConnect
    		INTEGER,
    	    wfSt2NeighborRetryConnect
    		INTEGER,
    	    wfSt2NeighborTmoDisconnect
    		INTEGER,
    	    wfSt2NeighborRetryDisconnect
    		INTEGER,
    	    wfSt2NeighborTmoHidChange
    		INTEGER,
    	    wfSt2NeighborRetryHidChange
    		INTEGER,
    	    wfSt2NeighborTmoRefuse
    		INTEGER,
    	    wfSt2NeighborRetryRefuse
    		INTEGER,
    	    wfSt2NeighborTmoHello
    		INTEGER,
    	    wfSt2NeighborRetryHello
    		INTEGER
        }

    wfSt2NeighborDelete OBJECT-TYPE
        SYNTAX	INTEGER {
    		    create(1),
    		    delete(2)
    		}
        ACCESS	read-write
        STATUS	mandatory
        DESCRIPTION
                "Determines whether the base record is configured"
        DEFVAL	{ create }
        ::= { wfSt2NeighborEntry 1 }

    wfSt2NeighborDisable OBJECT-TYPE
        SYNTAX	INTEGER {
    		    enable(1),
    		    disable(2)
    		}
        ACCESS	read-write
        STATUS	mandatory
        DESCRIPTION
                "Determines whether the base record is active"
        DEFVAL	{ enable }
        ::= { wfSt2NeighborEntry 2 }

    wfSt2NeighborNxtHopIPAddr OBJECT-TYPE
        SYNTAX	IpAddress
        ACCESS	read-only
        STATUS	mandatory
        DESCRIPTION
                "IP address of next hop router"
        ::= { wfSt2NeighborEntry 3 }

    wfSt2NeighborRteExplr OBJECT-TYPE
        SYNTAX	INTEGER {
    		    yes(1),
    		    no(2)
    		}
        ACCESS	read-write
        STATUS	mandatory
        DESCRIPTION
                "Is the neighbor capable of route exploration"
        DEFVAL	{ no }
        ::= { wfSt2NeighborEntry 4 }

    wfSt2NeighborHelloProtocol OBJECT-TYPE
        SYNTAX	INTEGER {
    		    enable(1),
    		    active(2),
    		    disable(3)
    		}
        ACCESS	read-write
        STATUS	mandatory
        DESCRIPTION
                "Helloing in use"
        DEFVAL	{ enable }
        ::= { wfSt2NeighborEntry 5 }

    wfSt2NeighborType OBJECT-TYPE
        SYNTAX	INTEGER {
    		    local(1),
    		    tunnel(2)
    		}
        ACCESS	read-write
        STATUS	mandatory
        DESCRIPTION
                "Neighbor type, local or tunnel"
        DEFVAL	{ local }
        ::= { wfSt2NeighborEntry 6 }

    wfSt2NeighborPriorityLevel OBJECT-TYPE
        SYNTAX	INTEGER(1..16)
        ACCESS	read-write
        STATUS	mandatory
        DESCRIPTION
                "Route exploration or tunnel priority level"
        DEFVAL	{ 8 }
        ::= { wfSt2NeighborEntry 7 }

    wfSt2NeighborRsvdParameter1 OBJECT-TYPE
        SYNTAX	INTEGER
        ACCESS	read-write
        STATUS	mandatory
        DESCRIPTION
                "neighbor reserved parameter"
        ::= { wfSt2NeighborEntry 8 }

    wfSt2NeighborRsvdParameter2 OBJECT-TYPE
        SYNTAX	INTEGER
        ACCESS	read-write
        STATUS	mandatory
        DESCRIPTION
                "neighbor reserved parameter"
        ::= { wfSt2NeighborEntry 9 }

    wfSt2NeighborLocalIPAddress OBJECT-TYPE
        SYNTAX	IpAddress
        ACCESS	read-write
        STATUS	mandatory
        DESCRIPTION
                "Network Interface IP address of the local tunnel endpoint"
        DEFVAL	{ 0 }
        ::= { wfSt2NeighborEntry 10 }

    wfSt2NeighborTmoAccept OBJECT-TYPE
        SYNTAX	INTEGER {
    		    taccdef(10)
    		}
        ACCESS	read-write
        STATUS	mandatory
        DESCRIPTION
                "Transmit accept ..."
        DEFVAL	{ taccdef }
        ::= { wfSt2NeighborEntry 11 }

    wfSt2NeighborRetryAccept OBJECT-TYPE
        SYNTAX	INTEGER {
    		    raccdef(3)
    		}
        ACCESS	read-write
        STATUS	mandatory
        DESCRIPTION
                "Receive accept ..."
        DEFVAL	{ raccdef }
        ::= { wfSt2NeighborEntry 12 }

    wfSt2NeighborTmoConnect OBJECT-TYPE
        SYNTAX	INTEGER {
    		    tcondef(10)
    		}
        ACCESS	read-write
        STATUS	mandatory
        DESCRIPTION
                "Transmit connect ..."
        DEFVAL	{ tcondef }
        ::= { wfSt2NeighborEntry 13 }

    wfSt2NeighborRetryConnect OBJECT-TYPE
        SYNTAX	INTEGER {
    		    rcondef(5)
    		}
        ACCESS	read-write
        STATUS	mandatory
        DESCRIPTION
                "Receive connect ..."
        DEFVAL	{ rcondef }
        ::= { wfSt2NeighborEntry 14 }

    wfSt2NeighborTmoDisconnect OBJECT-TYPE
        SYNTAX	INTEGER {
    		    tdiscondef(10)
    		}
        ACCESS	read-write
        STATUS	mandatory
        DESCRIPTION
                "Transmit disconnect ..."
        DEFVAL	{ tdiscondef }
        ::= { wfSt2NeighborEntry 15 }

    wfSt2NeighborRetryDisconnect OBJECT-TYPE
        SYNTAX	INTEGER {
    		    rdiscondef(3)
    		}
        ACCESS	read-write
        STATUS	mandatory
        DESCRIPTION
                "Receive disconnect ..."
        DEFVAL	{ rdiscondef }
        ::= { wfSt2NeighborEntry 16 }

    wfSt2NeighborTmoHidChange OBJECT-TYPE
        SYNTAX	INTEGER {
    		    thidchgdef(10)
    		}
        ACCESS	read-write
        STATUS	mandatory
        DESCRIPTION
                "Transmit hid change ..."
        DEFVAL	{ thidchgdef }
        ::= { wfSt2NeighborEntry 17 }

    wfSt2NeighborRetryHidChange OBJECT-TYPE
        SYNTAX	INTEGER {
    		    rhidchgdef(3)
    		}
        ACCESS	read-write
        STATUS	mandatory
        DESCRIPTION
                "Receive Hid Change ..."
        DEFVAL	{ rhidchgdef }
        ::= { wfSt2NeighborEntry 18 }

    wfSt2NeighborTmoRefuse OBJECT-TYPE
        SYNTAX	INTEGER {
    		    trefusedef(10)
    		}
        ACCESS	read-write
        STATUS	mandatory
        DESCRIPTION
                "Transmit refuse ..."
        DEFVAL	{ trefusedef }
        ::= { wfSt2NeighborEntry 19 }

    wfSt2NeighborRetryRefuse OBJECT-TYPE
        SYNTAX	INTEGER {
    		    rrefusedef(3)
    		}
        ACCESS	read-write
        STATUS	mandatory
        DESCRIPTION
                "Receive refuse ..."
        DEFVAL	{ rrefusedef }
        ::= { wfSt2NeighborEntry 20 }

    wfSt2NeighborTmoHello OBJECT-TYPE
        SYNTAX	INTEGER {
    		    thellodef(10)
    		}
        ACCESS	read-write
        STATUS	mandatory
        DESCRIPTION
                "Transmit hello ..."
        DEFVAL	{ thellodef }
        ::= { wfSt2NeighborEntry 21 }

    wfSt2NeighborRetryHello OBJECT-TYPE
        SYNTAX	INTEGER {
    		    rhellodef(5)
    		}
        ACCESS	read-write
        STATUS	mandatory
        DESCRIPTION
                "Receive hello ..."
        DEFVAL	{ rhellodef }
        ::= { wfSt2NeighborEntry 22 }

    END  -- Wellfleet-ST2-MIB
