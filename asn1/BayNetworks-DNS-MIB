--DNS mib file
--BayNetworks-DNS-MIB definitions
 
BayNetworks-DNS-MIB DEFINITIONS ::= BEGIN
 
 
    IMPORTS
 
      IpAddress, Counter
        FROM RFC1155-SMI
      OBJECT-TYPE
        FROM RFC-1212
      DisplayString
        FROM RFC1213-MIB
      wfDnsGroup
        FROM Wellfleet-COMMON-MIB;

    wfDns		OBJECT IDENTIFIER ::= { wfDnsGroup 1 }

    wfDnsDelete	OBJECT-TYPE
        SYNTAX  INTEGER {
                created(1),
                deleted(2)
        }
        ACCESS  read-write
        STATUS  mandatory
        DESCRIPTION
                "Delete DNS instance"
	DEFVAL  { created }
        ::= { wfDns 1 }

    wfDnsDisable OBJECT-TYPE
        SYNTAX	INTEGER {
    		    enabled(1),
    		    disabled(2)
    		}
        ACCESS	read-write
        STATUS	mandatory
        DESCRIPTION
                "Enables or Disables DNS Subsystem"
        DEFVAL	{ enabled }
        ::= { wfDns 2 }

    wfDnsTimeOut OBJECT-TYPE
        SYNTAX	INTEGER(1..60)
        ACCESS	read-write
        STATUS	mandatory
        DESCRIPTION
                "General Retransmission time-out value (seconds)"
        DEFVAL	{ 5 }
        ::= { wfDns 3 }

    wfDnsRexmit OBJECT-TYPE
        SYNTAX  INTEGER(0..15)
        ACCESS  read-write
        STATUS  mandatory
        DESCRIPTION
                "Maximum Number of Retransmissions"
        DEFVAL  { 3 }
        ::= { wfDns 4 }

    wfDnsMaxAllow OBJECT-TYPE
        SYNTAX  INTEGER(1..100)
        ACCESS  read-write
        STATUS  mandatory
        DESCRIPTION
                "Maximum Number of Outstanding queries allowed"
        DEFVAL  { 20 }
        ::= { wfDns 5 }

    wfDnsIpTos OBJECT-TYPE
        SYNTAX	INTEGER {
    		    normal(1),
    		    lowdelay(2)
    		}
        ACCESS	read-write
        STATUS	obsolete
        DESCRIPTION
                "The Type Of Service value set in the IP
                datagram specifies to the Internet transport
                layer how the datagram should be handled.
                For DNS packet transfers low delay
                is preferred"
        DEFVAL	{ lowdelay }
        ::= { wfDns 6 }

    wfDnsDomainName OBJECT-TYPE
        SYNTAX  DisplayString
        ACCESS  read-write
        STATUS  mandatory
        DESCRIPTION
                "The Default Domain name"
        ::= { wfDns 7 }

    wfDnsRecursion OBJECT-TYPE
        SYNTAX  INTEGER {
                    enabled(1),
                    disabled(2)
                }
        ACCESS  read-write
        STATUS  mandatory
        DESCRIPTION
                "Recursion desired verses iterative request"
        DEFVAL  { enabled }
        ::= { wfDns 8 }

    wfDnsTruncation OBJECT-TYPE
        SYNTAX  INTEGER {
                    enabled(1),
                    disabled(2)
                }
        ACCESS  read-write
        STATUS  mandatory
        DESCRIPTION
                "Ignore truncations errors"
        DEFVAL  { enabled }
        ::= { wfDns 9 }

    wfDnsAuthOnly OBJECT-TYPE
        SYNTAX  INTEGER {
                    enabled(1),
                    disabled(2)
                }
        ACCESS  read-write
        STATUS  mandatory
        DESCRIPTION
                "Use authoriatative answers only"
        DEFVAL  { disabled }
        ::= { wfDns 10 }

    wfDnsDefDomain OBJECT-TYPE
        SYNTAX  INTEGER {
                    enabled(1),
                    disabled(2)
                }
        ACCESS  read-write
        STATUS  mandatory
        DESCRIPTION
                "Use default domain name for requests"
        DEFVAL  { enabled }
        ::= { wfDns 11 }

    wfDnsQueries OBJECT-TYPE
        SYNTAX  Counter
        ACCESS  read-only
        STATUS  mandatory
        DESCRIPTION
                "Total number of queries send out"
        ::= { wfDns 12 }
 
    wfDnsResps OBJECT-TYPE
        SYNTAX  Counter
        ACCESS  read-only
        STATUS  mandatory
        DESCRIPTION
                "Total number of responses received"
        ::= { wfDns 13 }
 
    wfDnsNonAuthResps OBJECT-TYPE
        SYNTAX  Counter
        ACCESS  read-only
        STATUS  mandatory
        DESCRIPTION
                "Number of non-authoritative (cached data) responses"
        ::= { wfDns 14 }
 
    wfDnsNoData OBJECT-TYPE
        SYNTAX  Counter
        ACCESS  read-only
        STATUS  mandatory
        DESCRIPTION
                "Number of requests that contained NO_DATA (empty)"
        ::= { wfDns 15 }
 
    wfDnsMartians OBJECT-TYPE
        SYNTAX  Counter
        ACCESS  read-only
        STATUS  mandatory
        DESCRIPTION
                "Number of responses received from servers that the
                 resolver does not think it asked"
        ::= { wfDns 16 }
 
    wfDnsUnParseResps OBJECT-TYPE
        SYNTAX  Counter
        ACCESS  read-only
        STATUS  mandatory
        DESCRIPTION
                "Number responses received that were unparseable"
        ::= { wfDns 17 }

    wfDnsRexmitPkts OBJECT-TYPE
        SYNTAX  Counter
        ACCESS  read-only
        STATUS  mandatory
        DESCRIPTION
                "Number of Re-transmitted packets"
        ::= { wfDns 18 }

    wfDnsTimeOuts OBJECT-TYPE
        SYNTAX  Counter
        ACCESS  read-only
        STATUS  mandatory
        DESCRIPTION
                "Number of quries that internally timed out."
        ::= { wfDns 19 }

    wfDnsHostsFile OBJECT-TYPE
        SYNTAX  DisplayString
        ACCESS  read-write
        STATUS  mandatory
        DESCRIPTION
                "The default hosts file"
        ::= { wfDns 20 }

    wfDnsRcvdError OBJECT-TYPE
        SYNTAX  Counter
        ACCESS  read-only
        STATUS  mandatory
        DESCRIPTION
                "Number of quries that were returned with an error."
        ::= { wfDns 21 }
 
    wfDnsLocalError OBJECT-TYPE
        SYNTAX  Counter
        ACCESS  read-only
        STATUS  mandatory
        DESCRIPTION
                "The number of local errors which occured."
        ::= { wfDns 22 }

    wfDnsServerTable OBJECT-TYPE
        SYNTAX SEQUENCE OF WfDnsServerEntry
        ACCESS not-accessible
        STATUS mandatory
        DESCRIPTION
                "DNS base entry table.
                "
        ::= { wfDnsGroup 2 }
 
    wfDnsServerEntry OBJECT-TYPE
        SYNTAX  WfDnsServerEntry
        ACCESS  not-accessible
        STATUS  mandatory
        DESCRIPTION
                "An DNS base entry description"
        INDEX   { wfDnsServerIndex }
 
        ::= { wfDnsServerTable 1 }
 
    WfDnsServerEntry ::= SEQUENCE {
                wfDnsServerDelete
                INTEGER,
                wfDnsServerIndex
                INTEGER,
                wfDnsServerAddr
                IpAddress,
                wfDnsServerPortNo
                INTEGER
            }
 
    wfDnsServerDelete	OBJECT-TYPE
        SYNTAX  INTEGER {
                created(1),
                deleted(2)
        }
        ACCESS  read-write
        STATUS  mandatory
        DESCRIPTION
                "Delete DNS Server instance"
	DEFVAL  { created }
        ::= { wfDnsServerEntry 1 }

    wfDnsServerIndex OBJECT-TYPE
        SYNTAX INTEGER
        ACCESS read-only
        STATUS mandatory
        DESCRIPTION
                "Index of this entry. Index can only be one to three."
        ::= { wfDnsServerEntry 2 }
 
    wfDnsServerAddr OBJECT-TYPE
        SYNTAX  IpAddress
        ACCESS  read-write
        STATUS  mandatory
        DESCRIPTION
                "The IP address for DNS server."
        ::= { wfDnsServerEntry 3 }
 
    wfDnsServerPortNo OBJECT-TYPE
        SYNTAX  INTEGER
        ACCESS  read-write
        STATUS  mandatory
        DESCRIPTION
                "The port the DNS server is utilizing.  Default is 53."
        DEFVAL  { 53 }
        ::= { wfDnsServerEntry 4 }

    wfDnsProxyIntfTable OBJECT-TYPE
        SYNTAX  SEQUENCE OF WfDnsProxyIntfEntry
        ACCESS  not-accessible
        STATUS  mandatory
        DESCRIPTION
                "This table contains per-interface configuration information
                 for the DNS Proxy Server operation"
        ::= { wfDnsGroup 3 }
 
    wfDnsProxyIntfEntry OBJECT-TYPE
        SYNTAX  WfDnsProxyIntfEntry
        ACCESS  not-accessible
        STATUS  mandatory
        DESCRIPTION
                "a BOOTP relay agent interface description"
        INDEX   { wfDnsProxyIntfAddress }
        ::= { wfDnsProxyIntfTable 1 }
 
    WfDnsProxyIntfEntry ::= SEQUENCE {
            wfDnsProxyIntfDelete
                INTEGER,
            wfDnsProxyIntfDisable
                INTEGER,
            wfDnsProxyIntfState
                INTEGER,
            wfDnsProxyIntfAddress
                IpAddress,
            wfDnsProxyIntfPortNo
                INTEGER,
            wfDnsProxyIntfMode
                INTEGER,
            wfDnsProxyIntfDomain
                DisplayString,
            wfDnsProxyIntfFwdServer1
                IpAddress,
            wfDnsProxyIntfFwdServer2
                IpAddress,
            wfDnsProxyIntfFwdServer3
                IpAddress,
            wfDnsProxyIntfFwdServerPortNo
                INTEGER,
            wfDnsProxyIntfTimeOut
                INTEGER,
            wfDnsProxyIntfRexmit
                INTEGER,
            wfDnsProxyIntfMaxAllow
                INTEGER,
            wfDnsProxyIntfTruncDnsAnswer
                INTEGER,
            wfDnsProxyIntfTruncMaxNo
                INTEGER,
            wfDnsProxyIntfCacheSize
                INTEGER,
            wfDnsProxyIntfForward
                Counter,
            wfDnsProxyIntfResps
                Counter,
            wfDnsProxyIntfDropped
                Counter,
            wfDnsProxyIntfMartians
                Counter,
            wfDnsProxyIntfUnParseResps
                Counter,
            wfDnsProxyIntfRexmitPkts
                Counter,
            wfDnsProxyIntfTimeOuts
                Counter,
            wfDnsProxyIntfLocalError
               Counter,
            wfDnsProxyIntfCacheHits
               Counter 
        }
 
    wfDnsProxyIntfDelete OBJECT-TYPE
        SYNTAX  INTEGER {
                    created(1),
                    deleted(2)
                }
        ACCESS  read-write
        STATUS  mandatory
        DESCRIPTION
                "Create/Delete: if set to delete, the DNS Proxy Server is
                removed from this network interface."
        DEFVAL  { created }
        ::= { wfDnsProxyIntfEntry 1 }
 
    wfDnsProxyIntfDisable OBJECT-TYPE
        SYNTAX  INTEGER {
                    enabled(1),
                    disabled(2)
                }
        ACCESS  read-write
        STATUS  mandatory
        DESCRIPTION
                "Enable/Disable: controls whether the DNS Proxy Server is
                enabled or disabled on this network interface."
        DEFVAL  { enabled }
        ::= { wfDnsProxyIntfEntry 2 }
 
    wfDnsProxyIntfState OBJECT-TYPE
        SYNTAX  INTEGER {
                    up(1),
                    down(2),
                    init(3),
                    invalid(4),
                    notpres(5)
                }
        ACCESS  read-only
        STATUS  mandatory
        DESCRIPTION
                "The state of the DNS Proxy Server on this interface."
        DEFVAL  { notpres }
        ::= { wfDnsProxyIntfEntry 3 }
 
    wfDnsProxyIntfAddress OBJECT-TYPE
        SYNTAX  IpAddress
        ACCESS  read-only
        STATUS  mandatory
        DESCRIPTION
                "Network interface address for the DNS Proxy Server."
        ::= { wfDnsProxyIntfEntry 4 }

    wfDnsProxyIntfPortNo OBJECT-TYPE
        SYNTAX  INTEGER
        ACCESS  read-write
        STATUS  mandatory
        DESCRIPTION
                "The port the DNS Proxy is listening.  Default is 53."
        DEFVAL  { 53 }
        ::= { wfDnsProxyIntfEntry 5 }

    wfDnsProxyIntfMode OBJECT-TYPE
        SYNTAX  INTEGER {
                    pass-thru(1),
                    nat-translation(2)
                }
        ACCESS  read-write
        STATUS  mandatory
        DESCRIPTION
                "Controls mode whether the DNS Proxy Server is operating in
                 standard pass thru mode or translating address for Network
                 Address Translation (NAT)."
        DEFVAL  { pass-thru }
        ::= { wfDnsProxyIntfEntry 6 }

    wfDnsProxyIntfDomain OBJECT-TYPE
        SYNTAX  DisplayString
        ACCESS  read-write
        STATUS  mandatory
        DESCRIPTION
                "The domain name for this Network Interface (NAT only)."
        ::= { wfDnsProxyIntfEntry 7 }
 
    wfDnsProxyIntfFwdServer1 OBJECT-TYPE
        SYNTAX  IpAddress
        ACCESS  read-write
        STATUS  mandatory
        DESCRIPTION
                "The first DNS Server to forward requests to for this domain."
        ::= { wfDnsProxyIntfEntry 8 }
 
    wfDnsProxyIntfFwdServer2 OBJECT-TYPE
        SYNTAX  IpAddress
        ACCESS  read-write
        STATUS  mandatory
        DESCRIPTION
                "The second DNS Server to forward requests to for this domain."
        ::= { wfDnsProxyIntfEntry 9 }
 
    wfDnsProxyIntfFwdServer3 OBJECT-TYPE
        SYNTAX  IpAddress
        ACCESS  read-write
        STATUS  mandatory
        DESCRIPTION
                "The third DNS Server to forward requests to for this domain."
        ::= { wfDnsProxyIntfEntry 10 }

    wfDnsProxyIntfFwdServerPortNo OBJECT-TYPE
        SYNTAX  INTEGER
        ACCESS  read-write
        STATUS  mandatory
        DESCRIPTION
                "The port the DNS Fwd Server(s) are on.  Default is 53."
        DEFVAL  { 53 }
        ::= { wfDnsProxyIntfEntry 11 }

    wfDnsProxyIntfTimeOut OBJECT-TYPE
        SYNTAX  INTEGER(1..60)
        ACCESS  read-write
        STATUS  mandatory
        DESCRIPTION
                "General Retransmission time-out value (seconds)"
        DEFVAL  { 5 }
        ::= { wfDnsProxyIntfEntry 12 }
 
    wfDnsProxyIntfRexmit OBJECT-TYPE
        SYNTAX  INTEGER(0..15)
        ACCESS  read-write
        STATUS  mandatory
        DESCRIPTION
                "Maximum Number of Retransmissions"
        DEFVAL  { 2 }
        ::= { wfDnsProxyIntfEntry 13 }
 
    wfDnsProxyIntfMaxAllow OBJECT-TYPE
        SYNTAX  INTEGER(1..100)
        ACCESS  read-write
        STATUS  mandatory
        DESCRIPTION
                "Maximum Number of Outstanding queries allowed"
        DEFVAL  { 20 }
        ::= { wfDnsProxyIntfEntry 14 }
 
    wfDnsProxyIntfTruncDnsAnswer OBJECT-TYPE
        SYNTAX  INTEGER {
                    enabled(1),
                    disabled(2)
                }
        ACCESS  read-write
        STATUS  mandatory
        DESCRIPTION
                "Enable/Disable: controls whether the DNS Proxy Server is
                enabled for truncating the number of DNS answers"
        DEFVAL  { disabled }
        ::= { wfDnsProxyIntfEntry 15 }

    wfDnsProxyIntfTruncMaxNo OBJECT-TYPE
        SYNTAX  INTEGER (1..100)
        ACCESS  read-write
        STATUS  mandatory
        DESCRIPTION
                "If wfDnsProxyIntfTruncDnsAnswer is set to enable, this
                 controls the maximum number of answers returned to the
                 requester."
        DEFVAL  { 1 }
        ::= { wfDnsProxyIntfEntry 16 }

    wfDnsProxyIntfCacheSize OBJECT-TYPE
        SYNTAX  INTEGER(0..100)
        ACCESS  read-write
        STATUS  mandatory
        DESCRIPTION
                "Maximum Number Cache Entries allowed"
        DEFVAL  { 20 }
        ::= { wfDnsProxyIntfEntry 17 }

    wfDnsProxyIntfForward OBJECT-TYPE
        SYNTAX  Counter
        ACCESS  read-only
        STATUS  mandatory
        DESCRIPTION
                "Total number of queries forwarded"
        ::= { wfDnsProxyIntfEntry 18 }
 
    wfDnsProxyIntfResps OBJECT-TYPE
        SYNTAX  Counter
        ACCESS  read-only
        STATUS  mandatory
        DESCRIPTION
                "Total number of responses received"
        ::= { wfDnsProxyIntfEntry 19 }

    wfDnsProxyIntfDropped OBJECT-TYPE
        SYNTAX  Counter
        ACCESS  read-only
        STATUS  mandatory
        DESCRIPTION
                "Total number of queries dropped"
        ::= { wfDnsProxyIntfEntry 20 }

    wfDnsProxyIntfMartians OBJECT-TYPE
        SYNTAX  Counter
        ACCESS  read-only
        STATUS  mandatory
        DESCRIPTION
                "Number of responses received from servers that the
                 DNS Proxy does not think it asked"
        ::= { wfDnsProxyIntfEntry 21 }
 
    wfDnsProxyIntfUnParseResps OBJECT-TYPE
        SYNTAX  Counter
        ACCESS  read-only
        STATUS  mandatory
        DESCRIPTION
                "Number responses received that were unparseable"
        ::= { wfDnsProxyIntfEntry 22 }
 
    wfDnsProxyIntfRexmitPkts OBJECT-TYPE
        SYNTAX  Counter
        ACCESS  read-only
        STATUS  mandatory
        DESCRIPTION
                "Number of Re-transmitted packets"
        ::= { wfDnsProxyIntfEntry 23 }
 
    wfDnsProxyIntfTimeOuts OBJECT-TYPE
        SYNTAX  Counter
        ACCESS  read-only
        STATUS  mandatory
        DESCRIPTION
                "Number of quries that internally timed out."
        ::= { wfDnsProxyIntfEntry 24 }

    wfDnsProxyIntfLocalError OBJECT-TYPE
        SYNTAX  Counter
        ACCESS  read-only
        STATUS  mandatory
        DESCRIPTION
                "The number of local errors which occured."
        ::= { wfDnsProxyIntfEntry 25 }

    wfDnsProxyIntfCacheHits OBJECT-TYPE
        SYNTAX  Counter
        ACCESS  read-only
        STATUS  mandatory
        DESCRIPTION
                "The number of requests that were found in the local cache."
        ::= { wfDnsProxyIntfEntry 26 }

    END  -- Wellfleet-DNS-MIB
