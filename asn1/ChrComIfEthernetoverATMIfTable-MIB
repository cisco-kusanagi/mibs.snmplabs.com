ChrComIfEthernetoverATMIfTable-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfEthernet			FROM  Chromatis-MIB
	EthernetIfTypeEnum			FROM  EthernetTypes-MIB
	TruthValue				FROM  ChrTyp-MIB
	SpeedEnum				FROM  EthernetTypes-MIB
	DuplexModeEnum				FROM  EthernetTypes-MIB
	AlarmSeverityProfileIndexEnum		 FROM  EthernetTypes-MIB;

-- chrComIfEthernetoverATMIfTable Table

chrComIfEthernetoverATMIfTableTable		OBJECT-TYPE
	SYNTAX		SEQUENCE OF ChrComIfEthernetoverATMIfTableEntry
	MAX-ACCESS	not-accessible
	STATUS		current
	DESCRIPTION
	"This table is an extension of the ifTable for the Ethernet/ATM interface type. Contains MAC-level configuration parameters and allows association of an interface with a specific LVM and LPG within its ELM"
	::= { chrComIfEthernet 3}

chrComIfEthernetoverATMIfTableEntry		OBJECT-TYPE
	SYNTAX		ChrComIfEthernetoverATMIfTableEntry
	MAX-ACCESS	not-accessible
	STATUS		current
	DESCRIPTION
	""
	INDEX  {  chrComIfEthernetIfIndex }

--DEFAULT  get-function-async  MNIL_GetRoutine
--DEFAULT  set-function-async  MNIL_SetRoutine
--DEFAULT  next-function-async MNIL_NextRoutine
--DEFAULT  test-function-async MNIL_TestRoutine
--DEFAULT  cookie "overATMIfTable"
	::= { chrComIfEthernetoverATMIfTableTable  1 }

ChrComIfEthernetoverATMIfTableEntry  ::=
	SEQUENCE  {
	chrComIfEthernetIfIndex			Unsigned32	(0..4294967295),
	chrComIfEthernetELMIndex		Unsigned32	(0..1),
	chrComIfEthernetEthernetIfType		EthernetIfTypeEnum,
	chrComIfEthernetPortEnable		TruthValue,
	chrComIfEthernetAutoNegSpeed		TruthValue,
	chrComIfEthernetAutoNegDuplexMode	TruthValue,
	chrComIfEthernetAutoNegEnFlowControl	TruthValue,
	chrComIfEthernetSpeed			SpeedEnum,
	chrComIfEthernetDuplexMode		DuplexModeEnum,
	chrComIfEthernetEnFlowControl		TruthValue,
	chrComIfEthernetEnBackpressure		TruthValue,
	chrComIfEthernetLpgID			Unsigned32	(0..7),
	chrComIfEthernetLvmID			Unsigned32	(0..7),
	chrComIfEthernetAlarmVector		Integer32	(0..65535),
	chrComIfEthernetAlarmSeverityProfileIndex AlarmSeverityProfileIndexEnum
}

chrComIfEthernetIfIndex 	OBJECT-TYPE
	SYNTAX		Unsigned32	(0..4294967295)
	MAX-ACCESS 	read-only
	STATUS 		current
	DESCRIPTION
	"Index referring to the interface table"
	::= { chrComIfEthernetoverATMIfTableEntry  1 }

chrComIfEthernetELMIndex 	OBJECT-TYPE
	SYNTAX		Unsigned32	(0..1)
	MAX-ACCESS 	read-only
	STATUS 		current
	DESCRIPTION
	"ELM index within card (up to 2 ELMs per card; current card has only 1)"
	::= { chrComIfEthernetoverATMIfTableEntry  2 }

chrComIfEthernetEthernetIfType 	OBJECT-TYPE
	SYNTAX		EthernetIfTypeEnum
	MAX-ACCESS 	read-only
	STATUS 		current
	DESCRIPTION
	"Type of port (FE/GE, Electrical/Optical, etc.)"
	::= { chrComIfEthernetoverATMIfTableEntry  3 }

chrComIfEthernetPortEnable 	OBJECT-TYPE
	SYNTAX		TruthValue
	MAX-ACCESS 	read-write
	STATUS 		current
	DESCRIPTION
	"Specifies if port is enabled or disabled. Ingress and egress traffic for this card is dropped if disabled"
	::= { chrComIfEthernetoverATMIfTableEntry  4 }

chrComIfEthernetAutoNegSpeed 	OBJECT-TYPE
	SYNTAX		TruthValue
	MAX-ACCESS 	read-write
	STATUS 		current
	DESCRIPTION
	"Defines if autonegotiation is allowed for Speed"
	::= { chrComIfEthernetoverATMIfTableEntry  5 }

chrComIfEthernetAutoNegDuplexMode 	OBJECT-TYPE
	SYNTAX		TruthValue
	MAX-ACCESS 	read-write
	STATUS 		current
	DESCRIPTION
	"Defines if autonegotiation is allowed for DuplexMode"
	::= { chrComIfEthernetoverATMIfTableEntry  6 }

chrComIfEthernetAutoNegEnFlowControl 	OBJECT-TYPE
	SYNTAX		TruthValue
	MAX-ACCESS 	read-write
	STATUS 		current
	DESCRIPTION
	"Defines if autonegotiation is allowed for En-Flow-Control"
	::= { chrComIfEthernetoverATMIfTableEntry  7 }

chrComIfEthernetSpeed 	OBJECT-TYPE
	SYNTAX		SpeedEnum
	MAX-ACCESS 	read-write
	STATUS 		current
	DESCRIPTION
	"Speed"
	::= { chrComIfEthernetoverATMIfTableEntry  8 }

chrComIfEthernetDuplexMode 	OBJECT-TYPE
	SYNTAX		DuplexModeEnum
	MAX-ACCESS 	read-write
	STATUS 		current
	DESCRIPTION
	"Duplex Mode (Half/Full)"
	::= { chrComIfEthernetoverATMIfTableEntry  9 }

chrComIfEthernetEnFlowControl 	OBJECT-TYPE
	SYNTAX		TruthValue
	MAX-ACCESS 	read-write
	STATUS 		current
	DESCRIPTION
	"Defines if 802.3x Flow Control is enabled"
	::= { chrComIfEthernetoverATMIfTableEntry  10 }

chrComIfEthernetEnBackpressure 	OBJECT-TYPE
	SYNTAX		TruthValue
	MAX-ACCESS 	read-write
	STATUS 		current
	DESCRIPTION
	"Defines if backpressure is enabled in half-duplex mode"
	::= { chrComIfEthernetoverATMIfTableEntry  11 }

chrComIfEthernetLpgID 	OBJECT-TYPE
	SYNTAX		Unsigned32	(0..7)
	MAX-ACCESS 	read-write
	STATUS 		current
	DESCRIPTION
	"ID of Local Port Group (LPG) within the ELM that this port belongs to"
	::= { chrComIfEthernetoverATMIfTableEntry  12 }

chrComIfEthernetLvmID 	OBJECT-TYPE
	SYNTAX		Unsigned32	(0..7)
	MAX-ACCESS 	read-write
	STATUS 		current
	DESCRIPTION
	"ID of Local VLAN Member (LVM) within the ELM that this port belongs to"
	::= { chrComIfEthernetoverATMIfTableEntry  13 }

chrComIfEthernetAlarmVector 	OBJECT-TYPE
	SYNTAX		Integer32	(0..65535)
	MAX-ACCESS 	read-only
	STATUS 		current
	DESCRIPTION
	"16 bit field. The following are bits relative positions (0=LSB), and the trap ID associated to each alarm state. 
0. Ethernet Loss of Signal (-LOS) (metropolisEthLosAlarm)
"
	::= { chrComIfEthernetoverATMIfTableEntry  14 }

chrComIfEthernetAlarmSeverityProfileIndex 	OBJECT-TYPE
	SYNTAX		AlarmSeverityProfileIndexEnum
	MAX-ACCESS 	read-write
	STATUS 		current
	DESCRIPTION
	""
	::= { chrComIfEthernetoverATMIfTableEntry  15 }


END
