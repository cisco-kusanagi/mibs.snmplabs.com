QOSEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString
			FROM SNMPv2-TC
		qosExt
			FROM APENT-MIB;

--QOSEXT MIB

    apQosExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module ArrowPoint QOS class definitions"
      ::= { qosExt 1}


apQosTable OBJECT-TYPE
	SYNTAX          SEQUENCE OF APQosEntry
	MAX-ACCESS      not-accessible
	STATUS          current
	DESCRIPTION
		"QOS class attributes"
	::= { qosExt 2 }

apQosEntry OBJECT-TYPE
	SYNTAX          APQosEntry
	MAX-ACCESS      not-accessible
	STATUS          current	
	DESCRIPTION	
		"Configureable Interface specific characteristic record."
	INDEX   { apQosType, apQosSubType }
	::= { apQosTable 1 }

APQosEntry ::= SEQUENCE {
		apQosType              INTEGER,
		apQosSubType           INTEGER,
		apQosName              DisplayString,
		apQosClass             Integer32,
		apQosHopLatency        Integer32,
		apQosSampleRate        Integer32,
		apQosBitsPerSample     Integer32,
		apQosAvgBw             Integer32,
		apQosSampleSize        Integer32,
		apQosSilenceTime       Integer32
}

apQosType           OBJECT-TYPE
	SYNTAX			INTEGER {
							best-effort(1),
							streamed(2)
							}
	MAX-ACCESS      read-only
	STATUS  		current
	DESCRIPTION     
		"The basic category of QOS to be delivered"
	::= {apQosEntry 1}

apQosSubType        OBJECT-TYPE
	SYNTAX			INTEGER {
							best-effort(1),
							realAudio-2-14400(2),
							realAudio-2-28800(3),
							realAudio-3-28800(4),
							realAudio-3-28800-stereo(5),
							realAudio-3-isdn(6),
							realAudio-3-dual-isdn(7)
							}
	MAX-ACCESS      read-only
	STATUS  		current
	DESCRIPTION     
		"The more specific QOS categorization"
	::= {apQosEntry 2}

apQosName	 OBJECT-TYPE
	SYNTAX          DisplayString (SIZE(1..64))
	MAX-ACCESS      read-create
	STATUS          current
	DESCRIPTION     
		"The name used to reference the particular set of QOS settings"
	::= {apQosEntry 3}

apQosClass    OBJECT-TYPE
	SYNTAX			Integer32 (0..7)
	MAX-ACCESS      read-only
	STATUS  		current
	DESCRIPTION     
		"The QOS switching priority"
	::= {apQosEntry 4}

apQosHopLatency    OBJECT-TYPE
	SYNTAX			Integer32
	MAX-ACCESS      read-only
	STATUS  		current
	DESCRIPTION     
		"The maximum switch introduced delay which can be tolerated"
	::= {apQosEntry 5}

apQosSampleRate    OBJECT-TYPE
	SYNTAX			Integer32
	MAX-ACCESS      read-only
	STATUS  		current
	DESCRIPTION     
		"The sampling rate used to produce files that require this QOS"
	::= {apQosEntry 6}

apQosBitsPerSample    OBJECT-TYPE
	SYNTAX			Integer32
	MAX-ACCESS      read-only
	STATUS  		current
	DESCRIPTION     
		"The number of bits per sample"
	::= {apQosEntry 7}

apQosAvgBw    OBJECT-TYPE
	SYNTAX			Integer32
	MAX-ACCESS      read-only
	STATUS  		current
	DESCRIPTION     
		"The average bandwidth requirements for flows of this QOS"
	::= {apQosEntry 8}

apQosSampleSize    OBJECT-TYPE
	SYNTAX			Integer32
	MAX-ACCESS      read-only
	STATUS  		current
	DESCRIPTION     
		"The sampling size used when creating files for use with this QOS"
	::= {apQosEntry 9}

apQosSilenceTime    OBJECT-TYPE
	SYNTAX			Integer32
	MAX-ACCESS      read-only
	STATUS  		current
	DESCRIPTION     
		"The length of the quiet time between packets transmitted by 
		 the server for this QOS"
	::= {apQosEntry 10}
END
