-- *********************************************************************
-- Copyright (c) 1998-2005 Tiara Networks Inc.
-- All rights reserved.
--
-- April,1st 1998, kumar
--
-- 
--  MIB Tree Overview:
-- 
--
--dsxMIB
--  |_dsxT1E1IfGroup
--  |  |_dsxT1E1MIB
--  |      |_dsxT1E1IfConfigGroup
--  |      |   |_dsxT1E1IfConfigLineTable
--  |      |   |_dsxT1E1IfConfigFdlTable
--  |      |   |_dsxT1E1IfAlarmConfigGroup
--  |      |   |   |_dsxT1E1IfAlarmThresholdConfigTable {te1IfIndex, configIndex}
--  |      |   |_dsxT1E1IfTestConfigTable
--  |      |_dsxT1E1IfStatusGroup
--  |      |   |_dsxT1E1IfStatusTable
--  |      |   |_dsxT1E1IfAlarmStatusTable
--  |      |   |_dsxT1E1IfTestStatusTable
--  |      |   |_dsxT1E1IfLastTestResultTable
--  |      |_dsxT1E1IfStatsGroup
--  |      |   |_dsxT1E1IfArchiveStatsValidIntervalsTable
--  |      |   |_dsxT1E1IfAnsiStatsGroup
--  |      |   |   |_dsxT1E1IfAnsiCurrentStatsTable
--  |      |   |   |_dsxT1E1IfAnsiTotalStatsTable
--  |      |   |   | dsxT1E1IfAnsiArchiveIntervalStatsTable {te1IfIndex, interval number }
--  |      |   |_dsxT1E1IfAttStatsGroup   
--  |      |   |   |_dsxT1E1IfAttCurrentStatsTable
--  |      |   |   |_dsxT1E1IfAttTotalStatsTable
--  |      |   |   |_dsxT1E1IfAttArchiveStatsTable {te1IfIndex,interval number}
--  |      |   |_dsxT1E1IfIetfStatsGroup   
--  |      |   |   |_dsxT1E1IfIetfCurrentStatsTable 
--  |      |   |   |_dsxT1E1IfIetfTotalStatsTable   
--  |      |   |   |_dsxT1E1IfIetfArchiveStatsTable { te1IfIndex,interval number }
--  |      |   |_dsxT1E1IfUserStatsGroup   
--  |      |   |   |_dsxT1E1IfUserCurrentStatsTable 
--  |      |   |   |_dsxT1E1IfUserTotalStatsTable { te1IfIndex, day }
--  |      |   |   |_dsxT1E1IfUserLifetimeStatsTable
--  |      |   |   |_dsxT1E1IfUserArchiveStatsTable { te1IfIndex,interval number }
-- ***************************************************************************
TIARA-NETWORKS-DSX-TE1-MIB DEFINITIONS ::= BEGIN


IMPORTS
	TRAP-TYPE FROM RFC-1215
    MODULE-IDENTITY, 
    OBJECT-TYPE, 
    Unsigned32
        FROM SNMPv2-SMI
    dsxT1E1IfGroup
        FROM TIARA-NETWORKS-DSX-TC-MIB
    TruthValue
        FROM SNMPv2-TC
    DisplayString
        FROM RFC1213-MIB;

dsxT1E1MIB MODULE-IDENTITY
    LAST-UPDATED "9904230000Z"
    ORGANIZATION "Tiara Networks Inc."
    CONTACT-INFO
                "       Tiara Networks
                        Customer Service

                Postal: 525 Race Street, Suite 100,
                        San Jose, CA 95126
                        USA

                   Tel: +1 408-216-4700
                   Fax: +1 408-216-4701

                E-mail: support@tiaranetworks.com"

    DESCRIPTION
            " Interface MIB definitions for Tiara T1/E1 interface modules."
    REVISION "9904230000Z"
    DESCRIPTION
            "Initial revision."
    ::= { dsxT1E1IfGroup 1 }
    
 -- TE1 Interface Group 
 -- A definition template to be used for all other types of 
 -- interfaces
 -- Assigments for T1E1 Traps

dsxT1E1Traps  OBJECT IDENTIFIER ::= { dsxT1E1IfGroup 2}

dsxT1E1TrapVariables OBJECT IDENTIFIER  ::= { dsxT1E1Traps 1}

 -- T1/E1 Interface sub-group definitions
 
dsxT1E1IfConfigGroup      OBJECT IDENTIFIER ::= { dsxT1E1MIB 1 }
dsxT1E1IfStatusGroup      OBJECT IDENTIFIER ::= { dsxT1E1MIB 2 }
dsxT1E1IfStatsGroup       OBJECT IDENTIFIER ::= { dsxT1E1MIB 3 }

-- DSX T1/E1 Interface Configuration group definitions

-- DSX T1/E1 interface configuration table

dsxT1E1IfConfigLineTable OBJECT-TYPE
    SYNTAX      SEQUENCE OF DsxT1E1IfConfigLineEntry
    MAX-ACCESS  not-accessible
    STATUS      current
    DESCRIPTION
            "A list of T1/E1 interfaces currently configured."
    ::= { dsxT1E1IfConfigGroup 1 }

dsxT1E1IfConfigLineEntry OBJECT-TYPE
    SYNTAX      DsxT1E1IfConfigLineEntry
    MAX-ACCESS  not-accessible
    STATUS      current
    DESCRIPTION
            "An entry containing configuration for each  T1/E1 interface."
    INDEX   { dsxT1E1IfIndex }
    ::= { dsxT1E1IfConfigLineTable 1 }

DsxT1E1IfConfigLineEntry ::=
    SEQUENCE {
        dsxT1E1IfIndex                        INTEGER,
        dsxT1E1IfConfigServiceMode            TruthValue,
        dsxT1E1IfConfigLineMode               INTEGER,
        dsxT1E1IfConfigLineType               INTEGER,
        dsxT1E1IfConfigLineCode               INTEGER,
        dsxT1E1IfConfigLBO                    INTEGER,
        dsxT1E1IfConfigCableLength            INTEGER,
        dsxT1E1IfConfigRaiAlarm               INTEGER,
        dsxT1E1IfConfigTransmitClock          INTEGER,
        dsxT1E1IfConfigTimeSlotMap            OCTET STRING,
        dsxT1E1IfCircuitId                     DisplayString,
        dsxT1E1IfContactInfo                  DisplayString,
        dsxT1E1IfDescription                  DisplayString
    }

dsxT1E1IfIndex OBJECT-TYPE
    SYNTAX      INTEGER
    MAX-ACCESS  not-accessible
    STATUS      current
    DESCRIPTION
            "An integer value which is an index in to the entries of 
            ifTable (MIB-II) whose interface type is ds1" 
    ::= { dsxT1E1IfConfigLineEntry 1 }
    
dsxT1E1IfConfigServiceMode OBJECT-TYPE
    SYNTAX      TruthValue 
    MAX-ACCESS  read-write
    STATUS      current
    DESCRIPTION 
			"Indicates the T1/E1 interface is in service if it is TRUE. "
    ::= { dsxT1E1IfConfigLineEntry 2 }

dsxT1E1IfConfigLineMode OBJECT-TYPE
    SYNTAX      INTEGER 
                {
                    linemode-csu        (1),
                    linemode-dsx        (2)
                }
    MAX-ACCESS  read-write
    STATUS      current
    DESCRIPTION 
				"Line Mode for this T1/E1 interface"
    ::= { dsxT1E1IfConfigLineEntry 3 }

dsxT1E1IfConfigLineType OBJECT-TYPE
    SYNTAX      INTEGER 
                {
                    linetype-esf     (2),
                    linetype-d4      (3)
                }
    MAX-ACCESS  read-write
    STATUS      current
    DESCRIPTION
                "This variable indicates the variety of T1/E1
                interpretation of the  usage and error statistics.
				The values, in sequence, describe:

                TITLE:        SPECIFICATION:
                esf           Extended SuperFrame DS1
                d4            AT&T D4 format DS1"
                                
    ::= { dsxT1E1IfConfigLineEntry 4 }
    
dsxT1E1IfConfigLineCode OBJECT-TYPE
    SYNTAX      INTEGER 
                {
                    linecode-b8zs    (2),
                    linecode-ami     (5)
                }
    MAX-ACCESS  read-write
    STATUS      current
    DESCRIPTION
                "This variable describes the variety of Zero
                Code Suppression used on the link, which in
                turn affects a number of its characteristics.

                b8zs refers to the use of a specified pattern
                of normal bits and bipolar violations
                which are used to replace a sequence of eight
                zero bits.

                ami refers to a mode wherein no zero code
                suppression is present and the line encoding
                does not solve the problem directly. In this
                application, the higher layer must provide data
                which meets or exceeds the pulse density re-
                quirements, such as inverting HDLC data."

    ::= { dsxT1E1IfConfigLineEntry 5 }
    
dsxT1E1IfConfigLBO OBJECT-TYPE
    SYNTAX      INTEGER 
                {
                    lbo-zero-db (1),
                    lbo-75-db   (2),
                    lbo-15-db   (3),
                    lbo-225-db  (4)
                }
    MAX-ACCESS  read-write
    STATUS      current
    DESCRIPTION
               "Signal attenuation at 772 kHz
                lbo-zero-db     carrier advised LBO code A 0.0 - 5.5 db
                lbo-75-db       carrier advised LBO code B 7.5 - 13.0 db
                lbo-15-db       carrier advised LBO code C 15.0 - 22.0 db
                This variable can be set only for CSU linemode"
    ::= { dsxT1E1IfConfigLineEntry 6 }
    
dsxT1E1IfConfigCableLength OBJECT-TYPE
    SYNTAX      INTEGER 
                {
                    cable-length-0-133        (1),
                    cable-length-133-266      (2),
                    cable-length-266-399      (3),
                    cable-length-399-533      (4),
                    cable-length-533-655      (5)
                }
    MAX-ACCESS  read-write
    STATUS      current
    DESCRIPTION
            "This variable specifies the length of the 
			cable  in feet."
    ::= { dsxT1E1IfConfigLineEntry 7 }
    
dsxT1E1IfConfigRaiAlarm OBJECT-TYPE
    SYNTAX      INTEGER
                {
                    rai-gen-enable      (1),
                    rai-det-enable      (2),
                    rai-gen-det-enable   (3),
                    rai-disable         (4)
                }
    MAX-ACCESS  read-write
    STATUS      current
    DESCRIPTION
            "Configurition of Remote Alarm Indication 
			 Alarm generation and detection."
    ::= { dsxT1E1IfConfigLineEntry 8 }

dsxT1E1IfConfigTransmitClock OBJECT-TYPE
    SYNTAX      INTEGER
                {
                    timing-line     (1),
                    timing-internal    (2)
                }
    MAX-ACCESS  read-write
    STATUS      current
    DESCRIPTION
               "The source of Transmit Clock.
   
                 'timing-line' indicates that the recovered  re-
                ceive clock is used as the transmit clock.

                 'timing-internal' indicates  that  a  local  clock
                source is used."

    ::= { dsxT1E1IfConfigLineEntry 9 }

dsxT1E1IfConfigTimeSlotMap OBJECT-TYPE
    SYNTAX      OCTET STRING (SIZE (4) )
    MAX-ACCESS  read-only
    STATUS      current
    DESCRIPTION
               "Time slot map of the  T1/E1 line that are being used
				if it is used corresponding bit position is set."
    ::= { dsxT1E1IfConfigLineEntry 10 }

dsxT1E1IfCircuitId  OBJECT-TYPE
    SYNTAX         DisplayString
    MAX-ACCESS     read-write
    STATUS         current
    DESCRIPTION    ""
    ::= { dsxT1E1IfConfigLineEntry 11 }

dsxT1E1IfContactInfo  OBJECT-TYPE
    SYNTAX            DisplayString
    MAX-ACCESS        read-write
    STATUS            current
    DESCRIPTION       ""
    ::= { dsxT1E1IfConfigLineEntry 12 }

dsxT1E1IfDescription  OBJECT-TYPE
    SYNTAX            DisplayString
    MAX-ACCESS        read-write
    STATUS            current
    DESCRIPTION       ""
    ::= { dsxT1E1IfConfigLineEntry 13 }



-- DSX T1/E1 interface FDL configuration table
-- This table is applicable for T1 lines that are in ESF mode

dsxT1E1IfConfigFdlTable OBJECT-TYPE
    SYNTAX      SEQUENCE OF DsxT1E1IfConfigFdlEntry
    MAX-ACCESS  not-accessible
    STATUS      current
    DESCRIPTION
            "A list of T1/E1 interface currently configured."
    ::= { dsxT1E1IfConfigGroup 2 }

dsxT1E1IfConfigFdlEntry OBJECT-TYPE
    SYNTAX      DsxT1E1IfConfigFdlEntry
    MAX-ACCESS  not-accessible
    STATUS      current
    DESCRIPTION
         "Configurable Facility Data Link (FDL) field for 
		enable/disable the FDL utility on T1/E1 interface."
    AUGMENTS { dsxT1E1IfConfigLineEntry }
    ::= { dsxT1E1IfConfigFdlTable 1 }

DsxT1E1IfConfigFdlEntry ::=
    SEQUENCE {
        dsxT1E1IfConfigFdl               INTEGER,
        dsxT1E1IfConfigFdlCsuDsuType     INTEGER
    }

dsxT1E1IfConfigFdl      OBJECT-TYPE
    SYNTAX      INTEGER
                {
                    fdl-ansi-only    (1),
                    fdl-att-only     (2),
                    fdl-ansi-att     (3)
                }
    MAX-ACCESS  read-write
    STATUS      current
    DESCRIPTION 
			"The configuration FDL type 
				fdl-ansi-only - only supports ANSI FDL ,
				fdl-att-only    only supports ATT FDL,
				fdl-ansi-att     supports both ANSI and ATT FDL."

    ::= { dsxT1E1IfConfigFdlEntry 1 }

dsxT1E1IfConfigFdlCsuDsuType OBJECT-TYPE
    SYNTAX      INTEGER
                {
                    fdl-csu     (1),
                    fdl-dsu     (2),
                    fdl-csudsu  (3)
                }
    MAX-ACCESS  read-write
    STATUS      current
    DESCRIPTION 
				"The configuration of the type of equipment
					fdl-csu - responds to only CSU FDL requests
					fdl-dsu - responds to only DSU FDL requests
					fdl-csudsu - responds to both CSU and DSU requests."

    ::= { dsxT1E1IfConfigFdlEntry 2 }

-- DSX T1/E1 interface alarm configuration table

dsxT1E1IfAlarmConfigGroup OBJECT IDENTIFIER ::= {dsxT1E1IfConfigGroup 3 }

-- DSX T1/E1 Alarm Threshold Configuration Table
-- In order to configure a alarm Threshold, all the columns are mandatory
-- and failure to proide all the columns will result in badValue Error
   
dsxT1E1IfAlarmThresholdConfigTable OBJECT-TYPE
    SYNTAX      SEQUENCE OF DsxT1E1IfAlarmThresholdConfigEntry
    MAX-ACCESS  not-accessible
    STATUS      current
    DESCRIPTION
            "A list of T1/E1 interface alarm threshold configuration
			parameters."
    ::= { dsxT1E1IfAlarmConfigGroup 1 }

dsxT1E1IfAlarmThresholdConfigEntry OBJECT-TYPE
    SYNTAX      DsxT1E1IfAlarmThresholdConfigEntry
    MAX-ACCESS  not-accessible
    STATUS      current
    DESCRIPTION
            "An entry containing alarm configuration parameters 
			for each  T1/E1 interface.  "
    INDEX { dsxT1E1IfIndex, dsxT1E1IfAlarmThresholdConfigIndex }
    ::= { dsxT1E1IfAlarmThresholdConfigTable 1 }

DsxT1E1IfAlarmThresholdConfigEntry ::=
    SEQUENCE {
        dsxT1E1IfAlarmThresholdConfigIndex             INTEGER,
        dsxT1E1IfAlarmThresholdConfigObject            INTEGER,
        dsxT1E1IfAlarmThresholdConfigSamplingInterval  INTEGER,
        dsxT1E1IfAlarmThresholdConfigSampleType        INTEGER,
        dsxT1E1IfAlarmThresholdConfigStartupType       TruthValue,
        dsxT1E1IfAlarmThresholdConfigRisingThreshold   INTEGER,
        dsxT1E1IfAlarmThresholdConfigFallingThreshold  INTEGER
    }


dsxT1E1IfAlarmThresholdConfigIndex OBJECT-TYPE
    SYNTAX      INTEGER
    MAX-ACCESS  not-accessible
    STATUS      current
    DESCRIPTION
            "Index of the Threshold Alarms 1 - 10."
    ::= { dsxT1E1IfAlarmThresholdConfigEntry 1 }

dsxT1E1IfAlarmThresholdConfigObject OBJECT-TYPE
    SYNTAX      INTEGER 
                {
                   te1-object-eev (1),
                   te1-object-es  (2),
                   te1-object-uas (3),
                   te1-object-bes (4),
                   te1-object-ses (5),
                   te1-object-lofc (6),
                   te1-object-css (7),
                   te1-object-bpv (8),
                   te1-object-oof (9),
                   te1-object-crc (10)
                }
    MAX-ACCESS  read-write
    STATUS      current
    DESCRIPTION
            "Threshold alarm - variables being monitored."
    ::= { dsxT1E1IfAlarmThresholdConfigEntry 2 }

dsxT1E1IfAlarmThresholdConfigSamplingInterval OBJECT-TYPE
    SYNTAX      INTEGER (1..65535)
    MAX-ACCESS  read-write
    STATUS      current
    DESCRIPTION
            "Sampling Interval is the time between each sampling 
			period."
    ::= { dsxT1E1IfAlarmThresholdConfigEntry 3 }

dsxT1E1IfAlarmThresholdConfigSampleType OBJECT-TYPE
    SYNTAX      INTEGER
                {
                    sample-absolute     (1),
                    sample-delta        (2)
                }
    MAX-ACCESS  read-write
    STATUS      current
    DESCRIPTION
            "Threshold Alarm: Sampling type 
			sample-absolute - compares the monitored variable value
						 againist the  thresholds,
			sample-delta - compares the monitored variable value change
							from previous interval against thresholds."
    ::= { dsxT1E1IfAlarmThresholdConfigEntry 4 }

dsxT1E1IfAlarmThresholdConfigStartupType OBJECT-TYPE
    SYNTAX      TruthValue
    MAX-ACCESS  read-write
    STATUS      current
    DESCRIPTION
            "Threshold Alarm :if TRUE the first sample will be
			ignored if thresholds are crossed."
    ::= { dsxT1E1IfAlarmThresholdConfigEntry 5 }

dsxT1E1IfAlarmThresholdConfigRisingThreshold OBJECT-TYPE
    SYNTAX      INTEGER
    MAX-ACCESS  read-write
    STATUS      current
    DESCRIPTION
            "Threshold Alarm: Rising threshold limit  "
    ::= { dsxT1E1IfAlarmThresholdConfigEntry 6 }

dsxT1E1IfAlarmThresholdConfigFallingThreshold OBJECT-TYPE
    SYNTAX      INTEGER
    MAX-ACCESS  read-write
    STATUS      current
    DESCRIPTION
            "Threshold Alarm: Falling threshold limit "
    ::= { dsxT1E1IfAlarmThresholdConfigEntry 7 }



-- DSX T1/E1 interface Test configuration table

dsxT1E1IfTestConfigTable OBJECT-TYPE
    SYNTAX      SEQUENCE OF DsxT1E1IfTestConfigEntry
    MAX-ACCESS  not-accessible
    STATUS      current
    DESCRIPTION
            "A list of T1/E1 interface test configuration parameters."
    ::= { dsxT1E1IfConfigGroup 4 }

dsxT1E1IfTestConfigEntry OBJECT-TYPE
    SYNTAX      DsxT1E1IfTestConfigEntry
    MAX-ACCESS  not-accessible
    STATUS      current
    DESCRIPTION
            "An entry containing test configuration parameters for each
			currently T1/E1 interface."
    AUGMENTS { dsxT1E1IfConfigLineEntry }
    ::= { dsxT1E1IfTestConfigTable 1 }

DsxT1E1IfTestConfigEntry ::=
    SEQUENCE {
        dsxT1E1IfTestConfigType               INTEGER,
        dsxT1E1IfTestConfigTime               Unsigned32,
        dsxT1E1IfTestConfigPattern            INTEGER,
        dsxT1E1IfTestConfigLoopCode           INTEGER
    }

dsxT1E1IfTestConfigType OBJECT-TYPE
    SYNTAX      INTEGER
                {
                    no-test                  (1),
                    payload-loopback-test    (2),
                    line-loopback-test       (3),
                    pattern-test             (6),
                    remote-lpup-test         (7),
                    remote-lpdn-test         (8)
                }
    MAX-ACCESS  read-write
    STATUS      current
    DESCRIPTION
            "Test type. Specifies the type of test to execute on this
			T1/E1 interface.
             To perform no-test, payload-loopback-test, line-loopback-test
             only TestType is mandatory.
             To perform pattern-test, ConfigTime and ConfigPattern are
             mandatory. 
             To perform remote-lpup-test and remote-lpdn-test, ConfigLoopCode 
             is mandatory"
    ::= { dsxT1E1IfTestConfigEntry 1 }
    
dsxT1E1IfTestConfigTime OBJECT-TYPE
    SYNTAX      Unsigned32
    MAX-ACCESS  read-write
    STATUS      current
    DESCRIPTION
            "Test time. when set to 0, test time is unlimited.
			Otherwise  duration of test,  specified in seconds."
    ::= { dsxT1E1IfTestConfigEntry 2 }
    
dsxT1E1IfTestConfigPattern OBJECT-TYPE
    SYNTAX      INTEGER 
                {
                    pattern-all-ones            (1),
                    pattern-all-zeros           (2),
                    reserved1                   (3),
                    reserved2                   (4),
                    reserved3                   (5),
                    reserved4                   (6),
                    reserved5                   (7),
                    reserved6                   (8),
                    reserved7                   (9),
                    reserved9                   (10),
                    reserved10                  (11),
                    reserved11                  (12),
                    pattern-215minus1           (13),
                    reserved12                  (14),
                    pattern-qrw                 (15),
                    pattern-223minus1           (16)
                }
    MAX-ACCESS  read-write
    STATUS      current
    DESCRIPTION
            "Bit Pattern type used in testing T1/E1 for Pattern Test."
    ::= { dsxT1E1IfTestConfigEntry 3 }
    
dsxT1E1IfTestConfigLoopCode OBJECT-TYPE
    SYNTAX      INTEGER
                {
                    loopcode-none             (1),
                    loopcode-line-standard    (2),
                    loopcode-line-alternate   (3),
                    loopcode-line-ATTFDL      (4),
                    loopcode-payload-ATTFDL   (6),
                    loopcode-payload-ansiFDL  (7)
                }
    MAX-ACCESS  read-write
    STATUS      current
    DESCRIPTION
            " Type of loopcode is used for loopback test."
    ::= { dsxT1E1IfTestConfigEntry 4 }

-- DSX T1/E1 interface status Group definitions

dsxT1E1IfStatusTable OBJECT-TYPE
    SYNTAX      SEQUENCE OF DsxT1E1IfStatusEntry
    MAX-ACCESS  not-accessible
    STATUS      current
    DESCRIPTION
            "A list of T1/E1 interface status entries"
    ::= { dsxT1E1IfStatusGroup 1 }

dsxT1E1IfStatusEntry OBJECT-TYPE
    SYNTAX      DsxT1E1IfStatusEntry
    MAX-ACCESS  not-accessible
    STATUS      current
    DESCRIPTION
            "An entry containing status entry for each currently active 
            T1/E1 interface."
    AUGMENTS { dsxT1E1IfConfigLineEntry }
    ::= { dsxT1E1IfStatusTable 1 }

DsxT1E1IfStatusEntry ::=
    SEQUENCE {
        dsxT1E1IfStatusLineStatus     BITS,
        dsxT1E1IfStatusTransmitClock  INTEGER
    }

dsxT1E1IfStatusLineStatus OBJECT-TYPE
    SYNTAX      BITS
                {
                    reserved1            (0),
                    reserved2            (1),
                    rraiStatus           (2),
                    traiStatus           (3),
                    rlosStatus           (4),
                    risStatus            (5),
                    rexzStatus           (6),
                    reserved3            (7),
                    reserved4            (8),
                    reserved5            (9),
                    lorcStatus           (10),
                    tpdeStatus           (11),
                    reserved6            (12),
                    reserved7            (13),
                    sendLineCode         (14),
                    sendPayLoadCode      (15),
                    sendResetCode        (16),
                    sendTE1Code          (17),
                    sendPattern          (18),
                    reserved8            (19),
                    rcvTestCode          (20),
                    reserved9            (21),
                    reserved10           (22),
                    reserved11           (23),
                    loopbackStatus       (24),
                    reserved12           (25),
                    reserved13           (26),
                    taisStatus           (27),
                    raisStatus           (28),
                    reserved14           (29),
                    rlofStatus           (30),
                    reserved15           (31)
                }
    MAX-ACCESS  read-only
    STATUS      current
    DESCRIPTION
            "The summary of the status
	     RRAIStatus       - Recieve RAI (Recieve Alarm Indication),
	     TRAIStatus       - Transmit RAI ,
	     RLOSStatus       - Recieve Loss Of Sync,
	     RISStatus        - Recieve Idle Signal
	     REXZStatus       - Recieve Excessive Zeros,
	     LORCStatus       - Loss Of Recive Clock (LORC),
	     TDEStatus        - transmit pulse density,
             SendLineCode     - transmit linecode
             SendPayLoadCode  - transmit paylode code
             SendResetCode    - transmit reset code,
             SendTE1Code      - transmit T1/E1 linecode,
             SendPattern      - transmit T1/E1 Pattern,
	     RcvTestCode      - recive test code,
	     LoopbackStatus   - Status of Loop back,
	     TAISStatus       - Transmit Alarm Indication Siganl,
             RAISStatus       - Recieve Alarm Indication Signal,
	     LOFStatus        - Loss Of Frame.  "
    ::= { dsxT1E1IfStatusEntry 1 }

dsxT1E1IfStatusTransmitClock OBJECT-TYPE
    SYNTAX      INTEGER
                {
                    timing-line     (1),
                    timing-internal (2)
                }
    MAX-ACCESS  read-only
    STATUS      current
    DESCRIPTION
            "The source of Tranmit Clock.
   
                 'timing-line' indicates that the recovered  re-
                ceive clock is used as the transmit clock.

                 'timing-internal' indicates  that  a  local  clock
                source is used."

    ::= { dsxT1E1IfStatusEntry 2 }
    
-- DSX T1/E1 interface alarm status Group definitions

dsxT1E1IfAlarmStatusTable OBJECT-TYPE
    SYNTAX      SEQUENCE OF DsxT1E1IfAlarmStatusEntry
    MAX-ACCESS  not-accessible
    STATUS      current
    DESCRIPTION
            "A list of T1/E1 interface alarm status entries"
    ::= { dsxT1E1IfStatusGroup 2 }

dsxT1E1IfAlarmStatusEntry OBJECT-TYPE
    SYNTAX      DsxT1E1IfAlarmStatusEntry
    MAX-ACCESS  not-accessible
    STATUS      current
    DESCRIPTION
            "An entry containing alarm status  for each T1/E1 interface."
    AUGMENTS { dsxT1E1IfConfigLineEntry }
    ::= { dsxT1E1IfAlarmStatusTable 1 }

DsxT1E1IfAlarmStatusEntry ::=
    SEQUENCE {
        dsxT1E1IfAlarmStatusAlarmStatus       BITS,
        dsxT1E1IfAlarmStatusThresholdStatus   BITS
    }

dsxT1E1IfAlarmStatusAlarmStatus OBJECT-TYPE
    SYNTAX      BITS
                {
                    rraiAlarm           (0),
                    traiAlarm           (1),
                    raisAlarm           (2),
                    taisAlarm           (3),
                    rlofAlarm           (4),
                    rlosAlarm           (5),
                    loopbackStateAlarm  (6),
                    rcvTestCode         (7),
                    risAlarm            (8),
                    rexzAlarm           (9),
                    rfebeAlarm          (10),
                    rpeAlarm            (11),
                    rcpeAlarm           (12),
                    lorcAlarm           (13),
                    tpdeAlarm           (14),
                    tfebeAlarm          (15),
                    ibTestAlarm         (16)
                }
    MAX-ACCESS  read-only
    STATUS      current
    DESCRIPTION
            "Alarm Status of T1/E1 interface.
			RRAI - Recieve Rx Alarm Indication,
			TRAI - Transmit Rx Alarm Indication,
			RAIS - Recieve Alarm Indication Signal,
			TAIS - Transmit Alarm Indication Signal,
			RLOF - Recieve Loss Of Frame,
			RLOS - Recieve Loss Of Signal,
			Loopback - if looped back state is true,
			RIS  - Recieve Idle Signal,
			REXZ - Recieve Excessive Zeros,
			RFEBE - Recieve Far End Block Error,
			RPE  - Recieve Parity Error,
			RCPE - Recieve C-Parity Error,
			LORC - Loss Of Recieve Clock,
			TPDE -  Transmit Pulse DEnsity,
			TFEBE - Transmit Far End Block Error,
			ibTest - InBand Test running if true."
			 
	::= { dsxT1E1IfAlarmStatusEntry 1 }

dsxT1E1IfAlarmStatusThresholdStatus OBJECT-TYPE
    SYNTAX      BITS
                {
                    threshold1  (0),
                    threshold2  (1),
                    threshold3  (2),
                    threshold4  (3),
                    threshold5  (4),
                    threshold6  (5),
                    threshold7  (6),
                    threshold8  (7),
                    threshold9  (8),
                    threshold10 (9)
                }
    MAX-ACCESS  read-only
    STATUS      current
    DESCRIPTION
            "Status of the user configurable threshold Alarms
			1 means present."
    ::= { dsxT1E1IfAlarmStatusEntry 2 }

-- DSX T1/E1 interface test status Group definitions

dsxT1E1IfTestStatusTable OBJECT-TYPE
    SYNTAX      SEQUENCE OF DsxT1E1IfTestStatusEntry
    MAX-ACCESS  not-accessible
    STATUS      current
    DESCRIPTION
            "A list of T1/E1 interface test status entries"
    ::= { dsxT1E1IfStatusGroup 3 }

dsxT1E1IfTestStatusEntry OBJECT-TYPE
    SYNTAX      DsxT1E1IfTestStatusEntry
    MAX-ACCESS  not-accessible
    STATUS      current
    DESCRIPTION
            "An entry containing  test status entry for each 
            T1/E1 interface."
    AUGMENTS { dsxT1E1IfConfigLineEntry }
    ::= { dsxT1E1IfTestStatusTable 1 }

DsxT1E1IfTestStatusEntry ::=
    SEQUENCE {
        dsxT1E1IfTestStatusTestType           INTEGER,
        dsxT1E1IfTestStatusTestTime           Unsigned32,
        dsxT1E1IfTestStatusTestState          INTEGER,
        dsxT1E1IfTestStatusTestPattern        INTEGER,
        dsxT1E1IfTestStatusLockedSeconds      Unsigned32,
        dsxT1E1IfTestStatusSyncLossCount      Unsigned32,
        dsxT1E1IfTestStatusErrorCount         Unsigned32,
        dsxT1E1IfTestStatusLoopCode           INTEGER
    }
    
dsxT1E1IfTestStatusTestType OBJECT-TYPE
    SYNTAX      INTEGER 
                {
                    testtype-notest                    (1),
                    testtype-payload-loopback          (2),
                    testtype-line-loopback             (3),
                    testtype-pattern                   (6),
                    testtype-remote-lpup               (7),
                    testtype-remote-lpdn               (8)
                }
    MAX-ACCESS  read-only
    STATUS      current
    DESCRIPTION
            "Test type  initiated on T1/E1 line."
    ::= { dsxT1E1IfTestStatusEntry 1 }

dsxT1E1IfTestStatusTestTime OBJECT-TYPE
    SYNTAX      Unsigned32
    MAX-ACCESS  read-only
    STATUS      current
    DESCRIPTION
            "Time elapsed since the test started on T1/E1 line "
    ::= { dsxT1E1IfTestStatusEntry 2 }

dsxT1E1IfTestStatusTestState OBJECT-TYPE
    SYNTAX      INTEGER
                {
                    test-state-idle         (1),
                    test-state-searching    (2),
                    test-state-locked       (3),
                    test-state-relocked     (4),
                    test-state-inprogress   (5),
                    test-state-passed       (6),
                    test-state-failed       (7)
                }
    MAX-ACCESS  read-only
    STATUS      current
    DESCRIPTION
            "Current state of the running test on T1/E1 line "
    ::= { dsxT1E1IfTestStatusEntry 3 }

dsxT1E1IfTestStatusTestPattern OBJECT-TYPE
    SYNTAX      INTEGER
                {
                    pattern-all-ones            (1),
                    pattern-all-zeros           (2),
                    pattern-alternating         (3),
                    pattern-3in24               (4),
                    pattern-1in3                (5),
                    pattern-1in5                (6),
                    pattern-1in7                (7),
                    pattern-smartjack-lpup      (8),
                    pattern-smartjack-lpdown    (9),
                    pattern-user1               (10),
                    pattern-user2               (11),
                    pattern-29minus1            (12),
                    pattern-215minus1           (13),
                    pattern-220minus1           (14),
                    pattern-qrss                (15),
                    pattern-223minus1           (16)
                }
    MAX-ACCESS  read-only
    STATUS      current
    DESCRIPTION
            "Bit Pattern generated to test the T1/E1, only relevent to
			Pattern Test. "
    ::= { dsxT1E1IfTestStatusEntry 4 }

dsxT1E1IfTestStatusLockedSeconds OBJECT-TYPE
    SYNTAX      Unsigned32
    MAX-ACCESS  read-only
    STATUS      current
    DESCRIPTION
            "Count of seconds, during which the pattern is
				synchronized  "
    ::= { dsxT1E1IfTestStatusEntry 5 }

dsxT1E1IfTestStatusSyncLossCount OBJECT-TYPE
    SYNTAX      Unsigned32
    MAX-ACCESS  read-only
    STATUS      current
    DESCRIPTION
            " Counter for the pattern  synchronization losses "
    ::= { dsxT1E1IfTestStatusEntry 6 }

dsxT1E1IfTestStatusErrorCount OBJECT-TYPE
    SYNTAX      Unsigned32
    MAX-ACCESS  read-only
    STATUS      current
    DESCRIPTION
            "Counter for the Bit error during the test "
    ::= { dsxT1E1IfTestStatusEntry 7 }
    
dsxT1E1IfTestStatusLoopCode OBJECT-TYPE
    SYNTAX      INTEGER
                {
                    loopcode-none             (1),
                    loopcode-line-standard    (2),
                    loopcode-line-alternate   (3),
                    loopcode-line-ATTFDL      (4),
                    loopcode-payload-ATTFDL   (5),
                    loopcode-payload-ansiFDL  (6),
                    loopcode-v54              (7)
                }
    MAX-ACCESS  read-only
    STATUS      current
    DESCRIPTION
            "The loop codes transmitted on the T1/E1 interface
			Only relevent to the Remote LoopUp and Remote LoopDown tests."
    ::= { dsxT1E1IfTestStatusEntry 8 }
    
-- T1/E1 Last Test Result Table 

dsxT1E1IfLastTestResultTable OBJECT-TYPE
    SYNTAX      SEQUENCE OF DsxT1E1IfLastTestResultEntry
    MAX-ACCESS  not-accessible
    STATUS      current
    DESCRIPTION
            "A list of T1/E1 interface previous test status entries"
    ::= { dsxT1E1IfStatusGroup 4 }

dsxT1E1IfLastTestResultEntry OBJECT-TYPE
    SYNTAX      DsxT1E1IfLastTestResultEntry
    MAX-ACCESS  not-accessible
    STATUS      current
    DESCRIPTION
            "An entry containing previous test status entry for each
			T1/E1 interface."
    AUGMENTS { dsxT1E1IfConfigLineEntry }
    ::= { dsxT1E1IfLastTestResultTable 1 }

DsxT1E1IfLastTestResultEntry ::=
    SEQUENCE {
        dsxT1E1IfLastTestResultTestType           INTEGER,
        dsxT1E1IfLastTestResultTestTime           Unsigned32,
        dsxT1E1IfLastTestResultTestState          INTEGER,
        dsxT1E1IfLastTestResultTestPattern        INTEGER,
        dsxT1E1IfLastTestResultLockedSeconds      Unsigned32,
        dsxT1E1IfLastTestResultSyncLossCount      Unsigned32,
        dsxT1E1IfLastTestResultErrorCount         Unsigned32,
        dsxT1E1IfLastTestResultLoopCode           INTEGER
    }
    
dsxT1E1IfLastTestResultTestType OBJECT-TYPE
    SYNTAX      INTEGER 
                {
                    testtype-notest                    (1),
                    testtype-payload-loopback          (2),
                    testtype-line-loopback             (3),
                    testtype-pattern                   (6),
                    testtype-remote-lpup               (7),
                    testtype-remote-lpdn               (8)
                }
    MAX-ACCESS  read-only
    STATUS      current
    DESCRIPTION
            "Status of the previous test conducted on this T1/E1 interface,
			this field corresponds to Type of Test conducted"
    ::= { dsxT1E1IfLastTestResultEntry 1 }

dsxT1E1IfLastTestResultTestTime OBJECT-TYPE
    SYNTAX      Unsigned32
    MAX-ACCESS  read-only
    STATUS      current
    DESCRIPTION
            "Duration of the test conducted in previous test "
    ::= { dsxT1E1IfLastTestResultEntry 2 }

dsxT1E1IfLastTestResultTestState OBJECT-TYPE
    SYNTAX      INTEGER
                {
                    test-state-idle         (1),
                    test-state-searching    (2),
                    test-state-locked       (3),
                    test-state-relocked     (4),
                    test-state-inprogress   (5),
                    test-state-passed       (6),
                    test-state-failed       (7)
                }
    MAX-ACCESS  read-only
    STATUS      current
    DESCRIPTION
            " This field shows in which state previous test was 
			ended "
    ::= { dsxT1E1IfLastTestResultEntry 3 }

dsxT1E1IfLastTestResultTestPattern OBJECT-TYPE
    SYNTAX      INTEGER
                {
                    pattern-all-ones            (1),
                    pattern-all-zeros           (2),
                    pattern-alternating         (3),
                    pattern-3in24               (4),
                    pattern-1in3                (5),
                    pattern-1in5                (6),
                    pattern-1in7                (7),
                    pattern-smartjack-lpup      (8),
                    pattern-smartjack-lpdown    (9),
                    pattern-user1               (10),
                    pattern-user2               (11),
                    pattern-29minus1            (12),
                    pattern-215minus1           (13),
                    pattern-220minus1           (14),
                    pattern-qrss                (15),
                    pattern-223minus1           (16)
                }
    MAX-ACCESS  read-only
    STATUS      current
    DESCRIPTION
            "If the previous test conducted was  pattern test, This
			field will have type of pattern used to test. "
    ::= { dsxT1E1IfLastTestResultEntry 4 }

dsxT1E1IfLastTestResultLockedSeconds OBJECT-TYPE
    SYNTAX      Unsigned32
    MAX-ACCESS  read-only
    STATUS      current
    DESCRIPTION
            "Duration in which signal was synchronized while under test. "
    ::= { dsxT1E1IfLastTestResultEntry 5 }

dsxT1E1IfLastTestResultSyncLossCount OBJECT-TYPE
    SYNTAX      Unsigned32
    MAX-ACCESS  read-only
    STATUS      current
    DESCRIPTION
            "Counter for the pattern  synchronization losses in 
			previous test results."
    ::= { dsxT1E1IfLastTestResultEntry 6 }

dsxT1E1IfLastTestResultErrorCount OBJECT-TYPE
    SYNTAX      Unsigned32
    MAX-ACCESS  read-only
    STATUS      current
    DESCRIPTION
            "Counter for the Bit error during the test in previous test"
    ::= { dsxT1E1IfLastTestResultEntry 7 }
    
dsxT1E1IfLastTestResultLoopCode OBJECT-TYPE
    SYNTAX      INTEGER
                {
                    loopcode-none             (1),
                    loopcode-line-standard    (2),
                    loopcode-line-alternate   (3),
                    loopcode-line-ATTFDL      (4),
                    loopcode-payload-ATTFDL   (5),
                    loopcode-payload-ansiFDL  (6),
                    loopcode-v54              (7)
                }
    MAX-ACCESS  read-only
    STATUS      current
    DESCRIPTION
            "Type loopcode used to put interface under remote loop back"
    ::= { dsxT1E1IfLastTestResultEntry 8 }
    

-- DSX T1/E1 Stats Group Definitions

-- T1/E1 ArchiveValidIntervals table

-- Table to store the valid intervals of archive stats tables

dsxT1E1IfArchiveStatsValidIntervalsTable OBJECT-TYPE
    SYNTAX      SEQUENCE OF DsxT1E1IfArchiveStatsValidIntervalsEntry
    MAX-ACCESS  not-accessible
    STATUS      current
    DESCRIPTION
            "Number of intervals available in archive statistics table for 
				this T1/E1 interface"
    ::= { dsxT1E1IfStatsGroup 1 }

dsxT1E1IfArchiveStatsValidIntervalsEntry  OBJECT-TYPE
    SYNTAX      DsxT1E1IfArchiveStatsValidIntervalsEntry
    MAX-ACCESS  not-accessible
    STATUS      current
    DESCRIPTION
            "An entry containing statistics entry for each 
            T1/E1 interface."
    AUGMENTS { dsxT1E1IfConfigLineEntry }
    ::= { dsxT1E1IfArchiveStatsValidIntervalsTable 1 }

DsxT1E1IfArchiveStatsValidIntervalsEntry ::=
    SEQUENCE {
        dsxT1E1IfAnsiArchiveStatsValidIntervals        Unsigned32, 
        dsxT1E1IfAttArchiveStatsValidIntervals         Unsigned32, 
        dsxT1E1IfIetfArchiveStatsValidIntervals        Unsigned32, 
        dsxT1E1IfUserTotalStatsValidDays               Unsigned32, 
        dsxT1E1IfUserArchiveStatsValidIntervals        INTEGER
    }
    
dsxT1E1IfAnsiArchiveStatsValidIntervals OBJECT-TYPE
    SYNTAX   	Unsigned32
    MAX-ACCESS  read-only
    STATUS      current
    DESCRIPTION
            "Total number of archived statistics collected according to
			ANSI standards."
    ::= { dsxT1E1IfArchiveStatsValidIntervalsEntry 1 }
    
dsxT1E1IfAttArchiveStatsValidIntervals OBJECT-TYPE
    SYNTAX   	Unsigned32
    MAX-ACCESS  read-only
    STATUS      current
    DESCRIPTION
            "Total number of archived statistics collected according to
			ATT standards."
    ::= { dsxT1E1IfArchiveStatsValidIntervalsEntry 2 }
    
dsxT1E1IfIetfArchiveStatsValidIntervals OBJECT-TYPE
    SYNTAX   	Unsigned32
    MAX-ACCESS  read-only
    STATUS      current
    DESCRIPTION
            " Total number of archived statistics collected according to
			IETF standards."
    ::= { dsxT1E1IfArchiveStatsValidIntervalsEntry 3 }
    
dsxT1E1IfUserTotalStatsValidDays OBJECT-TYPE
    SYNTAX   	Unsigned32
    MAX-ACCESS  read-only
    STATUS      current
    DESCRIPTION
            "Total number of days archived statistics collected according to
			User definations."
    ::= { dsxT1E1IfArchiveStatsValidIntervalsEntry 4 }
    
dsxT1E1IfUserArchiveStatsValidIntervals OBJECT-TYPE
    SYNTAX   	INTEGER
    MAX-ACCESS  read-write
    STATUS      current
    DESCRIPTION
            " User Archive Stats Valid Interval.
              Setting this variable to 0 will clear
              all the User Statistics Tables "
    ::= { dsxT1E1IfArchiveStatsValidIntervalsEntry 5 }


-- DSX T1/E1 Stats Group Definitions

dsxT1E1IfAnsiStatsGroup   OBJECT IDENTIFIER   ::= { dsxT1E1IfStatsGroup 2 }
dsxT1E1IfAttStatsGroup    OBJECT IDENTIFIER   ::= { dsxT1E1IfStatsGroup 3 }
dsxT1E1IfIetfStatsGroup   OBJECT IDENTIFIER   ::= { dsxT1E1IfStatsGroup 4 }
dsxT1E1IfUserStatsGroup   OBJECT IDENTIFIER   ::= { dsxT1E1IfStatsGroup 5 }

-- DSX T1/E1 ANSI Stats Group definitions

-- ANSI Current Stats table

dsxT1E1IfAnsiCurrentStatsTable OBJECT-TYPE
    SYNTAX      SEQUENCE OF DsxT1E1IfAnsiCurrentStatsEntry
    MAX-ACCESS  not-accessible
    STATUS      current
    DESCRIPTION
            "Statistics collected according ANSI standards 
			 and collected in current 900 secondss period."
    ::= { dsxT1E1IfAnsiStatsGroup 1 }

dsxT1E1IfAnsiCurrentStatsEntry  OBJECT-TYPE
    SYNTAX      DsxT1E1IfAnsiCurrentStatsEntry
    MAX-ACCESS  not-accessible
    STATUS      current
    DESCRIPTION
            "Statistics collected in current 900 secs ( i.e. 15 mins) kept 
			in this table"
    AUGMENTS { dsxT1E1IfConfigLineEntry }
    ::= { dsxT1E1IfAnsiCurrentStatsTable 1 }

DsxT1E1IfAnsiCurrentStatsEntry ::=
    SEQUENCE {
        dsxT1E1IfAnsiCurrentStatsUASState        TruthValue,
        dsxT1E1IfAnsiCurrentStatsTimeInCurrent   Unsigned32,
        dsxT1E1IfAnsiCurrentPathStatsCV          Unsigned32,
        dsxT1E1IfAnsiCurrentPathStatsES          Unsigned32,
        dsxT1E1IfAnsiCurrentPathStatsSES         Unsigned32,
        dsxT1E1IfAnsiCurrentPathStatsSAS         Unsigned32,
        dsxT1E1IfAnsiCurrentPathStatsCSS         Unsigned32,
        dsxT1E1IfAnsiCurrentPathStatsUAS         Unsigned32,
        dsxT1E1IfAnsiCurrentLineStatsCV          Unsigned32,
        dsxT1E1IfAnsiCurrentLineStatsES          Unsigned32,
        dsxT1E1IfAnsiCurrentLineStatsSES         Unsigned32
    }
    
dsxT1E1IfAnsiCurrentStatsUASState OBJECT-TYPE
    SYNTAX      TruthValue
    MAX-ACCESS  read-only
    STATUS      current
    DESCRIPTION
        "The State of T1/E1 line according to ANSI standards"
    ::= { dsxT1E1IfAnsiCurrentStatsEntry 1 }

dsxT1E1IfAnsiCurrentStatsTimeInCurrent OBJECT-TYPE
    SYNTAX      Unsigned32
    MAX-ACCESS  read-only
    STATUS      current
    DESCRIPTION
        "The number of seconds that have elapsed since the
         beginning of the  current error measurement period"
    ::= { dsxT1E1IfAnsiCurrentStatsEntry 2 }

dsxT1E1IfAnsiCurrentPathStatsCV OBJECT-TYPE
    SYNTAX      Unsigned32
    MAX-ACCESS  read-only
    STATUS      current
    DESCRIPTION
            "The number of Path Coding  Violations  encoun-
                tered  by  a T1/E1 interface  in the current 15
                minute interval. "
    ::= { dsxT1E1IfAnsiCurrentStatsEntry 3 }

dsxT1E1IfAnsiCurrentPathStatsES OBJECT-TYPE
    SYNTAX      Unsigned32
    MAX-ACCESS  read-only
    STATUS      current
    DESCRIPTION
            "The number of Errored Seconds, encountered  by
                a T1/E1 interface in the current 15 minute inter-
                val. "
    ::= { dsxT1E1IfAnsiCurrentStatsEntry 4 }

dsxT1E1IfAnsiCurrentPathStatsSES OBJECT-TYPE
    SYNTAX      Unsigned32
    MAX-ACCESS  read-only
    STATUS      current
    DESCRIPTION
            "The number of Severely Errored Seconds encoun-
                tered  by  a  T1/E1  interface  in the current 15
                minute interval. "
    ::= { dsxT1E1IfAnsiCurrentStatsEntry 5 }

dsxT1E1IfAnsiCurrentPathStatsSAS OBJECT-TYPE
    SYNTAX      Unsigned32
    MAX-ACCESS  read-only
    STATUS      current
    DESCRIPTION
                "Seconds with Severe Alarms"
    ::= { dsxT1E1IfAnsiCurrentStatsEntry 6 }

dsxT1E1IfAnsiCurrentPathStatsCSS OBJECT-TYPE
    SYNTAX      Unsigned32
    MAX-ACCESS  read-only
    STATUS      current
    DESCRIPTION
            "The number of Controlled Slip Seconds  encoun-
                tered  by  a  T1/E1  interface  in the current 15
                minute interval. "
    ::= { dsxT1E1IfAnsiCurrentStatsEntry 7 }

dsxT1E1IfAnsiCurrentPathStatsUAS OBJECT-TYPE
    SYNTAX      Unsigned32
    MAX-ACCESS  read-only
    STATUS      current
    DESCRIPTION
            "The number of Unavailable Seconds  encountered
                by a T1/E1 interface in the current 15 minute in-
                terval. "
    ::= { dsxT1E1IfAnsiCurrentStatsEntry 8 }


dsxT1E1IfAnsiCurrentLineStatsCV OBJECT-TYPE
    SYNTAX      Unsigned32
    MAX-ACCESS  read-only
    STATUS      current
    DESCRIPTION
            "The number of Line Coding  Violations  encoun-
                tered  by  a  T1/E1  interface  in the current 15
                minute interval. "
    ::= { dsxT1E1IfAnsiCurrentStatsEntry 9 }

dsxT1E1IfAnsiCurrentLineStatsES OBJECT-TYPE
    SYNTAX      Unsigned32
    MAX-ACCESS  read-only
    STATUS      current
    DESCRIPTION
            "The number of Errored Seconds, encountered  by
                a T1/E1 interface in the current 15 minute inter-
                val. "
    ::= { dsxT1E1IfAnsiCurrentStatsEntry 10 }

dsxT1E1IfAnsiCurrentLineStatsSES OBJECT-TYPE
    SYNTAX      Unsigned32
    MAX-ACCESS  read-only
    STATUS      current
    DESCRIPTION
            "The number of Severely Errored Seconds encoun-
                tered  by  a  T1/E1  interface  in the current 15
                minute interval. "
    ::= { dsxT1E1IfAnsiCurrentStatsEntry 11 }


-- ANSI Total Path stats table

dsxT1E1IfAnsiTotalStatsTable OBJECT-TYPE
    SYNTAX      SEQUENCE OF DsxT1E1IfAnsiTotalStatsEntry
    MAX-ACCESS  not-accessible
    STATUS      current
    DESCRIPTION
            "Table for the Total Statistics over past 24 hrs"
    ::= { dsxT1E1IfAnsiStatsGroup 2 }

dsxT1E1IfAnsiTotalStatsEntry  OBJECT-TYPE
    SYNTAX      DsxT1E1IfAnsiTotalStatsEntry
    MAX-ACCESS  not-accessible
    STATUS      current
    DESCRIPTION
            "Table for the Total Statistics over past 24 hrs"
    AUGMENTS { dsxT1E1IfConfigLineEntry }
    ::= { dsxT1E1IfAnsiTotalStatsTable 1 }

DsxT1E1IfAnsiTotalStatsEntry ::=
    SEQUENCE {
        dsxT1E1IfAnsiTotalPathStatsCV          Unsigned32,
        dsxT1E1IfAnsiTotalPathStatsES          Unsigned32,
        dsxT1E1IfAnsiTotalPathStatsSES         Unsigned32,
        dsxT1E1IfAnsiTotalPathStatsSAS         Unsigned32,
        dsxT1E1IfAnsiTotalPathStatsCSS         Unsigned32,
        dsxT1E1IfAnsiTotalPathStatsUAS         Unsigned32,
        dsxT1E1IfAnsiTotalLineStatsCV          Unsigned32,
        dsxT1E1IfAnsiTotalLineStatsES          Unsigned32,
        dsxT1E1IfAnsiTotalLineStatsSES         Unsigned32
    }
    
dsxT1E1IfAnsiTotalPathStatsCV OBJECT-TYPE
    SYNTAX      Unsigned32
    MAX-ACCESS  read-only
    STATUS      current
    DESCRIPTION
            "The number of Path Coding  Violations  encoun-
                tered  by  a  T1/E1  interface in the previous 24
                hour interval. "
    ::= { dsxT1E1IfAnsiTotalStatsEntry 1 }

dsxT1E1IfAnsiTotalPathStatsES OBJECT-TYPE
    SYNTAX      Unsigned32
    MAX-ACCESS  read-only
    STATUS      current
    DESCRIPTION
            "The number of Errored Seconds encountered by a
                T1/E1 interface in the previous 24 hour interval. "
    ::= { dsxT1E1IfAnsiTotalStatsEntry 2 }

dsxT1E1IfAnsiTotalPathStatsSES OBJECT-TYPE
    SYNTAX      Unsigned32
    MAX-ACCESS  read-only
    STATUS      current
    DESCRIPTION
            "The number of Severely Errored Seconds encoun-
                tered  by  a  T1/E1  interface in the previous 24
                hour interval. "
    ::= { dsxT1E1IfAnsiTotalStatsEntry 3 }

dsxT1E1IfAnsiTotalPathStatsSAS OBJECT-TYPE
    SYNTAX      Unsigned32
    MAX-ACCESS  read-only
    STATUS      current
    DESCRIPTION
                "Total No seconds with Severe Alarms in past 24 hrs"
    ::= { dsxT1E1IfAnsiTotalStatsEntry 4 }

dsxT1E1IfAnsiTotalPathStatsCSS OBJECT-TYPE
    SYNTAX      Unsigned32
    MAX-ACCESS  read-only
    STATUS      current
    DESCRIPTION
            "The number of Controlled Slip Seconds  encoun-
                tered  by  a  T1/E1  interface in the previous 24
                hour interval. "
    ::= { dsxT1E1IfAnsiTotalStatsEntry 5 }

dsxT1E1IfAnsiTotalPathStatsUAS OBJECT-TYPE
    SYNTAX      Unsigned32
    MAX-ACCESS  read-only
    STATUS      current
    DESCRIPTION
            "The number of Unavailable Seconds  encountered
                by  a T1/E1 interface in the previous 24 hour in-
                terval. "
    ::= { dsxT1E1IfAnsiTotalStatsEntry 6 }


dsxT1E1IfAnsiTotalLineStatsCV OBJECT-TYPE
    SYNTAX      Unsigned32
    MAX-ACCESS  read-only
    STATUS      current
    DESCRIPTION
            "The number of Line Coding  Violations  encoun-
                tered  by  a  T1/E1  interface in the previous 24
                hour interval. "
    ::= { dsxT1E1IfAnsiTotalStatsEntry 7 }

dsxT1E1IfAnsiTotalLineStatsES OBJECT-TYPE
    SYNTAX      Unsigned32
    MAX-ACCESS  read-only
    STATUS      current
    DESCRIPTION
            "The number of Errored Seconds encountered by a
                T1/E1 interface in the previous 24 hour interval. "
    ::= { dsxT1E1IfAnsiTotalStatsEntry 8 }

dsxT1E1IfAnsiTotalLineStatsSES OBJECT-TYPE
    SYNTAX      Unsigned32
    MAX-ACCESS  read-only
    STATUS      current
    DESCRIPTION
            "The number of Severely Errored Seconds encoun-
                tered  by  a  T1/E1  interface in the previous 24
                hour interval. "
    ::= { dsxT1E1IfAnsiTotalStatsEntry 9 }


-- ANSI ARCHIVE INTERVAL STATISTICS TABLE

dsxT1E1IfAnsiArchiveIntervalStatsTable OBJECT-TYPE
    SYNTAX      SEQUENCE OF DsxT1E1IfAnsiArchiveIntervalStatsEntry
    MAX-ACCESS  not-accessible
    STATUS      current
    DESCRIPTION
            "A list of T1/E1 interface test status entries"
    ::= { dsxT1E1IfAnsiStatsGroup 3 }

dsxT1E1IfAnsiArchiveIntervalStatsEntry  OBJECT-TYPE
    SYNTAX      DsxT1E1IfAnsiArchiveIntervalStatsEntry
    MAX-ACCESS  not-accessible
    STATUS      current
    DESCRIPTION
            "An entry containing status entry for each currently active 
            T1/E1 interface."
    INDEX { dsxT1E1IfIndex, dsxT1E1IfAnsiArchiveStatsInterval }
    ::= { dsxT1E1IfAnsiArchiveIntervalStatsTable 1 }

DsxT1E1IfAnsiArchiveIntervalStatsEntry ::=
    SEQUENCE {
        dsxT1E1IfAnsiArchiveStatsInterval                Unsigned32,
        dsxT1E1IfAnsiArchiveIntervalPathStatsCV          Unsigned32,
        dsxT1E1IfAnsiArchiveIntervalPathStatsES          Unsigned32,
        dsxT1E1IfAnsiArchiveIntervalPathStatsSES         Unsigned32,
        dsxT1E1IfAnsiArchiveIntervalPathStatsSAS         Unsigned32,
        dsxT1E1IfAnsiArchiveIntervalPathStatsCSS         Unsigned32,
        dsxT1E1IfAnsiArchiveIntervalPathStatsUAS         Unsigned32,
        dsxT1E1IfAnsiArchiveIntervalLineStatsCV          Unsigned32,
        dsxT1E1IfAnsiArchiveIntervalLineStatsES          Unsigned32,
        dsxT1E1IfAnsiArchiveIntervalLineStatsSES         Unsigned32
    }

dsxT1E1IfAnsiArchiveStatsInterval OBJECT-TYPE
    SYNTAX      Unsigned32
    MAX-ACCESS  not-accessible
    STATUS      current
    DESCRIPTION
            "Number of Intervals available in archive table "
    ::= { dsxT1E1IfAnsiArchiveIntervalStatsEntry 1 }
    
dsxT1E1IfAnsiArchiveIntervalPathStatsCV OBJECT-TYPE
    SYNTAX   Unsigned32
    MAX-ACCESS  read-only
    STATUS      current
    DESCRIPTION
            "The number of Path Coding  Violations  encoun-
             tered  by  a  T1  interface  in the archive
             intervals. "
    ::= { dsxT1E1IfAnsiArchiveIntervalStatsEntry 2 }

dsxT1E1IfAnsiArchiveIntervalPathStatsES OBJECT-TYPE
    SYNTAX   Unsigned32
    MAX-ACCESS  read-only
    STATUS      current
    DESCRIPTION
            "The number of Errored Seconds, encountered  by
             a DS3 interface in the archive intervals. "
    ::= { dsxT1E1IfAnsiArchiveIntervalStatsEntry 3 }

dsxT1E1IfAnsiArchiveIntervalPathStatsSES OBJECT-TYPE
    SYNTAX   Unsigned32
    MAX-ACCESS  read-only
    STATUS      current
    DESCRIPTION
            "The number of Severely Errored Seconds encoun-
                tered  by  a  T1/E1  interface  in the archive 
                intervals . "
    ::= { dsxT1E1IfAnsiArchiveIntervalStatsEntry 4 }

dsxT1E1IfAnsiArchiveIntervalPathStatsSAS OBJECT-TYPE
    SYNTAX   Unsigned32
    MAX-ACCESS  read-only
    STATUS      current
    DESCRIPTION
            "The number of Severely Errored Framing Seconds
                encountered  by  a T1/E1 interface in the archive
                intervals. "
    ::= { dsxT1E1IfAnsiArchiveIntervalStatsEntry 5 }

dsxT1E1IfAnsiArchiveIntervalPathStatsCSS OBJECT-TYPE
    SYNTAX   Unsigned32
    MAX-ACCESS  read-only
    STATUS      current
    DESCRIPTION
                "The number of Controlled Slip Seconds
                encountered  by  a T1/E1 interface in the archive
                intervals. "
    ::= { dsxT1E1IfAnsiArchiveIntervalStatsEntry 6 }

dsxT1E1IfAnsiArchiveIntervalPathStatsUAS OBJECT-TYPE
    SYNTAX   Unsigned32
    MAX-ACCESS  read-only
    STATUS      current
    DESCRIPTION
            "The number of Unavailable Seconds  encountered
             by a T1/E1 interface in the archive intervals. "
    ::= { dsxT1E1IfAnsiArchiveIntervalStatsEntry 7 }

dsxT1E1IfAnsiArchiveIntervalLineStatsCV OBJECT-TYPE
    SYNTAX   Unsigned32
    MAX-ACCESS  read-only
    STATUS      current
    DESCRIPTION
            "The number of Line Coding  Violations  encoun-
             tered  by  a  T1/E1  interface  in the archive
             intervals. "
    ::= { dsxT1E1IfAnsiArchiveIntervalStatsEntry 8 }

dsxT1E1IfAnsiArchiveIntervalLineStatsES OBJECT-TYPE
    SYNTAX   Unsigned32
    MAX-ACCESS  read-only
    STATUS      current
    DESCRIPTION
            "The number of Errored Seconds, encountered  by
             a T1/E1 interface in the archive intervals. "
    ::= { dsxT1E1IfAnsiArchiveIntervalStatsEntry 9 }

dsxT1E1IfAnsiArchiveIntervalLineStatsSES OBJECT-TYPE
    SYNTAX   Unsigned32
    MAX-ACCESS  read-only
    STATUS      current
    DESCRIPTION
            "The number of Severely Errored Seconds encoun-
                tered  by  a  T1/E1  interface  in the archive 
                intervals . "
    ::= { dsxT1E1IfAnsiArchiveIntervalStatsEntry 10 }


-- ATT Stats Group

-- ATT Stats Current Table
dsxT1E1IfAttCurrentStatsTable OBJECT-TYPE
    SYNTAX      SEQUENCE OF DsxT1E1IfAttCurrentStatsEntry
    MAX-ACCESS  not-accessible
    STATUS      current
    DESCRIPTION
            "A list of T1/E1 interface statistics for current 
			interval"
    ::= { dsxT1E1IfAttStatsGroup 1 }

dsxT1E1IfAttCurrentStatsEntry  OBJECT-TYPE
    SYNTAX      DsxT1E1IfAttCurrentStatsEntry
    MAX-ACCESS  not-accessible
    STATUS      current
    DESCRIPTION
            "An entry containing statistics for each currently active 
            T1/E1 interface."
    AUGMENTS { dsxT1E1IfConfigLineEntry }
    ::= { dsxT1E1IfAttCurrentStatsTable 1 }

DsxT1E1IfAttCurrentStatsEntry ::=
    SEQUENCE {
        dsxT1E1IfAttCurrentStatsUASState                TruthValue,
        dsxT1E1IfAttCurrentStatsTimeInCurrent           Unsigned32,
        dsxT1E1IfAttCurrentStatsEEV                     Unsigned32,
        dsxT1E1IfAttCurrentStatsES                      Unsigned32,
        dsxT1E1IfAttCurrentStatsUAS                     Unsigned32,
        dsxT1E1IfAttCurrentStatsBES                     Unsigned32,
        dsxT1E1IfAttCurrentStatsSES                     Unsigned32,
        dsxT1E1IfAttCurrentStatsLOFC                    Unsigned32,
        dsxT1E1IfAttCurrentStatsCSS                     Unsigned32
    }
    
dsxT1E1IfAttCurrentStatsUASState OBJECT-TYPE
    SYNTAX      TruthValue
    MAX-ACCESS  read-only
    STATUS      current
    DESCRIPTION
            "The Current state of availablity of T1/E1 interface"
    ::= { dsxT1E1IfAttCurrentStatsEntry 1 }
    
dsxT1E1IfAttCurrentStatsTimeInCurrent OBJECT-TYPE
    SYNTAX      Unsigned32
    MAX-ACCESS  read-only
    STATUS      current
    DESCRIPTION
            "The number of seconds that  have  elapsed
                     since the beginning of the far end current
                     error-measurement period. "
    ::= { dsxT1E1IfAttCurrentStatsEntry 2 }
    
dsxT1E1IfAttCurrentStatsEEV OBJECT-TYPE
    SYNTAX      Unsigned32
    MAX-ACCESS  read-only
    STATUS      current
    DESCRIPTION
            "The number of Far Far End Errored EVents  en-
                countered  by a T1/E1 interface in the current 15
                minute interval. "
    ::= { dsxT1E1IfAttCurrentStatsEntry 3 }

dsxT1E1IfAttCurrentStatsES OBJECT-TYPE
    SYNTAX      Unsigned32
    MAX-ACCESS  read-only
    STATUS      current
    DESCRIPTION
            "The number of Far Far End Errored Seconds  en-
                countered  by a T1/E1 interface in the current 15
                minute interval. "
    ::= { dsxT1E1IfAttCurrentStatsEntry 4 }

dsxT1E1IfAttCurrentStatsUAS OBJECT-TYPE
    SYNTAX      Unsigned32
    MAX-ACCESS  read-only
    STATUS      current
    DESCRIPTION
            "The number of Unavailable Seconds  encountered
                by a T1/E1 interface in the current 15 minute in-
                terval. "
    ::= { dsxT1E1IfAttCurrentStatsEntry 5 }

dsxT1E1IfAttCurrentStatsBES OBJECT-TYPE
    SYNTAX      Unsigned32
    MAX-ACCESS  read-only
    STATUS      current
    DESCRIPTION
            "The number of Bursty  Errored  Seconds  (BESs)
                encountered  by  a T1/E1 interface in the current
                15 minute interval. "
    ::= { dsxT1E1IfAttCurrentStatsEntry 6 }

dsxT1E1IfAttCurrentStatsSES OBJECT-TYPE
    SYNTAX      Unsigned32
    MAX-ACCESS  read-only
    STATUS      current
    DESCRIPTION
            "The number of Far End Severely Errored Seconds
                encountered  by  a T1/E1 interface in the current
                15 minute interval. "
    ::= { dsxT1E1IfAttCurrentStatsEntry 7 }

dsxT1E1IfAttCurrentStatsLOFC OBJECT-TYPE
    SYNTAX      Unsigned32
    MAX-ACCESS  read-only
    STATUS      current
    DESCRIPTION
            "The number of loss of frames occurred in the 
             current 15 minute interval. "
    ::= { dsxT1E1IfAttCurrentStatsEntry 8 }


dsxT1E1IfAttCurrentStatsCSS OBJECT-TYPE
    SYNTAX      Unsigned32
    MAX-ACCESS  read-only
    STATUS      current
    DESCRIPTION
            "The number of Far End Controlled Slip  Seconds
                encountered  by  a T1/E1 interface in the current
                interval. "
    ::= { dsxT1E1IfAttCurrentStatsEntry 9 }
    

-- ATT TOTAL STATS

dsxT1E1IfAttTotalStatsTable OBJECT-TYPE
    SYNTAX      SEQUENCE OF DsxT1E1IfAttTotalStatsEntry
    MAX-ACCESS  not-accessible
    STATUS      current
    DESCRIPTION
            "A list of T1/E1 interface test status entries"
    ::= { dsxT1E1IfAttStatsGroup 2 }

dsxT1E1IfAttTotalStatsEntry  OBJECT-TYPE
    SYNTAX      DsxT1E1IfAttTotalStatsEntry
    MAX-ACCESS  not-accessible
    STATUS      current
    DESCRIPTION
            "An entry containing status entry for each currently active 
            T1/E1 interface."
    AUGMENTS { dsxT1E1IfConfigLineEntry }
    ::= { dsxT1E1IfAttTotalStatsTable 1 }

DsxT1E1IfAttTotalStatsEntry ::=
    SEQUENCE {
        dsxT1E1IfAttTotalStatsEEV                     Unsigned32,
        dsxT1E1IfAttTotalStatsES                      Unsigned32,
        dsxT1E1IfAttTotalStatsUAS                     Unsigned32,
        dsxT1E1IfAttTotalStatsBES                     Unsigned32,
        dsxT1E1IfAttTotalStatsSES                     Unsigned32,
        dsxT1E1IfAttTotalStatsLOFC                    Unsigned32,
        dsxT1E1IfAttTotalStatsCSS                     Unsigned32
    }
    
dsxT1E1IfAttTotalStatsEEV OBJECT-TYPE
    SYNTAX      Unsigned32
    MAX-ACCESS  read-only
    STATUS      current
    DESCRIPTION
            "Invoke the configured test. "
    ::= { dsxT1E1IfAttTotalStatsEntry 1 }

dsxT1E1IfAttTotalStatsES OBJECT-TYPE
    SYNTAX      Unsigned32
    MAX-ACCESS  read-only
    STATUS      current
    DESCRIPTION
            "The number of Near End Errored Seconds  encoun-
                tered  by  a  T1/E1  interface. "
    ::= { dsxT1E1IfAttTotalStatsEntry 2 }

dsxT1E1IfAttTotalStatsUAS OBJECT-TYPE
    SYNTAX      Unsigned32
    MAX-ACCESS  read-only
    STATUS      current
    DESCRIPTION
            "The number of Unavailable Seconds  encountered
                by  a T1/E1 interface. "
    ::= { dsxT1E1IfAttTotalStatsEntry 3 }

dsxT1E1IfAttTotalStatsBES OBJECT-TYPE
    SYNTAX      Unsigned32
    MAX-ACCESS  read-only
    STATUS      current
    DESCRIPTION
            "The number of Bursty  Errored  Seconds  (BESs)
                encountered  by a T1/E1 interface. "
    ::= { dsxT1E1IfAttTotalStatsEntry 4 }

dsxT1E1IfAttTotalStatsSES OBJECT-TYPE
    SYNTAX      Unsigned32
    MAX-ACCESS  read-only
    STATUS      current
    DESCRIPTION
            "The number of Near End Severely Errored Seconds
                encountered  by a T1/E1 interface. "
    ::= { dsxT1E1IfAttTotalStatsEntry 5 }

dsxT1E1IfAttTotalStatsLOFC OBJECT-TYPE
    SYNTAX      Unsigned32
    MAX-ACCESS  read-only
    STATUS      current
    DESCRIPTION
            "Count of loss of frames. "
    ::= { dsxT1E1IfAttTotalStatsEntry 6 }


dsxT1E1IfAttTotalStatsCSS OBJECT-TYPE
    SYNTAX      Unsigned32
    MAX-ACCESS  read-only
    STATUS      current
    DESCRIPTION
            "The number of Near End Controlled Slip  Seconds
                encountered  by a T1/E1 interface. "
    ::= { dsxT1E1IfAttTotalStatsEntry 7 }
    
-- ATT ARCHIVE STATS

dsxT1E1IfAttArchiveStatsTable OBJECT-TYPE
    SYNTAX      SEQUENCE OF DsxT1E1IfAttArchiveStatsEntry
    MAX-ACCESS  not-accessible
    STATUS      current
    DESCRIPTION
            "A list of T1/E1 interface test status entries"
    ::= { dsxT1E1IfAttStatsGroup 3 }

dsxT1E1IfAttArchiveStatsEntry  OBJECT-TYPE
    SYNTAX      DsxT1E1IfAttArchiveStatsEntry
    MAX-ACCESS  not-accessible
    STATUS      current
    DESCRIPTION
            "An entry containing status entry for each currently active 
            T1/E1 interface."
    INDEX { dsxT1E1IfIndex, dsxT1E1IfAttArchiveInterval }
    ::= { dsxT1E1IfAttArchiveStatsTable 1 }

DsxT1E1IfAttArchiveStatsEntry ::=
    SEQUENCE {
        dsxT1E1IfAttArchiveInterval                     Unsigned32,
        dsxT1E1IfAttArchiveStatsEEV                     Unsigned32,
        dsxT1E1IfAttArchiveStatsES                      Unsigned32,
        dsxT1E1IfAttArchiveStatsUAS                     Unsigned32,
        dsxT1E1IfAttArchiveStatsBES                     Unsigned32,
        dsxT1E1IfAttArchiveStatsSES                     Unsigned32,
        dsxT1E1IfAttArchiveStatsLOFC                    Unsigned32,
        dsxT1E1IfAttArchiveStatsCSS                     Unsigned32
    }
    
dsxT1E1IfAttArchiveInterval OBJECT-TYPE
    SYNTAX      Unsigned32
    MAX-ACCESS  not-accessible
    STATUS      current
    DESCRIPTION
            "Time interval for archiving the statistics. "
    ::= { dsxT1E1IfAttArchiveStatsEntry 1 }
        
dsxT1E1IfAttArchiveStatsEEV OBJECT-TYPE
    SYNTAX      Unsigned32
    MAX-ACCESS  read-only
    STATUS      current
    DESCRIPTION
            "Invoke the configured test. "
    ::= { dsxT1E1IfAttArchiveStatsEntry 2 }

dsxT1E1IfAttArchiveStatsES OBJECT-TYPE
    SYNTAX      Unsigned32
    MAX-ACCESS  read-only
    STATUS      current
    DESCRIPTION
            "The number of Near End Errored Seconds  encoun-
                tered  by  a  T1/E1  interface. "
    ::= { dsxT1E1IfAttArchiveStatsEntry 3 }

dsxT1E1IfAttArchiveStatsUAS OBJECT-TYPE
    SYNTAX      Unsigned32
    MAX-ACCESS  read-only
    STATUS      current
    DESCRIPTION
            "The number of Unavailable Seconds  encountered
                by  a T1/E1 interface. "
    ::= { dsxT1E1IfAttArchiveStatsEntry 4 }

dsxT1E1IfAttArchiveStatsBES OBJECT-TYPE
    SYNTAX      Unsigned32
    MAX-ACCESS  read-only
    STATUS      current
    DESCRIPTION
            "The number of Bursty  Errored  Seconds  (BESs)
                encountered  by a T1/E1 interface. "
    ::= { dsxT1E1IfAttArchiveStatsEntry 5 }

dsxT1E1IfAttArchiveStatsSES OBJECT-TYPE
    SYNTAX      Unsigned32
    MAX-ACCESS  read-only
    STATUS      current
    DESCRIPTION
            "The number of Near End Severely Errored Seconds
                encountered  by a T1/E1 interface. "
    ::= { dsxT1E1IfAttArchiveStatsEntry 6 }

dsxT1E1IfAttArchiveStatsLOFC OBJECT-TYPE
    SYNTAX      Unsigned32
    MAX-ACCESS  read-only
    STATUS      current
    DESCRIPTION
            "Count of loss of frames. "
    ::= { dsxT1E1IfAttArchiveStatsEntry 7 }


dsxT1E1IfAttArchiveStatsCSS OBJECT-TYPE
    SYNTAX      Unsigned32
    MAX-ACCESS  read-only
    STATUS      current
    DESCRIPTION
            "The number of Near End Controlled Slip  Seconds
                encountered  by a T1/E1 interface. "
    ::= { dsxT1E1IfAttArchiveStatsEntry 8 }




-- IETF Stats Group

-- IETF Current Stats Table

dsxT1E1IfIetfCurrentStatsTable OBJECT-TYPE
    SYNTAX      SEQUENCE OF DsxT1E1IfIetfCurrentStatsEntry
    MAX-ACCESS  not-accessible
    STATUS      current
    DESCRIPTION
            "A list of T1/E1 interface test status entries"
    ::= { dsxT1E1IfIetfStatsGroup 1 }

dsxT1E1IfIetfCurrentStatsEntry  OBJECT-TYPE
    SYNTAX      DsxT1E1IfIetfCurrentStatsEntry
    MAX-ACCESS  not-accessible
    STATUS      current
    DESCRIPTION
            "An entry containing status entry for each currently active 
            T1/E1 interface."
    AUGMENTS { dsxT1E1IfConfigLineEntry }
    ::= { dsxT1E1IfIetfCurrentStatsTable 1 }

DsxT1E1IfIetfCurrentStatsEntry ::=
    SEQUENCE {
        dsxT1E1IfIetfCurrentStatsUASState                 TruthValue,
        dsxT1E1IfIetfCurrentStatsTimeInCurrent            Unsigned32,
        dsxT1E1IfIetfCurrentStatsES                       Unsigned32,
        dsxT1E1IfIetfCurrentStatsSES                      Unsigned32,
        dsxT1E1IfIetfCurrentStatsSEFS                     Unsigned32,
        dsxT1E1IfIetfCurrentStatsUAS                      Unsigned32,
        dsxT1E1IfIetfCurrentStatsCSS                      Unsigned32,
        dsxT1E1IfIetfCurrentStatsPCV                      Unsigned32,
        dsxT1E1IfIetfCurrentStatsLES                      Unsigned32,
        dsxT1E1IfIetfCurrentStatsBES                      Unsigned32,
        dsxT1E1IfIetfCurrentStatsDM                       Unsigned32,
        dsxT1E1IfIetfCurrentStatsLCV                      Unsigned32        
    }
    
dsxT1E1IfIetfCurrentStatsUASState OBJECT-TYPE
    SYNTAX      TruthValue
    MAX-ACCESS  read-only
    STATUS      current
    DESCRIPTION
            "The number of seconds that  have  elapsed
                     since the beginning of the IETF current
                     error-measurement period. "
    ::= { dsxT1E1IfIetfCurrentStatsEntry 1 }
    
dsxT1E1IfIetfCurrentStatsTimeInCurrent OBJECT-TYPE
    SYNTAX      Unsigned32
    MAX-ACCESS  read-only
    STATUS      current
    DESCRIPTION
            "The number of seconds that  have  elapsed
                     since the beginning of the IETF current
                     error-measurement period. "
    ::= { dsxT1E1IfIetfCurrentStatsEntry 2 }
    
dsxT1E1IfIetfCurrentStatsES OBJECT-TYPE
    SYNTAX      Unsigned32
    MAX-ACCESS  read-only
    STATUS      current
    DESCRIPTION
            "The number of IETF Errored Seconds  encoun-
                tered  by  a  T1/E1  interface. "
    ::= { dsxT1E1IfIetfCurrentStatsEntry 3 }

dsxT1E1IfIetfCurrentStatsSES OBJECT-TYPE
    SYNTAX      Unsigned32
    MAX-ACCESS  read-only
    STATUS      current
    DESCRIPTION
            "The number of Far End Severely Errored Seconds
                encountered  by a T1/E1 interface. "
    ::= { dsxT1E1IfIetfCurrentStatsEntry 4 }

dsxT1E1IfIetfCurrentStatsSEFS OBJECT-TYPE
    SYNTAX      Unsigned32
    MAX-ACCESS  read-only
    STATUS      current
    DESCRIPTION
            "The number of IETF Severely Errored Framing
                Seconds  encountered  by a T1/E1 interface. "
    ::= { dsxT1E1IfIetfCurrentStatsEntry 5 }

dsxT1E1IfIetfCurrentStatsUAS OBJECT-TYPE
    SYNTAX      Unsigned32
    MAX-ACCESS  read-only
    STATUS      current
    DESCRIPTION
            "The number of Unavailable Seconds  encountered
                by  a T1/E1 interface. "
    ::= { dsxT1E1IfIetfCurrentStatsEntry 6 }

dsxT1E1IfIetfCurrentStatsCSS OBJECT-TYPE
    SYNTAX      Unsigned32
    MAX-ACCESS  read-only
    STATUS      current
    DESCRIPTION
            "The number of IETF Controlled Slip  Seconds
                encountered  by a T1/E1 interface. "
    ::= { dsxT1E1IfIetfCurrentStatsEntry 7 }

dsxT1E1IfIetfCurrentStatsPCV OBJECT-TYPE
    SYNTAX      Unsigned32
    MAX-ACCESS  read-only
    STATUS      current
    DESCRIPTION
            "The number of IETF Path  Coding  Violations
                reported  via the far end block error count en-
                countered by a T1/E1 interface. "
    ::= { dsxT1E1IfIetfCurrentStatsEntry 8 }


dsxT1E1IfIetfCurrentStatsLES OBJECT-TYPE
    SYNTAX      Unsigned32
    MAX-ACCESS  read-only
    STATUS      current
    DESCRIPTION
            "The number of IETF Line Errored Seconds en-
                countered by a T1/E1 interface. "
   ::= { dsxT1E1IfIetfCurrentStatsEntry 9 }

dsxT1E1IfIetfCurrentStatsBES OBJECT-TYPE
    SYNTAX      Unsigned32
    MAX-ACCESS  read-only
    STATUS      current
    DESCRIPTION
            "The number of Bursty  Errored  Seconds  (BESs)
                encountered  by a T1/E1 interface. "
   ::= { dsxT1E1IfIetfCurrentStatsEntry 10 }
    
dsxT1E1IfIetfCurrentStatsDM OBJECT-TYPE
    SYNTAX      Unsigned32
    MAX-ACCESS  read-only
    STATUS      current
    DESCRIPTION
            "The number of Degraded Minutes  (DMs)  encoun-
                tered  by  a  T1/E1  interface. "
   ::= { dsxT1E1IfIetfCurrentStatsEntry 11 }
    
dsxT1E1IfIetfCurrentStatsLCV OBJECT-TYPE
    SYNTAX      Unsigned32
    MAX-ACCESS  read-only
    STATUS      current
    DESCRIPTION
            "Invoke the configured test. "
   ::= { dsxT1E1IfIetfCurrentStatsEntry 12 }


-- IETF Total Stats Table

dsxT1E1IfIetfTotalStatsTable OBJECT-TYPE
    SYNTAX      SEQUENCE OF DsxT1E1IfIetfTotalStatsEntry
    MAX-ACCESS  not-accessible
    STATUS      current
    DESCRIPTION
            "A list of T1/E1 interface test status entries"
    ::= { dsxT1E1IfIetfStatsGroup 2 }

dsxT1E1IfIetfTotalStatsEntry  OBJECT-TYPE
    SYNTAX      DsxT1E1IfIetfTotalStatsEntry
    MAX-ACCESS  not-accessible
    STATUS      current
    DESCRIPTION
            "An entry containing status entry for each currently active 
            T1/E1 interface."
    AUGMENTS { dsxT1E1IfConfigLineEntry }
    ::= { dsxT1E1IfIetfTotalStatsTable 1 }

DsxT1E1IfIetfTotalStatsEntry ::=
    SEQUENCE {
        dsxT1E1IfIetfTotalStatsES                       Unsigned32,
        dsxT1E1IfIetfTotalStatsSES                      Unsigned32,
        dsxT1E1IfIetfTotalStatsSEFS                     Unsigned32,
        dsxT1E1IfIetfTotalStatsUAS                      Unsigned32,
        dsxT1E1IfIetfTotalStatsCSS                      Unsigned32,
        dsxT1E1IfIetfTotalStatsPCV                      Unsigned32,
        dsxT1E1IfIetfTotalStatsLES                      Unsigned32,
        dsxT1E1IfIetfTotalStatsBES                      Unsigned32,
        dsxT1E1IfIetfTotalStatsDM                       Unsigned32,
        dsxT1E1IfIetfTotalStatsLCV                      Unsigned32        
    }
    
dsxT1E1IfIetfTotalStatsES OBJECT-TYPE
    SYNTAX      Unsigned32
    MAX-ACCESS  read-only
    STATUS      current
    DESCRIPTION
            "The number of IETF Errored Seconds  encoun-
                tered  by  a  T1/E1  interface. "
    ::= { dsxT1E1IfIetfTotalStatsEntry 1 }

dsxT1E1IfIetfTotalStatsSES OBJECT-TYPE
    SYNTAX      Unsigned32
    MAX-ACCESS  read-only
    STATUS      current
    DESCRIPTION
            "The number of IETF Severely Errored Seconds
                encountered  by a T1/E1 interface. "
    ::= { dsxT1E1IfIetfTotalStatsEntry 2 }

dsxT1E1IfIetfTotalStatsSEFS OBJECT-TYPE
    SYNTAX      Unsigned32
    MAX-ACCESS  read-only
    STATUS      current
    DESCRIPTION
            "The number of IETF Severely Errored Framing
                Seconds  encountered  by a T1/E1 interface. "
    ::= { dsxT1E1IfIetfTotalStatsEntry 3 }

dsxT1E1IfIetfTotalStatsUAS OBJECT-TYPE
    SYNTAX      Unsigned32
    MAX-ACCESS  read-only
    STATUS      current
    DESCRIPTION
            "The number of Unavailable Seconds  encountered
                by  a T1/E1 interface. "
    ::= { dsxT1E1IfIetfTotalStatsEntry 4 }

dsxT1E1IfIetfTotalStatsCSS OBJECT-TYPE
    SYNTAX      Unsigned32
    MAX-ACCESS  read-only
    STATUS      current
    DESCRIPTION
            "The number of IETF Controlled Slip  Seconds
                encountered  by a T1/E1 interface. "
    ::= { dsxT1E1IfIetfTotalStatsEntry 5 }

dsxT1E1IfIetfTotalStatsPCV OBJECT-TYPE
    SYNTAX      Unsigned32
    MAX-ACCESS  read-only
    STATUS      current
    DESCRIPTION
            "The number of IETF Path  Coding  Violations
                reported  via the far end block error count en-
                countered by a T1/E1 interface. "
    ::= { dsxT1E1IfIetfTotalStatsEntry 6 }


dsxT1E1IfIetfTotalStatsLES OBJECT-TYPE
    SYNTAX      Unsigned32
    MAX-ACCESS  read-only
    STATUS      current
    DESCRIPTION
            "The number of IETF Line Errored Seconds en-
                countered by a T1/E1 interface. "
   ::= { dsxT1E1IfIetfTotalStatsEntry 7 }

dsxT1E1IfIetfTotalStatsBES OBJECT-TYPE
    SYNTAX      Unsigned32
    MAX-ACCESS  read-only
    STATUS      current
    DESCRIPTION
            "The number of Bursty  Errored  Seconds  (BESs)
                encountered  by a T1/E1 interface. "
   ::= { dsxT1E1IfIetfTotalStatsEntry 8 }
    
dsxT1E1IfIetfTotalStatsDM OBJECT-TYPE
    SYNTAX      Unsigned32
    MAX-ACCESS  read-only
    STATUS      current
    DESCRIPTION
            "The number of Degraded Minutes  (DMs)  encoun-
                tered  by  a  T1/E1  interface. "
   ::= { dsxT1E1IfIetfTotalStatsEntry 9 }
    
dsxT1E1IfIetfTotalStatsLCV OBJECT-TYPE
    SYNTAX      Unsigned32
    MAX-ACCESS  read-only
    STATUS      current
    DESCRIPTION
            "Invoke the configured test. "
   ::= { dsxT1E1IfIetfTotalStatsEntry 10 }


--  IETF Archive Stats

dsxT1E1IfIetfArchiveStatsTable OBJECT-TYPE
    SYNTAX      SEQUENCE OF DsxT1E1IfIetfArchiveStatsEntry
    MAX-ACCESS  not-accessible
    STATUS      current
    DESCRIPTION
            "A list of T1/E1 interface test status entries"
    ::= { dsxT1E1IfIetfStatsGroup 3 }

dsxT1E1IfIetfArchiveStatsEntry  OBJECT-TYPE
    SYNTAX      DsxT1E1IfIetfArchiveStatsEntry
    MAX-ACCESS  not-accessible
    STATUS      current
    DESCRIPTION
            "An entry containing status entry for each currently active 
            T1/E1 interface."
    INDEX { dsxT1E1IfIndex, dsxT1E1IfIetfArchiveStatsInterval }
    ::= { dsxT1E1IfIetfArchiveStatsTable 1 }

DsxT1E1IfIetfArchiveStatsEntry ::=
    SEQUENCE {
        dsxT1E1IfIetfArchiveStatsInterval                 Unsigned32, 
        dsxT1E1IfIetfArchiveStatsES                       Unsigned32,
        dsxT1E1IfIetfArchiveStatsSES                      Unsigned32,
        dsxT1E1IfIetfArchiveStatsSEFS                     Unsigned32,
        dsxT1E1IfIetfArchiveStatsUAS                      Unsigned32,
        dsxT1E1IfIetfArchiveStatsCSS                      Unsigned32,
        dsxT1E1IfIetfArchiveStatsPCV                      Unsigned32,
        dsxT1E1IfIetfArchiveStatsLES                      Unsigned32,
        dsxT1E1IfIetfArchiveStatsBES                      Unsigned32,
        dsxT1E1IfIetfArchiveStatsDM                       Unsigned32,
        dsxT1E1IfIetfArchiveStatsLCV                      Unsigned32        
    }
    
dsxT1E1IfIetfArchiveStatsInterval OBJECT-TYPE
    SYNTAX      Unsigned32
    MAX-ACCESS  not-accessible
    STATUS      current
    DESCRIPTION
            "The number of seconds that  have  elapsed
                     since the beginning of the IETF current
                     error-measurement period. "
    ::= { dsxT1E1IfIetfArchiveStatsEntry 1 }
    
dsxT1E1IfIetfArchiveStatsES OBJECT-TYPE
    SYNTAX      Unsigned32
    MAX-ACCESS  read-only
    STATUS      current
    DESCRIPTION
            "The number of IETF Errored Seconds  encoun-
                tered  by  a  T1/E1  interface. "
    ::= { dsxT1E1IfIetfArchiveStatsEntry 2 }

dsxT1E1IfIetfArchiveStatsSES OBJECT-TYPE
    SYNTAX      Unsigned32
    MAX-ACCESS  read-only
    STATUS      current
    DESCRIPTION
            "The number of IETF Severely Errored Seconds
                encountered  by a T1/E1 interface. "
    ::= { dsxT1E1IfIetfArchiveStatsEntry 3 }

dsxT1E1IfIetfArchiveStatsSEFS OBJECT-TYPE
    SYNTAX      Unsigned32
    MAX-ACCESS  read-only
    STATUS      current
    DESCRIPTION
            "The number of IETF Severely Errored Framing
                Seconds  encountered  by a T1/E1 interface. "
    ::= { dsxT1E1IfIetfArchiveStatsEntry 4 }

dsxT1E1IfIetfArchiveStatsUAS OBJECT-TYPE
    SYNTAX      Unsigned32
    MAX-ACCESS  read-only
    STATUS      current
    DESCRIPTION
            "The number of Unavailable Seconds  encountered
                by  a T1/E1 interface. "
    ::= { dsxT1E1IfIetfArchiveStatsEntry 5 }

dsxT1E1IfIetfArchiveStatsCSS OBJECT-TYPE
    SYNTAX      Unsigned32
    MAX-ACCESS  read-only
    STATUS      current
    DESCRIPTION
            "The number of IETF Controlled Slip  Seconds
                encountered  by a T1/E1 interface. "
    ::= { dsxT1E1IfIetfArchiveStatsEntry 6 }

dsxT1E1IfIetfArchiveStatsPCV OBJECT-TYPE
    SYNTAX      Unsigned32
    MAX-ACCESS  read-only
    STATUS      current
    DESCRIPTION
            "The number of IETF Path  Coding  Violations
                reported  via the far end block error count en-
                countered by a T1/E1 interface. "
    ::= { dsxT1E1IfIetfArchiveStatsEntry 7 }


dsxT1E1IfIetfArchiveStatsLES OBJECT-TYPE
    SYNTAX      Unsigned32
    MAX-ACCESS  read-only
    STATUS      current
    DESCRIPTION
            "The number of IETF Line Errored Seconds en-
                countered by a T1/E1 interface. "
   ::= { dsxT1E1IfIetfArchiveStatsEntry 8 }

dsxT1E1IfIetfArchiveStatsBES OBJECT-TYPE
    SYNTAX      Unsigned32
    MAX-ACCESS  read-only
    STATUS      current
    DESCRIPTION
            "The number of Bursty  Errored  Seconds  (BESs)
                encountered  by a T1/E1 interface. "
   ::= { dsxT1E1IfIetfArchiveStatsEntry 9 }
    
dsxT1E1IfIetfArchiveStatsDM OBJECT-TYPE
    SYNTAX      Unsigned32
    MAX-ACCESS  read-only
    STATUS      current
    DESCRIPTION
            "The number of Degraded Minutes  (DMs)  encoun-
                tered  by  a  T1/E1  interface. "
   ::= { dsxT1E1IfIetfArchiveStatsEntry 10 }
    
dsxT1E1IfIetfArchiveStatsLCV OBJECT-TYPE
    SYNTAX      Unsigned32
    MAX-ACCESS  read-only
    STATUS      current
    DESCRIPTION
            "Invoke the configured test. "
   ::= { dsxT1E1IfIetfArchiveStatsEntry 11 }    
   
-- User Stats Group

-- USER Current Stats Table

dsxT1E1IfUserCurrentStatsTable OBJECT-TYPE
    SYNTAX      SEQUENCE OF DsxT1E1IfUserCurrentStatsEntry
    MAX-ACCESS  not-accessible
    STATUS      current
    DESCRIPTION
            "A list of T1/E1 interface test status entries"
    ::= { dsxT1E1IfUserStatsGroup 1 }

dsxT1E1IfUserCurrentStatsEntry  OBJECT-TYPE
    SYNTAX      DsxT1E1IfUserCurrentStatsEntry
    MAX-ACCESS  not-accessible
    STATUS      current
    DESCRIPTION
            "An entry containing status entry for each currently active 
            T1/E1 interface."
    AUGMENTS { dsxT1E1IfConfigLineEntry }
    ::= { dsxT1E1IfUserCurrentStatsTable 1 }

DsxT1E1IfUserCurrentStatsEntry ::=
    SEQUENCE {
        dsxT1E1IfUserCurrentStatsUASState             TruthValue,
        dsxT1E1IfUserCurrentStatsTimeInCurrent        Unsigned32,
        dsxT1E1IfUserCurrentStatsEEV                  Unsigned32,
        dsxT1E1IfUserCurrentStatsES                   Unsigned32,
        dsxT1E1IfUserCurrentStatsUAS                  Unsigned32,
        dsxT1E1IfUserCurrentStatsBES                  Unsigned32,
        dsxT1E1IfUserCurrentStatsSES                  Unsigned32,
        dsxT1E1IfUserCurrentStatsLOFC                 Unsigned32,
        dsxT1E1IfUserCurrentStatsCSS                  Unsigned32,
        dsxT1E1IfUserCurrentStatsBPV                  Unsigned32,
        dsxT1E1IfUserCurrentStatsOOF                  Unsigned32,
        dsxT1E1IfUserCurrentStatsCRC                  Unsigned32        
    }

dsxT1E1IfUserCurrentStatsUASState OBJECT-TYPE
    SYNTAX      TruthValue
    MAX-ACCESS  read-only
    STATUS      current
    DESCRIPTION
            "Current state of availablity of T1/E1 interface"
    ::= { dsxT1E1IfUserCurrentStatsEntry 1 }
    
dsxT1E1IfUserCurrentStatsTimeInCurrent OBJECT-TYPE
    SYNTAX      Unsigned32
    MAX-ACCESS  read-only
    STATUS      current
    DESCRIPTION
            "The number of seconds that  have  elapsed
                     since the beginning of the IETF current
                     error-measurement period. "
    ::= { dsxT1E1IfUserCurrentStatsEntry 2 }
    
    
dsxT1E1IfUserCurrentStatsEEV OBJECT-TYPE
    SYNTAX      Unsigned32
    MAX-ACCESS  read-only
    STATUS      current
    DESCRIPTION
            "Invoke the configured test. "
    ::= { dsxT1E1IfUserCurrentStatsEntry 3 }

dsxT1E1IfUserCurrentStatsES OBJECT-TYPE
    SYNTAX      Unsigned32
    MAX-ACCESS  read-only
    STATUS      current
    DESCRIPTION
            "The number of Errored Seconds  encoun-
                tered  by  a  T1/E1  interface. "
    ::= { dsxT1E1IfUserCurrentStatsEntry 4 }

dsxT1E1IfUserCurrentStatsUAS OBJECT-TYPE
    SYNTAX      Unsigned32
    MAX-ACCESS  read-only
    STATUS      current
    DESCRIPTION
            "The number of Unavailable Seconds  encountered
                by  a T1/E1 interface. "
    ::= { dsxT1E1IfUserCurrentStatsEntry 5 }

dsxT1E1IfUserCurrentStatsBES OBJECT-TYPE
    SYNTAX      Unsigned32
    MAX-ACCESS  read-only
    STATUS      current
    DESCRIPTION
            "The number of Bursty  Errored  Seconds  (BESs)
                encountered  by a T1/E1 interface. "
    ::= { dsxT1E1IfUserCurrentStatsEntry 6 }

dsxT1E1IfUserCurrentStatsSES OBJECT-TYPE
    SYNTAX      Unsigned32
    MAX-ACCESS  read-only
    STATUS      current
    DESCRIPTION
            "The number of Severely Errored Seconds
                encountered  by a T1/E1 interface. "
    ::= { dsxT1E1IfUserCurrentStatsEntry 7 }

dsxT1E1IfUserCurrentStatsLOFC OBJECT-TYPE
    SYNTAX      Unsigned32
    MAX-ACCESS  read-only
    STATUS      current
    DESCRIPTION
            "Count of loss of frames. "
    ::= { dsxT1E1IfUserCurrentStatsEntry 8 }


dsxT1E1IfUserCurrentStatsCSS OBJECT-TYPE
    SYNTAX      Unsigned32
    MAX-ACCESS  read-only
    STATUS      current
    DESCRIPTION
            "The number of Controlled Slip  Seconds
                encountered  by a T1/E1 interface. "
   ::= { dsxT1E1IfUserCurrentStatsEntry 9 }

dsxT1E1IfUserCurrentStatsBPV OBJECT-TYPE
    SYNTAX      Unsigned32
    MAX-ACCESS  read-only
    STATUS      current
    DESCRIPTION
            "The number of Bipolar Violation Error Event occurred 
             for this interface. "
   ::= { dsxT1E1IfUserCurrentStatsEntry 10 }
    
dsxT1E1IfUserCurrentStatsOOF OBJECT-TYPE
    SYNTAX      Unsigned32
    MAX-ACCESS  read-only
    STATUS      current
    DESCRIPTION
            "The number of Out of Frame Defect occurred for this
             interface. "
   ::= { dsxT1E1IfUserCurrentStatsEntry 11 }
    
dsxT1E1IfUserCurrentStatsCRC OBJECT-TYPE
    SYNTAX      Unsigned32
    MAX-ACCESS  read-only
    STATUS      current
    DESCRIPTION
            "The number of CRC Defects that occurred for this interface. "
   ::= { dsxT1E1IfUserCurrentStatsEntry 12 } 
    

-- USER Total Stats Table

dsxT1E1IfUserTotalStatsTable OBJECT-TYPE
    SYNTAX      SEQUENCE OF DsxT1E1IfUserTotalStatsEntry
    MAX-ACCESS  not-accessible
    STATUS      current
    DESCRIPTION
            "A list of T1/E1 interface test status entries"
    ::= { dsxT1E1IfUserStatsGroup 2 }

dsxT1E1IfUserTotalStatsEntry  OBJECT-TYPE
    SYNTAX      DsxT1E1IfUserTotalStatsEntry
    MAX-ACCESS  not-accessible
    STATUS      current
    DESCRIPTION
            "An entry containing status entry for each currently active 
            T1/E1 interface."
    INDEX { dsxT1E1IfIndex, dsxT1E1IfUserTotalStatsDay }
    ::= { dsxT1E1IfUserTotalStatsTable 1 }

DsxT1E1IfUserTotalStatsEntry ::=
    SEQUENCE {
        dsxT1E1IfUserTotalStatsDay                  Unsigned32, 
        dsxT1E1IfUserTotalStatsEEV                  Unsigned32,
        dsxT1E1IfUserTotalStatsES                   Unsigned32,
        dsxT1E1IfUserTotalStatsUAS                  Unsigned32,
        dsxT1E1IfUserTotalStatsBES                  Unsigned32,
        dsxT1E1IfUserTotalStatsSES                  Unsigned32,
        dsxT1E1IfUserTotalStatsLOFC                 Unsigned32,
        dsxT1E1IfUserTotalStatsCSS                  Unsigned32,
        dsxT1E1IfUserTotalStatsBPV                  Unsigned32,
        dsxT1E1IfUserTotalStatsOOF                  Unsigned32,
        dsxT1E1IfUserTotalStatsCRC                  Unsigned32        
    }
    
dsxT1E1IfUserTotalStatsDay OBJECT-TYPE
    SYNTAX   	Unsigned32
    MAX-ACCESS  not-accessible
    STATUS      current
    DESCRIPTION
            "Total number of days elapsed since event recording 
             started for this interface. "
    ::= { dsxT1E1IfUserTotalStatsEntry 1 }
    
dsxT1E1IfUserTotalStatsEEV OBJECT-TYPE
    SYNTAX   	Unsigned32
    MAX-ACCESS  read-only
    STATUS      current
    DESCRIPTION
            "Invoke the configured test. "
    ::= { dsxT1E1IfUserTotalStatsEntry 2 }

dsxT1E1IfUserTotalStatsES OBJECT-TYPE
    SYNTAX   	Unsigned32
    MAX-ACCESS  read-only
    STATUS      current
    DESCRIPTION
            "The number of Errored Seconds  encoun-
                tered  by  a  T1/E1  interface. "
    ::= { dsxT1E1IfUserTotalStatsEntry 3 }

dsxT1E1IfUserTotalStatsUAS OBJECT-TYPE
    SYNTAX   	Unsigned32
    MAX-ACCESS  read-only
    STATUS      current
    DESCRIPTION
            "The number of Unavailable Seconds  encountered
                by  a T1/E1 interface. "
    ::= { dsxT1E1IfUserTotalStatsEntry 4 }

dsxT1E1IfUserTotalStatsBES OBJECT-TYPE
    SYNTAX   	Unsigned32
    MAX-ACCESS  read-only
    STATUS      current
    DESCRIPTION
            "The number of Bursty  Errored  Seconds  (BESs)
                encountered  by a T1/E1 interface. "
    ::= { dsxT1E1IfUserTotalStatsEntry 5 }

dsxT1E1IfUserTotalStatsSES OBJECT-TYPE
    SYNTAX   	Unsigned32
    MAX-ACCESS  read-only
    STATUS      current
    DESCRIPTION
            "The number of Severely Errored Seconds
                encountered  by a T1/E1 interface. "
    ::= { dsxT1E1IfUserTotalStatsEntry 6 }

dsxT1E1IfUserTotalStatsLOFC OBJECT-TYPE
    SYNTAX   	Unsigned32
    MAX-ACCESS  read-only
    STATUS      current
    DESCRIPTION
            "Count of loss of frames. "
    ::= { dsxT1E1IfUserTotalStatsEntry 7 }


dsxT1E1IfUserTotalStatsCSS OBJECT-TYPE
    SYNTAX   	Unsigned32
    MAX-ACCESS  read-only
    STATUS      current
    DESCRIPTION
            "The number of Controlled Slip  Seconds
                encountered  by a T1/E1 interface. "
   ::= { dsxT1E1IfUserTotalStatsEntry 8 }

dsxT1E1IfUserTotalStatsBPV OBJECT-TYPE
    SYNTAX   	Unsigned32
    MAX-ACCESS  read-only
    STATUS      current
    DESCRIPTION
            "The number of Bipolar Violation Error Event occurred 
             for this interface. "
   ::= { dsxT1E1IfUserTotalStatsEntry 9 }
    
dsxT1E1IfUserTotalStatsOOF OBJECT-TYPE
    SYNTAX   	Unsigned32
    MAX-ACCESS  read-only
    STATUS      current
    DESCRIPTION
            "The number of Out of Frame Defect occurred for this
             interface. "
   ::= { dsxT1E1IfUserTotalStatsEntry 10 }
    
dsxT1E1IfUserTotalStatsCRC OBJECT-TYPE
    SYNTAX   	Unsigned32
    MAX-ACCESS  read-only
    STATUS      current
    DESCRIPTION
            "The number of Out of Frame Defect occurred for this
             interface. "
   ::= { dsxT1E1IfUserTotalStatsEntry 11 }  
    
-- User Lifetime Stats Table

dsxT1E1IfUserLifetimeStatsTable OBJECT-TYPE
    SYNTAX      SEQUENCE OF DsxT1E1IfUserLifetimeStatsEntry
    MAX-ACCESS  not-accessible
    STATUS      current
    DESCRIPTION
            "Table maintained to keep the statistics for the whole lifetime
			of the system since it is first powered on."
    ::= { dsxT1E1IfUserStatsGroup 3 }

dsxT1E1IfUserLifetimeStatsEntry  OBJECT-TYPE
    SYNTAX      DsxT1E1IfUserLifetimeStatsEntry
    MAX-ACCESS  not-accessible
    STATUS      current
    DESCRIPTION
            "An entry containing status entry for each currently active 
            T1/E1 interface."
    AUGMENTS { dsxT1E1IfConfigLineEntry }
    ::= { dsxT1E1IfUserLifetimeStatsTable 1 }

DsxT1E1IfUserLifetimeStatsEntry ::=
    SEQUENCE {
        dsxT1E1IfUserLifetimeStatsEEV                  Unsigned32,
        dsxT1E1IfUserLifetimeStatsES                   Unsigned32,
        dsxT1E1IfUserLifetimeStatsUAS                  Unsigned32,
        dsxT1E1IfUserLifetimeStatsBES                  Unsigned32,
        dsxT1E1IfUserLifetimeStatsSES                  Unsigned32,
        dsxT1E1IfUserLifetimeStatsLOFC                 Unsigned32,
        dsxT1E1IfUserLifetimeStatsCSS                  Unsigned32,
        dsxT1E1IfUserLifetimeStatsBPV                  Unsigned32,
        dsxT1E1IfUserLifetimeStatsOOF                  Unsigned32,
        dsxT1E1IfUserLifetimeStatsCRC                  Unsigned32        
    }
    
dsxT1E1IfUserLifetimeStatsEEV OBJECT-TYPE
    SYNTAX   	Unsigned32
    MAX-ACCESS  read-only
    STATUS      current
    DESCRIPTION
            "The Total number of Error Events occured during since the system brought up"
    ::= { dsxT1E1IfUserLifetimeStatsEntry 1 }

dsxT1E1IfUserLifetimeStatsES OBJECT-TYPE
    SYNTAX   	Unsigned32
    MAX-ACCESS  read-only
    STATUS      current
    DESCRIPTION
            "The number of Errored Seconds  encoun-
                tered  by  a  T1/E1  interface. "
    ::= { dsxT1E1IfUserLifetimeStatsEntry 2 }

dsxT1E1IfUserLifetimeStatsUAS OBJECT-TYPE
    SYNTAX   	Unsigned32
    MAX-ACCESS  read-only
    STATUS      current
    DESCRIPTION
            "The number of Unavailable Seconds  encountered
                by  a T1/E1 interface. "
    ::= { dsxT1E1IfUserLifetimeStatsEntry 3 }

dsxT1E1IfUserLifetimeStatsBES OBJECT-TYPE
    SYNTAX   	Unsigned32
    MAX-ACCESS  read-only
    STATUS      current
    DESCRIPTION
            "The number of Bursty  Errored  Seconds  (BESs)
                encountered  by a T1/E1 interface. "
    ::= { dsxT1E1IfUserLifetimeStatsEntry 4 }

dsxT1E1IfUserLifetimeStatsSES OBJECT-TYPE
    SYNTAX   	Unsigned32
    MAX-ACCESS  read-only
    STATUS      current
    DESCRIPTION
            "The number of Severely Errored Seconds
                encountered  by a T1/E1 interface. "
    ::= { dsxT1E1IfUserLifetimeStatsEntry 5 }

dsxT1E1IfUserLifetimeStatsLOFC OBJECT-TYPE
    SYNTAX   	Unsigned32
    MAX-ACCESS  read-only
    STATUS      current
    DESCRIPTION
            "Count of loss of frames. "
    ::= { dsxT1E1IfUserLifetimeStatsEntry 6 }


dsxT1E1IfUserLifetimeStatsCSS OBJECT-TYPE
    SYNTAX   	Unsigned32
    MAX-ACCESS  read-only
    STATUS      current
    DESCRIPTION
            "The number of Controlled Slip  Seconds
                encountered  by a T1/E1 interface. "
   ::= { dsxT1E1IfUserLifetimeStatsEntry 7}

dsxT1E1IfUserLifetimeStatsBPV OBJECT-TYPE
    SYNTAX   	Unsigned32
    MAX-ACCESS  read-only
    STATUS      current
    DESCRIPTION
            "The number of Bipolar Violation Error Event occurred 
             for this interface. "
   ::= { dsxT1E1IfUserLifetimeStatsEntry 8 }
    
dsxT1E1IfUserLifetimeStatsOOF OBJECT-TYPE
    SYNTAX   	Unsigned32
    MAX-ACCESS  read-only
    STATUS      current
    DESCRIPTION
            "The number of Out of Frame Defect occurred for this
             interface. "
   ::= { dsxT1E1IfUserLifetimeStatsEntry 9 }
    
dsxT1E1IfUserLifetimeStatsCRC OBJECT-TYPE
    SYNTAX   	Unsigned32
    MAX-ACCESS  read-only
    STATUS      current
    DESCRIPTION
            "The number of Out of Frame Defect occurred for this
             interface. "
   ::= { dsxT1E1IfUserLifetimeStatsEntry 10 }  
    
-- USER Archive Stats

dsxT1E1IfUserArchiveStatsTable OBJECT-TYPE
    SYNTAX      SEQUENCE OF DsxT1E1IfUserArchiveStatsEntry
    MAX-ACCESS  not-accessible
    STATUS      current
    DESCRIPTION
            "The table maintained to keep last 24 hrs statistics in "
    ::= { dsxT1E1IfUserStatsGroup 4 }

dsxT1E1IfUserArchiveStatsEntry  OBJECT-TYPE
    SYNTAX      DsxT1E1IfUserArchiveStatsEntry
    MAX-ACCESS  not-accessible
    STATUS      current
    DESCRIPTION
            "An entry containing status entry for each currently active 
            T1/E1 interface."
    INDEX { dsxT1E1IfIndex, dsxT1E1IfUserArchiveStatsInterval }
    ::= { dsxT1E1IfUserArchiveStatsTable 1 }

DsxT1E1IfUserArchiveStatsEntry ::=
    SEQUENCE {
        dsxT1E1IfUserArchiveStatsInterval             Unsigned32, 
        dsxT1E1IfUserArchiveStatsEEV                  Unsigned32,
        dsxT1E1IfUserArchiveStatsES                   Unsigned32,
        dsxT1E1IfUserArchiveStatsUAS                  Unsigned32,
        dsxT1E1IfUserArchiveStatsBES                  Unsigned32,
        dsxT1E1IfUserArchiveStatsSES                  Unsigned32,
        dsxT1E1IfUserArchiveStatsLOFC                 Unsigned32,
        dsxT1E1IfUserArchiveStatsCSS                  Unsigned32,
        dsxT1E1IfUserArchiveStatsBPV                  Unsigned32,
        dsxT1E1IfUserArchiveStatsOOF                  Unsigned32,
        dsxT1E1IfUserArchiveStatsCRC                  Unsigned32        
    }
    
dsxT1E1IfUserArchiveStatsInterval OBJECT-TYPE
    SYNTAX   	Unsigned32
    MAX-ACCESS  not-accessible
    STATUS      current
    DESCRIPTION
            "The number of seconds that  have  elapsed
                     since the beginning of the IETF current
                     error-measurement period. "
    ::= { dsxT1E1IfUserArchiveStatsEntry 1 }
    
dsxT1E1IfUserArchiveStatsEEV OBJECT-TYPE
    SYNTAX   	Unsigned32
    MAX-ACCESS  read-only
    STATUS      current
    DESCRIPTION
            "Error Events collected over each period of 15 mins"
    ::= { dsxT1E1IfUserArchiveStatsEntry 2 }

dsxT1E1IfUserArchiveStatsES OBJECT-TYPE
    SYNTAX   	Unsigned32
    MAX-ACCESS  read-only
    STATUS      current
    DESCRIPTION
            "The number of Errored Seconds  encoun-
                tered  by  a  T1/E1  interface. "
    ::= { dsxT1E1IfUserArchiveStatsEntry 3 }

dsxT1E1IfUserArchiveStatsUAS OBJECT-TYPE
    SYNTAX   	Unsigned32
    MAX-ACCESS  read-only
    STATUS      current
    DESCRIPTION
            "The number of Unavailable Seconds  encountered
                by  a T1/E1 interface. "
    ::= { dsxT1E1IfUserArchiveStatsEntry 4 }

dsxT1E1IfUserArchiveStatsBES OBJECT-TYPE
    SYNTAX   	Unsigned32
    MAX-ACCESS  read-only
    STATUS      current
    DESCRIPTION
            "The number of Bursty  Errored  Seconds  (BESs)
                encountered  by a T1/E1 interface. "
    ::= { dsxT1E1IfUserArchiveStatsEntry 5 }

dsxT1E1IfUserArchiveStatsSES OBJECT-TYPE
    SYNTAX   	Unsigned32
    MAX-ACCESS  read-only
    STATUS      current
    DESCRIPTION
            "The number of Severely Errored Seconds
                encountered  by a T1/E1 interface. "
    ::= { dsxT1E1IfUserArchiveStatsEntry 6 }

dsxT1E1IfUserArchiveStatsLOFC OBJECT-TYPE
    SYNTAX   	Unsigned32
    MAX-ACCESS  read-only
    STATUS      current
    DESCRIPTION
            "Count of loss of frames. "
    ::= { dsxT1E1IfUserArchiveStatsEntry 7 }


dsxT1E1IfUserArchiveStatsCSS OBJECT-TYPE
    SYNTAX   	Unsigned32
    MAX-ACCESS  read-only
    STATUS      current
    DESCRIPTION
            "The number of Controlled Slip  Seconds
                encountered  by a T1/E1 interface. "
   ::= { dsxT1E1IfUserArchiveStatsEntry 8 }

dsxT1E1IfUserArchiveStatsBPV OBJECT-TYPE
    SYNTAX   	Unsigned32
    MAX-ACCESS  read-only
    STATUS      current
    DESCRIPTION
            "The number of Bipolar Violation Error Event occurred 
             for this interface. "
   ::= { dsxT1E1IfUserArchiveStatsEntry 9 }
    
dsxT1E1IfUserArchiveStatsOOF OBJECT-TYPE
    SYNTAX   	Unsigned32
    MAX-ACCESS  read-only
    STATUS      current
    DESCRIPTION
            "The number of Out of Frame Defect occurred for this
             interface. "
   ::= { dsxT1E1IfUserArchiveStatsEntry 10 }
    
dsxT1E1IfUserArchiveStatsCRC OBJECT-TYPE
    SYNTAX   	Unsigned32
    MAX-ACCESS  read-only
    STATUS      current
    DESCRIPTION
            "The number of Out of Frame Defect occurred for this
             interface. "
   ::= { dsxT1E1IfUserArchiveStatsEntry 11 }  
    

-- TRAP definitions for the T1E1 Interfaces
--
--

dsxT1E1Number   OBJECT-TYPE
    SYNTAX  INTEGER 
    MAX-ACCESS  not-accessible
    STATUS  current
    DESCRIPTION
        " This is the T1/E1 number of the interface from where this 
          alarm is originating."
    ::= { dsxT1E1TrapVariables 1}

dsxT1E1Type   OBJECT-TYPE
    SYNTAX  INTEGER {
                      type-t1(1),
                      type-t1-within-ct3(2) 
                    }
    MAX-ACCESS  not-accessible
    STATUS  current
    DESCRIPTION
        " This variable indicates whether this T1/E1 interface is with in a
          T3/E3 or by itself."
    ::= { dsxT1E1TrapVariables 2}

dsxT1E1T3Number   OBJECT-TYPE
    SYNTAX  INTEGER 
    MAX-ACCESS  not-accessible
    STATUS  current
    DESCRIPTION
        " This variable is applicable only if dsxT1E1Type is 
          'type_t1_within_ct3' and it indicates the T3/E3 interface 
          number this T1 belongs to."
    ::= { dsxT1E1TrapVariables 3}

dsxT1E1AlarmType   OBJECT-TYPE
    SYNTAX  INTEGER {
                te1-alarm-rais (1),
                te1-alarm-rrai (2),
                te1-alarm-roof (3),
                te1-alarm-rlos (4),
                te1-alarm-rlof (5),
                te1-alarm-rexz (6),
                te1-alarm-rfbe (7),
                te1-alarm-lorc (8),
                te1-alarm-tpde (9),
                te1-alarm-tais (10),
                te1-alarm-tblu (11),
                te1-alarm-trai (12),
                te1-alarm-threshold1 (13),
                te1-alarm-threshold2 (14),
                te1-alarm-threshold3 (15),
                te1-alarm-threshold4 (16),
                te1-alarm-threshold5 (17),
                te1-alarm-threshold6 (18),
                te1-alarm-threshold7 (19),
                te1-alarm-threshold8 (20),
                te1-alarm-threshold9 (21),
                te1-alarm-threshold10 (22)

                }
        MAX-ACCESS  not-accessible
        STATUS  current
        DESCRIPTION
             "Status of alarms for the T1/E1 interface
                                RRAI - Recieve RAI (Recieve Alarm Indication),
                                RLOS - Recieve Loss Of Sync,
                                REXZ - Recieve Excessive Zeros,
                                LORC - Loss Of Receive Clock (LORC),
                                TPDE - transmit pulse density,
                                TAIS - Transmit Alarm Indication Signal,
                                RAIS - Recieve Alarm Indication Signal,
                                RLOF - Recieve Loss Of Frame.
                                RFBE - Recieve Frame Bit Error,
                                ROOF - Recieve Out Of Frame,
                                TRAI - Transmit RAI (Recieve Alarm Indication),
                                Threshold 1-10 : TRUE if it is configured.
                                "
        ::= { dsxT1E1TrapVariables 4}

dsxT1E1AlarmOnTrap TRAP-TYPE
        ENTERPRISE dsxT1E1Traps
        VARIABLES { dsxT1E1IfIndex,
                    dsxT1E1Number,
                    dsxT1E1Type,
                    dsxT1E1T3Number,
                    dsxT1E1AlarmType }

        DESCRIPTION
             "T1/E1 interface alarm traps for the Alarm On state."
             --#TYPE "T1/E1 Alarm On state"
             --#SUMMARY "T1/E1 Alarm On trap sent from Interface index: %s T1/E1 number: %s with T1/E1 type: %s T1/E1 T3 number: %s and Alarm type: %s"
             --#ARGUMENTS {0,1,2,3,4}
             --#SEVERITY MAJOR
        ::= 1

dsxT1E1AlarmOffTrap TRAP-TYPE
        ENTERPRISE dsxT1E1Traps
        VARIABLES { dsxT1E1IfIndex,
                    dsxT1E1Number,
                    dsxT1E1Type,
                    dsxT1E1T3Number,
                    dsxT1E1AlarmType }

        DESCRIPTION
             "T1/E1 interface alarm trap for the Alarm Off state."
             --#TYPE "T1/E1 Alarm Off state"
             --#SUMMARY "T1/E1 Alarm Off trap sent from Interface index: %s T1/E1 number: %s with T1/E1 type: %s T1/E1 T3 number: %s and Alarm type: %s"
             --#ARGUMENTS {0,1,2,3,4}
             --#SEVERITY NORMAL
        ::= 2

END
