Wellfleet-FTP-MIB DEFINITIONS ::= BEGIN

-- Created by mdl2asn version 3.1
-- Creation date: Wed Aug 30 16:41:47 EDT 1995


    IMPORTS

      Counter, Gauge
        FROM RFC1155-SMI
      OBJECT-TYPE
        FROM RFC-1212
      wfFtpGroup
        FROM Wellfleet-COMMON-MIB;


    wfFtp		OBJECT IDENTIFIER ::= { wfFtpGroup 1 }

    wfFtpDelete OBJECT-TYPE
        SYNTAX	INTEGER {
    		    created(1),
    		    deleted(2)
    		}
        ACCESS	read-write
        STATUS	mandatory
        DESCRIPTION
                "Create/Delete parameter. Default is created.
                Users perform a set operation on this object
                in order to create/delete WfFTP. "
        DEFVAL	{ created }
        ::= { wfFtp 1 }

    wfFtpDisable OBJECT-TYPE
        SYNTAX	INTEGER {
    		    enabled(1),
    		    disabled(2)
    		}
        ACCESS	read-write
        STATUS	mandatory
        DESCRIPTION
                "Enables or Disables FTP Subsystem"
        DEFVAL	{ enabled }
        ::= { wfFtp 2 }

    wfFtpDefaultVolume OBJECT-TYPE
        SYNTAX	INTEGER {
    		    volume1(1),
    		    volume2(2),
    		    volume3(3),
    		    volume4(4),
    		    volume5(5),
    		    volume6(6),
                    volume7(7),
    		    volume8(8),
    		    volume9(9),
    		    volume10(10),
    		    volume11(11),
    		    volume12(12),
    		    volume13(13),
    		    volume14(14),
    		    volumea(65),
    		    volume1a(100),
    		    volume1b(101),
    		    volume2a(200),
    		    volume2b(201),
    		    volume3a(300),
    		    volume3b(301),
    		    volume4a(400),
    		    volume4b(401),
                    volume5a(500),
                    volume5b(501),
                    volume6a(600),
                    volume6b(601),
                    volume7a(700),
                    volume7b(701),
                    volume8a(800),
                    volume8b(801),
                    volume9a(900),
                    volume9b(901),
                    volume10a(1000),
                    volume10b(1001),
                    volume11a(1100),
                    volume11b(1101),
                    volume12a(1200),
                    volume12b(1201),
                    volume13a(1300),
                    volume13b(1301),
                    volume14a(1400),
                    volume14b(1401)
    		}
        ACCESS	read-write
        STATUS	mandatory
        DESCRIPTION
                "The file system volume number to which transferred files will
                be written and from which they will be retrieved. The volume
                number corresponds to the slot number on which the volume
                resides. On systems with a floppy disk, volumeA(65) should be
                used."
        DEFVAL	{ volume2 }
        ::= { wfFtp 3 }

    wfFtpLoginRetries OBJECT-TYPE
        SYNTAX	INTEGER
        ACCESS	read-write
        STATUS	mandatory
        DESCRIPTION
                "Number of ftp login retries allowed after a login failure.
                Default is 3"
        DEFVAL	{ 3 }
        ::= { wfFtp 4 }

    wfFtpIdleTimeOut OBJECT-TYPE
        SYNTAX	INTEGER
        ACCESS	read-write
        STATUS	mandatory
        DESCRIPTION
                "Time out in seconds to close the FTP control connection
                if the connection remains idle."
        DEFVAL	{ 900 }
        ::= { wfFtp 5 }

    wfFtpMaxSessions OBJECT-TYPE
        SYNTAX	INTEGER
        ACCESS	read-write
        STATUS	mandatory
        DESCRIPTION
                "Maximum number of FTP sessions allowed at one time"
        DEFVAL	{ 3 }
        ::= { wfFtp 6 }

    wfFtpType OBJECT-TYPE
        SYNTAX	INTEGER {
    		    ascii(1),
    		    binary(2)
    		}
        ACCESS	read-write
        STATUS	mandatory
        DESCRIPTION
                "Current data transmission type"
        DEFVAL	{ binary }
        ::= { wfFtp 7 }

    wfFtpCtrlIpTos OBJECT-TYPE
        SYNTAX	INTEGER {
    		    normal(1),
    		    lowdelay(2)
    		}
        ACCESS	read-write
        STATUS	obsolete
        DESCRIPTION
                "The Type Of Service value set in the IP datagram specifies
                to the Internet transport layer how the datagram should
                be handled. For FTP control connection low delay is the default"
        DEFVAL	{ lowdelay }
        ::= { wfFtp 8 }

    wfFtpDataIpTos OBJECT-TYPE
        SYNTAX	INTEGER {
    		    normal(1),
    		    highthroughput(2)
    		}
        ACCESS	read-write
        STATUS	obsolete
        DESCRIPTION
                "The Type Of Service value set in the IP datagram specifies
                to the Internet transport layer how the datagram should
                be handled. For FTP data transfers high throughput is the default"
        DEFVAL	{ highthroughput }
        ::= { wfFtp 9 }

    wfFtpTcpWindowSize OBJECT-TYPE
        SYNTAX	INTEGER(5000..64000)
        ACCESS	read-write
        STATUS	mandatory
        DESCRIPTION
                "The size in bytes of the windows used for WfFTP TCP connections"
        DEFVAL	{ 60000 }
        ::= { wfFtp 10 }

    wfFtpLogins OBJECT-TYPE
        SYNTAX	Counter
        ACCESS	read-only
        STATUS	mandatory
        DESCRIPTION
                "Number of attempted logins"
        ::= { wfFtp 11 }

    wfFtpManagerLoginFails OBJECT-TYPE
        SYNTAX	Counter
        ACCESS	read-only
        STATUS	mandatory
        DESCRIPTION
                "Number of manager logins that failed"
        ::= { wfFtp 12 }

    wfFtpOtherLoginFails OBJECT-TYPE
        SYNTAX	Counter
        ACCESS	read-only
        STATUS	mandatory
        DESCRIPTION
                "Number of logins other than manager logins that failed"
        ::= { wfFtp 13 }

    wfFtpXfers OBJECT-TYPE
        SYNTAX	Counter
        ACCESS	read-only
        STATUS	mandatory
        DESCRIPTION
                "Number of Transfers in Progress"
        ::= { wfFtp 14 }

    wfFtpInFiles OBJECT-TYPE
        SYNTAX	Counter
        ACCESS	read-only
        STATUS	mandatory
        DESCRIPTION
                "Number of files Successfully received"
        ::= { wfFtp 15 }

    wfFtpOutFiles OBJECT-TYPE
        SYNTAX	Counter
        ACCESS	read-only
        STATUS	mandatory
        DESCRIPTION
                "Number of files Successfully sent"
        ::= { wfFtp 16 }

    wfFtpInErrs OBJECT-TYPE
        SYNTAX	Counter
        ACCESS	read-only
        STATUS	mandatory
        DESCRIPTION
                "Number of errors logged during in bound transfer"
        ::= { wfFtp 17 }

    wfFtpOutErrs OBJECT-TYPE
        SYNTAX	Counter
        ACCESS	read-only
        STATUS	mandatory
        DESCRIPTION
                "Number of errors logged during out bound transfer"
        ::= { wfFtp 18 }

    wfFtpAborts OBJECT-TYPE
        SYNTAX	Counter
        ACCESS	read-only
        STATUS	mandatory
        DESCRIPTION
                "Number of transfer aborts"
        ::= { wfFtp 19 }

    wfFtpInXferRate OBJECT-TYPE
        SYNTAX	Gauge
        ACCESS	read-only
        STATUS	mandatory
        DESCRIPTION
                "Average transfer rate in kbytes per second for receiving data"
        ::= { wfFtp 20 }

    wfFtpOutXferRate OBJECT-TYPE
        SYNTAX	Gauge
        ACCESS	read-only
        STATUS	mandatory
        DESCRIPTION
                "Average transfer rate in kbytes per second for sending data"
        ::= { wfFtp 21 }

    END  -- Wellfleet-FTP-MIB
