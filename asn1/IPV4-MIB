IPV4-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, Gauge32, IpAddress
			FROM SNMPv2-SMI
		TruthValue,RowStatus
			FROM SNMPv2-TC
		apIpv4
			FROM APENT-MIB
		TRAP-TYPE
			FROM RFC-1215;


    apIpv4Mib MODULE-IDENTITY
	   LAST-UPDATED "9801282000Z" -- Wed January 28 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for IPv4 Global Information"
      ::= { apIpv4 1}

--arrowpoint
-- apmgmt
--  ipv4Ext
--   apIpv4
--     apIpv4SourceRoute
--     apIpv4RecordRoute
--     apIpv4EcmpMethod
--     apIpv4OrphanTimer
--     apIpv4ReachRoutes
--     apIpv4ReachRoutesMem
--     apIpv4TotalRoutes
--     apIpv4TotalRoutesMem
--     apIpv4ReachHosts
--     apIpv4ReachHostsMem
--     apIpv4TotalHosts
--     apIpv4TotalHostsMem
--     apIpv4PoolMem
--     apIpv4B2BRedundancy
--     apIpv4Opportunistic
--     apIpv4RedundancyState
--     apIpv4RedundancyIf
--     apIpv4RedundancyMasterMode
--     apIpv4RedundancyTrap
--     apIpv4EcmpSticky
--     apIpv4ImplicitService
--     apIpv4RedundancyLinkFailTable
--     apIpv4RedundancyFailReason
--     apIpv4VrrpVRID
--     apIpv4VrrpPriority
--     apIpv4numUplinkServices
--     apIpv4numViableUplinks
--     apIpv4numPhylinkMarked
--     apIpv4toMasterStateCnt
--     apIpv4toBackupStateCnt

-- IPv4 configuration information

apIpv4SourceRoute OBJECT-TYPE
	SYNTAX      INTEGER {
			    enable (1),
			    disable (2)
			    }
	MAX-ACCESS  read-write
	STATUS      current
	DESCRIPTION
	       "If enabled, IP packets with a source route option will be
            processed.  If disabled, they are dropped."
	DEFVAL {2}
	::= {apIpv4 2}

apIpv4RecordRoute OBJECT-TYPE
	SYNTAX      INTEGER {
			    enable (1),
			    disable (2)
			    }
	MAX-ACCESS  read-write
	STATUS      current
	DESCRIPTION
	       "If enabled, IP packets with a record route option will be
            processed.  If disabled, they are dropped."
	DEFVAL {2}
	::= {apIpv4 3}

apIpv4SubnetBcast OBJECT-TYPE
	SYNTAX      INTEGER {
			    enable (1),
			    disable (2)
			    }
	MAX-ACCESS  read-write
	STATUS      current
	DESCRIPTION
	       "If enabled, IP packets addressed to a broadcast address of a local
            subnet will be forwarded.  If disabled, they are dropped."
	DEFVAL {2}
	::= {apIpv4 4}

apIpv4EcmpMethod OBJECT-TYPE
	SYNTAX      INTEGER {
			    address (1),
			    round (2)
			    }
	MAX-ACCESS  read-write
	STATUS      current
	DESCRIPTION
	       "Defines the algorithm to use when multiple equal-cost paths are
            available to the same destination.  'address' uses the IP addresses
            to assign a path.  'round' does a simple round-robin."
	DEFVAL {1}
	::= {apIpv4 5}

apIpv4OrphanTimer OBJECT-TYPE
	SYNTAX      INTEGER
	MAX-ACCESS  read-write
	STATUS      current
	DESCRIPTION
	       "The amount of time, in seconds, that a route will be kept after
            an SCM recovery.  Default is 3 minutes."
	DEFVAL {180}
	::= {apIpv4 6}

apIpv4LogRouteChanges OBJECT-TYPE
	SYNTAX      INTEGER {
			    enable (1),
			    disable (2)
			    }
	MAX-ACCESS  read-write
	STATUS      current
	DESCRIPTION
	       "If enabled, IP route changes will be displayed in the system log."
	DEFVAL {2}
	::= {apIpv4 7}

apIpv4ReachRoutes OBJECT-TYPE
	SYNTAX      Gauge32
	MAX-ACCESS  read-only
	STATUS      current
	DESCRIPTION
	       "Current number of reachable routes."
	::= {apIpv4 8}

apIpv4ReachRoutesMem OBJECT-TYPE
	SYNTAX      Gauge32
	MAX-ACCESS  read-only
	STATUS      current
	DESCRIPTION
	       "Amount of memory used to maintain reachable routes."
	::= {apIpv4 9}

apIpv4TotalRoutes OBJECT-TYPE
	SYNTAX      Gauge32
	MAX-ACCESS  read-only
	STATUS      current
	DESCRIPTION
	       "Current number of routes maintainted, both reachable and
            unreachable."
	::= {apIpv4 10}

apIpv4TotalRoutesMem OBJECT-TYPE
	SYNTAX      Gauge32
	MAX-ACCESS  read-only
	STATUS      current
	DESCRIPTION
	       "Amount of memory used to maintain all routes."
	::= {apIpv4 11}

apIpv4ReachHosts OBJECT-TYPE
	SYNTAX      Gauge32
	MAX-ACCESS  read-only
	STATUS      current
	DESCRIPTION
	       "Current number of reachable host entries."
	::= {apIpv4 12}

apIpv4ReachHostsMem OBJECT-TYPE
	SYNTAX      Gauge32
	MAX-ACCESS  read-only
	STATUS      current
	DESCRIPTION
	       "Amount of memory used to maintain reachable host entries."
	::= {apIpv4 13}

apIpv4TotalHosts OBJECT-TYPE
	SYNTAX      Gauge32
	MAX-ACCESS  read-only
	STATUS      current
	DESCRIPTION
	       "Current number of host entries maintainted, both reachable and
            unreachable."
	::= {apIpv4 14}

apIpv4TotalHostsMem OBJECT-TYPE
	SYNTAX      Gauge32
	MAX-ACCESS  read-only
	STATUS      current
	DESCRIPTION
	       "Amount of memory used to maintain all host entries."
	::= {apIpv4 15}

apIpv4PoolMem OBJECT-TYPE
	SYNTAX      Gauge32
	MAX-ACCESS  read-only
	STATUS      current
	DESCRIPTION
	       "Amount of memory held in IP routing table pool."
	::= {apIpv4 16}

apIpv4B2BRedundancy OBJECT-TYPE
	SYNTAX      TruthValue
	MAX-ACCESS  read-write
	STATUS      current
    DESCRIPTION
           "Indicates whether box-to-box redundancy is configured on
            this box."
	DEFVAL { false }
    ::= { apIpv4 17 }

apIpv4Opportunistic OBJECT-TYPE
	SYNTAX      INTEGER {
			    local (1),
			    all (2),
			    disable (3)
			    }
	MAX-ACCESS  read-write
	STATUS      current
    DESCRIPTION
           "Indicates the operating mode for layer-3 opportunistic forwarding.
            In 'local' mode (the default), packets whose IP address equals
            a resolved node attached to a local subnet will be forwarded
            to that node regardless of the destination MAC address of the
            packet.  In 'all' mode, packets whose IP address matches any
            reachable IP routing entry will be forwarded according to the
            routing entry regardless of the destination MAC address of the
            packet.  In 'disable' mode, only packets whose destination MAC
            address equal this node's MAC address will be forwarded using
            an IP route entry."
	DEFVAL { local }
    ::= { apIpv4 18 }

apIpv4RedundancyState  OBJECT-TYPE
	SYNTAX  INTEGER {
					init(1),
					backup(2),
					master(3)
 					}
	MAX-ACCESS      read-only
	STATUS 			current
	DESCRIPTION     
		"The current redundancy state"
	DEFVAL { init }
	::= { apIpv4 19 }

apIpv4RedundancyIf  OBJECT-TYPE
	SYNTAX  	IpAddress
	MAX-ACCESS  read-only
	STATUS 		current
	DESCRIPTION     
		"The IP address of the redundant link"
	-- DEFVAL {'00000000'H }   0.0.0.0
	::= { apIpv4 20 }

apIpv4RedundancyMaster  OBJECT-TYPE
	SYNTAX      IpAddress
	MAX-ACCESS  read-only
	STATUS 		current
	DESCRIPTION     
		"The IP address of the redundant Master"
	-- DEFVAL {'00000000'H }   0.0.0.0
	::= { apIpv4 21 }

apIpv4RedundancyMasterMode  OBJECT-TYPE
	SYNTAX      TruthValue
	MAX-ACCESS  read-write
	STATUS      current
    DESCRIPTION
           "Indicates whether box-to-box redundancy is configured to
            always be the master."
	DEFVAL { false }
    ::= { apIpv4 22 }

apIpv4EcmpSticky OBJECT-TYPE
	SYNTAX INTEGER {
			enabled(1)                                ,
			disabled(0)                                   
	}
	MAX-ACCESS read-write
	STATUS current
	DESCRIPTION
		"This object specifies whether when making an ECMP
         decision on the return port, should the ingress
         port be the preferred path."
	DEFVAL { 1 }
    ::= { apIpv4 23 }

apIpv4ImplicitService OBJECT-TYPE
	SYNTAX INTEGER {
			enabled(1)                                              ,
			disabled(0)                                                     
	}
	MAX-ACCESS read-write
	STATUS current
	DESCRIPTION
		"This object specifies whether when configuring a static
         route, if an implicit service should be started for the
         next hop address."
	DEFVAL { 1 }
    ::= { apIpv4 24 }


apIpv4RedundancyLinkFailTable OBJECT-TYPE
   SYNTAX SEQUENCE OF APIpv4RedundancyLinkFailEntry
	MAX-ACCESS  not-accessible
	STATUS  current
	DESCRIPTION
		"The IP redundancy Interface failure monitor table."
	::= { apIpv4 25 }

apIpv4RedundancyLinkFailEntry OBJECT-TYPE
	SYNTAX  APIpv4RedundancyLinkFailEntry
	MAX-ACCESS  not-accessible
	STATUS  current
	DESCRIPTION
		"An entry in the IP redundancy Interface failure monitor table."
	INDEX   { apIpv4RedundancyLinkFailIfIndex }
	::= { apIpv4RedundancyLinkFailTable 1 }

APIpv4RedundancyLinkFailEntry ::=
    SEQUENCE {
	    apIpv4RedundancyLinkFailIfIndex
		      INTEGER,
            apIpv4RedundancyLinkStatus
		      RowStatus
       	     }

apIpv4RedundancyLinkFailIfIndex OBJECT-TYPE
	SYNTAX INTEGER (1..1024)
	MAX-ACCESS read-create
	STATUS current
	DESCRIPTION 
	    "Interface Index used to uniquely identify ethernet interface  "
     ::= {apIpv4RedundancyLinkFailEntry 1}


apIpv4RedundancyLinkStatus OBJECT-TYPE
   SYNTAX RowStatus
   MAX-ACCESS  read-create
   STATUS      current
   DESCRIPTION
           "Monitor this interface for physical link failure if true"
	::= { apIpv4RedundancyLinkFailEntry 2 }

apIpv4RedundancyFailReason OBJECT-TYPE
    SYNTAX INTEGER {
        		noFailure(0),
			phylinkFail(1),
			uplinkFailure(2),
			otherSwitchAssertMaster(3)
 	       	   }
   MAX-ACCESS    read-only
   STATUS 	current
	DESCRIPTION     
		"The redundancy state change reason"
	DEFVAL { noFailure }
	::= { apIpv4 26 }

apIpv4VrrpVRID OBJECT-TYPE
	SYNTAX INTEGER(0..255)
	MAX-ACCESS read-only
	STATUS current
	DESCRIPTION
		"This object tells virtual router ID in vrrp protocol."
        DEFVAL {0}
	::= { apIpv4 27 }

apIpv4VrrpPriority OBJECT-TYPE
	SYNTAX INTEGER(0..255)
	MAX-ACCESS read-only
	STATUS current
	DESCRIPTION
		"This object tells virtual router priority in vrrp."
        DEFVAL {0}
	::= { apIpv4 28 }

apIpv4numUplinkServices OBJECT-TYPE
	SYNTAX INTEGER(0..512)
	MAX-ACCESS read-only
	STATUS current
	DESCRIPTION
		"This object tells number of uplink services enabled."
        DEFVAL {0}
	::= { apIpv4 29 }

apIpv4numViableUplinks OBJECT-TYPE
	SYNTAX INTEGER(0..512)
	MAX-ACCESS read-only
	STATUS current
	DESCRIPTION
		"This object tells number of uplink services alive."
        DEFVAL {0}
	::= { apIpv4 30 }

apIpv4numPhylinkMarked OBJECT-TYPE
	SYNTAX INTEGER(0..5)
	MAX-ACCESS read-only
	STATUS current
	DESCRIPTION
		"This object tells number of redundant-physical links monitored."
        DEFVAL {0}
	::= { apIpv4 31 }

apIpv4toMasterStateCnt OBJECT-TYPE
	SYNTAX INTEGER(0..1024)
	MAX-ACCESS read-only
	STATUS current
	DESCRIPTION
		"This object tells number of times the box become master."
        DEFVAL {0}
	::= { apIpv4 32 }

apIpv4toBackupStateCnt OBJECT-TYPE
	SYNTAX INTEGER(0..1024)
	MAX-ACCESS read-only
	STATUS current
	DESCRIPTION
		"This object tells number of times the box become backup."
        DEFVAL {0}
	::= { apIpv4 33 }

apIpv4RedundancyTrap TRAP-TYPE
	ENTERPRISE apIpv4
	DESCRIPTION
	   "This trap is generated when the state of Redundancy changes."
	::= 1
END
