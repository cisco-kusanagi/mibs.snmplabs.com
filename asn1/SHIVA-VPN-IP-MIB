SHIVA-VPN-IP-MIB DEFINITIONS ::= BEGIN

IMPORTS
  Counter
      FROM RFC1155-SMI
  OBJECT-TYPE
      FROM RFC-1212
  ifIndex
      FROM RFC1213-MIB
  vpnIp
      FROM SHIVA-VPN-DEF;

  ipConfig OBJECT IDENTIFIER ::= { vpnIp 1 }
  ipStatus OBJECT IDENTIFIER ::= { vpnIp 2 }

  ipIfTable OBJECT-TYPE
      SYNTAX SEQUENCE OF IpIfEntry
      ACCESS not-accessible
      STATUS mandatory
      DESCRIPTION
          "The (conceptual) table containing information
           on configured interfaces running the IP protocol.
           This table augments the ifTable for tunnel
           interfaces." -- ** CHANGED FROM "non-tunnel"; the counter
           -- descriptions do not seem to make sense otherwise.
      ::= { ipStatus 50 }

  ipIfEntry OBJECT-TYPE
      SYNTAX IpIfEntry
      ACCESS not-accessible
      STATUS mandatory
      DESCRIPTION
          "An entry (conceptual row) containing the information
           on a particular IP interface."
      INDEX { ifIndex }
      ::= { ipIfTable 1 }

  IpIfEntry ::=
      SEQUENCE {
          ipIfInPkts
              Counter,
          ipIfOutPkts
              Counter,
          ipIfInOctets
              Counter,
          ipIfOutOctets
              Counter
      }

  ipIfInPkts OBJECT-TYPE
      SYNTAX Counter
      ACCESS read-only
      STATUS mandatory
      DESCRIPTION
          "The number of packets passed in to the IP
           layer on this interface."
      ::= { ipIfEntry 1 }

  ipIfOutPkts OBJECT-TYPE
      SYNTAX Counter
      ACCESS read-only
      STATUS mandatory
      DESCRIPTION
          "The number of packets passed out from the IP
           layer on this interface."
      ::= { ipIfEntry 2 }

  ipIfInOctets OBJECT-TYPE
      SYNTAX Counter
      ACCESS read-only
      STATUS mandatory
      DESCRIPTION
          "The number of bytes passed in to the IP
           layer on this interface.  This includes
           only the length of the IP packets proper,
           not any encapsulation from lower layers or
           tunnels."
      ::= { ipIfEntry 3 }

  ipIfOutOctets OBJECT-TYPE
      SYNTAX Counter
      ACCESS read-only
      STATUS mandatory
      DESCRIPTION
          "The number of bytes passed out from the IP
           layer on this interface.  This includes
           only the length of the IP packets proper,
           not any encapsulation for lower layers or
           tunnels."
      ::= { ipIfEntry 4 }

END
