-- extracted from draft-glenn-id-sensor-alert-mib-01.txt
-- at Sat Nov 25 16:04:49 2000

   INTRUSION-DETECTION-SENSOR-ALERT-MIB DEFINITIONS ::= BEGIN

    IMPORTS
      MODULE-IDENTITY,  Counter32, Gauge32, OBJECT-TYPE,
      OBJECT-IDENTITY,  mib-2      FROM SNMPv2-SMI
      DateAndTime, TimeStamp
                 FROM SNMPv2-TC
      MODULE-COMPLIANCE, OBJECT-GROUP
                 FROM SNMPv2-CONF
      SnmpEngineID, SnmpAdminString
                 FROM SNMP-FRAMEWORK-MIB
      InetAddressType, InetAddress
                 FROM INET-ADDRESS-MIB
      URLString
                 FROM NETWORK-SERVICES-MIB;

   idsaMIB MODULE-IDENTITY
       LAST-UPDATED "200011160000Z"        --  16th November 2000
       ORGANIZATION "IETF Intrusion Detection Message Exchange Format
                     Working Group"
       CONTACT-INFO
      "                      Glenn Mansfield
                     Postal: Cyber Solutions Inc.
                             6-6-3, Minami Yoshinari
                             Aoba-ku, Sendai, Japan 989-3204.

                        Tel: +81-22-303-4012
                        Fax: +81-22-303-4015
                     E-mail: glenn@cysols.com

                             Dipankar Gupta
                     Postal: Hewlett Packard Company
                             690 East Middlefield Road, MS 31R
                             Mountain View California 94043.

                        Tel: +1-650-919-8066
                        Fax: +1-650-919-8540
                     E-mail: dipankar_gupta@hp.com

       Working Group E-mail: idwg-public@zurich.ibm.com
               To subscribe: idwg-public-request@zurich.ibm.com"

       DESCRIPTION
               " The MIB for Intrusion Detection Messages."
            ::= { mib-2 xxx }     -- to be assigned by IANA

    idsaSensorObjects OBJECT-IDENTITY
        STATUS current
        DESCRIPTION
          " This is the base object for the objects used in the
            notifications."
        ::= {idsaMIB 1}

    idsaSensorID OBJECT-TYPE
        SYNTAX  SnmpAdminString
        MAX-ACCESS  read-only
        STATUS  current
        DESCRIPTION
          " An identifier to uniquely identify the Analyzer
            in the domain."
        ::= { idsaSensorObjects 1 }

    idsaSensorDescription OBJECT-TYPE
        SYNTAX  SnmpAdminString
        MAX-ACCESS  read-only
        STATUS  current
        DESCRIPTION
          " A short description of the Sensor."
        ::= { idsaSensorObjects 2 }

    idsaSensorProductID OBJECT-TYPE
        SYNTAX  SnmpAdminString
        MAX-ACCESS  read-only
        STATUS  current
        DESCRIPTION
          "A reference to MIB definitions specific to the
           analyzer generating the message.  If this information
           is not present, its value should be set to the OBJECT
           IDENTIFIER { 0 0 }, which is a syntatically valid
           object identifier."
        ::= { idsaSensorObjects 3 }

    idsaSensorAddressType OBJECT-TYPE
        SYNTAX InetAddressType
        MAX-ACCESS read-only
        STATUS current
        DESCRIPTION
          "The type of the address which follows."
        ::= { idsaSensorObjects 4}

    idsaSensorAddress OBJECT-TYPE
        SYNTAX InetAddress
        MAX-ACCESS read-only
        STATUS current
        DESCRIPTION
          "The Internet address of the sensor."
        ::= { idsaSensorObjects 5}

    idsaSensorManufacturer   OBJECT-TYPE
        SYNTAX SnmpAdminString
        MAX-ACCESS read-only
        STATUS current
        DESCRIPTION
          " the Manufacturer of the sensor that detected the event."
        ::= { idsaSensorObjects 6}

    idsaSensorProductName   OBJECT-TYPE
        SYNTAX SnmpAdminString
        MAX-ACCESS read-only
        STATUS current
        DESCRIPTION
          " the name of the product that detected the event."
        ::= { idsaSensorObjects 7}

    idsaSensorVersion   OBJECT-TYPE
        SYNTAX SnmpAdminString
        MAX-ACCESS read-only
        STATUS current
        DESCRIPTION
          " the version number of the sensor that detected the event."
        ::= { idsaSensorObjects 8}


    idsaSensorLocation OBJECT-TYPE
        SYNTAX SnmpAdminString
        MAX-ACCESS read-only
        STATUS current
        DESCRIPTION
          " the location of the tool that detected the event."
        ::= { idsaSensorObjects 9}


    idsaAlerts OBJECT-IDENTITY
        STATUS current
        DESCRIPTION
          " This is the base object for the subtree of objects defining
            the alerts."
        ::= {idsaMIB 2}

   --  idsaAlertTable: The Table of Alerts. Each row represents an Alert.
   --  idsaAlertID is the key to the table. The size of this table will be
   --  implementation dependent - some implementors may choose to keep
   --  a maximum of one messages in this table.

    idsaAlertTable OBJECT-TYPE
        SYNTAX  SEQUENCE OF IdsaAlertEntry
        MAX-ACCESS  not-accessible
        STATUS  current
        DESCRIPTION
          " Each row of this table contains information
            about an alert indexed by idsaAlertID."
        ::= { idsaAlerts 1 }

    idsaAlertEntry OBJECT-TYPE
        SYNTAX  IdsaAlertEntry
        MAX-ACCESS  not-accessible
        STATUS  current
        DESCRIPTION
          " Entry containing information pertaining to
            an alert."
        INDEX { idsaAlertID}
        ::= { idsaAlertTable 1 }

    IdsaAlertEntry ::= SEQUENCE {
       idsaAlertID
                 INTEGER,
       idsaAlertLocalAddressType
                 InetAddressType,
       idsaAlertLocalAddress
                 InetAddress,
       idsaAlertInterfaceIndex
                 INTEGER,
       idsaAlertTimeStamp
                 DateAndTime,
       idsaAlertActionsTaken
                 INTEGER,
       idsaAlertAttackName
                 SnmpAdminString,
       idsaAlertMoreInfo
                 URLString,
       idsaAlertSrcAddressType
                 InetAddressType,
       idsaAlertSrcAddress
                 InetAddress,
       idsaAlertDstAddressType
                  InetAddressType,
       idsaAlertDstAddress
                  InetAddress,

       idsaAlertSrcPort
                  INTEGER,
       idsaAlertDstPort
                  INTEGER
       }


    idsaAlertID OBJECT-TYPE
        SYNTAX INTEGER (1..65535)
        MAX-ACCESS read-only
        STATUS current
        DESCRIPTION
          " The AlertID uniquely identifies each alert generated
            by the sensor."
        ::= {idsaAlertEntry 1}

    idsaAlertLocalAddressType OBJECT-TYPE
        SYNTAX InetAddressType
        MAX-ACCESS read-only
        STATUS current
        DESCRIPTION
          "The type of the address which follows."
        ::= { idsaAlertEntry 2}

    idsaAlertLocalAddress OBJECT-TYPE
        SYNTAX InetAddress
        MAX-ACCESS read-only
        STATUS current
        DESCRIPTION
          "The Internet address associated with the alert ."
        ::= { idsaAlertEntry 3}

    idsaAlertInterfaceIndex OBJECT-TYPE
        SYNTAX INTEGER (1..65535)
        MAX-ACCESS read-only
        STATUS current
        DESCRIPTION
          " The ifIndex of the interface on which the event was
            detected  by the sensor."
        ::= {idsaAlertEntry 4}

    idsaAlertTimeStamp OBJECT-TYPE
        SYNTAX DateAndTime
        MAX-ACCESS read-only
        STATUS current
        DESCRIPTION
          " The local date and time when this alert was generated."
        ::= { idsaAlertEntry 5}

    -- the actions will probably be a comma separated list of action
    -- codes or a pointer to another MIB table from which the actions
    -- may be fetched.
    --
    idsaAlertActionsTaken OBJECT-TYPE
        SYNTAX SnmpAdminString
        MAX-ACCESS read-only
        STATUS current
        DESCRIPTION
          " The list of automatic actions taken by the sensor"
        ::= { idsaAlertEntry 6}

    -- SnmpAdminString length is 255 characters max. It contains
    -- information represented using the ISO/IEC IS 10646-1 character
    -- set, encoded using the UTF-8 transformation format to facilitate
    -- internationalization.

    idsaAlertAttackName OBJECT-TYPE
        SYNTAX SnmpAdminString
        MAX-ACCESS read-only
        STATUS current
        DESCRIPTION
          " the name of the atack, if known. If not known this field will
                  be inaccessile."
        ::= { idsaAlertEntry 7}

    idsaAlertMoreInfo OBJECT-TYPE
        SYNTAX  OBJECT IDENTIFIER
        MAX-ACCESS  read-only
        STATUS  current
        DESCRIPTION
          "A reference to MIB definitions specific to this
          message.  If this information is not
          present, its value should be set to the OBJECT
          IDENTIFIER { 0 0 }, which is a syntatically valid
          object identifier."
        ::= { idsaAlertEntry 8}

    idsaAlertSrcAddressType OBJECT-TYPE
        SYNTAX InetAddressType
        MAX-ACCESS read-only
        STATUS current
        DESCRIPTION
          "The type of the Internet address that was the attack source."
        ::= { idsaAlertEntry 9}

    idsaAlertSrcAddress OBJECT-TYPE
        SYNTAX InetAddress
        MAX-ACCESS read-only
        STATUS current
        DESCRIPTION
          " The Internet addresses of the entity from which the attack
            originated, if known. "
        ::= { idsaAlertEntry 10}

    idsaAlertDstAddressType OBJECT-TYPE
        SYNTAX InetAddressType
        MAX-ACCESS read-only
        STATUS current
        DESCRIPTION
          "The type of the Internet address that was the attack target."
        ::= { idsaAlertEntry 11}

    idsaAlertDstAddress OBJECT-TYPE
        SYNTAX InetAddress
        MAX-ACCESS read-only
        STATUS current
        DESCRIPTION
          " The Internet address of the entity to which the attack
            was destined, if known."
        ::= { idsaAlertEntry 12}

    idsaAlertSrcPort OBJECT-TYPE
        SYNTAX INTEGER
        MAX-ACCESS read-only
        STATUS current
        DESCRIPTION
          " The port number from where the attack has originated "
        ::= { idsaAlertEntry 13}

    idsaAlertDstPort OBJECT-TYPE
        SYNTAX INTEGER
        MAX-ACCESS read-only
        STATUS current
        DESCRIPTION
          " The port number to which the attack is destined "
        ::= { idsaAlertEntry 14}

    -- Conformance information

    idsaConformance OBJECT IDENTIFIER ::= {idsaMIB 3 }

    idsaGroups      OBJECT IDENTIFIER ::= { idsaConformance 1 }
    idsaCompliances OBJECT IDENTIFIER ::= { idsaConformance 2 }

    -- Compliance statements

    idsaAlertCompliance MODULE-COMPLIANCE
        STATUS  current
        DESCRIPTION
                "The compliance statement for SNMP entities
                 which implement the
                            INTRUSION-DETECTION-SENSOR-ALERT-MIB."

        MODULE  -- this module
            MANDATORY-GROUPS { idsaAlertGroup }

        ::= { idsaCompliances 1 }

    -- Units of conformance

    idsaAlertGroup    OBJECT-GROUP
        OBJECTS {
                    idsaSensorID,
                    idsaSensorDescription,
                    idsaSensorProductID,
                    idsaSensorAddressType,
                    idsaSensorAddress,
                    idsaSensorManufacturer,
                    idsaSensorProductName,
                    idsaSensorVersion,
                    idsaSensorLocation,
                    idsaAlertID,
                    idsaAlertLocalAddressType,
                    idsaAlertLocalAddress,
                    idsaAlertInterfaceIndex,
                    idsaAlertTimeStamp,
                    idsaAlertActionsTaken,
                    idsaAlertAttackName,
                    idsaAlertMoreInfo,
                    idsaAlertSrcAddressType,
                    idsaAlertSrcAddress,
                    idsaAlertDstAddressType,
                    idsaAlertDstAddress,
                    idsaAlertSrcPort,
                    idsaAlertDstPort

       }
        STATUS  current
        DESCRIPTION
                " A collection of objects for generation and despatch of
                  alerts pertaining to intrusions detected."
        ::= { idsaGroups 1 }

   END

-- 
--          "Copyright (C) The Internet Society (date). All Rights
--          Reserved.
-- 
--          This document and translations of it may be copied and
--          furnished to others, and derivative works that comment on or
--          otherwise explain it or assist in its implmentation may be
--          prepared, copied, published and distributed, in whole or in
--          part, without restriction of any kind, provided that the above
--          copyright notice and this paragraph are included on all such
--          copies and derivative works.  However, this document itself may
--          not be modified in any way, such as by removing the copyright
--          notice or references to the Internet Society or other Internet
--          organizations, except as needed for the  purpose of developing
--          Internet standards in which case the procedures for copyrights
--          defined in the Internet Standards process must be followed, or
--          as required to translate it into languages other than English.
-- 
--          The limited permissions granted above are perpetual and will
--          not be revoked by the Internet Society or its successors or
--          assigns.
-- 
--          This document and the information contained herein is provided
--          on an "AS IS" basis and THE INTERNET SOCIETY AND THE INTERNET
--          ENGINEERING TASK FORCE DISCLAIMS ALL WARRANTIES, EXPRESS OR
--          IMPLIED, INCLUDING BUT NOT LIMITED TO ANY WARRANTY THAT THE USE
--          OF THE INFORMATION HEREIN WILL NOT INFRINGE ANY RIGHTS OR ANY
--          IMPLIED WARRANTIES OF MERCHANTABILITY OR FITNESS FOR A
--          PARTICULAR PURPOSE."
