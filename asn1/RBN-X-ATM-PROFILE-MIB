-- *****************************************************************
-- RBN-X-ATM-PROFILE-MIB
--
-- Copyright (c) 1998 RedBack Networks, Inc.
-- All rights reserved.
-- 
-- *****************************************************************

RBN-X-ATM-PROFILE-MIB DEFINITIONS ::= BEGIN

IMPORTS
	MODULE-IDENTITY,
	OBJECT-TYPE
		FROM SNMPv2-SMI
	MODULE-COMPLIANCE,
	OBJECT-GROUP
		FROM SNMPv2-CONF
	atmTrafficDescrParamEntry
		FROM ATM-MIB
	rbnExperiment
		FROM RBN-SMI;

rbnXAtmProfileMIB MODULE-IDENTITY
	LAST-UPDATED	"9807161645Z"
	ORGANIZATION	"RedBack Networks, Inc."
	CONTACT-INFO
		"	RedBack Networks, Inc.

		Postal:	1389 Moffett Park Drive
			Sunnyvale, CA  94089-1134
			USA

		 Phone:	+1 408 548 3500
		   Fax: +1 408 548 3599

		E-mail:	mib-info@RedBackNetworks.com"
	DESCRIPTION
		"The MIB for instrumenting parameters associated with
		an ATM profile (traffic descriptor) beyond those
		instrumented by standards-track	MIBs.  This MIB is
		positioned in the RedBack Networks experimental MIB
		space because it mirrors MIB objects currently being
		developed by the IETF atommib Working Group, namely
		additions to the atmTrafficDescrParamTable found in
		the revised ATM-MIB (draft-ietf-atommib-atm1ng-XX.txt).
		At such time as the revised ATM-MIB superceeds the one
		defined in RFC 1695. this MIB will be obsoleted in favor
		of the IETF one."
	::= { rbnExperiment 2 }


rbnXAtmProfileMIBObjects OBJECT IDENTIFIER ::= { rbnXAtmProfileMIB 1 }

rbnXAtmProfileTable   OBJECT-TYPE
	SYNTAX       SEQUENCE OF RbnXAtmProfileEntry
	MAX-ACCESS   not-accessible
	STATUS       current
	DESCRIPTION
		"This table provides a collection of auxiliary
		objects	providing parameters for atm profiles."
	::= { rbnXAtmProfileMIBObjects 1 }

rbnXAtmProfileEntry    OBJECT-TYPE
	SYNTAX       RbnXAtmProfileEntry
	MAX-ACCESS   not-accessible
	STATUS       current
	DESCRIPTION
		"Each entry in this table represents a profile."
	AUGMENTS { atmTrafficDescrParamEntry }
	::= { rbnXAtmProfileTable 1 }


RbnXAtmProfileEntry ::=
	SEQUENCE {
		rbnXAtmServiceCategory	    INTEGER
	}


rbnXAtmServiceCategory  OBJECT-TYPE
	SYNTAX       INTEGER {
                     other(1),   -- none of the following
                     cbr(2),     -- constant bit rate
                     rtVbr(3),   -- real-time variable bit rate
                     nrtVbr(4),  -- non real-time variable bit rate
                     abr(5),     -- available bit rate
                     ubr(6)      -- unspecified bit rate
		     }
	MAX-ACCESS   read-create
	STATUS       current
	DESCRIPTION
		"The service category for circuits which reference
		the given profile."
	::= { rbnXAtmProfileEntry 1 }

-- Conformance Information

rbnXAtmProfileMIBConformance OBJECT IDENTIFIER ::=
	{ rbnXAtmProfileMIB 2 }

rbnXAtmProfileMIBGroups OBJECT IDENTIFIER ::= 
	{ rbnXAtmProfileMIBConformance 1 }

rbnXAtmProfileMIBCompliances OBJECT IDENTIFIER ::=
	{ rbnXAtmProfileMIBConformance 2 }


-- Compliance Statements

rbnXAtmProfileMIBCompliance MODULE-COMPLIANCE
	STATUS	    current
	DESCRIPTION
		"The compliance statement for RedBack Networks
		SNMP entities which represent AAL5 VCL statistics"
	MODULE	    -- this module
	MANDATORY-GROUPS {
		rbnXAtmProfileGroup
		}
	::= { rbnXAtmProfileMIBCompliances 1 }

-- Units of Conformance

rbnXAtmProfileGroup OBJECT-GROUP
	OBJECTS {
		rbnXAtmServiceCategory
	}
	STATUS	    current
	DESCRIPTION
		"A collection of objects providing supplemental
		ATM Traffic Descriptor (Profile) information
		beyond that specified by IETF standards-track MIBs"
	::= { rbnXAtmProfileMIBGroups 1 }

END
