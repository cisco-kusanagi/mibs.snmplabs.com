-- Avaya (Prominet) CAJUN SWITCH MIB VERSION V5.3
-- Avaya enterprise-specific Management Information Base for SNMP version 1
-- 
-- © 2001 Avaya Inc. ALL RIGHTS RESERVED
-- Printed in USA, March 2001
-- 
-- The products, specifications, and other technical information regarding the
-- products contained in this document are subject to change without notice. All
-- information in this document is believed to be accurate and reliable, but is
-- presented without warranty of any kind, express or implied, and users must
-- take full responsibility for their application of any products specified in
-- this document. Avaya disclaims responsibility for errors which may appear in
-- this document, and it reserves the right, in its sole discretion and without
-- notice, to make substitutions and modifications in the products and practices
-- described in this document.  
-- P550 is a registered trademark and Avaya, Cajun, CajunDocs, CajunRules, 
-- and CajunView are trademarks of Avaya Inc.
-- 
-- This MIB provides managed objects that supplement those capabilities
-- supported by the standard IETF MIBs.  It has the following main sections:
-- 
--    General Agent Support: Manages the SNMP agent.
--           Communications:
--      Resource Management: The Resource Manager is the focal point for
--                           managing dynamic resources.
--                  Chassis: Objects related to the management of the physical
--                           enclosure and environment.
--                Switching: Management of the layer II switching functions and
--                           Virtual LANs.
--         Event Management: RMON Events on steroids.
--              File System: Provides access to the embedded file system.
--

-- MODULE DEFINITION

   PROMINET-MIB DEFINITIONS ::= BEGIN

   IMPORTS
      enterprises,
      Gauge,
      NetworkAddress,
      IpAddress,Counter,
      TimeTicks
         FROM RFC1155-SMI
      OBJECT-TYPE
         FROM RFC-1212
      TimeStamp
         FROM SNMPv2-TC
      TRAP-TYPE
         FROM RFC-1215;

-- Textual Conventions

-- The Data Type returned in event log value

   EventValueType ::= 
      INTEGER {
         none(1),
         integer(2),
         longInteger(3),
         string(4),
         octets(5),
         ipAddress(6),
         macAddress(7),
         timeTicks(8)
         }
         
-- the resources managed by the Cajun Switch
   ResourceType ::=
      INTEGER {
         system(1),
         module(2),
         fan(3),
         temperatureSensor(4),
         interface(5),
         powerSupply(6),
         display(7),
         switchPort(8),
         bridge(9),
         vlan(10),
         aft(11),
         inboundGroupTable(12),
         outboundGroupTable(13),
         threeComMappingTable(14),
         event(15),
         alarm(16)
         }

-- This data type is used to uniquely identify a resource within the Cajun Switch.
-- It encodes the Resource ID into an OID, using 2 as the first component.
-- Using a 2 works around the OID encoding restrictions of the first component (ASN.1)

   ResourceId ::= OBJECT IDENTIFIER

   DisplayString ::= OCTET STRING
-- This data type is used to model textual information taken
-- from the NVT ASCII character set.  By convention, objects
-- with this syntax are declared as having
--
--      SIZE (0..255)

   RowStatus ::= INTEGER {
-- the following two values are states:
-- these values may be read or written

         active(1),
         notInService(2),

-- the following value is a state:
-- this value may be read, but not written

         notReady(3),

-- the following three values are
-- actions: these values may be written,
-- but are never read

         createAndGo(4),
         createAndWait(5),
         destroy(6)
         }

-- All representations of MAC addresses in this MIB Module
-- use, as a textual convention (i.e. this convention does
-- not affect their encoding), the data type:

   MacAddress ::= OCTET STRING (SIZE (6))

-- a 6 octet address in the "canonical" order
-- defined by IEEE 802.1a, i.e., as if it were transmitted
-- least significant bit first, even though 802.5 (in
-- contrast to other n802.x protocols) requires MAC
-- addresses to be transmitted most significant bit first.
--
-- 16-bit addresses, if needed, are represented by setting
-- their upper 4 octets to all 0's, i.e., AAFF would be
-- represented as 00000000AAFF.


-- Similarly, all representations of Bridge-Id in this MIB
-- Module use, as a textual convention (i.e. this
-- convention does not affect their encoding), the data
-- type:

   BridgeId ::= OCTET STRING (SIZE (8))

-- the Bridge-Identifier as used in the Spanning Tree
-- Protocol to uniquely identify a bridge.  Its first two
-- octets (in network byte order) contain a priority
-- value and its last 6 octets contain the MAC address
-- used to refer to a bridge in a unique fashion
-- (typically, the numerically smallest MAC address
-- of all ports on the bridge).

-- Several objects in this MIB module represent values of
-- timers used by the Spanning Tree Protocol.  In this
-- MIB, these timers have values in units of hundredths of
-- a second (i.e. 1/100 secs).
-- These timers, when stored in a Spanning Tree Protocol's
-- BPDU, are in units of 1/256 seconds.  Note, however,
-- that 802.1D-1990 specifies a settable granularity of
-- no more than 1 second for these timers.  To avoid
-- ambiguity, a data type is defined here as a textual
-- convention and all representation of these timers
-- in this MIB module are defined using this data type.  An
-- algorithm is also defined for converting between the
-- different units, to ensure a timer's value is not
-- distorted by multiple conversions.
-- The data type is:

-- a STP timer in units of 1/100 seconds
   Timeout ::= INTEGER

-- To convert a Timeout value into a value in units of
-- 1/256 seconds, the following algorithm should be used:
--
--      b  = floor( (n * 256) / 100)
--
-- where:
--      floor   =  quotient [ignore remainder]
--      n is the value in 1/100 second units
--      b is the value in 1/256 second units
--
-- To convert the value from 1/256 second units back to
-- 1/100 seconds, the following algorithm should be used:
--
--      n = ceiling( (b * 100) / 256)
--
-- where:
--      ceiling =  quotient [if remainder is 0], or
--                 quotient + 1 [if remainder is non-zero]
--      n is the value in 1/100 second units
--      b is the value in 1/256 second units
--
-- Note: it is important that the arithmetic operations are
-- done in the order specified (i.e., multiply first, divide
-- second).

-- Event Category Macro
--
-- Indicates the type of event:
-- - coldstart is generated at system bootup
-- - warmstart is generated when the software system (only) resets
-- - system error is generated for a variety of reasons including running out of memory, OS errors, and H/W faults
-- - status change indicates a change in the status value e.g. a port status change
-- - configuration indicates a change in the configuration value e.g. a port mode change
-- - scheduled events are triggered based on a calendar event
-- - authentication indicates attempted access to a restricted resource without the proper credentials, e.g. SNMP
-- authentication failure.
-- - threshold is generated by alarms

   EventCategory ::= INTEGER {
         userDefined(1),
         coldstart(2),
         warmstart(3),
         linkUp(4),
         linkDown(5),
         newResource(6),
         deletedResource(7),
         tempStatus(8),
         configuration(9),
         scheduled(10),
         authentication(11),
         system(12),
         risingThreshold(13),
         fallingThreshold(14),
         fanStatus(15),
         powerStatus(16),
         status(17),
         bridgeNewRoot(18),
         bridgeTopChange(19),
         switchFabricStatus(20)
         }

-- Support for Digital OEM. promAgent will be linked below gsEMIB
-- at run-time.  Depending on the OEM, only one node under the 
-- enterprises branch will be used which will be determined at run-time

   dec OBJECT IDENTIFIER ::= { enterprises 36 }
   ema OBJECT IDENTIFIER ::= { dec 2 }
   mib-extensions-1 OBJECT IDENTIFIER ::= { ema 18 }
   gsEMIB OBJECT IDENTIFIER ::= { mib-extensions-1 39 }

-- Support for ODS OEM. promAgent will be linked below odsLanBlazer7000MIB
-- at run-time.

   ods OBJECT IDENTIFIER ::= { enterprises 50 }
   odsTPS OBJECT IDENTIFIER ::= { ods 8 }
   odsLANBlazer OBJECT IDENTIFIER ::= { odsTPS 1 }
   odsLANBlazerMibs OBJECT IDENTIFIER ::= { odsLANBlazer 2 }
   odsLANBlazer7000Mib OBJECT IDENTIFIER ::= { odsLANBlazerMibs 1 }

-- Support for Intel OEM. promAgent will be linked below esGigaSwitch
-- at run-time.

   intel OBJECT IDENTIFIER ::= { enterprises 343 }
   mib2ext OBJECT IDENTIFIER ::= { intel 6 }
   esGigaSwitch OBJECT IDENTIFIER ::= { mib2ext 13 }

-- Support for Marconi OEM. promAgent will be linked below esrSwitch
-- at run-time.

   marconi OBJECT IDENTIFIER ::= { enterprises 1012 }
   ethernetL3 OBJECT IDENTIFIER ::= { marconi 81 }
   esrSwitch OBJECT IDENTIFIER ::= { ethernetL3 1 }

-- Avaya Switch Product Types
-- As of the Zydeco 5.3 release.
-- Avaya sysObjectIds are now defined in the aveisprod.mib.
-- That file is controled by ITC to co-ordinate sysObjectIds across all of EIS.

-- Prominet tree

   prominet OBJECT IDENTIFIER ::= { enterprises 2167 }

-- AGENT

   promAgent OBJECT IDENTIFIER ::= { prominet 1 }

-- GENERAL AGENT

   promAgentGen OBJECT IDENTIFIER ::= { promAgent 1 }

   promAgentMIBVersion OBJECT-TYPE
      SYNTAX  DisplayString (SIZE(0..32))
      ACCESS  read-only
      STATUS  mandatory
      DESCRIPTION
              "The version of the Lucent Cajun Switch MIB that this agent
              supports."
      ::= { promAgentGen 1 }

   promAgentMgrIndex OBJECT-TYPE
      SYNTAX  INTEGER
      ACCESS  read-only
      STATUS  mandatory
      DESCRIPTION
              "The value of this object represents the index into the community table that
              is used to authenticate SNMP requests for this manager."
      ::= { promAgentGen 2 }


-- COMMUNITY TABLE

   promAgentCommunity OBJECT IDENTIFIER ::= { promAgent 2 }

--
-- The community table is the database used by the agent to authenticate SNMP requests
-- and to generate SNMP traps.  This table is only accessible for users with security clearance.
--

   promCommunityTable OBJECT-TYPE
      SYNTAX  SEQUENCE OF PromCommunityEntry
      ACCESS  not-accessible
      STATUS  mandatory
      DESCRIPTION
              ""
      ::= { promAgentCommunity 1 }

   promCommunityEntry OBJECT-TYPE
      SYNTAX  PromCommunityEntry
      ACCESS  not-accessible
      STATUS  mandatory
      DESCRIPTION
              ""
      INDEX   { promCommunityIndex }
      ::= { promCommunityTable 1 }

   PromCommunityEntry ::=
      SEQUENCE {
         promCommunityIndex
            INTEGER,
         promCommunityString
            DisplayString,
         promCommunityAddressType
            INTEGER,
         promCommunityAddress
            NetworkAddress,
         promCommunityAccess
            INTEGER,
         promCommunityTrapReceiver
            INTEGER,
         promCommunitySecurityLevel
            INTEGER,
         promCommunityStatus
            RowStatus
      }

   promCommunityIndex OBJECT-TYPE
      SYNTAX  INTEGER
      ACCESS  read-only
      STATUS  mandatory
      DESCRIPTION
              "An index that uniquely identifies this entry."
      ::= { promCommunityEntry 1 }

   promCommunityString OBJECT-TYPE
      SYNTAX  DisplayString (SIZE(0..32))
      ACCESS  read-write
      STATUS  mandatory
      DESCRIPTION
              "The community string included in the SNMP PDU used for authentication
               purposes."
      ::= { promCommunityEntry 2 }

   promCommunityAddressType OBJECT-TYPE
      SYNTAX  INTEGER {
                 any(1),
                 ipv4(2)
              }
      ACCESS  read-write
      STATUS  mandatory
      DESCRIPTION
              "The type of address associated with this community.  If set to any(1), only
              the community string is authenticated."
      ::= { promCommunityEntry 3 }

   promCommunityAddress OBJECT-TYPE
      SYNTAX  NetworkAddress
      ACCESS  read-write
      STATUS  mandatory
      DESCRIPTION
              "If the address type is any, then the value of this object is a null string.  If
              the type is ipv4(2), then this value represents a 4 byte IP address."
      ::= { promCommunityEntry 4 }

   promCommunityAccess OBJECT-TYPE
      SYNTAX  INTEGER {
                 none(1),
                 readOnly(2),
                 readWrite(3),
                 moreSpecific(4)
              }
      ACCESS  read-write
      STATUS  mandatory
      DESCRIPTION
              "The MIB access supported for this community entry.

              A Get or GetNext SNMP PDU is authenticated if the value of this object
              is read-only(2) or read-write(3).  A Set request will be honored if the value
              of this object is read-write(3).

              If more granular access control is desired, then the value of this object is set
              to more-specific(4), and the view table should be consulted.  This enables
              the capability to set different access rights to different branches of the MIB
              for a particular community. "
      ::= { promCommunityEntry 5 }

   promCommunityTrapReceiver OBJECT-TYPE
      SYNTAX  INTEGER {
                 disable(1),
                 enable(2)
              }
      ACCESS  read-write
      STATUS  mandatory
      DESCRIPTION
              "If set to enable(1), this community entry is considered a trap receiver.
              When the agent generates an SNMP trap, a copy will be sent to this host
              using this community string."
      ::= { promCommunityEntry 6 }

   promCommunitySecurityLevel OBJECT-TYPE
      SYNTAX  INTEGER {
                 normal(1),
                 administrator(2)
              }
      ACCESS  read-write
      STATUS  mandatory
      DESCRIPTION
              "Secure tables are only accessible from users with security clearance.  For
              example, this table (the community table) is only accessible by parties that
              have the security clearance."
      ::= { promCommunityEntry 7 }

   promCommunityStatus OBJECT-TYPE
      SYNTAX  RowStatus
      ACCESS  read-write
      STATUS  mandatory
      DESCRIPTION
              ""
      ::= { promCommunityEntry 8 }


-- WEB SERVER

   promAgentWeb OBJECT IDENTIFIER ::= { promAgent 3 }

   promAgentWebServerURL OBJECT-TYPE
      SYNTAX  DisplayString (SIZE(0..31))
      ACCESS  read-write
      STATUS  mandatory
      DESCRIPTION
              "The URL of where the document server software is
              installed. The switch uses this location to find online
              help and bimapped graphics.  Enter the host name or IP
              address of the HTTP server at the HTTP Server Location
              prompt, followed by ':2010'. For example, for a host
              named 'phantom,', enter 'http://phantom:2010'.  If no
              server is desired or installed, set this object to the
              empty string."  
      ::= { promAgentWeb 1 }

   promAgentWebServerHelpDirectory OBJECT-TYPE
      SYNTAX  DisplayString (SIZE(0..31))
      ACCESS  read-write
      STATUS  mandatory
      DESCRIPTION
              "The subdirectory that contains the help files on the
              document server.  Typically, this directory is 'help'."  
      ::= { promAgentWeb 2 }
   
   
-- CHASSIS

-- Chassis Family

   promChassis OBJECT IDENTIFIER ::= { prominet 3 }

-- Chassis family of objects help manage modular devices, and their environmental
-- parameters.

   promChassisGen OBJECT IDENTIFIER ::= { promChassis 1 }

   promChassisType OBJECT-TYPE
      SYNTAX  INTEGER {
                 p550(1),
                 p220(2),
                 p660(3),
                 p880(4),
                 p580(5),
                 p882(6)
              }
      ACCESS  read-only
      STATUS  mandatory
      DESCRIPTION
              "The model of the chassis that this agent is managing."
      ::= { promChassisGen 1 }

   promChassisSlots OBJECT-TYPE
      SYNTAX  INTEGER
      ACCESS  read-only
      STATUS  mandatory
      DESCRIPTION
              "The number of slots available in this chassis.  If this chassis is a stackable
              chassis, the total capacity of stacking units."
      ::= { promChassisGen 2 }

   promChassisSystemReset OBJECT-TYPE
      SYNTAX  INTEGER { reset(1) }
      ACCESS  write-only
      STATUS  mandatory
      DESCRIPTION
              "A control to force the system into a reset state.
               Setting the value to 'reset' causes an immediate system reset.
               This object is only accessible from users with security clearance."
      ::= { promChassisGen 3 }



-- INVENTORY

   promInventory OBJECT IDENTIFIER ::= { promChassis 2 }

-- The inventory table contains manufacturing identification information of the
-- components contained within the system.

   promInventoryTable OBJECT-TYPE
      SYNTAX  SEQUENCE OF PromInventoryEntry
      ACCESS  not-accessible
      STATUS  mandatory
      DESCRIPTION
              "A table of inventory information."
      ::= { promInventory 1 }

   promInventoryEntry OBJECT-TYPE
      SYNTAX  PromInventoryEntry
      ACCESS  not-accessible
      STATUS  mandatory
      DESCRIPTION
              "Inventory information related to this device."
      INDEX   { promInventoryResourceType,
                promInventoryResourceIndex }
      ::= { promInventoryTable 1 }

   PromInventoryEntry ::=
      SEQUENCE {
         promInventoryResourceType
            ResourceType,
         promInventoryResourceIndex
            ResourceId,
         promInventoryModelNumber
            DisplayString,
         promInventorySerialNumber
            DisplayString,
         promInventoryVersion
            DisplayString,
         promInventoryManufactureInfo
            DisplayString,
         promInventoryScratchPad
            DisplayString,
         promInventoryPowerConsumption
	    DisplayString
      }


   promInventoryResourceType OBJECT-TYPE
      SYNTAX  ResourceType
      ACCESS  read-only
      STATUS  mandatory
      DESCRIPTION
              "The resource class of this inventory item."
      ::= { promInventoryEntry 1 }

   promInventoryResourceIndex OBJECT-TYPE
      SYNTAX  ResourceId
      ACCESS  read-only
      STATUS  mandatory
      DESCRIPTION
              "The resource identifier of this inventory item."
      ::= { promInventoryEntry 2 }

   promInventoryModelNumber OBJECT-TYPE
      SYNTAX  DisplayString (SIZE(0..32))
      ACCESS  read-only
      STATUS  mandatory
      DESCRIPTION
              "The model number of this device."
      ::= { promInventoryEntry 3 }

   promInventorySerialNumber OBJECT-TYPE
      SYNTAX  DisplayString (SIZE(0..32))
      ACCESS  read-only
      STATUS  mandatory
      DESCRIPTION
              "The serial number of this device."
      ::= { promInventoryEntry 4 }

   promInventoryVersion OBJECT-TYPE
      SYNTAX  DisplayString (SIZE(0..32))
      ACCESS  read-only
      STATUS  mandatory
      DESCRIPTION
              "The revision number of this device."
      ::= { promInventoryEntry 5 }

   promInventoryManufactureInfo OBJECT-TYPE
      SYNTAX  DisplayString   (SIZE(0..128))
      ACCESS  read-only
      STATUS  mandatory
      DESCRIPTION
              "Information related to the manufacturing of this device."
      ::= { promInventoryEntry 6 }

   promInventoryScratchPad OBJECT-TYPE
      SYNTAX  DisplayString   (SIZE(0..128))
      ACCESS  read-write
      STATUS  mandatory
      DESCRIPTION
              "A scratch pad area available for keeping user-supplied inventory
              information. "
      ::= { promInventoryEntry 7 }

   promInventoryPowerConsumption OBJECT-TYPE
      SYNTAX  DisplayString   (SIZE(0..32))
      ACCESS  read-only
      STATUS  mandatory     
      DESCRIPTION
              "Power consumption ( in WATTS ) by the module."
      ::= { promInventoryEntry 8 }

	
--
-- Power Systems

   promPowerSystems OBJECT IDENTIFIER ::= { promChassis 3 }

-- POWER SUPPLY TABLE

   promPowerSupplies OBJECT IDENTIFIER ::= { promPowerSystems 1 }

-- A table providing information about each power supply.
-- The index to the table is the power supply resource index.
--
-- Information in this table includes the status of the power supply
-- and how much power this supply generates.

   promPowerSupplyTable OBJECT-TYPE
      SYNTAX  SEQUENCE OF PromPowerSupplyEntry
      ACCESS  not-accessible
      STATUS  mandatory
      DESCRIPTION
              "A table of information related to each power supply in the system."
      ::= { promPowerSupplies 1 }

   promPowerSupplyEntry OBJECT-TYPE
      SYNTAX  PromPowerSupplyEntry
      ACCESS  not-accessible
      STATUS  mandatory
      DESCRIPTION
              "An entry providing information about a particular power supply in the
              system."
      INDEX   { promPowerSupplyIndex }
      ::= { promPowerSupplyTable 1 }

   PromPowerSupplyEntry ::=
      SEQUENCE {
         promPowerSupplyIndex
            ResourceId,
         promPowerSupplyType
            INTEGER,
         promPowerSupplyStatus
            INTEGER,
         promPowerSupplyInputStatus
            INTEGER,
         promPowerSupplyOutputStatus
            INTEGER,
         promPowerSupplyOutputCapacity
            INTEGER
      }


   promPowerSupplyIndex OBJECT-TYPE
      SYNTAX  ResourceId
      ACCESS  read-only
      STATUS  mandatory
      DESCRIPTION
              "An index that uniquely identifies this power supply.  This index
              corresponds to the promResourceIndex of the power supply type
              resource."
      ::= { promPowerSupplyEntry 1 }

   promPowerSupplyType OBJECT-TYPE
      SYNTAX  INTEGER {
                 unknown(1),
                 psA(2),
                 psB(3)
              }
      ACCESS  read-only
      STATUS  mandatory
      DESCRIPTION
              "An enumerated integer describing the type of power supply.  "
      ::= { promPowerSupplyEntry 2 }


   promPowerSupplyStatus OBJECT-TYPE
      SYNTAX  INTEGER {
                 okay(1),
                 faulty(2),
                 unknown(3)
              }
      ACCESS  read-only
      STATUS  mandatory
      DESCRIPTION
              "The status of this power supply.  Okay(1) indicates the power supply is
              operating properly. Faulty(2) indicates that the power supply is not
              functioning properly.  In this case, more information can be determined
              from the other power supply attributes."
      ::= { promPowerSupplyEntry 3 }


   promPowerSupplyInputStatus OBJECT-TYPE
      SYNTAX  INTEGER {
                 okay(1),
                 faulty(2),
                 unknown(3)
              }
      ACCESS  read-only
      STATUS  mandatory
      DESCRIPTION
              "The status of the input power feed (e.g. the AC power cord) to this
              power supply."
      ::= { promPowerSupplyEntry 4 }

   promPowerSupplyOutputStatus OBJECT-TYPE
      SYNTAX  INTEGER {
                 okay(1),
                 faulty(2),
                 unknown(3)
              }
      ACCESS  read-only
      STATUS  mandatory
      DESCRIPTION
              "The status of the output power from this power supply."
      ::= { promPowerSupplyEntry 5 }

   promPowerSupplyOutputCapacity OBJECT-TYPE
      SYNTAX  INTEGER
      ACCESS  read-only
      STATUS  mandatory
      DESCRIPTION
              "The total capacity of power supplied by this supply in Watts."
      ::= { promPowerSupplyEntry 6 }



-- POWER MANAGEMENT

   promPowerMgmtGen OBJECT IDENTIFIER ::= { promPowerSystems 2 }

   promPowerCapacity OBJECT-TYPE
      SYNTAX  INTEGER
      ACCESS  read-only
      STATUS  mandatory
      DESCRIPTION
              "The total capacity (in Watts) of power available (currently) in the system."
      ::= { promPowerMgmtGen 1 }

   promPowerUsed OBJECT-TYPE
      SYNTAX  INTEGER
      ACCESS  read-only
      STATUS  mandatory
      DESCRIPTION
              "The total power (in Watts) currently being consumed in the system."
      ::= { promPowerMgmtGen 2 }

-- POWER MANAGEMENT CONTROL

   promPowerMgmtCtl OBJECT IDENTIFIER ::= { promPowerSystems  3 }

   promPowerControlTable OBJECT-TYPE
      SYNTAX  SEQUENCE OF PromPowerControlEntry
      ACCESS  not-accessible
      STATUS  obsolete    
      DESCRIPTION
              "This table manages the power attributes associated with each module.

	      This object is obsolete.It is not supported."
      ::= { promPowerMgmtCtl 1 }

   promPowerControlEntry OBJECT-TYPE
      SYNTAX  PromPowerControlEntry
      ACCESS  not-accessible
      STATUS  obsolete
      DESCRIPTION
              "An entry in the power control table manages the power attributes of the
              specified module.

	      This object is obsolete."
      INDEX   { promModuleIndex }
      ::= { promPowerControlTable 1 }

   PromPowerControlEntry ::=
      SEQUENCE {
         promPowerControlUsed
            INTEGER,
         promPowerControlPriority
            INTEGER,
         promPowerControlMode
            INTEGER
      }

   promPowerControlUsed OBJECT-TYPE
      SYNTAX  INTEGER
      ACCESS  read-only
      STATUS  obsolete
      DESCRIPTION
              "The total power (in Watts) used by this module.
               This object is obsolete."
      ::= { promPowerControlEntry 1 }

   promPowerControlPriority OBJECT-TYPE
      SYNTAX  INTEGER {
                 high(1),
                 normal(2),
                 low(3)
              }
      ACCESS  read-write
      STATUS  obsolete
      DESCRIPTION
              "The priority of this module to be considered in the event of a power
              supply failure where the amount of power used exceeds the system
              capacity.  Low priority modules will be powered down before higher
              priority modules.
              
	      This object is obsolete"
      ::= { promPowerControlEntry 2 }

   promPowerControlMode OBJECT-TYPE
      SYNTAX  INTEGER {
                 enable(1),
                 disable(2),
                 poweredDown(3)
              }
      ACCESS  read-write
      STATUS  obsolete
      DESCRIPTION
              "Normally, a module power mode is enable(1).

              In the event of a power supply failure resulting in a power shortage, or in
              the event of this module being inserted without enough available power,
              the mode will be poweredDown(3).    Setting this object to the value of
              poweredDown(3) will result in an error.

              When enough power is available, the module will power back up when in
              this mode.  A module may be powered down through administrative
              action by setting the value of this object to disable(2). In this mode, the
              module will remain powered down until the mode is set back to enable.

	      This object is obsolete."
      ::= { promPowerControlEntry 3 }



-- TEMPERATURE

   promTemperature OBJECT IDENTIFIER ::= { promChassis 4 }

   promTempTable OBJECT-TYPE
      SYNTAX  SEQUENCE OF PromTempEntry
      ACCESS  not-accessible
      STATUS  mandatory
      DESCRIPTION
              "A table of information related to the temperature within the system."
      ::= { promTemperature 1 }

   promTempEntry OBJECT-TYPE
      SYNTAX  PromTempEntry
      ACCESS  not-accessible
      STATUS  mandatory
      DESCRIPTION
              "An entry providing temperature information related to a specific
              temperature probe in the system."
      INDEX   { promTempIndex }
      ::= { promTempTable 1 }

   PromTempEntry ::=
      SEQUENCE {
         promTempIndex
            ResourceId,
         promTempValue
            INTEGER,
         promTempUpperLimit
            INTEGER,
         promTempUpperWarning
            INTEGER,
         promTempLowerWarning
            INTEGER,
         promTempLowerLimit
            INTEGER
      }

   promTempIndex OBJECT-TYPE
      SYNTAX  ResourceId
      ACCESS  read-only
      STATUS  mandatory
      DESCRIPTION
              "A unique index that identifies this temperature probe.  This index
              corresponds to the promResourceIndex for temperature probe type
              resources."
      ::= { promTempEntry 1 }

   promTempValue OBJECT-TYPE
      SYNTAX  INTEGER
      ACCESS  read-only
      STATUS  mandatory
      DESCRIPTION
              "The current temperature reading of this temperature probe in degrees
              Celsius."
      ::= { promTempEntry 2 }

   promTempUpperLimit OBJECT-TYPE
      SYNTAX  INTEGER
      ACCESS  read-write
      STATUS  mandatory
      DESCRIPTION
              "The upper temperature limit of this temperature probe in degrees
              Celsius."
      ::= { promTempEntry 3 }

   promTempUpperWarning OBJECT-TYPE
      SYNTAX  INTEGER
      ACCESS  read-write
      STATUS  mandatory
      DESCRIPTION
              "The upper temperature warning of this temperature probe in degrees
              Celsius."
      ::= { promTempEntry 4 }

   promTempLowerWarning OBJECT-TYPE
      SYNTAX  INTEGER
      ACCESS  read-write
      STATUS  mandatory
      DESCRIPTION
              "The lower temperature warning of this temperature probe in degrees
              Celsius."
      ::= { promTempEntry 5 }

   promTempLowerLimit OBJECT-TYPE
      SYNTAX  INTEGER
      ACCESS  read-write
      STATUS  mandatory
      DESCRIPTION
              "The lower temperature limit of this temperature probe in degrees
              Celsius."
      ::= { promTempEntry 6 }



-- MODULE MANAGEMENT

   promModules OBJECT IDENTIFIER ::= { promChassis 5 }

   promModuleTable OBJECT-TYPE
      SYNTAX  SEQUENCE OF PromModuleEntry
      ACCESS  not-accessible
      STATUS  mandatory
      DESCRIPTION
              "A table of information related to the modules in the system."
      ::= { promModules 1 }

   promModuleEntry OBJECT-TYPE
      SYNTAX  PromModuleEntry
      ACCESS  not-accessible
      STATUS  mandatory
      DESCRIPTION
              "Attributes related to managing this module."
      INDEX   { promModuleIndex }
      ::= { promModuleTable 1 }

   PromModuleEntry ::=
      SEQUENCE {
         promModuleIndex
            ResourceId,
         promModuleName
            DisplayString,
         promModuleType
            INTEGER,
         promModuleBaseType
            INTEGER,
         promModuleSlotWidth
            INTEGER,
         promModuleSlotOffset
            INTEGER,
         promModulePorts
            INTEGER
      }

   promModuleIndex OBJECT-TYPE
      SYNTAX  ResourceId
      ACCESS  read-only
      STATUS  mandatory
      DESCRIPTION
              "An index that uniquely identifies this module.  This index corresponds to
              the promResourceIndex associated with module type resources."
      ::= { promModuleEntry 1 }

   promModuleName OBJECT-TYPE
      SYNTAX  DisplayString (SIZE (0..31))
      ACCESS  read-write
      STATUS  mandatory
      DESCRIPTION
              "A user-assignable name for this module."
      ::= { promModuleEntry 2 }


   promModuleType OBJECT-TYPE
      SYNTAX  INTEGER {
                 unknown(1),         -- unknown module
                 m5502-1000(2),      -- 2 Port Gigabit
                 m2206-1000(3),      -- 6 Port Gigabit
                 m5520-100TX-QS(4),  -- 20 Port 10/100: Quality Phy's
                 m5510-100FX(5),     -- 10 Port Fast Ethernet Fiber
                 m5500-SUP(6),       -- Supervisor (5500)
                 m5504-1000(7),      -- 4 Port Gigabit
                 m2201-1000(8),      -- 1 Port Gigabit Option
                 m5520-100TX-I(9),   -- 20 Port 10/100: Intel Phy's
                 m2202-100FX(10),    -- 2 Port Fast Ethernet Fiber Option
                 m5510R-100FX(11),   -- 10 Port Routing Fast Ethernet Fiber
                 m5512R-100TX(12),   -- 12 Port Routing 10/100
                 m5500R-SUP(13),     -- Routing Supervisor
                 m5502R-1000(14),    -- 2 Port Routing Gigabit
                 m2200-SUP(15),      -- Supervisor (2200)
                 m2204-100TX-I(16),  -- 4 Port 10/100 Option: Intel Phy's
                 m2224-100TX(17),    -- 24 Port 10/100 Option
                 m5502-OC3(18),      -- 2 Port L2 OC-3 ATM Module
                 m5520-100TX-LUC(19),-- 20 Port 10/100: Lucent Phy's
                 m2204-100TX-LUC(20),-- 4 Port 10/100: Lucent Phy's
                 m5548-100TX-BCM(21),-- 48 Port 10/100: Broadcom Phy's
                 m5502-AOC12SMF(22), -- 2 Port OC12 Single Mode Fiber ATM module
                 m5502-AOC12MMF(23), -- 2 Port OC12 Multi Mode Fiber ATM module
                 m2201-1000SX(24),   -- 1 Port Gigabit SX  expansion module
                 m2201-1000LX(25),   -- 1 Port Gigabit LX  expansion module
                 m2201-1000SLX(26),  -- 1 Port Gigabit SLX expansion module
                 m5500R-SUPA(27),    -- Supervisor module
                 m8000R-SUP(28),     -- 80 series supervisor module
                 m8002-1000(29),     -- 2 Port Gigabit
                 m5500R-HUR(30),     -- Server switch
                 m8024-100TX(31),    -- 24 Port 10/100 80 Series
                 m8048-100TX(32),    -- 48 Port 10/100 80 Series (Tobasco)
                 m8024-100FX(33),    -- 24 Port 100 Fast Ethernet Fiber
                 m8008-1000(34),     -- 8 Port Gigabit 80 Series
                 m5504-AOC3SMF(35),  -- 4 Port OC3 Single Mode Fiber
                 m5504-AOC3MMF(36),  -- 4 Port OC3 Multi Mode Fiber
                 m8004-1000(37),     -- 4 Port Gigabit 80 Series
                 m8001-CMTS(38),     -- 1 Port Cable Modem Termination System
                 m5502-AOC3SMF(39),  -- 2 Port OC3 Single Mode Fiber
                 m5502-AOC3MMF(40),  -- 2 Port Multi Mode Fiber
                 m8000R-HUR(41),     -- Server Switch 80 Series
                 m8008R-1000T(42),   -- 8 Port Gigabit Copper
                 m8004R-1000T(43),   -- 4 Port Gigabit Copper
                 m8024R-100FXW(44),  -- 24 Port 100 Optical Phy
                 m8002R-AOC12SMF(45),-- 2 Port OC12 Single Mode Fiber 80 series
                 m8002R-AOC12MMF(46),-- 2 Port OC12 Multi Mode Fiber 80 series
                 m8002R-AOC3SMF(47),-- 2 Port OC3 Single Mode Fiber 80 series
                 m8002R-AOC3MMF(48), -- 2 Port OC3 Multi Mode Fiber 80 series
                 m8048-JB-100TX(57)  -- 48 Port 10/100 80 Series (Jambalaya)
 
              }
      ACCESS  read-only
      STATUS  mandatory
      DESCRIPTION
              "An enumerated integer that is unique for each module model. "
      ::= { promModuleEntry 3 }

   promModuleBaseType OBJECT-TYPE
      SYNTAX  INTEGER {
                 gigabit(1),         -- Gigabit Ethernet Modules
                 fastEthernet(2),    -- Fast Ethernet Modules
                 supervisor(3),      -- Supervisor Modules
                 unspecified(4),     -- Unspecified Base 
                 uplink(5),          -- Uplink Modules
                 serverSwitching(6)  -- Server Switching Modules
              }
      ACCESS  read-only
      STATUS  mandatory
      DESCRIPTION
              "The base type of this module.  This object is used to describe the core
              functions of the module.  Often, base designs are derived into multiple
              module types which are typically just packaging variations (e.g. changing the
              connector types).  The  value of this object corresponds to the value of
              promResourceBaseType."
      ::= { promModuleEntry 4 }

   promModuleSlotWidth OBJECT-TYPE
      SYNTAX  INTEGER
      ACCESS  read-only
      STATUS  mandatory
      DESCRIPTION
              "The number of slots that this module occupies."
      ::= { promModuleEntry 5 }

   promModuleSlotOffset OBJECT-TYPE
      SYNTAX  INTEGER
      ACCESS  read-only
      STATUS  mandatory
      DESCRIPTION
              "The slot offset (one based) that identifies, along with the slot width and
              slot location, the actual slots that this module occupies.  The offset identifies
              which slot within the width of the module that this module reports as its
              slot number."
      ::= { promModuleEntry 6 }

   promModulePorts OBJECT-TYPE
      SYNTAX  INTEGER
      ACCESS  read-only
      STATUS  mandatory
      DESCRIPTION
              "The total number of ports associated with this module."
      ::= { promModuleEntry 7 }

-- Module Update time

promModuleUpdateTime OBJECT-TYPE
      SYNTAX  TimeStamp
      ACCESS  read-only
      STATUS  mandatory
      DESCRIPTION
              "The value of MIb II's sysUpTime object at the 
               time that the last module change occurred."
      ::= { promModules 2 }

promModuleUpdateList OBJECT-TYPE   
      SYNTAX  OCTET STRING
      ACCESS  read-only
      STATUS  mandatory
      DESCRIPTION
      "The function of this variable is to summarize the information concerning the
      presence of the module and the module type for each slot of the hub.  
      The second octet will contain '4' to indicate that what follows is 
      an octet string.  The third octet will contain '1' since each
      module type will be contained in 1 octet.  Octets 4 through 
      4+n (n=number of slots) will contain the module type for the 
      corresponding slot.  
      The information is coded as follows:
      First Octet: number of slots
      Second Octet: SNMP Type of information: Integer = 2, OctetString = 4.
      Third Octet: length of each field
      Fourth Octet: if no module in slot #1 then '0', else the module type i.e, 
      the integer corresponding to promModuleType.
      Last Octet: the module type corresponding to the last slot in the hub."
::= { promModules 3 }

-- PORT MANAGEMENT

   promPorts OBJECT IDENTIFIER ::= { promChassis 6 }

-- PORT MANAGEMENT DISCUSSION
--
--    This section manages the physical ports within the system.
--
--    There are attributes that are generic to the physical port class and every
-- physical port in the system supports these attributes.  These attributes are
-- represented in the generic port management section.
--
--    Note, however, that the following operations WILL EACH RESULT IN AN ERROR:
--       Setting promPortMode to disable(2) for an internal(1) port
--       Setting promPortName for an internal(1)) port
--
--    Each type of port may also support other promPortType-specific attributes.
-- If a port supports a particular attribute, there is an instance of that port
-- in the table that manages that attribute.  These attributes are represented
-- in the port tables that follow the generic port management section.
--
--    internal(1) ports do not support any type-specific attributes.
--
--    ether-ten-oneHundred(2) ports support:
--       promPortFlowControlMode
--       promPortDuplexMode
--       promPortSpeedMode
--       promPortAutoNegotiationMode
--       promPortAutoNegotiationSpeedAdvertisement
--       promPortAutoNegotiationDuplexAdvertisement
--       promPortRateLimitMode
--       promPortRateLimitRate
--       promPortRateLimitBurstSize
--       promPortPacePriorityMode
--       promPortCategoryMode
--
--    ether-oneHundred(3) ports support:
--       promPortFlowControlMode
--       promPortDuplexMode
--       promPortRateLimitMode
--       promPortRateLimitRate
--       promPortRateLimitBurstSize
--       promPortPacePriorityMode
--       promPortCategoryMode
--
--    ether-gigabit(4) ports (pre-standard) support:
--       promPortFlowControlMode
--          (setting to enable-with-aggressive-backoff(3) RESULTS IN AN ERROR)
--       promPortPacePriorityMode
--       promPortCategoryMode
--       promPortRemoteFaultDetect
--
--    ether-gigabit2(5) ports support:
--       promPortFlowControlMode
--          (setting to enable-with-aggressive-backoff(3) RESULTS IN AN ERROR)
--       promPortAutoNegotiationMode
--       promPortAutoNegotiationFlowControlAdvertisement
--       promPortPacePriorityMode
--       promPortCategoryMode
--       promPortRemoteFaultDetect
--
--    ether-gigabit-copper(6) ports support:
--       promPortAutoNegotiationFlowControlAdvertisement
--       promPortPacePriorityMode
--       promPortCategoryMode
--
--    ether-ten-oneHundred-telco(7) ports support:
--       promPortFlowControlMode
--          (Setting this parameter for a port sets it for all ports on the module)
--       promPortDuplexMode
--       promPortSpeedMode
--       promPortAutoNegotiationMode
--       promPortAutoNegotiationSpeedAdvertisement
--       promPortAutoNegotiationDuplexAdvertisement
--       promPortRateLimitMode
--          (Setting this parameter for a port sets it for all ports on the module)
--       promPortRateLimitRate
--          (Setting this parameter for a port sets it for all ports on the module)
--       promPortRateLimitBurstSize
--          (Setting this parameter for a port sets it for all ports on the module)
--       promPortCategoryMode

-- GENERIC PORT MANAGEMENT

   promPortMgt OBJECT IDENTIFIER ::= { promPorts 1 }

   promPortTable OBJECT-TYPE
      SYNTAX  SEQUENCE OF PromPortEntry
      ACCESS  not-accessible
      STATUS  mandatory
      DESCRIPTION
              "A table of information related to every data port in this data networking
              system."
      ::= { promPortMgt 1 }

   promPortEntry OBJECT-TYPE
      SYNTAX  PromPortEntry
      ACCESS  not-accessible
      STATUS  mandatory
      DESCRIPTION
              "A data port associated with this data networking system."
      INDEX   { promPortIndex }
      ::= { promPortTable 1 }

   PromPortEntry ::=
      SEQUENCE {
         promPortIndex
            ResourceId,
         promPortName
            DisplayString,
         promPortType
            INTEGER,
         promPortBaseType
            INTEGER,
         promPortMode
            INTEGER,
         promPortStatus
            INTEGER,
         promPortConnector
            INTEGER,
         promPortSpeedState
            INTEGER,
         promPortDuplexState
            INTEGER,
         promPortGroupBinding
            ResourceId,
         promPortFlowControlState
            INTEGER
      }

   promPortIndex OBJECT-TYPE
      SYNTAX  ResourceId
      ACCESS  read-only
      STATUS  mandatory
      DESCRIPTION
              "An index that uniquely identifies this port.  Typically, ports are child
              resources of the module that contains them.  In these cases, ports are
              identified by their module and their relative physical position on that
              module."
      ::= { promPortEntry 1 }

   promPortName OBJECT-TYPE
      SYNTAX  DisplayString (SIZE(0..31))
      ACCESS  read-write
      STATUS  mandatory
      DESCRIPTION
              "The user-assigned name for this port.

              Note that setting this object for an internal(1) port results in an error."
      ::= { promPortEntry 2 }

   promPortType OBJECT-TYPE
      SYNTAX  INTEGER {
                 internal(1),
                 ether-ten-oneHundred(2),
                 ether-oneHundred(3),
                 ether-gigabit(4),
                 ether-gigabit2(5),
                 ether-gigabit-lxt1000-copper(6),
                 ether-ten-oneHundred-bcm5308-rj71(7),
                 atm(8)
              }
      ACCESS  read-only
      STATUS  mandatory
      DESCRIPTION
              "An internal(1) port does not have an external connection.

              An ether-ten-oneHundred(2) port is an Ethernet port which can be switched between
              10 and 100 megabits per second.

              An ether-oneHundred(3) port is a 100 megabits per second Fast Ethernet port.

              An ether-gigabit(4) port is a 1000 megabits per second Gigabit Ethernet port.

              An ether-gigabit2(5) port is a 1000 megabits per second Gigabit Ethernet port.

              An ether-gigabit-copper(6) port is a 1000 megabits per second Gigabit Ethernet
              port using Category 5 twisted pair cabling.

              An ether-ten-oneHundred-telco(7) port is an Ethernet port which can be switched
              between 10 and 100 megabits per second using telco connectors."
      ::= { promPortEntry 3 }

   promPortBaseType OBJECT-TYPE
      SYNTAX  INTEGER {
                 internal(1),
                 ether-ten-oneHundred(2),
                 ether-oneHundred(3),
                 ether-gigabit(4),
                 atm(5)
              }
      ACCESS  read-only
      STATUS  mandatory
      DESCRIPTION
              "The base type of this port.  This object may be useful to help manage new
              port types that are similar in nature to legacy port types."
      ::= { promPortEntry 4 }

   promPortMode OBJECT-TYPE
      SYNTAX  INTEGER {
                 enable(1),
                 disable(2)
              }
      ACCESS  read-write
      STATUS  mandatory
      DESCRIPTION
              "The mode of this port.  When set to enable(1), this port passes data.
              When set to disable(2), the port does not receive or transmit data, nor does
              it generate port-level signaling e.g. link integrity pulses.

              Note that setting an internal(1) port to disable(2) results in an error."
      ::= { promPortEntry 5 }

   promPortStatus OBJECT-TYPE
      SYNTAX  INTEGER {
                 disabled(1),
                 okay(2),
                 warning(3),
                 disabledButOkay(4),
                 linkFailure(5)
              }
      ACCESS  read-only
      STATUS  mandatory
      DESCRIPTION
              "The status of this port.  Disabled(1) means that this port has been disabled
              through management action.  Okay(2) indicates that this port is operating
              properly.  Warning(3) indicates that this port is encountering an abnormal
              condition that, however, allows it to continue to pass data.  LinkFailure(5)
              means that this port is unable to pass data."
      ::= { promPortEntry 6 }

   promPortConnector OBJECT-TYPE
      SYNTAX  INTEGER {
                 internal(1),
                 rj45(2),
                 fiber-ST(3),
                 fiber-SC(4),
                 rs-232(5),
                 aui(6),
                 rj71(7),
                 gbic-1000-SX(8),
                 gbic-1000-LX(9),
                 gbic-1000-LX-LH(10),
                 notPresent(11),
                 unsupported(12)
              }
      ACCESS  read-only
      STATUS  mandatory
      DESCRIPTION
              "The connector type associated with this port."
      ::= { promPortEntry 7 }

   promPortSpeedState OBJECT-TYPE
      SYNTAX  INTEGER {
                 ten-megabits-per-second(1),
                 one-hundred-megabits-per-second(2),
                 one-hundred-fifty-five-megabits-per-second(3),
                 six-hundred-twenty-two-megabits-per-second(4),
                 one-gigabit-per-second(5),
                 under-negotiation(6)
              }
      ACCESS  read-only
      STATUS  mandatory
      DESCRIPTION
              "The data rate of this port in bits per second.  For example, a standard
              Ethernet port (e.g. 10BASE-T) would indicate a value of ten-megabits-per-second((1)
              indicating that the port supports a data rate of 10Mb/s.  For ports that can
              change their data rate (e.g. 10/100 ports), the value of this object indicates
              the current state of the port's speed capability."
      ::= { promPortEntry 8 }

   promPortDuplexState OBJECT-TYPE
      SYNTAX  INTEGER {
                 half-duplex(1),
                 full-duplex(2),
                 under-negotiation(3)
              }
      ACCESS  read-only
      STATUS  mandatory
      DESCRIPTION
              "The value of this object indicates whether this port is operating in full- or
              half-duplex mode.

              The value under-negotiation(3) indicates that the port has not selected an
              operational duplex setting yet."
      ::= { promPortEntry 9 }

   promPortGroupBinding OBJECT-TYPE
      SYNTAX  ResourceId
      ACCESS  read-only
      STATUS  mandatory
      DESCRIPTION
              "Each port is associated with a port group.  Typically, a port will belong to
              a port group of one and the value of this object will be the same as the
              port index for this instance.  That is, this port will point to itself.

              The intent of this object is to help manage ports that  have hierarchical
              relationships.  For example, an ATM port typically has a physical port and
              multiple logical ports (e.g. each logical port corresponding to an instance of
              an emulated LAN).  In this case, each LANE instance would refer to the
              instance of the physical port associated with the ATM front-end.

              Another example is an FDDI DAS type port.  In this case, there is a logical
              port associated with the FDDI switch port which is connected to the two
              FDDI physical port connectors.  The physical FDDI ports both point to
              the logical instance of an FDDI port."
      ::= { promPortEntry 10 }

   promPortFlowControlState OBJECT-TYPE
      SYNTAX  INTEGER {
                 enable(1),
                 disable(2),
                 enable-with-aggressive-backoff(3),
                 enable-send-only(4),
                 enable-respond-only(5),
                 under-negotiation(6)
              }
      ACCESS  read-only
      STATUS  mandatory
      DESCRIPTION
              "The value of this object indicates whether this port is operating using
              flow control.

              The value under-negotiation(3) indicates that the port has not selected an
              operational flow control setting yet."
      ::= { promPortEntry 11 }



-- PORT FLOW CONTROL

   promPortFlowControlMgt OBJECT IDENTIFIER ::= { promPorts 2 }

-- Flow Control
--
--  Flow control is used by ports to slow down the incoming flow of data.  It has been
--  shown to be a very effective mechanism for improving network efficiency when used
--  in conjunction with an end-station.

   promPortFlowControlTable OBJECT-TYPE
      SYNTAX  SEQUENCE OF PromPortFlowControlEntry
      ACCESS  not-accessible
      STATUS  mandatory
      DESCRIPTION
              "A table of ports that support flow control."
      ::= { promPortFlowControlMgt 1 }

   promPortFlowControlEntry OBJECT-TYPE
      SYNTAX  PromPortFlowControlEntry
      ACCESS  not-accessible
      STATUS  mandatory
      DESCRIPTION
              "Configuration objects related to port based flow control."
      INDEX   { promPortIndex }
      ::= { promPortFlowControlTable 1 }

   PromPortFlowControlEntry ::=
      SEQUENCE {
         promPortFlowControlMode
            INTEGER
      }

   promPortFlowControlMode OBJECT-TYPE
      SYNTAX  INTEGER {
                 enable(1),
                 disable(2),
                 enable-with-aggressive-backoff(3),
                 enable-send-only(4),
                 enable-respond-only(5)
              }
      ACCESS  read-write
      STATUS  mandatory
      DESCRIPTION
              "Flow control is used to prevent or reduce the dropping of frames due to
              the lack of buffer space.  Overall, networks are more efficient when a
              sending station is asked to pause in its sending process, rather than having
              the transmitted frames dropped.

              Flow control is not as efficient when used in conjunction with a shared
              ports, i.e. when used with a repeater.  Therefore, flow control is not
              recommended for a port connected to shared topologies.

              Flow control is most effective when the port is directly connected to an
              end-station, especially when connected to a server.  Flow control is
              recommended for ports connected directly to end-stations.

              When the port is in half-duplex mode, back pressure is used to control
              the incoming flow.  Back pressure essentially forces collisions for short
              periods of time.

              When the port is in full-duplex mode, IEEE 802.3 standard pause frames
              are used to control the incoming flow.

              Note that setting an ether-gigabit(4) port to enable-with-aggressive-backoff(3)
              results in an error.
              
              The enable-send-only(4) and enable-respond-only(5) are applicable for 
              ether-gigabit and ether-gigabit2 ports only."
      ::= { promPortFlowControlEntry 21 }



-- DUPLEX MODE

   promPortDuplexMgt OBJECT IDENTIFIER ::= { promPorts 3 }

-- A table that manages each port that supports the ability to switch
-- between full- and half- duplex mode.

   promPortDuplexTable OBJECT-TYPE
      SYNTAX  SEQUENCE OF PromPortDuplexEntry
      ACCESS  not-accessible
      STATUS  mandatory
      DESCRIPTION
              "A table of ports that support full- and half-duplex data communications."
      ::= { promPortDuplexMgt 1 }

   promPortDuplexEntry OBJECT-TYPE
      SYNTAX  PromPortDuplexEntry
      ACCESS  not-accessible
      STATUS  mandatory
      DESCRIPTION
              "A port device configuration that controls the duplex mode of this port."
      INDEX   { promPortIndex }
      ::= { promPortDuplexTable 1 }


   PromPortDuplexEntry ::=
      SEQUENCE {
         promPortDuplexMode
            INTEGER
      }


   promPortDuplexMode OBJECT-TYPE
      SYNTAX  INTEGER {
                 half-duplex(1),
                 full-duplex(2)
              }
      ACCESS  read-write
      STATUS  mandatory
      DESCRIPTION
              "A point-to-point Ethernet port may be configured to support half or full
              duplex communications.

              A full-duplex(2) port transmits and receives data concurrently,  effectively
              doubling the data rate of the port.

              Half-duplex(1) ports transmit or receive data, but not at the same time.
              Half-duplex ports use CSMA/CD as the access  method to the network.
              Ports that are connected to shared segments (i.e. connected to a repeater),
              should always be configured to be in half-duplex mode.

              This object indicates the desired duplexity of this port.  If
              auto-negotiation is turned on for this port, then this value is ignored."
      ::= { promPortDuplexEntry 31 }



--  SPEED MODE

--  The Speed Table manages the speed mode for ports that can switch speeds.

   promPortSpeedMgt OBJECT IDENTIFIER ::= { promPorts 4 }

   promPortSpeedTable OBJECT-TYPE
      SYNTAX  SEQUENCE OF PromPortSpeedEntry
      ACCESS  not-accessible
      STATUS  mandatory
      DESCRIPTION
              "A table of port devices that support multiple speeds."
      ::= { promPortSpeedMgt 1 }

   promPortSpeedEntry OBJECT-TYPE
      SYNTAX  PromPortSpeedEntry
      ACCESS  not-accessible
      STATUS  mandatory
      DESCRIPTION
              "A port that supports multiple speeds."
      INDEX   { promPortIndex }
      ::= { promPortSpeedTable 1 }

   PromPortSpeedEntry ::=
      SEQUENCE {
         promPortSpeedMode
            INTEGER
      }


   promPortSpeedMode OBJECT-TYPE
      SYNTAX  INTEGER {
                 ten-megabits-per-second(1),
                 one-hundred-megabits-per-second(2),
                 one-hundred-fifty-five-megabits-per-second(3),
                 six-hundred-twenty-two-megabits-per-second(4),
                 one-gigabit-per-second(5)
              }
      ACCESS  read-write
      STATUS  mandatory
      DESCRIPTION
              "Some of these values may not be applicable to certain types of ports.

              This object indicates the desired data rate of this port.  If
              auto-negotiation is turned on for this port, then this value is ignored."
      ::= { promPortSpeedEntry 41 }



-- AUTO NEGOTIATION

   promPortAutoNegotiationMgt OBJECT IDENTIFIER ::= { promPorts  5 }

   promPortAutoNegotiationTable OBJECT-TYPE
      SYNTAX  SEQUENCE OF PromPortAutoNegotiationEntry
      ACCESS  not-accessible
      STATUS  mandatory
      DESCRIPTION
              "A table of ports that support auto-negotiation."
      ::= { promPortAutoNegotiationMgt 1 }

   promPortAutoNegotiationEntry OBJECT-TYPE
      SYNTAX  PromPortAutoNegotiationEntry
      ACCESS  not-accessible
      STATUS  mandatory
      DESCRIPTION
              "Attributes associated with a port that supports auto-negotiation."
      INDEX   { promPortIndex }
      ::= { promPortAutoNegotiationTable 1 }

   PromPortAutoNegotiationEntry ::=
      SEQUENCE {
         promPortAutoNegotiationMode
            INTEGER,
         promPortAutoNegotiationSpeedAdvertisement
            INTEGER,
         promPortAutoNegotiationDuplexAdvertisement
            INTEGER,
         promPortAutoNegotiationFlowControlAdvertisement
            INTEGER
      }


   promPortAutoNegotiationMode OBJECT-TYPE
      SYNTAX  INTEGER {
                 autoNegotiate(1),
                 manualConfiguration(2)
              }
      ACCESS  read-write
      STATUS  mandatory
      DESCRIPTION
              "Setting this object to autoNegotiate(1) causes this port to negotiate the
              duplex mode and the port speed, subject to the port's capabilities."
      ::= { promPortAutoNegotiationEntry 51 }

   promPortAutoNegotiationSpeedAdvertisement OBJECT-TYPE
      SYNTAX  INTEGER {
                 ten-and-one-hundred-megabits-per-second(1),
                 one-hundred-megabits-per-second(2),
                 ten-megabits-per-second(3)
              }
      ACCESS  read-write
      STATUS  mandatory
      DESCRIPTION
              "The speed to advertise while auto-negotiating."
      ::= { promPortAutoNegotiationEntry 52 }

   promPortAutoNegotiationDuplexAdvertisement OBJECT-TYPE
      SYNTAX  INTEGER {
                 full-and-half-duplex(1),
                 half-duplex(2)
              }
      ACCESS  read-write
      STATUS  mandatory
      DESCRIPTION
              "The duplexity to advertise while auto-negotiating."
      ::= { promPortAutoNegotiationEntry 53 }

   promPortAutoNegotiationFlowControlAdvertisement OBJECT-TYPE
      SYNTAX  INTEGER {
                 enable(1),
                 disable(2),
                 enable-send-only(3),
                 enable-respond-only(4)
              }
      ACCESS  read-write
      STATUS  mandatory
      DESCRIPTION
              "The flow control capability to advertise while auto-negotiating."
      ::= { promPortAutoNegotiationEntry 54 }



-- RATE LIMITING

   promPortRateLimitMgt OBJECT IDENTIFIER ::= { promPorts 6 }

--  Rate Limiting
--
--  This table manages the rate limiting for ports that support this feature.  Rate Limiting
-- prevents floods from overwhelming a port (typically, a slower port).

   promPortRateLimitTable OBJECT-TYPE
      SYNTAX  SEQUENCE OF PromPortRateLimitEntry
      ACCESS  not-accessible
      STATUS  mandatory
      DESCRIPTION
              "A table of ports that support the ability to limit the rate of floods."
      ::= { promPortRateLimitMgt 1 }

   promPortRateLimitEntry OBJECT-TYPE
      SYNTAX  PromPortRateLimitEntry
      ACCESS  not-accessible
      STATUS  mandatory
      DESCRIPTION
              "The rate limit configuration associated with this port."
      INDEX   { promPortIndex }
      ::= { promPortRateLimitTable 1 }

   PromPortRateLimitEntry ::=
      SEQUENCE {
         promPortRateLimitMode
            INTEGER,
         promPortRateLimitRate
            INTEGER,
         promPortRateLimitBurstSize
            INTEGER
      }


   promPortRateLimitMode OBJECT-TYPE
      SYNTAX  INTEGER {
                 enable(1),
                 disable(2),
                 enableIncludeKnownMulticast(3)
              }
      ACCESS  read-write
      STATUS  mandatory
      DESCRIPTION
              "This object configures whether rate limiting is enabled for this port (the
              factory default is enable(1)).  Enabling rate limiting for this port prevents
              floods from overwhelming the output buffer associated with this port.

              Normally, rate limiting will only consider frames that are flooded to this
              port.  This typically does not include known multicasts.  However, known
              multicasts can be included in the flood limiting by setting the value of this
              object to enableIncludeKnownMulticast(3)."
      ::= { promPortRateLimitEntry 61 }

   promPortRateLimitRate OBJECT-TYPE
      SYNTAX  INTEGER {
                 one-percent(1),
                 two-percent(2),
                 five-percent(3),
                 ten-percent(4),
                 twenty-percent(5),
                 forty-percent(6),
                 eighty-percent(7)
              }
      ACCESS  read-write
      STATUS  mandatory
      DESCRIPTION
              "The percentage of the port's transmitted data allowed to be floods (or floods
              and known multicasts).  For example, the factory default setting of
              twenty-percent(4) indicates that 20% of the data rate can be floods.  For 10 Mb/s
              ports, this is equivalent to a maximum rate of approximately 3000 flooded pps;
              for 100 Mb/s ports, a maximum rate of approximately 30,000 flooded pps."
      ::= { promPortRateLimitEntry 62 }

   promPortRateLimitBurstSize OBJECT-TYPE
      SYNTAX  INTEGER {
                 rateLimit1(1),
                 rateLimit2(2),
                 rateLimit4(3),
                 rateLimit8(4),
                 rateLimit16(5),
                 rateLimit32(6),
                 rateLimit64(7),
                 rateLimit128(8),
                 rateLimit256(9),
                 rateLimit512(10),
                 rateLimit1024(11),
                 rateLimit2048(12)
              }
      ACCESS  read-write
      STATUS  mandatory
      DESCRIPTION
              "The maximum number of consecutive transmitted flooded (or flooded and known
              multicasted) packets.  Typically, the burst size is set so as to not overflow the
              port's buffer."
      ::= { promPortRateLimitEntry 63 }



--  PACE PRIORITY

   promPortPacePriorityMgt OBJECT IDENTIFIER ::= { promPorts 7 }

--  Pace Priority
--
-- This table manages all ports that support classification of frame priority via
-- 3Com's Pace(r) Prioritization.
--

   promPortPacePriorityTable OBJECT-TYPE
      SYNTAX  SEQUENCE OF PromPortPacePriorityEntry
      ACCESS  not-accessible
      STATUS  mandatory
      DESCRIPTION
              "A table of ports that support the ability to classify frame priority based on
              3Com Pace(r) Prioritization."
      ::= { promPortPacePriorityMgt 1 }

   promPortPacePriorityEntry OBJECT-TYPE
      SYNTAX  PromPortPacePriorityEntry
      ACCESS  not-accessible
      STATUS  mandatory
      DESCRIPTION
              "A port that supports 3Com Pace(r) priority."
      INDEX   { promPortIndex }
      ::= { promPortPacePriorityTable 1 }

   PromPortPacePriorityEntry ::=
      SEQUENCE {
         promPortPacePriorityMode
            INTEGER
      }


   promPortPacePriorityMode OBJECT-TYPE
      SYNTAX  INTEGER {
                 enable(1),
                 disable(2)
              }
      ACCESS  read-write
      STATUS  mandatory
      DESCRIPTION
              "When Pace priority is enabled, this port will detect frames that use 3Com
              Corporation's Pace(r) Priority signaling.  Frames signaled with priority in
              this manner are mapped to traffic priority level 4 (on scale of 0-7)."
      ::= { promPortPacePriorityEntry 71 }



--  PORT CATEGORY

   promPortCategoryMgt OBJECT IDENTIFIER ::= { promPorts 8 }

   promPortCategoryTable OBJECT-TYPE
      SYNTAX  SEQUENCE OF PromPortCategoryEntry
      ACCESS  not-accessible
      STATUS  mandatory
      DESCRIPTION
              "A table of ports that support the port category feature.  Currently, all
              ports support this capability."
      ::= { promPortCategoryMgt 1 }

   promPortCategoryEntry OBJECT-TYPE
      SYNTAX  PromPortCategoryEntry
      ACCESS  not-accessible
      STATUS  mandatory
      DESCRIPTION
              "A port that supports port categorization."
      INDEX   { promPortIndex }
      ::= { promPortCategoryTable 1 }

   PromPortCategoryEntry ::=
      SEQUENCE {
         promPortCategoryMode
            INTEGER
      }


   promPortCategoryMode OBJECT-TYPE
      SYNTAX  INTEGER {
                 userPort(1),
                 servicePort(2)
              }
      ACCESS  read-write
      STATUS  mandatory
      DESCRIPTION
              "By default, all ports are considered service ports.  A
              service port is a port that provides a networks service
              such as a connection to a server, other switches, or
              the like.  A service port will trigger the service port
              event for status changes with the alarm severity and
              will trigger an alarm in the alarm table on link
              failure. 

              In contrast, user ports trigger the user link event
              with warning severity.  They do not trigger an alarm
              upon link failures.  User ports are useful to prevent
              floods of traps or entries in the alarm table.  This is
              especially true for ports connected to user hosts that
              power up in the morning and power down again at the end
              of the work day."
      ::= { promPortCategoryEntry 81 }



--  REMOTE FAULT DETECT

   promPortRemoteFaultMgt OBJECT IDENTIFIER ::= { promPorts 9 }

--  Remote Fault Detect
--
-- This table manages all ethernet-gig ports to support a proprietary form of (pre-standard)
-- remote fault detection .
--

   promPortRemoteFaultTable OBJECT-TYPE
      SYNTAX  SEQUENCE OF PromPortRemoteFaultEntry
      ACCESS  not-accessible
      STATUS  mandatory
      DESCRIPTION
              "A table of ports that support the ability signal a (pre-standard) remote fault 
              to a far-end interface using proprietary messages."
      ::= { promPortRemoteFaultMgt 1 }

   promPortRemoteFaultEntry OBJECT-TYPE
      SYNTAX  PromPortRemoteFaultEntry
      ACCESS  not-accessible
      STATUS  mandatory
      DESCRIPTION
              "A port that supports pre-standard remote fault detection."
      INDEX   { promPortIndex }
      ::= { promPortRemoteFaultTable 1 }

   PromPortRemoteFaultEntry ::=
      SEQUENCE {
         promPortRemoteFaultDetect
            INTEGER
      }


   promPortRemoteFaultDetect OBJECT-TYPE
      SYNTAX  INTEGER {
                 enable(1),
                 disable(2)
              }
      ACCESS  read-write
      STATUS  mandatory
      DESCRIPTION
              "When remote fault detection is enabled, this port will transmit a 'remote fault present'
              control frame to its peer interface when it detects a link failure.  It will periodically 
              send the control frame until the link failure clears, at which time it will send a 
              'remote fault clear' control frame.  If this port receives a 'remote fault present'
              control frame it will declare a link failure until it is informed that the condition has 
              cleared or until the remote fault times out."
      ::= { promPortRemoteFaultEntry 91 }



-- BUFFER MANAGEMENT
--
-- This section is dedicated to managing any buffers that exist in the system.
-- Buffers are used to store network traffic.  They are indexed by the module
-- that contains the buffer and a unique index within the buffer.

   promBufferMgt OBJECT IDENTIFIER ::= { promChassis 7 }

   promBufferTable OBJECT-TYPE
      SYNTAX  SEQUENCE OF PromBufferEntry
      ACCESS  not-accessible
      STATUS  mandatory
      DESCRIPTION
              "A table of frame buffers in the system."
      ::= { promBufferMgt 1 }

   promBufferEntry OBJECT-TYPE
      SYNTAX  PromBufferEntry
      ACCESS  not-accessible
      STATUS  mandatory
      DESCRIPTION
              "Objects related to the management of this frame buffer."
      INDEX   { promBufferIndex }
      ::= { promBufferTable 1 }

   PromBufferEntry ::=
      SEQUENCE {
         promBufferIndex
            ResourceId,
         promBufferFabricPort
            ResourceId,
         promBufferFabricPortDirection
            INTEGER,
         promBufferSwitchPort
            ResourceId,
         promBufferMemory
            INTEGER,
         promBufferAgeTimer
            INTEGER,
         promBufferPriorityServicing
            INTEGER,
         promBufferPriorityAllocation
            INTEGER,
         promBufferPriorityThreshold
            INTEGER,
         promBufferCongestion
            INTEGER,
         promBufferHighOverflowDrops
            Counter,
         promBufferLowOverflowDrops
            Counter,
         promBufferHighStaleDrops
            Counter,
         promBufferLowStaleDrops
            Counter,
         promBufferCongestionDrops
            Counter
      }


   promBufferIndex OBJECT-TYPE
      SYNTAX  ResourceId
      ACCESS  read-only
      STATUS  mandatory
      DESCRIPTION
              "The unique index that identifies this buffer within the system.  Buffers are
              indexed first by their module association and then a unique index within
              that module."
      ::= { promBufferEntry 1 }

   promBufferFabricPort OBJECT-TYPE
      SYNTAX  ResourceId
      ACCESS  read-only
      STATUS  mandatory
      DESCRIPTION
              "The switch fabric port associated with this buffer."
      ::= { promBufferEntry 2 }

   promBufferFabricPortDirection OBJECT-TYPE
      SYNTAX  INTEGER {
                 in(1),
                 out(2)
              }
      ACCESS  read-only
      STATUS  mandatory
      DESCRIPTION
              "The value of this object indicates whether the buffer is used for buffering
              frames going into the switching fabric or coming out of the fabric."
      ::= { promBufferEntry 3 }

   promBufferSwitchPort OBJECT-TYPE
      SYNTAX  ResourceId
      ACCESS  read-only
      STATUS  mandatory
      DESCRIPTION
              "The switch port associated with this frame buffer.  Some buffers are not
              associated with any one switch port.  In those cases, the value of the
              resource ID returned will be the null resource ID."
      ::= { promBufferEntry 4 }

   promBufferMemory OBJECT-TYPE
      SYNTAX  INTEGER
      ACCESS  read-only
      STATUS  mandatory
      DESCRIPTION
              "The amount of memory available for frame buffering in Kilobytes (KB)."
      ::= { promBufferEntry 5 }

   promBufferAgeTimer OBJECT-TYPE
      SYNTAX  INTEGER {
                 disable(1),
                 quarter-second(2),
                 one-second(3)
              }
      ACCESS  read-write
      STATUS  mandatory
      DESCRIPTION
              "Configures the timer used for aging frames in this buffer.  If the timer
              expires for a frame, the frame is dropped and the event is counted in the
              stale drop counter.  By default, the age timer is set to a 0.25 seconds
              (quarter of a second).

              The actual time that a frame may be aged out may vary.  When set to a
              quarter of a second (250ms), the actual time may vary between 160ms and
              320ms.  When set to a second (1000ms), the time may vary between 640ms
              and 1.28 seconds (1028ms)."
      ::= { promBufferEntry 6 }

   promBufferPriorityServicing OBJECT-TYPE
      SYNTAX  INTEGER {
                 strictPriority(1),
                 everyTenThousand(2),
                 everyThousand(3),
                 everyHundred(4),
                 everyFour(5)
              }
      ACCESS  read-write
      STATUS  mandatory
      DESCRIPTION
              "The value of this object configures how often the normal priority queue is
              serviced relative to the high priority queue.  By default, the normal priority
              queue is serviced every thousand frames(3).  This means that the normal
              priority queue is guaranteed to be serviced after servicing, at most, one
              thousand high priority frames.

              It is important to service the normal priority queue for two reasons.  One is
              to prevent starvation for frames on the normal priority queue.  The other
              reason is that frames cannot be aged if they are not serviced (see the age
              timer)."
      ::= { promBufferEntry 7 }

   promBufferPriorityAllocation OBJECT-TYPE
      SYNTAX  INTEGER {
                 none(1),
                 tenPercent(2),
                 twentyPercent(3),
                 thirtyPercent(4),
                 fortyPercent(5),
                 fiftyPercent(6)
              }
      ACCESS  read-write
      STATUS  mandatory
      DESCRIPTION
              "This object controls how much of the total buffer space should be
              allocated to high priority queue.  Please be warned that setting this object to
              a different value causes the associated buffer to reset, causing a short loss of
              data.

              Setting the value of this object to none(1) not only allocates the entire buffer
              space to normal traffic, but also has the side effect of disabling the priority
              threshold.  In other words, all traffic will be considered as normal priority
              traffic."
      ::= { promBufferEntry 8 }

   promBufferPriorityThreshold OBJECT-TYPE
      SYNTAX  INTEGER {
                 none(1),
                 one(2),
                 two(3),
                 three(4),
                 four(5),
                 five(6),
                 six(7),
                 seven(8)
              }
      ACCESS  read-write
      STATUS  mandatory
      DESCRIPTION
              "This object configures the threshold for which frames are considered high
              priority.  Frames may have a priority classification ranging from 0-7, 7
              being the highest.  By default, every frame that has priority 4 (four(5)) or
              above is considered a high priority frame and is buffered accordingly.

              If this buffer does not have any buffer space allocated for high priority
              frames, then the buffer threshold will be none(1).  Setting this object to a
              different value without allocating buffer space to high priority traffic will
              result in an error."
      ::= { promBufferEntry 9 }

   promBufferCongestion OBJECT-TYPE
      SYNTAX  INTEGER {
                 informationNotAvailable(1),
                 notCongested(2),
                 congested(3)
              }
      ACCESS  read-only
      STATUS  mandatory
      DESCRIPTION
              "This object indicates whether this buffer is in a congested state.."
      ::= { promBufferEntry 10 }

   promBufferHighOverflowDrops OBJECT-TYPE
      SYNTAX  Counter
      ACCESS  read-only
      STATUS  mandatory
      DESCRIPTION
              "The count of the number of high priority frames dropped due to the high
              priority queue overflowing."
      ::= { promBufferEntry 11 }

   promBufferLowOverflowDrops OBJECT-TYPE
      SYNTAX  Counter
      ACCESS  read-only
      STATUS  mandatory
      DESCRIPTION
              "The count of the number of low priority frames dropped due to the low
              priority queue overflowing."
      ::= { promBufferEntry 12 }

   promBufferHighStaleDrops OBJECT-TYPE
      SYNTAX  Counter
      ACCESS  read-only
      STATUS  mandatory
      DESCRIPTION
              "The count of the number of high priority frames dropped due to being in
              the high priority queue too long (the frame aged out)."
      ::= { promBufferEntry 13 }

   promBufferLowStaleDrops OBJECT-TYPE
      SYNTAX  Counter
      ACCESS  read-only
      STATUS  mandatory
      DESCRIPTION
              "The count of the number of low priority frames dropped due to being in
              the low priority queue too long (the frame aged out)."
      ::= { promBufferEntry 14 }

   promBufferCongestionDrops OBJECT-TYPE
      SYNTAX  Counter
      ACCESS  read-only
      STATUS  mandatory
      DESCRIPTION
              "The count of the number of frames dropped due to the destination
              (output) buffer being congested. "
      ::= { promBufferEntry 16 }



-- SWITCHING

   promSwitching OBJECT IDENTIFIER ::= { prominet 5 }

-- LAYER II SWITCHING

   promSwitchingLayerII OBJECT IDENTIFIER ::= { promSwitching 1 }

-- SWITCH MANAGEMENT

   promSwitchGen OBJECT IDENTIFIER ::= { promSwitchingLayerII 1 }

   promSwitchSTPConfig OBJECT-TYPE
      SYNTAX  INTEGER {
                 ieee8021dStp(1),    -- simple bridge
                 stpPerVlan(2),      -- virtual bridging
                 twoLayerStp(3),     -- separate planes
                 disable(4)          -- STP disabled 
              }
      ACCESS  read-write
      STATUS  mandatory
      DESCRIPTION
              "When set to ieee8021dStp(1), the switch executes spanning tree conformant
              to the IEEE 802.1D bridging standard.  The switch runs one instance of
              spanning tree.

              When set to stpPerVlan(2), the switch executes a separate instance of spanning
              tree for each virtual LAN.  This configuration conforms to the model that
              instances of virtual LANs within the switch are separate virtual bridging
              functions.  This method may not work well with bridge/routers that are also
              running spanning tree.

              When set to twoLayerStp(3), the switch executes a two-layer spanning tree to prevent loops.  Two layer
              spanning tree creates a higher 'plane' of spanning tree between VLAN devices.  This method of running
              spanning tree is 'plug and play' with bridge/router type devices and also scales better than the other
              two methods for large environments. 
              
              When set to disable(4), spanning tree is disabled in the switch."
      ::= { promSwitchGen 1 }

   promSwitchAgingTime OBJECT-TYPE
   SYNTAX  INTEGER (10..1000000)
   ACCESS  read-write 
   STATUS  mandatory
   DESCRIPTION
      "The timeout period in seconds for aging dynamically learned forwarding 
             information.  A default of 300 seconds is recommended. An aged entry is 
       marked invalid, but is not removed from the Address Forwarding Table, 
             because it is assumed that it will be relearned to the same location within
             the table."
   ::= { promSwitchGen 2 }

   promSwitchSuperAgingTime OBJECT-TYPE
   SYNTAX  INTEGER (1..30)
   ACCESS  read-write
   STATUS  mandatory
   DESCRIPTION
      "The timeout period in days for removing stale invalid entries from the Address 
             Forwarding Table.  A superaged entry is removed completely from the Address
             Forwarding Table, because it is assumed that the entry will never be relearned."
   ::= { promSwitchGen 3 }

-- LAYERII

-- BRIDGE MANAGEMENT

   promBridgeMgmt OBJECT IDENTIFIER ::= { promSwitchingLayerII 2 }

-- Bridge Table

   promBridgeTable OBJECT-TYPE
      SYNTAX  SEQUENCE OF PromBridgeEntry
      ACCESS  not-accessible
      STATUS  mandatory
      DESCRIPTION
              "A table of Spanning Tree information for every bridge in the system."
      ::= { promBridgeMgmt 1 }

   promBridgeEntry OBJECT-TYPE
      SYNTAX  PromBridgeEntry
      ACCESS  not-accessible
      STATUS  mandatory
      DESCRIPTION
              ""
      INDEX   { promBridgeIndex }
      ::= { promBridgeTable 1 }

   PromBridgeEntry ::=
      SEQUENCE {
         promBridgeIndex
            ResourceId,
         promBridgeType
            INTEGER,
         promBridgeMode
            INTEGER,
         promBridgeStatus
            INTEGER,
         promBridgeStpPriority
            INTEGER,
         promBridgeStpTimeSinceTopologyChange
            TimeTicks,
         promBridgeStpTopChanges
            Counter,
         promBridgeStpDesignatedRoot
            BridgeId,
         promBridgeStpRootCost
            INTEGER,
         promBridgeStpRootPort
            INTEGER,
         promBridgeStpMaxAge
            Timeout,
         promBridgeStpHelloTime
            Timeout,
         promBridgeStpHoldTime
            INTEGER,
         promBridgeStpForwardDelay
            Timeout,
         promBridgeStpBridgeMaxAge
            Timeout,
         promBridgeStpBridgeHelloTime
            Timeout,
         promBridgeStpBridgeForwardDelay
            Timeout
      }

   promBridgeIndex OBJECT-TYPE
      SYNTAX  ResourceId
      ACCESS  read-only
      STATUS  mandatory
      DESCRIPTION
              "An index that uniquely identifies this bridge."
      ::= { promBridgeEntry 1 }

   promBridgeType OBJECT-TYPE
      SYNTAX  INTEGER {
                 dot1d(1),
                 virtual(2)
              }
      ACCESS  read-only
      STATUS  mandatory
      DESCRIPTION
              "Indicates whether this is a legacy dot1d bridge consisting of all switch
              ports or a virtual bridge consisting of all virtual subports for a particular
              Vlan."
      ::= { promBridgeEntry 2 }

   promBridgeMode OBJECT-TYPE
      SYNTAX  INTEGER {
                 enable(1),
                 disable(2)
              }
      ACCESS  read-write
      STATUS  mandatory
      DESCRIPTION
              "Used to enable or disable Spanning Tree for this bridge.  When set to
              disable(2), all BPDUs are forwarded like regular multicast packets.  The
              default value is enable(1)."
      ::= { promBridgeEntry 3 }

   promBridgeStatus OBJECT-TYPE
      SYNTAX  INTEGER {
                 enabled(1),
                 disabled(2)
              }
      ACCESS  read-only
      STATUS  mandatory
      DESCRIPTION
              "The enable/disable status of this bridge.  This object incorporates the
              setting of the promSwitchSTPConfig object.  When
              promSwitchSTPConfig is set such that this bridge will not be active,
              promBridgeStatus returns disabled(2).  If  promSwitchSTPConfig is set
              such that this bridge will be active, and promBridgeMode is enable(1), this
              object returns enabled(2)."
      ::= { promBridgeEntry 4 }

   promBridgeStpPriority OBJECT-TYPE
      SYNTAX  INTEGER (0..65535)
      ACCESS  read-write
      STATUS  mandatory
      DESCRIPTION
              "The priority value of the Bridge Identifier.  See dot1dStpPriority."
      ::= { promBridgeEntry 5 }

   promBridgeStpTimeSinceTopologyChange OBJECT-TYPE
      SYNTAX  TimeTicks
      ACCESS  read-only
      STATUS  mandatory
      DESCRIPTION
              "The time since the last topology change was detected.  See
              dot1dStpTimeSinceTopologyChange."
      ::= { promBridgeEntry 6 }

   promBridgeStpTopChanges OBJECT-TYPE
      SYNTAX  Counter
      ACCESS  read-only
      STATUS  mandatory
      DESCRIPTION
              "The total number of topology changes.  See dot1dStpTopChanges"
      ::= { promBridgeEntry 7 }

   promBridgeStpDesignatedRoot OBJECT-TYPE
      SYNTAX  BridgeId
      ACCESS  read-only
      STATUS  mandatory
      DESCRIPTION
              "The bridge considered to be root by this node.  See
              dot1dStpDesignatedRoot."
      ::= { promBridgeEntry  8 }

   promBridgeStpRootCost OBJECT-TYPE
      SYNTAX  INTEGER
      ACCESS  read-only
      STATUS  mandatory
      DESCRIPTION
              "The cost of the path to the root from this node.  See dot1dStpRootCost."
      ::= { promBridgeEntry 9 }

   promBridgeStpRootPort OBJECT-TYPE
      SYNTAX  INTEGER
      ACCESS  read-only
      STATUS  mandatory
      DESCRIPTION
              "The port number with the lowest cost path to the root bridge.  See
              dot1dStpRootPort."
      ::= { promBridgeEntry 10 }

   promBridgeStpMaxAge OBJECT-TYPE
      SYNTAX  Timeout
      ACCESS  read-only
      STATUS  mandatory
      DESCRIPTION
              "The maximum age used by this bridge to hold onto STP information
              before discarding.  See dot1dStpMaxAge."
      ::= { promBridgeEntry 11 }

   promBridgeStpHelloTime OBJECT-TYPE
      SYNTAX  Timeout
      ACCESS  read-only
      STATUS  mandatory
      DESCRIPTION
              "The amount of time between configuration BPDUs.  See
              dot1dStpHelloTime."
      ::= { promBridgeEntry 12 }

   promBridgeStpHoldTime OBJECT-TYPE
      SYNTAX  INTEGER
      ACCESS  read-only
      STATUS  mandatory
      DESCRIPTION
              "The time value that indicates the interval during which no more than two
              configuration BPDUs will be sent by this node.  See dot1dStpHoldTime."
      ::= { promBridgeEntry 13 }

   promBridgeStpForwardDelay OBJECT-TYPE
      SYNTAX  Timeout
      ACCESS  read-only
      STATUS  mandatory
      DESCRIPTION
              "The amount of time that this node stays in each of the Listening and
              Learning states.  See dot1dStpForwardDelay."
      ::= { promBridgeEntry 14 }

   promBridgeStpBridgeMaxAge OBJECT-TYPE
      SYNTAX  Timeout (600..4000)
      ACCESS  read-write
      STATUS  mandatory
      DESCRIPTION
              "The value of MaxAge when this bridge is the root. See
              dot1dStpBridgeMaxAge."
      ::= { promBridgeEntry 15 }

   promBridgeStpBridgeHelloTime OBJECT-TYPE
      SYNTAX  Timeout (100..1000)
      ACCESS  read-write
      STATUS  mandatory
      DESCRIPTION
              "The value of HelloTime to use when this bridge is the root.  See
              dot1dStpBridgeHelloTime."
      ::= { promBridgeEntry 16 }

   promBridgeStpBridgeForwardDelay OBJECT-TYPE
      SYNTAX  Timeout (400..3000)
      ACCESS  read-write
      STATUS  mandatory
      DESCRIPTION
              "The value of FowardDelay to use when this bridge is the root.  See
              dot1dStpBridgeForwardDelay."
      ::= { promBridgeEntry 17 }



-- Bridge Port Table

   promBridgePortMgmt OBJECT IDENTIFIER ::= { promSwitchingLayerII 3 }

   promBridgePortTable OBJECT-TYPE
      SYNTAX  SEQUENCE OF PromBridgePortEntry
      ACCESS  not-accessible
      STATUS  mandatory
      DESCRIPTION
              " A table of Spanning Tree information for every port that supports
              Spanning Tree in every bridge in the system "
      ::= { promBridgePortMgmt 1 }

   promBridgePortEntry OBJECT-TYPE
      SYNTAX  PromBridgePortEntry
      ACCESS  not-accessible
      STATUS  mandatory
      DESCRIPTION
              ""
      INDEX   { promBridgePortIndex }
      ::= { promBridgePortTable 1 }

   PromBridgePortEntry ::=
      SEQUENCE {
         promBridgePortIndex
            ResourceId,
         promBridgePortPriority
            INTEGER,
         promBridgePortState
            INTEGER,
         promBridgePortEnable
            INTEGER,
         promBridgePortPathCost
            INTEGER,
         promBridgePortDesignatedRoot
            BridgeId,
         promBridgePortDesignatedCost
            INTEGER,
         promBridgePortDesignatedBridge
            BridgeId,
         promBridgePortDesignatedPort
            OCTET STRING,
         promBridgePortForwardTransitions
            Counter,
         promBridgePortFastStart
            INTEGER,
         promBridgePortSetDefault
            INTEGER,
         promBridgePortEnableChangeDetection
            INTEGER
      }

   promBridgePortIndex OBJECT-TYPE
      SYNTAX  ResourceId
      ACCESS  read-only
      STATUS  mandatory
      DESCRIPTION
              "An index that uniquely identifies this bridge port.  This index corresponds
              to the promResourceIndex for bridge port type resources."
      ::= { promBridgePortEntry  1 }


   promBridgePortPriority OBJECT-TYPE
      SYNTAX  INTEGER (0..255)
      ACCESS  read-write
      STATUS  mandatory
      DESCRIPTION
              "The value of the priority field in the port ID.  See dot1dStpPortPriority.
              The default value is 128."
      ::= { promBridgePortEntry  2 }

   promBridgePortState OBJECT-TYPE
      SYNTAX  INTEGER {
                 disabled(1),
                 blocking(2),
                 listening(3),
                 learning(4),
                 forwarding(5),
                 broken(6)
              }
      ACCESS  read-only
      STATUS  mandatory
      DESCRIPTION
              "The port's current state as defined by the Spanning Tree Protocol.  See
              dot1dStpPortState.
              The virtual port is considered broken if its switch port is blocked."
      ::= { promBridgePortEntry  3 }

   promBridgePortEnable OBJECT-TYPE
      SYNTAX  INTEGER {
                 enabled(1),
                 disabled(2)
              }
      ACCESS  read-write
      STATUS  mandatory
      DESCRIPTION
              "The enabled/disabled status of this port.  See dot1dStpPortEnable. The
              default is enabled(2)."
      ::= { promBridgePortEntry  4 }

   promBridgePortPathCost OBJECT-TYPE
      SYNTAX  INTEGER (1..65535)
      ACCESS  read-write
      STATUS  mandatory
      DESCRIPTION
              "The contribution of this port to the path cost of the paths towards the
              spanning tree root.  See dot1dStpPortPathCost. The default value is
              dependent on the port speed, trunking mode, and duplexity."
      ::= { promBridgePortEntry  5 }

   promBridgePortDesignatedRoot OBJECT-TYPE
      SYNTAX  BridgeId
      ACCESS  read-only
      STATUS  mandatory
      DESCRIPTION
              "The bridge recorded as root for this port's segment.  See
              dot1dStpPortDesignatedRoot."
      ::= { promBridgePortEntry  6 }

   promBridgePortDesignatedCost OBJECT-TYPE
      SYNTAX  INTEGER
      ACCESS  read-only
      STATUS  mandatory
      DESCRIPTION
              "The path cost of the designated root of the segment connected to this
              port.  See dot1dStpPortDesignatedCost."
      ::= { promBridgePortEntry 7 }

   promBridgePortDesignatedBridge OBJECT-TYPE
      SYNTAX  BridgeId
      ACCESS  read-only
      STATUS  mandatory
      DESCRIPTION
              "The bridge identifier of the bridge that is considered the designated bridge
              for this port's segment.  See dot1dStpPortDesignatedBridge."
      ::= { promBridgePortEntry 8 }

   promBridgePortDesignatedPort OBJECT-TYPE
      SYNTAX  OCTET STRING (SIZE (2))
      ACCESS  read-only
      STATUS  mandatory
      DESCRIPTION
              "The port identifier of the port on the Designated Bridge for this port's
              segment.  See dot1dStpPortDesignatedPort."
      ::= { promBridgePortEntry 9 }

   promBridgePortForwardTransitions OBJECT-TYPE
      SYNTAX  Counter
      ACCESS  read-only
      STATUS  mandatory
      DESCRIPTION
              "The number of times this port has transitioned from the learning state to
              the forwarding state.  See dot1dStpPortForwardTransitions."
      ::= { promBridgePortEntry 10 }

   promBridgePortFastStart OBJECT-TYPE
      SYNTAX  INTEGER {
                 enable(1),
                 disable(2)
              }
      ACCESS  read-write
      STATUS  deprecated
      DESCRIPTION
              "This object is being replaced by the switch port object promSwitchPortFastStart. 
              When this bridge port object is set to enable(1), the bridge port and all other
              bridge ports on the same switch port, transition right from blocking to forwarding,
              skipping the listening and learning states.  When this bridge port object is set 
              to disable(2), the bridge port and all other bridge ports on the same switch port
              have this option disabled.  The user should be warned that using the fast start
              feature greatly increases the likelihood of unintended network loops that would
              otherwise be prevented by participating in the normal spanning tree algorithm.

              The factory default value for this object is disable(2)."
      ::= { promBridgePortEntry 11 }

   promBridgePortSetDefault OBJECT-TYPE
      SYNTAX  INTEGER {
                 useCurrentValues(1),
                 setDefault(2)
              }
      ACCESS  read-write
      STATUS  mandatory
      DESCRIPTION
              "When set to setDefault(2), the promBridgePortPriority,
              promBridgePortEnable, and promBridgePortPathCost
              will be set to the factory default values."
      ::= { promBridgePortEntry 12 }

   promBridgePortEnableChangeDetection OBJECT-TYPE
      SYNTAX  INTEGER {
                 enable(1),
                 disable(2)
              }
      ACCESS  read-write
      STATUS  mandatory
      DESCRIPTION
              "When this object is set to enable(1), a Topology Change Notification
              will be generated when this port goes to Blocking or Forwarding (if
              the port is a designated port).  When set to disable(2), no 
              Topology Change Notification will be generated for this port.  The
              default is enable(1)."
      ::= { promBridgePortEntry 13 }


-- ADDRESS MANAGEMENT

   promL2AddrMgmt OBJECT IDENTIFIER ::= { promSwitchingLayerII 4 }

-- Address Database

   promL2AddrDatabaseMgt OBJECT IDENTIFIER ::= { promL2AddrMgmt 1 }

-- Address Database
--
-- The address table provides data that would normally be available from the standard
-- bridge MIB.  The standard bridge MIB has a few short comings, however.
--
-- 1. It is indexed by MACAddress, forcing the bridge to sort a table that is normally
-- hashed.  When the address table is quite large, this sorting can become quite a drag on
-- the processor.
--
-- 2. The bridge MIB address table does not extend well to devices that support virtual
-- LANs.
--
-- 3. There are other objects that are desirable to be managed that the standard MIB does
-- not support.
--
-- This address database  is indexed by address entry  index.  Each address entry has the
-- traditional layer II MAC Address and port binding for that address, as well as some
-- other value added fields such as address priority.
--
-- Each address entry is logically contained by a separate address filtering table (AFT).
-- Separate address tables are important to the support of Virtual LANs (VLANs).  For
-- frames that are explicitly bound to a VLAN either by explicit tagging or by source
-- port association (port-based VLANs), separate AFTs enable a host to
-- appear on different VLANs with different port bindings.  Also, for frames that are
-- implicitly bound to VLANs based on protocol type and/or host address, separate
-- AFTs enable layer III VLANs for client systems.
--
-- In the case where the AFT is supporting a VLAN with a host or host, protocol policy,
-- the VLAN index indicated is the VLAN classification for that host or host, protocol
-- combination.
--
-- Note, it is the default to create separate AFTs for each VLAN and for each protocol
-- type.  In some cases, this may not be desirable and in these cases, multiple VLANs
-- and/or protocols may point to the same AFTs.

   promL2AddressTable OBJECT-TYPE
      SYNTAX  SEQUENCE OF PromL2AddressEntry
      ACCESS  not-accessible
      STATUS  mandatory
      DESCRIPTION
              "A table of address table entries.  The address table is used by the bridging
              function to perform forwarding and filtering decisions.  An address may
              appear multiple times in different entries corresponding to the different
              logical address tables."
      ::= { promL2AddrDatabaseMgt 1 }

   promL2AddressEntry OBJECT-TYPE
      SYNTAX  PromL2AddressEntry
      ACCESS  not-accessible
      STATUS  mandatory
      DESCRIPTION
              "A particular address table entry."
      INDEX   { promL2AddressIndex }
      ::= { promL2AddressTable 1 }

   PromL2AddressEntry ::=
      SEQUENCE {
         promL2AddressIndex
            INTEGER,
         promL2AddressTableIndex
            INTEGER,
         promL2AddressMacAddress
            MacAddress,
         promL2AddressPortBinding
            ResourceId,
         promL2AddressBindingValid
            INTEGER,
         promL2AddressVlanID
            INTEGER,
         promL2AddressPriority
            INTEGER,
         promL2AddressForward
            INTEGER,
         promL2AddressCopy
            INTEGER,
         promL2AddressPersistence
            INTEGER,
         promL2AddressStatus
            INTEGER
      }

   promL2AddressIndex OBJECT-TYPE
      SYNTAX  INTEGER
      ACCESS  read-only
      STATUS  mandatory
      DESCRIPTION
              "An index that uniquely identifies this address entry."
      ::= { promL2AddressEntry 1 }

   promL2AddressTableIndex OBJECT-TYPE
      SYNTAX  INTEGER
      ACCESS  read-only
      STATUS  mandatory
      DESCRIPTION
              "The address table that this entry is associated with."
      ::= { promL2AddressEntry 2 }

   promL2AddressMacAddress OBJECT-TYPE
      SYNTAX  MacAddress
      ACCESS  read-only
      STATUS  mandatory
      DESCRIPTION
              "The IEEE 802 MAC Address associated with this database entry."
      ::= { promL2AddressEntry 3 }

   promL2AddressPortBinding OBJECT-TYPE
      SYNTAX  ResourceId
      ACCESS  read-write
      STATUS  mandatory
      DESCRIPTION
              "The switch port that this address is associated with. "
      ::= { promL2AddressEntry 4 }

   promL2AddressBindingValid OBJECT-TYPE
      SYNTAX  INTEGER {
                 valid(1),
                 invalid(2)
              }
      ACCESS  read-only
      STATUS  mandatory
      DESCRIPTION
              "The port binding of an address entry is aged out in conformance with the
              specifications laid out in the IEEE 802.1D standard.   When the address is
              aged out, the port binding becomes invalid."
      ::= { promL2AddressEntry 5 }

   promL2AddressVlanID OBJECT-TYPE
      SYNTAX  INTEGER
      ACCESS  read-only
      STATUS  mandatory
      DESCRIPTION
              "The VLAN ID of the VLAN that this address entry corresponds to."
      ::= { promL2AddressEntry 6 }

   promL2AddressPriority OBJECT-TYPE
      SYNTAX  INTEGER {
                 priorityZero(1),
                 priorityFour(2)
              }
      ACCESS  read-write
      STATUS  mandatory
      DESCRIPTION
              "If set to high(2), frames destined to this address are classified with priority
              value 4."
      ::= { promL2AddressEntry 7 }

   promL2AddressForward OBJECT-TYPE
      SYNTAX  INTEGER {
                 normalForward(1),
                 specialDelivery(2)
              }
      ACCESS  read-only
      STATUS  mandatory
      DESCRIPTION
              "When set to specialDelivery(2), frames sent to this address are treated to
              special delivery where the spanning tree state of the inbound port is
              ignored.  Typically, special delivery is only used for Bridge PDUs such as
              spanning tree frames."
      ::= { promL2AddressEntry 8 }

   promL2AddressCopy OBJECT-TYPE
      SYNTAX  INTEGER {
                 normalForward(1),
                 copyCPU(2)
              }
      ACCESS  read-only
      STATUS  mandatory
      DESCRIPTION
              "It is sometimes useful for the switch processor to eavesdrop on traffic to
              certain destinations.   This is especially useful in supporting the intelligent
              multicasting function."
      ::= { promL2AddressEntry 9 }

   promL2AddressPersistence OBJECT-TYPE
      SYNTAX  INTEGER {
                 other(1),
                 invalid(2),
                 permanent(3),
                 deleteOnReset(4),
                 deleteOnTimeout(5)
              }
      ACCESS  read-write
      STATUS  mandatory
      DESCRIPTION
              "This object indicates the persistence of this entry:

              other(1) - This entry is currently in use but the conditions under which it
              will remain so are different from each of the following values.

              invalid(2) - Writing this value to the object removes the corresponding
              entry.

              permanent(3) -  Address is not aged out. Additionally, if the address is seen
              as a source on a different port for this VLAN, the frame is filtered and the
              filter event is counted.  Static address entries are stored in non-volatile
              memory and are restored to the address table following each system reset.

              deleteOnReset(4) - Indicates that the entry is not aged out, however the
              entry is not stored in non-volatile memory.  Therefore, when the device is
              reset, the entry will not be restored.

              deleteOnTimeout(5) - Typically, address entries are learned dynamically by
              the switch.  These entries are aged out of the table if they are not active on
              the network.  This value
              correlates to this state."
      ::= { promL2AddressEntry 10 }

   promL2AddressStatus OBJECT-TYPE
      SYNTAX  INTEGER {
                 other(1),
                 learned(2),
                 self(3),
                 mgmt(4)
              }
      ACCESS  read-only
      STATUS  mandatory
      DESCRIPTION
              "This object indicates the status of the entry:

              other(1) - None of the following.

              learned(2) - This entry was learned dynamically.

              self(3) - The value of the corresponding instance of
              promAddressMacAddress represents one of the bridge's addresses.

              mgmt(4) - This entry was added or modified by management.  Entries
              that have been added by management and made permanent"
      ::= { promL2AddressEntry 11 }



-- Address Summary Table

   promL2AddrSummaryMgt OBJECT IDENTIFIER ::= { promL2AddrMgmt 2 }

   promL2AddrSummaryTable OBJECT-TYPE
      SYNTAX  SEQUENCE OF PromL2AddrSummaryEntry
      ACCESS  not-accessible
      STATUS  mandatory
      DESCRIPTION
              "This summary table packs the address entries in the address database into
              summary objects.  The goal is to optimize the upload of the large amount
              of data stored therein.

              Typically, a management station would use getNext requests to retrieve the
              next logical summary object.  The returned object value contains the next n
              entries of the address database packed into one PDU.  The instance of the
              object returned is the index of the last address entry packed in the
              summary, thereby optimizing for the next getNext request."
      ::= { promL2AddrSummaryMgt 1 }

   promL2AddrSummaryEntry OBJECT-TYPE
      SYNTAX  PromL2AddrSummaryEntry
      ACCESS  not-accessible
      STATUS  mandatory
      DESCRIPTION
              "A summary object that packs as many address entries possible into a
              summary object."
      INDEX   { promL2AddressIndex }
      ::= { promL2AddrSummaryTable 1 }

   PromL2AddrSummaryEntry ::=
      SEQUENCE {
         promL2AddrSummary
            OCTET STRING
      }

   promL2AddrSummary OBJECT-TYPE
      SYNTAX  OCTET STRING (SIZE(20..4096))
      ACCESS  read-only
      STATUS  mandatory
      DESCRIPTION
              "The value of this object is a packed opaque structure representing an array
              of address entries.  The format of this structure is:

              struct L2AddressEntry {
                 UNS32 index;
                 UNS8  addr[6];     // mac address
                 UNS8  fabricPort;  //fabricPort and subPort == promL2AddressPortBinding
                 UNS8  subPort;
                 UNS16 vlanID,      //the global vlan id
                 UNS8 portBindingValidFlag;
                 UNS8 addressForwardFlag;
                 UNS8 addressCopyFlag;
                 UNS8 addressPersistence;
                 UNS8 addressStatus;
              };

              struct L2AddressSummary{
                 UNS8 numberOfEntries;  // Number of entries that follow
                 UNS8 version;             // version == 1
                 UNS16 endianFlag;
                 L2AddressEntry entryArray[numberOfEntries];
              };"
      ::= { promL2AddrSummaryEntry 1 }



-- Address Control

   promL2AddrControlMgt OBJECT IDENTIFIER ::= { promL2AddrMgmt 3 }

   promL2AddressControlTable OBJECT-TYPE
      SYNTAX  SEQUENCE OF PromL2AddressControlEntry
      ACCESS  not-accessible
      STATUS  mandatory
      DESCRIPTION
              "This table provides the network manager the ability to create new, static
              address entries.  Entries added through this table are added to the specified
              address table as a static entry and are save in non-volatile memory for
              reconfiguration upon system restart.

              This table is indexed by the promAgentMgrIndex value which provides a
              separate instance for each manager."
      ::= { promL2AddrControlMgt  1 }

   promL2AddressControlEntry OBJECT-TYPE
      SYNTAX  PromL2AddressControlEntry
      ACCESS  not-accessible
      STATUS  mandatory
      DESCRIPTION
              "A control entry enables this manager to add a new entry to the specified
              address table.  When the entry is written to, the control index value is reset
              to 0.  When the actual entry is created, the index value will read as non-zero,
              reporting the actual entry created."
      INDEX   { promAgentMgrIndex }
      ::= { promL2AddressControlTable 1 }

   PromL2AddressControlEntry ::=
      SEQUENCE {
         promL2AddressControlIndex
            INTEGER,
         promL2AddressControlMacAddress
            MacAddress,
         promL2AddressControlPortBinding
            ResourceId,
         promL2AddressControlVlanID
            INTEGER,
         promL2AddressControlPriority
            INTEGER,
         promL2AddressControlPersistence
            INTEGER,
         promL2AddressControlStatus
            INTEGER
      }

   promL2AddressControlIndex OBJECT-TYPE
      SYNTAX  INTEGER
      ACCESS  read-only
      STATUS  mandatory
      DESCRIPTION
              "The index of the address entry that was created for this address."
      ::= { promL2AddressControlEntry 1 }

   promL2AddressControlMacAddress OBJECT-TYPE
      SYNTAX  MacAddress
      ACCESS  read-write
      STATUS  mandatory
      DESCRIPTION
              "The IEEE 802 MAC Address associated with this database entry."
      ::= { promL2AddressControlEntry 2 }

   promL2AddressControlPortBinding OBJECT-TYPE
      SYNTAX  ResourceId
      ACCESS  read-write
      STATUS  mandatory
      DESCRIPTION
              "The port to bind this address to."
      ::= { promL2AddressControlEntry 3 }

   promL2AddressControlVlanID OBJECT-TYPE
      SYNTAX  INTEGER
      ACCESS  read-write
      STATUS  mandatory
      DESCRIPTION
              "The VLAN ID of the VLAN to bind this address to."
      ::= { promL2AddressControlEntry 4 }

   promL2AddressControlPriority OBJECT-TYPE
      SYNTAX  INTEGER {
                 priorityZero(1),
                 priorityFour(2)
              }
      ACCESS  read-write
      STATUS  mandatory
      DESCRIPTION
              "If set to high(2), frames destined to this address are classified with priority
              value 4."
      ::= { promL2AddressControlEntry 5 }


   promL2AddressControlPersistence OBJECT-TYPE
      SYNTAX  INTEGER {
                 permanent(1),
                 deleteOnReset(2),
                 deleteOnTimeout(3)
              }
      ACCESS  read-write
      STATUS  mandatory
      DESCRIPTION
              "The persistence of the entry to be created:

              permanent(1) -  Address is not aged out. Additionally, if the address is seen
              as a source on a different port for this VLAN, the frame is filtered and the
              filter event is counted.  Static address entries are stored in non-volatile
              memory and are restored to the address table following each system reset.

              deleteOnReset(2) - Indicates that the entry is not to be aged, however the
              entry is not stored in non-volatile memory.  Therefore, when the device is
              reset, the entry will not be restored.

              deleteOnTimeout(3) - Indicates that the entry is to be aged by the normal
              aging process."
      ::= { promL2AddressControlEntry 6 }

   promL2AddressControlStatus OBJECT-TYPE
      SYNTAX  INTEGER {
                 createRequest(1),
                 underCreation(2),
                 success(3),
                 otherError(4),
                 entryExistsError(5),
                 invalidMacAddress(6),
                 invalidPortBinding(7),
                 invalidVlanID(8)
              }
      ACCESS  read-write
      STATUS  mandatory
      DESCRIPTION
              "The status of an entry to be created.  When adding an entry all fields will
              be set, and then the control status is set to createRequest(1), indicating that
              the entry is to be created.  During creation, the status will be
              underCreation(2).  If the creation is successful, then the status will be set to
              success(3), and the value of promAddressControlIndex indicates the index
              of the entry that was created in the address table.  Otherwise if the creation
              was not successful, then one of the following error codes will be set and
              the entry will not be created:

              otherError(4) - An error other then the others defined.

              entryExistsError(5) - An entry already exists with this MAC address in this
              address table.

              invalidMacAddress(6) - Cannot create an entry with this MAC address.

              invalidTableIndex(7) - The table does not exist.

              invalidPortBinding(8) - The port binding is invalid.

              invalidVlanID(9) - The VLAN ID is invalid.

              Note that the only value that is valid to write to this object is
              createRequest(1), and that this object will never return the value
              createRequest(1)."
      ::= { promL2AddressControlEntry 7 }



-- Address Change

   promL2AddrChangeMgt OBJECT IDENTIFIER ::= { promL2AddrMgmt 4 }

-- Address Change Information

   promL2AddressChangeLast OBJECT-TYPE
      SYNTAX  INTEGER
      ACCESS  read-only
      STATUS  mandatory
      DESCRIPTION
              "The index of the last entry written to the address change table"
      ::= { promL2AddrChangeMgt  1 }

   promL2AddressChangeWraps OBJECT-TYPE
      SYNTAX  Counter
      ACCESS  read-only
      STATUS  mandatory
      DESCRIPTION
              "The count of the number of times the address change table has wrapped."
      ::= { promL2AddrChangeMgt  2 }

   promL2AddressChangeMaxEntries OBJECT-TYPE
      SYNTAX  INTEGER (1024..4096)
      ACCESS  read-write
      STATUS  mandatory
      DESCRIPTION
              "The maximum number of entries in the address change table."
      ::= { promL2AddrChangeMgt  3 }



-- Address Change Tables
--
-- Address Change Tables
--
   promL2AddressChangeTable OBJECT-TYPE
      SYNTAX  SEQUENCE OF PromL2AddressChangeEntry
      ACCESS  not-accessible
      STATUS  mandatory
      DESCRIPTION
              "."
      ::= { promL2AddrChangeMgt 4 }

   promL2AddressChangeEntry OBJECT-TYPE
      SYNTAX  PromL2AddressChangeEntry
      ACCESS  not-accessible
      STATUS  mandatory
      DESCRIPTION
              "The address change table provides a quick way of getting only the entries
              that have recently changed.  Since entries age out as part of the normal
              switching process, entries that have aged (i.e. their destination bindings are
              no longer valid) are not considered to be changed.  Any other modification
              to the entry, including deletion or creation, are considered to be changes.

              The address change table is considered a circular table.  When an entry
              changes, it is added to the next position within the table.  If the 'next'
              position goes beyond the end of the table,  the 'next' position is set to the
              beginning of the table (1) and the wrap counter
              (promAddressChangeWraps) is incremented.  The
              promAddressChangeLast value is updated with the index of the last
              entered entry.

              An entry may be in the table multiple times if it has changed multiple times.
              Every time that an entry changes, it is added to the change table.

              A network management application should follow the following algorithm
              when polling this table:

              1. Set lastChangeWrap = promAddressChangeWraps.
              2. Set lastChangeIndex = promAddressChangeLast
              3. Get the entire promAddressEntryTable.
              4. Submit a getNext for <lastChangeWrap>.<lastChangeIndex>,
              updating lastChangeWrap and lastChangeIndex with the returned next
              values.  Update the address entry database with the changed values.
              5. Repeat step 4 until no more entries are returned.
              6. Wait polling timeout period.
              7. Get wrap events counter and last index.  If the wrap events counter is
              equal to lastChangeWrap, then goto step 4.  Else if the wrap events
              counter is more then one greater then lastChangeWrap, goto step 1.
              Else the wrap events counter is exactly one greater then
              lastChangeWrap, and if the last index is greater then lastChangeIndex,
              then goto step 1, else goto step 4.

              The last step simply insures that we have not missed any of the change
              entries.  Essentially it says that if we have wrapped to beyond where we last
              polled, then we must get the entire table to synch up again.  Otherwise we
              can just get the entries that have changed."
      INDEX   { promL2AddressChangeWrapCount,
                promL2AddressChangeIndex }
      ::= { promL2AddressChangeTable 1 }

   PromL2AddressChangeEntry ::=
      SEQUENCE {
         promL2AddressChangeWrapCount
            INTEGER,
         promL2AddressChangeIndex
            INTEGER,
         promL2AddressChangeIndexChanged
            INTEGER,
         promL2AddressChangeSummary
            OCTET STRING
      }

   promL2AddressChangeWrapCount OBJECT-TYPE
      SYNTAX  INTEGER
      ACCESS  read-only
      STATUS  mandatory
      DESCRIPTION
              "The number of times that the promAddressChangeLastIndex had
              wrapped when this entry was added."
      ::= { promL2AddressChangeEntry 1 }

   promL2AddressChangeIndex OBJECT-TYPE
      SYNTAX  INTEGER
      ACCESS  read-only
      STATUS  mandatory
      DESCRIPTION
              "The index that uniquely identifies this address change entry."
      ::= { promL2AddressChangeEntry 2 }

   promL2AddressChangeIndexChanged OBJECT-TYPE
      SYNTAX  INTEGER
      ACCESS  read-only
      STATUS  mandatory
      DESCRIPTION
              "The address entry that changed.  The value of this object corresponds to
              the promL2AddressIndex object. "
      ::= { promL2AddressChangeEntry 3 }

   promL2AddressChangeSummary OBJECT-TYPE
      SYNTAX  OCTET STRING (SIZE(20))
      ACCESS  read-only
      STATUS  mandatory
      DESCRIPTION
              " The structure is interpreted in the following manner:"
      ::= { promL2AddressChangeEntry 4 }


-- SWITCH PORT MANAGEMENT

   promSwitchPortMgt OBJECT IDENTIFIER ::= { promSwitching 2 }

-- Switch Port Table
--
--  The switch port table manages the configuration and status of each
--  switch port.

   promSwitchPortTable OBJECT-TYPE
      SYNTAX  SEQUENCE OF PromSwitchPortEntry
      ACCESS  not-accessible
      STATUS  mandatory
      DESCRIPTION
              ""
      ::= { promSwitchPortMgt 1 }

   promSwitchPortEntry OBJECT-TYPE
      SYNTAX  PromSwitchPortEntry
      ACCESS  not-accessible
      STATUS  mandatory
      DESCRIPTION
              ""
      INDEX   { promSwitchPortIndex }
      ::= { promSwitchPortTable 1 }

   PromSwitchPortEntry ::=
      SEQUENCE {
         promSwitchPortIndex
            ResourceId,
         promSwitchPortSTAPMode
            INTEGER,
         promSwitchPortConvertToStatic
            INTEGER,
         promSwitchPortLearningMode
            INTEGER,
         promSwitchPortHuntGroup
            INTEGER,
         promSwitchPortPhysicalPort
            ResourceId,
         promSwitchPortKnownMode
            INTEGER,
         promSwitchPortMappingMethod
            INTEGER,
         promSwitchPortTrunkingMode
            INTEGER,
         promSwitchPortVlanBindingMethod
            INTEGER,
         promSwitchPortIgnoreTag
            INTEGER,
         promSwitchPortVlanID
            INTEGER,
         promSwitchPort3ComMappingTableIndex
            INTEGER,
         promSwitchPortAutoVlanCreation
            INTEGER,
         promSwitchPortMirrorMode
            INTEGER,
         promSwitchPortIfIndex
            INTEGER,
         promSwitchPortFastStart
            INTEGER,
         promSwitchPortVtpSnooping
            INTEGER,
         promSwitchPortIntrusionTrap
            INTEGER,
         promSwitchPortIntrusionTrapTimer
            INTEGER
      }

   promSwitchPortIndex OBJECT-TYPE
      SYNTAX  ResourceId
      ACCESS  read-only
      STATUS  mandatory
      DESCRIPTION
              "A unique index that identifies this switch port.  The value of
              this index corresponds to the value of the promResourceIndex for
              switch ports."
      ::= { promSwitchPortEntry 1 }

   promSwitchPortSTAPMode OBJECT-TYPE
      SYNTAX  INTEGER {
                 enable(1),   -- default
                 disable(2)
              }
      ACCESS  read-write
      STATUS  mandatory
      DESCRIPTION
              "Disabling spanning tree on a switch port prevents the switch
              port from participating in the spanning tree process.  When
              disabled(2), this port will neither generate BPDUs, nor process
              received BPDUs.  Also, the port will always start in the
              forwarding state.  A port configured in this mode will not be
              able to detect network loops involving this port.

              The factory default is to enable spanning tree on all ports."
      ::= { promSwitchPortEntry 2 }

   promSwitchPortConvertToStatic OBJECT-TYPE
      SYNTAX  INTEGER {
                 learnAsDynamic(1),
                 convertToStatic(2)
              }
      ACCESS  read-write
      STATUS  mandatory
      DESCRIPTION
              "When this object is set to convertToStatic(2), all addresses
              learned on this port will be added to the non-volatile version
              of the static address table.

              Typically, this object will be used to perform a crude form of
              address database update where the address activity associated
              with this port is collected as static (i.e. permanent) addresses
              while the value of this object is set to convertToStatic(2).
              Following this usually short period of time (perhaps a week of
              activity), the  value of this object is restored back to its
              default value of learnAsDynamic(1) and learning for this port is
              disabled.

              It is important that the user verify the address database to
              verify that only the desired addresses were made permanent."
      ::= { promSwitchPortEntry 3 }

   promSwitchPortLearningMode OBJECT-TYPE
      SYNTAX  INTEGER {
                 enable(1),   -- default
                 disable(2)
              }
      ACCESS  read-write
      STATUS  mandatory
      DESCRIPTION
              "Disable learning on a bridge port to prevent new addresses from
              being added to the address database.  Used in combination with
              static (permanent) address entries, disabling address learning
              is an effective security feature to prevent new hosts from
              appearing on the network, or to prevent hosts from moving to
              different locations in the network.  The default is enable."
      ::= { promSwitchPortEntry 4 }

   promSwitchPortHuntGroup OBJECT-TYPE
      SYNTAX  INTEGER
      ACCESS  read-write
      STATUS  mandatory
      DESCRIPTION
              "Hunt groups provide the capability to logically bind multiple
              switch ports into one switch port.  This provides a way of
              balancing the load of multiple links between like-configured
              switches.

              Care must be taken to configure the hunt groups properly to
              prevent accidental network looping.

              Use this object to bind this port to a specific hunt group.
              When not configured to a specific hunt group, set the value of
              this object to zero."
      ::= { promSwitchPortEntry 5 }

   promSwitchPortPhysicalPort OBJECT-TYPE
      SYNTAX  ResourceId
      ACCESS  read-only
      STATUS  mandatory
      DESCRIPTION
              "The physical port resource bound to this switch port."
      ::= { promSwitchPortEntry 6 }

   promSwitchPortKnownMode OBJECT-TYPE
      SYNTAX  INTEGER {
                 enable(1),
                 disable(2)
              }
      ACCESS  read-write
      STATUS  mandatory
      DESCRIPTION
              "Enabling known mode for this switch port causes the port to
              safely discard frames flooded because they are unknown unicast
              frames.  This mode greatly enhances the efficiency of the port's
              output buffer since space is not wasted for frames not meant for
              this port.

              Enabling this feature disables learning for this port.
              Addresses associated for this port should be entered statically.
              The default is disable."
      ::= { promSwitchPortEntry 7 }

   promSwitchPortMappingMethod OBJECT-TYPE
      SYNTAX  INTEGER {
                 port-based(1)
              }
      ACCESS  read-write
      STATUS  mandatory
      DESCRIPTION
              "The frame mapping method of this switch port.  When set to
              port-based(1) (the factory default), all non-tagged frames are
              classified to the VLAN associated with this switch port."
      ::= { promSwitchPortEntry 8 }

   promSwitchPortTrunkingMode OBJECT-TYPE
      SYNTAX  INTEGER {
                 clear(1),         -- Factory Default
                 ieee8021q(2),     -- IEEE 802.1Q Format
                 multiLevel(3),    -- Multi-level Format
                 trunk3Com(4)      -- 3Com Trunking Format
              }
      ACCESS  read-write
      STATUS  mandatory
      DESCRIPTION
              "The trunking mode of this port.  All frames transmitted out
              this switch port are translated to the appropriate trunking
              format:

                 Clear:           Ethernet or IEEE 802.3 frame format.
                                  This is the default.
                 IEEE 802.1Q:     The original frame with a new Ethernet Type
                                  (Protocol = 0xXXXX) and the VLAN ID inserted
                                  following the original Source Address.
                                  Also, the CRC is recalculated.
                 Multi-level:     The original frame is encapsulated in an
                                  IEEE 802.3 legal frame proprietary to a
                                  major networking equipment vendor.
                 3Com LinkSwitch: The original frame has the VLAN ID added to
                                  the front of the frame (before the
                                  Destination Address).  Trunking format is
                                  proprietary to 3Com Corporation."
      ::= { promSwitchPortEntry 9 }

   promSwitchPortVlanBindingMethod OBJECT-TYPE
      SYNTAX  INTEGER {
                 static(1),
                 persistent(2),
                 dynamic(3)
              }
      ACCESS  read-write
      STATUS  mandatory
      DESCRIPTION
              "The VLAN binding method of a switch port specifies the way in
              which the port can be a member of the egress lists of VLANs
              other than the port default VLAN specified by
              promSwitchPortVlanID:
                 static:      A Virtual Switch Port must be statically created for
                              each VLAN/port combination.
                 persistent:  A Virtual Switch Port is automatically created for
                              each VLAN known to the switch (i.e., the port is
                              a member of the egress lists of all VLANs).
                 dynamic:     A Virtual Switch Port is automatically created for
                              each VLAN when the associated VLAN ID is used as a
                              tag in an IEEE 802.1Q or Multi-level tagged frame
                              received on the port (i.e., the port is a member of
                              the egress lists of the VLANs from frames received
                              on the port).

              The default is static."
      ::= { promSwitchPortEntry 10 }

   promSwitchPortIgnoreTag OBJECT-TYPE
      SYNTAX  INTEGER {
                 useTag(1),      -- default
                 ignoreTag(2)
              }
      ACCESS  read-write
      STATUS  mandatory
      DESCRIPTION
              "Each switch port is capable of ignoring the VLAN Tag associated
              with a frame in a trunking format.  When ignored, the tag is
              used as the default in the event that a VLAN classification
              based on the switch's policy(s) cannot be made.

              This feature is useful for connecting layer 2 VLANs and layer 3
              VLANs.  The default is useTag."
      ::= { promSwitchPortEntry 11 }

   promSwitchPortVlanID OBJECT-TYPE
      SYNTAX  INTEGER
      ACCESS  read-write
      STATUS  mandatory
      DESCRIPTION
              "When this switch port is configured in port-based VLAN mode,
              all non-tagged frames received on this port are bound to this
              VLAN.  Otherwise, non-tagged frames are classified to this VLAN
              as the default if a VLAN binding cannot be otherwise determined.
              The factory default is 1, which is the VLAN ID of the Default
              VLAN."
      ::= { promSwitchPortEntry 12 }

   promSwitchPort3ComMappingTableIndex OBJECT-TYPE
      SYNTAX  INTEGER (1..100)
      ACCESS  read-write
      STATUS  mandatory
      DESCRIPTION
              "The 3Com VLAN mapping table associated with this switch port.
              The default is 1, which indicates the default mapping table."
      ::= { promSwitchPortEntry 13 }

   promSwitchPortAutoVlanCreation OBJECT-TYPE
      SYNTAX  INTEGER {
                 enable(1),
                 disable(2)
              }
      ACCESS  read-write
      STATUS  mandatory
      DESCRIPTION
              "Enabling auto VLAN creation for this switch port causes the
              port to dynamically create a VLAN whenever an IEEE 802.1Q or
              Multi-level tagged frame is received on the port with a tag value
              which does not correspond to a known VLAN.  All switch ports with
              a trunking mode of IEEE 802.1Q or Multi-level are bound to this
              created VLAN.  The default is disable."
      ::= { promSwitchPortEntry 14 }

   promSwitchPortMirrorMode OBJECT-TYPE
      SYNTAX  INTEGER {
                 enable(1),
                 disable(2)
              }
      ACCESS  read-only
      STATUS  mandatory
      DESCRIPTION
              "When set to enable(1), this object indicates that the port is 
              defined as a mirror port through the promPortMirroringTable.  A 
              mirror port duplicates frames received at one or more source ports."
      ::= { promSwitchPortEntry 15 }

   promSwitchPortIfIndex OBJECT-TYPE
      SYNTAX  INTEGER
      ACCESS  read-only
      STATUS  mandatory
      DESCRIPTION
              "Each switch port is associated with an interface.  This object
              provides a mechanism to map switch ports to bridge ports."
      ::= { promSwitchPortEntry 16 }

   promSwitchPortFastStart OBJECT-TYPE
      SYNTAX  INTEGER {
                 enable(1),
                 disable(2)
              }
      ACCESS  read-write
      STATUS  mandatory
      DESCRIPTION
              "When this object is set to enable(1), bridge ports on this switch port 
              transitions right from blocking to forwarding, skipping the listening
              and learning states.  The user should be warned that using the fast start
              feature greatly increases the likelihood of unintended network loops that
              would otherwise be prevented by participating in the normal spanning tree
              algorithm.

              The factory default value for this object is disable(2)."
      ::= { promSwitchPortEntry 17 }

   promSwitchPortVtpSnooping OBJECT-TYPE
      SYNTAX  INTEGER {
                 enable(1),
                 disable(2)
              }
      ACCESS  read-write
      STATUS  mandatory
      DESCRIPTION
              "When this object is set to enable(1), this switch port attempts to
              learn VLANs from a major networking equipment vendor if the switch port's
              trunking mode is IEEE 802.1Q Format or Multi-level Format.

              The factory default value for this object is enable(1)."
      ::= { promSwitchPortEntry 18 }

   promSwitchPortIntrusionTrap OBJECT-TYPE
      SYNTAX  INTEGER {
                 enable(1),
                 disable(2)
              }
      ACCESS  read-write
      STATUS  mandatory
      DESCRIPTION
              "Enabling intrusion trap for this switch port causes the traps to
              be generated when unknown MAC frames are received and port is 
              configured to receive only statically configured MAC frames and
              learning and flooding are disabled.
              The default is disable."
      ::= { promSwitchPortEntry 19 }

   promSwitchPortIntrusionTrapTimer OBJECT-TYPE
      SYNTAX  INTEGER
      ACCESS  read-write
      STATUS  mandatory
      DESCRIPTION
              "Defines the time that elapses between consecutive intrusion traps sent
              when unknown MAC frames are received and port is 
              configured to receive only statically configured MAC frames and
              learning and flooding are disabled.
              The default is 1800 seconds."
      ::= { promSwitchPortEntry 20 }

-- HUNT GROUPS

   promHuntGroupMgt OBJECT IDENTIFIER ::= { promSwitching 4 }

-- A hunt group logically binds together multiple switch ports so that they act as one
-- switch port.  This feature enables the ports within the hunt group to load
-- share the network traffic.
--
-- The hunt group feature is targeted for a restricted topology where two switches
-- are connected together by multiple lines of the same bandwidth.  Hunt groups
-- require that both switches be configured identically to the other.
--
-- Each hunt group requires a base port.  The hunt group assumes the characteristics
-- of the base port where all the managed information (configuration & statistics) of
-- any of the switch ports in the hunt group is only available from the base port
-- instance.

   promHuntGroupTable OBJECT-TYPE
      SYNTAX  SEQUENCE OF PromHuntGroupEntry
      ACCESS  not-accessible
      STATUS  mandatory
      DESCRIPTION
              ""
      ::= { promHuntGroupMgt  1 }

   promHuntGroupEntry OBJECT-TYPE
      SYNTAX  PromHuntGroupEntry
      ACCESS  not-accessible
      STATUS  mandatory
      DESCRIPTION
              ""
      INDEX   { promHuntGroupIndex }
      ::= { promHuntGroupTable 1 }

   PromHuntGroupEntry ::=
      SEQUENCE {
         promHuntGroupIndex
            INTEGER,
         promHuntGroupName
            DisplayString,
         promHuntGroupBasePort
            ResourceId,
         promHuntGroupNumberOfPorts
            INTEGER,
         promHuntGroupLoadSharing
            INTEGER,
         promHuntGroupStatus
            INTEGER
      }

   promHuntGroupIndex OBJECT-TYPE
      SYNTAX  INTEGER
      ACCESS  read-only
      STATUS  mandatory
      DESCRIPTION
              "An index that uniquely identifies this hunt group.  This index corresponds
              to the value of promResourceIndex for resources of the  hunt group type."
      ::= { promHuntGroupEntry 1 }

   promHuntGroupName OBJECT-TYPE
      SYNTAX  DisplayString
      ACCESS  read-write
      STATUS  mandatory
      DESCRIPTION
              ""
      ::= { promHuntGroupEntry 2 }

   promHuntGroupBasePort OBJECT-TYPE
      SYNTAX  ResourceId
      ACCESS  read-only
      STATUS  mandatory
      DESCRIPTION
              "The switch port index that serves as the base port for this hunt group.
              Each hunt group requires a base port.  In lieu of a specific configuration,
              the hunt group will inherit the first switch port bound to the hunt group as
              its base port.

              The base port serves as the management focus for the hunt group.  That is,
              a hunt group is managed as one switch port whose instance is provided by
              the base switch port.  All configuration (e.g. spanning tree information) and
              statistics related to switch ports are meaningful only through the instance of
              the base port."
      ::= { promHuntGroupEntry 3 }

   promHuntGroupNumberOfPorts OBJECT-TYPE
      SYNTAX  INTEGER
      ACCESS  read-only
      STATUS  mandatory
      DESCRIPTION
              "The current number of ports that belong to this hunt group."
      ::= { promHuntGroupEntry 4 }

   promHuntGroupLoadSharing OBJECT-TYPE
      SYNTAX  INTEGER {
                 enable(1),
                 disable(2)
              }
      ACCESS  read-write
      STATUS  mandatory
      DESCRIPTION
              ""
      ::= { promHuntGroupEntry 5 }

   promHuntGroupStatus OBJECT-TYPE
      SYNTAX  INTEGER {
                 createRequest(1),
                 underCreation(2),
                 deleteRequest(3),
                 active(4)
              }
      ACCESS  read-write
      STATUS  mandatory
      DESCRIPTION
              ""
      ::= { promHuntGroupEntry 6 }

-- Port Mirroring

   promPortMirroringMgt OBJECT IDENTIFIER ::= { promSwitching 5 }

-- Port Mirroring is used to duplicate packets received on one or more ports on 
-- another port so that the mirror port can be monitored, for example with an 
-- RMON probe.  Port Mirroring allows either all packets received on the source 
-- port, or a periodic sample, to be duplicated on the mirror port.

   promPortMirroringTable OBJECT-TYPE
      SYNTAX  SEQUENCE OF PromPortMirroringEntry
      ACCESS  not-accessible
      STATUS  mandatory
      DESCRIPTION
              "A table of port mirroring entries used to mirror traffic from 
              a source port to a mirror port."
   ::= { promPortMirroringMgt 1 }

   promPortMirroringEntry OBJECT-TYPE
      SYNTAX  PromPortMirroringEntry
      ACCESS  not-accessible
      STATUS  mandatory
      DESCRIPTION
              "Objects related to the PortMirroring functionality."
      INDEX   { promPortMirroringIndex }
      ::= { promPortMirroringTable 1 }


   PromPortMirroringEntry ::=
      SEQUENCE {
         promPortMirroringIndex
            ResourceId,
         promPortMirroringSourceSubPort
               INTEGER,
         promPortMirroringSamplerType
               INTEGER,
         promPortMirroringRate
               INTEGER,
         promPortMirroringMirrorPort
               ResourceId
      }

   promPortMirroringIndex OBJECT-TYPE
      SYNTAX  ResourceId
      ACCESS  read-only
      STATUS  mandatory
      DESCRIPTION
              "The unique index that identifies this entry. This index consists 
              of a switch fabric port and the index of a Packet Lookup Engine 
              servicing this fabric port."
      ::= { promPortMirroringEntry 1 }

   promPortMirroringSourceSubPort OBJECT-TYPE
      SYNTAX  INTEGER
      ACCESS  read-write
      STATUS  mandatory
      DESCRIPTION
              "The frame sampler source switch subport. The source port is the 
              port from which received traffic will be mirrored.  This object 
              identifies the switch subport only, the switch fabric port is 
              identified in promPortMirroringIndex.  If set to 0, all subports 
              associated with the promPortMirroringIndex will be source ports. The
              default value is 0."
      ::= { promPortMirroringEntry 2 }

   promPortMirroringSamplerType OBJECT-TYPE
      SYNTAX  INTEGER {
                 disable(1),
                 enable(2),
                 periodic(3)
              }
      ACCESS  read-write
      STATUS  mandatory
      DESCRIPTION
              "The type for this frame sampler. When set to enable(1), every 
              frame received on the source port(s) will be mirrored at the mirror
              port. When set to disable(2), no frames received on the source 
              port(s) will be mirrored at the mirror port.  When set to 
              periodic(3), frames will be mirrored at the rate defined in 
              promPortMirroringRate. The default value is disable(2)."
      ::= { promPortMirroringEntry 3 }

   promPortMirroringRate OBJECT-TYPE
      SYNTAX  INTEGER 
      ACCESS  read-write
      STATUS  mandatory
      DESCRIPTION
              "Used in conjunction with promPortMirroringSamplerType to implement 
              periodic sampling functionality. If promPortMirroringSamplerType is 
              set to periodic(3), this object defines the number of packets/second 
              that will be mirrored. If promPortMirroringSamplerType is not 
              periodic(3), this object will set to 0."
      ::= { promPortMirroringEntry 4 }

   promPortMirroringMirrorPort OBJECT-TYPE
      SYNTAX  ResourceId
      ACCESS  read-write
      STATUS  mandatory
      DESCRIPTION
              "The Switch Port on which frames received at source ports(s) will be 
              duplicated. If no mirror port has been defined this object will 
              return NULL."
      ::= { promPortMirroringEntry 5 }


-- VIRTUAL LANS

   promVlanMgt OBJECT IDENTIFIER ::= { prominet 7 }

-- VIRTUAL LAN TABLE

   promVlans OBJECT IDENTIFIER ::= { promVlanMgt 1 }

-- Each entry in this table identifies a virtual LAN.

   promVlanTable OBJECT-TYPE
      SYNTAX  SEQUENCE OF PromVlanEntry
      ACCESS  not-accessible
      STATUS  mandatory
      DESCRIPTION
              ""
      ::= { promVlans 1 }

   promVlanEntry OBJECT-TYPE
      SYNTAX  PromVlanEntry
      ACCESS  not-accessible
      STATUS  mandatory
      DESCRIPTION
              ""
      INDEX   { promVlanID }
      ::= { promVlanTable 1 }

   PromVlanEntry ::=
      SEQUENCE {
         promVlanID
            INTEGER,
         promVlanName
            DisplayString,
         promVlanIfIndex
            INTEGER,
         promVlanAFTIndex
            INTEGER,
         promVlanBridgeIndex
            ResourceId,
         promVlanStatus
            INTEGER,
         promVlanInitialHashTableSize
            INTEGER,
         promVlanAutoIncrementHTSize
            INTEGER,
         promVlanLearnStatus
            INTEGER
      }

   promVlanID OBJECT-TYPE
      SYNTAX  INTEGER
      ACCESS  read-only
      STATUS  mandatory
      DESCRIPTION
              "An identifier that is unique within the administrative domain.
              This ID is assigned by the management application and is
              meaningful within that context.

              This ID is used to identify VLANs when tagged using either the
              IEEE 802.1 frame format or the Multi-level frame format."
      ::= { promVlanEntry 1 }

   promVlanName OBJECT-TYPE
      SYNTAX  DisplayString (SIZE (1..31))
      ACCESS  read-write
      STATUS  mandatory
      DESCRIPTION
              "A user-assignable name for this Vlan."
      ::= { promVlanEntry 2 }


   promVlanIfIndex OBJECT-TYPE
      SYNTAX  INTEGER
      ACCESS  read-only
      STATUS  mandatory
      DESCRIPTION
              "Each virtual LAN has a virtual interface associated with it.
              This enables RMON monitoring to occur per-VLAN.  It also
              provides a handy mechanism to map virtual LANs to bridge ports
              by mapping them with the ifStack table from the Interface MIB."
      ::= { promVlanEntry 3 }

   promVlanAFTIndex OBJECT-TYPE
      SYNTAX  INTEGER
      ACCESS  read-write
      STATUS  mandatory
      DESCRIPTION
              "The address table used for this VLAN for explicitly tagged
              frames (frames received in a trunking frame format or from a
              port in port-based VLAN mode.)  Normally, each VLAN maps to a
              unique address table.  This is useful for environments with
              duplicate host addresses appear on different VLANs on different
              ports.

              For those environments where duplicate hosts on different VLANs
              don't exist, or exist but are on the same port, and where the
              address table size and/or aging is a concern, then multiple
              VLANs may be mapped to the same address table."
      ::= { promVlanEntry 4 }

   promVlanBridgeIndex OBJECT-TYPE
      SYNTAX  ResourceId
      ACCESS  read-write
      STATUS  mandatory
      DESCRIPTION
              "The bridge resource which is bound to this Vlan."
      ::= { promVlanEntry 5 }

   promVlanStatus OBJECT-TYPE
      SYNTAX  INTEGER {
                 createRequest(1),
                 underCreation(2),
                 destroyRequest(3),
                 underDestruction(4),
                 active(5),
                 otherError(6),
                 entryExistsError(7),
                 invalidVlanID(8),
                 invalidVlanName(9),
                 invalidVlanAFTIndex(10),
                 invalidVlanBridgeIndex(11),
                 invalidVlanInitialHashTableSize(12),
                 invalidVlanAutoIncrementHTSize(13)
              }
      ACCESS  read-write
      STATUS  mandatory
      DESCRIPTION
              "The status of an entry to be created or deleted.
              When adding an entry all fields will be set, and then the status
              is set to createRequest(1) (indicating that the entry is to be
              created).  When deleting an entry the status is set to
              destroyRequest(3) (indicating that the entry is to be destroyed).
              During creation the status will be underCreation(2). If the
              creation is successful, then the status will be set to
              active(5).  Otherwise if the creation was not successful then
              one of the following error codes will be set and the entry will
              not be created:
                 otherError(6) - An error other than the others defined.
                 entryExistsError(7) - An entry already exists.
                 invalidVlanID(8) - the VLAN ID is invalid.
                 invalidVlanName(9) - the VLAN name is invalid.
                 invalidVlanAFTIndex(10) - the VLAN AFT index is invalid.
                 invalidVlanBridgeIndex(11) - the VLAN bridge index is invalid.
                 invalidVlanInitialHashTableSize(12) - the VLAN initial hash
                                                       table size is invalid.
                 invalidVlanAutoIncrementHTSize(13) - the VLAN auto increment
                                                      hash table size is
                                                      invalid."
      ::= { promVlanEntry 6 }

   promVlanInitialHashTableSize OBJECT-TYPE
      SYNTAX  INTEGER (16..8192)
      ACCESS  read-write
      STATUS  mandatory
      DESCRIPTION
              "The initial hash table size used for MAC addresses on this
              VLAN.  This attribute may only be set when promVlanStatus is
              set to createRequest(1).  It must be a power of 2 between 16
              and 8192, inclusive."
      ::= { promVlanEntry 7 }

   promVlanAutoIncrementHTSize OBJECT-TYPE
      SYNTAX  INTEGER {
                 true(1),
                 false(2)
              }
      ACCESS  read-write
      STATUS  mandatory
      DESCRIPTION
              "This attribute specifies whether or not the hash table size
              used for MAC addresses on this VLAN is automatically increased
              as necessary to hold more MAC addresses.  This attribute may only
              be set when promVlanStatus is set to createRequest(1)."
      ::= { promVlanEntry 8 }

   promVlanLearnStatus OBJECT-TYPE
      SYNTAX  INTEGER {
                 notLearned(1),
                 vtpSnooping(2),
                 auto(3)
              }
      ACCESS  read-only
      STATUS  mandatory
      DESCRIPTION
              "This attribute indicates if the VLAN was learned.  If learned
              it indicates if the VLAN was learned either by VTP or
              Auto VLAN creation."
      ::= { promVlanEntry 9 }


-- 3COM MAPPING TABLES

   promVlanMappings OBJECT IDENTIFIER ::= { promVlanMgt 3 }

-- 3Com Map Table Identification

   prom3ComMapping OBJECT IDENTIFIER ::= { promVlanMappings 1 }

   prom3ComMappingTable OBJECT-TYPE
      SYNTAX  SEQUENCE OF Prom3ComMappingEntry
      ACCESS  not-accessible
      STATUS  mandatory
      DESCRIPTION
              ""
      ::= { prom3ComMapping 1 }

   prom3ComMappingEntry OBJECT-TYPE
      SYNTAX  Prom3ComMappingEntry
      ACCESS  not-accessible
      STATUS  mandatory
      DESCRIPTION
              ""
      INDEX   { prom3ComMappingTableIndex }
      ::= { prom3ComMappingTable 1 }

   Prom3ComMappingEntry ::=
      SEQUENCE {
         prom3ComMappingTableIndex
            INTEGER,
         prom3ComMappingTableName
            DisplayString,
         prom3ComMappingTableStatus
            INTEGER
      }

   prom3ComMappingTableIndex OBJECT-TYPE
      SYNTAX  INTEGER
      ACCESS  read-only
      STATUS  mandatory
      DESCRIPTION
              ""
      ::= { prom3ComMappingEntry 1 }

   prom3ComMappingTableName OBJECT-TYPE
      SYNTAX  DisplayString (SIZE (1..31))
      ACCESS  read-write
      STATUS  mandatory
      DESCRIPTION
              "A user-readable name associated with this table."
      ::= { prom3ComMappingEntry 2 }

   prom3ComMappingTableStatus OBJECT-TYPE
      SYNTAX  INTEGER {
                 createRequest(1),
                 destroyRequest(2),
                 active(3),
                 entryExistsError(4),
                 otherError(5)
              }
      ACCESS  read-write
      STATUS  mandatory
      DESCRIPTION
              "The status of an entry to be created. When adding an entry all
              fields will be set, and then the status is set to
              createRequest(1), indicating that the entry is to be created.
              If the creation is successful, then the status will be set to
              active(3).  Otherwise if the creation was not successful then
              one of the following error codes will be set and the entry will
              not be created:
                 entryExistsError(4) - An entry already exists.
                 otherError(5) - An error other than the others defined."
      ::= { prom3ComMappingEntry 3 }


-- 3Com VLAN Mappings

   promVlan3ComMapping OBJECT IDENTIFIER ::= { promVlanMappings 2 }

   promVlan3ComMappingTable OBJECT-TYPE
      SYNTAX  SEQUENCE OF PromVlan3ComMappingEntry
      ACCESS  not-accessible
      STATUS  mandatory
      DESCRIPTION
              ""
      ::= { promVlan3ComMapping 1 }

   promVlan3ComMappingEntry OBJECT-TYPE
      SYNTAX  PromVlan3ComMappingEntry
      ACCESS  not-accessible
      STATUS  mandatory
      DESCRIPTION
              ""
      INDEX   { prom3ComMappingTableIndex,
                promVlan3ComMappingIndex }
      ::= { promVlan3ComMappingTable 1 }

   PromVlan3ComMappingEntry ::=
      SEQUENCE {
         promVlan3ComMappingIndex
            INTEGER,
         promVlan3ComMappingVlanID
            INTEGER,
         promVlan3ComMappingStatus
            INTEGER
      }

   promVlan3ComMappingIndex OBJECT-TYPE
      SYNTAX  INTEGER (1..16)
      ACCESS  read-only
      STATUS  mandatory
      DESCRIPTION
              "The external tag of this 3Com VLAN."
      ::= { promVlan3ComMappingEntry 1 }

   promVlan3ComMappingVlanID OBJECT-TYPE
      SYNTAX  INTEGER
      ACCESS  read-write
      STATUS  mandatory
      DESCRIPTION
              "The VLAN ID of the VLAN that this 3Com tag is associated with."
      ::= { promVlan3ComMappingEntry 2 }

   promVlan3ComMappingStatus OBJECT-TYPE
      SYNTAX  INTEGER {
                 createRequest(1),
                 destroyRequest(2),
                 active(3),
                 otherError(4)
              }
      ACCESS  read-write
      STATUS  mandatory
      DESCRIPTION
              "The status of an entry to be created. When adding an entry all
              fields will be set, and then the status is set to
              createRequest(1), indicating that the entry is to be created.
              If the creation is successful, then the status will be set to
              active(3).  Otherwise if the creation was not successful then
              one of the following error codes will be set and the entry will
              not be created:
                 otherError(4) - An error other than the others defined."
      ::= { promVlan3ComMappingEntry 3 }



-- VIRTUAL SWITCH PORTS

   promVirtualPorts OBJECT IDENTIFIER ::= { promVlanMgt 4 }

   promVirtualSwitchPortTable OBJECT-TYPE
      SYNTAX  SEQUENCE OF PromVirtualSwitchPortEntry
      ACCESS  not-accessible
      STATUS  mandatory
      DESCRIPTION
              ""
      ::= { promVirtualPorts 1 }

   promVirtualSwitchPortEntry OBJECT-TYPE
      SYNTAX  PromVirtualSwitchPortEntry
      ACCESS  not-accessible
      STATUS  mandatory
      DESCRIPTION
              "An instance of a virtual switch port indicates that this
              switch port is a member of this VLAN."
      INDEX   { promVirtualSwitchPortIndex }
      ::= { promVirtualSwitchPortTable 1 }

   PromVirtualSwitchPortEntry ::=
      SEQUENCE {
         promVirtualSwitchPortIndex
            ResourceId,
         promVirtualSwitchPortFormat
            INTEGER,
         promVirtualSwitchPortBridgePort
            ResourceId,
         promVirtualSwitchPortBindingType
            INTEGER,
         promVirtualSwitchPortStatus
            INTEGER
      }

   promVirtualSwitchPortIndex OBJECT-TYPE
      SYNTAX  ResourceId
      ACCESS  read-only
      STATUS  mandatory
      DESCRIPTION
              "The Resource ID of the virtual switch port bound to the VLAN."
      ::= { promVirtualSwitchPortEntry 1 }

   promVirtualSwitchPortFormat OBJECT-TYPE
      SYNTAX  INTEGER {
                 clear(1),          -- don't tag for this VLAN, port
                 trunkingFormat(2)  -- use switch port format - may be clear
              }
      ACCESS  read-write
      STATUS  mandatory
      DESCRIPTION
              "Typically, a VLAN capable switch port has one of three modes:
              access, trunk, or hybrid.  In access mode, the port sends
              frames in clear format (untagged). In trunk mode, all outbound
              frames are translated into the switch port's configured
              trunking format.

              In hybrid mode, it is possible for a port to send trunked
              frames for some VLANs and clear frames for others.  In this
              case, the switch port is configured to trunk, and the virtual
              switch port(s) for those VLANs that require clear formatted
              frames are configured to be override the switch port setting.
              This is done by setting this object to clear(1).

              By default, the value of this object is trunkingFormat(2)
              which means to use the trunking format configured for this
              switch port. (which may be clear)."
      ::= { promVirtualSwitchPortEntry 2 }

   promVirtualSwitchPortBridgePort OBJECT-TYPE
      SYNTAX  ResourceId
      ACCESS  read-write
      STATUS  mandatory
      DESCRIPTION
              "The bridge port resource bound to this virtual port."
      ::= { promVirtualSwitchPortEntry 3 }

   promVirtualSwitchPortBindingType OBJECT-TYPE
      SYNTAX  INTEGER {
                 static(1),         -- port binding was manually created
                 persistent(2),     -- port binding was automatically created
                 dynamic(3)         -- port binding was automatically created
              }
      ACCESS  read-only
      STATUS  mandatory
      DESCRIPTION
              "The method by which this switch port was bound to the VLAN.
              If the value is static(1), the binding was manually created
              by the administrator.  If the value is persistent(2), the
              binding was created by the switch because the VLAN is the
              port-based VLAN for the switch port, or the switch port
              VLAN Binding Method is persistent.  These bindings may not
              be removed.  If the value is dynamic(3), the binding was
              created by the switch as a result of receiving a tagged
              frame on the switch port with a VLAN ID corresponding to
              the VLAN."
      ::= { promVirtualSwitchPortEntry 4 }

   promVirtualSwitchPortStatus OBJECT-TYPE
      SYNTAX  INTEGER {
                 createRequest(1),
                 destroyRequest(2),
                 active(3),
                 otherError(4),
                 entryExistsError(5),
                 entryNoExistError(6)
              }
      ACCESS  read-write
      STATUS  mandatory
      DESCRIPTION
              "The status of an entry to be created or deleted.
              When adding an entry all fields will be set, and then the status
              is set to createRequest(1) (indicating that the entry is to be
              created).  When deleting an entry the status is set to
              destroyRequest(2) (indicating that the entry is to be destroyed).
              If the creation is successful, then the status will be set to
              active(3).  Otherwise if the creation was not successful then
              one of the following error codes will be set and the entry will
              not be created:
                 otherError(4) - An error other than the others defined.
                 entryExistsError(5) - On creation, an entry already exists.
                                       On deletion, the entry may not be
                                       removed.
                 entryNoExistError(6) - The VLAN specified by ID
                                        does not exist."
      ::= { promVirtualSwitchPortEntry 5 }


   promVirtualModulePortTable OBJECT-TYPE
      SYNTAX  SEQUENCE OF PromVirtualModulePortEntry
      ACCESS  not-accessible
      STATUS  mandatory
      DESCRIPTION
              ""
      ::= { promVirtualPorts 2 }

   promVirtualModulePortEntry OBJECT-TYPE
      SYNTAX  PromVirtualModulePortEntry
      ACCESS  not-accessible
      STATUS  mandatory
      DESCRIPTION
              "An instance of a virtual module port indicates that this
              module port is a member of this VLAN."
      INDEX   { promVlanID, promPortIndex }
      ::= { promVirtualModulePortTable 1 }

   PromVirtualModulePortEntry ::=
      SEQUENCE {
         promVirtualModulePortIndex
            ResourceId,
         promVirtualModulePortFormat
            INTEGER,
         promVirtualModulePortBridgePort
            ResourceId,
         promVirtualModulePortBindingType
            INTEGER,
         promVirtualModulePortModuleName
            DisplayString,
         promVirtualModulePortPortName
            DisplayString
      }

   promVirtualModulePortIndex OBJECT-TYPE
      SYNTAX  ResourceId
      ACCESS  read-only
      STATUS  mandatory
      DESCRIPTION
              "The Resource ID of the virtual switch port bound to the VLAN."
      ::= { promVirtualModulePortEntry 1 }

   promVirtualModulePortFormat OBJECT-TYPE
      SYNTAX  INTEGER {
                 clear(1),          -- don't tag for this VLAN, port
                 trunkingFormat(2)  -- use switch port format - may be clear
              }
      ACCESS  read-only
      STATUS  mandatory
      DESCRIPTION
              "Typically, a VLAN capable switch port has one of three modes:
              access, trunk, or hybrid.  In access mode, the port sends
              frames in clear format (untagged). In trunk mode, all outbound
              frames are translated into the switch port's configured
              trunking format.

              In hybrid mode, it is possible for a port to send trunked
              frames for some VLANs and clear frames for others.  In this
              case, the switch port is configured to trunk, and the virtual
              switch port(s) for those VLANs that require clear formatted
              frames are configured to be override the switch port setting.
              This is done by setting this object to clear(1).

              By default, the value of this object is trunkingFormat(2)
              which means to use the trunking format configured for this
              switch port. (which may be clear)."
      ::= { promVirtualModulePortEntry 2 }

   promVirtualModulePortBridgePort OBJECT-TYPE
      SYNTAX  ResourceId
      ACCESS  read-only
      STATUS  mandatory
      DESCRIPTION
              "The bridge port resource bound to this virtual port."
      ::= { promVirtualModulePortEntry 3 }

   promVirtualModulePortBindingType OBJECT-TYPE
      SYNTAX  INTEGER {
                 static(1),         -- port binding was manually created
                 persistent(2),     -- port binding was automatically created
                 dynamic(3)         -- port binding was automatically created
              }
      ACCESS  read-only
      STATUS  mandatory
      DESCRIPTION
              "The method by which this switch port was bound to the VLAN.
              If the value is static(1), the binding was manually created
              by the administrator.  If the value is persistent(2), the
              binding was created by the switch because the VLAN is the
              port-based VLAN for the switch port, or the switch port
              VLAN Binding Method is persistent.  These bindings may not
              be removed.  If the value is dynamic(3), the binding was
              created by the switch as a result of receiving a tagged
              frame on the switch port with a VLAN ID corresponding to
              the VLAN."
      ::= { promVirtualModulePortEntry 4 }

   promVirtualModulePortModuleName OBJECT-TYPE
      SYNTAX  DisplayString (SIZE (0..31))
      ACCESS  read-only
      STATUS  mandatory
      DESCRIPTION
              "The name for this module."
      ::= { promVirtualModulePortEntry 5 }

   promVirtualModulePortPortName OBJECT-TYPE
      SYNTAX  DisplayString (SIZE(0..31))
      ACCESS  read-only
      STATUS  mandatory
      DESCRIPTION
              "The name for this port."
      ::= { promVirtualModulePortEntry 6 }


-- EVENT MANAGEMENT

   promEvents OBJECT IDENTIFIER ::= { prominet 10 }

-- EVENT TABLE

   promEventMgt OBJECT IDENTIFIER ::= { promEvents 1 }

-- Event Table
--

   promEventTable OBJECT-TYPE
      SYNTAX  SEQUENCE OF  PromEventEntry
      ACCESS  not-accessible
      STATUS  mandatory
      DESCRIPTION
              "Table of events currently supported."
      ::= { promEventMgt 1 }

   promEventEntry OBJECT-TYPE
      SYNTAX  PromEventEntry
      ACCESS  not-accessible
      STATUS  mandatory
      DESCRIPTION
              "Attributes associated with the event."
      INDEX   { promEventIndex }
      ::= { promEventTable 1 }

   PromEventEntry ::=
      SEQUENCE {
         promEventIndex
            INTEGER,
         promEventMode
            INTEGER,
         promEventLogAction
            INTEGER,
         promEventTrapAction
            INTEGER,
         promEventConsoleAction
            INTEGER
      }

   promEventIndex OBJECT-TYPE
      SYNTAX  INTEGER
      ACCESS  read-only
      STATUS  mandatory
      DESCRIPTION
              ""
      ::= { promEventEntry 1 }

   promEventMode OBJECT-TYPE
      SYNTAX  INTEGER {
                 enable(1),
                 disable(2)
              }
      ACCESS  read-write
      STATUS  mandatory
      DESCRIPTION
              "Disabling an event prevents this event from taking any actions when
              triggered.
              When set to enable to the console, the event will print the event information
              to the console serial port.  The user can select whether to view log
              messages, trap messages or any event at the console."
      ::= { promEventEntry 2 }

--
-- promEventCategory has been removed
--

   promEventLogAction OBJECT-TYPE
      SYNTAX  INTEGER {
                 enable(1),
                 disable(2)
              }
      ACCESS  read-write
      STATUS  mandatory
      DESCRIPTION
              "When enabled, this action will cause an event log entry to be created."
      ::= { promEventEntry 3 }

   promEventTrapAction OBJECT-TYPE
      SYNTAX  INTEGER {
                 enable(1),
                 disable(2)
              }
      ACCESS  read-write
      STATUS  mandatory
      DESCRIPTION
              "When enabled, this event will cause an SNMP trap to be generated."
      ::= { promEventEntry 4 }

   promEventConsoleAction OBJECT-TYPE
      SYNTAX  INTEGER {
                 enable(1),
                 disable(2)
              }
      ACCESS  read-write
      STATUS  mandatory
      DESCRIPTION
              "When enabled, this event will cause a message to printed to the console serial port."
      ::= { promEventEntry 5 }



-- EVENT LOG

   promEventLogMgt OBJECT IDENTIFIER ::= { promEvents 2 }

-- EVENT LOG OBJECTS

   promLogTableMaxSize OBJECT-TYPE
      SYNTAX  INTEGER (0..2048)
      ACCESS  read-write
      STATUS  mandatory
      DESCRIPTION
              "The maximum number of entries in the log table.
              Changing this value causes the existing log to be
              truncated and rebuilt."
      ::= { promEventLogMgt 1 }

   promLogLastEntry OBJECT-TYPE
      SYNTAX  INTEGER (1..65535)
      ACCESS  read-only
      STATUS  mandatory
      DESCRIPTION
              "The log index of the last entry entered in the log."
      ::= { promEventLogMgt 2 }


   promLogWraps OBJECT-TYPE
      SYNTAX  Counter
      ACCESS  read-only
      STATUS  mandatory
      DESCRIPTION
              "The number of times that the last entry has wrapped from 65K back to 1."
      ::= { promEventLogMgt 3 }


-- EVENT LOG TABLE

   promEventLog OBJECT IDENTIFIER ::= { promEvents 3 }

   promEventLogTable OBJECT-TYPE
      SYNTAX  SEQUENCE OF PromEventLogEntry
      ACCESS  not-accessible
      STATUS  mandatory
      DESCRIPTION
              "The log table for the events in the event table that are enabled for the
               Log Action."
      ::= { promEventLog 1 }

   promEventLogEntry OBJECT-TYPE
      SYNTAX  PromEventLogEntry
      ACCESS  not-accessible
      STATUS  mandatory
      DESCRIPTION
              "An entry in the log indicates information associated with a particular
              event."
      INDEX   { promEventLogIndex }
      ::= { promEventLogTable 1 }


   PromEventLogEntry ::=
      SEQUENCE {
         promEventLogEventIndex
            INTEGER,
         promEventLogIndex
            INTEGER,
         promEventLogTime
            TimeTicks,
         promEventLogDescr
            DisplayString,
         promEventLogType
            EventCategory,
         promEventLogSeverity
            INTEGER,
         promEventLogDTM
            DisplayString,
         promEventLogResType
            ResourceType,
         promEventLogResID
            ResourceId,
         promEventLogResLeaf
            INTEGER,
         promEventLogValueType
            EventValueType,
         promEventLogValue
            OCTET STRING,
         promEventLogEpochTime
            INTEGER,
         promEventLogID
            INTEGER
      }


   promEventLogEventIndex OBJECT-TYPE
      SYNTAX  INTEGER (1..65535)
      ACCESS  read-only
      STATUS  mandatory
      DESCRIPTION
              "The index that uniquely identifies the event that caused this log entry."
      ::= { promEventLogEntry 1 }

   promEventLogIndex OBJECT-TYPE
      SYNTAX  INTEGER (1..65535)
      ACCESS  read-only
      STATUS  mandatory
      DESCRIPTION
              "An index that uniquely identifies this log entry."
      ::= { promEventLogEntry 2 }

   promEventLogTime OBJECT-TYPE
      SYNTAX  TimeTicks
      ACCESS  read-only
      STATUS  mandatory
      DESCRIPTION
              "The value of sysUpTime when this event was triggered."
      ::= { promEventLogEntry 3 }

   promEventLogDescr OBJECT-TYPE
      SYNTAX  DisplayString (SIZE(0..255))
      ACCESS  read-only
      STATUS  mandatory
      DESCRIPTION
              "The event log description."
      ::= { promEventLogEntry 4 }

   promEventLogType OBJECT-TYPE
      SYNTAX  EventCategory
      ACCESS  read-only
      STATUS  mandatory
      DESCRIPTION
              "The type of event that caused this log entry."
      ::= { promEventLogEntry 5 }

   promEventLogSeverity OBJECT-TYPE
      SYNTAX  INTEGER (0..100)
      ACCESS  read-only
      STATUS  mandatory
      DESCRIPTION
              "The severity associated with this event.  It is recommended that the
              severity be interpreted in the following manner:

               0-19: Normal
              20-39: Informational
              40-59: Warning
              60-79: Alarm
              80-99: Severe Error
                100: Failure."
      ::= { promEventLogEntry 6 }

   promEventLogDTM OBJECT-TYPE
      SYNTAX  DisplayString (SIZE (18))
      ACCESS  read-only
      STATUS  mandatory
      DESCRIPTION
              "The date and time when this log entry was made.  The format is yy-Mon-
              dd hh:mm:ss, time is in 24 hour time."
      ::= { promEventLogEntry 7 }

   promEventLogResType OBJECT-TYPE
      SYNTAX  ResourceType
      ACCESS  read-only
      STATUS  mandatory
      DESCRIPTION
              "The type of object (if provided) that triggered this event.  If not provided,
              the value is equal to 'Invalid Resource'."
      ::= { promEventLogEntry 8 }

   promEventLogResID OBJECT-TYPE
      SYNTAX  ResourceId
      ACCESS  read-only
      STATUS  mandatory
      DESCRIPTION
              "The instance of this resource (if provided - see promEventLogResType)
              that triggered this event."
      ::= { promEventLogEntry 9 }

   promEventLogResLeaf OBJECT-TYPE
      SYNTAX  INTEGER
      ACCESS  read-only
      STATUS  mandatory
      DESCRIPTION
              "A number corresponding to the attribute associated with this resource and
              this event entry.  It corresponds exactly to the leaf MIB number of the MIB
              that manages this resource.  For example, if a port's mode changed, the
              configuration event log entry would indicate the value of  5 which is the
              leaf index of the promPortMode within the promPortTable MIB table."
      ::= { promEventLogEntry 10 }


   promEventLogValueType OBJECT-TYPE
      SYNTAX  EventValueType
      ACCESS  read-only
      STATUS  mandatory
      DESCRIPTION
              "The data type associated with the log event value.  This object indicates
              how to interpret the data stored in the event log value:

              - none(1) indicates no value returned.
              - integer32(2) -  a 4 byte unsigned integer.
              - integer64(3) - an 8 byte unsigned integer.
              - displayString(4) - a null terminated (or up to 8 characters) string.
              - ipv4NetworkAddress(5) - a 4 byte IP version 4 network address.
              - ieee802MACAddress(6) - a 6 byte MAC Address.
              - timeticks(7) - sysUpTime type value (4 bytes)"
      ::= { promEventLogEntry 11 }


   promEventLogValue OBJECT-TYPE
      SYNTAX  OCTET STRING (SIZE(0..8))
      ACCESS  read-only
      STATUS  mandatory
      DESCRIPTION
              "The value associated with the event encoded in an octet string.  Refer to
              promEventLogValueType for how to interpret this value.
              The value encoded in this string is in Big Endian order."
      ::= { promEventLogEntry 12 }

   promEventLogEpochTime OBJECT-TYPE
      SYNTAX  INTEGER
      ACCESS  read-only
      STATUS  mandatory
      DESCRIPTION
              "The number of time ticks since the epoch when this
              event was logged. The interpretation of this value is
              as follows:

              struct DateTimeOvly {
               UNS32 year:6;
               UNS32 month:4;
               UNS32 day:5;
               UNS32 hour:5;
               UNS32 minute:6;
               UNS32 second:6;
               };

              The epoch is January 1, 1997, at 00:00:00.  A value of
              0 refers to this date and time.  "
      ::= { promEventLogEntry 13 }

      promEventLogID OBJECT-TYPE
         SYNTAX  INTEGER (1..65535)
         ACCESS  read-only
         STATUS  mandatory
         DESCRIPTION
              "A unique index that identifies the occurence of this
              event.  This ID can be correlated between traps, logs
              and the like."
      ::= { promEventLogEntry 14 }

-- SHUTDOWN EVENT LOG

   promShutdownLogMgt OBJECT IDENTIFIER ::= { promEvents 4 }

-- The most recent event log entries are stored in non-volatile memory.  In the event
-- of a system restart, it may be useful to look at the last few events that were
-- logged before the system last went down.  The Shutdown Log Table stores those
-- last events.
--
-- SHUTDOWN EVENT LOG OBJECTS

   promShutdownLogTableMaxSize OBJECT-TYPE
      SYNTAX  INTEGER (0..64)
      ACCESS  read-write
      STATUS  mandatory
      DESCRIPTION
              "The maximum number of entries in the non-volatile log table.  Changing
              the value of this object changes the maximum number of entries to be
              stored in Shutdown."
      ::= { promShutdownLogMgt 1 }

   promShutdownLogLastEntry OBJECT-TYPE
      SYNTAX  INTEGER (1..65535)
      ACCESS  read-only
      STATUS  mandatory
      DESCRIPTION
              "The ID of the last entry made to the shutdown log."
      ::= { promShutdownLogMgt 2 }

   promShutdownLogAcknowledged OBJECT-TYPE
      SYNTAX  INTEGER {
                 not-acknowledged(1),
                 acknowledged(2)
              }
      ACCESS  read-only
      STATUS  mandatory
      DESCRIPTION
              "This object is to set to acknowledged(2) the first time the Shutdown Log
              Table is accessed indicating that the Shutdown log has been read (at least
              once) since the system restarted."
      ::= { promShutdownLogMgt 3 }



-- SHUTDOWN LOG TABLE
--
-- The Shutdown Log Table is a copy of the log file stored in non-volatile memory.  It is copied
-- to dynamic memory (RAM) when the system is initialized and the non-volatile version
-- is re-initialized.

   promEventShutdownLog OBJECT IDENTIFIER ::= { promEvents 5 }

   promEventShutdownLogTable OBJECT-TYPE
      SYNTAX  SEQUENCE OF PromEventShutdownLogEntry
      ACCESS  not-accessible
      STATUS  mandatory
      DESCRIPTION
              "A table of the last events logged before the system restarted."
      ::= { promEventShutdownLog 1 }

   promEventShutdownLogEntry OBJECT-TYPE
      SYNTAX  PromEventShutdownLogEntry
      ACCESS  not-accessible
      STATUS  mandatory
      DESCRIPTION
              "A log entry stored in non-volatile memory."
      INDEX   { promEventShutdownLogIndex }
      ::= { promEventShutdownLogTable 1 }

   PromEventShutdownLogEntry ::=
      SEQUENCE {
         promEventShutdownLogEventIndex
            INTEGER,
         promEventShutdownLogIndex
            INTEGER,
         promEventShutdownLogTime
            TimeTicks,
         promEventShutdownLogDescr
            DisplayString,
         promEventShutdownLogType
            EventCategory,
         promEventShutdownLogSeverity
            INTEGER,
         promEventShutdownLogDTM
            DisplayString,
         promEventShutdownLogResType
            ResourceType,
         promEventShutdownLogResID
            ResourceId,
         promEventShutdownLogResLeaf
            INTEGER,
         promEventShutdownLogValueType
            EventValueType,
         promEventShutdownLogValue
            OCTET STRING,
         promEventShutdownLogEpochTime
            INTEGER,
         promEventShutdownLogID
            INTEGER

      }


   promEventShutdownLogEventIndex OBJECT-TYPE
      SYNTAX  INTEGER (1..65535)
      ACCESS  read-only
      STATUS  mandatory
      DESCRIPTION
              "The index that uniquely identifies the event that caused this ShutdownLog
              entry."
      ::= { promEventShutdownLogEntry 1 }

   promEventShutdownLogIndex OBJECT-TYPE
      SYNTAX  INTEGER (1..65535)
      ACCESS  read-only
      STATUS  mandatory
      DESCRIPTION
              "An index that uniquely identifies this ShutdownLog entry."
      ::= { promEventShutdownLogEntry 2 }

   promEventShutdownLogTime OBJECT-TYPE
      SYNTAX  TimeTicks
      ACCESS  read-only
      STATUS  mandatory
      DESCRIPTION
              "The value of sysUpTime when this event was triggered.  Note, 
              the value corresponds to the sysUpTime when the system was last 
              running (i.e. before it was shutdown.)"
      ::= { promEventShutdownLogEntry 3 }

   promEventShutdownLogDescr OBJECT-TYPE
      SYNTAX  DisplayString (SIZE(0..255))
      ACCESS  read-only
      STATUS  mandatory
      DESCRIPTION
              "The event ShutdownLog description."
      ::= { promEventShutdownLogEntry 4 }

   promEventShutdownLogType OBJECT-TYPE
      SYNTAX  EventCategory
      ACCESS  read-only
      STATUS  mandatory
      DESCRIPTION
              "The type of event that caused this ShutdownLog entry."
      ::= { promEventShutdownLogEntry 5 }

   promEventShutdownLogSeverity OBJECT-TYPE
      SYNTAX  INTEGER (0..100)
      ACCESS  read-only
      STATUS  mandatory
      DESCRIPTION
              "The severity associated with this event.  It is recommended that the
              severity be interpreted in the following manner:

               0-19: Normal
              20-39: Informational
              40-59: Warning
              60-79: Alarm
              80-99: Severe Error
                100: Failure."
      ::= { promEventShutdownLogEntry 6 }

   promEventShutdownLogDTM OBJECT-TYPE
      SYNTAX  DisplayString (SIZE (18))
      ACCESS  read-only
      STATUS  mandatory
      DESCRIPTION
              "The date and time when this ShutdownLog entry was made.  The format
              is yy-Mon-dd hh:mm:ss, time is in 24 hour time."
      ::= { promEventShutdownLogEntry 7 }

   promEventShutdownLogResType OBJECT-TYPE
      SYNTAX  ResourceType
      ACCESS  read-only
      STATUS  mandatory
      DESCRIPTION
              "The type of object (if provided) that triggered this event.  If not provided,
              the value is invalid."
      ::= { promEventShutdownLogEntry 8 }

   promEventShutdownLogResID OBJECT-TYPE

      SYNTAX  ResourceId
      ACCESS  read-only
      STATUS  mandatory
      DESCRIPTION
              "The instance of this resource (if provided) that triggered this event."
      ::= { promEventShutdownLogEntry 9 }

   promEventShutdownLogResLeaf OBJECT-TYPE

      SYNTAX  INTEGER
      ACCESS  read-only
      STATUS  mandatory
      DESCRIPTION
              "To be provided."
      ::= { promEventShutdownLogEntry 10 }

   promEventShutdownLogValueType OBJECT-TYPE
      SYNTAX  EventValueType
      ACCESS  read-only
      STATUS  mandatory
      DESCRIPTION
              "The data type associated with the ShutdownLog event value.  This object
              indicates how to interpret the data stored in the event ShutdownLog
              value."
      ::= { promEventShutdownLogEntry 11 }


   promEventShutdownLogValue OBJECT-TYPE
      SYNTAX  OCTET STRING (SIZE(0..8))
      ACCESS  read-only
      STATUS  mandatory
      DESCRIPTION
              "The value associated with the event encoded in an octet string. "
      ::= { promEventShutdownLogEntry 12 }

   promEventShutdownLogEpochTime OBJECT-TYPE
      SYNTAX  INTEGER
      ACCESS  read-only
      STATUS  mandatory
      DESCRIPTION
              "The number of time ticks since the epoch when this
              event was logged. The interpretation of this value is
              as follows:

              struct DateTimeOvly {
               UNS32 year:6;
               UNS32 month:4;
               UNS32 day:5;
               UNS32 hour:5;
               UNS32 minute:6;
               UNS32 second:6;
               };

              The epoch is January 1, 1997, at 00:00:00.  A value of
              0 refers to this date and time.  "
      ::= { promEventShutdownLogEntry 13 }

    promEventShutdownLogID OBJECT-TYPE
         SYNTAX  INTEGER (1..65535)
         ACCESS  read-only
         STATUS  mandatory
         DESCRIPTION
              "A unique index that identifies the occurence of this
              event.  This ID can be correlated between traps, logs
              and the like."
      ::= { promEventShutdownLogEntry 14 }

-- EVENT TRAP DATA

   promEventTrapMgmt OBJECT IDENTIFIER ::= { promEvents 6 }

   promEventTrapEventIndex OBJECT-TYPE
      SYNTAX  INTEGER (1..65535)
      ACCESS  read-only
      STATUS  mandatory
      DESCRIPTION
              "The index that uniquely identifies the event that caused this trap."
      ::= { promEventTrapMgmt 1 }

   promEventTrapTime OBJECT-TYPE
      SYNTAX  TimeTicks
      ACCESS  read-only
      STATUS  mandatory
      DESCRIPTION
              "The value of sysUpTime when this event was triggered."
      ::= { promEventTrapMgmt 2 }

   promEventTrapDescr OBJECT-TYPE
      SYNTAX  DisplayString (SIZE(0..255))
      ACCESS  read-only
      STATUS  mandatory
      DESCRIPTION
              "The event log description."
      ::= { promEventTrapMgmt 3 }

   promEventTrapType OBJECT-TYPE
      SYNTAX  EventCategory
      ACCESS  read-only
      STATUS  mandatory
      DESCRIPTION
              "The type of event that caused this trap."
      ::= { promEventTrapMgmt 4 }

   promEventTrapSeverity OBJECT-TYPE
      SYNTAX  INTEGER (0..100)
      ACCESS  read-only
      STATUS  mandatory
      DESCRIPTION
              "The severity associated with this event.  It is recommended that the
              severity be interpreted in the following manner:

               0-19: Normal
              20-39: Informational
              40-59: Warning
              60-79: Alarm
              80-99: Severe Error
                100: Failure."
      ::= { promEventTrapMgmt 5 }

   promEventTrapDTM OBJECT-TYPE
      SYNTAX  DisplayString (SIZE (18))
      ACCESS  read-only
      STATUS  mandatory
      DESCRIPTION
              "The date and time when this trap was sent.  The format is yy-Mon-
              dd hh:mm:ss, time is in 24 hour time."
      ::= { promEventTrapMgmt 6 }

   promEventTrapResType OBJECT-TYPE
      SYNTAX  ResourceType
      ACCESS  read-only
      STATUS  mandatory
      DESCRIPTION
              "The type of object (if provided) that triggered this event.  If not provided,
              the value is equal to 'Invalid Resource'."
      ::= { promEventTrapMgmt 7 }

   promEventTrapResID OBJECT-TYPE
      SYNTAX  ResourceId
      ACCESS  read-only
      STATUS  mandatory
      DESCRIPTION
              "The instance of this resource (if provided - see promEventTrapResType)
              that triggered this event."
      ::= { promEventTrapMgmt 8 }

   promEventTrapResLeaf OBJECT-TYPE
      SYNTAX  INTEGER
      ACCESS  read-only
      STATUS  mandatory
      DESCRIPTION
              "A number corresponding to the attribute associated with this resource and
              this event entry.  It corresponds exactly to the leaf MIB number of the MIB
              that manages this resource.  For example, if a port's mode changed, the
              configuration event log entry would indicate the value of  5 which is the
              leaf index of the promPortMode within the promPortTable MIB table."
      ::= { promEventTrapMgmt 9 }


   promEventTrapValueType OBJECT-TYPE
      SYNTAX  EventValueType
      ACCESS  read-only
      STATUS  mandatory
      DESCRIPTION
              "The data type associated with the trap event value.  This object indicates
              how to interpret the data stored in the event trap value:

              - none(1) indicates no value returned.
              - integer32(2) -  a 4 byte unsigned integer.
              - integer64(3) - an 8 byte unsigned integer.
              - displayString(4) - a null terminated (or up to 8 characters) string.
              - ipv4NetworkAddress(5) - a 4 byte IP version 4 network address.
              - ieee802MACAddress(6) - a 6 byte MAC Address.
              - timeticks(7) - sysUpTime type value (4 bytes)"
      ::= { promEventTrapMgmt 10 }


   promEventTrapValue OBJECT-TYPE
      SYNTAX  OCTET STRING (SIZE(0..8))
      ACCESS  read-only
      STATUS  mandatory
      DESCRIPTION
              "The value associated with the event encoded in an octet string.  Refer to
              promEventTrapValueType for how to interpret this value.
              The value encoded in this string is in Big Endian order."
      ::= { promEventTrapMgmt 11 }

   promEventTrapEpochTime OBJECT-TYPE
      SYNTAX  INTEGER
      ACCESS  read-only
      STATUS  mandatory
      DESCRIPTION
              "The number of time ticks since the epoch when this
              event was logged. The interpretation of this value is
              as follows:

              struct DateTimeOvly {
               UNS32 year:6;
               UNS32 month:4;
               UNS32 day:5;
               UNS32 hour:5;
               UNS32 minute:6;
               UNS32 second:6;
               };

              The epoch is January 1, 1997, at 00:00:00.  A value of
              0 refers to this date and time.  "
      ::= { promEventTrapMgmt 12 }

      promEventTrapID OBJECT-TYPE
         SYNTAX  INTEGER (1..65535)
         ACCESS  read-only
         STATUS  mandatory
         DESCRIPTION
              "A unique index that identifies the occurence of this
              event.  This ID can be correlated between traps, logs
              and the like."
      ::= { promEventTrapMgmt 13 }


-- ALARM MANAGEMENT

   promAlarmMgt OBJECT IDENTIFIER ::= { prominet  11 }

-- ALARM GENERAL

   promAlarmGeneral OBJECT IDENTIFIER ::= { promAlarmMgt 1 }

-- Alarm Table
--
-- The alarm table contains events that are considered "alarmable".  This table is a handy place
-- to quickly check the "health" of the system.  Any non-normal indication in the system will be
-- indicated in this table.

   promAlarmGeneralActiveEntries OBJECT-TYPE
      SYNTAX  Gauge
      ACCESS  read-only
      STATUS  mandatory
      DESCRIPTION
              "The total number of alarm entries in the triggered state currently in the
              alarm table."
      ::= { promAlarmGeneral  1 }

   promAlarmGeneralTimeStamp OBJECT-TYPE
      SYNTAX  TimeTicks
      ACCESS  read-only
      STATUS  mandatory
      DESCRIPTION
              "The value of sysUpTime when any alarm state last changed (either
              triggering a new alarm or re-arming an old one)."
      ::= { promAlarmGeneral  2 }



-- ALARM TABLE

   promAlarms OBJECT IDENTIFIER ::= { promAlarmMgt 2 }

-- ACTIVE ALARM TABLE

   promActiveAlarmTable OBJECT-TYPE
      SYNTAX  SEQUENCE OF PromActiveAlarmEntry
      ACCESS  not-accessible
      STATUS  mandatory
      DESCRIPTION
              "A table of all alarms in the triggered state."
      ::= { promAlarms 2 }

   promActiveAlarmEntry OBJECT-TYPE
      SYNTAX  PromActiveAlarmEntry
      ACCESS  not-accessible
      STATUS  mandatory
      DESCRIPTION
              "An alarm in the triggered state."
      INDEX   { promActiveAlarmIndex }
      ::= { promActiveAlarmTable 1 }

   PromActiveAlarmEntry ::=
      SEQUENCE {
         promActiveAlarmIndex
            INTEGER,
         promActiveAlarmName
            DisplayString,
         promActiveAlarmValueHigh
            INTEGER,
         promActiveAlarmValueLow
            INTEGER,
         promActiveAlarmVariable
            OBJECT IDENTIFIER,
         promActiveAlarmResType
            ResourceType,
         promActiveAlarmResID
            ResourceId,
         promActiveAlarmLeaf
            INTEGER,
         promActiveAlarmOwner
            DisplayString
      }


   promActiveAlarmIndex OBJECT-TYPE
      SYNTAX  INTEGER
      ACCESS  read-only
      STATUS  mandatory
      DESCRIPTION
              "The unique index that identifies this alarm."
      ::= { promActiveAlarmEntry  1 }

   promActiveAlarmName OBJECT-TYPE
      SYNTAX  DisplayString (SIZE(0..31))
      ACCESS  read-only
      STATUS  mandatory
      DESCRIPTION
              "The name of this alarm."
      ::= { promActiveAlarmEntry  2 }

   promActiveAlarmValueHigh OBJECT-TYPE
      SYNTAX  INTEGER
      ACCESS  read-only
      STATUS  mandatory
      DESCRIPTION
              "The high order 32 bits of the value that triggered this alarm."
      ::= { promActiveAlarmEntry 3 }

   promActiveAlarmValueLow OBJECT-TYPE
      SYNTAX  INTEGER
      ACCESS  read-only
      STATUS  mandatory
      DESCRIPTION
              "The low order 32 bits of the value that triggered this alarm."
      ::= { promActiveAlarmEntry 4 }

   promActiveAlarmVariable OBJECT-TYPE
      SYNTAX  OBJECT IDENTIFIER
      ACCESS  read-only
      STATUS  mandatory
      DESCRIPTION
              "The OID of the alarm variable if this is a user-created alarm (null
              otherwise)."
      ::= { promActiveAlarmEntry 5 }

   promActiveAlarmResType OBJECT-TYPE
      SYNTAX  ResourceType
      ACCESS  read-only
      STATUS  mandatory
      DESCRIPTION
              "The resource type of this alarm if this is an internally created alarm."
      ::= { promActiveAlarmEntry 6 }

   promActiveAlarmResID OBJECT-TYPE
      SYNTAX  ResourceId
      ACCESS  read-only
      STATUS  mandatory
      DESCRIPTION
              "The resource identifier associated with this alarm if this is an internally 
               created alarm."
      ::= { promActiveAlarmEntry 7 }

   promActiveAlarmLeaf OBJECT-TYPE
      SYNTAX  INTEGER
      ACCESS  read-only
      STATUS  mandatory
      DESCRIPTION
              "The leaf index of the MIB table used to manage this resource that is associated 
              with this alarm, if this is an internally created alarm.  For example,  if this 
              alarm was created to monitor a port's status, then the value of this object will 
              be 6, corresponding to the leaf index of the promPortStatus object."
      ::= { promActiveAlarmEntry 8 }


   promActiveAlarmOwner OBJECT-TYPE
      SYNTAX  DisplayString (SIZE(0..255))
      ACCESS  read-only
      STATUS  mandatory
      DESCRIPTION
              "This is the owner of the alarm."
      ::= { promActiveAlarmEntry 9 }


-- TRAP

   promSnmpTraps OBJECT IDENTIFIER ::= { prominet  13 }

   promSystemTrap TRAP-TYPE
      ENTERPRISE  promSnmpTraps
      VARIABLES   { promEventTrapEventIndex,
                     promEventTrapTime,
                     promEventTrapDescr,
                     promEventTrapType,
                     promEventTrapSeverity,
                     promEventTrapDTM,
                     promEventTrapResType,
                     promEventTrapResID,
                     promEventTrapResLeaf,
                     promEventTrapValueType,
                     promEventTrapValue,
                     promEventTrapEpochTime,
                     promEventTrapID }

      DESCRIPTION
               "A promSystemTrap is sent by the agent when a system
               event is triggered.  These events are usually triggered
               when the software encounters an unexpected situation,
               e.g. a hardware failure or a software bug."
      ::= 2

   promConfigurationTrap TRAP-TYPE
      ENTERPRISE  promSnmpTraps
      VARIABLES   { promEventTrapEventIndex,
                     promEventTrapTime,
                     promEventTrapDescr,
                     promEventTrapType,
                     promEventTrapSeverity,
                     promEventTrapDTM,
                     promEventTrapResType,
                     promEventTrapResID,
                     promEventTrapResLeaf,
                     promEventTrapValueType,
                     promEventTrapValue,
                     promEventTrapEpochTime,
                     promEventTrapID }
      DESCRIPTION
               "A promConfigurationTrap is sent by the agent when the
               configuration event is triggered.  These events are
               triggered when a configuration change is made."
       ::= 3

   promTemperatureTrap TRAP-TYPE
      ENTERPRISE  promSnmpTraps
      VARIABLES   { promEventTrapEventIndex,
                     promEventTrapTime,
                     promEventTrapDescr,
                     promEventTrapType,
                     promEventTrapSeverity,
                     promEventTrapDTM,
                     promEventTrapResType,
                     promEventTrapResID,
                     promEventTrapResLeaf,
                     promEventTrapValueType,
                     promEventTrapValue,
                     promEventTrapEpochTime,
                     promEventTrapID }
      DESCRIPTION
               "A promTemperatureTrap is sent by the agent when the
               temperature event is triggered.  This event is
               triggered when a temperature probe detects the
               temperature crossing a threshold."
      ::= 4

   promResourceTrap TRAP-TYPE
      ENTERPRISE  promSnmpTraps
      VARIABLES   { promEventTrapEventIndex,
                     promEventTrapTime,
                     promEventTrapDescr,
                     promEventTrapType,
                     promEventTrapSeverity,
                     promEventTrapDTM,
                     promEventTrapResType,
                     promEventTrapResID,
                     promEventTrapResLeaf,
                     promEventTrapValueType,
                     promEventTrapValue,
                     promEventTrapEpochTime,
                     promEventTrapID }
      DESCRIPTION
               "A promResourceTrap is sent by the agent when the
               resource event is triggered.  The resource event is
               triggered when a resource is added or removed from the
               system."
      ::= 5

   promFanTrap TRAP-TYPE
      ENTERPRISE  promSnmpTraps
      VARIABLES   { promEventTrapEventIndex,
                     promEventTrapTime,
                     promEventTrapDescr,
                     promEventTrapType,
                     promEventTrapSeverity,
                     promEventTrapDTM,
                     promEventTrapResType,
                     promEventTrapResID,
                     promEventTrapResLeaf,
                     promEventTrapValueType,
                     promEventTrapValue,
                     promEventTrapEpochTime,
                     promEventTrapID }
      DESCRIPTION
               "A promFanTrap is sent by the agent when the
               fan status event is triggered.  The fan status event
               is triggered when a fan has a change in its status."
      ::= 6
      
   promPowerTrap TRAP-TYPE
      ENTERPRISE  promSnmpTraps
      VARIABLES   { promEventTrapEventIndex,
                     promEventTrapTime,
                     promEventTrapDescr,
                     promEventTrapType,
                     promEventTrapSeverity,
                     promEventTrapDTM,
                     promEventTrapResType,
                     promEventTrapResID,
                     promEventTrapResLeaf,
                     promEventTrapValueType,
                     promEventTrapValue,
                     promEventTrapEpochTime,
                     promEventTrapID }
      DESCRIPTION
               "A promPowerTrap is sent by the agent when the power
               event is triggered.  These events are triggered when a
               power supply changes status."
      ::= 9

-- VTP SNOOPING 

   promVtpSnooping OBJECT IDENTIFIER ::= { prominet 14 }

-- VLAN SNOOPING SWITCH 
-- General switch-wide objects

   promVtpSnoopingSwitch OBJECT IDENTIFIER ::= { promVtpSnooping 1 }

   promVtpSnoopingState OBJECT-TYPE
      SYNTAX  INTEGER {
                 enable(1),
                 disable(2)
              }
      ACCESS  read-write
      STATUS  mandatory
      DESCRIPTION
              "When this object is set to enable(1), the switch attempts to
              learn VLANs from a major networking equipment vendor on switch
              ports that have their VTP Snooping parameter set to enable(1).
              trunking mode is IEEE 802.1Q Format or Multi-level Format.

              The factory default value for this object is disable(2)."
      ::= { promVtpSnoopingSwitch 1 }

   promVtpSnoopingDomainName OBJECT-TYPE
      SYNTAX  DisplayString (SIZE(0..32))
      ACCESS  read-write
      STATUS  mandatory
      DESCRIPTION
              "The VTP Snooping Domain Name of the switch.  A switch may
              only belong to one domain."
      ::= { promVtpSnoopingSwitch 2 }

   promVtpSnoopingUpdaterId OBJECT-TYPE
      SYNTAX  NetworkAddress
      ACCESS  read-only
      STATUS  mandatory
      DESCRIPTION
              "The IP address of the switch from which the VTP Snooping 
              configuration was learned."
      ::= { promVtpSnoopingSwitch 3 }

   promVtpSnoopingUpdateTimeStamp OBJECT-TYPE
      SYNTAX  DisplayString (SIZE(0..12))
      ACCESS  read-only
      STATUS  mandatory
      DESCRIPTION
              "The time at which the VTP configuration changed
              on the initiating switch."
      ::= { promVtpSnoopingSwitch 4 }

   promVtpSnoopingConfigRevNum OBJECT-TYPE
      SYNTAX  INTEGER
      ACCESS  read-only
      STATUS  mandatory
      DESCRIPTION
               "VTP Configuration Revision Number on
               the switch that initiated the VTP message exchange."
      ::= { promVtpSnoopingSwitch 5 }
   

-- TCP Port config

   promPortMgmt OBJECT IDENTIFIER ::= { prominet 15 }

   promTCPPortMgmt OBJECT IDENTIFIER ::= { promPortMgmt 1 }

   promTCPPortHTTP OBJECT-TYPE
      SYNTAX  INTEGER (80 | 9000..65535)
      ACCESS  read-write
      STATUS  mandatory
      DESCRIPTION
              "The HTTP port of the switch web server. 
	      It allows the user to modify the HTTP port
	      value to be 80 (default) or between 9000 
	      and 65535."
      ::= { promTCPPortMgmt 1 }

   promTCPPortTelnet OBJECT-TYPE
      SYNTAX  INTEGER (23 | 9000..65535)
      ACCESS  read-write
      STATUS  mandatory
      DESCRIPTION
              "The Telnet port of the switch. It allows 
	      the user to modify the Telnet port value 
	      to be 23 (default) or between 9000 and 65535."
      ::= { promTCPPortMgmt 2 }

END
