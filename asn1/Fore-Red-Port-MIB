-- 
-- Copyright 1999 by Fore Systems, Inc. 
-- Converted to SMIv2 rfc 2578,2579,2580 - STD 58
--
Fore-Red-Port-MIB DEFINITIONS ::= BEGIN

IMPORTS
	Integer32, MODULE-IDENTITY,
	OBJECT-TYPE                  FROM    SNMPv2-SMI
	asx			     FROM    Fore-Common-MIB;

redPortConfModule    MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION
           "This module specifics Series D Portcard Redundancy table
	    mib objects."
    ::= { asx 17 }

------------------------------------------------------------------------

redPortConfTable OBJECT-TYPE
 	SYNTAX  SEQUENCE OF RedPortConfEntry
 	MAX-ACCESS	not-accessible
 	STATUS	current
 	DESCRIPTION
		"A table of SONET APS Port configuration Information"
 	::= { redPortConfModule 1 }

redPortConfEntry OBJECT-TYPE
 	SYNTAX	RedPortConfEntry
 	MAX-ACCESS	not-accessible
 	STATUS	current
 	DESCRIPTION
 		"A table entry containing SONET APS configuration
 		 information for each APS port"
	INDEX	{redPortBoard, redPortModule, redPortPort}
 	::= {redPortConfTable 1}

RedPortConfEntry ::=
 	SEQUENCE {
		redPortBoard 			Integer32,
		redPortModule 			Integer32,
		redPortPort 			Integer32,
		redPortPendingAdminMode 	INTEGER,
		redPortPendingCommitState 	INTEGER,
		redPortAdminMode 		INTEGER,
		redPortOperState		INTEGER
 	}

redPortBoard 	OBJECT-TYPE
 	SYNTAX	Integer32
 	MAX-ACCESS	read-only
 	STATUS	current
 	DESCRIPTION
 		"The index of this port's switch board"
 	::= {redPortConfEntry 1}

redPortModule	OBJECT-TYPE
 	SYNTAX	Integer32
 	MAX-ACCESS	read-only
 	STATUS	current
 	DESCRIPTION
 		"The network module of this port"
 	::= {redPortConfEntry 2}

redPortPort	OBJECT-TYPE
 	SYNTAX	Integer32
 	MAX-ACCESS	read-only
 	STATUS	current
 	DESCRIPTION
 		"The number of this port"
 	::= {redPortConfEntry 3}

redPortPendingAdminMode  OBJECT-TYPE
 	SYNTAX INTEGER {
 		working (1),
 		protection (2),
 		unprotected(3),
		none(4)
 	}
 	MAX-ACCESS	read-write
 	STATUS	current
 	DESCRIPTION
 		"The pending admin mode for this port"
 	::= {redPortConfEntry 4}

redPortPendingCommitState OBJECT-TYPE
 	SYNTAX  INTEGER {
 		no (1),
 		yes (2)
 	}
 	MAX-ACCESS	read-only
 	STATUS	current
 	DESCRIPTION
 		"This variable indicates if the commit state is
 		 pending for this particular port"
 	::= {redPortConfEntry 5}

redPortAdminMode OBJECT-TYPE
 	SYNTAX  INTEGER {
		working(1),
		protection(2),
		unprotected(3)
 	}
 	MAX-ACCESS	read-only
 	STATUS	current
 	DESCRIPTION
		"The admin mode for the port"
 	::= {redPortConfEntry 6}

redPortOperState 	OBJECT-TYPE
 	SYNTAX	INTEGER {
		active(1),
		standby(2),
		unprotected(3),
		loopbackon(4),
		loopbackoff(5)
	}
 	MAX-ACCESS	read-only
 	STATUS	current
 	DESCRIPTION
 		"The Oper state of this port"
 	::= {redPortConfEntry 7}

redPortCommit 	OBJECT-TYPE
	SYNTAX 	INTEGER {
		    commit(1) 
		}
      	MAX-ACCESS      read-write
      	STATUS      current
      	DESCRIPTION
           		"command to commit a port  configuration

           		Note this object is write-only and reading it will
           		result in implementation-specific results."
      	::= { redPortConfModule 2 }

END
