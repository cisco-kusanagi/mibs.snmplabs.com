BAS-MGR-TRACE-MIB DEFINITIONS ::= BEGIN

IMPORTS
    MODULE-IDENTITY, Integer32, OBJECT-TYPE     FROM SNMPv2-SMI
    basTrace, BasChassisId, BasSlotId,
    BasInterfaceId, BasLogicalPortId            FROM BAS-MIB;

basMgrTraceLog MODULE-IDENTITY
    LAST-UPDATED "9903141120Z"
    ORGANIZATION "Broadband Access Systems, Inc."
    CONTACT-INFO
        " Tech Support
          Broadband Access Systems, Inc.
          201 Forest Street
          Marlborough, MA 01752
          USA

          508-485-8200
          support@basystems.com"
    DESCRIPTION
        "The MIB module defining Trace Logging for Chassis manager
        cards."
    ::= { basTrace 2 }

--*****************************************************************************
--* basMgrTraceLogTable
--*****************************************************************************

basMgrTraceLogTable OBJECT-TYPE
    SYNTAX      SEQUENCE OF BasMgrTraceLogEntry
    MAX-ACCESS  not-accessible
    STATUS      current
    DESCRIPTION
        ""
    ::= { basMgrTraceLog 1 }

basMgrTraceLogEntry OBJECT-TYPE
    SYNTAX      BasMgrTraceLogEntry
    MAX-ACCESS  not-accessible
    STATUS      current
    DESCRIPTION
      ""
    INDEX       { basMgrTraceLogChassis, basMgrTraceLogSlot,
                  basMgrTraceLogIf, basMgrTraceLogLPort,
                  basMgrTraceLogComponentId }
    ::= {basMgrTraceLogTable 1 }

BasMgrTraceLogEntry ::= 
    SEQUENCE {
        basMgrTraceLogChassis      BasChassisId,
        basMgrTraceLogSlot         BasSlotId,
        basMgrTraceLogIf           BasInterfaceId,
        basMgrTraceLogLPort        BasLogicalPortId,
        basMgrTraceLogComponentId  INTEGER,
        basMgrTraceLogLevel        INTEGER
    }

basMgrTraceLogChassis OBJECT-TYPE
    SYNTAX      BasChassisId
    MAX-ACCESS  not-accessible
    STATUS      current
    DESCRIPTION
        "The BAS Chassis ID of the card."
    ::= { basMgrTraceLogEntry 1 }

basMgrTraceLogSlot OBJECT-TYPE
    SYNTAX      BasSlotId
    MAX-ACCESS  not-accessible
    STATUS      current
    DESCRIPTION
        "The BAS Slot ID of the card."
    ::= { basMgrTraceLogEntry 2 }

basMgrTraceLogIf OBJECT-TYPE
    SYNTAX      BasInterfaceId
    MAX-ACCESS  not-accessible
    STATUS      current
    DESCRIPTION
        "The BAS interface ID of the card."
    ::= { basMgrTraceLogEntry 3 }

basMgrTraceLogLPort OBJECT-TYPE
    SYNTAX      BasLogicalPortId
    MAX-ACCESS  not-accessible
    STATUS      current
    DESCRIPTION
        "The BAS logical port ID of the card."
    ::= { basMgrTraceLogEntry 4 }

basMgrTraceLogComponentId OBJECT-TYPE
    SYNTAX      INTEGER {
                        cfm(1),
                        ma(2),
                        la(3),
                        rm(4),
                        ldp(5),
                        cmts(6),
                        cmtsMac(7),
                        cmtsBpi(8),
                        snmp(9),
                        agentx(10),
                        dhcpRelay(11),
                        mal(12),
                        javaRmiServ(13),
                        cfgRmiServ(14),
                        provRmiServ(15),
                        faultsRmiServ(16),
                        ldap(17),
                        jni(18),
                        ca(19),
                        rbp(20),
                        crp(21),
                        ftd(22),
                        rip(23),
                        ospf(24),
                        ip(25),
                        udp(26),
                        tcp(27),
                        sw(28),
                        icmp(29),
                        dhcpServ(30),
                        timeServ(31),
                        syslogServ(32),
                        tftpServ(33),
                        cli(34),
                        log(35),
                        tracelogd(36),
                        cmts-generic(37),
                        cmts-0(38),       
                        cmts-1(39),
                        cmts-2(40),
                        cmts-3(41),
                        cmts-4(42),
                        cmts-5(43),
                        cmts-6(44),
                        cmts-7(45),
                        cmts-8(46),
                        cmts-9(47),
                        cmts-10(48),
                        cmts-11(49),
                        cmts-12(50),
                        cmts-13(51),
                        cmts-14(52),
                        cmts-15(53),
                        cmts-docsis-err(54),
                        idle(55),
                        rcv(56),
                        cmts-17(57),
                        rip-debug(58),
                        rip-console(59),
                        routing-trace(60),
                        ospf-debug(61),
                        ip-debug(62),
                        bas-rip-rx(63),
                        bas-rip-tx(64),
                        bas-rip-task(65),
                        bas-rip-timer(66),
                        bas-rip-route(67),
                        bas-rip-gen(68),
                        bas-rip-mem(69),
                        bas-rip-state(70),
                        last-app(71)
                        }
    MAX-ACCESS  not-accessible
    STATUS      current
    DESCRIPTION
        "The software component ID."
    ::= { basMgrTraceLogEntry 5 }

basMgrTraceLogLevel OBJECT-TYPE
    SYNTAX      INTEGER {
			init(1),
                        critical(2),
                        warning(3),
                        info(4)
                }
    MAX-ACCESS  read-write
    STATUS      current
    DESCRIPTION
        "The software component's trace logging severity level."
    ::= { basMgrTraceLogEntry 6 }

END
