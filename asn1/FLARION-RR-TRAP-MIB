-- $Id: FLARION-RR-TRAP-MIB.txt,v 1.4.2.1 2004/11/11 22:40:01 phsu Exp $


FLARION-RR-TRAP-MIB DEFINITIONS ::= BEGIN

IMPORTS
        NOTIFICATION-TYPE
                FROM SNMPv2-SMI
       
        rrTrapSpecific, rrTimeStamp, rrSeqNum, rrSeverity,
        rrMoType, rrMoId, rrAddtlInfo
                FROM FLARION-TRAP-MIB

        flaTimeStamp, flaSeqNum, flaSeverity, flaMoType,
        flaMoId, flaAddtlInfo, flarionTraps
                FROM FLARION-TRAP-MIB;


rrTrap          OBJECT IDENTIFIER ::= { flarionTraps 3 }
rrTrapPrefix    OBJECT IDENTIFIER ::= { rrTrap 0 }


lnaOperStatusUp   NOTIFICATION-TYPE
    OBJECTS     { flaTimeStamp, flaSeqNum, flaSeverity,
                  flaMoType, flaMoId, flaAddtlInfo }
    STATUS      current
    DESCRIPTION "LNA operational status is up."
    ::= { rrTrapPrefix 1 }

lnaOperStatusDown   NOTIFICATION-TYPE
    OBJECTS     { flaTimeStamp, flaSeqNum, flaSeverity,
                  flaMoType, flaMoId, flaAddtlInfo }
    STATUS      current
    DESCRIPTION "LNA operational status is down."
    ::= { rrTrapPrefix 2 }

lnaDiversityBreakerOk   NOTIFICATION-TYPE
    OBJECTS     { flaTimeStamp, flaSeqNum, flaSeverity,
                  flaMoType, flaMoId, flaAddtlInfo }
    STATUS      current
    DESCRIPTION "LNA diversity breaker is not tripped."
    ::= { rrTrapPrefix 3 }

lnaDiversityBreakerTripped  NOTIFICATION-TYPE
    OBJECTS     { flaTimeStamp, flaSeqNum, flaSeverity,
                  flaMoType, flaMoId, flaAddtlInfo }
    STATUS      current
    DESCRIPTION "LNA diversity breaker tripped."
    ::= { rrTrapPrefix 4 }

paShelfFanSpeedNormal   NOTIFICATION-TYPE
    OBJECTS     { flaTimeStamp, flaSeqNum, flaSeverity,
                  flaMoType, flaMoId, flaAddtlInfo }
    STATUS      current
    DESCRIPTION "PA shelf fan speed is within normal operating range."
    ::= { rrTrapPrefix 5 }

paShelfFanSpeedFault    NOTIFICATION-TYPE
    OBJECTS     { flaTimeStamp, flaSeqNum, flaSeverity,
                  flaMoType, flaMoId, flaAddtlInfo }
    STATUS      current
    DESCRIPTION "PA shelf fan speed is not within normal operating range."
    ::= { rrTrapPrefix 6 }

paShelfFanTempNormal    NOTIFICATION-TYPE
    OBJECTS     { flaTimeStamp, flaSeqNum, flaSeverity,
                  flaMoType, flaMoId, flaAddtlInfo }
    STATUS      current
    DESCRIPTION "PA shelf fan temperature is within normal operating range."
    ::= { rrTrapPrefix 7 }

paShelfFanTempFault NOTIFICATION-TYPE
    OBJECTS     { flaTimeStamp, flaSeqNum, flaSeverity,
                  flaMoType, flaMoId, flaAddtlInfo }
    STATUS      current
    DESCRIPTION "PA shelf fan temperature is not within normal operating range."
    ::= { rrTrapPrefix 8 }

paShelfBreakerOk    NOTIFICATION-TYPE
    OBJECTS     { flaTimeStamp, flaSeqNum, flaSeverity,
                  flaMoType, flaMoId, flaAddtlInfo }
    STATUS      current
    DESCRIPTION "PA shelf breaker is not tripped."
    ::= { rrTrapPrefix 9 }

paShelfBreakerTripped   NOTIFICATION-TYPE
    OBJECTS     { flaTimeStamp, flaSeqNum, flaSeverity,
                  flaMoType, flaMoId, flaAddtlInfo }
    STATUS      current
    DESCRIPTION "PA shelf breaker tripped."
    ::= { rrTrapPrefix 10 }

paOperStatusUp  NOTIFICATION-TYPE
    OBJECTS     { flaTimeStamp, flaSeqNum, flaSeverity,
                  flaMoType, flaMoId, flaAddtlInfo }
    STATUS      deprecated
    DESCRIPTION "PA operational status is up."
    ::= { rrTrapPrefix 11 }

paOperStatusDown    NOTIFICATION-TYPE
    OBJECTS     { flaTimeStamp, flaSeqNum, flaSeverity,
                  flaMoType, flaMoId, flaAddtlInfo }
    STATUS      deprecated
    DESCRIPTION "PA operational status is down."
    ::= { rrTrapPrefix 12 }

paTempNormal    NOTIFICATION-TYPE
    OBJECTS     { flaTimeStamp, flaSeqNum, flaSeverity,
                  flaMoType, flaMoId, flaAddtlInfo }
    STATUS      current
    DESCRIPTION "PA temperature is within normal operating range."
    ::= { rrTrapPrefix 13 }

paTempHigh      NOTIFICATION-TYPE
    OBJECTS     { flaTimeStamp, flaSeqNum, flaSeverity,
                  flaMoType, flaMoId, flaAddtlInfo }
    STATUS      current
    DESCRIPTION "PA temperature is high."
    ::= { rrTrapPrefix 14 }

paTempSevere    NOTIFICATION-TYPE
    OBJECTS     { flaTimeStamp, flaSeqNum, flaSeverity,
                  flaMoType, flaMoId, flaAddtlInfo }
    STATUS      current
    DESCRIPTION "PA temperature is severe."
    ::= { rrTrapPrefix 15 }

paTempCritical  NOTIFICATION-TYPE
    OBJECTS     { flaTimeStamp, flaSeqNum, flaSeverity,
                  flaMoType, flaMoId, flaAddtlInfo }
    STATUS      current
    DESCRIPTION "PA temperature is critical."
    ::= { rrTrapPrefix 16 }

paDcPowerNormal NOTIFICATION-TYPE
    OBJECTS     { flaTimeStamp, flaSeqNum, flaSeverity,
                  flaMoType, flaMoId, flaAddtlInfo }
    STATUS      current
    DESCRIPTION "PA DC power fault condition does not exist."
    ::= { rrTrapPrefix 17 }

paDcPowerFaultTrap NOTIFICATION-TYPE
    OBJECTS     { flaTimeStamp, flaSeqNum, flaSeverity,
                  flaMoType, flaMoId, flaAddtlInfo }
    STATUS      current
    DESCRIPTION "PA DC power fault condition exists."
    ::= { rrTrapPrefix 18 }

paRfOverdriveNormal NOTIFICATION-TYPE
    OBJECTS     { flaTimeStamp, flaSeqNum, flaSeverity,
                  flaMoType, flaMoId, flaAddtlInfo }
    STATUS      current
    DESCRIPTION "PA input RF overdrive condition does not exist."
    ::= { rrTrapPrefix 19 }

paRfOverdriveFaultTrap NOTIFICATION-TYPE
    OBJECTS     { flaTimeStamp, flaSeqNum, flaSeverity,
                  flaMoType, flaMoId, flaAddtlInfo }
    STATUS      current
    DESCRIPTION "PA input RF overdrive condition exists."
    ::= { rrTrapPrefix 20 }

paReflectedPowerNormal  NOTIFICATION-TYPE
    OBJECTS     { flaTimeStamp, flaSeqNum, flaSeverity,
                  flaMoType, flaMoId, flaAddtlInfo }
    STATUS      current
    DESCRIPTION "PA reflected power fault condition does not exist."
    ::= { rrTrapPrefix 21 }

paReflectedPowerFaultTrap NOTIFICATION-TYPE
    OBJECTS     { flaTimeStamp, flaSeqNum, flaSeverity,
                  flaMoType, flaMoId, flaAddtlInfo }
    STATUS      current
    DESCRIPTION "PA reflected power fault condition exists."
    ::= { rrTrapPrefix 22 }

pcuPowerNormal  NOTIFICATION-TYPE
    OBJECTS     { flaTimeStamp, flaSeqNum, flaSeverity,
                  flaMoType, flaMoId, flaAddtlInfo }
    STATUS      current
    DESCRIPTION "PCU power restored."
    ::= { rrTrapPrefix 23 }

pcuPowerFailTrap NOTIFICATION-TYPE
    OBJECTS     { flaTimeStamp, flaSeqNum, flaSeverity,
                  flaMoType, flaMoId, flaAddtlInfo }
    STATUS      current
    DESCRIPTION "PCU power failed."
    ::= { rrTrapPrefix 24 }

aiuOperStatusUp NOTIFICATION-TYPE
    OBJECTS     { flaTimeStamp, flaSeqNum, flaSeverity,
                  flaMoType, flaMoId, flaAddtlInfo }
    STATUS      current
    DESCRIPTION "AIU operational status is up."
    ::= { rrTrapPrefix 25 }

aiuOperStatusDown   NOTIFICATION-TYPE
    OBJECTS     { flaTimeStamp, flaSeqNum, flaSeverity,
                  flaMoType, flaMoId, flaAddtlInfo }
    STATUS      current
    DESCRIPTION "AIU operational status is up."
    ::= { rrTrapPrefix 26 }

aiuTempNormal   NOTIFICATION-TYPE
    OBJECTS     { flaTimeStamp, flaSeqNum, flaSeverity,
                  flaMoType, flaMoId, flaAddtlInfo }
    STATUS      current
    DESCRIPTION "AIU temperature is within normal operating range."
    ::= { rrTrapPrefix 27 }

aiuTempHigh     NOTIFICATION-TYPE
    OBJECTS     { flaTimeStamp, flaSeqNum, flaSeverity,
                  flaMoType, flaMoId, flaAddtlInfo }
    STATUS      current
    DESCRIPTION "AIU temperature is high."
    ::= { rrTrapPrefix 28 }

aiuTempSevere   NOTIFICATION-TYPE
    OBJECTS     { flaTimeStamp, flaSeqNum, flaSeverity,
                  flaMoType, flaMoId, flaAddtlInfo }
    STATUS      current
    DESCRIPTION "AIU temperature is severe."
    ::= { rrTrapPrefix 29 }

aiuTempCritical NOTIFICATION-TYPE
    OBJECTS     { flaTimeStamp, flaSeqNum, flaSeverity,
                  flaMoType, flaMoId, flaAddtlInfo }
    STATUS      current
    DESCRIPTION "AIU temperature is critical."
    ::= { rrTrapPrefix 30 }

aiuVoltageNormal    NOTIFICATION-TYPE
    OBJECTS     { flaTimeStamp, flaSeqNum, flaSeverity,
                  flaMoType, flaMoId, flaAddtlInfo }
    STATUS      current
    DESCRIPTION "AIU voltage is within normal operating range."
    ::= { rrTrapPrefix 31 }

aiuVoltageHigh  NOTIFICATION-TYPE
    OBJECTS     { flaTimeStamp, flaSeqNum, flaSeverity,
                  flaMoType, flaMoId, flaAddtlInfo }
    STATUS      current
    DESCRIPTION "AIU voltage is high."
    ::= { rrTrapPrefix 32 }

aiuVoltageLow   NOTIFICATION-TYPE
    OBJECTS     { flaTimeStamp, flaSeqNum, flaSeverity,
                  flaMoType, flaMoId, flaAddtlInfo }
    STATUS      current
    DESCRIPTION "AIU voltage is low."
    ::= { rrTrapPrefix 33 }

rxuOperStatusUp NOTIFICATION-TYPE
    OBJECTS     { flaTimeStamp, flaSeqNum, flaSeverity,
                  flaMoType, flaMoId, flaAddtlInfo }
    STATUS      current
    DESCRIPTION "RXU operational status is up."
    ::= { rrTrapPrefix 34 }

rxuOperStatusDown   NOTIFICATION-TYPE
    OBJECTS     { flaTimeStamp, flaSeqNum, flaSeverity,
                  flaMoType, flaMoId, flaAddtlInfo }
    STATUS      current
    DESCRIPTION "RXU operational status is down."
    ::= { rrTrapPrefix 35 }

rxuOperStatusNotPresent NOTIFICATION-TYPE
    OBJECTS     { flaTimeStamp, flaSeqNum, flaSeverity,
                  flaMoType, flaMoId, flaAddtlInfo }
    STATUS      current
    DESCRIPTION "RXU operational status is not present."
    ::= { rrTrapPrefix 36 }

rxuTempNormal   NOTIFICATION-TYPE
    OBJECTS     { flaTimeStamp, flaSeqNum, flaSeverity,
                  flaMoType, flaMoId, flaAddtlInfo }
    STATUS      current
    DESCRIPTION "RXU temperature is within normal operating range."
    ::= { rrTrapPrefix 37 }

rxuTempHigh     NOTIFICATION-TYPE
    OBJECTS     { flaTimeStamp, flaSeqNum, flaSeverity,
                  flaMoType, flaMoId, flaAddtlInfo }
    STATUS      current
    DESCRIPTION "RXU temperature is high."
    ::= { rrTrapPrefix 38 }

rxuTempSevere   NOTIFICATION-TYPE
    OBJECTS     { flaTimeStamp, flaSeqNum, flaSeverity,
                  flaMoType, flaMoId, flaAddtlInfo }
    STATUS      current
    DESCRIPTION "RXU temperature is severe."
    ::= { rrTrapPrefix 39 }

rxuTempCritical NOTIFICATION-TYPE
    OBJECTS     { flaTimeStamp, flaSeqNum, flaSeverity,
                  flaMoType, flaMoId, flaAddtlInfo }
    STATUS      current
    DESCRIPTION "RXU temperature is critical."
    ::= { rrTrapPrefix 40 }

txuOperStatusUp NOTIFICATION-TYPE
    OBJECTS     { flaTimeStamp, flaSeqNum, flaSeverity,
                  flaMoType, flaMoId, flaAddtlInfo }
    STATUS      current
    DESCRIPTION "TXU operational status is up."
    ::= { rrTrapPrefix 41 }

txuOperStatusDown   NOTIFICATION-TYPE
    OBJECTS     { flaTimeStamp, flaSeqNum, flaSeverity,
                  flaMoType, flaMoId, flaAddtlInfo }
    STATUS      current
    DESCRIPTION "TXU operational status is down."
    ::= { rrTrapPrefix 42 }

txuOperStatusNotPresent NOTIFICATION-TYPE
    OBJECTS     { flaTimeStamp, flaSeqNum, flaSeverity,
                  flaMoType, flaMoId, flaAddtlInfo }
    STATUS      current
    DESCRIPTION "TXU operational status is not present."
    ::= { rrTrapPrefix 43 }

txuTempNormal   NOTIFICATION-TYPE
    OBJECTS     { flaTimeStamp, flaSeqNum, flaSeverity,
                  flaMoType, flaMoId, flaAddtlInfo }
    STATUS      current
    DESCRIPTION "TXU temperature is within normal operating range."
    ::= { rrTrapPrefix 44 }

txuTempHigh     NOTIFICATION-TYPE
    OBJECTS     { flaTimeStamp, flaSeqNum, flaSeverity,
                  flaMoType, flaMoId, flaAddtlInfo }
    STATUS      current
    DESCRIPTION "TXU temperature is high."
    ::= { rrTrapPrefix 45 }

txuTempSevere   NOTIFICATION-TYPE
    OBJECTS     { flaTimeStamp, flaSeqNum, flaSeverity,
                  flaMoType, flaMoId, flaAddtlInfo }
    STATUS      current
    DESCRIPTION "TXU temperature is severe."
    ::= { rrTrapPrefix 46 }

txuTempCritical NOTIFICATION-TYPE
    OBJECTS     { flaTimeStamp, flaSeqNum, flaSeverity,
                  flaMoType, flaMoId, flaAddtlInfo }
    STATUS      current
    DESCRIPTION "TXU temperature is critical."
    ::= { rrTrapPrefix 47 }

rrShelfFanNormal    NOTIFICATION-TYPE
    OBJECTS     { flaTimeStamp, flaSeqNum, flaSeverity,
                  flaMoType, flaMoId, flaAddtlInfo }
    STATUS      current
    DESCRIPTION "RadioRouter shelf fan is operating within normal limits."
    ::= { rrTrapPrefix 48 }

rrShelfFanFault NOTIFICATION-TYPE
    OBJECTS     { flaTimeStamp, flaSeqNum, flaSeverity,
                  flaMoType, flaMoId, flaAddtlInfo }
    STATUS      current
    DESCRIPTION "RadioRouter shelf fan is operating outside normal limits."
    ::= { rrTrapPrefix 49 }

alarmInputAlarmed   NOTIFICATION-TYPE
    OBJECTS     { flaTimeStamp, flaSeqNum, flaSeverity,
                  flaMoType, flaMoId, flaAddtlInfo }
    STATUS      current
    DESCRIPTION "Alarm input indicates an alarm condition. The flaMoId object
                indicates which input has changed."
    ::= { rrTrapPrefix 50 }

alarmInputCleared   NOTIFICATION-TYPE
    OBJECTS     { flaTimeStamp, flaSeqNum, flaSeverity,
                  flaMoType, flaMoId, flaAddtlInfo }
    STATUS      current
    DESCRIPTION "Alarm input has changed to cleared. The flaMoId object
                indicates which input has changed."
    ::= { rrTrapPrefix 51 }

cabinetDoorOpened   NOTIFICATION-TYPE
    OBJECTS     { flaTimeStamp, flaSeqNum, flaSeverity,
                  flaMoType, flaMoId, flaAddtlInfo }
    STATUS      current
    DESCRIPTION "Cabinet door is open. This applies to outdoor cabinets only."
    ::= { rrTrapPrefix 52 }

cabinetDoorClosed   NOTIFICATION-TYPE
    OBJECTS     { flaTimeStamp, flaSeqNum, flaSeverity,
                  flaMoType, flaMoId, flaAddtlInfo }
    STATUS      current
    DESCRIPTION "Cabinet door is closed. This trap applies to outdoor cabinets
                only."
    ::= { rrTrapPrefix 53 }

cabinetSmokeFireAlarmed NOTIFICATION-TYPE
    OBJECTS     { flaTimeStamp, flaSeqNum, flaSeverity,
                  flaMoType, flaMoId, flaAddtlInfo }
    STATUS      current
    DESCRIPTION "Smoke or fire detected in cabinet. This trap applies to outdoor
                cabinets only."
    ::= { rrTrapPrefix 54 }

cabinetSmokeFireCleared NOTIFICATION-TYPE
    OBJECTS     { flaTimeStamp, flaSeqNum, flaSeverity,
                  flaMoType, flaMoId, flaAddtlInfo }
    STATUS      current
    DESCRIPTION "Smoke or fire no longer detected in cabinet. This trap applies
                to outdoor cabinets only."
    ::= { rrTrapPrefix 55 }

cabinetHeaterBreakerTripped NOTIFICATION-TYPE
    OBJECTS     { flaTimeStamp, flaSeqNum, flaSeverity,
                  flaMoType, flaMoId, flaAddtlInfo }
    STATUS      current
    DESCRIPTION "Cabinet heater breaker tripped. This trap applies to outdoor
                cabinets only."
    ::= { rrTrapPrefix 56 }

cabinetHeaterBreakerNormal  NOTIFICATION-TYPE
    OBJECTS     { flaTimeStamp, flaSeqNum, flaSeverity,
                  flaMoType, flaMoId, flaAddtlInfo }
    STATUS      current
    DESCRIPTION "Cabinet heater breaker is not tripped. This trap applies to 
                outdoor cabinets only."
    ::= { rrTrapPrefix 57 }

cabinetHeatExchangerBreakerTripped  NOTIFICATION-TYPE
    OBJECTS     { flaTimeStamp, flaSeqNum, flaSeverity,
                  flaMoType, flaMoId, flaAddtlInfo }
    STATUS      current
    DESCRIPTION "Cabinet heat exchanger breaker tripped. This trap applies to 
                outdoor cabinets only."
    ::= { rrTrapPrefix 58 }

cabinetHeatExchangerBreakerNormal   NOTIFICATION-TYPE
    OBJECTS     { flaTimeStamp, flaSeqNum, flaSeverity,
                  flaMoType, flaMoId, flaAddtlInfo }
    STATUS      current
    DESCRIPTION "Cabinet heat exchanger breaker is not tripped. This trap
                applies to outdoor cabinets only."
    ::= { rrTrapPrefix 59 }

heatExAmbientImpellerFault  NOTIFICATION-TYPE
    OBJECTS     { flaTimeStamp, flaSeqNum, flaSeverity,
                  flaMoType, flaMoId, flaAddtlInfo }
    STATUS      current
    DESCRIPTION "Cabinet heat exchanger ambient impeller fault exists. This trap
                applies to outdoor cabinets only."
    ::= { rrTrapPrefix 60 }

heatExAmbientImpellerCleared    NOTIFICATION-TYPE
    OBJECTS     { flaTimeStamp, flaSeqNum, flaSeverity,
                  flaMoType, flaMoId, flaAddtlInfo }
    STATUS      current
    DESCRIPTION "Cabinet heat exchanger ambient impeller fault has cleared. This
                trap applies to outdoor cabinets only."
    ::= { rrTrapPrefix 61 }

heatExEnclosureImpellerFault NOTIFICATION-TYPE
    OBJECTS     { flaTimeStamp, flaSeqNum, flaSeverity,
                  flaMoType, flaMoId, flaAddtlInfo }
    STATUS      current
    DESCRIPTION "Cabinet heat exchanger enclosure impeller fault exists. This
                trap applies to outdoor cabinets only."
    ::= { rrTrapPrefix 62 }

heatExEnclosureImpellerCleared  NOTIFICATION-TYPE
    OBJECTS     { flaTimeStamp, flaSeqNum, flaSeverity,
                  flaMoType, flaMoId, flaAddtlInfo }
    STATUS      current
    DESCRIPTION "Cabinet heat exchanger enclosure impeller fault has cleared.
                This trap applies to outdoor cabinets only."
    ::= { rrTrapPrefix 63 }

heatExTempFault NOTIFICATION-TYPE
    OBJECTS     { flaTimeStamp, flaSeqNum, flaSeverity,
                  flaMoType, flaMoId, flaAddtlInfo }
    STATUS      current
    DESCRIPTION "Cabinet heat exchanger temperature fault exists. This trap
                applies to outdoor cabinets only."
    ::= { rrTrapPrefix 64 }

heatExTempCleared   NOTIFICATION-TYPE
    OBJECTS     { flaTimeStamp, flaSeqNum, flaSeverity,
                  flaMoType, flaMoId, flaAddtlInfo }
    STATUS      current
    DESCRIPTION "Cabinet heat exchanger temperature fault has cleared. This trap
                applies to outdoor cabinets only."
    ::= { rrTrapPrefix 65 }

heatExSummaryFault  NOTIFICATION-TYPE
    OBJECTS     { flaTimeStamp, flaSeqNum, flaSeverity,
                  flaMoType, flaMoId, flaAddtlInfo }
    STATUS      current
    DESCRIPTION "Cabinet heat exchanger summary fault exists. This trap
                applies to outdoor cabinets only."
    ::= { rrTrapPrefix 66 }

heatExSummaryCleared    NOTIFICATION-TYPE
    OBJECTS     { flaTimeStamp, flaSeqNum, flaSeverity,
                  flaMoType, flaMoId, flaAddtlInfo }
    STATUS      current
    DESCRIPTION "Cabinet heat exchanger summary fault has cleared. This trap
                applies to outdoor cabinets only."
    ::= { rrTrapPrefix 67 }

cabinetAcFault  NOTIFICATION-TYPE
    OBJECTS     { flaTimeStamp, flaSeqNum, flaSeverity,
                  flaMoType, flaMoId, flaAddtlInfo }
    STATUS      current
    DESCRIPTION "Cabinet AC failure due to surge suppressor fuse."
    ::= { rrTrapPrefix 68 }

cabinetAcOk     NOTIFICATION-TYPE
    OBJECTS     { flaTimeStamp, flaSeqNum, flaSeverity,
                  flaMoType, flaMoId, flaAddtlInfo }
    STATUS      current
    DESCRIPTION "Cabinet AC has been restored."
    ::= { rrTrapPrefix 69 }

cabinetPowerFaultTrap NOTIFICATION-TYPE
    OBJECTS     { flaTimeStamp, flaSeqNum, flaSeverity,
                  flaMoType, flaMoId, flaAddtlInfo }
    STATUS      current
    DESCRIPTION "Cabinet power fault exists."
    ::= { rrTrapPrefix 70 }

cabinetPowerOk  NOTIFICATION-TYPE
    OBJECTS     { flaTimeStamp, flaSeqNum, flaSeverity,
                  flaMoType, flaMoId, flaAddtlInfo }
    STATUS      current
    DESCRIPTION "Cabinet power has been restored."
    ::= { rrTrapPrefix 71 }

aiuOperStatusNotPresent NOTIFICATION-TYPE
    OBJECTS     { flaTimeStamp, flaSeqNum, flaSeverity,
                  flaMoType, flaMoId, flaAddtlInfo }
    STATUS      current
    DESCRIPTION "AIU operational status is not present."
    ::= { rrTrapPrefix 72 }

paOperStatusEnabled NOTIFICATION-TYPE
    OBJECTS     { flaTimeStamp, flaSeqNum, flaSeverity,
                  flaMoType, flaMoId, flaAddtlInfo }
    STATUS      current
    DESCRIPTION "PA is enabled."
    ::= { rrTrapPrefix 73 }

paOperStatusDisabledPa  NOTIFICATION-TYPE
    OBJECTS     { flaTimeStamp, flaSeqNum, flaSeverity,
                  flaMoType, flaMoId, flaAddtlInfo }
    STATUS      current
    DESCRIPTION "PA detected a fault condition and disabled itself."
    ::= { rrTrapPrefix 74 }

paOperStatusDisabledBts NOTIFICATION-TYPE
    OBJECTS     { flaTimeStamp, flaSeqNum, flaSeverity,
                  flaMoType, flaMoId, flaAddtlInfo }
    STATUS      current
    DESCRIPTION "PA was disabled by basestation user intervention."
    ::= { rrTrapPrefix 75 }

paOperStatusNotPresent  NOTIFICATION-TYPE
    OBJECTS     { flaTimeStamp, flaSeqNum, flaSeverity,
                  flaMoType, flaMoId, flaAddtlInfo }
    STATUS      current
    DESCRIPTION "PA operational status is not present."
    ::= { rrTrapPrefix 76 }


--
-- The following traps are deprecated
--

--
-- Rectifier Traps (specific 10 - 19)
--
rectifierFanStatus  NOTIFICATION-TYPE
    OBJECTS     { rrTimeStamp,
                  rrSeqNum,
                  rrSeverity,
                  rrMoType,
                  rrMoId,
                  rrAddtlInfo 
                }
    STATUS      deprecated
    DESCRIPTION "Rectifier fan status changed."
    ::= { rrTrapSpecific 10 }

acRectifierStatus  NOTIFICATION-TYPE
    OBJECTS     { rrTimeStamp,
                  rrSeqNum,
                  rrSeverity,
                  rrMoType,
                  rrMoId,
                  rrAddtlInfo 
                }
    STATUS      deprecated
    DESCRIPTION "AC rectifier status changed."
    ::= { rrTrapSpecific 11 }

acRectifierBreakerStatus  NOTIFICATION-TYPE
    OBJECTS     { rrTimeStamp,
                  rrSeqNum,
                  rrSeverity,
                  rrMoType,
                  rrMoId,
                  rrAddtlInfo 
                }
    STATUS      deprecated
    DESCRIPTION "AC rectifier breaker status changed."
    ::= { rrTrapSpecific 12 }

dcRectifierStatus  NOTIFICATION-TYPE
    OBJECTS     { rrTimeStamp,
                  rrSeqNum,
                  rrSeverity,
                  rrMoType,
                  rrMoId,
                  rrAddtlInfo 
                }
    STATUS      deprecated
    DESCRIPTION "DC rectifier status changed."
    ::= { rrTrapSpecific 13 }


--
-- LNA Traps (specific 20 - 29)
--
lnaOperStatus   NOTIFICATION-TYPE
    OBJECTS     { rrTimeStamp,
                  rrSeqNum,
                  rrSeverity,
                  rrMoType,
                  rrMoId,
                  rrAddtlInfo 
                }
    STATUS      deprecated
    DESCRIPTION "LNA operational status changed."
    ::= { rrTrapSpecific 20 }

lnaDiversityBreaker NOTIFICATION-TYPE
    OBJECTS     { rrTimeStamp,
                  rrSeqNum,
                  rrSeverity,
                  rrMoType,
                  rrMoId,
                  rrAddtlInfo 
                }
    STATUS      deprecated
    DESCRIPTION "LNA diversity breaker tripped."
    ::= { rrTrapSpecific 21 }



--
-- PowerAmp Traps (specific 30 - 39)
--
paShelfFanSpeedStatus   NOTIFICATION-TYPE
    OBJECTS     { rrTimeStamp,
                  rrSeqNum,
                  rrSeverity,
                  rrMoType,
                  rrMoId,
                  rrAddtlInfo
                }
    STATUS      deprecated
    DESCRIPTION "PA shelf fan speed status changed."
    ::= { rrTrapSpecific 30 }

paShelfFanTempStatus    NOTIFICATION-TYPE
    OBJECTS     { rrTimeStamp,
                  rrSeqNum,
                  rrSeverity,
                  rrMoType,
                  rrMoId,
                  rrAddtlInfo
                }
    STATUS      deprecated
    DESCRIPTION "PA shelf fan temperature status changed."
    ::= { rrTrapSpecific 31 }

paShelfBreakerStatus    NOTIFICATION-TYPE
    OBJECTS     { rrTimeStamp,
                  rrSeqNum,
                  rrSeverity,
                  rrMoType,
                  rrMoId,
                  rrAddtlInfo
                }
    STATUS      deprecated
    DESCRIPTION "PA shelf breaker status changed."
    ::= { rrTrapSpecific 32 }

paOperStatus    NOTIFICATION-TYPE
    OBJECTS     { rrTimeStamp,
                  rrSeqNum,
                  rrSeverity,
                  rrMoType,
                  rrMoId,
                  rrAddtlInfo
                }
    STATUS      deprecated
    DESCRIPTION "PA operational status changed."
    ::= { rrTrapSpecific 33 }

paTempStatus    NOTIFICATION-TYPE
    OBJECTS     { rrTimeStamp,
                  rrSeqNum,
                  rrSeverity,
                  rrMoType,
                  rrMoId,
                  rrAddtlInfo
                }
    STATUS      deprecated
    DESCRIPTION "PA temperature status changed."
    ::= { rrTrapSpecific 34 }

paDcPowerFaultStatus    NOTIFICATION-TYPE
    OBJECTS     { rrTimeStamp,
                  rrSeqNum,
                  rrSeverity,
                  rrMoType,
                  rrMoId,
                  rrAddtlInfo
                }
    STATUS      deprecated
    DESCRIPTION "PA DC power fault status changed."
    ::= { rrTrapSpecific 35 }

paInputRfOverdriveFault NOTIFICATION-TYPE
    OBJECTS     { rrTimeStamp,
                  rrSeqNum,
                  rrSeverity,
                  rrMoType,
                  rrMoId,
                  rrAddtlInfo
                }
    STATUS      deprecated
    DESCRIPTION "PA input RF overdrive status changed."
    ::= { rrTrapSpecific 36 }

paFeedForwardLoopFault  NOTIFICATION-TYPE
    OBJECTS     { rrTimeStamp,
                  rrSeqNum,
                  rrSeverity,
                  rrMoType,
                  rrMoId,
                  rrAddtlInfo
                }
    STATUS      deprecated
    DESCRIPTION "PA feed forward loop status changed."
    ::= { rrTrapSpecific 37 }

paReflectedPowerFault   NOTIFICATION-TYPE
    OBJECTS     { rrTimeStamp,
                  rrSeqNum,
                  rrSeverity,
                  rrMoType,
                  rrMoId,
                  rrAddtlInfo
                }
    STATUS      deprecated
    DESCRIPTION "PA reflected power fault exists."
    ::= { rrTrapSpecific 38 }


--
-- cPCI Traps (specific 50 - 99) 
--


--
-- Power Control Unit Traps (specific 100 - 109)
--
pcuPowerFail    NOTIFICATION-TYPE
    OBJECTS     { rrTimeStamp,
                  rrSeqNum,
                  rrSeverity,
                  rrMoType,
                  rrMoId,
                  rrAddtlInfo
                }
    STATUS      deprecated
    DESCRIPTION "PCU power failed."
    ::= { rrTrapSpecific 100 }

pcuOperStatus   NOTIFICATION-TYPE
    OBJECTS     { rrTimeStamp,
                  rrSeqNum,
                  rrSeverity,
                  rrMoType,
                  rrMoId,
                  rrAddtlInfo
                }
    STATUS      deprecated
    DESCRIPTION "PCU operational status changed."
    ::= { rrTrapSpecific 101 }

pcuFaultLedStatus   NOTIFICATION-TYPE
    OBJECTS     { rrTimeStamp,
                  rrSeqNum,
                  rrSeverity,
                  rrMoType,
                  rrMoId,
                  rrAddtlInfo
                }
    STATUS      deprecated
    DESCRIPTION "PCU fault LED status changed."
    ::= { rrTrapSpecific 102 }

pcuTempStatus   NOTIFICATION-TYPE
    OBJECTS     { rrTimeStamp,
                  rrSeqNum,
                  rrSeverity,
                  rrMoType,
                  rrMoId,
                  rrAddtlInfo
                }
    STATUS      deprecated
    DESCRIPTION "PCU temperature status changed."
    ::= { rrTrapSpecific 103 }

pcuVoltageStatus    NOTIFICATION-TYPE
    OBJECTS     { rrTimeStamp,
                  rrSeqNum,
                  rrSeverity,
                  rrMoType,
                  rrMoId,
                  rrAddtlInfo
                }
    STATUS      deprecated
    DESCRIPTION "PCU voltage status changed."
    ::= { rrTrapSpecific 104 }


--
-- AIU Traps (specific 110 - 119)
--
aiuOperStatus   NOTIFICATION-TYPE
    OBJECTS     { rrTimeStamp,
                  rrSeqNum,
                  rrSeverity,
                  rrMoType,
                  rrMoId,
                  rrAddtlInfo
                }
    STATUS      deprecated
    DESCRIPTION "AIU operational status changed."
    ::= { rrTrapSpecific 110 }

aiuFaultLedStatus   NOTIFICATION-TYPE
    OBJECTS     { rrTimeStamp,
                  rrSeqNum,
                  rrSeverity,
                  rrMoType,
                  rrMoId,
                  rrAddtlInfo
                }
    STATUS      deprecated
    DESCRIPTION "AIU fault LED status changed."
    ::= { rrTrapSpecific 111 }

aiuTempStatus   NOTIFICATION-TYPE
    OBJECTS     { rrTimeStamp,
                  rrSeqNum,
                  rrSeverity,
                  rrMoType,
                  rrMoId,
                  rrAddtlInfo
                }
    STATUS      deprecated
    DESCRIPTION "AIU temperature status changed."
    ::= { rrTrapSpecific 112 }

aiuVoltageStatus    NOTIFICATION-TYPE
    OBJECTS     { rrTimeStamp,
                  rrSeqNum,
                  rrSeverity,
                  rrMoType,
                  rrMoId,
                  rrAddtlInfo
                }
    STATUS      deprecated
    DESCRIPTION "AIU voltage status changed."
    ::= { rrTrapSpecific 113 }

--
-- RXU Traps (specific 250 - 259)
--
rxuOperStatus   NOTIFICATION-TYPE
    OBJECTS     { rrTimeStamp,
                  rrSeqNum,
                  rrSeverity,
                  rrMoType,
                  rrMoId,
                  rrAddtlInfo
                }
    STATUS      deprecated
    DESCRIPTION "RXU operational status changed."
    ::= { rrTrapSpecific 250 }

rxuFaultLedStatus   NOTIFICATION-TYPE
    OBJECTS     { rrTimeStamp,
                  rrSeqNum,
                  rrSeverity,
                  rrMoType,
                  rrMoId,
                  rrAddtlInfo
                }
    STATUS      deprecated
    DESCRIPTION "RXU fault LED status changed."
    ::= { rrTrapSpecific 251 }

rxuTempStatus   NOTIFICATION-TYPE
    OBJECTS     { rrTimeStamp,
                  rrSeqNum,
                  rrSeverity,
                  rrMoType,
                  rrMoId,
                  rrAddtlInfo
                }
    STATUS      deprecated
    DESCRIPTION "RXU temperature status changed."
    ::= { rrTrapSpecific 252 }

rxuVoltageStatus    NOTIFICATION-TYPE
    OBJECTS     { rrTimeStamp,
                  rrSeqNum,
                  rrSeverity,
                  rrMoType,
                  rrMoId,
                  rrAddtlInfo
                }
    STATUS      deprecated
    DESCRIPTION "RXU voltage status changed."
    ::= { rrTrapSpecific 253 }


--
-- TXU Traps (specific 260 - 269)
--
txuOperStatus   NOTIFICATION-TYPE
    OBJECTS     { rrTimeStamp,
                  rrSeqNum,
                  rrSeverity,
                  rrMoType,
                  rrMoId,
                  rrAddtlInfo
                }
    STATUS      deprecated
    DESCRIPTION "TXU operational status changed."
    ::= { rrTrapSpecific 260 }

txuFaultLedStatus   NOTIFICATION-TYPE
    OBJECTS     { rrTimeStamp,
                  rrSeqNum,
                  rrSeverity,
                  rrMoType,
                  rrMoId,
                  rrAddtlInfo
                }
    STATUS      deprecated
    DESCRIPTION "TXU fault LED status changed."
    ::= { rrTrapSpecific 261 }

txuTempStatus   NOTIFICATION-TYPE
    OBJECTS     { rrTimeStamp,
                  rrSeqNum,
                  rrSeverity,
                  rrMoType,
                  rrMoId,
                  rrAddtlInfo
                }
    STATUS      deprecated
    DESCRIPTION "TXU temperature status changed."
    ::= { rrTrapSpecific 262 }

txuVoltageStatus    NOTIFICATION-TYPE
    OBJECTS     { rrTimeStamp,
                  rrSeqNum,
                  rrSeverity,
                  rrMoType,
                  rrMoId,
                  rrAddtlInfo
                }
    STATUS      deprecated
    DESCRIPTION "TXU voltage status changed."
    ::= { rrTrapSpecific 263 }


--
-- Fan Traps (specific 270 - 279)
--
rrShelfFanStatus    NOTIFICATION-TYPE
    OBJECTS     { rrTimeStamp,
                  rrSeqNum,
                  rrSeverity,
                  rrMoType,
                  rrMoId,
                  rrAddtlInfo 
                }
    STATUS      deprecated
    DESCRIPTION "RadioRouter shelf fan status changed."
    ::= { rrTrapSpecific 270 }


--
-- Cabinet Traps (specific 300 - 349)
--
cabinetDoor     NOTIFICATION-TYPE
    OBJECTS     { rrTimeStamp,
                  rrSeqNum,
                  rrSeverity,
                  rrMoType,
                  rrMoId,
                  rrAddtlInfo 
                }
    STATUS      deprecated
    DESCRIPTION "Cabinet door ajar notification."
    ::= { rrTrapSpecific 300 }

cabinetSmokeFire    NOTIFICATION-TYPE
    OBJECTS     { rrTimeStamp,
                  rrSeqNum,
                  rrSeverity,
                  rrMoType,
                  rrMoId,
                  rrAddtlInfo 
                }
    STATUS      deprecated
    DESCRIPTION "Smoke or fire detected in cabinet."
    ::= { rrTrapSpecific 301 }

cabinetHeaterBreaker    NOTIFICATION-TYPE
    OBJECTS     { rrTimeStamp,
                  rrSeqNum,
                  rrSeverity,
                  rrMoType,
                  rrMoId,
                  rrAddtlInfo 
                }
    STATUS      deprecated
    DESCRIPTION "Cabinet heater breaker tripped."
    ::= { rrTrapSpecific 302 }

cabinetHeatExchangerBreaker NOTIFICATION-TYPE
    OBJECTS     { rrTimeStamp,
                  rrSeqNum,
                  rrSeverity,
                  rrMoType,
                  rrMoId,
                  rrAddtlInfo 
                }
    STATUS      deprecated
    DESCRIPTION "Cabinet heat exchanger breaker tripped."
    ::= { rrTrapSpecific 303 }

cabinetAcMainBreaker    NOTIFICATION-TYPE
    OBJECTS     { rrTimeStamp,
                  rrSeqNum,
                  rrSeverity,
                  rrMoType,
                  rrMoId,
                  rrAddtlInfo 
                }
    STATUS      deprecated
    DESCRIPTION "Cabinet AC-main breaker tripped."
    ::= { rrTrapSpecific 304 }

cabinetUtilityBreaker   NOTIFICATION-TYPE
    OBJECTS     { rrTimeStamp,
                  rrSeqNum,
                  rrSeverity,
                  rrMoType,
                  rrMoId,
                  rrAddtlInfo 
                }
    STATUS      deprecated
    DESCRIPTION "Cabinet utility breaker tripped."
    ::= { rrTrapSpecific 305 }

heatExAmbientImpeller   NOTIFICATION-TYPE
    OBJECTS     { rrTimeStamp,
                  rrSeqNum,
                  rrSeverity,
                  rrMoType,
                  rrMoId,
                  rrAddtlInfo 
                }
    STATUS      deprecated
    DESCRIPTION "Cabinet heat exchanger ambient impeller failed."
    ::= { rrTrapSpecific 306 }

heatExEnClosureImpeller NOTIFICATION-TYPE
    OBJECTS     { rrTimeStamp,
                  rrSeqNum,
                  rrSeverity,
                  rrMoType,
                  rrMoId,
                  rrAddtlInfo 
                }
    STATUS      deprecated
    DESCRIPTION "Cabinet heat exchanger enclosure impeller failed."
    ::= { rrTrapSpecific 307 }

heatExTemp      NOTIFICATION-TYPE
    OBJECTS     { rrTimeStamp,
                  rrSeqNum,
                  rrSeverity,
                  rrMoType,
                  rrMoId,
                  rrAddtlInfo 
                }
    STATUS      deprecated
    DESCRIPTION "Cabinet heat exchanger temperature status changed."
    ::= { rrTrapSpecific 308 }

heatExSummary   NOTIFICATION-TYPE
    OBJECTS     { rrTimeStamp,
                  rrSeqNum,
                  rrSeverity,
                  rrMoType,
                  rrMoId,
                  rrAddtlInfo 
                }
    STATUS      deprecated
    DESCRIPTION "Cabinet heat exchanger summary status changed."
    ::= { rrTrapSpecific 309 }

cabinetPowerService NOTIFICATION-TYPE
    OBJECTS     { rrTimeStamp,
                  rrSeqNum,
                  rrSeverity,
                  rrMoType,
                  rrMoId,
                  rrAddtlInfo 
                }
    STATUS      deprecated
    DESCRIPTION "Cabinet power service status changed."
    ::= { rrTrapSpecific 310 }

cabinetHumidityStatus   NOTIFICATION-TYPE
    OBJECTS     { rrTimeStamp,
                  rrSeqNum,
                  rrSeverity,
                  rrMoType,
                  rrMoId,
                  rrAddtlInfo 
                }
    STATUS      deprecated
    DESCRIPTION "Cabinet humidity status changed."
    ::= { rrTrapSpecific 311 }

cabinetAcFail   NOTIFICATION-TYPE
    OBJECTS     { rrTimeStamp,
                  rrSeqNum,
                  rrSeverity,
                  rrMoType,
                  rrMoId,
                  rrAddtlInfo 
                }
    STATUS      deprecated
    DESCRIPTION "Cabinet AC failure due to surge suppressor fuse."
    ::= { rrTrapSpecific 312 }

cabinetPowerFault   NOTIFICATION-TYPE
    OBJECTS     { rrTimeStamp,
                  rrSeqNum,
                  rrSeverity,
                  rrMoType,
                  rrMoId,
                  rrAddtlInfo 
                }
    STATUS      deprecated
    DESCRIPTION "Cabinet power fault."
    ::= { rrTrapSpecific 313 }

END
