-- File Name : EMSNetrake.mib
-- Date      : Mon Sep 13 18:36:01 CDT 2004
-- Author    : AdventNet AgentToolkit (C Edition) - MibEditor 5.0

EMSNetrake-MIB	DEFINITIONS ::= BEGIN
	IMPORTS
		DisplayString, DateAndTime, RowStatus
			FROM SNMPv2-TC
		DisplayString
			FROM RFC1213-MIB
		Integer32, enterprises, MODULE-IDENTITY, OBJECT-TYPE, IpAddress, NOTIFICATION-TYPE
			FROM SNMPv2-SMI;

	netrake	MODULE-IDENTITY
		LAST-UPDATED	"9909201005Z"
		ORGANIZATION	"Netrake"
		CONTACT-INFO	"Netrake Corporation"
		DESCRIPTION		"www.netrake.com"
		REVISION		"200109201005Z"
		DESCRIPTION		"0.1"
		::=  {  enterprises  10950  }

	org	OBJECT IDENTIFIER
		::=  {  iso  3  }

	dod	OBJECT IDENTIFIER
		::=  {  org  6  }

	internet	OBJECT IDENTIFIER
		::=  {  dod  1  }

	private	OBJECT IDENTIFIER
		::=  {  internet  4  }

	enterprises	OBJECT IDENTIFIER
		::=  {  private  1  }

	products	OBJECT IDENTIFIER
		::=  {  netrake  1  }

	ems	OBJECT IDENTIFIER
		::=  {  products  2  }

	managedDevices	OBJECT IDENTIFIER
		::=  {  ems  1  }

	activeAlarm	OBJECT IDENTIFIER
		::=  {  ems  2  }

	managedDevicesTable	OBJECT-TYPE
		SYNTAX		SEQUENCE  OF  ManagedDevicesEntry
		MAX-ACCESS	not-accessible
		STATUS		current
		DESCRIPTION	"This table contains the list of devices being managed by   
this EMS"
		::=  { managedDevices  1 }

	managedDevicesEntry	OBJECT-TYPE
		SYNTAX		ManagedDevicesEntry
		MAX-ACCESS	not-accessible
		STATUS		current
		DESCRIPTION	"Row Description"
		INDEX		{  deviceName  }
		::=  { managedDevicesTable 1 }

	ManagedDevicesEntry  ::=  SEQUENCE {
		deviceName  DisplayString,
		deviceSerialNumber  DisplayString,
		deviceModel  DisplayString,
		deviceMgmtIpAddress  IpAddress,
		deviceAlarmStatus  INTEGER,
		deviceOperState  DisplayString,
		deviceRowStatus  RowStatus,
		deviceDisplayName  DisplayString
		}


	deviceName	OBJECT-TYPE	
		SYNTAX			DisplayString
		MAX-ACCESS		read-only
		STATUS			current
		DESCRIPTION		"Name assigned to the device"
		::=  {  managedDevicesEntry  1  }


	deviceSerialNumber	OBJECT-TYPE	
		SYNTAX			DisplayString
		MAX-ACCESS		read-only
		STATUS			current
		DESCRIPTION		"Serial number of device"
		::=  {  managedDevicesEntry  2  }


	deviceModel	OBJECT-TYPE	
		SYNTAX			DisplayString
		MAX-ACCESS		read-only
		STATUS			current
		DESCRIPTION		"Model number of device"
		::=  {  managedDevicesEntry  3  }


	deviceMgmtIpAddress	OBJECT-TYPE	
		SYNTAX			IpAddress
		MAX-ACCESS		read-only
		STATUS			current
		DESCRIPTION		"Device's management IP address"
		::=  {  managedDevicesEntry  4  }


	deviceAlarmStatus	OBJECT-TYPE	
		SYNTAX			INTEGER  { unknown ( 0 ) , critical ( 1 ) , major ( 2 ) , minor ( 3 ) , warning ( 4 ) , clear ( 5 ) , info ( 6 ) } 
		MAX-ACCESS		read-only
		STATUS			current
		DESCRIPTION		"Overall alarm status of the device based on highest      
severity alarm active on the device"
		::=  {  managedDevicesEntry  5  }


	deviceOperState	OBJECT-TYPE	
		SYNTAX			DisplayString
		MAX-ACCESS		read-only
		STATUS			current
		DESCRIPTION		"Operational state of the device"
		::=  {  managedDevicesEntry  6  }


	deviceRowStatus	OBJECT-TYPE	
		SYNTAX			RowStatus
		MAX-ACCESS		read-only
		STATUS			current
		DESCRIPTION		"Column Description"
		::=  {  managedDevicesEntry  7  }


	deviceDisplayName	OBJECT-TYPE	
		SYNTAX			DisplayString
		MAX-ACCESS		read-only
		STATUS			current
		DESCRIPTION		"Name displayed on the EMS GUI Hierarchy"
		::=  {  managedDevicesEntry  8  }

	deviceChangeTrap	NOTIFICATION-TYPE
		OBJECTS			{ deviceAlarmStatus ,deviceDisplayName ,deviceMgmtIpAddress ,deviceModel ,deviceName ,deviceOperState ,deviceRowStatus ,deviceSerialNumber  }
		STATUS			current
		DESCRIPTION		"This trap is sent whenever a change occurs on the device   
or a device is added or removed"
		::=  {  managedDevices  2  }

	emsActiveAlarmTable	OBJECT-TYPE
		SYNTAX		SEQUENCE  OF  EmsActiveAlarmEntry
		MAX-ACCESS	not-accessible
		STATUS		current
		DESCRIPTION	"This table contains the list of active alarms"
		::=  { activeAlarm  1 }

	emsActiveAlarmEntry	OBJECT-TYPE
		SYNTAX		EmsActiveAlarmEntry
		MAX-ACCESS	not-accessible
		STATUS		current
		DESCRIPTION	"Row Description"
		INDEX		{  emsActiveAlarmId, emsActiveAlarmDeviceName  }
		::=  { emsActiveAlarmTable 1 }

	EmsActiveAlarmEntry  ::=  SEQUENCE {
		emsActiveAlarmId  Integer32,
		emsActiveAlarmDeviceName  DisplayString,
		emsActiveAlarmDateTime  DateAndTime,
		emsActiveAlarmSeverity  INTEGER,
		emsActiveAlarmDescription  DisplayString,
		emsActiveAlarmNumOccurances  Integer32,
		emsActiveAlarmServiceAffecting  INTEGER,
		emsActiveAlarmRowStatus  RowStatus,
		emsActiveAlarmTypeID  Integer32
		}


	emsActiveAlarmId	OBJECT-TYPE	
		SYNTAX			Integer32  ( -2147483648 .. 2147483647  ) 
		MAX-ACCESS		read-only
		STATUS			current
		DESCRIPTION		"Unique identifier for instance of alarm"
		::=  {  emsActiveAlarmEntry  1  }


	emsActiveAlarmDeviceName	OBJECT-TYPE	
		SYNTAX			DisplayString  ( SIZE ( 0 .. 255  ) ) 
		MAX-ACCESS		read-only
		STATUS			current
		DESCRIPTION		"Name of the device that is associated with this alarm"
		::=  {  emsActiveAlarmEntry  2  }


	emsActiveAlarmDateTime	OBJECT-TYPE	
		SYNTAX			DateAndTime
		MAX-ACCESS		read-only
		STATUS			current
		DESCRIPTION		"Date/time that the alarm was detected"
		::=  {  emsActiveAlarmEntry  3  }


	emsActiveAlarmSeverity	OBJECT-TYPE	
		SYNTAX			INTEGER  { unknown ( 0 ) , critical ( 1 ) , major ( 2 ) , minor ( 3 ) , warning ( 4 ) , clear ( 5 ) , info ( 6 ) } 
		MAX-ACCESS		read-only
		STATUS			current
		DESCRIPTION		"Severity of the alarm"
		::=  {  emsActiveAlarmEntry  4  }


	emsActiveAlarmDescription	OBJECT-TYPE	
		SYNTAX			DisplayString  ( SIZE ( 0 .. 255  ) ) 
		MAX-ACCESS		read-only
		STATUS			current
		DESCRIPTION		"Description of alarm"
		::=  {  emsActiveAlarmEntry  5  }


	emsActiveAlarmNumOccurances	OBJECT-TYPE	
		SYNTAX			Integer32  ( -2147483648 .. 2147483647  ) 
		MAX-ACCESS		read-only
		STATUS			current
		DESCRIPTION		"Number of occurances of the alarmable condition since it   
became active"
		::=  {  emsActiveAlarmEntry  6  }


	emsActiveAlarmServiceAffecting	OBJECT-TYPE	
		SYNTAX			INTEGER  { serviceAffecting ( 1 ) , notServiceAffecting ( 2 ) } 
		MAX-ACCESS		read-only
		STATUS			current
		DESCRIPTION		"Indicates whether the alarm is service affecting"
		::=  {  emsActiveAlarmEntry  7  }


	emsActiveAlarmRowStatus	OBJECT-TYPE	
		SYNTAX			RowStatus  { active ( 1 ) , notInService ( 2 ) , notReady ( 3 ) , createAndGo ( 4 ) , createAndWait ( 5 ) , destroy ( 6 ) } 
		MAX-ACCESS		read-only
		STATUS			current
		DESCRIPTION		"Row Status of active alarm table"
		::=  {  emsActiveAlarmEntry  8  }


	emsActiveAlarmTypeID	OBJECT-TYPE	
		SYNTAX			Integer32  ( 1 .. 50000  ) 
		MAX-ACCESS		read-only
		STATUS			current
		DESCRIPTION		"Alarm type id - maps to documentation"
		::=  {  emsActiveAlarmEntry  9  }

	emsActiveAlarmChangeTrap	NOTIFICATION-TYPE
		OBJECTS			{ emsActiveAlarmDateTime , emsActiveAlarmDescription , emsActiveAlarmDeviceName , emsActiveAlarmId , emsActiveAlarmNumOccurances , emsActiveAlarmRowStatus , emsActiveAlarmServiceAffecting , emsActiveAlarmSeverity , emsActiveAlarmTypeID }
		STATUS			current
		DESCRIPTION		"This trap is sent whenever an alarm is changed, added, or  
deleted"
		::=  {  activeAlarm  2  }

END
