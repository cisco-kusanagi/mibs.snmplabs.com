-->#
--># Copyright (C) Siemens AG 1998
-->#               All rights reserved
-->#
-->#protocol specification
-->%PROTOCOL SNMP
-->#
-->#configuration
-->%REMCONFIG NO
-->%REMOPERATION NO
-->#
 
HiplexAF-MIB DEFINITIONS ::= BEGIN
 
--
-- Title:   MIB for SNMP Management of HIPLEX AF
-- Date:    September 1998
-- Author:  Stefan Reisch        OEC BS2 DC3
--
 
 
IMPORTS
	TRAP-TYPE FROM RFC-1215
        enterprises
            FROM RFC1155-SMI
        DisplayString
            FROM RFC1213-MIB
        OBJECT-TYPE
            FROM RFC-1212;
 
 
sni                        OBJECT IDENTIFIER ::= { enterprises 231 }
sniProductMibs             OBJECT IDENTIFIER ::= { sni 2 }
sniHiplexAF                OBJECT IDENTIFIER ::= { sniProductMibs 35 }
 
--
-- Definition of Objects
--
 
hiplexAFObjects            OBJECT IDENTIFIER ::= { sniHiplexAF 1 }
hiplexAFGlobalData         OBJECT IDENTIFIER ::= { hiplexAFObjects 1 }
hiplexAFHostInfo           OBJECT IDENTIFIER ::= { hiplexAFObjects 2 }
hiplexAFSWUInfo            OBJECT IDENTIFIER ::= { hiplexAFObjects 3 }
hiplexAFSWUHostParamInfo   OBJECT IDENTIFIER ::= { hiplexAFObjects 4 }
hiplexAFSWUHostFEPInfo     OBJECT IDENTIFIER ::= { hiplexAFObjects 5 }
hiplexAFSWUVolumeInfo      OBJECT IDENTIFIER ::= { hiplexAFObjects 6 }
hiplexAFSWUApplicationInfo OBJECT IDENTIFIER ::= { hiplexAFObjects 7 }
hiplexAFPubsetVolumeInfo   OBJECT IDENTIFIER ::= { hiplexAFObjects 8 }
 
hiplexAFVersion OBJECT-TYPE
    SYNTAX  DisplayString
    ACCESS  read-only
    STATUS  mandatory
    DESCRIPTION "Version of Hiplex AF agent"
    ::= { hiplexAFGlobalData 1}
 
hiplexAFSPVSUserid OBJECT-TYPE
    SYNTAX  DisplayString
    ACCESS  read-only
    STATUS  mandatory
    DESCRIPTION "User-Id of Hiplex AF (usually TSOS)"
    ::= { hiplexAFGlobalData 2}
 
hiplexAFSPVSCatid OBJECT-TYPE
    SYNTAX  DisplayString
    ACCESS  read-write
    STATUS  mandatory
    DESCRIPTION "Catalog-Id of Shared Pubset containing
                 Jobvariables and Files of Hiplex AF"
    ::= { hiplexAFGlobalData 3}
 
hiplexAFState     OBJECT-TYPE
        SYNTAX   INTEGER {
        started(1),
        stopped(2),
        undefined(255)
        }
        ACCESS  read-write
        STATUS  mandatory
        DESCRIPTION
           "State of Hiplex AF:
            started:   at least one main procedure has been started
                       on one host
            stopped:   Hiplex AF is stopped. No Hiplex AF procedure is
                       running on any host
            undefined: state of Hiplex AF is unkown. Jobvariables
                       with correct value could not be found.
            State may be set to stopped if it is started."
        ::= { hiplexAFGlobalData 4 }
 
hiplexAFTermHost  OBJECT-TYPE
        SYNTAX  DisplayString
        ACCESS  read-only
        STATUS  mandatory
        DESCRIPTION "BCAM Name of the system where termination request
                     for Hiplex AF was started."
        ::= { hiplexAFGlobalData 5 }
 
-- Host Table
 
hiplexAFHostTabNum OBJECT-TYPE
    SYNTAX  INTEGER
    ACCESS  read-only
    STATUS  mandatory
    DESCRIPTION
           "number of Hosts in the availability cluster"
    ::= { hiplexAFHostInfo 1 }
 
hiplexAFHostTable OBJECT-TYPE
    SYNTAX  SEQUENCE OF HiplexAFHostEntry
    ACCESS  not-accessible
    STATUS  mandatory
    DESCRIPTION
           "The table of host in the availability cluster"
    ::= { hiplexAFHostInfo 2 }
 
hiplexAFHostEntry OBJECT-TYPE
    SYNTAX  HiplexAFHostEntry
    ACCESS  not-accessible
    STATUS  mandatory
    DESCRIPTION
           "entry for each host"
    INDEX   { hiplexAFHostName }
    ::= { hiplexAFHostTable 1 }
 
HiplexAFHostEntry ::=
    SEQUENCE {
        hiplexAFHostName
        DisplayString,
        hiplexAFHostEventId
        INTEGER,
        hiplexAFHostStateInd
        INTEGER,
        hiplexAFHostOperatorRole
        DisplayString,
        hiplexAFHostHomeCatid
        DisplayString,
        hiplexAFHostSystemId
        INTEGER,
        hiplexAFHostBS2Version
        DisplayString,
        hiplexAFHostImcatInd
        INTEGER,
        hiplexAFHostMasterSlaveInd
        INTEGER,
        hiplexAFHostSnmpAgentStateInd
        INTEGER
    }
 
hiplexAFHostName    OBJECT-TYPE
        SYNTAX  DisplayString
        ACCESS  read-only
        STATUS  mandatory
        DESCRIPTION "BCAM Name of the system"
        ::= { hiplexAFHostEntry 1 }
 
hiplexAFHostEventId     OBJECT-TYPE
        SYNTAX  INTEGER
        {
           no-event                (1),
           termination-requested   (2),
           undefined             (255)
        }
        ACCESS  read-only
        STATUS  mandatory
        DESCRIPTION "Request Indicator for the main procedure"
        ::= { hiplexAFHostEntry 2 }
 
hiplexAFHostStateInd    OBJECT-TYPE
        SYNTAX  INTEGER
        {
           working      (1),
           terminated   (2),
           undefined  (255)
        }
        ACCESS  read-write
        STATUS  mandatory
        DESCRIPTION "State of the main procedure. Indicator for
                partitipation of the host.
                State may only be set to working if it is terminated."
        ::= { hiplexAFHostEntry 3 }
 
hiplexAFHostOperatorRole       OBJECT-TYPE
        SYNTAX  DisplayString
        ACCESS  read-write
        STATUS  mandatory
        DESCRIPTION "Value of parameter Operator-Role of START-XAF command"
        ::= { hiplexAFHostEntry 4 }
 
hiplexAFHostHomeCatid       OBJECT-TYPE
        SYNTAX  DisplayString
        ACCESS  read-only
        STATUS  mandatory
        DESCRIPTION "Home Catalog Id of the system"
        ::= { hiplexAFHostEntry 5 }
 
hiplexAFHostSystemId        OBJECT-TYPE
        SYNTAX  INTEGER
        ACCESS  read-only
        STATUS  mandatory
        DESCRIPTION "SystemId of the system according to the output
                     of the SHOW-SHARED-PUBSET-command"
        ::= { hiplexAFHostEntry 6 }
 
hiplexAFHostBS2Version      OBJECT-TYPE
        SYNTAX  DisplayString
        ACCESS  read-only
        STATUS  mandatory
        DESCRIPTION "Version of BS2000 on the system according to the
                     output of the SHOW-SHARED-PUBSET-command"
        ::= { hiplexAFHostEntry 7 }
 
hiplexAFHostImcatInd    OBJECT-TYPE
        SYNTAX  INTEGER
        {
           check        (1),
           crash        (2),
           excat        (3),
           imcat        (4),
           mchange      (5),
           readerr      (6),
           shutdown     (7),
           wrterr       (8),
           undefined  (255)
        }
        ACCESS  read-only
        STATUS  mandatory
        DESCRIPTION "Sharer State of the host, according to the output
                     of the SHOW-SHARED-PUBSET-command"
        ::= { hiplexAFHostEntry 8 }
 
hiplexAFHostMasterSlaveInd    OBJECT-TYPE
        SYNTAX  INTEGER
        {
           master       (1),
           backup       (2),
           slave        (3),
           undefined  (255)
        }
        ACCESS  read-only
        STATUS  mandatory
        DESCRIPTION "Sharer type of the host"
        ::= { hiplexAFHostEntry 9 }
 
hiplexAFHostSnmpAgentStateInd    OBJECT-TYPE
        SYNTAX  INTEGER
        {
           working      (1),
           not-working  (2),
           undefined  (255)
        }
        ACCESS  read-write
        STATUS  mandatory
        DESCRIPTION "State of the SNMP-Subagent.
                State may be set to not-working if it is working."
        ::= { hiplexAFHostEntry 10 }
 
-- Switch Unit Table
 
hiplexAFSWUTabNum OBJECT-TYPE
    SYNTAX  INTEGER
    ACCESS  read-only
    STATUS  mandatory
    DESCRIPTION
           "number of Switch Units in the availability cluster"
    ::= { hiplexAFSWUInfo 1 }
 
hiplexAFSWUTable OBJECT-TYPE
    SYNTAX  SEQUENCE OF HiplexAFSWUEntry
    ACCESS  not-accessible
    STATUS  mandatory
    DESCRIPTION
           "The table of host in the availability cluster"
    ::= { hiplexAFSWUInfo 2 }
 
hiplexAFSWUEntry    OBJECT-TYPE
    SYNTAX  HiplexAFSWUEntry
    ACCESS  not-accessible
    STATUS  mandatory
    DESCRIPTION
           "entry for each host"
    INDEX   { hiplexAFSWUName }
    ::= { hiplexAFSWUTable 1 }
 
HiplexAFSWUEntry ::=
    SEQUENCE {
        hiplexAFSWUName
        DisplayString,
        hiplexAFSWUCreaTime
--      DateAndTime,
        DisplayString,
        hiplexAFSWUWorkSystem
        DisplayString,
        hiplexAFSWUVirtHost
        DisplayString,
        hiplexAFSWUVirtHostAct
        DisplayString,
        hiplexAFSWUVirtHostDeact
        DisplayString,
        hiplexAFSWUFEPNumber
        INTEGER,
        hiplexAFSWUPubsetNumber
        INTEGER,
        hiplexAFSWUApplicationNumber
        INTEGER
    }
 
hiplexAFSWUName       OBJECT-TYPE
        SYNTAX  DisplayString
        ACCESS  read-only
        STATUS  mandatory
        DESCRIPTION "Name of the switch unit"
    ::= { hiplexAFSWUEntry 1 }
 
hiplexAFSWUCreaTime     OBJECT-TYPE
--      SYNTAX  DateAndTime
        SYNTAX  DisplayString
        ACCESS  read-only
        STATUS  mandatory
        DESCRIPTION "Creation Time of Switch Unit (configuration file)"
    ::= { hiplexAFSWUEntry 2 }
 
hiplexAFSWUWorkSystem    OBJECT-TYPE
        SYNTAX  DisplayString
        ACCESS  read-write
        STATUS  mandatory
        DESCRIPTION "BCAM Name of the system which presently is
                     work system for this switch unit. Changing the
                     value of this object will start a switch procedure."
    ::= { hiplexAFSWUEntry 3 }
 
hiplexAFSWUVirtHost      OBJECT-TYPE
        SYNTAX  DisplayString
        ACCESS  read-only
        STATUS  mandatory
        DESCRIPTION "BCAM Name of the virtual host of the switch unit"
    ::= { hiplexAFSWUEntry 4 }
 
hiplexAFSWUVirtHostAct   OBJECT-TYPE
        SYNTAX  DisplayString
        ACCESS  read-only
        STATUS  mandatory
        DESCRIPTION "Name of the procedure for activating the routes to
                     the virtual host"
    ::= { hiplexAFSWUEntry 5 }
 
hiplexAFSWUVirtHostDeact OBJECT-TYPE
        SYNTAX  DisplayString
        ACCESS  read-only
        STATUS  mandatory
        DESCRIPTION "Name of the procedure for deactivating the routes to
                     the virtual host"
    ::= { hiplexAFSWUEntry 6 }
 
hiplexAFSWUFEPNumber     OBJECT-TYPE
        SYNTAX  INTEGER
        ACCESS  read-only
        STATUS  mandatory
        DESCRIPTION "Number of front end processors"
    ::= { hiplexAFSWUEntry 7 }
 
hiplexAFSWUPubsetNumber     OBJECT-TYPE
        SYNTAX  INTEGER
        ACCESS  read-only
        STATUS  mandatory
        DESCRIPTION "Number of non-shared pubsets used by applications
                     of the switch unit"
    ::= { hiplexAFSWUEntry 8 }
 
hiplexAFSWUApplicationNumber    OBJECT-TYPE
        SYNTAX  INTEGER
        ACCESS  read-only
        STATUS  mandatory
        DESCRIPTION "Number of applications contained in this
                     switch unit"
    ::= { hiplexAFSWUEntry 9 }
 
-- Switch Unit Parameter Table
 
hiplexAFSWUHostParamTable OBJECT-TYPE
    SYNTAX  SEQUENCE OF HiplexAFSWUHostParamEntry
    ACCESS  not-accessible
    STATUS  mandatory
    DESCRIPTION
           "The table of host specific Parameters of Switch Units"
    ::= { hiplexAFSWUHostParamInfo 1 }
 
hiplexAFSWUHostParamEntry OBJECT-TYPE
    SYNTAX  HiplexAFSWUHostParamEntry
    ACCESS  not-accessible
    STATUS  mandatory
    DESCRIPTION
           "entry for each host"
    INDEX   { hiplexAFSWUName, hiplexAFHostName }
    ::= { hiplexAFSWUHostParamTable 1 }
 
HiplexAFSWUHostParamEntry ::=
    SEQUENCE {
        hiplexAFSWUHostParamEventId
        INTEGER,
        hiplexAFSWUHostParamStateInd
        INTEGER,
        hiplexAFSWUHostParamPriority
        INTEGER,
        hiplexAFSWUHostParamOperatorRole
        DisplayString
    }
 
hiplexAFSWUHostParamEventId    OBJECT-TYPE
        SYNTAX  INTEGER
        {
           no-action   (1),
           pass-over   (2),
           take-over   (3),
           terminate   (4),
           undefined (255)
        }
        ACCESS  read-only
        STATUS  mandatory
        DESCRIPTION "Last action of the switch unit on the system"
    ::= { hiplexAFSWUHostParamEntry 1 }
 
hiplexAFSWUHostParamStateInd   OBJECT-TYPE
        SYNTAX  INTEGER
        {
           work           (1),
           standby        (2),
           crashed        (3),
           terminated     (4),
           undefined    (255)
        }
        ACCESS  read-write
        STATUS  mandatory
        DESCRIPTION "State of the Switch Unit. Value terminated may be
                     changed to work or standby"
    ::= { hiplexAFSWUHostParamEntry 2 }
 
hiplexAFSWUHostParamPriority   OBJECT-TYPE
        SYNTAX  INTEGER (1..16)
        ACCESS  read-write
        STATUS  mandatory
        DESCRIPTION "Priority of the host in case of an automatic switch"
    ::= { hiplexAFSWUHostParamEntry 3 }
 
hiplexAFSWUHostParamOperatorRole       OBJECT-TYPE
        SYNTAX  DisplayString
        ACCESS  read-write
        STATUS  mandatory
        DESCRIPTION "Value of parameter Operator-Role of
                     START-SWITCH-UNIT command"
        ::= { hiplexAFSWUHostParamEntry 4 }
 
-- Table of Front End Processors
 
hiplexAFSWUHostFEPTabNum OBJECT-TYPE
    SYNTAX  INTEGER (0..10)
    ACCESS  read-only
    STATUS  mandatory
    DESCRIPTION
           "number of FEP Entries"
    ::= { hiplexAFSWUHostFEPInfo 1 }
 
hiplexAFSWUHostFEPTable OBJECT-TYPE
    SYNTAX  SEQUENCE OF HiplexAFSWUHostFEPEntry
    ACCESS  not-accessible
    STATUS  mandatory
    DESCRIPTION
           "The table of parameters of switch units concerning
            front end processors"
    ::= { hiplexAFSWUHostFEPInfo 2 }
 
hiplexAFSWUHostFEPEntry OBJECT-TYPE
    SYNTAX  HiplexAFSWUHostFEPEntry
    ACCESS  not-accessible
    STATUS  mandatory
    DESCRIPTION
           "Entry describing a relation between a switch units
            and front end processor"
    INDEX   { hiplexAFSWUName , hiplexAFHostName, hiplexAFSWUHostFEPIndex }
    ::= { hiplexAFSWUHostFEPTable 1 }
 
HiplexAFSWUHostFEPEntry ::=
    SEQUENCE {
        hiplexAFSWUHostFEPIndex
        INTEGER,
        hiplexAFSWUHostFEPName
        DisplayString,
        hiplexAFSWUHostFEPPortnumber
        INTEGER
    }
 
hiplexAFSWUHostFEPIndex  OBJECT-TYPE
        SYNTAX  INTEGER (1..10)
        ACCESS  read-only
        STATUS  mandatory
        DESCRIPTION "Index of Front End Processor"
    ::= { hiplexAFSWUHostFEPEntry 1 }
 
hiplexAFSWUHostFEPName   OBJECT-TYPE
        SYNTAX  DisplayString
        ACCESS  read-write
        STATUS  mandatory
        DESCRIPTION "BCAM Name of Front End Processor"
    ::= { hiplexAFSWUHostFEPEntry 2 }
 
hiplexAFSWUHostFEPPortnumber  OBJECT-TYPE
        SYNTAX  INTEGER
        ACCESS  read-write
        STATUS  mandatory
        DESCRIPTION "Number of Port used for the System"
    ::= { hiplexAFSWUHostFEPEntry 3 }
 
-- Table of Data Volumes
 
hiplexAFSWUVolumeTabNum OBJECT-TYPE
    SYNTAX  INTEGER
    ACCESS  read-only
    STATUS  mandatory
    DESCRIPTION
           "number of data volumes "
    ::= { hiplexAFSWUVolumeInfo 1 }
 
hiplexAFSWUVolumeTable OBJECT-TYPE
    SYNTAX  SEQUENCE OF HiplexAFSWUVolumeEntry
    ACCESS  not-accessible
    STATUS  mandatory
    DESCRIPTION
           "Table of data volumes"
    ::= { hiplexAFSWUVolumeInfo 2 }
 
hiplexAFSWUVolumeEntry OBJECT-TYPE
    SYNTAX  HiplexAFSWUVolumeEntry
    ACCESS  not-accessible
    STATUS  mandatory
    DESCRIPTION
           "Entry for each data volume"
    INDEX   { hiplexAFSWUName, hiplexAFSWUVolumeName }
    ::= { hiplexAFSWUVolumeTable 1 }
 
HiplexAFSWUVolumeEntry ::=
    SEQUENCE {
        hiplexAFSWUVolumeName
        DisplayString,
        hiplexAFSWUVolumeTypeName
        DisplayString,
        hiplexAFSWUVolumeType
        INTEGER,
        hiplexAFSWUVolumeImportProc
        DisplayString,
        hiplexAFSWUVolumeExportProc
        DisplayString
    }
 
hiplexAFSWUVolumeName  OBJECT-TYPE
        SYNTAX  DisplayString
        ACCESS  read-only
        STATUS  mandatory
        DESCRIPTION "Name of Data Volume"
    ::= { hiplexAFSWUVolumeEntry 1 }
 
hiplexAFSWUVolumeTypeName  OBJECT-TYPE
        SYNTAX  DisplayString
        ACCESS  read-only
        STATUS  mandatory
        DESCRIPTION "Name of Data Volumetype "
    ::= { hiplexAFSWUVolumeEntry 2 }
 
hiplexAFSWUVolumeType  OBJECT-TYPE
        SYNTAX  INTEGER
        {
           shared-pubset     (1),
           pubset            (2),
           private-disk      (3),
           by-user           (4),
           undefined       (255)
        }
        ACCESS  read-only
        STATUS  mandatory
        DESCRIPTION "Type of data volume"
    ::= { hiplexAFSWUVolumeEntry 3 }
 
hiplexAFSWUVolumeImportProc  OBJECT-TYPE
        SYNTAX  DisplayString
        ACCESS  read-only
        STATUS  mandatory
        DESCRIPTION "Name of procedure importing data volume"
    ::= { hiplexAFSWUVolumeEntry 4 }
 
hiplexAFSWUVolumeExportProc   OBJECT-TYPE
        SYNTAX  DisplayString
        ACCESS  read-only
        STATUS  mandatory
        DESCRIPTION "Name of procedure exporting data volume"
    ::= { hiplexAFSWUVolumeEntry 5 }
 
 
-- Application Table
 
hiplexAFSWUApplicationTabNum OBJECT-TYPE
    SYNTAX  INTEGER
    ACCESS  read-only
    STATUS  mandatory
    DESCRIPTION
           "Number of applications"
    ::= { hiplexAFSWUApplicationInfo 1 }
 
hiplexAFSWUApplicationTable OBJECT-TYPE
    SYNTAX  SEQUENCE OF HiplexAFSWUApplicationEntry
    ACCESS  not-accessible
    STATUS  mandatory
    DESCRIPTION
           "Table of applications"
    ::= { hiplexAFSWUApplicationInfo 2 }
 
hiplexAFSWUApplicationEntry OBJECT-TYPE
    SYNTAX  HiplexAFSWUApplicationEntry
    ACCESS  not-accessible
    STATUS  mandatory
    DESCRIPTION
           "entry for each application"
    INDEX   { hiplexAFSWUName, hiplexAFSWUApplicationMonJVName }
    ::= { hiplexAFSWUApplicationTable 1 }
 
HiplexAFSWUApplicationEntry ::=
    SEQUENCE {
        hiplexAFSWUApplicationMonJVName
        DisplayString,
        hiplexAFSWUApplicationType
        INTEGER,
        hiplexAFSWUApplicationStartProc
        DisplayString,
        hiplexAFSWUApplicationStopProc
        DisplayString
    }
 
hiplexAFSWUApplicationMonJVName  OBJECT-TYPE
        SYNTAX  DisplayString
        ACCESS  read-only
        STATUS  mandatory
        DESCRIPTION "Name of jobvariable monitoring application"
    ::= { hiplexAFSWUApplicationEntry 1 }
 
hiplexAFSWUApplicationType  OBJECT-TYPE
        SYNTAX  INTEGER
        {
        job          (1),
        utm          (2),
        bcam         (3),
        by-user      (4),
        undefined  (255)
        }
        ACCESS  read-only
        STATUS  mandatory
        DESCRIPTION "Application type"
    ::= { hiplexAFSWUApplicationEntry 2 }
 
hiplexAFSWUApplicationStartProc  OBJECT-TYPE
        SYNTAX  DisplayString
        ACCESS  read-only
        STATUS  mandatory
        DESCRIPTION "Procedure used to start the application"
    ::= { hiplexAFSWUApplicationEntry 3 }
 
hiplexAFSWUApplicationStopProc  OBJECT-TYPE
        SYNTAX  DisplayString
        ACCESS  read-only
        STATUS  mandatory
        DESCRIPTION "Procedure used to stop the application"
    ::= { hiplexAFSWUApplicationEntry 4 }
 
 
-- Trap Filter Table
 
hiplexAFTrapFilterTable OBJECT-TYPE
    SYNTAX  SEQUENCE OF HiplexAFTrapFilterEntry
    ACCESS  not-accessible
    STATUS  mandatory
    DESCRIPTION
           "This double-indexed table is a matrix containing an indicator
            for each pair (host1,host2). A HIPLEX-AF subagent residing
            on host1 will send traps concerning events of host2 only if
            the indicator has value yes."
    ::= { hiplexAFObjects 20 }
 
hiplexAFTrapFilterEntry OBJECT-TYPE
    SYNTAX  HiplexAFTrapFilterEntry
    ACCESS  not-accessible
    STATUS  mandatory
    DESCRIPTION
           "Entry for each pair (host1,host2)"
    INDEX  { hiplexAFTrapFilterHost1Name , hiplexAFTrapFilterHost2Name}
    ::= { hiplexAFTrapFilterTable 1 }
 
HiplexAFTrapFilterEntry ::=
    SEQUENCE {
        hiplexAFTrapFilterHost1Name
        DisplayString,
        hiplexAFTrapFilterHost2Name
        DisplayString,
        hiplexAFTrapFilterTrapSendInd
        INTEGER
    }
 
hiplexAFTrapFilterHost1Name    OBJECT-TYPE
        SYNTAX  DisplayString
        ACCESS  read-only
        STATUS  mandatory
        DESCRIPTION "BCAM Name of the system where HIPLEX-AF
                     subagent is running"
        ::= { hiplexAFTrapFilterEntry 1 }
 
hiplexAFTrapFilterHost2Name    OBJECT-TYPE
        SYNTAX  DisplayString
        ACCESS  read-only
        STATUS  mandatory
        DESCRIPTION "BCAM Name of the system in the HIPLEX-AF cluster."
        ::= { hiplexAFTrapFilterEntry 2 }
 
hiplexAFTrapFilterTrapSendInd     OBJECT-TYPE
        SYNTAX  INTEGER
        {
           yes                 (1),
           no                  (2),
           undefined           (255)
        }
        ACCESS  read-write
        STATUS  mandatory
        DESCRIPTION "yes: traps will be sent.
                     no:  no traps will be sent."
        ::= { hiplexAFTrapFilterEntry 3 }
 
--
-- Definition of Traps
--
 
hiplexAFTraps              OBJECT IDENTIFIER ::= { sniHiplexAF 2 }
 
hiplexAFStart TRAP-TYPE
    ENTERPRISE  hiplexAFTraps
    VARIABLES   { hiplexAFHostName }
    DESCRIPTION
           "Hiplex AF main procedure has been started."
    ::= 301
 
hiplexAFSWUStart TRAP-TYPE
    ENTERPRISE  hiplexAFTraps
    VARIABLES   { hiplexAFSWUHostParamStateInd, hiplexAFSWUName, hiplexAFHostName }
    DESCRIPTION
           "Switch unit procedure has been started."
    ::= 302
 
hiplexAFStop TRAP-TYPE
    ENTERPRISE  hiplexAFTraps
    VARIABLES   { hiplexAFTermHost }
    DESCRIPTION
           "Termination of Hiplex AF has been started."
    ::= 303
 
hiplexAFCrash TRAP-TYPE
    ENTERPRISE  hiplexAFTraps
    VARIABLES   { hiplexAFHostName }
    DESCRIPTION
           "A system has been terminated abnormally."
    ::= 304
 
hiplexAFSWUAppStop TRAP-TYPE
    ENTERPRISE  hiplexAFTraps
    VARIABLES   { hiplexAFSWUHostParamStateInd, hiplexAFSWUName, hiplexAFHostName }
    DESCRIPTION
           "The applications of a switch unit will be stopped."
    ::= 305
 
hiplexAFSWUAppStart TRAP-TYPE
    ENTERPRISE  hiplexAFTraps
    VARIABLES   { hiplexAFSWUHostParamStateInd, hiplexAFSWUName, hiplexAFHostName }
    DESCRIPTION
           "The applications of a switch unit will be started."
    ::= 306
 
hiplexAFSWUStop TRAP-TYPE
    ENTERPRISE  hiplexAFTraps
    VARIABLES   { hiplexAFSWUHostParamStateInd, hiplexAFSWUName, hiplexAFHostName }
    DESCRIPTION
           "Switch unit procedure has been stopped."
    ::= 307
 
END
