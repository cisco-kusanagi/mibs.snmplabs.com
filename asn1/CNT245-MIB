--
--
--          Computer Network Technology, Corp.
--              6000 Nathan Lane North 
--              Plymouth, Minnesota  55442   
--
--                phone:  (763) 268-6000
--                  fax:  (763) 268-6800
--              support:  1-800-NET-TECH
--                email:  cnt.com
--
--      MIB Version:     1.8
--      Product Family:  CNT Zeus(2) Subagent(4) Compression(5)
--
-- +------------+ if you change this mib, you increment the version number.
-- | Attention! | Also, this MIB is supported the by compression aggregation
-- +------------+ agent, and that agent must also be compiled with this mib
--                version.
--                Also, the zap SNMP manager (/zeus/io/snmp_manager) supports
--                this mib so it must be updated to reflect any changes.
-- Version 1.7: Add CompressionRatio and DecompressionRatio.
-- Version 1.8: Change Syntax to compile with SimpleSoft strict mode.


CNT245-MIB DEFINITIONS ::= BEGIN

        IMPORTS
                enterprises
                        FROM RFC1155-SMI
                Integer32, MODULE-IDENTITY, Counter64
                        FROM SNMPv2-SMI
                OBJECT-TYPE
                        FROM RFC-1212;

	cnt2Compression MODULE-IDENTITY
		LAST-UPDATED "0110011200Z"
		ORGANIZATION "Computer Network Technology Corporation"
		CONTACT-INFO "<intentionaly left out>"
		DESCRIPTION  "This defines the CNT Compression Engine MIB"
		::= { enterprises cnt(333) cnt2(2) cnt2Subagent(4) 5 }

        --
        -- Using the MODULE-IDENTITY above replaces the use of individual
        -- object identifications.
        --
        -- cnt             OBJECT IDENTIFIER ::= { enterprises 333 }
        -- cnt2            OBJECT IDENTIFIER ::= { cnt 2 }
        -- cnt2Subagent    OBJECT IDENTIFIER ::= { cnt2 4 }
        -- cnt2Compression OBJECT IDENTIFIER ::= { cnt2Subagent 5 }


        -- Slot Compression Group

            cnt2CompressionTable OBJECT-TYPE
                SYNTAX  SEQUENCE OF Cnt2CompressionEntry
                MAX-ACCESS  not-accessible
                STATUS  current
                DESCRIPTION
                        "A list of compression/decompression engines
                        on this system."
                ::= { cnt2Compression 1 }

            cnt2CompressionEntry OBJECT-TYPE
                SYNTAX  Cnt2CompressionEntry
                MAX-ACCESS  not-accessible
                STATUS  current
                DESCRIPTION
                        "An instance of a compression/decompression."
                INDEX    { cnt2CompressionSlotIndex, cnt2CompressionIndex }
                ::= { cnt2CompressionTable 1 }

            Cnt2CompressionEntry ::=
                SEQUENCE {
                    cnt2CompressionSlotIndex
                        Integer32,
                    cnt2CompressionIndex
                        Integer32,
                    cnt2BytesToCompress
                        Counter64,
                    cnt2CompressedBytes
                        Counter64,
                    cnt2BytesToDecompress
                        Counter64,
                    cnt2DecompressedBytes
                        Counter64
                }


            cnt2CompressionSlotIndex OBJECT-TYPE
                SYNTAX  Integer32
                MAX-ACCESS  read-only
                STATUS  current
                DESCRIPTION
                        "The slot number where this compression/
                         decompression was done.  This index
                         matches cnt2SlotIndex."
                ::= { cnt2CompressionEntry 1 }

            cnt2CompressionIndex OBJECT-TYPE
                SYNTAX  Integer32
                MAX-ACCESS  read-only
                STATUS  current
                DESCRIPTION
                        "The relative instance of the
                        compression/decompression engine for this
                        slot.  This index is always 1."
                ::= { cnt2CompressionEntry 2 }

            cnt2BytesToCompress OBJECT-TYPE
                SYNTAX  Counter64
                MAX-ACCESS  read-only
                STATUS  current
                DESCRIPTION
                        "The number of bytes submitted to the
                        engine for compression.  This value will
                        include all bytes submitted whether or not
                        compression was successful.  This value
                        will always be equal or larger than
                        cnt2CompressedBytes."
                ::= { cnt2CompressionEntry 3 }

            cnt2CompressedBytes OBJECT-TYPE
                SYNTAX  Counter64
                MAX-ACCESS  read-only
                STATUS  current
                DESCRIPTION
                        "The number of bytes received from the
                        engine after compression.  This value
                        will include all of the bytes received
                        from the engine whether or not compres-
                        sion was successful, since the engine
                        returns the initial size in any unsucces-
                        sful attempt at compression.  This value
                        will be equal or smaller than
                        cnt2BytesToCompress."
                ::= { cnt2CompressionEntry 4 }

            cnt2BytesToDecompress OBJECT-TYPE
                SYNTAX  Counter64
                MAX-ACCESS  read-only
                STATUS  current
                DESCRIPTION
                        "The number of bytes submitted to the
                        engine for decompression.  This value will
                        include all bytes submitted whether or not
                        decompression was successful.  This value
                        will always be equal or smaller than
                        cnt2DecompressedBytes."
                ::= { cnt2CompressionEntry 5 }

            cnt2DecompressedBytes OBJECT-TYPE
                SYNTAX  Counter64
                MAX-ACCESS  read-only
                STATUS  current
                DESCRIPTION
                        "The number of bytes received from the
                        engine after decompression.  This value
                        will include all of the bytes received
                        from the engine whether or not decompres-
                        sion was successful, since the engine
                        returns the initial size in any unsucces-
                        sful attempt at decompression.  This value
                        will be equal or larger than
                        cnt2BytesToDecompress."
                ::= { cnt2CompressionEntry 6 }


        -- the CNT I/F Compression Group

            cnt2ifCompressionNumber OBJECT-TYPE
                SYNTAX  Integer32
                MAX-ACCESS  read-only
                STATUS  current
                DESCRIPTION
                        "The number of interfaces using compression/
                        decompression in this system."
                ::= { cnt2Compression 2 }

            cnt2ifCompressionTable OBJECT-TYPE
                SYNTAX  SEQUENCE OF Cnt2ifCompressionEntry
                MAX-ACCESS  not-accessible
                STATUS  current
                DESCRIPTION
                        "A list of interface entries using compression/
                        decompression in this system.  The number of
                        entries is given by cnt2ifCompressionNumber."
                ::= { cnt2Compression 3 }

            cnt2ifCompressionEntry OBJECT-TYPE
                SYNTAX  Cnt2ifCompressionEntry
                MAX-ACCESS  not-accessible
                STATUS  current
                DESCRIPTION
                        "An interface entry using compression/
                        decompression."
                INDEX    { cnt2ifCompressionSlotIndex, cnt2ifCompressionIndex }
                ::= { cnt2ifCompressionTable 1 }

            Cnt2ifCompressionEntry ::=
                SEQUENCE {
                    cnt2ifCompressionSlotIndex
                        Integer32,
                    cnt2ifCompressionIndex
                        Integer32,
                    cnt2ifCompressedOctets
                        Counter64,
                    cnt2ifCompressionRatio
                        Integer32
                }

            cnt2ifCompressionSlotIndex OBJECT-TYPE
                SYNTAX  Integer32
                MAX-ACCESS  read-only
                STATUS  current
                DESCRIPTION
                        "The slot number where this compression
                         was done.  This index matches cnt2IfSlotIndex."
                ::= { cnt2ifCompressionEntry 1 }

            cnt2ifCompressionIndex OBJECT-TYPE
                SYNTAX  Integer32
                MAX-ACCESS  read-only
                STATUS  current
                DESCRIPTION
                        "The local interface index on which this
                        compression was done.  This index matches
                        cnt2IfIndex."
                ::= { cnt2ifCompressionEntry 2 }

            cnt2ifCompressedOctets OBJECT-TYPE
                SYNTAX  Counter64
                MAX-ACCESS  read-only
                STATUS  current
                DESCRIPTION
                        "The number of bytes that were compressed
                        out of the transmitted data stream.  To
                        calculate the compression ratio for trans-
                        mitted data, the following calculation
                        would be used:

                            ifOutOctets + cnt2ifCompressedOctets
                            ------------------------------------
                                         ifOutOctets.

                        to calculate the overall compression for
                        this interface, the following calculation
                        would be used:

                            ifOutOctets + cnt2ifCompressedOctets +
                            cnt2ifDecompressedOctets + ifInOctets
                            --------------------------------------
                                   ifOutOctets + ifInOctets."

                ::= { cnt2ifCompressionEntry 3 }
 
            cnt2ifCompressionRatio OBJECT-TYPE
                SYNTAX  Integer32
                MAX-ACCESS  read-only
                STATUS  current
                DESCRIPTION
                        "The Compression ratio for this index. 
					 	 The value is represent of 1 to xx.xx Compression
						 Ratio. Example: Ratio of 1:15.82 would have this 
						 set to a value of 1582.
						 The internal Calculation is done as:
							100 * (ifOutOctets + cnt2ifCompressedOctets)
							---------------------------------------------
                                         ifOutOctets
						 Then the result is mod by 100 for floating point. 
						 This OID gets created dynamically when there 
						 is a compression circuit active."
                ::= { cnt2ifCompressionEntry 4 }


            cnt2ifDecompressionTable OBJECT-TYPE
                SYNTAX  SEQUENCE OF Cnt2ifDecompressionEntry
                MAX-ACCESS  not-accessible
                STATUS  current
                DESCRIPTION
                        "A list of interface entries using decompression
                        in this system.  The number of entries is given
                        by cnt2ifCompressionNumber."
                ::= { cnt2Compression 4 }

            cnt2ifDecompressionEntry OBJECT-TYPE
                SYNTAX  Cnt2ifDecompressionEntry
                MAX-ACCESS  not-accessible
                STATUS  current
                DESCRIPTION
                        "An interface entry using decompression."
                INDEX    { cnt2ifDecompressionSlotIndex,
                           cnt2ifDecompressionIndex }
                ::= { cnt2ifDecompressionTable 1 }

            Cnt2ifDecompressionEntry ::=
                SEQUENCE {
                    cnt2ifDecompressionSlotIndex
                        Integer32,
                    cnt2ifDecompressionIndex
                        Integer32,
                    cnt2ifDecompressedOctets
                        Counter64,
                    cnt2ifDecompressionRatio
                        Integer32
                }

            cnt2ifDecompressionSlotIndex OBJECT-TYPE
                SYNTAX  Integer32
                MAX-ACCESS  read-only
                STATUS  current
                DESCRIPTION
                        "The slot number where this decompression was
                         done.  This index matches cnt2IfSlotIndex."
                ::= { cnt2ifDecompressionEntry 1 }

            cnt2ifDecompressionIndex OBJECT-TYPE
                SYNTAX  Integer32
                MAX-ACCESS  read-only
                STATUS  current
                DESCRIPTION
                        "The local interface index on which this
                        decompression was done.  This index matches
                        cnt2IfIndex."
                ::= { cnt2ifDecompressionEntry 2 }

            cnt2ifDecompressedOctets OBJECT-TYPE
                SYNTAX  Counter64
                MAX-ACCESS  read-only
                STATUS  current
                DESCRIPTION
                        "The number of bytes that were compressed
                        out of the received data stream.  To
                        calculate the compression ratio for
                        received data, the following calculation
                        would be used:

                            ifInOctets + cnt2ifDeCompressedOctets
                            -------------------------------------
                                         ifInOctets

                        to calculate the overall compression for
                        this interface, the following calculation
                        would be used:

                            ifOutOctets + cnt2ifCompressedOctets +
                            cnt2ifDecompressedOctets + ifInOctets
                            --------------------------------------
                                   ifOutOctets + ifInOctets."

                ::= { cnt2ifDecompressionEntry 3 }

            cnt2ifDecompressionRatio OBJECT-TYPE
                SYNTAX  Integer32
                MAX-ACCESS  read-only
                STATUS  current
                DESCRIPTION
                        "The Decompression ratio for this index. 
					 	 The value is represent 1 to xx.xx decompression
						 Ratio. Example: Ratio of 13.82 :1 would have this 
						 set to a value of 1382.
						 The internal Calculation is done as:
                            100 * (ifInOctets + cnt2ifDeCompressedOctets)
							---------------------------------------------
                                         ifInOctets
						 Then the result is mod by 100 for floating point. 
						 This OID gets created dynamically when there 
						 is a decompression circuit active."
                ::= { cnt2ifDecompressionEntry 4 }

END
