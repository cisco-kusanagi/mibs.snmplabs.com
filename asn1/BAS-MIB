BAS-MIB DEFINITIONS ::= BEGIN

IMPORTS
    MODULE-IDENTITY, enterprises,
    IpAddress, Integer32, OBJECT-TYPE           FROM SNMPv2-SMI
    TEXTUAL-CONVENTION, MacAddress              FROM SNMPv2-TC;

basMIB MODULE-IDENTITY
    LAST-UPDATED "9810071330Z"
    ORGANIZATION "Broadband Access Systems, Inc."
    CONTACT-INFO
		" Tech Support
          Broadband Access Systems, Inc.
          201 Forest Street
          Marlborough, MA 01752
          USA

          508-485-8200
          support@basystems.com"
    DESCRIPTION
        "The MIB module defining the nodes in the Broadband Access
        Systems, Inc. MIB tree."
    ::= { enterprises 3493 }


-- 
-- The Unique product IDs are to be allocated below this node
-- 

basProductId		OBJECT IDENTIFIER ::= { basMIB 1 }

basCudaChassMgr		OBJECT IDENTIFIER ::= { basMIB 4 }
basCuda10100Rs		OBJECT IDENTIFIER ::= { basMIB 5 }
basCuda1000Rs		OBJECT IDENTIFIER ::= { basMIB 6 }
basCudaOC12Rs		OBJECT IDENTIFIER ::= { basMIB 7 }
basCuda10100		OBJECT IDENTIFIER ::= { basMIB 8 }
basCuda1000		OBJECT IDENTIFIER ::= { basMIB 9 }
basCudaOC12		OBJECT IDENTIFIER ::= { basMIB 10 }
basCudaCMTS1		OBJECT IDENTIFIER ::= { basMIB 11 }
basCudaOC3Rs		OBJECT IDENTIFIER ::= { basMIB 12 }
basCudaOC48Rs		OBJECT IDENTIFIER ::= { basMIB 13 }
basCudaOC3		OBJECT IDENTIFIER ::= { basMIB 14 }
basCudaOC48		OBJECT IDENTIFIER ::= { basMIB 15 }

-- 
-- The proprietary MIB groups are to be allocated below this node
-- 

basMibGroup       OBJECT IDENTIFIER ::= { basMIB 2 }
basTrapGroup      OBJECT IDENTIFIER ::= { basMIB 3 }  --

basExtSys         OBJECT IDENTIFIER ::= { basMibGroup 1 }  -- MIB-II system extensions
basExtIf          OBJECT IDENTIFIER ::= { basMibGroup 2 }  -- interface extensions
basExtIp          OBJECT IDENTIFIER ::= { basMibGroup 3 }  -- IP extensions
basExtCmts        OBJECT IDENTIFIER ::= { basMibGroup 4 }  -- CMTS extensions
basFtd            OBJECT IDENTIFIER ::= { basMibGroup 5 }  -- FTD Mib
basRbp            OBJECT IDENTIFIER ::= { basMibGroup 6 }  -- RBP Mib
basAlias          OBJECT IDENTIFIER ::= { basMibGroup 7 }  -- Alias Mib
basExtEvent       OBJECT IDENTIFIER ::= { basMibGroup 8 }  -- Event Extensions
basTopology       OBJECT IDENTIFIER ::= { basMibGroup 9 }  -- Topology Mib
basAccessControl  OBJECT IDENTIFIER ::= { basMibGroup 10 } -- Access Control
basPbrfFilter     OBJECT IDENTIFIER ::= { basMibGroup 11 } -- Policy Based Route Filtering
basCmConfig       OBJECT IDENTIFIER ::= { basMibGroup 12 } -- Cable Modem Configuration
basTrafGen        OBJECT IDENTIFIER ::= { basMibGroup 13 } -- Traffic Generation Configuration
basTrace          OBJECT IDENTIFIER ::= { basMibGroup 14 } -- Trace Logging
basDhcpRelay      OBJECT IDENTIFIER ::= { basMibGroup 15 } -- DHCP Relay
basMcc		  OBJECT IDENTIFIER ::= { basMibGroup 16 } -- MCC
basAnalyzer	  OBJECT IDENTIFIER ::= { basMibGroup 17 } -- Analyzer
basCluster	  OBJECT IDENTIFIER ::= { basMibGroup 18 } -- Analyzer
basRip            OBJECT IDENTIFIER ::= { basMibGroup 19 } -- BAS RIP mib
basSonet          OBJECT IDENTIFIER ::= { basMibGroup 20 } -- POS

basStartup        OBJECT IDENTIFIER ::= { basExtSys 1 }  -- Startup information
basCardInfo       OBJECT IDENTIFIER ::= { basExtSys 2 }  -- Card information
basChassisInfo    OBJECT IDENTIFIER ::= { basExtSys 3 }  -- Chassis information
basProvInfo       OBJECT IDENTIFIER ::= { basExtSys 4 }  -- Provisioning information
basHackedInfo     OBJECT IDENTIFIER ::= { basExtSys 1000 }  -- Card information on the NT systems
basHackedAccessControl  OBJECT IDENTIFIER ::= { basMibGroup 1001 } -- AccessControl on NT

basAliasSnmp      OBJECT IDENTIFIER ::= { basAlias 1 }  -- Alias SNMP MIB
basAliasIp        OBJECT IDENTIFIER ::= { basAlias 2 }  -- Alias IP MIB
basAliasTcp       OBJECT IDENTIFIER ::= { basAlias 3 }  -- Alias TCP MIB
basAliasUdp       OBJECT IDENTIFIER ::= { basAlias 4 }  -- Alias UDP MIB
basAliasCidr      OBJECT IDENTIFIER ::= { basAlias 5 }  -- Alias CIDR MIB
basAliasRip       OBJECT IDENTIFIER ::= { basAlias 6 }  -- Alias RIP MIB
basAliasOspf      OBJECT IDENTIFIER ::= { basAlias 7 }  -- Alias OSPF MIB
basAliasDocsIf    OBJECT IDENTIFIER ::= { basAlias 8 }  -- Alias CMTS RF MIB
basAliasDocsCd    OBJECT IDENTIFIER ::= { basAlias 9 }  -- Alias Cable Device MIB
basAliasCmtsCfg   OBJECT IDENTIFIER ::= { basAlias 10 } -- Alias CMTS extensions MIB

--
-- Policy Based Route Filtering per protocol
--
basPbrfRIP        OBJECT IDENTIFIER ::= { basPbrfFilter 1 }
basPbrfOSPF       OBJECT IDENTIFIER ::= { basPbrfFilter 2 }


BasChassisId ::= TEXTUAL-CONVENTION
    DISPLAY-HINT    "d"
    STATUS          current
    DESCRIPTION
        "A unique value, greater than zero, for each Chassis 
        in the managed Broadband Access System (BAS) Cluster.
        It is recommended that values are assigned contiguously
        starting from 1.  The value for each Chassis must remain 
        constant at least from one re-initialization of the 
        BAS Cluster Manager to the next re-initialization."
    SYNTAX Integer32 (1..128)

BasSlotId ::= TEXTUAL-CONVENTION
    DISPLAY-HINT    "d"
    STATUS          current
    DESCRIPTION
        "A unique value, greater than zero, for each application
        card slot in the managed BAS Chassis.  The value 
        for each slot must remain constant at least from one re-
        initialization of the network management software within
        the card installed in the slot to the next re-initialization."
    SYNTAX Integer32 (1..12)

BasInterfaceId ::= TEXTUAL-CONVENTION
    DISPLAY-HINT    "d"
    STATUS          current
    DESCRIPTION
        "A unique value, greater than zero, for each interface 
        in the managed BAS application card within a chassis slot.
        It is recommended that values are assigned contiguously
        starting from 1.  The value for each interface ID must 
        remain constant at least from one re-initialization of the 
        network management software associated with the interface
        to the next re-initialization. Interface 1 has a special
        meaning, it describes a logical port on the application 
        card within the chassis slot. The specific logical port 
        is specified via another object of syntax BasLogicalPortId."
    SYNTAX Integer32

BasLogicalPortId ::= TEXTUAL-CONVENTION
        DISPLAY-HINT    "d"
    STATUS              current
    DESCRIPTION
        "A unique value, greater than zero, for each logical port
        in the managed BAS application card within a chassis slot.
        It is recommended that values are assigned contiguously
        starting from 1.  The value for each logical port ID must 
        remain constant at least from one re-initialization of the 
        network management software associated with the application 
        card to the next re-initialization. Currently two logical 
        ports are defined, 1 ==> main processor, 2 ==> daughter 
        card processor. 
		 
        The value of an object of this syntax is meaningful only 
        when the associated object type of syntax BasInterfaceId 
        is equal to 1."
    SYNTAX Integer32

BasCardClass ::= TEXTUAL-CONVENTION
    DISPLAY-HINT    "d"
    STATUS          current
    DESCRIPTION
        "A unique value for each class of card in a 
        managed Broadband Access System (BAS) Cluster Chassis.
        The value for each Chassis card class must remain 
        constant at least from one re-initialization of the 
        network management software on the particular card 
        to the next re-initialization."
    SYNTAX INTEGER {
        clusterManager(1),
        routeServer(2),             -- implies a RS with a 10/100 interface
        forwarder(3),               -- implies a FWD with a 10/100 interface
        cmts(4),
	routeServerForwarder(5),    -- obsolete.  Was used by PC test environment.
	cmtsForwarder(6),           -- obsolete.  Was used by PC test environment.
        routeServer10100(7),
        routeServer1000(8),
        routeServerOC12(9),
        forwarder10100(10),
        forwarder1000(11),
        forwarderOC12(12),
        routeServerOC3(13),
        routeServerOC48(14),
        forwarderOC3(15),
        forwarderOC48(16)
    }

BasIfClass ::= TEXTUAL-CONVENTION
    DISPLAY-HINT    "d"
    STATUS          current
    DESCRIPTION
        "A unique value for each interface class in the
        managed BAS application card within a chassis slot."
    SYNTAX INTEGER {
        icl(1),
        ccl(2),
        egress(3)
    }

BasChassisType ::= TEXTUAL-CONVENTION
    DISPLAY-HINT    "d"
    STATUS          current
    DESCRIPTION
        "A unique value for each type of chassis in a 
        managed Broadband Access System (BAS) Cluster.
        The value for each Chassis type must remain 
        constant at least from one re-initialization of the 
        network management software on the particular card 
        to the next re-initialization."
    SYNTAX INTEGER {
        cuda(1)
    }

BasSubnetClass ::= TEXTUAL-CONVENTION
    DISPLAY-HINT    "d"
    STATUS          current
    DESCRIPTION
        "A unique value for each subnet class in the
        DHCP Relay table."
    SYNTAX INTEGER {
        unauthorized(1),
        authorized(2),
        cablemodem(3)
    }
--
-- BAS defined traps
--

basTrapObjects OBJECT IDENTIFIER ::= { basTrapGroup 1 }
basTraps       OBJECT IDENTIFIER ::= { basTrapGroup 2 }

--
-- Objects associated with BAS traps.
--
basTrapChassis OBJECT-TYPE
    SYNTAX      BasChassisId
    MAX-ACCESS  accessible-for-notify
    STATUS      current
    DESCRIPTION
        "Used to identify a chassis."
    ::= { basTrapObjects 1 }

basTrapSlot OBJECT-TYPE
    SYNTAX      BasSlotId
    MAX-ACCESS  accessible-for-notify
    STATUS      current
    DESCRIPTION
        "Used to identify a slot."
    ::= { basTrapObjects 2 }

basTrapIf OBJECT-TYPE
    SYNTAX      BasInterfaceId
    MAX-ACCESS  accessible-for-notify
    STATUS      current
    DESCRIPTION
        "Used to identify an interface."
    ::= { basTrapObjects 3 }

basTrapLPort OBJECT-TYPE
    SYNTAX      BasLogicalPortId
    MAX-ACCESS  accessible-for-notify
    STATUS      current
    DESCRIPTION
        "Used to identify a logical port."
    ::= { basTrapObjects 4 }

basTrapCmtsCmMacAddress OBJECT-TYPE
    SYNTAX      MacAddress
    MAX-ACCESS  accessible-for-notify
    STATUS      current
    DESCRIPTION
        "Used to identify a Cable Modem MacAddress."
    ::= { basTrapObjects 5 }

basTrapCmtsCmIpAddress OBJECT-TYPE
    SYNTAX      IpAddress
    MAX-ACCESS  accessible-for-notify
    STATUS      current
    DESCRIPTION
        "Used to identify a Cable Modem IpAddress."
    ::= { basTrapObjects 6 }

basTrapMgmtOneIpAddress OBJECT-TYPE
    SYNTAX      IpAddress
    MAX-ACCESS  accessible-for-notify
    STATUS      current
    DESCRIPTION
        "IpAddress for management card 1"
    ::= { basTrapObjects 7 }

basTrapMgmtTwoIpAddress OBJECT-TYPE
    SYNTAX      IpAddress
    MAX-ACCESS  accessible-for-notify
    STATUS      current
    DESCRIPTION
        "IpAddress for management card 2"
    ::= { basTrapObjects 8 }

basTrapCraftIpAddress OBJECT-TYPE
    SYNTAX      IpAddress
    MAX-ACCESS  accessible-for-notify
    STATUS      current
    DESCRIPTION
        "IpAddress for the craft port"
    ::= { basTrapObjects 9 }

basTrapIclClass OBJECT-TYPE
    SYNTAX      BasIfClass
    MAX-ACCESS  accessible-for-notify
    STATUS      current
    DESCRIPTION
        "IpAddress for the craft port"
    ::= { basTrapObjects 10 }

basTrapChassisNumber OBJECT-TYPE
    SYNTAX      Integer32
    MAX-ACCESS  accessible-for-notify
    STATUS      current
    DESCRIPTION
        "IpAddress for the craft port"
    ::= { basTrapObjects 11 }

basTrapCmtsCmGwAddress OBJECT-TYPE
    SYNTAX      IpAddress
    MAX-ACCESS  accessible-for-notify
    STATUS      current
    DESCRIPTION
        "Used to identify a Cable Modem Gateway IpAddress."
    ::= { basTrapObjects 12 }

basTrapCardType OBJECT-TYPE
    SYNTAX      BasCardClass
    MAX-ACCESS  accessible-for-notify
    STATUS      current
    DESCRIPTION
        "Used to identify a particular card"
    ::= { basTrapObjects 13 }

basTrapSubnetType OBJECT-TYPE
    SYNTAX      BasSubnetClass
    MAX-ACCESS  accessible-for-notify
    STATUS      current
    DESCRIPTION
        "used to identify a DHCP relay Server type"
    ::= { basTrapObjects 14 }

END
