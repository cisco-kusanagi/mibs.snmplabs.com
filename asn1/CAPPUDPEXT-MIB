CAPPUDPEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, IpAddress,Integer32
			FROM SNMPv2-SMI
		RowStatus,DisplayString
			FROM SNMPv2-TC
		cappUdpExt
			FROM APENT-MIB;

--CAPPUDPEXT MIB

    apCappUdpExtMib MODULE-IDENTITY
	   LAST-UPDATED "9707202000Z" -- Wed July 20 20:00:00 EST 1997
	   ORGANIZATION "ArrowPoint Communications Inc."
	   CONTACT-INFO
	   "                Steven Colby
	   Postal:          ArrowPoint Communications Inc.
				  		235 Littleton Road
				  		Westford, Massachusetts 01886
	   Tel:             +1 508 692 5875
	   E-Mail:          mibsupport@arrowpoint.com"
       DESCRIPTION
	  "The MIB module used to describe the ArrowPoint Communications
	  logging functionality"
      ::= { cappUdpExt 1}


apCappUdpState OBJECT-TYPE
	SYNTAX			INTEGER {
								disable(0),
								enable(1)
							}
	MAX-ACCESS		read-write
	STATUS			current
	DESCRIPTION
		"This object is responsible for controlling globally whether CAPP-UDP
		 is configured to operate on this system.  When the CAPP-UDP state
		 is set to disabled, no packets may be transmitted or received 
		 through CAPP-UDP."
	::= { cappUdpExt 2}

apCappUdpSecureAll OBJECT-TYPE
	SYNTAX			INTEGER {
								disable(0),
								enable(1)
							}
	MAX-ACCESS		read-write
	STATUS			current
	DESCRIPTION
		"This object is responsible for controlling globally whether non-
         secure CAPP-UDP frames will be received.  When 'enabled', all frames
         that are non-secure will be dropped.  Dropped frames can be observed
         via the apCappUdpDropCount"
	::= { cappUdpExt 3}

apCappUdpPort OBJECT-TYPE
	SYNTAX			Integer32
	MAX-ACCESS		read-write
	STATUS			current
	DESCRIPTION
		"This object contains the port number used by CAPP-UDP for 
         frame reception"
	DEFVAL { 5002 }
	::= { cappUdpExt 4}


apCappUdpDropFrames OBJECT-TYPE
	SYNTAX			Integer32
	MAX-ACCESS		read-only
	STATUS			current
	DESCRIPTION
		"This object contains a count of the number of CAPP-UDP frames that
         we dropped due to reception filtering. Reception filtering includes 
         malformed frames & improper security settings."
	::= { cappUdpExt 5}

apCappUdpReceiveFrames OBJECT-TYPE
	SYNTAX			Integer32
	MAX-ACCESS		read-only
	STATUS			current
	DESCRIPTION
		"This object contains a count of the number of CAPP-UDP frames that
         were successfully received."
	::= { cappUdpExt 6}

apCappUdpTransmitFrames OBJECT-TYPE
	SYNTAX			Integer32
	MAX-ACCESS		read-only
	STATUS			current
	DESCRIPTION
		"This object contains a count of the number of CAPP-UDP frames that
         were successfully transmitted."
	::= { cappUdpExt 7}

apCappUdpDropBytes OBJECT-TYPE
	SYNTAX			Integer32
	MAX-ACCESS		read-only
	STATUS			current
	DESCRIPTION
		"This object contains a count of the number of CAPP-UDP bytes that
         we dropped due to reception filtering. Reception filtering includes 
         malformed frames & improper security settings."
	::= { cappUdpExt 8}

apCappUdpReceiveBytes OBJECT-TYPE
	SYNTAX			Integer32
	MAX-ACCESS		read-only
	STATUS			current
	DESCRIPTION
		"This object contains a count of the number of CAPP-UDP bytes that
         were successfully received."
	::= { cappUdpExt 9}

apCappUdpTransmitBytes OBJECT-TYPE
	SYNTAX			Integer32
	MAX-ACCESS		read-only
	STATUS			current
	DESCRIPTION
		"This object contains a count of the number of CAPP-UDP bytes that
         were successfully transmitted."
	::= { cappUdpExt 10}

apCappUdpOptionsTable OBJECT-TYPE
	SYNTAX          SEQUENCE OF APCappUdpOptionsEntry
	MAX-ACCESS      not-accessible
	STATUS          current
	DESCRIPTION
		"The CAPP-UDP security options table"
	::= { cappUdpExt 11}

apCappUdpOptionsEntry OBJECT-TYPE
	SYNTAX          APCappUdpOptionsEntry
	MAX-ACCESS      not-accessible
	STATUS          current
	DESCRIPTION
		"A row in the CAPP-UDP security options table"
	INDEX   { apCappUdpOptionsIpAddress }
	::= { apCappUdpOptionsTable 1 }

APCappUdpOptionsEntry ::= SEQUENCE {
		apCappUdpOptionsIpAddress     IpAddress,
		apCappUdpOptionsType		  INTEGER,
		apCappUdpOptionsSecret		  DisplayString,
		apCappUdpOptionsStatus		  RowStatus
}

apCappUdpOptionsIpAddress OBJECT-TYPE
	SYNTAX          IpAddress
    MAX-ACCESS      read-create
	STATUS          current
	DESCRIPTION     
			"The ip address of this CAPP-UDP security option entry"
	::= { apCappUdpOptionsEntry 1}

apCappUdpOptionsType OBJECT-TYPE
	SYNTAX			INTEGER {
							  encrypt-none(0),
							  encrypt-md5(1)
							}
	MAX-ACCESS		read-create
	STATUS			current
	DESCRIPTION
		"The type of options configured for this row"
	::= { apCappUdpOptionsEntry 2 }

apCappUdpOptionsSecret OBJECT-TYPE
	SYNTAX          DisplayString (SIZE(1..31))
	MAX-ACCESS      read-create
	STATUS          current
	DESCRIPTION      
		"The secret associated with the options entry.  This object will not
		 return the secret, for security considerations."
	::= {apCappUdpOptionsEntry 3}


apCappUdpOptionsStatus OBJECT-TYPE
	SYNTAX          RowStatus
	MAX-ACCESS      read-create
	STATUS          current
	DESCRIPTION      
		"The status object for this row"
	::= {apCappUdpOptionsEntry 4}

END
