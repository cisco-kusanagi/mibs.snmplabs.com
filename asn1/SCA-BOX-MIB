SCA-BOX-MIB DEFINITIONS ::= BEGIN

-- Copyright (C) 1997 Intel Corporation. All rights reserved.
--
-- Intel Box MIB, 11-04-1997
--
-- Change History:
-- <date> <change>
--


IMPORTS
	TRAP-TYPE FROM RFC-1215
        IpAddress       FROM RFC1155-SMI
        DisplayString   FROM RFC1213-MIB
        scanet          FROM SCANET-MIB
        OBJECT-TYPE     FROM RFC-1212;



        box               OBJECT IDENTIFIER ::= { scanet 3 }
        enclosure         OBJECT IDENTIFIER ::= { box 1 }
        boards            OBJECT IDENTIFIER ::= { box 2 }

        --
        -- box.enclosure part
        --

        led  OBJECT-TYPE                -- Leds at front panel
                SYNTAX  OCTET STRING -- (SIZE (0..255))
                ACCESS  read-only
                STATUS  mandatory
                DESCRIPTION
                       "ts-xxxx
                        0 : red
                            off(0),red(1)
                        1 : green
                            off(0),green(2)

                        cs-xxxx
                        0 : fault
                            off(0),red(1)
                        1 : master
                            off(0),green(2)
                        2 : test1
                            off(0),yellow(4)
                        3 : test2
                            off(0),yellow(4)
                        4 : test3
                            off(0),yellow(4)
                        5 : test4
                            off(0),yellow(4)
                        6 : rx/tx
                            off(0),green(2)

                        se-xxxx
                        0 : fault
                            off(0),red(1)
                        1 : power
                            off(0),green(2)
                        2 : status1
                            off(0),red(1),green(2),yellow(4)
                        3 : status2
                            off(0),red(1),green(2),yellow(4)
                        4 : status3
                            off(0),red(1),green(2),yellow(4)
                        5 : status4
                             off(0),red(1),green(2),yellow(4)
                        6 : status5
                            off(0),red(1),green(2),yellow(4)

                        Note. Lower 3 bits indicates off/color (off(0),red(1),
                        green(2),yellow(4)), Higher 5 bits reserved for
                        flash frequency."
               ::= { enclosure 1 }

        fan  OBJECT-TYPE
                SYNTAX INTEGER {                -- FanFailureBits
--                      ok(0),
                        fanFailure(1)
                }
                ACCESS  read-only
                STATUS  mandatory
                DESCRIPTION
                        "If this object returns 1 then a Fan has failed."
                ::= { enclosure 2 }

        power  OBJECT-TYPE
                SYNTAX INTEGER {                -- PowerFailureBits
--                      ok(0),
                        power1Failure(1),
                        power2Failure(2),
                        power3Failure(4),
                        power4Failure(8),
                        power5Failure(16),
                        power6Failure(32)
                }
                ACCESS  read-only
                STATUS  mandatory
                DESCRIPTION
                        "If this object returns a non-zero value then one
                         or more power supplies have failed."
                ::= { enclosure 3 }

        slots OBJECT-TYPE
                SYNTAX INTEGER {
--                        none(0),                 ts-xxxx, pc-xxxx, cs-xxxx
                          slot-2(2),            -- se-02xx
                          slot-5(5),            -- se-05xx or cs-xxxx(brdInfoTable)
                          slot-14(14),          -- se-14xx
                          slot-17(17)           -- se-17xx
                          }
                ACCESS  read-only
                STATUS  mandatory               -- mandatory for se-xxxx
                DESCRIPTION
                        "The number of slots in the enclosure."
                ::= { enclosure 4 }

        slotmap OBJECT-TYPE
               SYNTAX OCTET STRING
               ACCESS  read-only
               STATUS  mandatory
               DESCRIPTION
                      "A bitmap of the slots in which a card is present.
                       Setting bit0 to 1 indicates that a card is present
                       in slot 1, and so on."
               ::= { enclosure 5 }

        temperature OBJECT-TYPE
               SYNTAX INTEGER {
--                      ok(0),
                        temperatureFailure(1)
                        }
                ACCESS  read-only
               STATUS  mandatory
               DESCRIPTION
                        "If this object returns 1 then a temperature sensor
                         has detected an excessive temperature in the enclosure."
               ::= { enclosure 6 }

        fanNo OBJECT-TYPE
               SYNTAX INTEGER
               ACCESS  read-only
               STATUS  mandatory
               DESCRIPTION
                      "Total number of fans supported."
               ::= { enclosure 7 }

        powerNo OBJECT-TYPE
               SYNTAX INTEGER
               ACCESS  read-only
               STATUS  mandatory
               DESCRIPTION
                      "Total number of power supplies supported."
               ::= { enclosure 8 }

        temperatureNo OBJECT-TYPE
               SYNTAX INTEGER {
--                      no(0),
                        yes(1)
               }
               ACCESS  read-only
               STATUS  mandatory
               DESCRIPTION
                      "A return value of 1 indicates that temperature sensors
                       are supported in the enclosure."
               ::= { enclosure 9 }

        fanPresent  OBJECT-TYPE
               SYNTAX INTEGER
               ACCESS  read-only
               STATUS  mandatory
               DESCRIPTION
                      "A bitmask of the fans that are present.
                       Bit0 refers to fan 1, bit 1 to fan 2, etc."
               ::= { enclosure 10 }

        powerPresent  OBJECT-TYPE
               SYNTAX INTEGER
               ACCESS  read-only
               STATUS  mandatory
               DESCRIPTION
                      "A bitmask of the power supples that are present.
                       Bit0 refers to power supply 1, bit 1 to power supply 2, etc."
               ::= { enclosure 11 }

        temperaturePresent OBJECT-TYPE
               SYNTAX INTEGER {
--                      no(0),
                        yes(1)
                }
               ACCESS  read-only
               STATUS  mandatory
               DESCRIPTION
                      " A return value of 1 indicates that temperature sensors
                        are present in the enclosure."
               ::= { enclosure 12 }

        psuFail  OBJECT-TYPE
                 SYNTAX INTEGER {                -- psuFailureEnum
                        psu1Failure(1),
                        psu2Failure(2),
                        psu3Failure(3),
                        psu4Failure(4),
                        psu5Failure(5),
                        psu6Failure(6)
                }
                ACCESS  not-accessible
                STATUS  mandatory
                DESCRIPTION
                        "This object returns a non-zero value in a trap
                         according to the power supply number when a
                         power supply have failed."
                ::= { enclosure 13 }

        slotmapFail  OBJECT-TYPE
                SYNTAX INTEGER          -- slot number
                ACCESS  not-accessible
                STATUS  mandatory
                DESCRIPTION
                        "This object returns a non-zero value in a trap
                         according to the slot number when a card
                         is enabled or disabled in the system center"
                ::= { enclosure 14 }

        --
        -- Board Information Table
        --
        brdInfoTable OBJECT-TYPE
                SYNTAX  SEQUENCE OF BrdInfoEntry
                ACCESS  not-accessible
                STATUS  mandatory               -- mandatory for se-xxxx
                ::= { boards 1 }

                brdInfoEntry OBJECT-TYPE
                        SYNTAX  BrdInfoEntry
                        ACCESS  not-accessible
                        STATUS  mandatory
                        DESCRIPTION "Info from 32 bytes standard memory area."
                        INDEX   { brdNumber1 }
                        ::= { brdInfoTable 1 }

                BrdInfoEntry ::= SEQUENCE {
                        brdNumber1    INTEGER,
                        cardType      INTEGER,
                        pcbRevision   INTEGER,
                        macAddress    OCTET STRING,
                        driverSeq     INTEGER,
                        product       DisplayString,
                        serialNumber  DisplayString,
                        masterSlave   INTEGER,
                        ram           INTEGER,
                        shram         INTEGER,
                        eprom         INTEGER,
                        e2prom        INTEGER,
                        flashprom     INTEGER,
                        spec0         OCTET STRING,
                        spec1         OCTET STRING,
                        spec2         OCTET STRING,
                        spec3         OCTET STRING,
                        ipAddr        IpAddress,        -- ip address and nsap needed to
                        nsap          OCTET STRING      -- go to next SNMP-agent in ENS
                }

                brdNumber1 OBJECT-TYPE
                         SYNTAX  INTEGER
                        ACCESS  read-only
                        STATUS  mandatory
                        DESCRIPTION "Board Sequence number in enclosure (= slot number)"
                        ::= { brdInfoEntry 1 }

                cardType OBJECT-TYPE
                        SYNTAX  INTEGER
                        ACCESS  read-only
                        STATUS  mandatory
                        DESCRIPTION "Unique 16 bit card type
                        This ID is used for unique sw identification of the card.
                        The list of possible return values is company private."
                        ::= { brdInfoEntry 2 }

                pcbRevision OBJECT-TYPE
                        SYNTAX  INTEGER
                        ACCESS  read-only
                        STATUS  mandatory
                        DESCRIPTION "PCB Revision number"
                        ::= { brdInfoEntry 3 }

                macAddress OBJECT-TYPE
                        SYNTAX  OCTET STRING -- (SIZE (6))
                        ACCESS  read-only
                        STATUS  mandatory
                        DESCRIPTION
                                "The Base MAC-Address allocated for MAC Interfaces
                                 on the board."
                        ::= { brdInfoEntry 4 }

                driverSeq OBJECT-TYPE
                        SYNTAX  INTEGER
                        ACCESS  read-only
                        STATUS  mandatory
                        DESCRIPTION "Required driver sequence number (SW)"
                        ::= { brdInfoEntry 5 }

                product OBJECT-TYPE
                        SYNTAX  DisplayString (SIZE (0..255))
                        ACCESS  read-only
                        STATUS  mandatory
                        DESCRIPTION "Product Identification."
                        ::= { brdInfoEntry 6 }

                serialNumber OBJECT-TYPE
                        SYNTAX  OCTET STRING (SIZE (0..255))
                        ACCESS  read-only
                        STATUS  mandatory
                        DESCRIPTION "Production serial number"
                        ::= { brdInfoEntry 7 }

                masterSlave OBJECT-TYPE
                        SYNTAX  INTEGER
                        ACCESS  read-only
                        STATUS  mandatory
                        DESCRIPTION "The board backplane bus properties."
                        ::= { brdInfoEntry 8 }

                ram OBJECT-TYPE
                        SYNTAX  INTEGER
                        ACCESS  read-only
                        STATUS  mandatory
                        ::= { brdInfoEntry 9 }

                shram OBJECT-TYPE
                         SYNTAX  INTEGER
                        ACCESS  read-only
                        STATUS  mandatory
                        ::= { brdInfoEntry 10 }

                eprom OBJECT-TYPE
                        SYNTAX  INTEGER
                        ACCESS  read-only
                        STATUS  mandatory
                        ::= { brdInfoEntry 11 }

                e2prom OBJECT-TYPE
                        SYNTAX  INTEGER
                        ACCESS  read-only
                        STATUS  mandatory
                        ::= { brdInfoEntry 12 }

                flashprom OBJECT-TYPE
                        SYNTAX  INTEGER
                        ACCESS  read-only
                        STATUS  mandatory
                        ::= { brdInfoEntry 13 }

                spec0 OBJECT-TYPE
                        SYNTAX  OCTET STRING -- (SIZE (0..255))
                        ACCESS  read-only
                        STATUS  mandatory
                        DESCRIPTION "Specific board info
                                The purpose of this BYTE is to indicate special
                                board hw-options. The definition of this byte
                                is board specific.
                                A System Center product with relevant information
                                in this byte have a specifiation in the product
                                manual's."
                        ::= { brdInfoEntry 14 }

                spec1 OBJECT-TYPE
                        SYNTAX  OCTET STRING -- (SIZE (0..255))
                        ACCESS  read-only
                        STATUS  mandatory
                        DESCRIPTION "Specific board info
                                The purpose of this BYTE is to indicate special
                                board hw-options. The definition of this byte
                                is board specific.
                                A System Center product with relevant information
                                in this byte have a specifiation in the product
                                manual's."
                        ::= { brdInfoEntry 15 }

                spec2 OBJECT-TYPE
                        SYNTAX  OCTET STRING -- (SIZE (0..255))
                        ACCESS  read-only
                        STATUS  mandatory
                        DESCRIPTION "Specific board info
                                The purpose of this BYTE is to indicate special
                                board hw-options. The definition of this byte
                                is board specific.
                                A System Center product with relevant information
                                in this byte have a specifiation in the product
                                manual's."
                        ::= { brdInfoEntry 16 }

                spec3 OBJECT-TYPE
                        SYNTAX  OCTET STRING -- (SIZE (0..255))
                        ACCESS  read-only
                        STATUS  mandatory
                         DESCRIPTION "Specific board info
                                The purpose of this BYTE is to indicate special
                                board hw-options. The definition of this byte
                                is board specific.
                                A System Center product with relevant information
                                in this byte have a specifiation in the product
                                manual's."
                        ::= { brdInfoEntry 17 }

                ipAddr OBJECT-TYPE
                        SYNTAX  IpAddress
                        ACCESS  read-only
                        STATUS  mandatory
                        DESCRIPTION "IP Address to Manage Board in this slot"
                        ::= { brdInfoEntry 18 }

                nsap   OBJECT-TYPE
                        SYNTAX  OCTET STRING -- (SIZE (0..255))
                        ACCESS  read-only
                        STATUS  mandatory
                        DESCRIPTION "NSAP to Manage Board in this slot"
                        ::= { brdInfoEntry 19 }



        --
        -- Board Status Table
        --
        brdStatusTable OBJECT-TYPE
                SYNTAX  SEQUENCE OF BrdStatusEntry
                ACCESS  not-accessible
                STATUS  mandatory                       -- mandatory for se-xxxx
                ::= { boards 2 }

                brdStatusEntry OBJECT-TYPE
                        SYNTAX  BrdStatusEntry
                        ACCESS  not-accessible
                        STATUS  mandatory
                        DESCRIPTION "Status information from boards."
                        INDEX   { brdNumber2 }
                        ::= { brdStatusTable 1 }

                BrdStatusEntry ::= SEQUENCE {
                        brdNumber2    INTEGER,
                        brdStatus     INTEGER,
                        brdLed        OCTET STRING
                }

                brdNumber2 OBJECT-TYPE
                        SYNTAX  INTEGER
                        ACCESS  read-only
                        STATUS  mandatory
                        DESCRIPTION "Board Sequence number in enclosure (= slot number)"
                        ::= { brdStatusEntry 1 }

                brdStatus OBJECT-TYPE           -- SC card status byte
                        SYNTAX  INTEGER
                        ACCESS  read-only
                        STATUS  mandatory
                        DESCRIPTION "Board Status byte.

                                bit0    - reserved
                                bit1    Card Failed
                                bit2    - reserved
                                bit3    - reserved
                                bit4    Red component of Status LED (active low)
                                 bit5    Green component of Status LED (active low)
                                bit6    - reserved
                                bit7    - reserved"
                        ::= { brdStatusEntry 2 }

                brdLed OBJECT-TYPE              -- Board led(s)
                        SYNTAX  OCTET STRING    -- (SIZE (0..255))
                        ACCESS  read-only
                        STATUS  mandatory
                        DESCRIPTION
                                "Depends on the card type.

                                 Note. Lower 3 bits indicates off/color (off(0),red(1),
                                 green(2),yellow(4)), Higher 5 bits reserved for
                                 flash frequency."
                        ::= { brdStatusEntry 3 }


        brdPlugTable OBJECT-TYPE
                SYNTAX  SEQUENCE OF BrdPlugEntry
                ACCESS  not-accessible
                STATUS  mandatory
                DESCRIPTION
                        "Table of plugs (and the possibly attached pims) on the board"
                        -- Plugs for other kinds of options should be placed
                        -- in brdOptionTable
                ::= { boards 3 }

                brdPlugEntry OBJECT-TYPE
                        SYNTAX BrdPlugEntry
                        ACCESS not-accessible
                        STATUS mandatory
                        DESCRIPTION "Information about plugs on boards."
                        INDEX   { brdNumber3, brdPlugNumber }
                        ::= { brdPlugTable 1 }

                BrdPlugEntry ::= SEQUENCE {
                        brdNumber3              INTEGER,
                        brdPlugNumber           INTEGER,
                        brdPlugPosition         OCTET STRING,
                        brdPlugStatus           INTEGER,
                        brdPlugType             OCTET STRING,
                        brdPlugPimType          OCTET STRING,
                        brdPlugPimLeds          OCTET STRING,
                        brdPlugPimOptions       OCTET STRING
                }

                brdNumber3 OBJECT-TYPE
                        SYNTAX  INTEGER
                        ACCESS  read-only
                        STATUS  mandatory
                        DESCRIPTION "Board Sequence number in enclosure (= slot number)"
                        ::= { brdPlugEntry 1 }

                brdPlugNumber OBJECT-TYPE
                        SYNTAX  INTEGER
                        ACCESS  read-only
                        STATUS  mandatory
                        DESCRIPTION "Plug Number - used to index plugs on board."
                        ::= { brdPlugEntry 2 }

                brdPlugPosition OBJECT-TYPE
                        SYNTAX OCTET STRING
                        ACCESS read-only
                        STATUS mandatory
                        DESCRIPTION "Position/name of plug on board."
                         ::= { brdPlugEntry 3 }

                brdPlugStatus OBJECT-TYPE
                        SYNTAX INTEGER {
                                notAvailable    (1),
                                available       (2)
                        }
                        ACCESS read-only
                        STATUS mandatory
                        DESCRIPTION "Availability of plug on this hardware revision"
                        ::= { brdPlugEntry 4 }

                brdPlugType     OBJECT-TYPE
                        SYNTAX OCTET STRING
                        ACCESS read-only
                        STATUS mandatory
                        DESCRIPTION
                                "Type of plug"
                                -- Eg: 'WAN Plug', 'T-R LAN plug' etc.
                        ::= { brdPlugEntry 5 }

                brdPlugPimType  OBJECT-TYPE
                        SYNTAX OCTET STRING (SIZE (1..50))
                        ACCESS read-only
                        STATUS mandatory
                        DESCRIPTION
                                "Type of pim inserted in plug"

                                -- String                       Comments
                                -- ======                       ========
                                -- 'None'                       No pim in plug
                                -- 'Unknown'                    No pim or unknown
                                -- 'AUI'
                                -- '10Base2'
                                -- '10Base-T'
                                -- '10Base-X'
                                -- '10Base-FL'
                                -- '10Base-FB'

                                -- 'V.24'
                                -- 'V.35'
                                -- 'V.36'
                                -- 'V.11/X.21'
                                -- 'EIA530'

                                -- 'FDDI Multimode'
                                -- 'FDDI SingleMode'
                                -- 'CDDI 100BaseT'

                                -- Token-Ring related PIMs ??
                        ::= { brdPlugEntry 6 }

                        brdPlugPimLeds  OBJECT-TYPE
                                SYNTAX OCTET STRING
                                ACCESS read-only
                                STATUS mandatory
                                DESCRIPTION
                                        "Status of LEDs on pim in plug"
                                        -- For pims having LEDs a text explaining the use of
                                        -- the octet string should be inserted in DESCRIPTION
                                        -- - as done for object 'led'
                                        -- If no LEDs are available on pim 'No LEDs on pim'
                                        -- should be returned.
                        ::= { brdPlugEntry 7 }

                        brdPlugPimOptions OBJECT-TYPE
                                 SYNTAX OCTET STRING
                                ACCESS read-only
                                STATUS mandatory
                                DESCRIPTION
                                        "Textual description of any options installed
                                         on pim in plug"
                        ::= { brdPlugEntry 8 }


        brdOptionTable OBJECT-TYPE
                SYNTAX  SEQUENCE OF BrdOptionEntry
                ACCESS  not-accessible
                STATUS  mandatory
                DESCRIPTION
                        "Table of various possible board options.
                         Options might be sub-boards or other kinds of hardware options."
                ::= { boards 4 }

                brdOptionEntry OBJECT-TYPE
                        SYNTAX BrdOptionEntry
                        ACCESS not-accessible
                        STATUS mandatory
                        DESCRIPTION "Information about board options."
                        INDEX   { brdNumber4, brdOptionNumber }
                        ::= { brdOptionTable 1 }

                BrdOptionEntry  ::= SEQUENCE {
                        brdNumber4      INTEGER,
                        brdOptionNumber INTEGER,
                        brdOptionName   OCTET STRING,
                        brdOptionState  INTEGER
                }

                brdNumber4 OBJECT-TYPE
                        SYNTAX  INTEGER
                        ACCESS  read-only
                        STATUS  mandatory
                        DESCRIPTION "Board Sequence number in enclosure (= slot number)"
                        ::= { brdOptionEntry 1 }

                brdOptionNumber OBJECT-TYPE
                        SYNTAX  INTEGER
                        ACCESS  read-only
                        STATUS  mandatory
                        DESCRIPTION
                                "Option Number - used to index options on board.
                                 If options is visible on front panel, they must
                                 be sorted (top-most/left-most first)."   -- toe ??
                        ::= { brdOptionEntry 2 }

                brdOptionName   OBJECT-TYPE
                        SYNTAX OCTET STRING
                        ACCESS read-only
                        STATUS mandatory
                        DESCRIPTION "Descriptive Name of option."
                        ::= { brdOptionEntry 3 }

                brdOptionState  OBJECT-TYPE
                        SYNTAX INTEGER {
                                notInstalled    (1),
                                installed       (2)
                        }
                        ACCESS read-only
                        STATUS mandatory
                        DESCRIPTION "Is the option installed ?"
                        ::= { brdOptionEntry 4 }


        brdSwitchSettingTable OBJECT-TYPE
                SYNTAX  SEQUENCE OF BrdSwitchSettingEntry
                ACCESS  not-accessible
                STATUS  mandatory
                DESCRIPTION "Table of switch settings on the board."
                ::= { boards 5 }

                brdSwitchSettingEntry OBJECT-TYPE
                        SYNTAX BrdSwitchSettingEntry
                        ACCESS not-accessible
                        STATUS mandatory
                        DESCRIPTION "Information about Switch Setting"
                        INDEX   { brdNumber5, brdSwitchNumber }
                        ::= { brdSwitchSettingTable 1 }

                BrdSwitchSettingEntry ::= SEQUENCE {
                        brdNumber5              INTEGER,
                        brdSwitchNumber         INTEGER,
                        brdSwitchName           OCTET STRING,
                        brdSwitchSetting        OCTET STRING
                }

                brdNumber5 OBJECT-TYPE
                        SYNTAX  INTEGER
                        ACCESS  read-only
                        STATUS  mandatory
                        DESCRIPTION "Board Sequence number in enclosure (= slot number)"
                        ::= { brdSwitchSettingEntry 1 }

                brdSwitchNumber OBJECT-TYPE
                        SYNTAX  INTEGER
                        ACCESS  read-only
                        STATUS  mandatory
                        DESCRIPTION "Switch Number - used to index switches on board."
                        ::= { brdSwitchSettingEntry 2 }

                brdSwitchName   OBJECT-TYPE
                        SYNTAX OCTET STRING
                        ACCESS read-only
                        STATUS mandatory
                        DESCRIPTION "Descriptive Name - used to identify switch on board."
                        ::= { brdSwitchSettingEntry 3 }

                brdSwitchSetting        OBJECT-TYPE
                        SYNTAX OCTET STRING
                        ACCESS read-only
                        STATUS mandatory
                        DESCRIPTION
                                "Descriptive Name - used to describe switch setting on board.
                                 Eg. 'On', 'Off', 'Enabled', 'Disabled', '0', '01001100',
                                 'A', 'B', 'C', 'Open', 'Closed', 'Inserted',
                                 'Not inserted', etc."
                        ::= { brdSwitchSettingEntry 4 }




---
--- Trap section
---

    boxPowerFailureEvent TRAP-TYPE
        ENTERPRISE  box
        VARIABLES   { psuFail }
        DESCRIPTION
                    "This trap is sent when a power supply failure has been
                     detected.
                     The variable indicates the failing power supply."
    ::= 1

    boxFanFailureEvent TRAP-TYPE
        ENTERPRISE  box
        DESCRIPTION
                    "This trap is sent when a fan failure has been detected."
    ::= 2

    boxTempFailureEvent TRAP-TYPE
        ENTERPRISE  box
        DESCRIPTION
                    "This trap is sent when a temperature sensor has
                     detected excessive temperature in the enclosure."
    ::= 3

    boxModuleInsertedEvent TRAP-TYPE
        ENTERPRISE  box
        VARIABLES   { slotmapFail }
        DESCRIPTION
                    "This trap is sent when a module is inserted in the
                     the enclosure.
                     The variable slotmapFail indicates in which slot
                     a module is inserted"
    ::= 4

    boxModuleRemovedEvent TRAP-TYPE
        ENTERPRISE  box
        VARIABLES   { slotmapFail }
        DESCRIPTION
                    "This trap is sent when a module is removed in the
                     the enclosure.
                     The variable slotmapFail indicates in which slot
                     a module is removed"
    ::= 5


          END
