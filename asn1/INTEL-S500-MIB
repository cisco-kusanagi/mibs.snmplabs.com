INTEL-S500-MIB DEFINITIONS ::= BEGIN

-- Copyright (C) 1997-1999 Intel Corporation. All rights reserved.
--
-- The Express Switch 500 Series specific MIB
--
-- Build 1
--

IMPORTS
        IpAddress, TimeTicks,Counter       FROM RFC1155-SMI
        DisplayString           FROM RFC1213-MIB
        mib2ext                 FROM INTEL-GEN-MIB
        OBJECT-TYPE             FROM RFC-1212
		  TRAP-TYPE FROM RFC-1215;


        s500                    OBJECT IDENTIFIER ::= { mib2ext 10 }
        module                  OBJECT IDENTIFIER ::= { s500 1 }
        ports                   OBJECT IDENTIFIER ::= { s500 2 }
        statistic               OBJECT IDENTIFIER ::= { s500 3 }
        adaptiveForwardMode     OBJECT IDENTIFIER ::= { s500 4 }
        chipSets                OBJECT IDENTIFIER ::= { s500 5 }
        smu                     OBJECT IDENTIFIER ::= { s500 6 }
        permanentEntries        OBJECT IDENTIFIER ::= { s500 7 }
        matrix                  OBJECT IDENTIFIER ::= { s500 8 }
        mediamodules            OBJECT IDENTIFIER ::= { s500 9 }

        --
        -- Switch module group
        --

          defaultSwitchMode OBJECT-TYPE
               SYNTAX  INTEGER {
                          cutThrough(2),
                          fragmentFree(3),
                          storeAndForward(4),
                          adaptive(5)
                          }
               ACCESS  read-write
               STATUS  mandatory
               DESCRIPTION
                       "Default switch mode. This is used by the object
                        portSwitchMode when it's value is default(1)"
               ::= { module 1 }

          defaultFlowControlMode OBJECT-TYPE
               SYNTAX  INTEGER {
                          enable(2),
                          disable(3)
                          }
               ACCESS  read-write
               STATUS  mandatory
               DESCRIPTION
                       "Default Flow Control mode. This is used by the object
                        portConfFlowControl when it's value is default(1)"
               ::= { module 2 }

          smuMaster OBJECT-TYPE
               SYNTAX  INTEGER {
                          enable(1),
                          disable(2)
                          }
               ACCESS  read-only
               STATUS  mandatory
               DESCRIPTION
                       "OBSOLETE"
               ::= { module 3 }

          localManagementTimeout OBJECT-TYPE
               SYNTAX  INTEGER
               ACCESS  read-write
               STATUS  mandatory
               DESCRIPTION
                       "The time (in minutes) that has elapsed before a local
                        management session (telnet or serial) closes when
                        it has not been used.
                        The value '0' means no timeout."
               ::= { module 4 }

          temperatureLevel OBJECT-TYPE
               SYNTAX  INTEGER {
                         normal(1),
                         high(2),
                         critical(3)
                        }
               ACCESS  read-only
               STATUS  mandatory
               DESCRIPTION
                       "temperatureLevel values:
                        normal(1)  : Temperature normal
                        high(2)    : Temperature high. Check air circulation
                        critical(3): Temperature  critical. Shut down
                                     in 30 seconds"
               ::= { module 5 }

          redundantPowerSupplyStatus OBJECT-TYPE
               SYNTAX  INTEGER {
                         notPresent(1),
                         present(2),
                         active(3)
                        }
               ACCESS  read-only
               STATUS  mandatory
               DESCRIPTION
                       "Status for redundant power supply:
                        notPresent(1): RPS not connected or failed. (It
                                       may be present but not plugged in
                                       or damaged etc.)
                        present(2):    RPS not active. (It may be present,
                                       connected, in perfect health, but
                                       just not being used.)
                        active(3):     RPS active"
               ::= { module 6 }

          portMirroring OBJECT-TYPE
               SYNTAX  INTEGER {
                          enable(1),
                          disable(2)
                          }
               ACCESS  read-write
               STATUS  mandatory
               DESCRIPTION
                       "enable(1): Enabling of port mirroring. This is only
                        possible if RMON is disabled.
                        disable(2): Disabling of port mirroring.
                        RMON can only be enabled if port mirroring is disabled"
               ::= { module 7 }

          disableRmon OBJECT-TYPE
               SYNTAX  INTEGER {
                          destroyAll(1)
                          }
               ACCESS  write-only
               STATUS  mandatory
               DESCRIPTION
                       "destroyAll(1): Disable RMON and destroy all
                       probes. This is necessary for enabling port mirroring"
               ::= { module 8 }

          isRmonActive OBJECT-TYPE
               SYNTAX  INTEGER {
                          enabled(1),
                          disabled(2)
                          }
               ACCESS  read-only
               STATUS  mandatory
               DESCRIPTION
                       "enabled(1): RMON is enabled
                        disabled(2): RMON is disabled"
               ::= { module 9 }

          switchTotalTraffic OBJECT-TYPE
               SYNTAX  Counter
               ACCESS  read-only
               STATUS  mandatory
               DESCRIPTION
                       "Total switch traffic measured in octets"
               ::= { module 10 }

          bufferPoolUsed OBJECT-TYPE
               SYNTAX  INTEGER
               ACCESS  read-only
               STATUS  mandatory
               DESCRIPTION
                       "Total switch buffer pool usage.
                        (percentage between 0 and 100)"
               ::= { module 11 }

          featuresBitFlag OBJECT-TYPE
               SYNTAX  OCTET STRING (SIZE(4))
               ACCESS  read-only
               STATUS  mandatory
               DESCRIPTION
                       "Bit field index from bit 1 to 32. If an bit is
                       set, the switch supports the related feature.
                       BIT 1: Distributed VLAN
                       BIT 2: Layer 3 switching
                       BIT 3: Diagnostics
                       BIT 4: RSVP
                       BIT 5: IP multicast
                       BIT 6: IP filtering
                       BIT 7: ATM STP
                       BIT 8: Port trunking
                       BIT 9: Port mirroring
                       BIT 10: VLAN stacking
                       BIT 11: Forwarding of learn packets
                       BIT 12: IGMP pruning
                       BIT 13: ToS
		       BIT 14: Bulk En-/Disable STP
		       BIT 15: VLAN table flush
		       BIT 16: Transparent Cache
		       BIT 17: Compressed Stack"
               ::= { module 12 }

          switchBw OBJECT-TYPE
               SYNTAX  INTEGER
               ACCESS  read-only
               STATUS  mandatory
               DESCRIPTION
                       "Max switch BW. (Mbits per second)"
               ::= { module 13 }

          ownMatrixAttachmentPort OBJECT-TYPE
               SYNTAX  INTEGER
               ACCESS  read-only
               STATUS  mandatory
               DESCRIPTION
                       "Returns the port number of the Matrix port the
                        switch is attached to. NB: will return 50 for
                        a switch not connected to a Matrix Module"
               ::= { module 14 }

          stackCrc OBJECT-TYPE
               SYNTAX  INTEGER
               ACCESS  read-only
               STATUS  mandatory
               DESCRIPTION
                       "checksum for stack specific parameters
			If a parameter is unavailable 0 is returned "
               ::= { module 15 }

        --
        -- Switch port group
        --

        portSnmpPort OBJECT-TYPE
                SYNTAX  INTEGER
                ACCESS  read-only
                STATUS  mandatory
                DESCRIPTION
                        "Returns the port which this SNMP request went
                        through. This gives the port on which the SNMP
                        management system is connected."
              ::= { ports 1 }

        portLastChange OBJECT-TYPE
                SYNTAX  TimeTicks
                ACCESS  read-only
                STATUS  mandatory
                DESCRIPTION
                        "The value of sysUpTime after any interface
                         has changed state"
              ::= { ports 2 }

        portInfoTable OBJECT-TYPE
                SYNTAX  SEQUENCE OF PortInfoEntry
                ACCESS  not-accessible
                STATUS  mandatory
                DESCRIPTION
                        "Port information table which includes all ports."
                ::= { ports 3 }

                portInfoEntry OBJECT-TYPE
                        SYNTAX  PortInfoEntry
                        ACCESS  not-accessible
                        STATUS  mandatory
                        DESCRIPTION
                                "Contains the type of interface ."
                        INDEX   { portInfoChassisIndex,
                                  portInfoModuleIndex, portInfoIndex }
                        ::= { portInfoTable 1 }

                PortInfoEntry ::= SEQUENCE {
                        portInfoChassisIndex      INTEGER,
                        portInfoModuleIndex       INTEGER,
                        portInfoIndex             INTEGER,
                        portInfoType              INTEGER
                }

                portInfoChassisIndex OBJECT-TYPE
                        SYNTAX  INTEGER
                        ACCESS  read-only
                        STATUS  mandatory
                        DESCRIPTION
                                "Chassis index"
                        ::= { portInfoEntry 1 }

                portInfoModuleIndex OBJECT-TYPE
                        SYNTAX  INTEGER
                        ACCESS  read-only
                        STATUS  mandatory
                        DESCRIPTION
                                "Module index"
                        ::= { portInfoEntry 2 }

                portInfoIndex OBJECT-TYPE
                        SYNTAX  INTEGER
                        ACCESS  read-only
                        STATUS  mandatory
                        DESCRIPTION
                                "An index value that uniquely identifies
                                an interface. The interface identified by
                                a particular value of this index is the
                                same interface as identified by the same
                                value of ifIndex."
                        ::= { portInfoEntry 3 }

                portInfoType OBJECT-TYPE
                        SYNTAX  INTEGER {
                                  hundredbasetx(1),
                                  hundredbasefx(2),
                                  core(3),
                                  internal(4),
                                  layer3link(5),
                                  gigabasesx(10),
                                  gigabaselx(11)
                                }
                        ACCESS  read-only
                        STATUS  mandatory
                        DESCRIPTION
                                "The type of Physical interface at the port."
                        ::= { portInfoEntry 4 }

        portConfTable OBJECT-TYPE
                SYNTAX  SEQUENCE OF PortConfEntry
                ACCESS  not-accessible
                STATUS  mandatory
                DESCRIPTION
                        "Port configuration and status table."
                ::= { ports 4 }

                portConfEntry OBJECT-TYPE
                        SYNTAX  PortConfEntry
                        ACCESS  not-accessible
                        STATUS  mandatory
                        DESCRIPTION
                                "An entry containing the objects for
                                configuration and status of a port."
                        INDEX   { portConfChassisIndex,
                                  portConfModuleIndex, portConfIndex }
                        ::= { portConfTable 1 }

                PortConfEntry ::= SEQUENCE {
                        portConfChassisIndex      INTEGER,
                        portConfModuleIndex       INTEGER,
                        portConfIndex             INTEGER,
                        portConfDescr             DisplayString,
                        portConfLocation          DisplayString,
                        portConfConfigSwitchMode  INTEGER,
                        portConfFlowControl       INTEGER,
                        portConfSpeedSupported    INTEGER,
                        portConfDuplexSupported   INTEGER,
                        portConfConfigSpeed       INTEGER,
                        portConfConfigDuplex      INTEGER,
                        portConfConfigAutoNeg     INTEGER,
                        portConfSpeed             INTEGER,
                        portConfDuplex            INTEGER,
                        portConfAutoNeg           INTEGER,
                        portConfSwitchMode        INTEGER,
			portConfTrunkSupported    INTEGER,
			portConfTrunkConfig       INTEGER,
                        portConfTrunkName	  DisplayString,
			portConfMirrorSupported   INTEGER,
			portConfMirrorConfig      INTEGER,
			portConfVlanSupported	  INTEGER
                }

                portConfChassisIndex OBJECT-TYPE
                        SYNTAX  INTEGER
                        ACCESS  read-only
                        STATUS  mandatory
                        DESCRIPTION
                                "Chassis index"
                        ::= { portConfEntry 1 }

                portConfModuleIndex OBJECT-TYPE
                        SYNTAX  INTEGER
                        ACCESS  read-only
                        STATUS  mandatory
                        DESCRIPTION
                                "Module index"
                        ::= { portConfEntry 2 }

                portConfIndex OBJECT-TYPE
                        SYNTAX  INTEGER
                        ACCESS  read-only
                        STATUS  mandatory
                        DESCRIPTION
                                "An index value that uniquely identifies
                                an interface. The interface identified by
                                a particular value of this index is the
                                same interface as identified by the same
                                value of ifIndex."
                        ::= { portConfEntry 3 }

                portConfDescr OBJECT-TYPE
                        SYNTAX  DisplayString (SIZE (0..31))
                        ACCESS  read-write
                        STATUS  mandatory
                        DESCRIPTION
                                "User configurable description of the port."
                        ::= { portConfEntry 4 }

                portConfLocation OBJECT-TYPE
                        SYNTAX  DisplayString (SIZE (0..15))
                        ACCESS  read-write
                        STATUS  mandatory
                        DESCRIPTION
                                "User configurable location of the port."
                        ::= { portConfEntry 5 }

                portConfConfigSwitchMode OBJECT-TYPE
                        SYNTAX  INTEGER {
                                  default(1),
                                  cutThrough(2),
                                  fragmentFree(3),
                                  storeAndForward(4),
                                  adaptive(5),
                                  notAvailable(99)
                                }
                        ACCESS  read-write
                        STATUS  mandatory
                        DESCRIPTION
                                "Port Switch mode. If set to default(1) the
                                value from defaultSwitchMode is used."
                        ::= { portConfEntry 6 }

                portConfFlowControl OBJECT-TYPE
                        SYNTAX  INTEGER {
                                  default(1),
                                  enable(2),
                                  disable(3),
                                  notAvailable(99)
                                }
                        ACCESS  read-write
                        STATUS  mandatory
                        DESCRIPTION
                                "Port Flow Control mode. If set to
                                default(1) the value from
                                defaultFlowControlMode is used."
                        ::= { portConfEntry 7 }

                portConfSpeedSupported OBJECT-TYPE
                        SYNTAX  INTEGER {
                                  speed10Mbit(1),
                                  speed100Mbit(2),
                                  speed10And100Mbit(3),
                                  speed10And100AndAutoMbit(4),
                                  speed155Mbit(5),
                                  speed1Gbit(6),
                                  speed1AndAutoGbit(7),
                                  notAvailable(99)
                                }
                        ACCESS  read-only
                        STATUS  mandatory
                        DESCRIPTION
                                "The possible speeds of a port"
                        ::= { portConfEntry 8 }

                portConfDuplexSupported OBJECT-TYPE
                        SYNTAX  INTEGER {
                                  half(1),
                                  full(2),
                                  halfAndFull(3),
                                  auto(4),
                                  autoAndFull(6),
                                  autoAndHalfAndFull(7),
                                  notAvailable(99)
                                }
                        ACCESS  read-only
                        STATUS  mandatory
                        DESCRIPTION
                                "The possible duplex modes of a port"
                        ::= { portConfEntry 9 }

                portConfConfigSpeed OBJECT-TYPE
                        SYNTAX  INTEGER {
                                  speed10Mbit(1),
                                  speed100Mbit(2),
                                  speed1Gbit(3)
                                }
                        ACCESS  read-write
                        STATUS  mandatory
                        DESCRIPTION
                                "The configured speed for a port"
                        ::= { portConfEntry 10 }

                portConfConfigDuplex OBJECT-TYPE
                        SYNTAX  INTEGER {
                                  half(1),
                                  full(2)
                                }
                        ACCESS  read-write
                        STATUS  mandatory
                        DESCRIPTION
                                "The configured duplex mode for a port"
                        ::= { portConfEntry 11 }

                portConfConfigAutoNeg OBJECT-TYPE
                        SYNTAX  INTEGER {
                                  enable(1),
                                  disable(2)
                                }
                        ACCESS  read-write
                        STATUS  mandatory
                        DESCRIPTION
                                "The configured auto-negotiation for a port"
                        ::= { portConfEntry 12 }

                portConfSpeed OBJECT-TYPE
                        SYNTAX  INTEGER {
                                  speed10Mbit(1),
                                  speedAutoDetect10Mbit(2),
                                  speed100Mbit(3),
                                  speedAutoDetect100Mbit(4),
                                  speed1Gbit(5),
                                  speedAutoDetect1Gbit(6),
                                  speed155Mbit(7),
                                  notAvailable(99)
                                }
                        ACCESS  read-only
                        STATUS  mandatory
                        DESCRIPTION
                                "The current speed for a port"
                        ::= { portConfEntry 13 }

                portConfDuplex OBJECT-TYPE
                        SYNTAX  INTEGER {
                                  half(1),
                                  autoDetectHalf(2),
                                  full(3),
                                  autoDetectFull(4),
                                  notAvailable(99)
                                }
                        ACCESS  read-only
                        STATUS  mandatory
                        DESCRIPTION
                                "The current duplex mode for a port"
                        ::= { portConfEntry 14 }

                portConfAutoNeg OBJECT-TYPE
                        SYNTAX  INTEGER {
                                  manual(1),
                                  auto(2),
                                  failed(3),
                                  notAvailable(99)
                                }
                        ACCESS  read-only
                        STATUS  mandatory
                        DESCRIPTION
                                "The currect auto-negotiation for a port"
                        ::= { portConfEntry 15 }

                portConfSwitchMode OBJECT-TYPE
                        SYNTAX  INTEGER {
                                  cutThrough(1),
                                  adaptiveCutThrough(2),
                                  fragmentFree(3),
                                  adaptiveFragmentFree(4),
                                  storeAndForward(5),
                                  adaptiveStoreAndForward(6),
                                  notAvailable(99)
                                }
                        ACCESS  read-only
                        STATUS  mandatory
                        DESCRIPTION
                                "Current forwarding mode of the port."
                        ::= { portConfEntry 16 }

                portConfTrunkSupported OBJECT-TYPE
                        SYNTAX  INTEGER {
                                  trunkWidthTwo(1),
                                  trunkWidthFour(2),
                                  trunkMaster(3),
                                  trunkSlave(4),
                                  notAvailable(99)
                                }
                        ACCESS  read-only
                        STATUS  mandatory
                        DESCRIPTION
                                "The types of port trunking available for
                                 the actual port. A trunk consists of a
                                 number ports sitting next to each
                                 other. The first port is selected as
                                 master for the trunk, the following as slaves.
                                 trunkWidthTwo(1): Port is available as
                                 master for 2 port trunking.
                                 trunkWidthFour(2): Port is available as
                                 master for 4 port trunking.
                                 trunkMaster(3): Port is master in a trunk.
                                 trunkSlave(4): Port is slave in a trunk.
                                 notAvailable(99): Port is not available
                                 for trunking."
                        ::= { portConfEntry 17 }

                portConfTrunkConfig OBJECT-TYPE
                        SYNTAX  INTEGER {
                                  trunkWidthTwo(1),
                                  trunkWidthFour(2),
                                  disable(99)
                                }
                        ACCESS  read-write
                        STATUS  mandatory
                        DESCRIPTION
                                "The size of the actual trunk. 0 means
                                 trunkWidthTwo(1): This port is member of
                                 a 2 port trunk.
                                 trunkWidthFour(2):This port is member of
                                 a 4 port trunk.
                                 disable(99): This port is not trunked"
                        ::= { portConfEntry 18 }

                portConfTrunkName OBJECT-TYPE
                        SYNTAX  DisplayString (SIZE (0..15))
                        ACCESS  read-write
                        STATUS  mandatory
                        DESCRIPTION
                                "Trunk name"
                        ::= { portConfEntry 19 }

                portConfMirrorSupported OBJECT-TYPE
                        SYNTAX  INTEGER {
                                  mirrorSourceOnly(1),
                                  mirrorDestinationOnly(2),
                                  mirrorSourceOrDestination(3),
                                  notAvailable(99)
                                }
                        ACCESS  read-only
                        STATUS  mandatory
                        DESCRIPTION
                                "Which mode of port mirroring does the port
                                 support.
                                 mirrorSourceOnly(1): Port can only be
                                 used as source for mirroring
                                 mirrorDestinationOnly(2): Port can only be
                                 used as destination for mirroring
                                 mirrorSourceOrDestination(3): Port can
                                 be used as source or destination
                                 notAvailable(99): Port can not be used
                                 for mirroring"
                        ::= { portConfEntry 20 }

                portConfMirrorConfig OBJECT-TYPE
                        SYNTAX  INTEGER {
                                  mirrorSource(1),
                                  mirrorDestination(2),
                                  disabled(99)
                                }
                        ACCESS  read-write
                        STATUS  mandatory
                        DESCRIPTION
                                "The configured port mirroring for
                                 the actual port.
                                 mirrorSource(1): Port is source for
                                 mirroring
                                 mirrorDestination(2): Port is
                                 destination for mirroring
                                 disabled(99): Port is not mirrored"
                        ::= { portConfEntry 21 }

                portConfVlanSupported OBJECT-TYPE
                        SYNTAX  INTEGER {
                                  enabled(1),
                                  notAvailable(99)
                                }
                        ACCESS  read-only
                        STATUS  mandatory
                        DESCRIPTION
                                "Describes if the port can be used as a port
                                 rule in the VLAN configuration.
                                 enabled(1): Port can be used in port
                                 VLANs
                                 notAvailable(99): Port can not be used
                                 in port VLANs"
                        ::= { portConfEntry 22 }

        portAllSpanningTreeMode OBJECT-TYPE
                SYNTAX  INTEGER {
                          allEnabled(1),
                          allDisabled(2),
                          mixed(3)
                        }
                ACCESS  read-write
                STATUS  mandatory
                DESCRIPTION
                        "Enable or Disable Spanning Tree Protocol for
                         all ports on switch.
                         SET is only allowed with value allEnabled(1) or
                         allDisabled(2)."
              ::= { ports 5 }

        --
        -- Switch statistic group
        --

        txStatTable OBJECT-TYPE
                SYNTAX  SEQUENCE OF TxStatEntry
                ACCESS  not-accessible
                STATUS  mandatory
                DESCRIPTION
                        "Transmit statistics table."
                ::= { statistic 1 }

                txStatEntry OBJECT-TYPE
                        SYNTAX  TxStatEntry
                        ACCESS  not-accessible
                        STATUS  mandatory
                        DESCRIPTION
                                "An entry containing objects for
                                transmit statistics."
                        INDEX   { txStatIndex }
                        ::= { txStatTable 1 }

                -- The following counters are available in RFC1643:
                --      txCSenseErrors
                --      txSQEErrors
                --      txLateCollisions
                --      txCollisions[CollCount]
                --      txExcessiveCollisionErrors

                TxStatEntry ::= SEQUENCE {
                        txStatIndex                   INTEGER,
                        txUCPkts64Octets              Counter,
                        txUCPkts65To127Octets         Counter,
                        txUCPkts128To255Octets        Counter,
                        txUCPkts256To511Octets        Counter,
                        txUCPkts512To1023Octets       Counter,
                        txUCPkts1024To1518Octets      Counter,
                        txMCPkts64Octets              Counter,
                        txMCPkts65To127Octets         Counter,
                        txMCPkts128To255Octets        Counter,
                        txMCPkts256To511Octets        Counter,
                        txMCPkts512To1023Octets       Counter,
                        txMCPkts1024To1518Octets      Counter,
                        txBCPkts64Octets              Counter,
                        txBCPkts65To127Octets         Counter,
                        txBCPkts128To255Octets        Counter,
                        txBCPkts256To511Octets        Counter,
                        txBCPkts512To1023Octets       Counter,
                        txBCPkts1024To1518Octets      Counter,
                        txOctetsIllegalAddrType       Counter,
                        tx1ArbitFrameDelay            Counter,
                        tx2ArbitFrameDelay            Counter,
                        tx3ArbitFrameDelay            Counter,
                        tx4ArbitFrameDelay            Counter,
                        tx5ArbitFrameDelay            Counter,
                        tx6ArbitFrameDelay            Counter,
                        tx7ArbitFrameDelay            Counter,
                        txDeferreds                   Counter,
                        txOctetsHis                   Counter,
                        txOctetsLos                   Counter,
                        txOctetsOutOfRange            Counter,
                        txExcessiveDeferralsErrors    Counter,
                        txNiaUnderRunAborts           Counter,
                        txExcessiveLengthDrops        Counter,
                        txLinkDownEvents              Counter,
                        txAllCounterPackets           OCTET STRING,
                        txAllCounterOthers            OCTET STRING
                }

                txStatIndex OBJECT-TYPE
                        SYNTAX  INTEGER
                        ACCESS  read-only
                        STATUS  mandatory
                        DESCRIPTION
                                "An index value that uniquely identifies
                                an interface. The interface identified by
                                a particular value of this index is the
                                same interface as identified by the same
                                value of ifIndex."
                        ::= { txStatEntry 1 }

                txUCPkts64Octets OBJECT-TYPE
                        SYNTAX  Counter
                        ACCESS  read-only
                        STATUS  mandatory
                        DESCRIPTION
                                "64 byte unicast packets transmitted"
                        ::= { txStatEntry 2 }

                txUCPkts65To127Octets OBJECT-TYPE
                        SYNTAX  Counter
                        ACCESS  read-only
                        STATUS  mandatory
                        DESCRIPTION
                                "65 to 127 byte unicast packets transmitted"
                        ::= { txStatEntry 3 }

                txUCPkts128To255Octets OBJECT-TYPE
                        SYNTAX  Counter
                        ACCESS  read-only
                        STATUS  mandatory
                        DESCRIPTION "128 to 255 byte unicast packets
                                transmitted"
                        ::= { txStatEntry 4 }

                txUCPkts256To511Octets OBJECT-TYPE
                        SYNTAX  Counter
                        ACCESS  read-only
                        STATUS  mandatory
                        DESCRIPTION
                                "256 to 511 byte unicast packets transmitted"
                        ::= { txStatEntry 5 }

                txUCPkts512To1023Octets OBJECT-TYPE
                        SYNTAX  Counter
                        ACCESS  read-only
                        STATUS  mandatory
                        DESCRIPTION
                                "512 to 1023 byte unicast packets transmitted"
                        ::= { txStatEntry 6 }

                txUCPkts1024To1518Octets OBJECT-TYPE
                        SYNTAX  Counter
                        ACCESS  read-only
                        STATUS  mandatory
                        DESCRIPTION
                                "1024 to 1518 byte unicast packets transmitted"
                        ::= { txStatEntry 7 }

                txMCPkts64Octets OBJECT-TYPE
                        SYNTAX  Counter
                        ACCESS  read-only
                        STATUS  mandatory
                        DESCRIPTION
                                "64 byte multicast packets transmitted"
                        ::= { txStatEntry 8 }

                txMCPkts65To127Octets OBJECT-TYPE
                        SYNTAX  Counter
                        ACCESS  read-only
                        STATUS  mandatory
                        DESCRIPTION
                                "65 to 127 byte multicast packets transmitted"
                        ::= { txStatEntry 9 }

                txMCPkts128To255Octets OBJECT-TYPE
                        SYNTAX  Counter
                        ACCESS  read-only
                        STATUS  mandatory
                        DESCRIPTION
                                "128 to 255 byte multicast packets transmitted"
                        ::= { txStatEntry 10 }

                txMCPkts256To511Octets OBJECT-TYPE
                        SYNTAX  Counter
                        ACCESS  read-only
                        STATUS  mandatory
                        DESCRIPTION
                                "256 to 511 byte multicast packets transmitted"
                        ::= { txStatEntry 11 }

                txMCPkts512To1023Octets OBJECT-TYPE
                        SYNTAX  Counter
                        ACCESS  read-only
                        STATUS  mandatory
                        DESCRIPTION
                                "512 to 1023 byte multicast packets
                                transmitted"
                        ::= { txStatEntry 12 }

                txMCPkts1024To1518Octets OBJECT-TYPE
                        SYNTAX  Counter
                        ACCESS  read-only
                        STATUS  mandatory
                        DESCRIPTION
                                "1024 to 1518 byte multicast packets
                                 transmitted"
                        ::= { txStatEntry 13 }

                txBCPkts64Octets OBJECT-TYPE
                        SYNTAX  Counter
                        ACCESS  read-only
                        STATUS  mandatory
                        DESCRIPTION
                                "64 byte broadcast packets transmitted"
                        ::= { txStatEntry 14 }

                txBCPkts65To127Octets OBJECT-TYPE
                        SYNTAX  Counter
                        ACCESS  read-only
                        STATUS  mandatory
                        DESCRIPTION
                                "65 to 127 byte broadcast packets
                                transmitted"
                        ::= { txStatEntry 15 }

                txBCPkts128To255Octets OBJECT-TYPE
                        SYNTAX  Counter
                        ACCESS  read-only
                        STATUS  mandatory
                        DESCRIPTION
                                "128 to 255 byte broadcast packets
                                transmitted"
                        ::= { txStatEntry 16 }

                txBCPkts256To511Octets OBJECT-TYPE
                        SYNTAX  Counter
                        ACCESS  read-only
                        STATUS  mandatory
                        DESCRIPTION
                                "256 to 511 byte broadcast packets
                                transmitted"
                        ::= { txStatEntry 17 }

                txBCPkts512To1023Octets OBJECT-TYPE
                        SYNTAX  Counter
                        ACCESS  read-only
                        STATUS  mandatory
                        DESCRIPTION
                                "512 to 1023 byte broadcast packets
                                transmitted"
                        ::= { txStatEntry 18 }

                txBCPkts1024To1518Octets OBJECT-TYPE
                        SYNTAX  Counter
                        ACCESS  read-only
                        STATUS  mandatory
                        DESCRIPTION
                                "1024 to 1518 byte broadcast packets
                                transmitted"
                        ::= { txStatEntry 19 }

                txOctetsIllegalAddrType OBJECT-TYPE
                        SYNTAX  Counter
                        ACCESS  read-only
                        STATUS  mandatory
                        DESCRIPTION
                                "Internal error -- not possible. Always zero."
                        ::= { txStatEntry 20 }

                tx1ArbitFrameDelay OBJECT-TYPE
                        SYNTAX  Counter
                        ACCESS  read-only
                        STATUS  mandatory
                        DESCRIPTION
                                "Tx packets delayed less than 1 slot
                                time (due to NIMBUS
                                overload)."
                        ::= { txStatEntry 21 }

                tx2ArbitFrameDelay OBJECT-TYPE
                        SYNTAX  Counter
                        ACCESS  read-only
                        STATUS  mandatory
                        DESCRIPTION
                                "Tx packets delayed between 1 and 2 slot
                                times (due to NIMBUS overload)"
                        ::= { txStatEntry 22 }

                tx3ArbitFrameDelay OBJECT-TYPE
                        SYNTAX  Counter
                        ACCESS  read-only
                        STATUS  mandatory
                        DESCRIPTION
                                "Tx packets delayed between 2 and 4 slot
                                times (due to NIMBUS overload)"
                        ::= { txStatEntry 23 }

                tx4ArbitFrameDelay OBJECT-TYPE
                        SYNTAX  Counter
                        ACCESS  read-only
                        STATUS  mandatory
                        DESCRIPTION
                                "Tx packets delayed between 4 and 8 slot
                                times (due to NIMBUS overload)"
                        ::= { txStatEntry 24 }

                tx5ArbitFrameDelay OBJECT-TYPE
                        SYNTAX  Counter
                        ACCESS  read-only
                        STATUS  mandatory
                        DESCRIPTION
                                "Tx packets delayed between 8 and 16 slot
                                times (due to NIMBUS overload)"
                        ::= { txStatEntry 25 }

                tx6ArbitFrameDelay OBJECT-TYPE
                        SYNTAX  Counter
                        ACCESS  read-only
                        STATUS  mandatory
                        DESCRIPTION
                                "Tx packets delayed between 16 and 32
                                slot times (due to NIMBUS overload)"
                        ::= { txStatEntry 26 }

                tx7ArbitFrameDelay OBJECT-TYPE
                        SYNTAX  Counter
                        ACCESS  read-only
                        STATUS  mandatory
                        DESCRIPTION
                                "Tx packets delayed more than 32 slot
                                times (due to NIMBUS overload)"
                        ::= { txStatEntry 27 }

                txDeferreds OBJECT-TYPE
                        SYNTAX  Counter
                        ACCESS  read-only
                        STATUS  mandatory
                        DESCRIPTION
                                "Half duplex: Tx packet delayed, due to
                                receiving a packet.
                                Full duplex: Tx packet delayed, due to
                                receiving of a MAC pause control frame."
                        ::= { txStatEntry 28 }

                txOctetsHis OBJECT-TYPE
                        SYNTAX  Counter
                        ACCESS  read-only
                        STATUS  mandatory
                        DESCRIPTION
                                "Upper part of a 64 bit octet
                                transmitted counter"
                        ::= { txStatEntry 29 }

                txOctetsLos OBJECT-TYPE
                        SYNTAX  Counter
                        ACCESS  read-only
                        STATUS  mandatory
                        DESCRIPTION
                                "Lower part of a 64 bit octet
                                transmitted counter"
                        ::= { txStatEntry 30 }

                txOctetsOutOfRange OBJECT-TYPE
                        SYNTAX  Counter
                        ACCESS  read-only
                        STATUS  mandatory
                        DESCRIPTION
                                "Internal error"
                        ::= { txStatEntry 31 }

                txExcessiveDeferralsErrors OBJECT-TYPE
                        SYNTAX  Counter
                        ACCESS  read-only
                        STATUS  mandatory
                        DESCRIPTION
                                "Maximum deferral should be the
                                duration of a maximum length packet, if
                                no errors on the net. Excessive deferral
                                is indicated if deferral duration is more
                                than approximately 49 maximum packets."
                        ::= { txStatEntry 32 }

                txNiaUnderRunAborts OBJECT-TYPE
                        SYNTAX  Counter
                        ACCESS  read-only
                        STATUS  mandatory
                        DESCRIPTION
                                "Internal discard"
                        ::= { txStatEntry 34 }

                txExcessiveLengthDrops OBJECT-TYPE
                        SYNTAX  Counter
                        ACCESS  read-only
                        STATUS  mandatory
                        DESCRIPTION
                                "Tx packets discarded due to too long
                                packets (Only possible if receiving too
                                long packets are allowed)"
                        ::= { txStatEntry 35 }

                txLinkDownEvents OBJECT-TYPE
                        SYNTAX  Counter
                        ACCESS  read-only
                        STATUS  mandatory
                        DESCRIPTION
                                "No link pulses are received. Usually
                                this means that the cable is removed."
                        ::= {txStatEntry 36 }

                txAllCounterPackets OBJECT-TYPE
                        SYNTAX  OCTET STRING (SIZE (127))
                        ACCESS  read-only
                        STATUS  mandatory
                        DESCRIPTION
                                "A collection of all counters for byte
                                and packet counters. This object is
                                needed to optimize SNMP traffic. The
                                counters in this string are:

                                txStatIndex                   INTEGER
                                txOctetsHis                   Counter
                                txOctetsLos                   Counter
                                txUCPkts64Octets              Counter
                                txUCPkts65To127Octets         Counter
                                txUCPkts128To255Octets        Counter
                                txUCPkts256To511Octets        Counter
                                txUCPkts512To1023Octets       Counter
                                txUCPkts1024To1518Octets      Counter
                                txMCPkts64Octets              Counter
                                txMCPkts65To127Octets         Counter
                                txMCPkts128To255Octets        Counter
                                txMCPkts256To511Octets        Counter
                                txMCPkts512To1023Octets       Counter
                                txMCPkts1024To1518Octets      Counter
                                txBCPkts64Octets              Counter
                                txBCPkts65To127Octets         Counter
                                txBCPkts128To255Octets        Counter
                                txBCPkts256To511Octets        Counter
                                txBCPkts512To1023Octets       Counter
                                txBCPkts1024To1518Octets      Counter

                                The values are represented in the OCTET
                                STRING in the listed order, each value
                                stored as a 32 bits big engine value."
                        ::= { txStatEntry 37 }


                txAllCounterOthers OBJECT-TYPE
                        SYNTAX  OCTET STRING (SIZE (127))
                        ACCESS  read-only
                        STATUS  mandatory
                        DESCRIPTION
                                "A collection of all counters -- other than
                                for byte and packet counters. This object is
                                needed to optimize SNMP traffic. The
                                counters in this string are:

                                txStatIndex                   INTEGER
                                txDeferreds                   Counter
                                txExcessiveDeferralsErrors    Counter
                                txForwRxErrorCollision        Counter
                                txNiaUnderRunAborts           Counter
                                txLinkDownEvents              Counter

                                -- Counters from RFC1643
                                txCSenseErrors                Counter
                                txSQEErrors                   Counter
                                txLateCollisions              Counter
                                txExcessiveCollisionErrors    Counter
                                txSingleCollisionFrames       Counter
                                txMultipleCollisionFrames     Counter

                                The values are represented in the OCTET
                                STRING in the listed order, each value
                                stored as a 32 bits big engine value."
                        ::= { txStatEntry 38 }




        rxStatTable OBJECT-TYPE
                SYNTAX  SEQUENCE OF RxStatEntry
                ACCESS  not-accessible
                STATUS  mandatory
                DESCRIPTION
                        "Receive statistics table."
                ::= { statistic 2 }

                rxStatEntry OBJECT-TYPE
                        SYNTAX  RxStatEntry
                        ACCESS  not-accessible
                        STATUS  mandatory
                        DESCRIPTION
                                "An entry containing objects for
                                receive statistics."
                        INDEX   { rxStatIndex }
                        ::= { rxStatTable 1 }

                -- The following counters are available in RFC1643:
                --      rxAlignErrors
                --      rxFCSErrors

                RxStatEntry ::= SEQUENCE {
                        rxStatIndex                        INTEGER,
                        rxUCPkts64OctetsLocals             Counter,
                        rxUCPkts64OctetsForwardeds         Counter,
                        rxUCPkts65To127OctetsLocals        Counter,
                        rxUCPkts65To127OctetsForwardeds    Counter,
                        rxUCPkts128To255OctetsLocals       Counter,
                        rxUCPkts128To255OctetsForwardeds   Counter,
                        rxUCPkts256To511OctetsLocals       Counter,
                        rxUCPkts256To511OctetsForwardeds   Counter,
                        rxUCPkts512To1023OctetsLocals      Counter,
                        rxUCPkts512To1023OctetsForwardeds  Counter,
                        rxUCPkts1024To1518OctetsLocals     Counter,
                        rxUCPkts1024To1518OctetsForwardeds Counter,
                        rxShortErrors                      Counter,
                        rxRuntErrors                       Counter,
                        rxDataRateMMErrors                 Counter,
                        rxMCPkts64OctetsLocals             Counter,
                        rxMCPkts64OctetsForwardeds         Counter,
                        rxMCPkts65To127OctetsLocals        Counter,
                        rxMCPkts65To127OctetsForwardeds    Counter,
                        rxMCPkts128To255OctetsLocals       Counter,
                        rxMCPkts128To255OctetsForwardeds   Counter,
                        rxMCPkts256To511OctetsLocals       Counter,
                        rxMCPkts256To511OctetsForwardeds   Counter,
                        rxMCPkts512To1023OctetsLocals      Counter,
                        rxMCPkts512To1023OctetsForwardeds  Counter,
                        rxMCPkts1024To1518OctetsLocals     Counter,
                        rxMCPkts1024To1518OctetsForwardeds Counter,
                        rxOctetsLocalHis                   Counter,
                        rxOctetsLocalLos                   Counter,
                        rxOctetsForwardedHis               Counter,
                        rxOctetsForwardedLos               Counter,
                        rxBCPkts64OctetsLocals             Counter,
                        rxBCPkts64OctetsForwardeds         Counter,
                        rxBCPkts65To127OctetsLocals        Counter,
                        rxBCPkts65To127OctetsForwardeds    Counter,
                        rxBCPkts128To255OctetsLocals       Counter,
                        rxBCPkts128To255OctetsForwardeds   Counter,
                        rxBCPkts256To511OctetsLocals       Counter,
                        rxBCPkts256To511OctetsForwardeds   Counter,
                        rxBCPkts512To1023OctetsLocals      Counter,
                        rxBCPkts512To1023OctetsForwardeds  Counter,
                        rxBCPkts1024To1518OctetsLocals     Counter,
                        rxBCPkts1024To1518OctetsForwardeds Counter,
                        rxFilterMACUnexp2ndPortDrops       Counter,
                        rxFilterIllegalMACDrops            Counter,
                        rxFlowCtrlPram                     Counter,
                        rxFlowCtrlNimbus                   Counter,
                        rxPramOverRuns                     Counter,
                        rxNimbusOverRuns                   Counter,
                        rxVeryLongErrors                   Counter,
                        rxLongErrors                       Counter,
                        rxPauseMacControlReceived          Counter,
                        rxUnknownMacControlFrame           Counter,
                        rxPiaOutOfPoolDropErrors           Counter,
                        rxCodeViolations                   Counter,
                        rxJabberErrors                     Counter,
                        rxNiaOverRunDropErrors             Counter,
                        rxAllCounterPackets                OCTET STRING,
                        rxAllCounterOthers                 OCTET STRING
                }

                rxStatIndex OBJECT-TYPE
                        SYNTAX  INTEGER
                        ACCESS  read-only
                        STATUS  mandatory
                        DESCRIPTION
                                "An index value that uniquely identifies
                                an interface. The interface identified by
                                a particular value of this index is the
                                same interface as identified by the same
                                value of ifIndex."
                        ::= { rxStatEntry 1 }

                rxUCPkts64OctetsLocals OBJECT-TYPE
                        SYNTAX  Counter
                        ACCESS  read-only
                        STATUS  mandatory
                        DESCRIPTION
                                "64 byte unicast packets received
                                which have not been forwarded"
                        ::= { rxStatEntry 2 }

                rxUCPkts64OctetsForwardeds OBJECT-TYPE
                        SYNTAX  Counter
                        ACCESS  read-only
                        STATUS  mandatory
                        DESCRIPTION
                                "64 byte unicast packets received
                                which have been forwarded"
                        ::= { rxStatEntry 3 }

                rxUCPkts65To127OctetsLocals OBJECT-TYPE
                        SYNTAX  Counter
                        ACCESS  read-only
                        STATUS  mandatory
                        DESCRIPTION
                                "65 to 127 byte unicast packets received
                                which have not been forwarded"
                        ::= { rxStatEntry 4 }

                rxUCPkts65To127OctetsForwardeds OBJECT-TYPE
                        SYNTAX  Counter
                        ACCESS  read-only
                        STATUS  mandatory
                        DESCRIPTION
                                "65 to 127 byte unicast packets received
                                which have been forwarded"
                        ::= { rxStatEntry 5 }

                rxUCPkts128To255OctetsLocals OBJECT-TYPE
                        SYNTAX  Counter
                        ACCESS  read-only
                        STATUS  mandatory
                        DESCRIPTION
                                "128 to 255 byte unicast packets received
                                which have not been forwarded"
                        ::= { rxStatEntry 6 }

                rxUCPkts128To255OctetsForwardeds OBJECT-TYPE
                        SYNTAX  Counter
                        ACCESS  read-only
                        STATUS  mandatory
                        DESCRIPTION
                                "128 to 255 byte unicast packets received
                                which have been forwarded"
                        ::= { rxStatEntry 7 }

                rxUCPkts256To511OctetsLocals OBJECT-TYPE
                        SYNTAX  Counter
                        ACCESS  read-only
                        STATUS  mandatory
                        DESCRIPTION
                                "256 to 511 byte unicast packets received
                                which have not been forwarded"
                        ::= { rxStatEntry 8 }

                rxUCPkts256To511OctetsForwardeds OBJECT-TYPE
                        SYNTAX  Counter
                        ACCESS  read-only
                        STATUS  mandatory
                        DESCRIPTION
                                "255 to 511 byte unicast packets received
                                which have been forwarded"
                        ::= { rxStatEntry 9 }

                rxUCPkts512To1023OctetsLocals OBJECT-TYPE
                        SYNTAX  Counter
                        ACCESS  read-only
                        STATUS  mandatory
                        DESCRIPTION
                                "512 to 1023 byte unicast packets received
                                which have not been forwarded"
                        ::= { rxStatEntry 10 }

                rxUCPkts512To1023OctetsForwardeds OBJECT-TYPE
                        SYNTAX  Counter
                        ACCESS  read-only
                        STATUS  mandatory
                        DESCRIPTION
                                "512 to 1023 byte unicast packets received
                                which has been forwarded"
                        ::= { rxStatEntry 11 }

                rxUCPkts1024To1518OctetsLocals OBJECT-TYPE
                        SYNTAX  Counter
                        ACCESS  read-only
                        STATUS  mandatory
                        DESCRIPTION
                                "1024 to 1518 byte unicast packets received
                                which have not been forwarded"
                        ::= { rxStatEntry 12 }

                rxUCPkts1024To1518OctetsForwardeds OBJECT-TYPE
                        SYNTAX  Counter
                        ACCESS  read-only
                        STATUS  mandatory
                        DESCRIPTION
                                "1024 to 1518 byte unicast packets received
                                which have been forwarded"
                        ::= { rxStatEntry 13 }

                rxShortErrors OBJECT-TYPE
                        SYNTAX  Counter
                        ACCESS  read-only
                        STATUS  mandatory
                        DESCRIPTION
                                "Receive fragments shorter than the
                                minimum ordinary collision fragment."
                          ::= {rxStatEntry 14 }

                rxRuntErrors OBJECT-TYPE
                        SYNTAX  Counter
                        ACCESS  read-only
                        STATUS  mandatory
                        DESCRIPTION
                                "Ordinary collision fragments received."
                        ::= { rxStatEntry 15 }

                rxDataRateMMErrors OBJECT-TYPE
                        SYNTAX  Counter
                        ACCESS  read-only
                        STATUS  mandatory
                        DESCRIPTION
                                "A data rate miss-match error occurs if
                                the data rate deviation is larger
                                than allowed. This should only occur if
                                problems with the TX oscillator in the
                                adapter transmitting the frame."
                        ::= {rxStatEntry 16 }

                rxMCPkts64OctetsLocals OBJECT-TYPE
                        SYNTAX  Counter
                        ACCESS  read-only
                        STATUS  mandatory
                        DESCRIPTION
                                "64 byte multicast packets received
                                which have not been forwarded"
                        ::= { rxStatEntry 17 }

                rxMCPkts64OctetsForwardeds OBJECT-TYPE
                        SYNTAX  Counter
                        ACCESS  read-only
                        STATUS  mandatory
                        DESCRIPTION
                                "64 byte multicast packets received
                                which have been forwarded"
                        ::= { rxStatEntry 18 }

                rxMCPkts65To127OctetsLocals OBJECT-TYPE
                        SYNTAX  Counter
                        ACCESS  read-only
                        STATUS  mandatory
                        DESCRIPTION
                                "65 to 127 byte multicast packets received
                                which have not been forwarded"
                        ::= { rxStatEntry 19 }

                rxMCPkts65To127OctetsForwardeds OBJECT-TYPE
                        SYNTAX  Counter
                        ACCESS  read-only
                        STATUS  mandatory
                        DESCRIPTION
                                "65 to 127 byte multicast packets received
                                which have been forwarded"
                        ::= { rxStatEntry 20 }

                rxMCPkts128To255OctetsLocals OBJECT-TYPE
                        SYNTAX  Counter
                        ACCESS  read-only
                        STATUS  mandatory
                        DESCRIPTION
                                "128 to 255 byte multicast packets received
                                which have not been forwarded"
                        ::= { rxStatEntry 21 }

                rxMCPkts128To255OctetsForwardeds OBJECT-TYPE
                        SYNTAX  Counter
                        ACCESS  read-only
                        STATUS  mandatory
                        DESCRIPTION
                                "128 to 255 byte multicast packets received
                                which have been forwarded"
                        ::= { rxStatEntry 22 }

                rxMCPkts256To511OctetsLocals OBJECT-TYPE
                        SYNTAX  Counter
                        ACCESS  read-only
                        STATUS  mandatory
                        DESCRIPTION
                                "256 to 511 byte multicast packets received
                                which have not been forwarded"
                        ::= { rxStatEntry 23 }

                rxMCPkts256To511OctetsForwardeds OBJECT-TYPE
                        SYNTAX  Counter
                        ACCESS  read-only
                        STATUS  mandatory
                        DESCRIPTION
                                "256 to 511 byte multicast packets received
                                which have been forwarded"
                        ::= { rxStatEntry 24 }

                rxMCPkts512To1023OctetsLocals OBJECT-TYPE
                        SYNTAX  Counter
                        ACCESS  read-only
                        STATUS  mandatory
                        DESCRIPTION
                                "512 to 1023 byte multicast packets received
                                which have not been forwarded"
                        ::= { rxStatEntry 25 }

                rxMCPkts512To1023OctetsForwardeds OBJECT-TYPE
                        SYNTAX  Counter
                        ACCESS  read-only
                        STATUS  mandatory
                        DESCRIPTION
                                "512 to 1023 byte multicast packets received
                                which have been forwarded"
                        ::= { rxStatEntry 26 }

                rxMCPkts1024To1518OctetsLocals OBJECT-TYPE
                        SYNTAX  Counter
                        ACCESS  read-only
                        STATUS  mandatory
                        DESCRIPTION
                                "1024 to 1518 byte multicast packets received
                                which have not been forwarded"
                        ::= { rxStatEntry 27 }

                rxMCPkts1024To1518OctetsForwardeds OBJECT-TYPE
                        SYNTAX  Counter
                        ACCESS  read-only
                        STATUS  mandatory
                        DESCRIPTION
                                "1024 to 1518 byte multicast packets received
                                which have been forwarded"
                        ::= { rxStatEntry 28 }

                rxOctetsLocalHis OBJECT-TYPE
                        SYNTAX  Counter
                        ACCESS  read-only
                        STATUS  mandatory
                        DESCRIPTION
                                "Upper part of a 64 bit octet received
                                counter which has not been forwarded"
                        ::= { rxStatEntry 29 }

                rxOctetsLocalLos OBJECT-TYPE
                        SYNTAX  Counter
                        ACCESS  read-only
                        STATUS  mandatory
                        DESCRIPTION
                                "Lower part of a 64 bit octet received
                                counter which has not been forwarded"
                        ::= { rxStatEntry 30 }

                rxOctetsForwardedHis OBJECT-TYPE
                        SYNTAX  Counter
                        ACCESS  read-only
                        STATUS  mandatory
                        DESCRIPTION
                                "Upper part of a 64 bit octet received
                                counter which has been forwarded"
                        ::= { rxStatEntry 31 }

                rxOctetsForwardedLos OBJECT-TYPE
                        SYNTAX  Counter
                        ACCESS  read-only
                        STATUS  mandatory
                        DESCRIPTION
                                "Lower part of a 64 bit octet received
                                counter which has been forwarded"
                        ::= { rxStatEntry 32 }

                rxBCPkts64OctetsLocals OBJECT-TYPE
                        SYNTAX  Counter
                        ACCESS  read-only
                        STATUS  mandatory
                        DESCRIPTION
                                "64 byte broadcast packets received
                                which have not been forwarded"
                        ::= { rxStatEntry 33 }

                rxBCPkts64OctetsForwardeds OBJECT-TYPE
                        SYNTAX  Counter
                        ACCESS  read-only
                        STATUS  mandatory
                        DESCRIPTION
                                "64 byte broadcast packets received
                                which have been forwarded"
                        ::= { rxStatEntry 34 }

                rxBCPkts65To127OctetsLocals OBJECT-TYPE
                        SYNTAX  Counter
                        ACCESS  read-only
                        STATUS  mandatory
                        DESCRIPTION
                                "65 to 127 byte broadcast packets received
                                which have not been forwarded"
                        ::= { rxStatEntry 35 }

                rxBCPkts65To127OctetsForwardeds OBJECT-TYPE
                        SYNTAX  Counter
                        ACCESS  read-only
                        STATUS  mandatory
                        DESCRIPTION
                                "65 to 127 byte broadcast packets received
                                which have been forwarded"
                        ::= { rxStatEntry 36 }

                rxBCPkts128To255OctetsLocals OBJECT-TYPE
                        SYNTAX  Counter
                        ACCESS  read-only
                        STATUS  mandatory
                        DESCRIPTION
                                "128 to 255 byte broadcast packets received
                                which have not been forwarded"
                        ::= { rxStatEntry 37 }

                rxBCPkts128To255OctetsForwardeds OBJECT-TYPE
                        SYNTAX  Counter
                        ACCESS  read-only
                        STATUS  mandatory
                        DESCRIPTION
                                "128 to 255 byte broadcast packets received
                                which have been forwarded"
                        ::= { rxStatEntry 38 }

                rxBCPkts256To511OctetsLocals OBJECT-TYPE
                        SYNTAX  Counter
                        ACCESS  read-only
                        STATUS  mandatory
                        DESCRIPTION
                                "256 to 511 byte broadcast packets received
                                which have not been forwarded"
                        ::= { rxStatEntry 39 }

                rxBCPkts256To511OctetsForwardeds OBJECT-TYPE
                        SYNTAX  Counter
                        ACCESS  read-only
                        STATUS  mandatory
                        DESCRIPTION
                                "256 to 511 byte broadcast packets received
                                which have been forwarded"
                        ::= { rxStatEntry 40 }

                rxBCPkts512To1023OctetsLocals OBJECT-TYPE
                        SYNTAX  Counter
                        ACCESS  read-only
                        STATUS  mandatory
                        DESCRIPTION
                                "512 to 1023 byte broadcast packets received
                                which have not been forwarded"
                        ::= { rxStatEntry 41 }

                rxBCPkts512To1023OctetsForwardeds OBJECT-TYPE
                        SYNTAX  Counter
                        ACCESS  read-only
                        STATUS  mandatory
                        DESCRIPTION
                                "512 to 1023 byte broadcast packets received
                                which have been forwarded"
                        ::= { rxStatEntry 42 }

                rxBCPkts1024To1518OctetsLocals OBJECT-TYPE
                        SYNTAX  Counter
                        ACCESS  read-only
                        STATUS  mandatory
                        DESCRIPTION
                                "1024 to 1518 byte broadcast packets received
                                which have not been forwarded"
                        ::= { rxStatEntry 43 }

                rxBCPkts1024To1518OctetsForwardeds OBJECT-TYPE
                        SYNTAX  Counter
                        ACCESS  read-only
                        STATUS  mandatory
                        DESCRIPTION
                                "1024 to 1518 byte broadcast packets received
                                which have been forwarded"
                        ::= { rxStatEntry 44 }

                rxFilterMACUnexp2ndPortDrops OBJECT-TYPE
                        SYNTAX  Counter
                        ACCESS  read-only
                        STATUS  mandatory
                        DESCRIPTION
                                "MAC address has been moved from one
                                port to another"
                        ::= { rxStatEntry 45 }

                rxFilterIllegalMACDrops OBJECT-TYPE
                        SYNTAX  Counter
                        ACCESS  read-only
                        STATUS  mandatory
                        DESCRIPTION
                                "Packet is dropped because the source MAC
                                address is illegal (zero or broadcase)"
                        ::= { rxStatEntry 46 }

                rxFlowCtrlPram OBJECT-TYPE
                        SYNTAX  Counter
                        ACCESS  read-only
                        STATUS  mandatory
                        DESCRIPTION
                                "Half duplex: Number of Flow Control
                                collisions generated due to PRAM
                                limitations.
                                Full duplex: Number of MAC pause control
                                frames transmitted due to PRAM limitations."
                        ::= { rxStatEntry 47 }

                rxFlowCtrlNimbus OBJECT-TYPE
                        SYNTAX  Counter
                        ACCESS  read-only
                        STATUS  mandatory
                        DESCRIPTION
                                "Half duplex: Number of Flow Control
                                collisions generated due to NIMBUS overload.
                                Full duplex: Number of MAC pause control
                                frames transmitted due to NIMBUS overload."
                        ::= { rxStatEntry 48 }

                rxPramOverRuns OBJECT-TYPE
                        SYNTAX  Counter
                        ACCESS  read-only
                        STATUS  mandatory
                        DESCRIPTION
                                "Rx packets discarded due to PRAM limitation"
                        ::= { rxStatEntry 49 }

                rxNimbusOverRuns OBJECT-TYPE
                        SYNTAX  Counter
                        ACCESS  read-only
                        STATUS  mandatory
                        DESCRIPTION
                                "Rx packets discarded due to NIMBUS limitation"
                        ::= { rxStatEntry 50 }

                rxVeryLongErrors OBJECT-TYPE
                        SYNTAX  Counter
                        ACCESS  read-only
                        STATUS  mandatory
                        DESCRIPTION
                                "Rx packets that are much too long
                                (> 6000 bytes)."
                        ::= { rxStatEntry 51 }

                rxLongErrors OBJECT-TYPE
                        SYNTAX  Counter
                        ACCESS  read-only
                        STATUS  mandatory
                        DESCRIPTION
                                "Rx packets that are too long (> 1518 bytes)"
                        ::= { rxStatEntry 52 }

                rxPauseMacControlReceived OBJECT-TYPE
                        SYNTAX  Counter
                        ACCESS  read-only
                        STATUS  mandatory
                        DESCRIPTION
                                "Number of MAC pause control frames received"
                        ::= { rxStatEntry 53 }

                rxUnknownMacControlFrame OBJECT-TYPE
                        SYNTAX  Counter
                        ACCESS  read-only
                        STATUS  mandatory
                        DESCRIPTION
                                "Number of unsupported MAC control frames
                                received"
                        ::= { rxStatEntry 54 }

                rxPiaOutOfPoolDropErrors OBJECT-TYPE
                        SYNTAX  Counter
                        ACCESS  read-only
                        STATUS  mandatory
                        DESCRIPTION
                                "Reception is aborted due to lack of
                                pool memory -- the switch is overloaded."
                        ::= { rxStatEntry 55 }

                rxCodeViolations OBJECT-TYPE
                        SYNTAX  Counter
                        ACCESS  read-only
                        STATUS  mandatory
                        DESCRIPTION
                                "An illegal symbol received on a
                                100Base-X port."
                        ::= { rxStatEntry 56 }

                rxJabberErrors OBJECT-TYPE
                        SYNTAX  Counter
                        ACCESS  read-only
                        STATUS  mandatory
                        DESCRIPTION
                                "Rx packets that are too long and
                                contains CRC errors and/or dribble nibble."
                        ::= { rxStatEntry 57 }

                rxNiaOverRunDropErrors OBJECT-TYPE
                        SYNTAX  Counter
                        ACCESS  read-only
                        STATUS  mandatory
                        DESCRIPTION
                                "The NIA Rx buffer goes to overrun if
                                the nimbus is overloaded (NIA10 only)."
                        ::= { rxStatEntry 58 }

                rxAllCounterPackets OBJECT-TYPE
                        SYNTAX  OCTET STRING (SIZE (164))
                        ACCESS  read-only
                        STATUS  mandatory
                        DESCRIPTION
                                "A collection of all counters for byte
                                and packet counters. This object is
                                needed to optimise SNMP traffic. The
                                counters in this string are:

                                rxStatIndex                        INTEGER
                                rxOctetsLocalHis                   Counter
                                rxOctetsLocalLos                   Counter
                                rxOctetsForwardedHis               Counter
                                rxOctetsForwardedLos               Counter
                                rxUCPkts64OctetsLocals             Counter
                                rxUCPkts64OctetsForwardeds         Counter
                                rxUCPkts65To127OctetsLocals        Counter
                                rxUCPkts65To127OctetsForwardeds    Counter
                                rxUCPkts128To255OctetsLocals       Counter
                                rxUCPkts128To255OctetsForwardeds   Counter
                                rxUCPkts256To511OctetsLocals       Counter
                                rxUCPkts256To511OctetsForwardeds   Counter
                                rxUCPkts512To1023OctetsLocals      Counter
                                rxUCPkts512To1023OctetsForwardeds  Counter
                                rxUCPkts1024To1518OctetsLocals     Counter
                                rxUCPkts1024To1518OctetsForwardeds Counter
                                rxMCPkts64OctetsLocals             Counter
                                rxMCPkts64OctetsForwardeds         Counter
                                rxMCPkts65To127OctetsLocals        Counter
                                rxMCPkts65To127OctetsForwardeds    Counter
                                rxMCPkts128To255OctetsLocals       Counter
                                rxMCPkts128To255OctetsForwardeds   Counter
                                rxMCPkts256To511OctetsLocals       Counter
                                rxMCPkts256To511OctetsForwardeds   Counter
                                rxMCPkts512To1023OctetsLocals      Counter
                                rxMCPkts512To1023OctetsForwardeds  Counter
                                rxMCPkts1024To1518OctetsLocals     Counter
                                rxMCPkts1024To1518OctetsForwardeds Counter
                                rxBCPkts64OctetsLocals             Counter
                                rxBCPkts64OctetsForwardeds         Counter
                                rxBCPkts65To127OctetsLocals        Counter
                                rxBCPkts65To127OctetsForwardeds    Counter
                                rxBCPkts128To255OctetsLocals       Counter
                                rxBCPkts128To255OctetsForwardeds   Counter
                                rxBCPkts256To511OctetsLocals       Counter
                                rxBCPkts256To511OctetsForwardeds   Counter
                                rxBCPkts512To1023OctetsLocals      Counter
                                rxBCPkts512To1023OctetsForwardeds  Counter
                                rxBCPkts1024To1518OctetsLocals     Counter
                                rxBCPkts1024To1518OctetsForwardeds Counter

                                The values are represented in the OCTET
                                STRING in the listed order. Each value
                                stored as a 32 bits big engine value."
                        ::= { rxStatEntry 59 }


                rxAllCounterOthers OBJECT-TYPE
                        SYNTAX  OCTET STRING (SIZE (48))
                        ACCESS  read-only
                        STATUS  mandatory
                        DESCRIPTION
                                "A collection of all counters other than
                                for byte and packet counters. This object is
                                needed to optimize SNMP traffic. The
                                counters in this string are:

                                rxStatIndex                        INTEGER
                                rxShortErrors                      Counter
                                rxRuntErrors                       Counter
                                rxDataRateMMErrors                 Counter
                                rxFilterMACUnexp2ndPortDrops       Counter
                                rxFilterIllegalMACDrops            Counter
                                rxVeryLongErrors                   Counter
                                rxLongErrors                       Counter
                                rxCodeViolation                    Counter
                                rxJabberErrors                     Counter

                                -- Counters from RFC1643
                                rxAlignErrors                      Counter
                                rxFCSErrors                        Counter


                                The values are represented in the OCTET
                                STRING in the listed order, each value
                                stored as a 32 bits big engine value."
                        ::= { rxStatEntry 60 }

                totalRxTxPackets OBJECT-TYPE
                        SYNTAX  OCTET STRING
                        ACCESS  read-only
                        STATUS  mandatory
                        DESCRIPTION
                                "This object is used for LED control to
                                display traffic. Values in the string are
                                all packets transmitted and received at
                                each port. The number and order of values
                                equals the ifIndex, however only physical
                                ports are included in the array. Each
                                entry is 4 bytes. The first 4 bytes of
                                the string is the value of portLastChange."
                        ::= { statistic 3 }

                totalCollisions OBJECT-TYPE
                        SYNTAX  OCTET STRING
                        ACCESS  read-only
                        STATUS  mandatory
                        DESCRIPTION
                                "This object is used for LED control to
                                display collision. Values in the string
                                are the total collisions at each
                                port. The number and order of values
                                equals the ifIndex, however only physical
                                ports are included in the array. Each
                                entry is 4 bytes.  The first 4 bytes of
                                the string is the value of portLastChange."
                        ::= { statistic 4 }


          adaptiveForwardModeSampleTime OBJECT-TYPE
               SYNTAX  INTEGER
               ACCESS  read-write
               STATUS  mandatory
               DESCRIPTION
                       "Specify how long (in seconds) the received
                        packets will be monitored. The resulting
                        forwarding mode will be based on the quality of
                        the packets"
               ::= { adaptiveForwardMode 1 }

          adaptiveForwardModeRuntsOffset OBJECT-TYPE
               SYNTAX  INTEGER
               ACCESS  read-write
               STATUS  mandatory
               DESCRIPTION
                       "Specifies the minimum amount of runts during the
                       sample time which forces the port out of
                       cutThrough(2). The value is specified in per mill
                       * 1000"
               ::= { adaptiveForwardMode 2 }

          adaptiveForwardModeRuntsRange OBJECT-TYPE
               SYNTAX  INTEGER
               ACCESS  read-write
               STATUS  mandatory
               DESCRIPTION
                       "Specifies (together with
                       adaptiveForwardModeRuntsOffset) the maximum amount
                       of runts allowed during the sample time. This
                       forces the port back to cutThrough(2). The value is
                       specified in per mill * 1000"
               ::= { adaptiveForwardMode 3 }

          adaptiveForwardModeCrcsOffset OBJECT-TYPE
               SYNTAX  INTEGER
               ACCESS  read-write
               STATUS  mandatory
               DESCRIPTION
                       "Specifies the maximum amount of CRC errors during
                       the sample time. This forces the port out of
                       Store-and-Forward. The value is specified in per mill *
                       1000"
               ::= { adaptiveForwardMode 4 }

          adaptiveForwardModeCrcsRange OBJECT-TYPE
               SYNTAX  INTEGER
               ACCESS  read-write
               STATUS  mandatory
               DESCRIPTION
                       "Specifies together with
                       adaptiveForwardModeCrcsOffset the maximum amount
                       of CRC errors during the sample time. This forces
                       the port out of Store-and-Forward. The value is
                       specified in per mill * 1000"
               ::= { adaptiveForwardMode 5 }


        -- chipSetNIA110 OBJECT IDENTIFIER ::= { chipSets 1 }


        --
        -- Switch smu group OBSOLETE
        --

        smuModuleTable OBJECT-TYPE
                SYNTAX  SEQUENCE OF SmuModuleEntry
                ACCESS  not-accessible
                STATUS  mandatory
                DESCRIPTION
                        "Not implemented yet"
                ::= { smu 1 }

                smuModuleEntry OBJECT-TYPE
                        SYNTAX  SmuModuleEntry
                        ACCESS  not-accessible
                        STATUS  mandatory
                        DESCRIPTION
                                "Not implemented yet"
                        INDEX { smuModuleChassisIndex, smuModuleIndex }
                        ::= { smuModuleTable 1 }

                SmuModuleEntry ::= SEQUENCE {
                        smuModuleChassisIndex       INTEGER,
                        smuModuleIndex              INTEGER,
                        smuModuleState              INTEGER
                }

                smuModuleChassisIndex OBJECT-TYPE
                        SYNTAX  INTEGER
                        ACCESS  read-only
                        STATUS  mandatory
                        DESCRIPTION
                                "Not implemented yet"
                        ::= { smuModuleEntry 1 }

                smuModuleIndex OBJECT-TYPE
                        SYNTAX  INTEGER
                        ACCESS  read-only
                        STATUS  mandatory
                        DESCRIPTION
                                "Not implemented yet"
                        ::= { smuModuleEntry 2 }

                smuModuleState OBJECT-TYPE
                        SYNTAX  INTEGER
                        ACCESS  read-only
                        STATUS  mandatory
                        DESCRIPTION
                                "Not implemented yet"
                        ::= { smuModuleEntry 3 }


        smuPortTable OBJECT-TYPE
                SYNTAX  SEQUENCE OF SmuPortEntry
                ACCESS  not-accessible
                STATUS  mandatory
                DESCRIPTION
                        "Not implemented yet"
                ::= { smu 2 }

                smuPortEntry OBJECT-TYPE
                        SYNTAX  SmuPortEntry
                        ACCESS  not-accessible
                        STATUS  mandatory
                        DESCRIPTION
                                "Not implemented yet"
                        INDEX { smuPortChassisIndex,
                                smuPortModuleIndex,
                                smuPortIndex }
                        ::= { smuPortTable 1 }

                SmuPortEntry ::= SEQUENCE {
                        smuPortChassisIndex       INTEGER,
                        smuPortModuleIndex        INTEGER,
                        smuPortIndex              INTEGER,
                        smuPortAttachedNumber     INTEGER,
                        smuPortAttachedMac        OCTET STRING,
                        smuPortAttachedIp         IpAddress
                }

                smuPortChassisIndex OBJECT-TYPE
                        SYNTAX  INTEGER
                        ACCESS  read-only
                        STATUS  mandatory
                        DESCRIPTION
                                "Not implemented yet"
                        ::= { smuPortEntry 1 }

                smuPortModuleIndex OBJECT-TYPE
                        SYNTAX  INTEGER
                        ACCESS  read-only
                        STATUS  mandatory
                        DESCRIPTION
                                "Not implemented yet"
                        ::= { smuPortEntry 2 }

                smuPortIndex OBJECT-TYPE
                        SYNTAX  INTEGER
                        ACCESS  read-only
                        STATUS  mandatory
                        DESCRIPTION
                                "Not implemented yet"
                        ::= { smuPortEntry 3 }

                smuPortAttachedNumber OBJECT-TYPE
                        SYNTAX  INTEGER
                        ACCESS  read-only
                        STATUS  mandatory
                        DESCRIPTION
                                "Not implemented yet"
                        ::= { smuPortEntry 4 }

                smuPortAttachedMac OBJECT-TYPE
                        SYNTAX  OCTET STRING (SIZE (6))
                        ACCESS  read-only
                        STATUS  mandatory
                        DESCRIPTION
                                "Not implemented yet"
                        ::= { smuPortEntry 5 }

                smuPortAttachedIp OBJECT-TYPE
                        SYNTAX  IpAddress
                        ACCESS  read-only
                        STATUS  mandatory
                        DESCRIPTION
                                "Not implemented yet"
                        ::= { smuPortEntry 6 }


        --
        -- Switch permanentEntries group
        --

         permanentEntriesTable OBJECT-TYPE
                SYNTAX  SEQUENCE OF PermanentEntriesEntry
                ACCESS  not-accessible
                STATUS  mandatory
                DESCRIPTION
                        ""
                ::= { permanentEntries 1 }

                permanentEntriesEntry OBJECT-TYPE
                        SYNTAX  PermanentEntriesEntry
                        ACCESS  not-accessible
                        STATUS  mandatory
                        DESCRIPTION
                                ""
                        INDEX { permanentEntriesMACAddr }
                        ::= { permanentEntriesTable 1 }

                PermanentEntriesEntry ::= SEQUENCE {
                        permanentEntriesMACAddr         OCTET STRING (SIZE (6)),
                        permanentEntriesPortId          INTEGER,
                        permanentEntriesCreateObj       INTEGER,
                        permanentEntriesDeleteObj       INTEGER
                }

                permanentEntriesMACAddr OBJECT-TYPE
                        SYNTAX  OCTET STRING (SIZE (6))
                        ACCESS  read-write
                        STATUS  mandatory
                        DESCRIPTION
                                "MAC address of permanent entry."
                        ::= { permanentEntriesEntry 1 }

                permanentEntriesPortId OBJECT-TYPE
                        SYNTAX  INTEGER
                        ACCESS  read-write
                        STATUS  mandatory
                        DESCRIPTION
                                "Port number for permanent entry."
                        ::= { permanentEntriesEntry 2 }

                permanentEntriesCreateObj OBJECT-TYPE
                        SYNTAX  INTEGER
                        ACCESS  read-write
                        STATUS  mandatory
                        DESCRIPTION
                                "Create a non-existant table entry. If
                                the entry already exists, genError is
                                returned.
                                Format: PortId (INTEGER)"
                        ::= { permanentEntriesEntry 3 }

                permanentEntriesDeleteObj OBJECT-TYPE
                        SYNTAX  INTEGER {
                                  delete(1)
                                }
                        ACCESS  read-write
                        STATUS  mandatory
                        DESCRIPTION
                                "Delete an existing table entry."
                        ::= { permanentEntriesEntry 4 }


        --
        -- Switch matrix module group
        --

        matrixModuleTable OBJECT-TYPE
                SYNTAX  SEQUENCE OF MatrixModuleEntry
                ACCESS  not-accessible
                STATUS  mandatory
                DESCRIPTION
                        "The table for general stack information"
                ::= { matrix 1 }

                matrixModuleEntry OBJECT-TYPE
                        SYNTAX  MatrixModuleEntry
                        ACCESS  not-accessible
                        STATUS  mandatory
                        DESCRIPTION
                                "Information for a specific module slot
                                about stackconnections, state, masterinformation"
                        INDEX { matrixModuleIndex }
                        ::= { matrixModuleTable 1 }

                MatrixModuleEntry ::= SEQUENCE {
                        matrixModuleIndex              INTEGER,
                        matrixModuleState              INTEGER,
			matrixNumberConnected          INTEGER,
                        matrixMasterPort               INTEGER
                }

                matrixModuleIndex OBJECT-TYPE
                        SYNTAX  INTEGER
                        ACCESS  read-only
                        STATUS  mandatory
                        DESCRIPTION
                                "Slot number to retrieve information for.
                                1 is slot A, 2 is slot B"
                        ::= { matrixModuleEntry 1 }

                matrixModuleState OBJECT-TYPE
                        SYNTAX  INTEGER {
                                  active(1),
                                  standby(2),
                                  error(3),
                                  back(4),
                                  notAvailable(99)
                                }
                        ACCESS  read-only
                        STATUS  mandatory
                        DESCRIPTION
                                "State of the matrix module. If
                                notAvailable(99) no matrix module can be seen,
                                active(1) is indicating a running module,
                                standby(2) is indicating a module that is
                                ready to become active if needed in a
                                redundant setup,
                                error(3) indicates a stack/redundancy
                                error,
                                back(4) is id the SIM module is running
                                in a back to back configuration"
                        ::= { matrixModuleEntry 2 }

                matrixNumberConnected OBJECT-TYPE
                        SYNTAX  INTEGER
                        ACCESS  read-only
                        STATUS  mandatory
                        DESCRIPTION
                                "The number of connected units to the
                                matrix module"
                        ::= { matrixModuleEntry 3 }

                matrixMasterPort OBJECT-TYPE
                        SYNTAX  INTEGER
                        ACCESS  read-only
                        STATUS  mandatory
                        DESCRIPTION
                                "0 means no master available, otherwise
                                an ifindex is returned (50->57)"
                        ::= { matrixModuleEntry 4 }

        matrixPortTable OBJECT-TYPE
                SYNTAX  SEQUENCE OF MatrixPortEntry
                ACCESS  not-accessible
                STATUS  mandatory
                DESCRIPTION
                        "Matrix module per port overview."
                ::= { matrix 2 }

                matrixPortEntry OBJECT-TYPE
                        SYNTAX  MatrixPortEntry
                        ACCESS  not-accessible
                        STATUS  mandatory
                        DESCRIPTION
                                 "Per switch of information gathered
                                 from the matrix module about the connected
                                 devices"
                        INDEX { matrixModuleIndex,
                                matrixPortIndex }
                        ::= { matrixPortTable 1 }

                MatrixPortEntry ::= SEQUENCE {
                        matrixPortModuleIndex     INTEGER,
                        matrixPortIndex           INTEGER,
                        matrixPort                INTEGER,
                        matrixPortType            INTEGER,
                        matrixPortMajVer          INTEGER,
                        matrixPortMinVer          INTEGER,
                        matrixPortMac             OCTET STRING,
                        matrixPortIp              IpAddress,
                        matrixPortSubnetMask      IpAddress,
                        matrixPortGateway         IpAddress
                }

                matrixPortModuleIndex OBJECT-TYPE
                        SYNTAX  INTEGER
                        ACCESS  read-only
                        STATUS  mandatory
                        DESCRIPTION
                                "Slot number to retrieve information for.
                                1 is slot A, 2 is slot B"
                        ::= { matrixPortEntry 1 }

                matrixPortIndex OBJECT-TYPE
                        SYNTAX  INTEGER
                        ACCESS  read-only
                        STATUS  mandatory
                        DESCRIPTION
                                "Index for retrieving the matrix ports"
                        ::= { matrixPortEntry 2 }

                matrixPort OBJECT-TYPE
                        SYNTAX  INTEGER
                        ACCESS  read-only
                        STATUS  mandatory
                        DESCRIPTION
                                "0 means no device is available, otherwise
                                an ifindex is returned (50->57)"
                        ::= { matrixPortEntry 3 }

                matrixPortType OBJECT-TYPE
                        SYNTAX  INTEGER {
                                  es510(1),
                                  es520(2),
                                  es550T(3),
                                  es550F(4),
                                  gb2(5),
                                  atm(6),
                                  notAvailable(99)
                                }
                        ACCESS  read-only
                        STATUS  mandatory
                        DESCRIPTION
                                "The connected device type,
                                notAvailable(99) if unknown or none"
                        ::= { matrixPortEntry 4 }

                matrixPortMajVer OBJECT-TYPE
                        SYNTAX  INTEGER
                        ACCESS  read-only
                        STATUS  mandatory
                        DESCRIPTION
                                "Major Version of matrix module shared memory
                                layout supported"
                        ::= { matrixPortEntry 5 }

                matrixPortMinVer OBJECT-TYPE
                        SYNTAX  INTEGER
                        ACCESS  read-only
                        STATUS  mandatory
                        DESCRIPTION
                                "Minor Version of matrix module shared memory
                                layout supported"
                        ::= { matrixPortEntry 6 }

                matrixPortMac OBJECT-TYPE
                        SYNTAX  OCTET STRING (SIZE (6))
                        ACCESS  read-only
                        STATUS  mandatory
                        DESCRIPTION
                                "Mac address of the device connected to a
                                specific matrix port. If the device does
                                not have a mac address it will be zero"
                        ::= { matrixPortEntry 7 }

                matrixPortIp OBJECT-TYPE
                        SYNTAX  IpAddress
                        ACCESS  read-write
                        STATUS  mandatory
                        DESCRIPTION
                                "IP address of the device connected to a
                                specific matrix port. If the device does
                                not have an IP address it will be zero"
                        ::= { matrixPortEntry 8 }

                matrixPortSubnetMask OBJECT-TYPE
                        SYNTAX  IpAddress
                        ACCESS  read-write
                        STATUS  mandatory
                        DESCRIPTION
                                "IP subnet mask of the device connected
                                 to a specific matrix port."
                        ::= { matrixPortEntry 9 }

                matrixPortGateway OBJECT-TYPE
                        SYNTAX  IpAddress
                        ACCESS  read-write
                        STATUS  mandatory
                        DESCRIPTION
                                "IP gateway of the device connected
                                 to a specific matrix port."
                        ::= { matrixPortEntry 10 }

        matrixLastChange OBJECT-TYPE
                SYNTAX  TimeTicks
                ACCESS  read-only
                STATUS  mandatory
                DESCRIPTION
                        "Timestamp for last change in matrix tables on any
                        Matrix module"
                ::= { matrix 3 }

        --
        -- Switch mediamodules group
        --

          mediaModuleTable   OBJECT-TYPE
              SYNTAX  SEQUENCE OF MediaModuleEntry
              ACCESS  not-accessible
              STATUS  mandatory
              DESCRIPTION
                      "Possible values of indices are
                       1..moduleMaxMediaModules"
              ::= { mediamodules    1 }

          mediaModuleEntry   OBJECT-TYPE
              SYNTAX  MediaModuleEntry
              ACCESS  not-accessible
              STATUS  mandatory
              DESCRIPTION
                      "Possible values of indices are
                       1..stackMaxChassis, 1..chassisMaxModules
                       and 1..moduleMaxMediaModules"
              INDEX   { mediaModuleChassisIndex,mediaModuleModuleIndex,mediaModuleIndex }
                      ::= { mediaModuleTable  1 }

          MediaModuleEntry ::=
              SEQUENCE {
                       moduleMode                   INTEGER,
                       matrixAttachmentPort         INTEGER
                       }

          moduleMode  OBJECT-TYPE
               SYNTAX  INTEGER {
                            stackMode(1),
                            standAloneMode(2)
                            }
               ACCESS  read-write
               STATUS  mandatory
               DESCRIPTION
                       "Hardware mode for media module.
                        Stack mode is 1 (connected to stack),
                        Stand alone mode is 2 (connected to switch)."
               ::= { mediaModuleEntry 1 }

          matrixAttachmentPort  OBJECT-TYPE
               SYNTAX  INTEGER
               ACCESS  read-only
               STATUS  mandatory
               DESCRIPTION
                       "Returns the port number of the Matrix port the
                        uplink mmodule is attached to. NB: will return 50 for
                        a uplink module not connected to a Matrix Module"
               ::= { mediaModuleEntry 2}

          mediaModuleChange   OBJECT-TYPE
              SYNTAX  TimeTicks
              ACCESS  read-only
              STATUS  mandatory
              DESCRIPTION
                      "The value of sysUpTime after any mediamoduletype
                       has changed"
              ::= { mediamodules    2 }
---
--- Trap section
---

    s500PermVioEvent TRAP-TYPE
        ENTERPRISE  s500
        VARIABLES   { portConfChassisIndex, portConfModuleIndex, portConfIndex }
        DESCRIPTION
                    "This trap is sent when there has been a permanent entry
                     violation. A MAC address has been detected at a
                     port, other than the port where it has been configured as a
                     permanent entry.
                     The variable portIfIndex indicates the port where the
                     MAC incorrectly has been detected.
                     The problem can be solved by re-configuring the MAC's
                     permanent entry, or by physically moving the MAC to the
                     port it has been configured for."
    ::= 1

    s500AdaptiveForwEvent TRAP-TYPE
        ENTERPRISE  s500
        VARIABLES   { portConfChassisIndex, portConfModuleIndex, portConfIndex,
                      portConfSwitchMode, portConfSwitchMode }
        DESCRIPTION
                    "This trap is sent when a port automatically is
                    changing forwarding mode. This will only happen when
                    the port has been configured to Adaptive mode.
                    The syntax is (Portnumber, New mode, Old mode)"
    ::= 2

    s500TemperatureEvent TRAP-TYPE
        ENTERPRISE  s500
        VARIABLES   { temperatureLevel }
        DESCRIPTION
                    "This trap indicates that the temparature of the
                    chassis has changed"
    ::= 3

    s500RedundantPowerSupplyEvent TRAP-TYPE
        ENTERPRISE  s500
        VARIABLES   { redundantPowerSupplyStatus }
        DESCRIPTION
                    "This trap indicates that the status of the redundant
                    power supply has changed"
    ::= 4


END
