TUBS-PROC-MIB DEFINITIONS ::= BEGIN

IMPORTS
    MODULE-IDENTITY, OBJECT-TYPE, 
    enterprises, Counter32, Integer32, TimeTicks, Unsigned32
    	FROM SNMPv2-SMI
    DisplayString, RowStatus, DateAndTime, TruthValue, TimeStamp, TAddress
        FROM SNMPv2-TC;

procMIB MODULE-IDENTITY
     LAST-UPDATED "9411152024Z"
     ORGANIZATION "TU Braunschweig"
     CONTACT-INFO
              "        Juergen Schoenwaelder

               Postal: TU Braunschweig
                       Bueltenweg 74/75
                       D-38108 Braunschweig
                       GERMANY

                  Tel: +49 531 391 3249
                  Fax: +49 531 391 5936

               E-mail: schoenw@ibr.cs.tu-bs.de"
     DESCRIPTION
             "Experimental MIB modules for process listings."
     ::= { enterprises tubs(1575) ibr(1) 3 }

procReload OBJECT-TYPE
	SYNTAX		DateAndTime
	MAX-ACCESS      read-write
	STATUS		current
	DESCRIPTION	"Any set operation will reload the process
		table. It contains a time stamp when the proc table
		was reloaded the last time."
	::= { procMIB 1 }

procTable OBJECT-TYPE
	SYNTAX     	SEQUENCE OF ProcEntry
	MAX-ACCESS 	not-accessible
	STATUS     	current
	DESCRIPTION	"The process table."
	::= { procMIB 2 }

procEntry OBJECT-TYPE
        SYNTAX     	ProcEntry
        MAX-ACCESS 	not-accessible
        STATUS     	current
        DESCRIPTION	"An entry for a process in the processes table."
        INDEX      	{ procID }
        ::= { procTable 1 }

ProcEntry ::= SEQUENCE {
        procID
        	Integer32,
	procCmd
		DisplayString
	}

procID OBJECT-TYPE
	SYNTAX		Integer32
	MAX-ACCESS	read-only
	STATUS		current
	DESCRIPTION	"The unique process ID."
	::= { procEntry 1 }

procCmd OBJECT-TYPE
	SYNTAX		DisplayString
	MAX-ACCESS	read-only
	STATUS		current
	DESCRIPTION	"The command name used to start this process."
	::= { procEntry 2 }

END
