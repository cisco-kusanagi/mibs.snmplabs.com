PAIRGAIN-DS1-MIB DEFINITIONS ::= BEGIN

IMPORTS
      MODULE-IDENTITY, OBJECT-TYPE, Integer32, Counter32, Gauge32,
      NOTIFICATION-TYPE, enterprises
        FROM SNMPv2-SMI
      MODULE-COMPLIANCE, OBJECT-GROUP, NOTIFICATION-GROUP
        FROM SNMPv2-CONF
	  pgainDSLAM
        FROM PAIRGAIN-COMMON-HD-MIB
      TEXTUAL-CONVENTION, DateAndTime, RowStatus
        FROM SNMPv2-TC
      InterfaceIndex, ifIndex
        FROM IF-MIB;

pgds1Mib MODULE-IDENTITY
      LAST-UPDATED "0003030000Z"
      ORGANIZATION "Pairgain Technologies Inc."
		  CONTACT-INFO    "
                    14402 Franklin Avenue
                    Tustin, CA  92780
                    "
      DESCRIPTION
        "The MIB module for managing PairGain ds1 OIDs
         within the  Avidia System."
      ::= {pgainDSLAM 17}

pgds1MibObjects        	OBJECT IDENTIFIER ::= { pgds1Mib 1 }

-- The  pgds1ConfigTable Table
pgds1ConfigTable OBJECT-TYPE
          SYNTAX  SEQUENCE OF Pgds1ConfigEntry
          MAX-ACCESS  not-accessible
          STATUS  current
          DESCRIPTION
                 "The pgDS1 Configuration table."
          ::= { pgds1MibObjects 1 }
pgds1ConfigEntry OBJECT-TYPE
          SYNTAX  Pgds1ConfigEntry
          MAX-ACCESS  not-accessible
          STATUS  current
          DESCRIPTION
                 "An entry in the DS1 Configuration table."
          INDEX   { pgds1LineIndex }
          ::= { pgds1ConfigTable 1 }
Pgds1ConfigEntry ::=
          SEQUENCE {
              pgds1LineIndex                        InterfaceIndex,
              pgds1IfIndex                          InterfaceIndex,
              pgds1LineBuildout                         INTEGER
     }
pgds1LineIndex OBJECT-TYPE
          SYNTAX  InterfaceIndex
          MAX-ACCESS  read-only
          STATUS  current
          DESCRIPTION
                 "This object should be made equal to ifIndex.  The
                 next paragraph describes its previous usage.
                 Making the object equal to ifIndex allows proper
                 use of ifStackTable and ds0/ds0bundle mibs.

                 Previously, this object is the identifier of a DS1
                 Interface on a managed device.  If there is an
                 ifEntry that is directly associated with this and
                 only this DS1 interface, it should have the same
                 value as ifIndex.  Otherwise, number the
                 dsx1LineIndices with an unique identifier
                 following the rules of choosing a number that is
                 greater than ifNumber and numbering the inside
                 interfaces (e.g., equipment side) with even
                 numbers and outside interfaces (e.g, network side)
                 with odd numbers."
          ::= { pgds1ConfigEntry 1 }
pgds1IfIndex OBJECT-TYPE
          SYNTAX  InterfaceIndex
          MAX-ACCESS  read-only
          STATUS  deprecated
          DESCRIPTION
                 "This value for this object is equal to the value
                 of ifIndex from the Interfaces table of MIB II
                 (RFC 1213)."
          ::= { pgds1ConfigEntry 2 }
pgds1LineBuildout OBJECT-TYPE
          SYNTAX  INTEGER (0..8)
          MAX-ACCESS  read-write
          STATUS  current
          DESCRIPTION
                 "The length of the ds1 line. This
                 objects provides information for line build out
                 circuitry.  This object is only useful if the
                 interface has configurable line build out
                 circuitry.
			0	0dB
			1	-7.5dB
			2	-15dB
			3	-22.5dB
			4	0-133ft
			5	133-266ft
			6	266-399ft
			7	399-533ft
			8	533-655ft "
          ::= { pgds1ConfigEntry 3 }
END
