IP-EXTENSION-MIB DEFINITIONS ::= BEGIN

-- Referencing the parent branch.

IMPORTS
            MODULE-IDENTITY, OBJECT-TYPE, IpAddress	FROM SNMPv2-SMI
            PhysAddress, RowStatus                      FROM SNMPv2-TC
	    cjnProtocol                             	FROM Cajun-ROOT;

cjnIpv4 MODULE-IDENTITY
        LAST-UPDATED "9902110000Z" -- Wednesday Feb 10, 1999"
        ORGANIZATION "Lucent's Concord Technology Center (CTC)"
        CONTACT-INFO
	        "Erick Crowell -- ecrowell@lucent.com
		 Raj Duggal (Group Leader) -- rduggal@lucent.com
		 Ira Steckler -- isteckler@lucent.com"
	DESCRIPTION
       		"Cajun Private IP version 4 mib extentions"
	::= { cjnProtocol 1 }


-- IP Global Extension Group
--
	cjnIpGblExt		OBJECT IDENTIFIER ::= { cjnIpv4 1 }

	cjnIpEnabled OBJECT-TYPE
	   SYNTAX INTEGER {
		enabled(1),
		disabled(2)
		}
	   MAX-ACCESS read-write
	   STATUS current
	   DESCRIPTION
	   "Enable / Disable IP Unicast on this system."
	   ::= { cjnIpGblExt 1 }
	
	cjnIpMCEnabled OBJECT-TYPE
	   SYNTAX INTEGER {
		enabled(1),
		disabled(2)
		}
	   MAX-ACCESS read-write
	   STATUS current
	   DESCRIPTION
	   "Enable or disable IP multicast on a global basis. 
	This will affect all IP interfaces set up to use multicast protocols."

	   ::= { cjnIpGblExt 2 }

	cjnIpRteEnabled OBJECT-TYPE
	   SYNTAX INTEGER {
		enabled(1),
		disabled(2)
		}
	   MAX-ACCESS read-write
	   STATUS current
	   DESCRIPTION
	   "Enable / Disable IP Routing on this system."
	   ::= { cjnIpGblExt 3 }
	
	cjnIpSSREnabled OBJECT-TYPE
	   SYNTAX INTEGER {
		enabled(1),
		disabled(2)
		}
	   MAX-ACCESS read-write
	   STATUS current
	   DESCRIPTION
	   "Enable / Disable the use of IP Source Routing."
	   ::= { cjnIpGblExt 4 }

	cjnMaxRoutes OBJECT-TYPE
	   SYNTAX INTEGER (1..999999)
	   MAX-ACCESS read-write
	   STATUS current
	   DESCRIPTION
	   "Specify the maximum number of routes that can be added to the routing table.
	Note that these routes refer only to IP Unicast entries."
      DEFVAL { 16384 }
	   ::= { cjnIpGblExt 5 }  

	cjnMaxArpCacheEntries OBJECT-TYPE
	   SYNTAX INTEGER (1..999999)
	   MAX-ACCESS read-write
	   STATUS current
	   DESCRIPTION
	   "Specify the maximum number of ARP cache entries. 
	Refers to the space available for the IP address table. When you 
	increase the number of entries, it may cause the table to be relearned 
	more frequently. Consequently, it will make address space 
	usage more efficient. "
      DEFVAL { 16384 }
	   ::= { cjnIpGblExt 6 }

	cjnIpGlobalStatsReset  OBJECT-TYPE
	    SYNTAX  INTEGER {
	      enable(1),
	      disable(2)
	    }	
	   MAX-ACCESS read-write
	   STATUS current
	   DESCRIPTION
	   "When set to the value enable (1) all IP Global statistics are
	  reset to zero after which the value of this MIB object returns to disable(2)"
	   ::= { cjnIpGblExt 7 }

-- Proxy Arp Configuration 
--
	cjnProxyArpGblConf	OBJECT IDENTIFIER ::= { cjnIpv4 2 }

	cjnProxyArpLimit  OBJECT-TYPE
	   SYNTAX INTEGER {
		enabled(1),
		disabled(2)
		}
	   MAX-ACCESS read-write
	   STATUS current
	   DESCRIPTION
	   "Enable or disable Proxy ARP on the same network. When 
	enabled, the router will only respond to ARP requests when
	the source and target IP address are in the same IP network
	and different IP subnets. When disabled, the router will only 
	respond to ARP requests when the source and target IP address
	are in different networks."
	   ::= { cjnProxyArpGblConf 1 }

	cjnProxyArpDefRte OBJECT-TYPE
	   SYNTAX INTEGER {
		enabled(1),
		disabled(2)
		}
	   MAX-ACCESS read-write
	   STATUS current
	   DESCRIPTION
	   "Enable or disable the use of the default route on your 
	Cajun switch as the route for Proxy ARPs."
	   ::= { cjnProxyArpGblConf 2 }

-- Routing protocol preferences
--
	cjnRtePrefGblGroup		OBJECT IDENTIFIER ::= { cjnIpv4 3 }

-- For all routing preference values the higher the preference number the
-- more preferable a route from that protocol become.

-- If all values are set equals the "natural" hierarchy takes effect
-- where the protocol with a lowest cost route takes preference.

	cjnLocalRtePref OBJECT-TYPE
	   SYNTAX INTEGER
	   MAX-ACCESS read-write
	   STATUS current
	   DESCRIPTION
	   "The Routing Preference of Local Routes."
	   ::= { cjnRtePrefGblGroup 1 }  

	cjnRIPRtePref OBJECT-TYPE
	   SYNTAX INTEGER
	   MAX-ACCESS read-write
	   STATUS current
	   DESCRIPTION
	   "The Routing Preference of RIP Routes."
	   ::= { cjnRtePrefGblGroup 2 }  

	cjnOSPFIntraAreaRtePref OBJECT-TYPE
	   SYNTAX INTEGER
	   MAX-ACCESS read-write
	   STATUS current
	   DESCRIPTION
	   "The Routing Preference of OSPF Intra-area Routes."
	   ::= { cjnRtePrefGblGroup 3 }  

	cjnOSPFExternalRtePref OBJECT-TYPE
	   SYNTAX INTEGER
	   MAX-ACCESS read-write
	   STATUS current
	   DESCRIPTION
	   "The Routing Preference of OSPF External Routes."
	   ::= { cjnRtePrefGblGroup 4 }  

	cjnHighPrefStaticRtePref OBJECT-TYPE
	   SYNTAX INTEGER
	   MAX-ACCESS read-write
	   STATUS current
	   DESCRIPTION
	   "The Routing Preference of High-preference Static Routes."
	   ::= { cjnRtePrefGblGroup 5 }  

	cjnLowPrefStaticRtePref OBJECT-TYPE
	   SYNTAX INTEGER
	   MAX-ACCESS read-write
	   STATUS current
	   DESCRIPTION
	   "The Routing Preference of Low-preference Static Routes."
	   ::= { cjnRtePrefGblGroup 6 }  

	cjnOSPFInterAreaRtePref OBJECT-TYPE
	   SYNTAX INTEGER
	   MAX-ACCESS read-write
	   STATUS current
	   DESCRIPTION
	   "The Routing Preference of OSPF Inter-area Routes."
	   ::= { cjnRtePrefGblGroup 7 }  

-- IP Global Statistics Group
--
	cjnIpGblStats	OBJECT IDENTIFIER ::= { cjnIpv4 4 }

	cjnIpInReceives OBJECT-TYPE
	   SYNTAX INTEGER
	   MAX-ACCESS read-write
	   STATUS current
	   DESCRIPTION
	   "The total number of input datagrams received from 
	interfaces, including those received in error. "
	   ::= { cjnIpGblStats 1 }

	cjnIpInHdrErrors OBJECT-TYPE
	   SYNTAX INTEGER
	   MAX-ACCESS read-write
	   STATUS current
	   DESCRIPTION
	   "The number of input datagrams discarded due to
	errors in their IP headers, including bad
	checksums, version number mismatch, other format
	errors, time-to-live exceeded, errors discovered
	in processing their IP options, etc. "
	   ::= { cjnIpGblStats 2 }

	cjnIpInAddrErrors  OBJECT-TYPE
	   SYNTAX INTEGER
	   MAX-ACCESS read-write
	   STATUS current
	   DESCRIPTION
	   "The number of input datagrams discarded because
	the IP address in their IP header's destination
	field was not a valid address to be received at
	this entity.  This count includes invalid
	addresses (e.g., 0.0.0.0) and addresses of
	unsupported Classes (e.g., Class E).  For entities
	which are not IP Gateways and therefore do not
	forward datagrams, this counter includes datagrams
	discarded because the destination address was nota 
	local address. "
	   ::= { cjnIpGblStats 3 }

	cjnIpForwDatagrams OBJECT-TYPE
	   SYNTAX INTEGER
	   MAX-ACCESS read-write
	   STATUS current
	   DESCRIPTION
	   "The number of input datagrams for which this
	entity was not their final IP destination, as a
	result of which an attempt was made to find a
	route to forward them to that final destination.
	In entities which do not act as IP Gateways, this
	counter will include only those packets which were
	Source-Routed via this entity, and the Source-
	Route option processing was successful. "
	   ::= { cjnIpGblStats 4 }

	cjnIpInUnknownProtos OBJECT-TYPE
	   SYNTAX INTEGER
	   MAX-ACCESS read-write
	   STATUS current
	   DESCRIPTION
	   "The number of locally-addressed datagrams
	received successfully but discarded because of an
	unknown or unsupported protocol."
	   ::= { cjnIpGblStats 5 }

	cjnIpInDiscards OBJECT-TYPE
	   SYNTAX INTEGER
	   MAX-ACCESS read-write
	   STATUS current
	   DESCRIPTION
	   "The number of input IP datagrams for which no
	problems were encountered to prevent their
	continued processing, but which were discarded
	(e.g., for lack of buffer space).  Note that this
	counter does not include any datagrams discarded
	while awaiting re-assembly. "
	   ::= { cjnIpGblStats 6 }

	cjnIpInDelivers OBJECT-TYPE
	   SYNTAX INTEGER
	   MAX-ACCESS read-write
	   STATUS current
	   DESCRIPTION
	   "The total number of input datagrams successfully
	delivered to IP user-protocols (including ICMP). "
	   ::= { cjnIpGblStats 7 }

	cjnIpOutRequests OBJECT-TYPE
	   SYNTAX INTEGER
	   MAX-ACCESS read-write
	   STATUS current
	   DESCRIPTION
	   "The total number of IP datagrams which local IP
	user-protocols (including ICMP) supplied to IP in
	requests for transmission.  Note that this counter
	does not include any datagrams counted in
	ipForwDatagrams. "
	   ::= { cjnIpGblStats 8 }

	cjnIpOutDiscards OBJECT-TYPE
	   SYNTAX INTEGER
	   MAX-ACCESS read-write
	   STATUS current
	   DESCRIPTION
	   "The number of output IP datagrams for which no
	problem was encountered to prevent their
	transmission to their destination, but which were
	discarded (e.g., for lack of buffer space).  Note
	that this counter would include datagrams counted
	in ipForwDatagrams if any such packets met this
	(discretionary) discard criterion. "
	   ::= { cjnIpGblStats 9 }

	cjnIpOutNoRoutes OBJECT-TYPE
	   SYNTAX INTEGER
	   MAX-ACCESS read-write
	   STATUS current
	   DESCRIPTION
	   "The number of IP datagrams discarded because no
	route could be found to transmit them to their
	destination.  Note that this counter includes any
	packets counted in ipForwDatagrams which meet this
	`no-route' criterion.  Note that this includes any
	datagarms which a host cannot route because all of
	its default gateways are down. "
	   ::= { cjnIpGblStats 10 }

	cjnIpReasmTimeout OBJECT-TYPE
	   SYNTAX INTEGER
	   MAX-ACCESS read-write
	   STATUS current
	   DESCRIPTION
	   "The maximum number of seconds which received
	fragments are held while they are awaiting
	reassembly at this entity. "
	   ::= { cjnIpGblStats 11 }

	cjnIpReasmReqds OBJECT-TYPE
	   SYNTAX INTEGER
	   MAX-ACCESS read-write
	   STATUS current
	   DESCRIPTION
	   "The number of IP fragments received which needed
	to be reassembled at this entity. "
	   ::= { cjnIpGblStats 12 }

	cjnIpReasmOKs OBJECT-TYPE
	   SYNTAX INTEGER
	   MAX-ACCESS read-write
	   STATUS current
	   DESCRIPTION
	   "The number of IP datagrams successfully re-
	assembled. "
	   ::= { cjnIpGblStats 13 }

	cjnIpReasmFails OBJECT-TYPE
	   SYNTAX INTEGER
	   MAX-ACCESS read-write
	   STATUS current
	   DESCRIPTION
	   "The number of failures detected by the IP re-
	assembly algorithm (for whatever reason: timed
	out, errors, etc).  Note that this is not
	necessarily a count of discarded IP fragments
	since some algorithms (notably the algorithm in
	RFC 815) can lose track of the number of fragments
	by combining them as they are received. "
	   ::= { cjnIpGblStats 14 }

	cjnIpFragOKs OBJECT-TYPE
	   SYNTAX INTEGER
	   MAX-ACCESS read-write
	   STATUS current
	   DESCRIPTION
	   "The number of IP datagrams that have been
	successfully fragmented at this entity. "
	   ::= { cjnIpGblStats 15 }

	cjnIpFragFails OBJECT-TYPE
	   SYNTAX INTEGER
	   MAX-ACCESS read-write
	   STATUS current
	   DESCRIPTION
	   "The number of IP datagrams that have been
	discarded because they needed to be fragmented at
	this entity but could not be, e.g., because their
	Don't Fragment flag was set. "
	   ::= { cjnIpGblStats 16 }

	cjnIpFragCreates OBJECT-TYPE
	   SYNTAX INTEGER
	   MAX-ACCESS read-write
	   STATUS current
	   DESCRIPTION
	   "The number of IP datagram fragments that have
	been generated as a result of fragmentation at
	this entity."
	   ::= { cjnIpGblStats 17 }

	cjnIpRoutingDiscards OBJECT-TYPE
	   SYNTAX INTEGER
	   MAX-ACCESS read-write
	   STATUS current
	   DESCRIPTION
	   "The number of routing entries which were chosen
	to be discarded even though they are valid.  One
	possible reason for discarding such an entry could
	be to free-up buffer space for other routing
	entries."
	   ::= { cjnIpGblStats 18 }

	cjnIcmpInMsgs OBJECT-TYPE
	   SYNTAX INTEGER
	   MAX-ACCESS read-write
	   STATUS current
	   DESCRIPTION
	   "The total number of ICMP messages which the
	entity received.  Note that this counter includes
	all those counted by icmpInErrors. "
	   ::= { cjnIpGblStats 19 }

	cjnIcmpInErrors OBJECT-TYPE
	   SYNTAX INTEGER
	   MAX-ACCESS read-write
	   STATUS current
	   DESCRIPTION
	   "The number of ICMP messages which the entity
	received but determined as having ICMP-specific
	errors (bad ICMP checksums, bad length, etc.). "
	   ::= { cjnIpGblStats 20 }

	cjnIcmpInDestUnreachs OBJECT-TYPE
	   SYNTAX INTEGER
	   MAX-ACCESS read-write
	   STATUS current
	   DESCRIPTION
	   "The number of ICMP Destination Unreachable
	messages received. "
	   ::= { cjnIpGblStats 21 }

	cjnIcmpInTimeExcds OBJECT-TYPE
	   SYNTAX INTEGER
	   MAX-ACCESS read-write
	   STATUS current
	   DESCRIPTION
	   "The number of ICMP Time Exceeded messages
	received."
	   ::= { cjnIpGblStats 22 }

	cjnIcmpInParmProbs OBJECT-TYPE
	   SYNTAX INTEGER
	   MAX-ACCESS read-write
	   STATUS current
	   DESCRIPTION
	   "The number of ICMP Parameter Problem messages
	received. "
	   ::= { cjnIpGblStats 23 }

	cjnIcmpInSrcQuenchs OBJECT-TYPE
	   SYNTAX INTEGER
	   MAX-ACCESS read-write
	   STATUS current
	   DESCRIPTION
	   "The number of ICMP Source Quench messages
	received. "
	   ::= { cjnIpGblStats 24 }

	cjnIcmpInRedirects OBJECT-TYPE
	   SYNTAX INTEGER
	   MAX-ACCESS read-write
	   STATUS current
	   DESCRIPTION
	   "The number of ICMP Redirect messages received."
	   ::= { cjnIpGblStats 25 }

	cjnIcmpInEchos OBJECT-TYPE
	   SYNTAX INTEGER
	   MAX-ACCESS read-write
	   STATUS current
	   DESCRIPTION
	   "The number of ICMP Echo (request) messages
	received. "
	   ::= { cjnIpGblStats 26 }

	cjnIcmpInEchoReps OBJECT-TYPE
	   SYNTAX INTEGER
	   MAX-ACCESS read-write
	   STATUS current
	   DESCRIPTION
	   "The number of ICMP Echo Reply messages received."
	   ::= { cjnIpGblStats 27 }

	cjnIcmpInTimestamps OBJECT-TYPE
	   SYNTAX INTEGER
	   MAX-ACCESS read-write
	   STATUS current
	   DESCRIPTION
	   "The number of ICMP Timestamp (request) messages
	received."
	   ::= { cjnIpGblStats 28 }

	cjnIcmpInTimestampReps OBJECT-TYPE
	   SYNTAX INTEGER
	   MAX-ACCESS read-write
	   STATUS current
	   DESCRIPTION
	   "The number of ICMP Timestamp Reply messages
	received."
	   ::= { cjnIpGblStats 29 }

	cjnIcmpInAddrMasks OBJECT-TYPE
	   SYNTAX INTEGER
	   MAX-ACCESS read-write
	   STATUS current
	   DESCRIPTION
	   "The number of ICMP Address Mask Request messages
	received. "
	   ::= { cjnIpGblStats 30 }

	cjnIcmpInAddrMaskReps OBJECT-TYPE
	   SYNTAX INTEGER
	   MAX-ACCESS read-write
	   STATUS current
	   DESCRIPTION
	   "The number of ICMP Address Mask Reply messages
	received. "
	   ::= { cjnIpGblStats 31 }

	cjnIcmpOutMsgs OBJECT-TYPE
	   SYNTAX INTEGER
	   MAX-ACCESS read-write
	   STATUS current
	   DESCRIPTION
	   "The total number of ICMP messages which this
	entity attempted to send.  Note that this counter
	includes all those counted by icmpOutErrors. "
	   ::= { cjnIpGblStats 32 }

	cjnIcmpOutErrors OBJECT-TYPE
	   SYNTAX INTEGER
	   MAX-ACCESS read-write
	   STATUS current
	   DESCRIPTION
	   "The number of ICMP messages which this entity did
	not send due to problems discovered within ICMP
	such as a lack of buffers.  This value should not
	include errors discovered outside the ICMP layer
	such as the inability of IP to route the resultant
	datagram.  In some implementations there may be no
	types of error which contribute to this counter'svalue. "
	   ::= { cjnIpGblStats 33 }

	cjnIcmpOutDestUnreachs OBJECT-TYPE
	   SYNTAX INTEGER
	   MAX-ACCESS read-write
	   STATUS current
	   DESCRIPTION
	   "The number of ICMP Destination Unreachable
	messages sent. "
	   ::= { cjnIpGblStats 34 }

	cjnIcmpOutTimeExcds OBJECT-TYPE
	   SYNTAX INTEGER
	   MAX-ACCESS read-write
	   STATUS current
	   DESCRIPTION
	   "The number of ICMP Time Exceeded messages sent. "
	   ::= { cjnIpGblStats 35 }

	cjnIcmpOutParmProbs OBJECT-TYPE
	   SYNTAX INTEGER
	   MAX-ACCESS read-write
	   STATUS current
	   DESCRIPTION
	   "The number of ICMP Parameter Problem messages sent. "
	   ::= { cjnIpGblStats 36 }

	cjnIcmpOutSrcQuenchs OBJECT-TYPE
	   SYNTAX INTEGER
	   MAX-ACCESS read-write
	   STATUS current
	   DESCRIPTION
	   "The number of ICMP Source Quench messages sent. "
	   ::= { cjnIpGblStats 37 }

	cjnIcmpOutRedirects OBJECT-TYPE
	   SYNTAX INTEGER
	   MAX-ACCESS read-write
	   STATUS current
	   DESCRIPTION
	   "The number of ICMP Redirect messages sent.  For a
	host, this object will always be zero, since hosts
	do not send redirects. "
	   ::= { cjnIpGblStats 38 }

	cjnIcmpOutEchos OBJECT-TYPE
	   SYNTAX INTEGER
	   MAX-ACCESS read-write
	   STATUS current
	   DESCRIPTION
	   "The number of ICMP Echo (request) messages sent."
	   ::= { cjnIpGblStats 39 }

	cjnIcmpOutEchoReps OBJECT-TYPE
	   SYNTAX INTEGER
	   MAX-ACCESS read-write
	   STATUS current
	   DESCRIPTION
	   "The number of ICMP Echo Reply messages sent. "
	   ::= { cjnIpGblStats 40 }

	cjnIcmpOutTimestamps OBJECT-TYPE
	   SYNTAX INTEGER
	   MAX-ACCESS read-write
	   STATUS current
	   DESCRIPTION
	   "The number of ICMP Timestamp (request) messages sent. "
	   ::= { cjnIpGblStats 41 }

	cjnIcmpOutTimestampReps OBJECT-TYPE
	   SYNTAX INTEGER
	   MAX-ACCESS read-write
	   STATUS current
	   DESCRIPTION
	   "The number of ICMP Timestamp Reply messages sent. "
	   ::= { cjnIpGblStats 42 }

	cjnIcmpOutAddrMasks OBJECT-TYPE
	   SYNTAX INTEGER
	   MAX-ACCESS read-write
	   STATUS current
	   DESCRIPTION
	   "The number of ICMP Address Mask Request messages sent. "
	   ::= { cjnIpGblStats 43 }

	cjnIcmpOutAddrMaskReps OBJECT-TYPE
	   SYNTAX INTEGER
	   MAX-ACCESS read-write
	   STATUS current
	   DESCRIPTION
	   "The number of ICMP Address Mask Reply messages sent. "
	   ::= { cjnIpGblStats 44 }

	cjnUdpInDatagrams OBJECT-TYPE
	   SYNTAX INTEGER
	   MAX-ACCESS read-write
	   STATUS current
	   DESCRIPTION
	   "The total number of UDP datagrams delivered to
	UDP users. "
	   ::= { cjnIpGblStats 45 }

	cjnUdpNoPorts OBJECT-TYPE
	   SYNTAX INTEGER
	   MAX-ACCESS read-write
	   STATUS current
	   DESCRIPTION
	   "The total number of received UDP datagrams for
	which there was no application at the destination
	port."
	   ::= { cjnIpGblStats 46 }

	cjnUdpInErrors OBJECT-TYPE
	   SYNTAX INTEGER
	   MAX-ACCESS read-write
	   STATUS current
	   DESCRIPTION
	   "The number of received UDP datagrams that could
	not be delivered for reasons other than the lack
	of an application at the destination port. "
	   ::= { cjnIpGblStats 47 }

	cjnUdpOutDatagrams OBJECT-TYPE
	   SYNTAX INTEGER
	   MAX-ACCESS read-write
	   STATUS current
	   DESCRIPTION
	   "The total number of UDP datagrams sent from this
	entity. "
	   ::= { cjnIpGblStats 48 }

	cjnIpmcForwDatagrams OBJECT-TYPE
	   SYNTAX INTEGER
	   MAX-ACCESS read-write
	   STATUS current
	   DESCRIPTION
	   " "
	   ::= { cjnIpGblStats 49 }

	cjnIpmcInDiscards OBJECT-TYPE
	   SYNTAX INTEGER
	   MAX-ACCESS read-write
	   STATUS current
	   DESCRIPTION
	   " "
	   ::= { cjnIpGblStats 50 }

	cjnIpmcInReceives OBJECT-TYPE
	   SYNTAX INTEGER
	   MAX-ACCESS read-write
	   STATUS current
	   DESCRIPTION
	   " "
	   ::= { cjnIpGblStats 51 }

          -- the IP Address Translation table

          -- The IP address translation table contain the IpAddress to
          -- `physical' address equivalences.  Some interfaces do not
          -- use translation tables for determining address
          -- equivalences (e.g., DDN-X.25 has an algorithmic method);
          -- if all interfaces are of this type, then the Address
          -- Translation table is empty, i.e., has zero entries.

        cjnIpNetToMediaGroup	OBJECT IDENTIFIER ::= { cjnIpv4 5 }	

        cjnIpNetToMediaTable OBJECT-TYPE
              SYNTAX  SEQUENCE OF CjnIpNetToMediaEntry
              MAX-ACCESS not-accessible
              STATUS  current
              DESCRIPTION
                      "The IP Address Translation table used for mapping
                      from IP addresses to physical addresses."
              ::= { cjnIpNetToMediaGroup 1 }

        cjnIpNetToMediaEntry OBJECT-TYPE
              SYNTAX  CjnIpNetToMediaEntry
              MAX-ACCESS  not-accessible
              STATUS  current
              DESCRIPTION
                      "Each entry contains one IpAddress to `physical'
                      address equivalence."
              INDEX   { cjnIpNetToMediaIfIndex,
			cjnIpNetToMediaNetAddress }
              ::= { cjnIpNetToMediaTable 1 }

        CjnIpNetToMediaEntry ::=
              SEQUENCE {
                  cjnIpNetToMediaIfIndex
                      INTEGER,
                  cjnIpNetToMediaPhysAddress
                      PhysAddress,
                  cjnIpNetToMediaRowStatus
                      RowStatus,
                  cjnIpNetToMediaNetAddress
                      IpAddress,
                  cjnIpNetToMediaType
                      INTEGER
              }

        cjnIpNetToMediaIfIndex OBJECT-TYPE
              SYNTAX  INTEGER
              MAX-ACCESS  read-only
              STATUS  current
              DESCRIPTION
                      "The interface on which this entry's equivalence
                      is effective.  The interface identified by a
                      particular value of this index is the same
                      interface as identified by the same value of
                      ifIndex. A value of 0 indicates that the entry
		      is a static entry and does not bind to any interface."
              ::= { cjnIpNetToMediaEntry 1 }

        cjnIpNetToMediaPhysAddress OBJECT-TYPE
              SYNTAX  PhysAddress
              MAX-ACCESS  read-create
              STATUS  current
              DESCRIPTION
                      "The media-dependent `physical' address."
              ::= { cjnIpNetToMediaEntry 2 }

        cjnIpNetToMediaNetAddress OBJECT-TYPE
              SYNTAX  IpAddress
              MAX-ACCESS  read-write
              STATUS  current
              DESCRIPTION
                      "The IpAddress corresponding to the media-
                      dependent `physical' address."
              ::= { cjnIpNetToMediaEntry 3 } 

        cjnIpNetToMediaRowStatus OBJECT-TYPE
              SYNTAX  RowStatus	
              MAX-ACCESS  read-create
              STATUS  current
              DESCRIPTION
                      "The Status of this entry in the table.  Note the
                       available states: 
                       active(1), -- Obviously Active.
                       notInService(2) -- Interface configured but disabled.
                       notReady(3), -- Interface NOT configured.
                       createAndGo(4), 
                       createAndWait(5)  
                       or destroy(6) "
	      ::= { cjnIpNetToMediaEntry 4 }

        cjnIpNetToMediaType OBJECT-TYPE
              SYNTAX  INTEGER {
                          other(1),        -- none of the following
                          invalid(2),      -- an invalidated mapping
                          dynamic(3),
                          static(4)
                      }
              MAX-ACCESS  read-create
              STATUS  current
              DESCRIPTION
                      "The type of mapping.
		       The only vaild setting is to change from
		       dynamic to static. Any other setting is invaild."

                      
              ::= { cjnIpNetToMediaEntry 5 }

END
