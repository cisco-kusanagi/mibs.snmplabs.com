RFC-HIPPI-MIB DEFINITIONS ::= BEGIN

    IMPORTS
        Counter
            FROM RFC1155-SMI
        OBJECT-TYPE
            FROM RFC-1212
        transmission
            FROM RFC1213-MIB
        nscTransmission
	    FROM NSC-MIB;

    --  This MIB module uses the extended OBJECT-TYPE macro
    --  as defined in [6].

    --  HIPPI MIB module

    nscHippi OBJECT IDENTIFIER ::= { nscTransmission 1 }

    --  textual conventions

    --  It would be best to be able to define a datatype for a large counter
    --  that could be implemented with two integers to provide for counters
    --  that quickly grow beyond the 32 bit value defined in SNMP. Unfortunately
    --  the current definitions do not allow for this so you will see the
    --  datatype implemented as two separate integers (rather then one
    --  datatype) in the MIB below.

    --  The hippiTable object type consists of a hippiEntry
    --  for every nscHippi object being supported.

    hippiNumber OBJECT-TYPE
        SYNTAX  INTEGER
        ACCESS  read-only
        STATUS  mandatory
        DESCRIPTION
            "An integer value indicating the number of
             HippiEntry objects that are in the hippiTable."
        ::= { nscHippi 1 }

    hippiTable OBJECT-TYPE
        SYNTAX  SEQUENCE OF HippiEntry
        ACCESS  not-accessible
        STATUS  mandatory
        DESCRIPTION
            "The HIPPI table of entries"
	--DEFAULT get-function get_hippiInteger
	--DEFAULT set-function set_hippiInteger
	--DEFAULT test-function test_hippiField
	--DEFAULT next-function next_hippiField
        ::= { nscHippi 2 }

    hippiEntry OBJECT-TYPE
        SYNTAX  HippiEntry
        ACCESS  not-accessible
        STATUS  mandatory
        DESCRIPTION
            "An entry in the HIPPI table"
        INDEX   {hippiPortNumber }
        ::= { hippiTable 1 }

    HippiEntry ::= SEQUENCE {
        hippiPortNumber
            INTEGER,
        hippiWordSize
            INTEGER,
        hippiEndPointType
            INTEGER,
        hippiWordCountHigh
            INTEGER,
        hippiWordCountLow
            INTEGER,
        hippiBurstCountHigh
            INTEGER,
        hippiBurstCountLow
            INTEGER,
        hippiPacketCountHigh
            INTEGER,
        hippiPacketCountLow
            INTEGER,
        hippiParityErrors
            Counter,
        hippiInputPortRejectCount
            Counter,
        hippiDestRejectCount
            Counter,
        hippiSourceRejectCount
            Counter,
        hippiDestDisconnectCount
            Counter,
        hippiSourceDisconnectCount
            Counter,
        hippiLastIField
            OCTET STRING,
        hippiConnectState
            INTEGER,
        hippiLastErrorType
            INTEGER,
        hippiLastErrorIField
            OCTET STRING,
        hippiInterconnectStatus
            INTEGER
    }

    --  Although the objects in this table are read-only, at the
    --  agent's discretion they may be made read-write so that the
    --  management station, when appropriately authorized, may be
    --  used to reset counters.

    hippiPortNumber OBJECT-TYPE
        SYNTAX  INTEGER
        ACCESS  read-only
        STATUS  mandatory
        DESCRIPTION
            "Unique sequential integer identifying the hippi media.
            This is the ifIndex value of the corresponding ifEntry."
        ::= { hippiEntry 1 }

    hippiWordSize OBJECT-TYPE
        SYNTAX  INTEGER {
                    hippi32bitDataBus (1),
                    hippi64bitDataBus (2)
                }
        ACCESS  read-only
        STATUS  mandatory
        DESCRIPTION
            "This enumerated value indicates the size of the data
            bus associated with this particular hippi media. This
            defines whether the interface operates at 800 or 1600
            Mbits/s."
        ::= { hippiEntry 2 }

    hippiEndPointType OBJECT-TYPE
        SYNTAX  INTEGER {
                    hippiSourceEndPoint (1),
                    hippiDestinationEndPoint (2)
                }
        ACCESS  read-only
        STATUS  mandatory
        DESCRIPTION
            "This enumerated value indicates whether this side
            of the hippi simplex connection is operating as a
            source or a destination."
        ::= { hippiEntry 3 }

    hippiWordCountHigh OBJECT-TYPE
        SYNTAX  INTEGER (0..'7FFFFFFF'h)
        ACCESS  read-write
        STATUS  mandatory
        DESCRIPTION
            "The word counter represents the number of words transferred
            through the media. The counter is cleared at power up or reset.
            This is the portion of the count above 999,999,999. This object
            may be made read-write accessible to allow resetting the counter
            from an appropriately configured management station."
        ::= { hippiEntry 4 }

    hippiWordCountLow OBJECT-TYPE
        SYNTAX  INTEGER (0..999999999)
        ACCESS  read-write
        STATUS  mandatory
        DESCRIPTION
            "The word counter represents the number of words transferred 
            through the media. The counter is cleared at power up or reset.
            This is the portion of the count below 1,000,000,000.  This
            object may be made read-write accessible to allow resetting
            the counter from an appropriately configured management station."
        ::= { hippiEntry 5 }

    hippiBurstCountHigh OBJECT-TYPE
        SYNTAX  INTEGER (0..'7FFFFFFF'h)
        ACCESS  read-write
        STATUS  mandatory
        DESCRIPTION
            "Total number of bursts transferred by this media since
            power up or reset. This is the portion of the count above
            999,999,999. This object may be made read-write accessible
            to allow resetting the counter from an appropriately
            configured management station."
        ::= { hippiEntry 6 }

    hippiBurstCountLow OBJECT-TYPE
        SYNTAX  INTEGER (0..999999999)
        ACCESS  read-write
        STATUS  mandatory
        DESCRIPTION
            "Total number of bursts transferred by this media since
            power up or reset. This is the portion of the count below
            1,000,000,000. This object may be made read-write accessible
            to allow resetting the counter from an appropriately
            configured management station."
        ::= { hippiEntry 7 }

    hippiPacketCountHigh OBJECT-TYPE
        SYNTAX  INTEGER (0..'7FFFFFFF'h)
        ACCESS  read-write
        STATUS  mandatory
        DESCRIPTION
            "The packet count represents the number of packets transferred
            on the media.  The counter is cleared at power up or reset. This
            is the portion of the count above 999,999,999. This object may
            be made read-write accessible to allow resetting the counter
            from an appropriately configured management station."
        ::= { hippiEntry 8 }

    hippiPacketCountLow OBJECT-TYPE
        SYNTAX  INTEGER (0..999999999)
        ACCESS  read-write
        STATUS  mandatory
        DESCRIPTION
            "The packet count represents the number of packets transferred
            on the media.  The counter is cleared at power up or reset. This
            is the portion of the count below 1,000,000,000. This object may
            be made read-write accessible to allow resetting the counter
            from an appropriately configured management station."
        ::= { hippiEntry 9 }

    hippiParityErrors OBJECT-TYPE
        SYNTAX  Counter
        ACCESS  read-write
        STATUS  mandatory
        DESCRIPTION
            "This counter represents the number of data parity errors
            that have occurred on the media since power up or reset. Since
            the parity bus is one directional from the source to the
            destination, this object only has meaning when the
            hippiEndPointType indicates this media is a destination end
            point. This object may be made read-write accessible to allow
            resetting the counter from an appropriately configured management
            station."
        ::= { hippiEntry 10 }

    hippiInputPortRejectCount OBJECT-TYPE
        SYNTAX  Counter
        ACCESS  read-write
        STATUS  mandatory
        DESCRIPTION
            "Total number of times that the input port has rejected a
            connection attempt due to I-Field parity errors, busy ports,
            or invalid source addresses since power up or reset. This object
            is only meaningful when the hippiEndPointType indicates this
            media is a destination end point. This object may be made read-
            write accessible to allow resetting the counter from an
            appropriately configured management station."
        ::= { hippiEntry 11 }

    hippiDestRejectCount OBJECT-TYPE
        SYNTAX  Counter
        ACCESS  read-write
        STATUS  mandatory
        DESCRIPTION
            "This counter represents the number of connection requests
            that were rejected by a destination end point since power up
            or reset. This object may be made read-write accessible to
            allow resetting the counter from an appropriately configured
            management station."
        ::= { hippiEntry 12 }

    hippiSourceRejectCount OBJECT-TYPE
        SYNTAX  Counter
        ACCESS  read-write
        STATUS  mandatory
        DESCRIPTION
            "This counter represents the number of times that the source
            end point dropped the connection request before the connection
            to the final destination was completed since power up or reset.
            This object may be made read-write accessible to allow resetting
            the counter from an appropriately configured management station."
        ::= { hippiEntry 13 }

    hippiDestDisconnectCount OBJECT-TYPE
        SYNTAX  Counter
        ACCESS  read-write
        STATUS  mandatory
        DESCRIPTION
            "This counter represents the number of completed connections
            that were terminated by a destination end point since power up
            or reset. This object may be made read-write accessible to allow
            resetting the counter from an appropriately configured management
            station."
        ::= { hippiEntry 14 }

    hippiSourceDisconnectCount OBJECT-TYPE
        SYNTAX  Counter
        ACCESS  read-write
        STATUS  mandatory
        DESCRIPTION
            "This counter represents the number of completed connections
            that were terminated normally by the source end point since
            power up or reset. This object may be made read-write accessible
            to allow resetting the counter from an appropriately configured
            management station."
        ::= { hippiEntry 15 }

    hippiLastIField OBJECT-TYPE
        SYNTAX  OCTET STRING (SIZE (4) )
        ACCESS  read-only
        STATUS  mandatory
        DESCRIPTION
            "This data type specifies the HIPPI I-Field address that was
            associated with the last operation on the media. If the
            hippiEndPointType indicates this is a Destination then the
            I-Field gives an indication of how the end point was addressed.
            If the media is a Source then the I-Field indicates the last
            address that the media attempted to connect to."
	--DEFAULT get-function get_hippiIField
        ::= { hippiEntry 16 }

    hippiConnectState OBJECT-TYPE
        SYNTAX  INTEGER {
                    hippiDisconnect (1),
                    hippiConnectRequest (2),
                    hippiConnected (3)
                }
        ACCESS  read-only
        STATUS  mandatory
        DESCRIPTION
            "Indicates the current connection state of the media."
        ::= { hippiEntry 17 }

    hippiLastErrorType OBJECT-TYPE
        SYNTAX  INTEGER {
                    hippiErrorTypeReject (1),
                    hippiErrorTypeBusy (2),
                    hippiErrorTypeTimeout (3),
                    hippiErrorTypeParityError (4),
                    hippiErrorTypeInvalidAddress (5)
                }
        ACCESS  read-only
        STATUS  mandatory
        DESCRIPTION
            "Contains the type identifier of the last error that was
            encountered on this media. The type identifier and the
            hippiLastErrorIField values are intended to be used together
            to aid in determining line connection problems."
        ::= { hippiEntry 18 }

    hippiLastErrorIField OBJECT-TYPE
        SYNTAX  OCTET STRING (SIZE (4) )
        ACCESS  read-only
        STATUS  mandatory
        DESCRIPTION
            "This data type specifies the HIPPI I-Field address that
            was associated with the last error for this media. The
            hippiLastErrorType along with this I-Field information is
            intended to help in determining connection problems. If the
            hippiEndPointType indicates this is a Destination then the
            I-Field gives an indication of how the end point was addressed.
            If the media is a Source then the I-Field indicates the last
            address that the media attempted to connect to"
	--DEFAULT get-function get_hippiIField
        ::= { hippiEntry 19 }

    hippiInterconnectStatus OBJECT-TYPE
        SYNTAX  INTEGER (0..'F'h)
        ACCESS  read-only
        STATUS  mandatory
        DESCRIPTION
            "As defined in HIPPI-PH, HIPPI connections have interconnect
            signals that are carried to allow endpoints to determine power
            on and enable. These signals are also useful in determining
            that cables are established correctly. There are two (2) signals
            for all connections that are referred to as INTERCONNECT-A.
            These signals are used to identify a source to destination as
            well as a destination to source connection. In addition, 64 bit
            wide connections (1600 MB) have two (2) additional signals that
            are referred to as INTERCONNECT-B. These are exactly the same
            as the INTERCONNECT-A signals but are carried on the second set
            of cables that make up the 64 bit connection.

            These signals are encoded into the lowest order four (4) bits
            of the hippiInterconnectStatus object as follows:
                0 0 0 1   INTERCONNECT-A Source to Destination (1)
                0 0 1 0   INTERCONNECT-A Destination to Source (2)
                0 1 0 0   INTERCONNECT-B Source to Destination (4)
                1 0 0 0   INTERCONNECT-B Destination to Source (8)"
        ::= { hippiEntry 20 }

    END
