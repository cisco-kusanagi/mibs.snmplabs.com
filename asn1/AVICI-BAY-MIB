AVICI-BAY-MIB DEFINITIONS ::= BEGIN

    IMPORTS
        MODULE-IDENTITY,  OBJECT-TYPE, Counter32, Gauge32, Integer32,
        TimeTicks, NOTIFICATION-TYPE
            FROM SNMPv2-SMI
   	DisplayString
      	    FROM SNMPv2-TC
        MODULE-COMPLIANCE, OBJECT-GROUP, NOTIFICATION-GROUP
            FROM SNMPv2-CONF
        aviciMibs
            FROM AVICI-SMI
	AviciVoltageType, AviciHighAvailabilityType, AviciBayType,
        AviciSlotType, AviciProductIdType, AviciRevisionType,
        AviciPartNumberType, AviciSerialNumberType, AviciLedValue,
        AviciUnitType
            FROM AVICI-TC
	aviciSysTrapDescr
	    FROM AVICI-SYSTEM-MIB;
    
aviciBayMIB MODULE-IDENTITY
        LAST-UPDATED "990702121500Z"
        ORGANIZATION "Avici Systems Inc"
        CONTACT-INFO "        
                  Avici Systems, Inc.
                  101 Billerica Avenue
                  North Billerica, MA 01862-1256
 
                  (978) 964-2000
                  (978) 964-2100 (fax)
 
                  snmp@avici.com"
        DESCRIPTION
            "The MIB module for an Avici Bay."
        ::= { aviciMibs 4 }


aviciBayObjects                 OBJECT IDENTIFIER ::= { aviciBayMIB 1 }

aviciBayNotifications           OBJECT IDENTIFIER ::= { aviciBayMIB 2 }

aviciBayControllerNotifications OBJECT IDENTIFIER ::= { aviciBayMIB 3 }

aviciBayNotificationPrefix      OBJECT IDENTIFIER ::=
                                  { aviciBayNotifications 0 }

aviciBayControllerNotificationPrefix OBJECT IDENTIFIER ::=
                                  { aviciBayControllerNotifications 0 }

--  the Bay Table
--
--  This table contains all global attributes
--  of each bay.

aviciBayTable       OBJECT-TYPE
        SYNTAX      SEQUENCE OF AviciBayEntry
        MAX-ACCESS  not-accessible
        STATUS      current
        DESCRIPTION
            "This table contains parameters and state variables for
             each Avici bay."
        ::= { aviciBayObjects 1 }
    
aviciBayEntry       OBJECT-TYPE
        SYNTAX      AviciBayEntry
        MAX-ACCESS  not-accessible
        STATUS      current
        DESCRIPTION
            "An entry containing management information for
             each bay."
        INDEX       { aviciBayIndex }
        ::= { aviciBayTable 1 }
    
AviciBayEntry ::= SEQUENCE {
        aviciBayIndex                      		AviciBayType,
        aviciBayCriticalLed	                        AviciLedValue,
        aviciBayMajorLed	                   	AviciLedValue,
        aviciBayMinorLed	                   	AviciLedValue,
        aviciBayAlarmCutOff                             INTEGER,
        aviciBayModTempCriticalThreshold 		Integer32,
        aviciBayModTempMajorThreshold    		Integer32,
        aviciBayModTempMinorThreshold     		Integer32,
        aviciBayTempCriticalThreshold  			Integer32,
        aviciBayTempMajorThreshold     			Integer32,
        aviciBayTempMinorThreshold     			Integer32
    }
    
aviciBayIndex       OBJECT-TYPE
        SYNTAX      AviciBayType
        MAX-ACCESS  read-only
        STATUS      current
        DESCRIPTION
            "The index number of the bay entry."
        ::= { aviciBayEntry 1 }

aviciBayCriticalLed OBJECT-TYPE
        SYNTAX      AviciLedValue
        MAX-ACCESS  read-only
        STATUS      current
        DESCRIPTION
            "The state of the Critical Led on the Bay."
        ::= {  aviciBayEntry 2 }
    
aviciBayMajorLed    OBJECT-TYPE
        SYNTAX      AviciLedValue
        MAX-ACCESS  read-only
        STATUS      current
        DESCRIPTION
            "The state of the Major Led on the Bay."
        ::= {  aviciBayEntry 3 }

aviciBayMinorLed    OBJECT-TYPE
        SYNTAX      AviciLedValue
        MAX-ACCESS  read-only
        STATUS      current
        DESCRIPTION
            "The state of the Minor Led on the Bay."
        ::= {  aviciBayEntry 4 }

aviciBayAlarmCutOff OBJECT-TYPE
        SYNTAX  INTEGER { 
                  on(1), 
                  off(2) 
         }
        MAX-ACCESS  read-only
        STATUS      current
        DESCRIPTION
            "Central office alarms are triggered by a hardware condition.
             A write can only use the value off. This turns off the
	     Central Office audible alarms."
        ::= {  aviciBayEntry 5 }

aviciBayModTempCriticalThreshold  OBJECT-TYPE
        SYNTAX      Integer32
        MAX-ACCESS  read-only
        STATUS      current
        DESCRIPTION
            "The module temperature in degrees C above which a critical
             alarm will be triggered."
        ::= {  aviciBayEntry 6 }
    
aviciBayModTempMajorThreshold     OBJECT-TYPE
        SYNTAX      Integer32
        MAX-ACCESS  read-only
        STATUS      current
        DESCRIPTION
            "The module temperature in degrees C above which a major
             alarm will be triggered."
        ::= { aviciBayEntry 7 }
    
aviciBayModTempMinorThreshold  OBJECT-TYPE
        SYNTAX      Integer32
        MAX-ACCESS  read-only
        STATUS      current
        DESCRIPTION
            "The module temperature in degrees C above which a minor
             alarm will be triggered."
        ::= { aviciBayEntry 8 }
    
aviciBayTempCriticalThreshold  OBJECT-TYPE
        SYNTAX      Integer32
        MAX-ACCESS  read-only
        STATUS      current
        DESCRIPTION
            "The incoming ambient air temperature in degrees C above which
             a critical alarm will be triggered."
        ::= { aviciBayEntry 9 }
    
aviciBayTempMajorThreshold     OBJECT-TYPE
        SYNTAX      Integer32
        MAX-ACCESS  read-only
        STATUS      current
        DESCRIPTION
            "The incoming ambient air temperature in degrees C above which
             a major alarm will be triggered."
        ::= { aviciBayEntry 10 }
    
aviciBayTempMinorThreshold  OBJECT-TYPE
        SYNTAX      Integer32
        MAX-ACCESS  read-only
        STATUS      current
        DESCRIPTION
            "The incoming ambient air temperature in degrees C above which
             a minor alarm will be triggered."
        ::= { aviciBayEntry 11 }
    
--  the Bay Controller Table
--
--  This table contains all global attributes which control
--  the behaviour of each bay controller.

aviciBayControllerTable        OBJECT-TYPE
        SYNTAX      SEQUENCE OF AviciBayControllerEntry
        MAX-ACCESS  not-accessible
        STATUS      current
        DESCRIPTION
            "This table contains parameters and state variables for
             the bay controller."
        ::= { aviciBayObjects 2 }
    
aviciBayControllerEntry        OBJECT-TYPE
        SYNTAX      AviciBayControllerEntry
        MAX-ACCESS  not-accessible
        STATUS      current
        DESCRIPTION
            "A list of status and parameter values for
             each bay."
        INDEX       { aviciBayIndex, aviciBayControllerIndex }
        ::= { aviciBayControllerTable 1 }
    
AviciBayControllerEntry ::= SEQUENCE {
        aviciBayControllerIndex                 INTEGER,
        aviciBayControllerOperStatus            INTEGER,
        aviciBayControllerAdminStatus           INTEGER,
        aviciBayControllerPartNumber            AviciPartNumberType,
        aviciBayControllerSerialNumber          AviciSerialNumberType,
        aviciBayControllerRevision              AviciRevisionType,
        aviciBayControllerSoftwareVersion       DisplayString,
        aviciBayControllerFirmwareVersion       DisplayString,
        aviciBayControllerProductId             AviciProductIdType,
        aviciBayControllerProductSerialNumber   AviciSerialNumberType,
        aviciBayControllerProductRevision       AviciRevisionType,
        aviciBayControllerDescr                 DisplayString
    }
    
aviciBayControllerIndex       OBJECT-TYPE
        SYNTAX      INTEGER (1..2)
        MAX-ACCESS  read-only
        STATUS      current
        DESCRIPTION
            "The index number of the bay controller entry."
        ::= { aviciBayControllerEntry 1 }
 
aviciBayControllerOperStatus      OBJECT-TYPE
        SYNTAX      INTEGER {
                       down(1),           -- Down
                       passive(2),        -- Passive Operation
                       active(3),         -- Active Operation
                       failed(4)          -- Diagnostic or Failure Cleanup
                    }
        MAX-ACCESS  read-only
        STATUS      current
        DESCRIPTION
            "The current operational status of the
             bay controller."
        ::= { aviciBayControllerEntry 2 }
    
aviciBayControllerAdminStatus      OBJECT-TYPE
        SYNTAX      INTEGER {
                       reboot(1),         -- Cause a reboot of the board
                       passive(2),        -- Passive Operation
                       active(3),         -- Active Operation
                       diagnostic(4)      -- Run System Diagnostic (may reboot)
                    }
        MAX-ACCESS  read-write
        STATUS      current
        DESCRIPTION
            "The current admin status of the bay controller."
        ::= { aviciBayControllerEntry 3 }

aviciBayControllerPartNumber       OBJECT-TYPE
        SYNTAX      AviciPartNumberType
        MAX-ACCESS  read-only
        STATUS      current
        DESCRIPTION
            "The part number of this bay controller object."
        ::= { aviciBayControllerEntry 4 }  

  
aviciBayControllerSerialNumber       OBJECT-TYPE
        SYNTAX      AviciSerialNumberType
        MAX-ACCESS  read-only
        STATUS      current
        DESCRIPTION
            "The serial number of this bay controller object."
        ::= { aviciBayControllerEntry 5 }  

aviciBayControllerRevision   OBJECT-TYPE
        SYNTAX      AviciRevisionType
        MAX-ACCESS  read-only
        STATUS      current
        DESCRIPTION
            "The revision number of this bay controller object."
        ::= { aviciBayControllerEntry 6 } 

aviciBayControllerSoftwareVersion  OBJECT-TYPE
        SYNTAX      DisplayString (SIZE (0..255))
        MAX-ACCESS  read-only
        STATUS      current
        DESCRIPTION
            "The version of the software running on this bay controller object."
        ::= { aviciBayControllerEntry 7 }  

aviciBayControllerFirmwareVersion  OBJECT-TYPE
        SYNTAX      DisplayString (SIZE (0..255))
        MAX-ACCESS  read-only
        STATUS      current
        DESCRIPTION
            "The version of the firmware running on this bay controller object."
        ::= { aviciBayControllerEntry 8 }  

aviciBayControllerProductId   OBJECT-TYPE
        SYNTAX      AviciProductIdType
        MAX-ACCESS  read-only
        STATUS      current
        DESCRIPTION
            "The product identification number of this bay controller object."
        ::= { aviciBayControllerEntry 9 }  

aviciBayControllerProductSerialNumber   OBJECT-TYPE
        SYNTAX      AviciSerialNumberType
        MAX-ACCESS  read-only
        STATUS      current
        DESCRIPTION
            "The product serial number of this bay controller object."
        ::= { aviciBayControllerEntry 10 }  

aviciBayControllerProductRevision   OBJECT-TYPE
        SYNTAX      AviciRevisionType
        MAX-ACCESS  read-only
        STATUS      current
        DESCRIPTION
            "The product revision number of this bay controller object."
        ::= { aviciBayControllerEntry 11 }     

aviciBayControllerDescr OBJECT-TYPE
   	     SYNTAX      DisplayString (SIZE (0..255))
   	     MAX-ACCESS  read-only
   	     STATUS      current
   	     DESCRIPTION
           "A description of this bay controller object."
         ::= { aviciBayControllerEntry 12 }   
         
--  the Voltage table    
--
--  This table contains parameters and state variables for
--  voltage lines and rails.  Each bay contains eight voltage
--  rails used for backplane communication. 
    
aviciBayVoltageTable      OBJECT-TYPE
        SYNTAX      SEQUENCE OF AviciBayVoltageEntry
        MAX-ACCESS  not-accessible
        STATUS      current
        DESCRIPTION
            "This table contains parameters and state variables for
             voltage lines and rails.  Each bay contains eight voltage
             rails used for backplane communication."
        ::= { aviciBayObjects 3 }
    
aviciBayVoltageEntry      OBJECT-TYPE
        SYNTAX      AviciBayVoltageEntry
        MAX-ACCESS  not-accessible
        STATUS      current
        DESCRIPTION
            "A list of status and parameter values for
             voltage lines and rails."
        INDEX       { aviciBayIndex, aviciBayVoltageIndex }
        ::= { aviciBayVoltageTable 1 }
    
AviciBayVoltageEntry ::= SEQUENCE {
         aviciBayVoltageIndex   INTEGER,
         aviciBayVoltageType    AviciVoltageType,
         aviciBayVoltage        Integer32,
         aviciBayVoltageStatus  INTEGER,
         aviciBayVoltageDescr   DisplayString
    }
    
aviciBayVoltageIndex      OBJECT-TYPE
        SYNTAX      INTEGER (1..18)
        MAX-ACCESS  read-only
        STATUS      current
        DESCRIPTION
            "The index number of the voltage entry."
        ::= { aviciBayVoltageEntry 1 }
    
aviciBayVoltageType OBJECT-TYPE
        SYNTAX      AviciVoltageType
        MAX-ACCESS  read-only
        STATUS      current
        DESCRIPTION
            "The type of the voltage entry."
        ::= { aviciBayVoltageEntry 2 }
    
aviciBayVoltage     OBJECT-TYPE
        SYNTAX      Integer32
        MAX-ACCESS  read-only
        STATUS      current
        DESCRIPTION
            "The current actual logical voltage of the 
             line.  The logical voltage is the mapped value
             reported by the AD7870 ADC for the line."
        ::= { aviciBayVoltageEntry 3 }
        
aviciBayVoltageStatus     OBJECT-TYPE
        SYNTAX      INTEGER {
                        inSpec(1),
                        outSpec(2)        -- Line voltage is not within spec 
                    }
        MAX-ACCESS  read-only
        STATUS      current
        DESCRIPTION
            "The current state of the voltage device. If no failure has
             occurred, the value of this object is inSpec."
        ::= { aviciBayVoltageEntry 4 }

aviciBayVoltageDescr OBJECT-TYPE
   	SYNTAX      DisplayString (SIZE (0..255))
        MAX-ACCESS  read-only
   	STATUS      current
   	DESCRIPTION
            "A description of this voltage object."
         ::= { aviciBayVoltageEntry 5 }

    
--  the Fan table
--
--  This table contains parameters and state variables
--  for blowers.  
    
aviciBayFanTable    OBJECT-TYPE
        SYNTAX      SEQUENCE OF AviciBayFanEntry
        MAX-ACCESS  not-accessible
        STATUS      current
        DESCRIPTION
            "This table contains parameters and state variables
             for blowers.  There are up to 4 fans in a shelf
             installed at the bottom of each bay."
        ::= { aviciBayObjects 4 }
    
aviciBayFanEntry    OBJECT-TYPE
        SYNTAX      AviciBayFanEntry
        MAX-ACCESS  not-accessible
        STATUS      current
        DESCRIPTION
            "A list of status and parameter values for a
             fan controller."
        INDEX       { aviciBayIndex, aviciBayFanIndex }
        ::= { aviciBayFanTable 1 }
    
AviciBayFanEntry ::= SEQUENCE {
         aviciBayFanIndex         INTEGER,
         aviciBayFanAdminStatus   INTEGER,
         aviciBayFanOperStatus    INTEGER,
         aviciBayFanSpeed         Integer32,
         aviciBayFanCurrTemp      Integer32,
         aviciBayFanMaxTemp       Gauge32,
         aviciBayFanLedStatus     AviciLedValue,
         aviciBayFanCurrFailures  Integer32,
         aviciBayFanDescr         DisplayString
    }
    
aviciBayFanIndex    OBJECT-TYPE
        SYNTAX      INTEGER (1..4)
        MAX-ACCESS  read-only
        STATUS      current
        DESCRIPTION
            "The index number of the fan entry."
        ::= { aviciBayFanEntry 1 }
    
aviciBayFanAdminStatus   OBJECT-TYPE
        SYNTAX      INTEGER {
                        offline(1),     -- Ready for removal
                        autonomous(2),  -- Software control disabled
                        controlled(3)   -- Software control enabled
                    }
        MAX-ACCESS  read-only
        STATUS      current
        DESCRIPTION
            "The current administrative status of the fan."
        ::= { aviciBayFanEntry 2 }
    
aviciBayFanOperStatus    OBJECT-TYPE
        SYNTAX      INTEGER {
                        offline(1),      -- Ready for removal
                        autonomous(2),   -- Software control disabled
                        controlled(3),   -- Software control enabled
                        failed(4)        -- Service Required. Fan state
                                         -- unknown
                    }
        MAX-ACCESS  read-only
        STATUS      current
        DESCRIPTION
            "The current operational status of the fan."
        ::= { aviciBayFanEntry 3 }
    
aviciBayFanSpeed        OBJECT-TYPE
        SYNTAX      Integer32 (0..2700)
        MAX-ACCESS  read-only
        STATUS      current
        DESCRIPTION
            "The current speed of the fan in RPM."
        ::= { aviciBayFanEntry 4 }
    
aviciBayFanCurrTemp     OBJECT-TYPE
        SYNTAX      Integer32
        MAX-ACCESS  read-only
        STATUS      current
        DESCRIPTION
            "The current room temp at the fan in degrees C."
        ::= { aviciBayFanEntry 5 }
    
aviciBayFanMaxTemp      OBJECT-TYPE
        SYNTAX      Gauge32
        MAX-ACCESS  read-only
        STATUS      current
        DESCRIPTION
            "The maximum temperature at the fan since
             the bay controller booted in degrees C."
        ::= { aviciBayFanEntry 6 }
    
aviciBayFanLedStatus     OBJECT-TYPE
        SYNTAX      AviciLedValue
        MAX-ACCESS  read-only
        STATUS      current
        DESCRIPTION
            "The current status of the fan's LED. 
                    off         --  Fan normal
                    red         --  Fan failure
                    green       --  Fan in autonomous mode (self-controlled)"
        ::= { aviciBayFanEntry 7 }
               
aviciBayFanCurrFailures OBJECT-TYPE
   	   SYNTAX         Integer32 (0..511)
   	   MAX-ACCESS     read-only
   	   STATUS         current
   	   DESCRIPTION    
      	    "This variable specifies this fan object's current failures.
      	     A value of 0 means there are no current failures for this fan object. The value 
      	     represents a vector of bits, each specifying a type of fan failure:
            - Bit 0  Communication failure 
            - Bit 1  General failure (fan jammed, etc.)
            - Bit 2  Filter blocked
            - Bit 3  Bad or absent internal thermistor
            - Bit 4  Bad or absent external thermistor
            - Bit 5  Fan temperature above minor threshold but less than major
            - Bit 6  Fan temperature above major threshold but less than critical threshold
            - Bit 7  Fan temperature above critical threshold
		    "
	    ::= { aviciBayFanEntry 8 }
	    
aviciBayFanDescr OBJECT-TYPE
        SYNTAX      DisplayString (SIZE (0..255))
        MAX-ACCESS  read-only
        STATUS      current
        DESCRIPTION
            "A description of this fan object."
         ::= { aviciBayFanEntry 9 }
   
--
--  the Slot table
--        

aviciBaySlotTable   OBJECT-TYPE
        SYNTAX      SEQUENCE OF AviciBaySlotEntry
        MAX-ACCESS  not-accessible
        STATUS      current
        DESCRIPTION
            "This table contains parameters and state variables
             for the slots. "
        ::= { aviciBayObjects 5 }
    
aviciBaySlotEntry   OBJECT-TYPE
        SYNTAX      AviciBaySlotEntry
        MAX-ACCESS  not-accessible
        STATUS      current
        DESCRIPTION
            "A list of status and parameter values
             for each module in a TSR bay."
        INDEX       { aviciBayIndex, aviciSlotIndex }
        ::= { aviciBaySlotTable 1 }
    
AviciBaySlotEntry ::= SEQUENCE {
         aviciSlotIndex             AviciSlotType,
         aviciBaySlotStatus         INTEGER,
         aviciBaySlotRxOctets       Counter32,
         aviciBaySlotRxMessages     Counter32,
         aviciBaySlotRxDiscards     Counter32,
         aviciBaySlotRxProtoErrs    Counter32,
         aviciBaySlotRxIOErrs       Counter32,
         aviciBaySlotRxTimeouts     Counter32,
         aviciBaySlotTxOctets       Counter32,
         aviciBaySlotTxMessages     Counter32,
         aviciBaySlotTxDiscards     Counter32,
         aviciBaySlotTxProtoErrs    Counter32,
         aviciBaySlotTxIOErrs       Counter32,
         aviciBaySlotTxTimeouts     Counter32
    }
    
aviciSlotIndex      OBJECT-TYPE
        SYNTAX      AviciSlotType
        MAX-ACCESS  read-only
        STATUS      current
        DESCRIPTION
            "The index number of the slot entry."
        ::= { aviciBaySlotEntry 1 }

aviciBaySlotStatus  OBJECT-TYPE     
        SYNTAX      INTEGER {
                    empty(1),
                    occupied(2),
                    identified(3)
                    }
        MAX-ACCESS  read-only
        STATUS      current
        DESCRIPTION
            "The current state of the slot."
        ::= { aviciBaySlotEntry 2 }

aviciBaySlotRxOctets  OBJECT-TYPE
        SYNTAX      Counter32
        MAX-ACCESS  read-only
        STATUS      current
        DESCRIPTION
            "The total number of slot octets received."
        ::= { aviciBaySlotEntry 3 }
    
aviciBaySlotRxMessages  OBJECT-TYPE
        SYNTAX      Counter32
        MAX-ACCESS  read-only
        STATUS      current
        DESCRIPTION
            "The number of successful slot reads."
        ::= { aviciBaySlotEntry 4 }
    
aviciBaySlotRxDiscards  OBJECT-TYPE
        SYNTAX      Counter32
        MAX-ACCESS  read-only
        STATUS      current
        DESCRIPTION
            "The total number of slot received messages
             discarded for any reason."
        ::= { aviciBaySlotEntry 5 }
    
aviciBaySlotRxProtoErrs OBJECT-TYPE
        SYNTAX      Counter32
        MAX-ACCESS  read-only
        STATUS      current
        DESCRIPTION
            "The number of slot received messages
             discarded due to protocol error."
        ::= { aviciBaySlotEntry 6 }
    
aviciBaySlotRxIOErrs    OBJECT-TYPE
        SYNTAX      Counter32
        MAX-ACCESS  read-only
        STATUS      current
        DESCRIPTION
            "The number of slot received messages
             discarded due to I/O error."
        ::= { aviciBaySlotEntry 7 }
    
aviciBaySlotRxTimeouts  OBJECT-TYPE
        SYNTAX      Counter32
        MAX-ACCESS  read-only
        STATUS      current
        DESCRIPTION
            "The number of slot received messages
             discarded due to module timeout error."
        ::= { aviciBaySlotEntry 8 }
    
aviciBaySlotTxOctets  OBJECT-TYPE
        SYNTAX      Counter32
        MAX-ACCESS  read-only
        STATUS      current
        DESCRIPTION
            "The total number of slot octets sent."
        ::= { aviciBaySlotEntry 9 }
    
aviciBaySlotTxMessages  OBJECT-TYPE
        SYNTAX      Counter32
        MAX-ACCESS  read-only
        STATUS      current
        DESCRIPTION
            "The number of successful slot writes."
        ::= { aviciBaySlotEntry 10 }
    
aviciBaySlotTxDiscards  OBJECT-TYPE
        SYNTAX      Counter32
        MAX-ACCESS  read-only
        STATUS      current
        DESCRIPTION
            "The total number of slot send messages
             aborted for any reason."
        ::= { aviciBaySlotEntry 11 }
    
aviciBaySlotTxProtoErrs  OBJECT-TYPE
        SYNTAX      Counter32
        MAX-ACCESS  read-only
        STATUS      current
        DESCRIPTION
            "The number of slot send messages
             aborted due to protocol error."
        ::= { aviciBaySlotEntry 12 }
    
aviciBaySlotTxIOErrs  OBJECT-TYPE
        SYNTAX      Counter32
        MAX-ACCESS  read-only
        STATUS      current
        DESCRIPTION
            "The number of slot send messages
             aborted due to I/O error."
        ::= { aviciBaySlotEntry 13 }
    
aviciBaySlotTxTimeouts  OBJECT-TYPE
        SYNTAX      Counter32
        MAX-ACCESS  read-only
        STATUS      current
        DESCRIPTION
            "The number of slot send messages
             aborted due to module timeout error."
        ::= { aviciBaySlotEntry 14 }

--
-- Circuit Breaker Table
--
 
aviciBayBreakerTable OBJECT-TYPE 
     	SYNTAX SEQUENCE OF AviciBayBreakerEntry 
     	MAX-ACCESS not-accessible 
     	STATUS current 
     	DESCRIPTION 
     		"This table contains parameters and state variables for 
     		the 48-volt breakers at the top of the TSR chassis. There 
     		are 4 mains and 4 backups, one pair for each of the 4 
     		shelves." 
     ::= { aviciBayObjects 6 } 


aviciBayBreakerEntry OBJECT-TYPE 
     	SYNTAX AviciBayBreakerEntry 
     	MAX-ACCESS not-accessible 
     	STATUS current 
     	DESCRIPTION 
     		"The state and type of each breaker." 
     	INDEX { aviciBayIndex, aviciBayBreakerIndex } 
     ::= { aviciBayBreakerTable 1 } 


AviciBayBreakerEntry ::= SEQUENCE { 
     	aviciBayBreakerIndex  Integer32,
     	aviciBayBreakerType   AviciHighAvailabilityType,
     	aviciBayBreakerStatus INTEGER,
        aviciBayBreakerDescr  DisplayString
     } 


aviciBayBreakerIndex OBJECT-TYPE 
     	SYNTAX      Integer32
     	MAX-ACCESS read-only 
     	STATUS current 
     	DESCRIPTION 
     		"The index number of the breaker entry." 
     ::= { aviciBayBreakerEntry 1 } 


aviciBayBreakerType OBJECT-TYPE 
     	SYNTAX AviciHighAvailabilityType
     	MAX-ACCESS read-only 
     	STATUS current 
     	DESCRIPTION 
     		"The type of the breaker entry." 
     ::= { aviciBayBreakerEntry 2 } 

aviciBayBreakerStatus OBJECT-TYPE 
     	SYNTAX INTEGER { 
     		unknown(1), 
     		open(2),    -- Breaker has tripped 
     		closed(3)   -- Normal State 
     	} 
     	MAX-ACCESS read-only 
     	STATUS current 
     	DESCRIPTION 
     		"The current state of the breaker." 
     ::= { aviciBayBreakerEntry 3 } 

aviciBayBreakerDescr OBJECT-TYPE
   	     SYNTAX      DisplayString (SIZE (0..255))
   	     MAX-ACCESS  read-only
   	     STATUS      current
   	     DESCRIPTION
           "A description of this breaker object."
      ::= { aviciBayBreakerEntry 4 }
--
-- Central Office Alarm Objects
--


--  The aviciBayCoAlarmSystem group
--
--  a collection of objects common to all central office alarms
--

aviciBayCoAlarmSystem   OBJECT IDENTIFIER ::= { aviciBayObjects 7 }

     
aviciBayCoActiveAlarmCount  OBJECT-TYPE
         SYNTAX     Integer32
         MAX-ACCESS read-only
         STATUS     current
         DESCRIPTION
             "The number of current events causing central office alarms in
              this Avici bay. If there are no such current events, this
              object contains the value 0 "
       ::= { aviciBayCoAlarmSystem 1 }   

aviciBayCoAlarmLastChange OBJECT-TYPE
         SYNTAX     TimeTicks
         MAX-ACCESS read-only
         STATUS     current
         DESCRIPTION
             "The value of sysUpTime at the time the aviciBayCoAlarmTable
              changed."
        ::= { aviciBayCoAlarmSystem 2 }   
                 

--
-- Central Office Alarms Table - contains all current events causing central
-- office alarms in this Avici bay.
--

aviciBayCoAlarmTable OBJECT-TYPE 
     	SYNTAX SEQUENCE OF AviciBayCoAlarmEntry 
     	MAX-ACCESS not-accessible 
     	STATUS current 
     	DESCRIPTION 
     		"This table contains any currently active central office
     		alarms." 
     ::= { aviciBayObjects 8 } 

aviciBayCoAlarmEntry OBJECT-TYPE 
     	SYNTAX  AviciBayCoAlarmEntry 
     	MAX-ACCESS not-accessible 
     	STATUS current 
     	DESCRIPTION 
     		"A description of each active central office alarm." 
     	INDEX { aviciBayIndex, aviciBayCoAlarmIndex } 
     ::= { aviciBayCoAlarmTable 1 } 

AviciBayCoAlarmEntry ::= SEQUENCE {  
        aviciBayCoAlarmIndex INTEGER (1..65535),
        aviciBayCoAlarmType  INTEGER,
        aviciBayCoAlarmDescr DisplayString,
        aviciBayCoAlarmTime  TimeTicks,
        aviciBayCoAlarmUnitNum Integer32,
        aviciBayCoAlarmUnitType AviciUnitType
     }

aviciBayCoAlarmIndex OBJECT-TYPE
        SYNTAX      INTEGER (1..65535)
        MAX-ACCESS  read-only
        STATUS      current
        DESCRIPTION
            "The index of this central office alarm on this bay."
        ::= { aviciBayCoAlarmEntry 1 } 
        
aviciBayCoAlarmType OBJECT-TYPE 
     	SYNTAX INTEGER { 
     		critical(1), 
     		major(2),    
     		minor(3)   
     	} 
     	MAX-ACCESS read-only 
     	STATUS current 
     	DESCRIPTION 
     		"The severity level of this central office alarm." 
        ::= { aviciBayCoAlarmEntry 2 }

aviciBayCoAlarmDescr  OBJECT-TYPE
        SYNTAX      DisplayString (SIZE (0..255))
        MAX-ACCESS  read-only
        STATUS      current
        DESCRIPTION
            "A description of the event that caused this central office 
             alarm."
        ::= { aviciBayCoAlarmEntry 3 } 

aviciBayCoAlarmTime OBJECT-TYPE
        SYNTAX       TimeTicks
        MAX-ACCESS   read-only
        STATUS       current
        DESCRIPTION
            "The time this event occurred in hundreths of a second since the
             last time the system was rebooted."
       ::= { aviciBayCoAlarmEntry 4 }  

aviciBayCoAlarmUnitNum OBJECT-TYPE
        SYNTAX       Integer32
        MAX-ACCESS   read-only
        STATUS       current
        DESCRIPTION
            "The identification number of the failing component. If there is
             more than one failing component of the same unit type in a bay,
             then the identification number is the bay number."
        ::= { aviciBayCoAlarmEntry 5 } 

aviciBayCoAlarmUnitType OBJECT-TYPE
        SYNTAX       AviciUnitType
        MAX-ACCESS   read-only
        STATUS       current
        DESCRIPTION
            "The type of the failing component. If there is more than one 
             failing component of the same unit type in a bay, for example,
             a fan, then this value is multipleFailures. "
       ::= { aviciBayCoAlarmEntry 6 }  


--
-- the bay controller notifications
--
    

aviciBayControllerColdStart        NOTIFICATION-TYPE
	OBJECTS	{
                 aviciBayIndex,
                 aviciBayControllerIndex, aviciSysTrapDescr }
        STATUS       current
        DESCRIPTION
            "The aviciBayControllerColdStart notification signifies that
             the bay controller has powered-up."
        ::= { aviciBayControllerNotificationPrefix 1 }

aviciBayControllerWarmStart        NOTIFICATION-TYPE
        OBJECTS { aviciBayIndex, aviciBayControllerIndex, aviciSysTrapDescr }
        STATUS       current
        DESCRIPTION
            "The aviciBayControllerWarmStart notification signifies that the
             bay controller has been restarted."
        ::= { aviciBayControllerNotificationPrefix 2 }

aviciBayControllerDown        NOTIFICATION-TYPE
        OBJECTS { aviciBayIndex, aviciBayControllerIndex, aviciSysTrapDescr }
        STATUS       current
        DESCRIPTION
            "The aviciBayControllerDown notification signifies that a
             server is no longer communicating with the bay controller after
             having established communication."
        ::= { aviciBayControllerNotificationPrefix 3 }

--
-- the bay notifications
--

aviciBayVoltageNotification NOTIFICATION-TYPE
        OBJECTS { 
                aviciBayIndex, 
                aviciBayVoltageIndex, 
                aviciBayVoltage,
                aviciBayVoltageStatus,
                aviciSysTrapDescr
                }
        STATUS       current
        DESCRIPTION
            "A Voltage notification is sent when a change is detected in the 5
             volt backplane communication rails.  These backplane 
             communication rails are used by the bay controller to
             communicate with the occupant of a given slot.  There are 8
             rails, each servicing the slots in one half of a shelf in the
             bay (aviciBayVoltageIndex == rail):

              Rail   Slots
             ==============
               1    1 - 5
               2    6 - 10 
               3   11 - 15
               4   16 - 20
               5   21 - 25
               6   26 - 30
               7   31 - 35
               8   36 - 40

             If the voltage is out of specification, the communication path
             will not function.  When a given backplane communication channel
             is not functioning, modules serviced by this rail cannot be
             discovered (if a module is inserted) and will not be authorized
             to boot (if an existing module reboots).  The current voltage is
             reported in the aviciBayVoltage object.  A human readable
             description of the event triggering this notification is
             included in the aviciSysTrapDescr object."
    ::= { aviciBayNotificationPrefix 1 }

    
aviciBayFanNotification NOTIFICATION-TYPE
        OBJECTS {
                aviciBayIndex,
                aviciBayFanIndex,
                aviciBayFanCurrFailures,
                aviciSysTrapDescr
                }
        STATUS       current
        DESCRIPTION
            "A Fan notification is sent when the specified fan detects a 
             fault or clears a fault.  The current ambient air temperature
             entering the fan is reported in the aviciBayFanCurrTemp object.
             All existing fan faults are reported in the
             aviciBayFanCurrFailures object as a bitmap.  If no failures 
             exist, this object contains a 0.  A human readable description
             of the event triggering this notification is included in the
             aviciSysTrapDescr object.

             Communication Failure:  This failure indicates that the cooling
             module has been removed or the cooling module firmware is no
             longer communicating with the bay controller.  If a 
             communication failure occurs, the fans will run in autonomous
             mode until communication with the bay controller is
             reestablished.  Once communication is established, the failure
             is cleared.

             General Failure:  This failure indicates that the cooling module
             firmware is able to communicate with the bay controller and is
             reporting a broken fan.  This could mean that the fan is burned
             out, jammed, or the firmware is unable to sense fan speed due to
             tachometer failure.  When the problem is corrected, the failure
             is cleared.

             Filter Blocked:  This failure indicates that the fan  detected
             that the filter is blocked.  When the obstruction is removed
             from the filter or the clogged air filter is replaced, this
             failure will clear.

             Bad or absent internal thermistor:  This failure indicates that
             the fan internal thermistor is missing or is not functioning.
             If the thermister is not functioning, the fan cannot sense the
             incoming ambient air temperature.  The ambient temperature is
             used to control fan speed in autonomous mode and when there are
             no modules reporting their current temperature. 

             Bad or absent external thermistor:  This failure indicates that
             the fan external thermistor is expected to be installed and is
             not functioning. 

             Minor temperature threshold:  This failure indicates that the
             incoming ambient air temperature is above the minor threshold
             temperature, but below the major threshold temperature.  Either
             the cooling system in the building has failed, or it has
             insufficient cooling capacity for the equipment in the room.
             A rapid rise in temperature usually indicates cooling system
             failure whereas a slow rise usually indicates insufficient
             cooling capacity.  When the temperature drops below the minor
             threshold, this failure will clear.

             Major temperature threshold:  This failure indicates that the
             incoming ambient air temperature is above the major threshold
             temperature, but below the critical threshold temperature.
             Either the cooling system in the building has failed, or it has
             insufficient cooling capacity for the equipment in the room.
             A rapid rise in temperature usually indicates cooling system
             failure whereas a slow rise usually indicates insufficient
             cooling capacity.  When the temperature drops below the major
             threshold, this failure will clear.

             Critical temperature threshold:  This failure indicates that the
             incoming ambient air temperature is above the critical threshold
             temperature.  Either the cooling system in the building has 
             failed, or it has insufficient cooling capacity for the 
             equipment in the room.  A rapid rise in temperature usually
             indicates cooling system failure whereas a slow rise usually
             indicates insufficient cooling capacity.  When the temperature
             drops below the critical threshold, this failure will clear."
    ::= { aviciBayNotificationPrefix 2 }

   
aviciBayBreakerNotification NOTIFICATION-TYPE
        OBJECTS {
            aviciBayIndex,
            aviciBayBreakerIndex,
            aviciBayBreakerType,
            aviciBayBreakerStatus,
            aviciSysTrapDescr
     	} 
     	STATUS current 
     	DESCRIPTION 
            "A Breaker notification is sent when the specified breaker has
             tripped or been manually reset.  The breaker may have tripped
             due to a short circuit, excessive current being drawn, or by
             an excessively high incoming voltage.  This failure is cleared
             when the breaker is manually reset.  If the breaker is manually
             opened, no trap will be sent."
     ::= { aviciBayNotificationPrefix 3 } 

aviciBayMultiFanFailures NOTIFICATION-TYPE
        OBJECTS {
            aviciBayIndex,
            aviciSysTrapDescr
        }
        STATUS current 
     	DESCRIPTION 
            "Two or more fans have failed in this bay." 
        ::= { aviciBayNotificationPrefix 4 } 


aviciBayMultiBayControllerFailures NOTIFICATION-TYPE
        OBJECTS {
            aviciBayIndex,
            aviciSysTrapDescr
        }
        STATUS current 
     	DESCRIPTION 
            "Both bay controllers have failed in this bay." 
        ::= { aviciBayNotificationPrefix 5 } 

--
-- Conformance Information
--    

aviciBayMIBConformance OBJECT IDENTIFIER ::= { aviciBayMIB 4 }
aviciBayMIBCompliances OBJECT IDENTIFIER ::= { aviciBayMIBConformance 1 }
aviciBayMIBGroups OBJECT IDENTIFIER ::= { aviciBayMIBConformance 2 }

--
-- Compliance Statements
--

aviciBayMIBCompliance MODULE-COMPLIANCE
        STATUS current
        DESCRIPTION
            "The compliance statement for the aviciBay."
        MODULE
        MANDATORY-GROUPS {
            aviciBayGroup,
            aviciBayControllerGroup,
            aviciCentralOfficeGroup,
            aviciBayNotificationGroup
        }
    
        ::= { aviciBayMIBCompliances 1 } 

aviciBayGroup OBJECT-GROUP
        OBJECTS {
            aviciBayIndex,
            aviciBayCriticalLed,
            aviciBayMajorLed,
            aviciBayMinorLed,
            aviciBayAlarmCutOff,
            aviciBayModTempCriticalThreshold,
            aviciBayModTempMajorThreshold,
            aviciBayModTempMinorThreshold,
            aviciBayTempCriticalThreshold,
            aviciBayTempMajorThreshold,
            aviciBayTempMinorThreshold,
            aviciBayVoltageIndex,
            aviciBayVoltageType,
            aviciBayVoltage,
            aviciBayVoltageStatus,
            aviciBayVoltageDescr,
            aviciBayFanIndex,
            aviciBayFanAdminStatus,
            aviciBayFanOperStatus,
            aviciBayFanSpeed,
            aviciBayFanCurrTemp,
            aviciBayFanMaxTemp,
            aviciBayFanLedStatus,
            aviciBayFanCurrFailures,
            aviciBayFanDescr,
            aviciSlotIndex,
            aviciBaySlotStatus,
            aviciBaySlotRxOctets,
            aviciBaySlotRxMessages,
            aviciBaySlotRxDiscards,
            aviciBaySlotRxProtoErrs,
            aviciBaySlotRxIOErrs,
            aviciBaySlotRxTimeouts,
            aviciBaySlotTxOctets,
            aviciBaySlotTxMessages,
            aviciBaySlotTxDiscards,
            aviciBaySlotTxProtoErrs,
            aviciBaySlotTxIOErrs,
            aviciBaySlotTxTimeouts,
            aviciBayBreakerIndex,
            aviciBayBreakerType,
            aviciBayBreakerStatus,
            aviciBayBreakerDescr
        }
        STATUS     current
        DESCRIPTION
            "Objects for the bay."
        ::= { aviciBayMIBGroups 1 }

aviciBayControllerGroup OBJECT-GROUP
        OBJECTS {
            aviciBayControllerIndex,
            aviciBayControllerOperStatus,
            aviciBayControllerAdminStatus,
            aviciBayControllerPartNumber,
            aviciBayControllerSerialNumber,
            aviciBayControllerRevision,
            aviciBayControllerSoftwareVersion,
            aviciBayControllerFirmwareVersion,
            aviciBayControllerProductId,
            aviciBayControllerProductSerialNumber,
            aviciBayControllerProductRevision,
            aviciBayControllerDescr
        }
        STATUS     current
        DESCRIPTION
            "Objects for the bayController."
        ::= { aviciBayMIBGroups 2 }


aviciBayCentralOfficeGroup OBJECT-GROUP
        OBJECTS {
            aviciBayCoActiveAlarmCount,
            aviciBayCoAlarmLastChange,
            aviciBayCoAlarmIndex,
            aviciBayCoAlarmType,
            aviciBayCoAlarmDescr,
            aviciBayCoAlarmTime,
            aviciBayCoAlarmUnitNum,
            aviciBayCoAlarmUnitType
        }
        STATUS     current
        DESCRIPTION
            "Objects for the central office."
        ::= { aviciBayMIBGroups 3 }

aviciBayNotificationGroup NOTIFICATION-GROUP
        NOTIFICATIONS {
            aviciBayControllerColdStart,
            aviciBayControllerWarmStart,
            aviciBayControllerDown,    
            aviciBayVoltageNotification,
            aviciBayFanNotification,
            aviciBayBreakerNotification,
            aviciBayMultiFanFailures,
            aviciBayMultiBayControllerFailures
        }
        STATUS    current
        DESCRIPTION
            "Notifications for the bay."
        ::= { aviciBayMIBGroups 4 }

END
