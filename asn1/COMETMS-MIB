COMETMS-MIB DEFINITIONS ::= BEGIN


IMPORTS
	enterprises, IpAddress, Counter, TimeTicks
		FROM RFC1155-SMI
	OBJECT-TYPE
		FROM RFC-1212
	DisplayString
		FROM RFC-1213;


comet         OBJECT IDENTIFIER ::= { enterprises 22626 }
products      OBJECT IDENTIFIER ::= { comet 1 }
ms				    OBJECT IDENTIFIER ::= { products 4 }
settings      OBJECT IDENTIFIER ::= { ms 1 }
channels      OBJECT IDENTIFIER ::= { ms 2 }
chTable       OBJECT IDENTIFIER ::= { channels 1 }



-- Power Source MIB
-- Parameters (Prefix ps)

messageString OBJECT-TYPE
	SYNTAX		DisplayString (SIZE (0..128))
	ACCESS		read-only
	STATUS		mandatory
	DESCRIPTION	"Message giving more detailed information on alarms."
::= { settings 1 }

msName OBJECT-TYPE
	SYNTAX		DisplayString (SIZE (0..17))
	ACCESS		read-only
	STATUS		mandatory
	DESCRIPTION	"MS name "
::= { settings 2 }

serialNo OBJECT-TYPE
	SYNTAX		DisplayString (SIZE (0..8))
	ACCESS		read-only
	STATUS		mandatory
	DESCRIPTION	"MS serial number "
::= { settings 3 }

msType OBJECT-TYPE
	SYNTAX		INTEGER(0..255)
	ACCESS		read-only
	STATUS		mandatory
	DESCRIPTION	"MS type  "
::= { settings 4 }

selfTest OBJECT-TYPE
	SYNTAX		DisplayString (SIZE (0..30))
	ACCESS		read-only
	STATUS		mandatory
	DESCRIPTION	"System selftest status "
::= { settings 5 }

intAcc OBJECT-TYPE
	SYNTAX		DisplayString (SIZE (0..10))
	ACCESS		read-only
	STATUS		mandatory
	DESCRIPTION	"Internal Acoustic alarm"
::= { settings 6 }

extAcc OBJECT-TYPE
	SYNTAX		DisplayString (SIZE (0..10))
	ACCESS		read-only
	STATUS		mandatory
	DESCRIPTION	"Alarm out acoustic signalization."
::= { settings 7 }

memUsg OBJECT-TYPE
	SYNTAX		DisplayString (SIZE (0..22))
	ACCESS		read-only
	STATUS		mandatory
	DESCRIPTION	"Memory usage."
::= { settings 8 }

-----------------------------------------------------------------------
-- channels
-----------------------------------------------------------------------
chTable OBJECT-TYPE
	SYNTAX  SEQUENCE OF chEntry
	ACCESS  not-accessible
	STATUS  mandatory
	DESCRIPTION	"Channels information table ."
::= { channels 1 }

chEntry OBJECT-TYPE
	SYNTAX  chEntry
	ACCESS  not-accessible
	STATUS  optional
	DESCRIPTION	"Channels values entries."
	INDEX   { index }
::= { chTable 1 }

chEntry ::=
	SEQUENCE {
		channelName
			OCTET STRING,
		channelValue
			OCTET STRING,
		channelUnit
			OCTET STRING,
		channelAlarm
			OCTET STRING,
		channelProces
			OCTET STRING
		}


channelName OBJECT-TYPE
	SYNTAX		DisplayString (SIZE (0..17))
	ACCESS		read-only
	STATUS		mandatory
	DESCRIPTION	"Channel name."
::= { chEntry 1 }

channelValue OBJECT-TYPE
	SYNTAX		DisplayString (SIZE (0..40))
	ACCESS		read-only
	STATUS		mandatory
	DESCRIPTION	"Channel value."
::= { chEntry 2 }

channelUnit OBJECT-TYPE
	SYNTAX		DisplayString (SIZE (0..17))
	ACCESS		read-only
	STATUS		mandatory
	DESCRIPTION	"Channel unit."
::= { chEntry 3 }

channelAlarm OBJECT-TYPE
	SYNTAX		DisplayString (SIZE (0..17))
	ACCESS		read-only
	STATUS		mandatory
	DESCRIPTION	"Channels alarm state."
::= { chEntry 4 }

channelProces OBJECT-TYPE
	SYNTAX		DisplayString (SIZE (0..17))
	ACCESS		read-only
	STATUS		mandatory
	DESCRIPTION	"Channels proces name."
::= { chEntry 5 }

END
