DMTF-SERVICE-LAYER-MIB DEFINITIONS ::= BEGIN

IMPORTS
	OBJECT-TYPE, NOTIFICATION-TYPE,
	MODULE-IDENTITY, enterprises, Counter32, Counter64, Gauge32, Integer32
		FROM SNMPv2-SMI
	DmiDate,DmiString,
	dmiEventDateTime,dmiCompId,dmiEventSeverity,
	dmiEventStateKey,dmiEventAssociatedGroup,
	dmiEventSystem,dmiEventSubSystem
		FROM DMTF-DMI-MIB;

DmiCounter		::= Counter32
DmiCounter64		::= Counter64
DmiGauge		::= Gauge32
DmiInteger		::= Integer32
DmiOctetstring		::= OCTET STRING
DmiCompId		::= INTEGER
DmiGroupId		::= INTEGER

dmtf                	OBJECT IDENTIFIER ::= { enterprises 412 }
dmtfStdMifs         	OBJECT IDENTIFIER ::= { dmtf 2 }
dmtfDynOids         	OBJECT IDENTIFIER ::= { dmtf 3 }


dmtfServiceLayerMIF MODULE-IDENTITY
     LAST-UPDATED "9710221800Z"
     ORGANIZATION "Desktop Management Task Force"
     CONTACT-INFO
          "         DMTF Technical Advisory Committee

		    Mailstop JF2-53
                    2111 N.E. 25th Avenue
                    Hillsboro, OR 97124

		    Phone: +1 503 264-9300
                    Email: dmtf-info@dmtf.org
          "
     DESCRIPTION
          "This MIB is a translation of the DMTF Service Layer MIF
	  defined by the Desktop Management Interface Specfiication,
          based on the translation rules defined by the
          DMTF DMI to SNMP Mapping Standard, Version 1.0.

	  DMI-based systems running a DMI-to-SNMP Mapping
          Agent provide the ability to access DMI component
          instrumentation via SNMP protocol operations.
          "
::= { dmtfStdMifs 1 }

SdmtfComponentID ::= SEQUENCE {
	manufacturer	DmiString,
	product	DmiString,
	version	DmiString,
	serialNumber	DmiString,
	installation	DmiDate,
	verify	DmiInteger
}

dmtfComponentIDTable OBJECT-TYPE
	SYNTAX		SEQUENCE OF SdmtfComponentID
	MAX-ACCESS	not-accessible
	STATUS		current
	DESCRIPTION	"This group defines the attributes common to all components.
 This group is required."
	::= { dmtfServiceLayerMIF 1 }

dmtfComponentIDEntry OBJECT-TYPE
	SYNTAX		SdmtfComponentID
	MAX-ACCESS	not-accessible
	STATUS		current
	DESCRIPTION	"This group defines the attributes common to all components.
 This group is required."
	INDEX		{ DmiCompId,DmiGroupId }
	::= { dmtfComponentIDTable 1 }


manufacturer OBJECT-TYPE
	SYNTAX		DmiString
	MAX-ACCESS	read-only
	STATUS		current
	DESCRIPTION	"Manufacturer of this system."
	REFERENCE "'DMTF|ComponentID|001' 1"
	::= { dmtfComponentIDEntry 1 }

product OBJECT-TYPE
	SYNTAX		DmiString
	MAX-ACCESS	read-only
	STATUS		current
	DESCRIPTION	"Product name for this system."
	REFERENCE "'DMTF|ComponentID|001' 2"
	::= { dmtfComponentIDEntry 2 }

version OBJECT-TYPE
	SYNTAX		DmiString
	MAX-ACCESS	read-only
	STATUS		current
	DESCRIPTION	"Version number of this system."
	REFERENCE "'DMTF|ComponentID|001' 3"
	::= { dmtfComponentIDEntry 3 }

serialNumber OBJECT-TYPE
	SYNTAX		DmiString
	MAX-ACCESS	read-only
	STATUS		current
	DESCRIPTION	"Serial number for this system."
	REFERENCE "'DMTF|ComponentID|001' 4"
	::= { dmtfComponentIDEntry 4 }

installation OBJECT-TYPE
	SYNTAX		DmiDate
	MAX-ACCESS	read-only
	STATUS		current
	DESCRIPTION	"The time and date when this component was installed."
	REFERENCE "'DMTF|ComponentID|001' 5"
	::= { dmtfComponentIDEntry 5 }

verify OBJECT-TYPE
	SYNTAX		INTEGER {
		anErrorOccurredCheckStatusCode(0),
		thisComponentDoesNotExist(1),
		verificationIsNotSupported(2),
		reserved(3),
		thisComponentExistsButTheFunctionalityIsUntested(4),
		thisComponentExistsButTheFunctionalityIsUnknown(5),
		thisComponentExistsAndIsNotFunctioningCorrectly(6),
		thisComponentExistsAndIsFunctioningCorrectly(7)
	}
	MAX-ACCESS	read-only
	STATUS		current
	DESCRIPTION	"A code that provides a level of verification that the component
is still installed and working."
	REFERENCE "'DMTF|ComponentID|001' 6"
	::= { dmtfComponentIDEntry 6 }


SdmtfSPIndicationSubscription ::= SEQUENCE {
	dmtfSPIndicationSubscriptionState INTEGER,
	subscriberRPCType	DmiString,
	subscriberTransportType	DmiString,
	subscriberAddressing	DmiString,
	subscriberID	DmiInteger,
	subscriptionExpirationWarningDateStamp	DmiDate,
	subscriptionExpirationDateStamp	DmiDate,
	indicationFailureThreshold	DmiInteger
}

dmtfSPIndicationSubscriptionTable OBJECT-TYPE
	SYNTAX		SEQUENCE OF SdmtfSPIndicationSubscription
	MAX-ACCESS	not-accessible
	STATUS		current
	DESCRIPTION	"This group defines the subscription information for a managing
node interested in indications from this system. The DMI Service Provider
will maintain this as table, with each row representing an individual managing
node."
	::= { dmtfServiceLayerMIF 3 }

dmtfSPIndicationSubscriptionEntry OBJECT-TYPE
	SYNTAX		SdmtfSPIndicationSubscription
	MAX-ACCESS	not-accessible
	STATUS		current
	DESCRIPTION	"This group defines the subscription information for a managing
node interested in indications from this system. The DMI Service Provider
will maintain this as table, with each row representing an individual managing
node."
	INDEX		{ DmiCompId,DmiGroupId, subscriberRPCType, subscriberTransportType, subscriberAddressing, subscriberID }
	::= { dmtfSPIndicationSubscriptionTable 1 }


dmtfSPIndicationSubscriptionState OBJECT-TYPE
	SYNTAX		INTEGER {
		active(1),
		notInService(2),
		notReady(3),
		createAndGo(4),
		createAndWait(5),
		destroy(6)
	}
	MAX-ACCESS	read-write
	STATUS		current
	REFERENCE "'DMTF|SP Indication Subscription|001' 0"
	::= { dmtfSPIndicationSubscriptionEntry 0 }

subscriberRPCType OBJECT-TYPE
	SYNTAX		DmiString
	MAX-ACCESS	read-only
	STATUS		current
	DESCRIPTION	"This is an identifier of the type of RPC in use by the Subscribe
."
	REFERENCE "'DMTF|SP Indication Subscription|001' 1"
	::= { dmtfSPIndicationSubscriptionEntry 1 }

subscriberTransportType OBJECT-TYPE
	SYNTAX		DmiString
	MAX-ACCESS	read-only
	STATUS		current
	DESCRIPTION	"This is an identifier of the type of Transport in use by
the Subscriber."
	REFERENCE "'DMTF|SP Indication Subscription|001' 2"
	::= { dmtfSPIndicationSubscriptionEntry 2 }

subscriberAddressing OBJECT-TYPE
	SYNTAX		DmiString
	MAX-ACCESS	read-only
	STATUS		current
	DESCRIPTION	"Addressing information of the managing node that has subscribed
to receive indications from this managed node."
	REFERENCE "'DMTF|SP Indication Subscription|001' 3"
	::= { dmtfSPIndicationSubscriptionEntry 3 }

subscriberID OBJECT-TYPE
	SYNTAX		DmiInteger
	MAX-ACCESS	read-only
	STATUS		current
	DESCRIPTION	"An ID or handle passed by the managing node to the SP.  It
is opaque to the DMI Service Provider, but is used in all indications to
the managing node as a correlator, or multiplexing handle.  It is intended
only for use by the managing node."
	REFERENCE "'DMTF|SP Indication Subscription|001' 4"
	::= { dmtfSPIndicationSubscriptionEntry 4 }

subscriptionExpirationWarningDateStamp OBJECT-TYPE
	SYNTAX		DmiDate
	MAX-ACCESS	read-only
	STATUS		current
	DESCRIPTION	"On this date and time, the DMI Service Provider will send
an indication to the subscriber, notifying it that the subscription is about
to lapse."
	REFERENCE "'DMTF|SP Indication Subscription|001' 5"
	::= { dmtfSPIndicationSubscriptionEntry 5 }

subscriptionExpirationDateStamp OBJECT-TYPE
	SYNTAX		DmiDate
	MAX-ACCESS	read-only
	STATUS		current
	DESCRIPTION	"On this date, after having issued the appropriate number
of warning indications as described by the Subscription Expiration Warning
Timestamp, this subscription will lapse."
	REFERENCE "'DMTF|SP Indication Subscription|001' 6"
	::= { dmtfSPIndicationSubscriptionEntry 6 }

indicationFailureThreshold OBJECT-TYPE
	SYNTAX		DmiInteger
	MAX-ACCESS	read-only
	STATUS		current
	DESCRIPTION	"This is a number that corresponds to the number of indication
transmission failures to allow, before the indication subscription is considered
to be invalid, and removed."
	REFERENCE "'DMTF|SP Indication Subscription|001' 7"
	::= { dmtfSPIndicationSubscriptionEntry 7 }


SdmtfSPFilterInformation ::= SEQUENCE {
	dmtfSPFilterInformationState INTEGER,
	subscriberRPCType	DmiString,
	subscriberTransportType	DmiString,
	subscriberAddressing	DmiString,
	subscriberID	DmiInteger,
	componentID-1	DmiInteger,
	groupClassString	DmiString,
	eventSeverity	DmiInteger
}

dmtfSPFilterInformationTable OBJECT-TYPE
	SYNTAX		SEQUENCE OF SdmtfSPFilterInformation
	MAX-ACCESS	not-accessible
	STATUS		current
	DESCRIPTION	"This group defines a row in a table of event filters.  One
filter is created for each combination of ComponentID, Class, and severity
that the managing node is interested in."
	::= { dmtfServiceLayerMIF 4 }

dmtfSPFilterInformationEntry OBJECT-TYPE
	SYNTAX		SdmtfSPFilterInformation
	MAX-ACCESS	not-accessible
	STATUS		current
	DESCRIPTION	"This group defines a row in a table of event filters.  One
filter is created for each combination of ComponentID, Class, and severity
that the managing node is interested in."
	INDEX		{ DmiCompId,DmiGroupId, subscriberRPCType, subscriberTransportType, subscriberAddressing, subscriberID, componentID, groupClassString }
	::= { dmtfSPFilterInformationTable 1 }


dmtfSPFilterInformationState OBJECT-TYPE
	SYNTAX		INTEGER {
		active(1),
		notInService(2),
		notReady(3),
		createAndGo(4),
		createAndWait(5),
		destroy(6)
	}
	MAX-ACCESS	read-write
	STATUS		current
	REFERENCE "'DMTF|SPFilterInformation|001' 0"
	::= { dmtfSPFilterInformationEntry 0 }

subscriberRPCType2 OBJECT-TYPE
	SYNTAX		DmiString
	MAX-ACCESS	read-only
	STATUS		current
	DESCRIPTION	"This is an identifier of the type of RPC in use by the Subscribe
."
	REFERENCE "'DMTF|SPFilterInformation|001' 1"
	::= { dmtfSPFilterInformationEntry 1 }

subscriberTransportType2 OBJECT-TYPE
	SYNTAX		DmiString
	MAX-ACCESS	read-only
	STATUS		current
	DESCRIPTION	"This is an identifier of the type of Transport in use by
the Subscriber."
	REFERENCE "'DMTF|SPFilterInformation|001' 2"
	::= { dmtfSPFilterInformationEntry 2 }

subscriberAddressing2 OBJECT-TYPE
	SYNTAX		DmiString
	MAX-ACCESS	read-only
	STATUS		current
	DESCRIPTION	"Addressing information of the managing node that has subscribed
to receive indications from this managed node."
	REFERENCE "'DMTF|SPFilterInformation|001' 3"
	::= { dmtfSPFilterInformationEntry 3 }

subscriberID2 OBJECT-TYPE
	SYNTAX		DmiInteger
	MAX-ACCESS	read-only
	STATUS		current
	DESCRIPTION	"An ID or handle passed by the managing node to the SP.  It
is opaque to the DMI Service Provider, but is used in all indications to
the managing node as a correlator, or multiplexing handle.  It is intended
only for use by the managing node."
	REFERENCE "'DMTF|SPFilterInformation|001' 4"
	::= { dmtfSPFilterInformationEntry 4 }

componentID OBJECT-TYPE
	SYNTAX		DmiInteger
	MAX-ACCESS	read-only
	STATUS		current
	DESCRIPTION	"The component ID, as assigned by the DMI Service Provider,
of the component from which the managing node wishes to receive events."
	REFERENCE "'DMTF|SPFilterInformation|001' 5"
	::= { dmtfSPFilterInformationEntry 5 }

groupClassString OBJECT-TYPE
	SYNTAX		DmiString
	MAX-ACCESS	read-only
	STATUS		current
	DESCRIPTION	"The Class string corresponding to the groups within the above
mentioned component, from which the managing node wishes to receive events."
	REFERENCE "'DMTF|SPFilterInformation|001' 6"
	::= { dmtfSPFilterInformationEntry 6 }

eventSeverity OBJECT-TYPE
	SYNTAX		INTEGER {
		monitor(1),
		information(2),
		oK(4),
		nonCritical-1(8),
		critical(16),
		nonRecoverable(32)
	}
	MAX-ACCESS	read-write
	STATUS		current
	DESCRIPTION	"The event severity level, at which an event originating in
a group described by the previous class and componentID, should be forwarded
to the managing node."
	REFERENCE "'DMTF|SPFilterInformation|001' 7"
	::= { dmtfSPFilterInformationEntry 7 }

END
