NCR-CORESST-MIB DEFINITIONS ::= BEGIN

--
-- NCR Core SST MIB
--

IMPORTS
    enterprises, Counter
        FROM RFC1155-SMI
    OBJECT-TYPE
        FROM RFC-1212
    DisplayString
        FROM RFC1213-MIB
    TruthValue
        FROM RFC1253-MIB;

        ncr                     OBJECT IDENTIFIER ::= { enterprises 191 }
        sst                     OBJECT IDENTIFIER ::= { ncr 39 }
        sstCore                 OBJECT IDENTIFIER ::= { sst 1 }
        sstProduct              OBJECT IDENTIFIER ::= { sst 13 }
        sstObjs                 OBJECT IDENTIFIER ::= { sstProduct 2}
        sstGeneral              OBJECT IDENTIFIER ::= { sstObjs 1 }    
        sstDevice               OBJECT IDENTIFIER ::= { sstObjs 2 }
        sstApplic               OBJECT IDENTIFIER ::= { sstObjs 3 }
        sstLogs                 OBJECT IDENTIFIER ::= { sstObjs 4 }
        sstTrans                OBJECT IDENTIFIER ::= { sstApplic 1 }
        sstAgent                OBJECT IDENTIFIER ::= { sstApplic 2 }


-----------------------------------------------------------
-- SST Core - Component State Definition
-----------------------------------------------------------

VerificationState ::= INTEGER { doesNotExist       (1),
                                verifyNotSupported (2),
                                reserved           (3),
                                untested           (4),
                                unknown            (5),
                                failed             (6),
                                good               (7) }

-----------------------------------------------------------
-- SST Core - SST General Definitions
-----------------------------------------------------------

SSTService      ::= INTEGER { inService             (1),
                              outService            (2),
                              outServicePending     (3) }

SSTReset        ::= INTEGER { cancelReset           (1),
                              reset                 (2),
                              resetPending          (3) }

SSTState	::= INTEGER { healthy		    (1),
			      attentionSoon	    (2),
			      attentionNow	    (3),
			      notConfigured	    (4) }			

AgentState	::= INTEGER { ncrPlatformNotInstalled (1),
			     serviceStopped	     (2),
                             serviceStartPending     (3),
                             serviceRunning          (5) }

-----------------------------------------------------------
-- Management Protocol Type Table
-----------------------------------------------------------

sstManagementProtocolTable OBJECT-TYPE
    SYNTAX  SEQUENCE OF SstManagementProtocolEntry
    ACCESS  not-accessible
    STATUS  mandatory
    DESCRIPTION
    "This table defines the attributes of the management
     protocol used for the agent."
    ::= { sstCore 1 }

sstManagementProtocolEntry OBJECT-TYPE
       SYNTAX  SstManagementProtocolEntry
       ACCESS  not-accessible
       STATUS  mandatory
       DESCRIPTION
       ""
       INDEX { sstManagementProtocolIndex }
       ::= { sstManagementProtocolTable 1 }

SstManagementProtocolEntry ::=
       SEQUENCE { 
          sstManagementProtocolIndex        INTEGER,
          sstManagementProtocolType         OCTET STRING 
        }

sstManagementProtocolIndex OBJECT-TYPE
    SYNTAX INTEGER
    ACCESS read-only
    STATUS mandatory    
    DESCRIPTION 
    "This is a unique number for every entry in the management 
    protocol table."
    ::= { sstManagementProtocolEntry 1 }

sstManagementProtocolType OBJECT-TYPE
    SYNTAX DisplayString
    ACCESS read-only
    STATUS mandatory
    DESCRIPTION 
    "The management protocol, which identifies the type 
    of SST and the type of agent running on the SST."
    ::= { sstManagementProtocolEntry 2 }

-----------------------------------------------------------
-- Component State Table
-----------------------------------------------------------

sstComponentStateTable OBJECT-TYPE
    SYNTAX  SEQUENCE OF SstComponentStateEntry
    ACCESS  not-accessible
    STATUS  mandatory
    DESCRIPTION                        
    "This table defines all the information about 
     state changes in device modules."
    ::= { sstCore 2 }

sstComponentStateEntry OBJECT-TYPE
    SYNTAX  SstComponentStateEntry
    ACCESS  not-accessible
    STATUS  mandatory
    DESCRIPTION
    "This defines the contents of the table."
    INDEX   { sstComponentStateIndex }
    ::= { sstComponentStateTable 1 }

SstComponentStateEntry ::=
    SEQUENCE { 
           sstComponentStateIndex            INTEGER,
           sstComponentStateDescrip          DisplayString,
           sstComponentStateCategory         DisplayString,
           sstComponentStateCode             DisplayString,
           sstComponentStateDateTimeEvt      DisplayString,
           sstComponentStateDateTimeProx     DisplayString,
           sstComponentStateDevice           DisplayString,
           sstComponentStateData             DisplayString,
           sstComponentStateSubIndex         INTEGER
         }

sstComponentStateIndex OBJECT-TYPE
    SYNTAX INTEGER
    ACCESS read-only
    STATUS mandatory    
    DESCRIPTION 
    "A unique number for every entry in the component state table."
    ::= { sstComponentStateEntry 1 }

sstComponentStateDescrip OBJECT-TYPE
    SYNTAX DisplayString
    ACCESS read-only
    STATUS mandatory    
    DESCRIPTION 
    "A description of the operational state of the module."
    ::= { sstComponentStateEntry 2 }

sstComponentStateCategory OBJECT-TYPE
    SYNTAX DisplayString
    ACCESS read-only
    STATUS mandatory    
    DESCRIPTION 
    "This indicates the current summary state of the module."
    ::= { sstComponentStateEntry 3 }

sstComponentStateCode OBJECT-TYPE
    SYNTAX DisplayString
    ACCESS read-only
    STATUS mandatory    
    DESCRIPTION 
    "The platform-defined status code of the 
    operational state of the module."
    ::= { sstComponentStateEntry 4 }

sstComponentStateDateTimeEvt OBJECT-TYPE
    SYNTAX DisplayString
    ACCESS read-only
    STATUS mandatory    
    DESCRIPTION 
    "The date, in DD/MM/YYYY format, and the time, in HH:MM:SS format, 
    when the event occurred on the SST."
    ::= { sstComponentStateEntry 5 }

sstComponentStateDateTimeProx OBJECT-TYPE
    SYNTAX DisplayString
    ACCESS read-only
    STATUS mandatory    
    DESCRIPTION 
    "The date, in DD/MM/YYYY format, and the time, in HH:MM:SS format,
    when the event was processed by a proxy. This can be NULL if 
    not processed by a proxy."
    ::= { sstComponentStateEntry 6 }

sstComponentStateDevice OBJECT-TYPE
    SYNTAX DisplayString
    ACCESS read-only
    STATUS mandatory    
    DESCRIPTION 
    "The short description of the device and the 
    name of the module affected by the event."
    ::= { sstComponentStateEntry 7 }

sstComponentStateData OBJECT-TYPE
    SYNTAX DisplayString
    ACCESS read-only
    STATUS mandatory    
    DESCRIPTION 
    "Any additional information if available, otherwise NULL."
    ::= { sstComponentStateEntry 8 }


sstComponentStateSubIndex OBJECT-TYPE
    SYNTAX INTEGER
    ACCESS read-only
    STATUS mandatory    
    DESCRIPTION 
    "The index entry of the first service in 
    the services table associated with the device."
    ::= { sstComponentStateEntry 9 }

-----------------------------------------------------------
-- Service State Table
-----------------------------------------------------------

sstServiceStateTable OBJECT-TYPE
    SYNTAX  SEQUENCE OF SstServiceStateEntry
    ACCESS  not-accessible
    STATUS  mandatory
    DESCRIPTION                        
    "This table defines all the information about   
    state changes in device services (indicating service availability)."
    ::= { sstCore 4 }

sstServiceStateEntry OBJECT-TYPE
    SYNTAX  SstServiceStateEntry
    ACCESS  not-accessible
    STATUS  mandatory
    DESCRIPTION
    "This defines the contents of the table."
    INDEX   { sstServiceStateIndex }
    ::= { sstServiceStateTable 1 }

SstServiceStateEntry ::=
    SEQUENCE { 
          sstServiceStateIndex               INTEGER,
          sstServiceStateStates              DisplayString,
          sstServiceStateInfo                DisplayString,
          sstServiceStateDateTimeEvt         DisplayString,
          sstServiceStateDateTimeProx        DisplayString,
          sstServiceStateService             DisplayString,
          sstServiceStateAdditionalData      DisplayString
        }

sstServiceStateIndex OBJECT-TYPE
    SYNTAX INTEGER
    ACCESS read-only
    STATUS mandatory    
    DESCRIPTION 
    "A unique number for every entry in the service state table."
    ::= { sstServiceStateEntry 1 }

sstServiceStateStates OBJECT-TYPE
    SYNTAX DisplayString
    ACCESS read-only
    STATUS mandatory    
    DESCRIPTION 
    "The current state of each part of the service."
    ::= { sstServiceStateEntry 2 }

sstServiceStateInfo OBJECT-TYPE
    SYNTAX DisplayString
    ACCESS read-only
    STATUS mandatory    
    DESCRIPTION 
    "The maintenance information associated with the 
    last state change in the service: M-Code, M-Status, M-Data."
    ::= { sstServiceStateEntry 3 }

sstServiceStateDateTimeEvt OBJECT-TYPE
    SYNTAX DisplayString
    ACCESS read-only
    STATUS mandatory    
    DESCRIPTION 
    "The date, in DD/MM/YYYY format, and the time, in HH:MM:SS format, 
    of the last state change in the service."
    ::= { sstServiceStateEntry 4 }

sstServiceStateDateTimeProx OBJECT-TYPE
    SYNTAX DisplayString
    ACCESS read-only
    STATUS mandatory    
    DESCRIPTION 
    "The date, in DD/MM/YYYY format, and the time, in HH:MM:SS format,
    when the event was processed by a proxy. This can be NULL if 
    not processed by a proxy."
    ::= { sstServiceStateEntry 5 }

sstServiceStateService OBJECT-TYPE
    SYNTAX DisplayString
    ACCESS read-only
    STATUS mandatory    
    DESCRIPTION 
    "The name of the service affected by the state change."
    ::= { sstServiceStateEntry 6 }

sstServiceStateAdditionalData OBJECT-TYPE
    SYNTAX DisplayString
    ACCESS read-only
    STATUS mandatory    
    DESCRIPTION 
    "The replenishment status data associated with the
    last state change in the service: RS-Data."
    ::= { sstServiceStateEntry 7 }

-----------------------------------------------------------
-- SST General State Table
-----------------------------------------------------------

sstManufacturer OBJECT-TYPE
    SYNTAX DisplayString
    ACCESS read-only
    STATUS mandatory    
    DESCRIPTION 
    "The name of the manufacturer of the product."
    ::= { sstGeneral 1 }

sstProduct OBJECT-TYPE
    SYNTAX DisplayString
    ACCESS read-write
    STATUS mandatory    
    DESCRIPTION 
    "The SST model."
    ::= { sstGeneral 2 }

sstVersion OBJECT-TYPE
    SYNTAX DisplayString
    ACCESS read-only
    STATUS mandatory    
    DESCRIPTION 
    "The version of the NCR platform running on the SST."
    ::= { sstGeneral 3 }

sstSerialNo OBJECT-TYPE
    SYNTAX DisplayString
    ACCESS read-write
    STATUS mandatory    
    DESCRIPTION 
    "The serial number of the SST."
    ::= { sstGeneral 4 }

sstInstallation OBJECT-TYPE
    SYNTAX DisplayString
    ACCESS read-only
    STATUS mandatory    
    DESCRIPTION 
    "The date and time, in DMI-defined format, 
    when the component was (last) installed."
    ::= { sstGeneral 5 }

sstVerify OBJECT-TYPE
    SYNTAX VerificationState
    ACCESS read-only
    STATUS mandatory    
    DESCRIPTION 
    "A level of verification that the DMI component is installed and 
     functioning.  This attribute is not currently supported."
    ::= { sstGeneral 6 }

sstService OBJECT-TYPE
    SYNTAX SSTService
    ACCESS read-write
    STATUS mandatory    
    DESCRIPTION 
    "This indicates the current availability of 
    the transaction application. Set this value to causes the agent 
    to attempt to put the SST in or out of service."
    ::= { sstGeneral 7 }



sstReset OBJECT-TYPE
    SYNTAX SSTReset
    ACCESS read-write
    STATUS mandatory    
    DESCRIPTION 
    "A signal to the SST to shut down and reset. Get this value to 
    see whether a reset is pending. Set this value to cause the agent 
    to reset the SST within 300 seconds, or cancel the reset."
    ::= { sstGeneral 8 }

sstAggregateModuleState OBJECT-TYPE
    SYNTAX SSTState
    ACCESS read-only
    STATUS mandatory    
    DESCRIPTION 
    "This is the overall summary state of all modules. 
    This holds the most serious summary state which
    currently exists on any SST module." 
    ::= { sstGeneral 10 }

sstTotalTable OBJECT-TYPE
    SYNTAX  SEQUENCE OF SstTotalEntry
    ACCESS  not-accessible
    STATUS  mandatory
    DESCRIPTION                        
    "This group defines the attributes of the initial (source) 
    replenishment count and the cumulative (destination) count of the 
    movement of transaction media such as cards, envelopes and currency notes."
    ::= { sstGeneral 9 }


-----------------------------------------------------------
-- SST Total Table (see also sstGeneral 9)
-----------------------------------------------------------

sstTotalEntry OBJECT-TYPE
    SYNTAX  SstTotalEntry
    ACCESS  not-accessible
    STATUS  mandatory
    DESCRIPTION
    "This defines the contents of the table."
    INDEX   { sstCountName,
              sstCountIndex   }
    ::= { sstTotalTable 1 }

SstTotalEntry ::=
    SEQUENCE { 
                  sstCountName                 DisplayString,
                  sstCountIndex                INTEGER,
                  sstCountSource               INTEGER,
                  sstCountDestination          INTEGER
             }

sstCountName OBJECT-TYPE
    SYNTAX DisplayString
    ACCESS read-only
    STATUS mandatory    
    DESCRIPTION 
    "The name of the service with which the counter is associated."
    ::= { sstTotalEntry 1 }

sstCountIndex OBJECT-TYPE
    SYNTAX INTEGER
    ACCESS read-only
    STATUS mandatory    
    DESCRIPTION 
    "A unique number for each of the counters maintained by sstCountName."
    ::= { sstTotalEntry 2 }

sstCountSource OBJECT-TYPE
    SYNTAX INTEGER
    ACCESS read-write
    STATUS mandatory    
    DESCRIPTION 
    "The initial value set when the media 
    container is filled (for example, a 
    currency cassette) or emptied (for 
    example, a purge bin)."
    ::= { sstTotalEntry 3 }

sstCountDestination OBJECT-TYPE
    SYNTAX INTEGER
    ACCESS read-write
    STATUS mandatory    
    DESCRIPTION 
    "The cumulative count of the media movements. 
    This is used with the initial value to 
    calculate the current quantity of media 
    available in the container, for example, 
    the number of envelopes left in the envelope 
    dispenser."
    ::= { sstTotalEntry 4 }

-----------------------------------------------------------
-- Transaction Application Attributes
-----------------------------------------------------------

sstTransManufacturer OBJECT-TYPE
    SYNTAX DisplayString
    ACCESS read-only
    STATUS mandatory    
    DESCRIPTION 
    "The name of the manufacturer of the product."
    ::= { sstTrans 1 }

sstTransProduct OBJECT-TYPE
    SYNTAX DisplayString
    ACCESS read-only
    STATUS mandatory    
    ::= { sstTrans 2 }

sstTransVersion OBJECT-TYPE
    SYNTAX DisplayString
    ACCESS read-only
    STATUS mandatory    
    DESCRIPTION 
    "This attribute does not apply to SST transaction application
     information."
    ::= { sstTrans 3 }

sstTransSerialNo OBJECT-TYPE
    SYNTAX DisplayString
    ACCESS read-only
    STATUS mandatory    
    DESCRIPTION 
    "This attribute does not apply to SST transaction application
     information."
    ::= { sstTrans 4 }

sstTransInstallation OBJECT-TYPE
    SYNTAX DisplayString
    ACCESS read-only
    STATUS mandatory    
    DESCRIPTION 
    "The date and time, in DMI-defined format, 
    when the component was (last) installed."
    ::= { sstTrans 5 }

sstTransVerify OBJECT-TYPE
    SYNTAX VerificationState
    ACCESS read-only
    STATUS mandatory    
    DESCRIPTION 
    "A level of verification that the DMI component is installed and 
     functioning.  This attribute is not currently supported."
    ::= { sstTrans 6 }

-----------------------------------------------------------
-- Transaction Application State Table
-----------------------------------------------------------

sstTransStateTable OBJECT-TYPE
    SYNTAX  SEQUENCE OF SstTransStateEntry
    ACCESS  not-accessible
    STATUS  mandatory
    DESCRIPTION                        
    "This table contains information about state changes in
     the transaction application."
    ::= { sstTrans 7 }

sstTransStateEntry OBJECT-TYPE
    SYNTAX  SstTransStateEntry
    ACCESS  not-accessible
    STATUS  mandatory
    DESCRIPTION
    "Table Description."
    INDEX   { sstTransName }
    ::= { sstTransStateTable 1 }

SstTransStateEntry ::=
    SEQUENCE { 
          sstTransName          DisplayString,
          sstTransState         OCTET STRING
        }

sstTransName OBJECT-TYPE
    SYNTAX DisplayString
    ACCESS read-only
    STATUS mandatory    
    DESCRIPTION 
    "The name of the transaction application operation
     causing the state change."
    ::= { sstTransStateEntry 1 }

sstTransState OBJECT-TYPE
    SYNTAX OCTET STRING
    ACCESS read-write
    STATUS mandatory    
    DESCRIPTION 
    "Getting the value of this attribute provides the last reported
     state of the transaction application operation.  Setting the
     value allows new state to be sent to the transaction 
     application operation."
    ::= { sstTransStateEntry 2 }

-----------------------------------------------------------
-- Agent Attributes
-----------------------------------------------------------

sstAgentManufacturer OBJECT-TYPE
    SYNTAX DisplayString
    ACCESS read-only
    STATUS mandatory    
    DESCRIPTION 
    "The name of the manufacturer of the SST agent software."
    ::= { sstAgent 1 }

sstAgentProduct OBJECT-TYPE
    SYNTAX DisplayString
    ACCESS read-only
    STATUS mandatory    
    ::= { sstAgent 2 }

sstAgentVersion OBJECT-TYPE
    SYNTAX DisplayString
    ACCESS read-only
    STATUS mandatory    
    DESCRIPTION 
    "This attribute does not apply to the agent software."
    ::= { sstAgent 3 }

sstAgentSerialNo OBJECT-TYPE
    SYNTAX DisplayString
    ACCESS read-only
    STATUS mandatory    
    DESCRIPTION 
    "This attribute does not apply to the agent software."
    ::= { sstAgent 4 }

sstAgentInstallation OBJECT-TYPE
    SYNTAX DisplayString
    ACCESS read-only
    STATUS mandatory    
    DESCRIPTION 
    "The date and time, in DMI-defined format, when the component 
     was (last) installed."
    ::= { sstAgent 5 }

sstAgentVerify OBJECT-TYPE
    SYNTAX VerificationState
    ACCESS read-only
    STATUS mandatory    
    DESCRIPTION 
    "A level of verification that the DMI component is installed and 
     functioning.  This attribute is not currently supported."
    ::= { sstAgent 6 }

-----------------------------------------------------------
-- Agent Status
-----------------------------------------------------------

sstAgentState OBJECT-TYPE
    SYNTAX AgentState
    ACCESS read-only
    STATUS mandatory    
    DESCRIPTION 
    "A value for the current state of the agent."
    ::= { sstAgent 7 }

sstAgentLastException OBJECT-TYPE
    SYNTAX OCTET STRING
    ACCESS read-only
    STATUS mandatory    
    DESCRIPTION
    "Details of the last exception that occurred on the SST,
     comprising date, time and exception binary data."
    ::= { sstAgent 8 }

sstAgentLicenseLevel OBJECT-TYPE
    SYNTAX INTEGER
    ACCESS read-only
    STATUS mandatory    
    DESCRIPTION 
    "The current license level of the agent."
    ::= { sstAgent 9 }

sstAgentLicenseCode OBJECT-TYPE
    SYNTAX DisplayString
    ACCESS read-write
    STATUS mandatory    
    DESCRIPTION 
    "The current license code of the agent."
    ::= { sstAgent 10 }

sstAgentLocalisationSet OBJECT-TYPE 
    SYNTAX INTEGER  
    ACCESS read-write   
    STATUS mandatory        
    DESCRIPTION     
    "The current local language of the agent. 
    Setting this value causes all DisplayString 
    types to be displayed in the local language 
    of choice. The default value of (0) uses the 
    factory-defined set."	
    ::= { sstAgent 11 }

sstAgentTime OBJECT-TYPE
    SYNTAX DisplayString
    ACCESS read-only
    STATUS mandatory    
    DESCRIPTION 
    "The current system time and timezone of the SST."
    ::= { sstAgent 12 }

-----------------------------------------------------------
------- Filtering State Table
-----------------------------------------------------------

sstAgentFilterTable OBJECT-TYPE 
    SYNTAX  SEQUENCE OF SstAgentFilterEntry 
    ACCESS  not-accessible  
    STATUS  mandatory
    DESCRIPTION
    "This table contains a list of DMI Classes and
    their current Filtered State for traps"	
    ::= { sstAgent 13 }

sstAgentFilterEntry OBJECT-TYPE 
    SYNTAX  SstAgentFilterEntry 
    ACCESS  not-accessible  
    STATUS  mandatory   
    DESCRIPTION 
    "This defines the contents of the table. " 
    INDEX   { sstAgentFilterClass }  
    ::= { sstAgentFilterTable 1 }

SstAgentFilterEntry ::= 
    SEQUENCE {        
        sstAgentFilterClass    DisplayString,        
        sstAgentFilterState    TruthValue        
        }

sstAgentFilterClass OBJECT-TYPE  
    SYNTAX DisplayString  
    ACCESS read-write
    STATUS mandatory        
    DESCRIPTION     
    "A DMI style Class definition for an
    instrumented Group "	
    ::= { sstAgentFilterEntry 1 }

sstAgentFilterState OBJECT-TYPE    
    SYNTAX TruthValue   
    ACCESS read-write   
    STATUS mandatory        
    DESCRIPTION     
    "To add a filter to the table, set sstAgentFilterState 
    to 1, supplying the sstAgentFilterClass as the key. 
    A row is added to the table.  To remove a filter from 
    the table, set the sstAgentFilterState to 0.  The row 
    is removed from the table." 
    ::= { sstAgentFilterEntry 2 }

-----------------------------------------------------------
-- Error Log Attributes
-----------------------------------------------------------

sstLogManufacturer OBJECT-TYPE
    SYNTAX DisplayString
    ACCESS read-only
    STATUS mandatory    
    DESCRIPTION 
    "The name of the manufacturer of the product."
    ::= { sstLogs 1 }

sstLogProduct OBJECT-TYPE
    SYNTAX DisplayString
    ACCESS read-only
    STATUS mandatory    
    ::= { sstLogs 2 }

sstLogVersion OBJECT-TYPE
    SYNTAX DisplayString
    ACCESS read-only
    STATUS mandatory    
    DESCRIPTION 
    "This attribute does not apply to the event log software."
    ::= { sstLogs 3 }

sstLogSerialNo OBJECT-TYPE
    SYNTAX DisplayString
    ACCESS read-only
    STATUS mandatory    
    DESCRIPTION 
    "This attribute does not apply to the event log software."
    ::= { sstLogs 4 }

sstLogInstallation OBJECT-TYPE
    SYNTAX DisplayString
    ACCESS read-only
    STATUS mandatory    
    DESCRIPTION 
    "The date and time, in DMI-defined format, when the component 
     was (last) installed."
    ::= { sstLogs 5 }

sstLogVerify OBJECT-TYPE
    SYNTAX VerificationState
    ACCESS read-only
    STATUS mandatory    
    DESCRIPTION 
    "A level of verification that the DMI component is installed and 
     functioning.  This attribute is not currently supported."
    ::= { sstLogs 6 }

END

NCR-CORESSTSYSTEMLOG-MIB DEFINITIONS ::= BEGIN

--
-- NCR Core SST System Log MIB
--

IMPORTS
    enterprises, Counter
        FROM RFC1155-SMI
    OBJECT-TYPE
        FROM RFC-1212
    DisplayString
        FROM RFC1213-MIB
    TruthValue
    FROM RFC1253-MIB;

        ncr                     OBJECT IDENTIFIER ::= { enterprises 191 }
        sst                     OBJECT IDENTIFIER ::= { ncr 39 }
        sstCore                 OBJECT IDENTIFIER ::= { sst 1 }
        sstProduct              OBJECT IDENTIFIER ::= { sst 13 }
        sstObjs                 OBJECT IDENTIFIER ::= { sstProduct 2}
        sstGeneral              OBJECT IDENTIFIER ::= { sstObjs 1 }    
        sstDevice               OBJECT IDENTIFIER ::= { sstObjs 2 }
        sstApplic               OBJECT IDENTIFIER ::= { sstObjs 3 }
        sstLogs                 OBJECT IDENTIFIER ::= { sstObjs 4 }

-----------------------------------------------------------
-- Device Log Table
-----------------------------------------------------------

sstDeviceLogTable OBJECT-TYPE
    SYNTAX  SEQUENCE OF SstLogEntry
    ACCESS  not-accessible
    STATUS  mandatory
    DESCRIPTION                        
    "This group defines the attributes of event entries in the
     SST device log."
    ::= { sstLogs 7 }

sstLogEntry OBJECT-TYPE
    SYNTAX  SstLogEntry
    ACCESS  not-accessible
    STATUS  mandatory
    DESCRIPTION
    "This defines the contents of the table."
    INDEX   { sstLogIndex }
    ::= { sstDeviceLogTable 1 }

SstLogEntry ::=
    SEQUENCE { 
           sstLogIndex           INTEGER,
           sstLogDeviceName      DisplayString,
           sstLogServiceName     DisplayString,
           sstLogTCode           OCTET STRING,
           sstLogSData           OCTET STRING,
           sstLogMData           OCTET STRING,
           sstLogDescription     OCTET STRING
         }

sstLogIndex OBJECT-TYPE
    SYNTAX INTEGER
    ACCESS read-only
    STATUS mandatory    
    DESCRIPTION 
    "A unique number for every entry in the device log."
    ::= { sstLogEntry 1 }

sstLogDeviceName OBJECT-TYPE
    SYNTAX DisplayString
    ACCESS read-only
    STATUS mandatory    
    DESCRIPTION 
    "The name of the device that generated the event."
    ::= { sstLogEntry 2 }

sstLogServiceName OBJECT-TYPE
    SYNTAX DisplayString
    ACCESS read-only
    STATUS mandatory    
    DESCRIPTION 
    "The name of the service associated with the device."
    ::= { sstLogEntry 3 }

sstLogTCode OBJECT-TYPE
    SYNTAX OCTET STRING
    ACCESS read-only
    STATUS mandatory    
    DESCRIPTION 
    "The transaction code reported from the device."
    ::= { sstLogEntry 4 }

sstLogSData OBJECT-TYPE
    SYNTAX OCTET STRING
    ACCESS read-only
    STATUS mandatory    
    DESCRIPTION 
    "The severity information reported from the device."
    ::= { sstLogEntry 5 }

sstLogMData OBJECT-TYPE
    SYNTAX OCTET STRING
    ACCESS read-only
    STATUS mandatory    
    DESCRIPTION 
    "The maintenance information reported from the device."
    ::= { sstLogEntry 6 }

sstLogDescription OBJECT-TYPE
    SYNTAX OCTET STRING
    ACCESS read-only
    STATUS mandatory    
    DESCRIPTION 
    "Additional information about the event."
    ::= { sstLogEntry 7 }

END
