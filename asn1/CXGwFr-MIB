CXGwFr-MIB DEFINITIONS ::= BEGIN

IMPORTS
	OBJECT-TYPE     FROM RFC-1212

-- Proprietary definitions:
	cxGwFr, Alias, SapIndex
				FROM CXProduct-SMI;

--  GFF UPPER SAPs DEFINITION GROUP.

gffSapTable     OBJECT-TYPE
	SYNTAX  SEQUENCE  OF GffSapEntry
	ACCESS  not-accessible
	STATUS  mandatory
	DESCRIPTION
"Table containing configuration information about all the GFF module SAPs."
	::= { cxGwFr 1 }

	gffSapEntry     OBJECT-TYPE     
	-- This defines a row in the table.
		SYNTAX  GffSapEntry
		ACCESS  not-accessible
		STATUS  mandatory
		DESCRIPTION
"This row holds all the parameters related to a particular GFF module SAP."
		INDEX { gffSapId }
		::= { gffSapTable 1 }

	GffSapEntry ::=         
	-- This defines cells in a row (or columns in the SAPs table).
		SEQUENCE {
			gffSapId                        SapIndex,
			gffSapRowStatus         INTEGER,
			gffSapType                      INTEGER,
			gffSapAlias                     Alias,
			gffSapCompanionAlias    Alias,
			gffSapAssociatedSlotNo  INTEGER,
			gffSapWindowWidth               INTEGER,
			gffSapTrafficPriority           INTEGER,
			gffSapMaxFrameSize              INTEGER
		}

	gffSapId OBJECT-TYPE
		SYNTAX  SapIndex
		ACCESS  read-only
		STATUS  mandatory
		DESCRIPTION
"Identifies the SAP by a unique numerical value."
		::= { gffSapEntry 1 }

	gffSapRowStatus OBJECT-TYPE
		SYNTAX  INTEGER {
					invalid (1),
					valid    (2)
				}
		ACCESS  read-write
		STATUS  mandatory
		DESCRIPTION
"This parameter is relevant to upper SAPs only.

Indicates whether this SAP is configured in the CE.

Options:
invalid (1): Deletes the current entry (row) in the table.

valid (2): Creates a SAP entry (row) in the table.

Default Value: valid (2)

Related Objects:
gffSapType

Configuration Changed: administrative"
		::= { gffSapEntry 2 }

	gffSapType OBJECT-TYPE
		SYNTAX  INTEGER {
					lower (1),
					upper (2)
				}
		ACCESS  read-write
		STATUS  mandatory
		DESCRIPTION
"Identifies the SAP type. There is one lower SAP connected permanently to 
TBC and up to 16 upper SAPs connected to FRM.

Options:
lower (1): SAP is a lower type (leads to the bus of the CX1000 chassis)

upper (2): SAP is an upper type (leads to a lower SAP in the Frame Relay 
software layer)

Default Value: none

Configuration Changed: administrative"
		::= { gffSapEntry 3 }

	gffSapAlias OBJECT-TYPE
		SYNTAX  Alias
		ACCESS  read-write
		STATUS  mandatory
		DESCRIPTION
"Identifies the GFF local SAP by a textual name.

Range of Values: 0 to 35 alphanumeric characters beginning with a 
non-numeric character.

Default Value:

gffsap1 (for gffSapId 1)

gffsap2 (for gffSapId 2)

gffsap3 (for gffSapId 3)

gffsap4 (for gffSapId 4)

gffsap5 (for gffSapId 5)

gffsap6 (for gffSapId 6)

gffsap7 (for gffSapId 7)

gffsap8 (for gffSapId 8)

gffsap9 (for gffSapId 9)

gffsap10 (for gffSapId 10)

gffsap11 (for gffSapId 11)

gffsap12 (for gffSapId 12)

gffsap13 (for gffSapId 13)

gffsap14 (for gffSapId 14)

gffsap15 (for gffSapId 15)

gffsap16 (for gffSapId 16)

gffsap17 (for gffSapId 17)

Configuration Changed: administrative"
		::= { gffSapEntry 4 }

	gffSapCompanionAlias OBJECT-TYPE
		SYNTAX  Alias
		ACCESS  read-write
		STATUS  mandatory
		DESCRIPTION
"Determines the textual name identifying the remote or companion SAP that 
will communicate with this SAP.

Range of Values: 0 to 35 alphanumeric characters beginning with a 
non-numeric character.

Default Value: undefined for gffSapId 1-16; tbsap4 for gffSapId 17

Configuration Changed: administrative"
	::= { gffSapEntry 5 }


	gffSapAssociatedSlotNo OBJECT-TYPE
		SYNTAX  INTEGER (1..16)
		ACCESS  read-write
		STATUS  mandatory
		DESCRIPTION
"This parameter is relevant to upper SAPs only.

Identifies the local chassis slot number that communicates with the Frame 
Relay service through this SAP.

Range of Values: 1 - 16

Default Value: 6

Related Objects:
gffSapType

Configuration Changed: administrative"
	::= { gffSapEntry 6 }

	gffSapWindowWidth OBJECT-TYPE
		SYNTAX  INTEGER (40..100)
		ACCESS  read-write
		STATUS  mandatory
		DESCRIPTION
"This object is relevant to upper SAPs only and concerns the traffic going 
from FRM to GFF.

Determines the number of OS buffers the Frame Relay software layer can 
transmitted through this SAP without receiving acknowledgement.

Range of Values: 40 - 100

Default Value: 40

Related Objects:
gffSapType

Configuration Changed: administrative"
	DEFVAL { 40 }
	::= { gffSapEntry 7 }

	gffSapTrafficPriority OBJECT-TYPE
		SYNTAX  INTEGER (1..3)
		ACCESS  read-write
		STATUS  mandatory
		DESCRIPTION
"Determines the priority for sending frames to a PX600 card or to the 
Frame Relay software layer.

Options: 
1: urgent

2: expeditious

3: normal

Default Value: 3

Configuration Changed: operative, but only if this object's row was 
included in the table at the last system reset. Otherwise, change is 
administrative. "
	::= { gffSapEntry 8 }

	gffSapMaxFrameSize OBJECT-TYPE
		SYNTAX  INTEGER (3..8192)
		ACCESS  read-write
		STATUS  mandatory
		DESCRIPTION
"Determines the maximum frame size the Frame Relay software layer can 
expect from the GFF module.

Range of Values: 3 - 8192 (bytes)

Default Value: 4096

Configuration Changed: operative, but only if this object's row was 
included in the table at the last system reset. Otherwise, change is 
administrative. "
		DEFVAL {4096}
	::= { gffSapEntry 9 }
END
