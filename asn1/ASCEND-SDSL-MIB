--			SDSL Enterprise Mib
--
--			Ascend Communications, Inc
--			1275 Harbor Bay Pkwy
--			Alameda, CA 94502
--			+1 510 769 6001
--			info@ascend.com
--
--		Copyright (c) 1993-1995 Ascend Communications, Inc.
--		All rights reserved.
--
-- CVS ID:      $Id: sdsl.mib,v 29.4.66.2 2000/01/28 18:30:16 jjablons Exp $
--
-- 06 Dec 96:	Initial release

	-- Ascend wanTypeSdsl group
	--
	-- This group contains MIB variables used to manage the SDSL
	-- interface

	-- SDSL interface status
	--
	-- The below entries contain interface status information. The slot
	-- number and interface are identified via that sdslSlotIndex and 
	-- sdslLineIndex parameters. 
	--
ASCEND-SDSL-MIB DEFINITIONS ::= BEGIN

    IMPORTS
	wanTypeSdsl
	    FROM ASCEND-WAN-MIB
	OBJECT-TYPE
	    FROM RFC-1212;
	
    sdslLineStatusTable	OBJECT-TYPE
	SYNTAX		SEQUENCE OF SdslLineStatusEntry
	ACCESS		not-accessible
	STATUS		mandatory
	DESCRIPTION	"SDSL status parameters."
	::= { wanTypeSdsl 1 }

    sdslLineStatusEntry	OBJECT-TYPE
	SYNTAX		SdslLineStatusEntry
	ACCESS		not-accessible
	STATUS		mandatory
	DESCRIPTION	"An interface status entry containing objects to describe the
			interface."
	INDEX		{ sdslStatusIfEntryIndex }
	::= { sdslLineStatusTable 1 }

    SdslLineStatusEntry ::=
	SEQUENCE {
	    sdslStatusIfEntryIndex
		INTEGER,
	    sdslStatusShelfIndex
	        INTEGER,
	    sdslStatusSlotIndex
		INTEGER,
	    sdslStatusLineIndex
		INTEGER,
	    sdslStatusUnitType
		INTEGER,
	    sdslStatusLineState
		INTEGER,
	    sdslStatusUpRate
		INTEGER,
	    sdslStatusDownRate
		INTEGER,
	    sdslStatusVendorId
		INTEGER,
	    sdslStatusMajorFirmWareVer
		INTEGER,
	    sdslStatusMinorFirmWareVer
		INTEGER,
	    sdslStatusHardWareVer
		INTEGER,
	    sdslStatusLineRate
		INTEGER
	}

   sdslStatusIfEntryIndex    OBJECT-TYPE
	SYNTAX		INTEGER	
	ACCESS		read-only
	STATUS		mandatory
	DESCRIPTION	"Interface group index assigned to this port." 
	::= { sdslLineStatusEntry 1 }
   
    sdslStatusShelfIndex OBJECT-TYPE
	SYNTAX		INTEGER
	ACCESS		read-only
	STATUS		mandatory
	DESCRIPTION	"TNT's SDSL modules Shelf ID."
	::= { sdslLineStatusEntry 2 }

    sdslStatusSlotIndex	OBJECT-TYPE
	SYNTAX		INTEGER
	ACCESS		read-only
	STATUS		mandatory
	DESCRIPTION	"TNT's SDSL modules Slot ID."
	::= { sdslLineStatusEntry 3 }

    sdslStatusLineIndex	OBJECT-TYPE
	SYNTAX		INTEGER
	ACCESS		read-only
	STATUS		mandatory
	DESCRIPTION	"SDSL modules line ID." 
	::= { sdslLineStatusEntry 4 }

   sdslStatusUnitType	OBJECT-TYPE
	SYNTAX		INTEGER {
			    other( 1 ),		-- none of the following
			    coe( 2 ),		-- Central Office Equipment.
			    cpe( 3 )		-- Customer Premises
						-- Equipment. 
			}
	ACCESS		read-only
	STATUS		mandatory
	DESCRIPTION	"Unit type defines if the unit is operating either as a
			Central Office Equipment (COE) or Customer Premiss
			equipment (CPE)."
	::= { sdslLineStatusEntry 5 }

   sdslStatusLineState	OBJECT-TYPE
	SYNTAX		INTEGER {
			    other( 1 ),		-- none of the following
			    configure( 2 ),	-- Interface is in
						-- Configuration state. 
			    deactivate( 3 ),    -- Port is down. Deactive 
						-- has been issued. 
			    deactive-lost( 4 ), -- Waiting for LOS or LOST 
						-- indication.
			    start-up( 5 ),	-- Interface is in start-up
						-- mode. 
			    pend-port-up( 6 ), 
			    up( 7 ),		-- Interface is in UP state, and
						-- ready to transfer data.
			    pend-deactivate( 8 ),-- Interface may transition
						-- from UP to DOWN state. 
			    out-of-service( 9 ) -- Interface is placed OOS.
			}

	ACCESS		read-only
	STATUS		mandatory
	DESCRIPTION	"Interface state describes the current ports
			operating state. States are: Config, Pend Down, 
			Up, Down, Start-up, or N/A."
	::= { sdslLineStatusEntry 6 }
	
   sdslStatusUpRate		OBJECT-TYPE
	SYNTAX		INTEGER{
    			  m2320000(2320000),

                          m1568000(1568000),

                          m1552000(1552000),

                          m1536000(1536000),

                          m1168000(1168000),

                          m1152000(1152000),

                          m1040000(1040000),

                          k784000(784000),

                          k768000(768000),

                          k528000(528000),

                          k416000(416000),

                          k400000(400000),

                          k384000(384000),

                          k272000(272000),

                          k208000(208000),

                          k192000(192000),

                          k160000(160000),

                          k144000(144000)	
                               } 
	ACCESS		read-write
	STATUS		deprecated
                        -- Deprecated starting from TAOS 8.0
	DESCRIPTION    "The current up stream (cpe to coe) rate
                        The object dslStatusUpRate is deprecated.
                        To set line rate the object sdslConfigLineRate
                        of the new sdslLineConfigTable should be used."
	::= { sdslLineStatusEntry 7 }

   sdslStatusDownRate		OBJECT-TYPE
	SYNTAX		INTEGER{
    			  m2320000(2320000),

                          m1568000(1568000),

                          m1552000(1552000),

                          m1536000(1536000),

                          m1168000(1168000),

                          m1152000(1152000),

                          m1040000(1040000),

                          k784000(784000),

                          k768000(768000),

                          k528000(528000),

                          k416000(416000),

                          k400000(400000),

                          k384000(384000),

                          k272000(272000),

                          k208000(208000),

                          k192000(192000),

                          k160000(160000),

                          k144000(144000)	
                               } 
	ACCESS		read-write
	STATUS		deprecated
                        -- Deprecated starting from TAOS 8.0
	DESCRIPTION    "The current down stream (coe to cpe) rate
                        The object dslStatusDownRate is deprecated.
                        To set line rate the object sdslConfigLineRate
                        of the new sdslLineConfigTable should be used."
	::= { sdslLineStatusEntry 8 }

   sdslStatusVendorId   OBJECT-TYPE
	SYNTAX		INTEGER
	ACCESS		read-only
	STATUS		mandatory
	DESCRIPTION	"Vendor identification."
	::= { sdslLineStatusEntry 9 }

   sdslStatusMajorFirmWareVer	OBJECT-TYPE
	SYNTAX		INTEGER
	ACCESS		read-only
	STATUS		mandatory
	DESCRIPTION	"Major firmware version."
	::= { sdslLineStatusEntry 10 }

   sdslStatusMinorFirmWareVer	OBJECT-TYPE
	SYNTAX		INTEGER
	ACCESS		read-only
	STATUS		mandatory
	DESCRIPTION	"Minor firmware version."
	::= { sdslLineStatusEntry 11 }

   sdslStatusHardWareVer	OBJECT-TYPE
	SYNTAX		INTEGER
	ACCESS		read-only
	STATUS		mandatory
	DESCRIPTION	"Hardware version."
	::= { sdslLineStatusEntry 12 }

   sdslStatusLineRate		OBJECT-TYPE
	SYNTAX		INTEGER{
                          unknown(1),

    			  m2320000(2320000),

                          m1568000(1568000),

                          m1552000(1552000),

                          m1536000(1536000),

                          m1168000(1168000),

                          m1152000(1152000),

                          m1040000(1040000),

                          k784000(784000),

                          k768000(768000),

                          k528000(528000),

                          k416000(416000),

                          k400000(400000),

                          k384000(384000),

                          k272000(272000),

                          k208000(208000),

                          k192000(192000),

                          k160000(160000),

                          k144000(144000)	
                               }
	ACCESS		read-only
	STATUS		mandatory
	DESCRIPTION	"The current line rate"
	::= { sdslLineStatusEntry 13 }

    sdslLineStatisticTable OBJECT-TYPE
	SYNTAX		SEQUENCE OF SdslLineStatisticEntry
	ACCESS		not-accessible
	STATUS		mandatory
	DESCRIPTION	"SDSL statistical parameters."
	::= { wanTypeSdsl 2 }

   sdslLineStatisticEntry OBJECT-TYPE
	SYNTAX		SdslLineStatisticEntry
	ACCESS		not-accessible
	STATUS		mandatory
	DESCRIPTION	"An interface statistical entry containing objects to
			describe the interface."
	INDEX		{ sdslStatIfEntryIndex }
	::= { sdslLineStatisticTable 1 }

    SdslLineStatisticEntry ::=
	SEQUENCE {
	    sdslStatIfEntryIndex
		INTEGER,
	    sdslStatShelfIndex
		INTEGER,
	    sdslStatSlotIndex
		INTEGER,
	    sdslStatLineIndex
		INTEGER,
	    sdslStatConnUpDays
		INTEGER,
	    sdslStatConnUpHours
	        INTEGER,
	    sdslStatConnUpMinutes
		INTEGER,
	    sdslStatRxSignalPresent
		INTEGER,
	    sdslStatLineQualityDb
		INTEGER,
	    sdslStatUpDwnCntr
		INTEGER,
	    sdslStatLineSelfTest
		INTEGER,
	    sdslStatBertTimer
		INTEGER,
	    sdslStatBertEna
		INTEGER,
	    sdslStatBertState
		INTEGER,
	    sdslStatBertErrorCounter
		INTEGER
	}

   sdslStatIfEntryIndex	OBJECT-TYPE
	SYNTAX		INTEGER
	ACCESS		read-only
	STATUS		mandatory
	DESCRIPTION	"The interface groups interface index is used 
			 to index into this table."
	::= { sdslLineStatisticEntry 1 }

   sdslStatShelfIndex	OBJECT-TYPE
	SYNTAX		INTEGER
	ACCESS		read-only
	STATUS		mandatory
	DESCRIPTION	"SDSL modules Shelf ID."
	::= { sdslLineStatisticEntry 2 }

   sdslStatSlotIndex	OBJECT-TYPE
	SYNTAX		INTEGER
	ACCESS		read-only
	STATUS		mandatory
	DESCRIPTION	"SDSL modules Slot ID."
	::= { sdslLineStatisticEntry 3 }

   sdslStatLineIndex	OBJECT-TYPE
	SYNTAX		INTEGER
	ACCESS		read-only
	STATUS		mandatory
	DESCRIPTION	"SDSL modules interface ID." 
	::= { sdslLineStatisticEntry 4 }

   sdslStatConnUpDays	OBJECT-TYPE
	SYNTAX		INTEGER
	ACCESS		read-only
	STATUS		mandatory
	DESCRIPTION	"Connection up day count."
	::= { sdslLineStatisticEntry 5 }

   sdslStatConnUpHours	OBJECT-TYPE
	SYNTAX		INTEGER
	ACCESS		read-only
	STATUS		mandatory
	DESCRIPTION	"Connection Up 24 hour count."
	::= { sdslLineStatisticEntry 6 }

   sdslStatConnUpMinutes	OBJECT-TYPE
	SYNTAX		INTEGER
	ACCESS		read-only
	STATUS		mandatory
	DESCRIPTION	"Connection up minute count."
	::= { sdslLineStatisticEntry 7 }

   sdslStatRxSignalPresent	OBJECT-TYPE
	SYNTAX		INTEGER {
			    no( 1 ),	-- LOS of signal detected. 
			    yes( 2 )	-- Receive signal present. 
			}
	ACCESS		read-only
	STATUS		mandatory
	DESCRIPTION	"Receive signal present detection."
	::= { sdslLineStatisticEntry 8 }

  sdslStatLineQualityDb OBJECT-TYPE
	SYNTAX		INTEGER
	ACCESS		read-only
	STATUS		mandatory
	DESCRIPTION	"Lines noise margin. Reliable data will transfer
			with a reading of -5db or greater."
	::= { sdslLineStatisticEntry 9 }


    sdslStatUpDwnCntr OBJECT-TYPE
	SYNTAX		INTEGER
	ACCESS		read-only
	STATUS		mandatory
	DESCRIPTION	"Line Up Down counter value displays the number
			of times the interface transitions from a down to up
			state."
	::= { sdslLineStatisticEntry 10 }

    sdslStatLineSelfTest    OBJECT-TYPE
	SYNTAX		INTEGER {
				other( 4 ),
				selfTestFailed( 1 ),	
				localLoopBackFailed( 2 ),
				passed( 3 )
			}
	ACCESS		read-only
	STATUS		mandatory
	DESCRIPTION	"Line hardware self test results (Passed or 
			 Failed)."
	::= { sdslLineStatisticEntry 11 }

    sdslStatBertTimer    OBJECT-TYPE
	SYNTAX		INTEGER {
				one-minute(1),
				two-minutes(2),
				three-minutes(3),
				four-minutes(4),
				five-minutes(5),
				ten-minutes(6),
				fifteen-minutes(7),
				twenty-minutes(8),
				thirty-minutes(9)
			}
	ACCESS		read-write
	STATUS		mandatory
	DESCRIPTION	"BER test duration configuration. The BER test lasts for the 
			 duration of this timer."
	::= { sdslLineStatisticEntry 12 }
	
    sdslStatBertEna    OBJECT-TYPE
	SYNTAX		INTEGER {
				no( 1 ),
				yes( 2 )
			}
	ACCESS		read-write
	STATUS		mandatory
	DESCRIPTION	"Enable/disable of the BER test. If nodes are
			 connected, then the BER test is ran between the
			 units. If this node is not connected to a remote 
			 node, then the interface is placed into analog 
			 loopback and the BER test is started."
	::= { sdslLineStatisticEntry 13 }
	
    sdslStatBertState    OBJECT-TYPE
	SYNTAX		INTEGER {
				active(1),
				stopped(2),
				start-up(3),
				waiting(4),
				pend-active(5),
				bert-los(6)
			}
	ACCESS		read-only
	STATUS		mandatory
	DESCRIPTION	"BER test states. When this node is not connected to
			 another node, the test is disabled. When two nodes are connected 
			 then the BER test waits for the other node to start it's BER test and 
			 then starts collecting bit errors immediately."
	::= { sdslLineStatisticEntry 14 }
	
    sdslStatBertErrorCounter    OBJECT-TYPE
	SYNTAX		INTEGER
	ACCESS		read-only
	STATUS		mandatory
	DESCRIPTION	"BER test bit error counter."
	::= { sdslLineStatisticEntry 15 }

        -- Line Configuration Table
        -- Supported on MAX20, DSLS15, DSLS50 platforms starting from TAOS 8.0

   sdslLineConfigTable	OBJECT-TYPE
	SYNTAX		SEQUENCE OF SdslLineConfigEntry
	ACCESS		not-accessible
	STATUS		mandatory
	DESCRIPTION	"SDSL status parameters."
	::= { wanTypeSdsl 3 }

    sdslLineConfigEntry	OBJECT-TYPE
	SYNTAX		SdslLineConfigEntry
	ACCESS		not-accessible
	STATUS		mandatory
	DESCRIPTION	"An interface status entry containing objects to describe the
			interface."
	INDEX		{ sdslConfigIfEntryIndex }
	::= { sdslLineConfigTable 1 }

    SdslLineConfigEntry ::=
	SEQUENCE {
	    sdslConfigIfEntryIndex      INTEGER,
	    sdslConfigShelfIndex        INTEGER,
	    sdslConfigSlotIndex         INTEGER,
	    sdslConfigLineIndex         INTEGER,
	    sdslConfigLineRate          INTEGER
	}

   sdslConfigIfEntryIndex    OBJECT-TYPE
	SYNTAX		INTEGER	
	ACCESS		read-only
	STATUS		mandatory
	DESCRIPTION	"Interface group index assigned to this port." 
	::= { sdslLineConfigEntry 1 }
   
    sdslConfigShelfIndex OBJECT-TYPE
	SYNTAX		INTEGER
	ACCESS		read-only
	STATUS		mandatory
	DESCRIPTION	"TNT's SDSL modules Shelf ID."
	::= { sdslLineConfigEntry 2 }

    sdslConfigSlotIndex	OBJECT-TYPE
	SYNTAX		INTEGER
	ACCESS		read-only
	STATUS		mandatory
	DESCRIPTION	"TNT's SDSL modules Slot ID."
	::= { sdslLineConfigEntry 3 }

    sdslConfigLineIndex	OBJECT-TYPE
	SYNTAX		INTEGER
	ACCESS		read-only
	STATUS		mandatory
	DESCRIPTION	"SDSL modules line ID." 
	::= { sdslLineConfigEntry 4 }
	
   sdslConfigLineRate		OBJECT-TYPE
	SYNTAX		INTEGER{
                          unknown(1),

    			  m2320000(2320000),

                          m1568000(1568000),

                          m1552000(1552000),

                          m1536000(1536000),

                          m1168000(1168000),

                          m1152000(1152000),

                          m1040000(1040000),

                          k784000(784000),

                          k768000(768000),

                          k528000(528000),

                          k416000(416000),

                          k400000(400000),

                          k384000(384000),

                          k272000(272000),

                          k208000(208000),

                          k192000(192000),

                          k160000(160000),

                          k144000(144000)	
                               }
	ACCESS		read-write
	STATUS		mandatory
	DESCRIPTION	"The current line  rate"
	::= { sdslLineConfigEntry 5 }

END
