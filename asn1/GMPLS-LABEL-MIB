-- extracted from draft-ietf-ccamp-gmpls-lsr-mib-00.txt
-- at Sat Jun 29 06:09:50 2002

GMPLS-LABEL-MIB DEFINITIONS ::= BEGIN

IMPORTS
   MODULE-IDENTITY, OBJECT-TYPE, NOTIFICATION-TYPE,
   experimental, Unsigned32
      FROM SNMPv2-SMI
   MODULE-COMPLIANCE, OBJECT-GROUP
      FROM SNMPv2-CONF
   GmplsGeneralizedLabelTypes,
GmplsGeneralizedLabelSubtypes,
   GmplsFreeformLabel
      FROM GMPLS-TC-MIB
   ;

gmplsLabelMIB MODULE-IDENTITY
   LAST-UPDATED
      "200206240900Z "  -- 24 June 2002 9:00:00"
   ORGANIZATION
      "Common Control And Management Protocols (CCAMP)
   Working Group"
   CONTACT-INFO
      "       Thomas D. Nadeau
      Postal: Cisco Systems, Inc.
              250 Apollo Drive
              Chelmsford, MA 01824
         Tel: +1-978-244-3051
       Email: tnadeau@cisco.com
      
              Cheenu Srinivasan
      Postal: Parama Networks, Inc.
              1030 Broad Street
              Shrewsbury, NJ 07702
         Tel: +1-732-544-9120 x731
       Email: cheenu@paramanet.comTel: +1-732-544-9120x731
      
              Adrian Farrel
      Postal: Movaz Networks, Inc.
              7926 Jones Branch Drive
              McLean, VA 22102
         Tel: +1-703-847-1867
       Email: afarrel@movaz.com
      
              Edward Harrison
      Postal: Data Connection Ltd.
              100 Church Street
              Enfield, Middlesex
              EN2 6BQ, United Kingdom
         Tel: +44-20-8366-1177
       Email: eph@dataconnection.com
      
              Tim Hall
      Postal: Data Connection Ltd.
              100 Church Street
              Enfield, Middlesex
              EN2 6BQ, United Kingdom
         Tel: +44-20-8366-1177
       Email: timhall@dataconnection.com"
   DESCRIPTION
       "This MIB module contains managed object
        definitions for labels within GMPLS
        systems."
       
   -- Revision history.
   
   REVISION
       "200206240900Z "  -- 24 June 2002 9:00:00
        GMT"
   DESCRIPTION
       "Initial version."
   -- Above revision history to be replaced as below
   -- REVISION "yyyymmddhhmmZ"
   -- DESCRIPTION "Initial version, published as RFC xxxx"
   -- xxxx to be assigned by RFC Editor
   ::= { experimental XXX } -- To Be Assigned by IANA

-- Top level components of this MIB.

-- tables, scalars
gmplsLabelObjects       OBJECT IDENTIFIER ::= {
gmplsLabelMIB 0 }
gmplsLabelConformance   OBJECT IDENTIFIER ::= {
gmplsLabelMIB 1 }

-- GMPLS Label Table.

gmplsLabelTable OBJECT-TYPE
   SYNTAX        SEQUENCE OF GmplsLabelEntry
   MAX-ACCESS    not-accessible
   STATUS        current
   DESCRIPTION
       "Table of GMPLS Labels.  This table extends
        mplsLabelTable to handle the more complex
        label forms required for GMPLS.
        Each entry in this table represents an
        individual GMPLS label value.  Labels in
        the tables in other MIBs are referred to
        using index entries into mplsLabelTable.
        The indexing of this table is identical.
        In effect, this table taken together with
        mplsLabelTable provides an integer mapping
        for label values that may be more complex
        than simple integers."
   ::= { gmplsLabelObjects 1 }

gmplsLabelEntry OBJECT-TYPE
   SYNTAX        GmplsLabelEntry
   MAX-ACCESS    not-accessible
   STATUS        current
   DESCRIPTION
       "An entry in this table extends the label
        defintion in mplsLabelTable for use with
        certain types of switching appropriate to
        GMPLS."
   INDEX { mplsLabelInterface, mplsLabelIndex,
gmplsSublabelIndex }
   ::= { gmplsLabelTable 1 }

GmplsLabelEntry ::= SEQUENCE {
  gmplsSublabelIndex Unsigned32,
  gmplsLabelType     GmplsGeneralizedLabelTypes,
  gmplsLabelSubtype  GmplsGeneralizedLabelSubtypes,
  gmplsPortWavelengthLabel      Unsigned32,
  gmplsFreeformLength           INTEGER,
  gmplsFreeformLabel            GmplsFreeformLabel,
  gmplsSonetSdhSignalIndex      INTEGER,
  gmplsSdhVc                    INTEGER,
  gmplsSdhVcBranch              INTEGER,
  gmplsSonetSdhBranch           INTEGER,
  gmplsSonetSdhGroupBranch      INTEGER,
  gmplsWavebandId               Unsigned32,
  gmplsWavebandStartLabel       Unsigned32,
  gmplsWavebandEndLabel         Unsigned32
   }

gmplsSublabelIndex OBJECT-TYPE
   SYNTAX        Unsigned32 (1..4294967295)
   MAX-ACCESS    read-only
   STATUS        current
   DESCRIPTION
       "In conjunction with mplsLabelInterface and
        mplsLabelIndex, this object uniquely
        identifies this row.  This sub-index allows
        a single GMPLS label to be defined as a
        concatenation of labels.  This is
        particularly useful in TDM.
        The ordering of sub-labels is strict with
        the sub-label with lowest
        gmplsSublabelIndex appearing first.  Note
        that all sub-labels of a single GMPLS label
        must share the same mplsLabelInterface and
        mplsLabelIndex values.  For labels that are
        not composed of concatenated sub-labels,
        this value should be set to zero."
   ::= { gmplsLabelEntry 1 }

gmplsLabelType OBJECT-TYPE
   SYNTAX        GmplsGeneralizedLabelTypes
   MAX-ACCESS    read-create
   STATUS        current
   DESCRIPTION
       "Identifies the type of this label as it
        appears in a Generalized Label.  This
        object has meaning only if the value of
        mplsLabelType is other(1)."
   ::= { gmplsLabelEntry 2 }

gmplsLabelSubtype OBJECT-TYPE
   SYNTAX        GmplsGeneralizedLabelSubtypes
   MAX-ACCESS    read-create
   STATUS        current
   DESCRIPTION
       "Subtype to help determine which of the
        subsequent fields should be used to form
        the Generalized Label."
   ::= { gmplsLabelEntry 3 }

gmplsPortWavelengthLabel OBJECT-TYPE
   SYNTAX        Unsigned32
   MAX-ACCESS    read-create
   STATUS        current
   DESCRIPTION
       "The value of a Port or Wavelength Label
        when carried as a Generalized Label.  Only
        valid if mplsLabelType is set to other(1),
        gmplsLabelType is set to
        generalizedLabel(2), and gmplsLabelSubtype
        is set to portWavelengthLabel(2)."
   ::= { gmplsLabelEntry 4 }

gmplsFreeformLength OBJECT-TYPE
   SYNTAX        INTEGER (1..64)
   MAX-ACCESS    read-create
   STATUS        current
   DESCRIPTION
       "The length of a freeform Generalized Label
        indicated in the gmplsFreeformLabel object.
        Only valid if mplsLabelType is set to
        other(1), gmplsLabelType is set to
        generalizedLabel(2), and gmplsLabelSubtype
        is set to freeformGeneralizedLabel(3)."
   ::= { gmplsLabelEntry 5 }

gmplsFreeformLabel OBJECT-TYPE
   SYNTAX        GmplsFreeformLabel
   MAX-ACCESS    read-create
   STATUS        current
   DESCRIPTION
       "The value of a freeform Generalized Label
        that does not conform to one of the
        standardized label encoding or that an
        implementation chooses to represent as an
        octet string without further decoding.  The
        length of this object is given by the value
        of gmplsFreeformLength.  Only valid if
        mplsLabelType is set to other(1),
        gmplsLabelType is set to
        generalizedLabel(2), and gmplsLabelSubtype
        is set to freeformGeneralizedLabel(3)."
   ::= { gmplsLabelEntry 6 }

gmplsSonetSdhSignalIndex OBJECT-TYPE
   SYNTAX        INTEGER (0..4095)
   MAX-ACCESS    read-create
   STATUS        current
   DESCRIPTION
       "The Signal Index value (S) of a Sonet or
        SDH Generalized Label.  0 indicates that
        this field is non-significant.  Only valid
        if mplsLabelType is set to other(1),
        gmplsLabelType is set to
        generalizedLabel(2), and gmplsLabelSubtype
        is set to sonetLabel(4) or sdhLabel(5)."
   ::= { gmplsLabelEntry 7 }

gmplsSdhVc OBJECT-TYPE
   SYNTAX        INTEGER (0..15)
   MAX-ACCESS    read-create
   STATUS        current
   DESCRIPTION
       "The VC Indicator (U) of an SDH Generalized
        Label.  0 indicates that this field is non-
        significant.  Only valid if mplsLabelType
        is set to other(1), gmplsLabelType is set
        to generalizedLabel(2), and
        gmplsLabelSubtype is set to sdhLabel(5)."
   ::= { gmplsLabelEntry 8 }

gmplsSdhVcBranch OBJECT-TYPE
   SYNTAX        INTEGER (0..15)
   MAX-ACCESS    read-create
   STATUS        current
   DESCRIPTION
       "The VC Branch Indicator (K) of an SDH
        Generalized Label.  0 indicates that this
        field is non-significant.  Only valid if
        mplsLabelType is set to other(1),
        gmplsLabelType is set to
        generalizedLabel(2), and gmplsLabelSubtype
        is set to sdhLabel(5)."
   ::= { gmplsLabelEntry 9 }

gmplsSonetSdhBranch OBJECT-TYPE
   SYNTAX        INTEGER (0..15)
   MAX-ACCESS    read-create
   STATUS        current
   DESCRIPTION
       "The Branch Indicator (L) of a Sonet or SDH
        Generalized Label.  0 indicates that this
        field is non-significant.  Only valid if
        mplsLabelType is set to other(1),
        gmplsLabelType is set to
        generalizedLabel(2), and gmplsLabelSubtype
        is set to sonetLabel(4) or SdhLabel(5)."
   ::= { gmplsLabelEntry 10 }

gmplsSonetSdhGroupBranch OBJECT-TYPE
   SYNTAX        INTEGER (0..15)
   MAX-ACCESS    read-create
   STATUS        current
   DESCRIPTION
       "The Group Branch Indicator (M) of a Sonet
        or SDH Generalized Label.  0 indicates that
        this field is non-significant.  Only valid
        if mplsLabelType is set to other(1),
        gmplsLabelType is set to
        generalizedLabel(2), and gmplsLabelSubtype
        is set to sonetLabel(4) or sdhLabel(5)."
   ::= { gmplsLabelEntry 11 }

gmplsWavebandId OBJECT-TYPE
   SYNTAX        Uunsigned32
   MAX-ACCESS    read-create
   STATUS        current
   DESCRIPTION
       "The waveband identifier component of a
        waveband label.  Only valid if
        mplsLabelType is set to other(1),
        gmplsLabelType is set to
        generalizedLabel(2), and gmplsLabelSubtype
        is set to wavebandLabel(6)."
   ::= { gmplsLabelEntry 12 }

gmplsWavebandStartLabel OBJECT-TYPE
   SYNTAX        Uunsigned32
   MAX-ACCESS    read-create
   STATUS        current
   DESCRIPTION
       "The starting label component of a waveband
        label.  Only valid if mplsLabelType is set
        to other(1), gmplsLabelType is set to
        generalizedLabel(2), and gmplsLabelSubtype
        is set to wavebandLabel(6)."
   ::= { gmplsLabelEntry 13 }

gmplsWavebandEndLabel OBJECT-TYPE
   SYNTAX        Uunsigned32
   MAX-ACCESS    read-create
   STATUS        current
   DESCRIPTION
       "The end label component of a waveband
        label.  Only valid if mplsLabelType is set
        to other(1), gmplsLabelType is set to
        generalizedLabel(2), and gmplsLabelSubtype
        is set to wavebandLabel(6)."
   ::= { gmplsLabelEntry 14 }

-- End of GMPLS Label Table

-- Module compliance.

gmplsLabelGroups
   OBJECT IDENTIFIER ::= { gmplsLabelConformance 1 }

gmplsLabelCompliances
   OBJECT IDENTIFIER ::= { gmplsLabelConformance 2 }

gmplsLabelModuleCompliance MODULE-COMPLIANCE
   STATUS current
   DESCRIPTION
          "Compliance  statement for  agents  that
           support the GMPLS Label MIB."

MODULE -- this module

   -- The mandatory groups have to be implemented by
   -- LSRs claiming support for this MIB.  This MIB itself,
   -- however, is mandatory only on LSRs supporting GMPLS
   
   MANDATORY-GROUPS {
      gmplsLabelTableGroup
   }

   -- Units of conformance.
   
   GROUP gmplsLabelTableGroup
   DESCRIPTION
       "This group is mandatory for devices which
        support the gmplsLabelTable."

   GROUP gmplsPortWavelengthLabelGroup
   DESCRIPTION
       "This group extends gmplsLabelTableGroup for
        implementations that support port and
        wavelength labels."

   GROUP gmplsFreeformLabelGroup
   DESCRIPTION
       "This group extends gmplsLabelTableGroup for
        implementations that support freeform
        labels."

   GROUP gmplsSonetSdhLabelGroup
   DESCRIPTION
       "This group extends gmplsLabelTableGroup for
        implementations that support SonetSdh
        labels."

   GROUP gmplsWavebandLabelGroup
   DESCRIPTION
          "This group extends gmplsLabelTableGroup
           for implementations that support
           Waveband labels."

   -- gmplsLabelTable

   OBJECT      gmplsLabelType
   MIN-ACCESS  read-only
   DESCRIPTION
       "Write access is not required."

   OBJECT      gmplsLabelSubtype
   MIN-ACCESS  read-only
   DESCRIPTION
   "Write access is not required."

   OBJECT      gmplsPortWavelengthLabel
   MIN-ACCESS  read-only
   DESCRIPTION
       "Write access is not required."

   OBJECT      gmplsFreeformLength
   MIN-ACCESS  read-only
   DESCRIPTION
       "Write access is not required."

   OBJECT      gmplsFreeformLabel
   MIN-ACCESS  read-only
   DESCRIPTION
       "Write access is not required."

   OBJECT      gmplsSonetSdhSignalIndex
   MIN-ACCESS  read-only
   DESCRIPTION
       "Write access is not required."

   OBJECT      gmplsSdhVc
   MIN-ACCESS  read-only
   DESCRIPTION
       "Write access is not required."

   OBJECT      gmplsSdhVcBranch
   MIN-ACCESS  read-only
   DESCRIPTION
       "Write access is not required."

   OBJECT      gmplsSonetSdhBranch
   MIN-ACCESS  read-only
   DESCRIPTION
       "Write access is not required."

   OBJECT      gmplsSonetSdhGroupBranch
   MIN-ACCESS  read-only
   DESCRIPTION
       "Write access is not required."

   OBJECT      gmplsWavebandId
   MIN-ACCESS  read-only
   DESCRIPTION
       "Write access is not required."

   OBJECT      gmplsWavebandStartLabel
   MIN-ACCESS  read-only
   DESCRIPTION
       "Write access is not required."

   OBJECT      gmplsWavebandEndLabel
   MIN-ACCESS  read-only
   DESCRIPTION
       "Write access is not required."

::= { gmplsLabelCompliances 1 }

-- Units of conformance.

gmplsLabelTableGroup OBJECT-GROUP
   OBJECTS {
      gmplsLabelType,
      gmplsLabelSubtype
   }
   STATUS  current
   DESCRIPTION
       "Necessary, but not sufficient, set of
        objects to implement label table support.
        In addition, depending on the type of
        labels supported (for example, wavelength
        labels), the following other groups defined
        below are mandatory:
        gmplsPortWavelengthLabelGroup and/or
        gmplsFreeformLabelGroup and/or
        gmplsSonetSdhLabelGroup."
   ::= { gmplsLabelGroups 1 }

gmplsPortWavelengthLabelGroup OBJECT-GROUP
   OBJECTS {
      gmplsPortWavelengthLabel
   }
   STATUS  current
   DESCRIPTION
       "Object needed to implement Port and
        Wavelength labels."
   ::= { gmplsLabelGroups 2 }

gmplsFreeformLabelGroup OBJECT-GROUP
   OBJECTS {
      gmplsFreeformLength,
      gmplsFreeformLabel
   }
   STATUS  current
   DESCRIPTION
       "Object needed to implement Freeform
        labels."
   ::= { gmplsLabelGroups 3 }

gmplsSonetSdhLabelGroup OBJECT-GROUP
   OBJECTS {
      gmplsSonetSdhSignalIndex,
      gmplsSdhVc,
      gmplsSdhVcBranch,
      gmplsSonetSdhBranch,
      gmplsSonetuSdhGroupBranch
   }
   STATUS  current
   DESCRIPTION
       "Object needed to implement SONET and SDH
        labels."
   ::= { gmplsLabelGroups 4 }

gmplsWavebandLabelGroup OBJECT-GROUP
   OBJECTS {
          gmplsWavebandId,
      gmplsWavebandStartLabel,
      gmplsWavebandEndLabel
   }
   STATUS  current
   DESCRIPTION
       "Object needed to implement Waveband
        labels."
   ::= { gmplsLabelGroups 5 }

END

--    Copyright (C) The Internet Society (2002). All Rights
--    Reserved.
--    
--    This document and translations of it may be copied and
--    furnished to others, and derivative works that comment on
--    or otherwise explain it or assist in its implementation
--    may be prepared, copied, published and distributed, in
--    whole or in part, without restriction of any kind,
--    provided that the above copyright notice and this
--    paragraph are included on all such copies and derivative
--    works.  However, this document itself may not be modified
--    in any way, such as by removing the copyright notice or
--    references to the Internet Society or other Internet
--    organizations, except as needed for the purpose of
--    developing Internet standards in which case the
--    procedures for copyrights defined in the Internet
--    Standards process must be followed, or as required to
--    translate it into languages other than English.
--    
--    The limited permissions granted above are perpetual and
--    will not be revoked by the Internet Society or its
--    successors or assigns. This document and the information
--    contained herein is provided on an "AS IS" basis and THE
--    INTERNET SOCIETY AND THE INTERNET ENGINEERING TASK FORCE
--    DISCLAIMS ALL WARRANTIES, EXPRESS OR IMPLIED, INCLUDING
--    BUT NOT LIMITED TO ANY WARRANTY THAT THE USE OF THE
--    INFORMATION HEREIN WILL NOT INFRINGE ANY RIGHTS OR ANY
--    IMPLIED WARRANTIES OF MERCHANTABILITY OR FITNESS FOR A
--    PARTICULAR PURPOSE.
