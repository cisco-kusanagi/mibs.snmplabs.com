HOTWIRE-MSDSL-INTERFACE-MIB DEFINITIONS ::= BEGIN
----------------------------------------------------------------
--
--
--
--
--  Version :	1.0.1	APPROVED
--  	Created by:	Richard A. Bowhall & Mike Deakley
--  	Updates by:	Richard A. Bowhall & Mike Himelstein
--
--  	Last Update: Mar. 13,2000 by R.A.Bowhall (rab@paradyne.com)
--			(modified msdslFracPortIfTS's SYNTAX from
--			 SYNTAX  INTEGER (1..31) to SYNTAX  INTEGER (1..32))
--		     Feb. 24,2000 by R.A.Bowhall (rab@paradyne.com)
--			(removed last paragraph from msdslFracPortTS
--			Description.)
--		     Oct. 8,1999 by R.A.Bowhall (rab@paradyne.com)
--			(Removed the msdslLEDs, msdslIdentity, and most
--			of msdslConfiguration.  These objects will not
--			be supported until a later release of the msdsl
--			products.)
--		     Sept. 1, 1999 by R.A.Bowhall (rab@paradyne.com)
--			(Moved 'notAssigned(4)' in msdslConfigAllocMethod
--			 object)
--		     August 9, 1999 by R.A.Bowhall (rab@paradyne.com)
--			(Updates to Cross connect comments)
--		     July 30, 1999 by R.A.Bowhall (rab@paradyne.com)
--			(modified msdslPortConfigAllocMethodTable to
--			 use the correct index)
--                   July 27, 1999 by R.A.Bowhall (rab@paradyne.com
--			(modified msdsl Cross Connect names:
--			 msdslFracPortNumber   to msdslFracPortTS
--			 msdslFracPortIfNumber to msdslFracPortIfTS )
--			(changed msdslPortConfigAllocMethod  to a table)
--		     July 14, 1999 by R.A.Bowhall (rab@paradyne.com)
--			(added msdsldsx1WorstIntervalCSSs to the
--			 msdsldsx1WorstInterval group 
--			(added msdslG703WorstIntervalCSSs to the
--			 msdslG703WorstInterval group
--		     June  24, 1999 by R.A.Bowhall (rab@paradyne.com)
--			(added the msdslConfigPayLoadRate, 
--			 msdslConfigSystemLineTermination, msdslConfigSystem-
--			 SysPriClk, and msdslConfigSystemSysSecClk 
--			 to the Configuration group
--		     June  15, 1999 by R.A.Bowhall (rab@paradyne.com)
--			(added the msdsl Cross Connect Configuration group
--			 at msdslConfiguration 28)
--		     May  11, 1999 by R.A.Bowhall (rab@paradyne.com)
--			(added msdslDSLSWrevision to the msdslIdentity group)
--			(added msdslDSLLineCode to the msdslIdentity group)

--
--	Copyright (C) 1999, Paradyne. All rights reserved.
--	
--	Title: Paradyne hot-msdsl definitions
--
----------------------------------------------------------------
IMPORTS
    enterprises, IpAddress,
    TimeTicks, Counter, Gauge FROM RFC1155-SMI
    OBJECT-TYPE FROM RFC-1212
    TRAP-TYPE FROM RFC-1215
    DisplayString, ifIndex FROM RFC1213-MIB
     pdnmsdsl
      FROM PDN-HEADER-MIB;
----------------------------------------------------------------
--
--
--
-- OVERVIEW:
--
-- The Paradyne enterprise MSDSL MIB. This MIB is written 
-- specifically to facilitate in the management of M[S/H]DSL
-- devices.
--
-- This MIB is intended to have the functionality of the 
-- ATI screens of the graphical user interface. 

-- History 

--   END OF COMMENTS

----------------------------------------------------------------
----------------------------------------------------------------
--thenewpdn-mgmt   OBJECT IDENTIFIER ::= { thenewpdn 2 }
--paradyne         OBJECT IDENTIFIER ::= { thenewpdn-mgmt 24 }
--pdn-common       OBJECT IDENTIFIER ::= { paradyne 2 }
--pdn-interfaces   OBJECT IDENTIFIER ::= { pdn-common 6 }
--pdnmsdsl         OBJECT IDENTIFIER ::= { pdn-interfaces 15 }
----------------------------------------------------------------
 msdslDevice			OBJECT IDENTIFIER ::= { pdnmsdsl 1 }
----------------------------------------------------------------
 msdslCurrent                   OBJECT IDENTIFIER ::= {  msdslDevice 1 }
 msdslInterval                  OBJECT IDENTIFIER ::= {  msdslDevice 2 }
 msdslWorstInterval             OBJECT IDENTIFIER ::= {  msdslDevice 3 }
 msdslTotal                     OBJECT IDENTIFIER ::= {  msdslDevice 4 }
 
 msdslFarEndCurrent             OBJECT IDENTIFIER ::= {  msdslDevice 5 }
 msdslFarEndInterval            OBJECT IDENTIFIER ::= {  msdslDevice 6 }
 msdslFarEndWorstInterval       OBJECT IDENTIFIER ::= {  msdslDevice 7 }
 msdslFarEndTotal               OBJECT IDENTIFIER ::= {  msdslDevice 8 }
 
 msdslCurrentPerf               OBJECT IDENTIFIER ::= {  msdslDevice 9 }
 msdslIntervalPerf              OBJECT IDENTIFIER ::= {  msdslDevice 10 }
 
 msdslFarEndCurrentPerf         OBJECT IDENTIFIER ::= {  msdslDevice 11 }
 msdslFarEndIntervalPerf        OBJECT IDENTIFIER ::= {  msdslDevice 12 }
 
 msdsldsx1WorstInterval         OBJECT IDENTIFIER ::= {  msdslDevice 13 }
 msdslG703WorstInterval         OBJECT IDENTIFIER ::= {  msdslDevice 14 }
----------------------------------------------------------------
 msdslConfiguration		OBJECT IDENTIFIER ::= {  msdslDevice 15 }
----------------------------------------------------------------


 -- START OF MSDSL Status definitions
 -- the MSDSL Status Group
 --
 --		msdslStatus (1 - 14)

 -- The MSDSL Status group contains the following Tables:
 -- 	 (1) msdslCurrentTable
 --	 (2) msdslIntervalTable
 --	 (3) msdslWorstIntervalTable
 --	 (4) msdslTotalTable
 --	 (5) msdslFarEndCurrentTable
 --	 (6) msdslFarEndIntervalTable
 --	 (7) msdslFarEndWorstIntervalTable
 --	 (8) msdslFarEndTotalTable
 --	 (9) msdslCurrentPerfTable
 --	(10) msdslIntervalPerfTable
 --	(11) msdslFarEndCurrentPerfTable
 --	(12) msdslFarEndIntervalPerfTable
 --	(13) msdsldsx1WorstIntervalTable
 --	(14) msdslG703WorstIntervalTable
 --
 -- These tables contain various statistics being 
 -- collected by a M[S/H]DSL device.


 -- The MSDSL Current 15 minute Interval data collection Table
 
 -- The msdsl Current Interval Table contains various error statistics
 -- collected by each msdsl Interface over the current 15 minutes of
 -- operation.


	msdslCurrentTable OBJECT-TYPE
	     SYNTAX  SEQUENCE OF MsdslCurrentEntry
	     ACCESS  not-accessible
	     STATUS  mandatory
	     DESCRIPTION
		"The MSDSL Current 15 minute interval table."
	    ::= { msdslCurrent 1 }

	msdslCurrentEntry OBJECT-TYPE
	     SYNTAX  MsdslCurrentEntry
	     ACCESS  not-accessible
	     STATUS  mandatory
	     DESCRIPTION
		"An entry in the MSDSL Current table."
	    INDEX   { msdslCurrentIfIndex }
	    ::= { msdslCurrentTable 1 }

	MsdslCurrentEntry ::= SEQUENCE {
	     msdslCurrentIfIndex		INTEGER,
	     msdslCurrentESs			Gauge,
	     msdslCurrentSESs			Gauge,
	     msdslCurrentFEBEs			Gauge,
	     msdslErrEventsCounter		INTEGER,
	     msdslErrTimeElapsed 		INTEGER,
	     msdslErrValidIntervals 		INTEGER
	 }

	 msdslCurrentIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslCurrentEntry 1 }


	 msdslCurrentESs OBJECT-TYPE
	     SYNTAX  Gauge
	     ACCESS  read-only
	     STATUS  mandatory
	     DESCRIPTION
		"The number of Errored Seconds, encountered  by
		a MSDSL interface in the current 15 minute inter-
		val."
	    ::= { msdslCurrentEntry 2 }


	 msdslCurrentSESs OBJECT-TYPE
	     SYNTAX  Gauge
	     ACCESS  read-only
	     STATUS  mandatory
	     DESCRIPTION
		"The number of Severely Errored Seconds encoun-
		tered  by  a  msdsl  interface  in the current 15
		minute interval."
	    ::= { msdslCurrentEntry 3 }



	 msdslCurrentFEBEs OBJECT-TYPE
	     SYNTAX Gauge
	     ACCESS read-only
	     STATUS mandatory
	     DESCRIPTION
		"The number of Far End Block Errors (FEBE) en-
		countered  by a MSDSL interface in the current 15
		minute interval."
	 ::= {msdslCurrentEntry 4 }


	 msdslErrEventsCounter OBJECT-TYPE
	     SYNTAX  INTEGER (0..65535)
	     ACCESS  read-only
	     STATUS  mandatory
	     DESCRIPTION
		"An error event is a CRC error, maximum count
		 is 65,535.  If the count reaches 65,535 it will
		 remain at that value until reset. Reset is when
		 the near end data is cleared."
	    ::= { msdslCurrentEntry 5 }

	msdslErrTimeElapsed OBJECT-TYPE
	     SYNTAX INTEGER (0..899)
	     ACCESS read-only
	     STATUS mandatory
	     DESCRIPTION
		"The number of seconds that have elapsed since
		 the beginning of the current error-measurment
		 period."
	 ::= {msdslCurrentEntry 6 }


	msdslErrValidIntervals OBJECT-TYPE
	     SYNTAX INTEGER (0..96)
	     ACCESS read-only
	     STATUS mandatory
	     DESCRIPTION
		"The number of previous intervals for which
		 valid data was collected.  The value will be 96
		 unless the interface was brought on-line within
		 the last 24 hours, in which case the value will
		 be the number of complete 15 minute intervals
		 since the interface has been online."
	 ::= {msdslCurrentEntry 7 }




 -- The MSDSL 96 fifteen minute Interval Table

 -- The msdsl Interval Table contains various error statistics
 -- collected by each msdsl Interface over the previous 24 hours of
 -- operation.  The past 24 hours are broken into 96 completed
 -- 15 minute intervals.

	msdslIntervalTable OBJECT-TYPE
	     SYNTAX  SEQUENCE OF MsdslIntervalEntry
	     ACCESS  not-accessible
	     STATUS  mandatory
	     DESCRIPTION
		"An MSDSL Interval table."
	    ::= { msdslInterval 2 }

	msdslIntervalEntry OBJECT-TYPE
	     SYNTAX  MsdslIntervalEntry
	     ACCESS  not-accessible
	     STATUS  mandatory
	     DESCRIPTION
		"An entry in the MSDSL Interval table."
	    INDEX   { msdslIntervalIfIndex, msdslIntervalNumber }
	    ::= { msdslIntervalTable 1 }

	MsdslIntervalEntry ::= SEQUENCE {
	     msdslIntervalIfIndex		INTEGER,
	     msdslIntervalNumber		INTEGER,
	     msdslIntervalESs			Gauge,
	     msdslIntervalSESs			Gauge,
	     msdslIntervalFEBEs			Gauge
	 }

	 msdslIntervalIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslIntervalEntry 1 }


	 msdslIntervalNumber OBJECT-TYPE
	     SYNTAX  INTEGER (1..96)
	     ACCESS  read-only
	     STATUS  mandatory
	     DESCRIPTION
		"A number between 1 and 96, where 1 is the most
		recently completed 15 minute interval and 96 is
		the least recently completed 15 minutes  inter-
		val   (assuming   that  all  96  intervals  are
		valid)."
	    ::= { msdslIntervalEntry 2 }

	 msdslIntervalESs OBJECT-TYPE
	     SYNTAX  Gauge

	     ACCESS  read-only
	     STATUS  mandatory
	     DESCRIPTION
		"The number of Errored Seconds encountered by a
		DSL  interface in one of the previous 96, indi-
		vidual 15 minute, intervals."
	    ::= { msdslIntervalEntry 3 }


	 msdslIntervalSESs OBJECT-TYPE
	     SYNTAX  Gauge
	     ACCESS  read-only
	     STATUS  mandatory
	     DESCRIPTION
		"The number of Severely Errored Seconds encoun-
		tered by a DSL interface in one of the previous
		96, individual 15 minute, intervals."
	    ::= { msdslIntervalEntry 4 }


	 msdslIntervalFEBEs OBJECT-TYPE
	     SYNTAX  Gauge
	     ACCESS  read-only
	     STATUS  mandatory
	     DESCRIPTION
		"The number of Far End Block Errors 
		encountered  by  a  MSDSL interface in one of the
		previous 96, individual 15 minute, intervals."
	    ::= { msdslIntervalEntry 5 }


 -- The MSDSL Worst Interval Table

 -- The msdsl Worst Interval Table is defined as that interval
 -- which contains the largest number. If multiple intervals
 -- contain the same worst value, then the oldest will be
 -- displayed.

	msdslWorstIntervalTable OBJECT-TYPE
	     SYNTAX  SEQUENCE OF MsdslWorstIntervalEntry
	     ACCESS  not-accessible
	     STATUS  mandatory
	     DESCRIPTION
		"The MSDSL Worst Interval table."
	    ::= { msdslWorstInterval 3 }

	msdslWorstIntervalEntry OBJECT-TYPE
	     SYNTAX  MsdslWorstIntervalEntry
	     ACCESS  not-accessible
	     STATUS  mandatory
	     DESCRIPTION
		"An entry in the msdsl Worst Interval table."
	    INDEX { msdslWorstIntervalIfIndex }
	    ::= { msdslWorstIntervalTable 1 }

	MsdslWorstIntervalEntry ::= SEQUENCE {
	     msdslWorstIntervalIfIndex		INTEGER,
	     msdslWorstIntervalESs		INTEGER,
	     msdslWorstIntervalSESs		INTEGER,
	     msdslWorstIntervalFEBEs		INTEGER
	 }

	 msdslWorstIntervalIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslWorstIntervalEntry 1 }


	 msdslWorstIntervalESs OBJECT-TYPE
	     SYNTAX  INTEGER (1..96)
	     ACCESS  read-only
	     STATUS  mandatory
	     DESCRIPTION
		"The value (1 to 96) indicating the interval 
		 containing the worst Errored Seconds encountered
		 by a DSL  interface."
	    ::= { msdslWorstIntervalEntry 2 }


	 msdslWorstIntervalSESs OBJECT-TYPE
	     SYNTAX  INTEGER (1..96)
	     ACCESS  read-only
	     STATUS  mandatory
	     DESCRIPTION
		"The value (1 to 96) indicating the interval 
		 containing the worst Errored Seconds encountered
		 by a DSL  interface."
	    ::= { msdslWorstIntervalEntry 3 }


	 msdslWorstIntervalFEBEs OBJECT-TYPE
	     SYNTAX  INTEGER (1..96)
	     ACCESS  read-only
	     STATUS  mandatory
	     DESCRIPTION
		"The value (1 to 96) indicating the interval 
		 containing the worst Errored Seconds encountered
		 by a DSL  interface."
	    ::= { msdslWorstIntervalEntry 4 }


 -- The MSDSL Total Table

 -- The DSL Total Table contains the cumulative sum of the
 -- various statistics for the 24 hour period preceding the
 -- current interval.

	msdslTotalTable OBJECT-TYPE
	     SYNTAX  SEQUENCE OF MsdslTotalEntry
	     ACCESS  not-accessible
	     STATUS  mandatory
	     DESCRIPTION
		"The DSL Total table.  24 hour interval."
	    ::= { msdslTotal 4 }


	msdslTotalEntry OBJECT-TYPE
	     SYNTAX  MsdslTotalEntry
	     ACCESS  not-accessible
	     STATUS  mandatory
	     DESCRIPTION
		"An entry in the DSL Total table."
	    INDEX   { msdslTotalIfIndex }
	    ::= { msdslTotalTable 1 }

	MsdslTotalEntry ::= SEQUENCE {
	     msdslTotalIfIndex		INTEGER,
	     msdslTotalESs		Gauge,
	     msdslTotalSESs 		Gauge,
	     msdslTotalFEBEs 		Gauge 
	}

	msdslTotalIfIndex OBJECT-TYPE
	     SYNTAX  INTEGER (1..'7fffffff'h)
	     ACCESS  read-only
	     STATUS  mandatory
	     DESCRIPTION
		"The index value which uniquely identifies  the
		DSL interface  to which this entry is applica-
		ble.  The interface identified by a  particular
		value  of  this  index is the same interface as
		identified by the same value as a msdslLineIfIndex
		object instance."
	    ::= { msdslTotalEntry 1 }


	msdslTotalESs OBJECT-TYPE
	     SYNTAX  Gauge
	     ACCESS  read-only
	     STATUS  mandatory
	     DESCRIPTION
		"The number of Errored Seconds encountered by a
		DSL interface in the previous 24 hour interval"
	    ::= { msdslTotalEntry 2 }


	msdslTotalSESs OBJECT-TYPE
	     SYNTAX  Gauge
	     ACCESS  read-only
	     STATUS  mandatory
	     DESCRIPTION
		"The number of Severely Errored Seconds encoun-
		tered  by  a  DSL  interface in the previous 24
		hour interval."
	    ::= { msdslTotalEntry 3 }

 
	msdslTotalFEBEs OBJECT-TYPE
	     SYNTAX Gauge
	     ACCESS read-only
	     STATUS mandatory
	     DESCRIPTION
		"The number of Far End Block Errors ( FEBE)
		encountered  by a DSL interface in the previous
		24 hour interval."
	    ::= { msdslTotalEntry 4 }



 -- Far End Tables
 --
 -- The MSDSL Far End  Current table contains various statistics being
 -- collected for the current 15 minute interval.


	msdslFarEndCurrentTable OBJECT-TYPE
	     SYNTAX  SEQUENCE OF MsdslFarEndCurrentEntry
	     ACCESS  not-accessible
	     STATUS  mandatory
	     DESCRIPTION
		"The MSDSL Current table."
	    ::= { msdslFarEndCurrent 5 }

	msdslFarEndCurrentEntry OBJECT-TYPE
	     SYNTAX  MsdslFarEndCurrentEntry
	     ACCESS  not-accessible
	     STATUS  mandatory
	     DESCRIPTION
		"An entry in the MSDSL Current table."
	    INDEX   { msdslFarEndCurrentIfIndex }
	    ::= { msdslFarEndCurrentTable 1 }

	MsdslFarEndCurrentEntry ::= SEQUENCE {
	     msdslFarEndCurrentIfIndex 		INTEGER,
	     msdslFarEndCurrentESs 		Gauge,
	     msdslFarEndCurrentSESs 		Gauge,
	     msdslFarEndCurrentFEBEs 		Gauge
	 }

	msdslFarEndCurrentIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslFarEndCurrentEntry 1 }


	msdslFarEndCurrentESs OBJECT-TYPE
	     SYNTAX  Gauge
	     ACCESS  read-only
	     STATUS  mandatory
	     DESCRIPTION
		"The number of Errored Seconds, encountered  by
		a MSDSL interface in the current 15 minute inter-
		val."
	    ::= { msdslFarEndCurrentEntry 2 }


	msdslFarEndCurrentSESs OBJECT-TYPE
	     SYNTAX  Gauge
	     ACCESS  read-only
	     STATUS  mandatory
	     DESCRIPTION
		"The number of Severely Errored Seconds encoun-
		tered  by  a  msdsl  interface  in the current 15
		minute interval."
	    ::= { msdslFarEndCurrentEntry 3 }



	msdslFarEndCurrentFEBEs OBJECT-TYPE
	     SYNTAX Gauge
	     ACCESS read-only
	     STATUS mandatory
	     DESCRIPTION
		"The number of Far End Block Errors (FEBE) en-
		countered  by a MSDSL interface in the current 15
		minute interval."
	 ::= { msdslFarEndCurrentEntry 4 }




 -- The msdsl FarEnd Interval
 --
 -- The msdsl FarEnd Interval Table contains various error statistics
 -- collected by each msdsl Interface over the previous 24 hours of
 -- operation.  The past 24 hours are broken into 96 completed
 -- 15 minute intervals.

	msdslFarEndIntervalTable OBJECT-TYPE
	     SYNTAX  SEQUENCE OF MsdslFarEndIntervalEntry
	     ACCESS  not-accessible
	     STATUS  mandatory
	     DESCRIPTION
		"The MSDSL Far End Interval table."
	    ::= { msdslFarEndInterval 6 }

	msdslFarEndIntervalEntry OBJECT-TYPE
	     SYNTAX  MsdslFarEndIntervalEntry
	     ACCESS  not-accessible
	     STATUS  mandatory
	     DESCRIPTION
		"An entry in the msdsl Interval table."
	     INDEX { msdslFarEndIntervalIfIndex,
		     msdslFarEndIntervalNumber }
	    ::= { msdslFarEndIntervalTable 1 }

	MsdslFarEndIntervalEntry ::= SEQUENCE {
	     msdslFarEndIntervalIfIndex 	INTEGER,
	     msdslFarEndIntervalNumber 		INTEGER,
	     msdslFarEndIntervalESs 		Gauge,
	     msdslFarEndIntervalSESs 		Gauge,
	     msdslFarEndIntervalFEBEs 		Gauge
	 }

	msdslFarEndIntervalIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslFarEndIntervalEntry 1 }


	msdslFarEndIntervalNumber OBJECT-TYPE
	     SYNTAX  INTEGER (1..96)
	     ACCESS  read-only
	     STATUS  mandatory
	     DESCRIPTION
		"A number between 1 and 96, where 1 is the most
		recently completed 15 minute interval and 96 is
		the least recently completed 15 minutes  inter-
		val   (assuming   that  all  96  intervals  are
		valid)."
	    ::= { msdslFarEndIntervalEntry 2 }

	msdslFarEndIntervalESs OBJECT-TYPE
	     SYNTAX  Gauge

	     ACCESS  read-only
	     STATUS  mandatory
	     DESCRIPTION
		"The number of Errored Seconds encountered by a
		DSL  interface in one of the previous 96, indi-
		vidual 15 minute, intervals."
	    ::= { msdslFarEndIntervalEntry 3 }


	msdslFarEndIntervalSESs OBJECT-TYPE
	     SYNTAX  Gauge
	     ACCESS  read-only
	     STATUS  mandatory
	     DESCRIPTION
		"The number of Severely Errored Seconds encoun-
		tered by a DSL interface in one of the previous
		96, individual 15 minute, intervals."
	    ::= { msdslFarEndIntervalEntry 4 }


	msdslFarEndIntervalFEBEs OBJECT-TYPE
	     SYNTAX  Gauge
	     ACCESS  read-only
	     STATUS  mandatory
	     DESCRIPTION
		"The number of Far End Block Errors 
		encountered  by  a  MSDSL interface in one of the
		previous 96, individual 15 minute, intervals."
	    ::= { msdslFarEndIntervalEntry 5 }


 -- The msdsl Far End Worst Interval
 --
 -- The msdsl FarEnd Worst Interval Table contains various 
 -- error statistics collected by each msdsl Interface over
 -- the previous 24 hours of operation.  The past 24 hours 
 -- are broken into 96 completed 15 minute intervals.

	msdslFarEndWorstIntervalTable OBJECT-TYPE
	     SYNTAX  SEQUENCE OF MsdslFarEndWorstIntervalEntry
	     ACCESS  not-accessible
	     STATUS  mandatory
	     DESCRIPTION
		"The MSDSL Far End Interval table."
	    ::= { msdslFarEndWorstInterval 7 }

	msdslFarEndWorstIntervalEntry OBJECT-TYPE
	     SYNTAX  MsdslFarEndWorstIntervalEntry
	     ACCESS  not-accessible
	     STATUS  mandatory
	     DESCRIPTION
		"An entry in the msdsl Worst Interval table."
	     INDEX { msdslFarEndWorstIntervalIfIndex }
	    ::= { msdslFarEndWorstIntervalTable 1 }

	MsdslFarEndWorstIntervalEntry ::= SEQUENCE {
	     msdslFarEndWorstIntervalIfIndex 		INTEGER,
	     msdslFarEndWorstIntervalESs 		INTEGER,
	     msdslFarEndWorstIntervalSESs 		INTEGER,
	     msdslFarEndWorstIntervalFEBEs 		INTEGER
	 }

	msdslFarEndWorstIntervalIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslFarEndWorstIntervalEntry 1 }

	msdslFarEndWorstIntervalESs OBJECT-TYPE
	     SYNTAX  INTEGER (1..96)
	     ACCESS  read-only
	     STATUS  mandatory
	     DESCRIPTION
		"The number of Far End Block Errors 
		encountered  by  a  MSDSL interface in one of the
		previous 96, individual 15 minute, intervals."
	    ::= { msdslFarEndWorstIntervalEntry 2 }


	msdslFarEndWorstIntervalSESs OBJECT-TYPE
	     SYNTAX  INTEGER (1..96)
	     ACCESS  read-only
	     STATUS  mandatory
	     DESCRIPTION
		"The value (1 to 96) indicating the interval 
		 containing the worst Errored Seconds encountered
		 by a DSL  interface."
	    ::= { msdslFarEndWorstIntervalEntry 3 }


	msdslFarEndWorstIntervalFEBEs OBJECT-TYPE
	     SYNTAX  INTEGER (1..96)
	     ACCESS  read-only
	     STATUS  mandatory
	     DESCRIPTION
		"The value (1 to 96) indicating the interval 
		 containing the worst Errored Seconds encountered
		 by a DSL  interface."
	    ::= { msdslFarEndWorstIntervalEntry 4 }

 -- The DSL Far End Total Table 
 --
 -- The DSL Total Table contains the cumulative sum of the
 -- various statistics for the 24 hour period preceding the
 -- current interval.

	msdslFarEndTotalTable OBJECT-TYPE
	     SYNTAX  SEQUENCE OF MsdslFarEndTotalEntry
	     ACCESS  not-accessible
	     STATUS  mandatory
	     DESCRIPTION
		"The DSL Total table.  24 hour interval."
	    ::= { msdslFarEndTotal 8 }

	msdslFarEndTotalEntry OBJECT-TYPE
	     SYNTAX  MsdslFarEndTotalEntry
	     ACCESS  not-accessible
	     STATUS  mandatory
	     DESCRIPTION
		"An entry in the DSL Total table."
	    INDEX   { msdslTotalIfIndex }
	    ::= { msdslFarEndTotalTable 1 }

	MsdslFarEndTotalEntry ::= SEQUENCE {
	     msdslFarEndTotalIfIndex 		INTEGER,
	     msdslFarEndTotalESs 		Gauge,
	     msdslFarEndTotalSESs 		Gauge,
	     msdslFarEndTotalFEBEs 		Gauge 
	     }

	msdslFarEndTotalIfIndex OBJECT-TYPE
	     SYNTAX  INTEGER (1..'7fffffff'h)
	     ACCESS  read-only
	     STATUS  mandatory
	     DESCRIPTION
		"The index value which uniquely identifies  the
		DSL interface  to which this entry is applica-
		ble.  The interface identified by a  particular
		value  of  this  index is the same interface as
		identified by the same value as a msdslLineIfIndex
		object instance."
	    ::= { msdslFarEndTotalEntry 1 }


	msdslFarEndTotalESs OBJECT-TYPE
	     SYNTAX  Gauge
	     ACCESS  read-only
	     STATUS  mandatory
	     DESCRIPTION
		"The number of Errored Seconds encountered by a
		DSL interface in the previous 24 hour interval"
	    ::= { msdslFarEndTotalEntry 2 }


	msdslFarEndTotalSESs OBJECT-TYPE
	     SYNTAX  Gauge
	     ACCESS  read-only
	     STATUS  mandatory
	     DESCRIPTION
		"The number of Severely Errored Seconds encoun-
		tered  by  a  DSL  interface in the previous 24
		hour interval."
	    ::= { msdslFarEndTotalEntry 3 }

 
	msdslFarEndTotalFEBEs OBJECT-TYPE
	     SYNTAX Gauge
	     ACCESS read-only
	     STATUS mandatory
	     DESCRIPTION
		"The number of Far End Block Errors ( FEBE)
		encountered  by a DSL interface in the previous
		24 hour interval."
	    ::= { msdslFarEndTotalEntry 4 }



 -- The MSDSL Current Performance Statistics Table
 -- statistics being collected for the current 15 minute interval.

	msdslCurrentPerfTable OBJECT-TYPE
	     SYNTAX  SEQUENCE OF MsdslCurrentPerfEntry
	     ACCESS  not-accessible
	     STATUS  mandatory
	     DESCRIPTION
		"The MSDSL Current Peformance Statistics  table."
	    ::= { msdslCurrentPerf 9 }

	msdslCurrentPerfEntry OBJECT-TYPE
	     SYNTAX  MsdslCurrentPerfEntry
	     ACCESS  not-accessible
	     STATUS  mandatory
	     DESCRIPTION
		"An entry in the MSDSL Current performance table."
	    INDEX   { msdslCurrentPerfIfIndex }
	    ::= { msdslCurrentPerfTable 1 }

	MsdslCurrentPerfEntry ::= SEQUENCE {
	     msdslCurrentPerfIfIndex 		INTEGER,
	     msdslCurrentPerfMargin 		Gauge,
	     msdslCurrentPerfTxPwr 		Gauge,
	     msdslCurrentPerfRxGain 		Gauge,
	     msdslPerfPayloadRate 		Gauge,
	     msdslTimeElapsed 			INTEGER,
	     msdslValidIntervals 		INTEGER
	 }

	msdslCurrentPerfIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslCurrentPerfEntry 1 }


	msdslCurrentPerfMargin OBJECT-TYPE
	     SYNTAX  Gauge
	     ACCESS  read-only
	     STATUS  mandatory
	     DESCRIPTION
		"The average Margin value for the current 
		15 minute interval."
	    ::= { msdslCurrentPerfEntry 2 }


	msdslCurrentPerfTxPwr OBJECT-TYPE
	     SYNTAX  Gauge
	     ACCESS  read-only
	     STATUS  mandatory
	     DESCRIPTION
		"The average value of the Transmit power
		in the current 15 minute interval."
	    ::= { msdslCurrentPerfEntry 3 }


	msdslCurrentPerfRxGain OBJECT-TYPE
	     SYNTAX Gauge
	     ACCESS read-only
	     STATUS mandatory
	     DESCRIPTION
		"The average value of the Receiver gain the current
		15 minute interval."
	 ::= {msdslCurrentPerfEntry 4 }


	msdslPerfPayloadRate OBJECT-TYPE
	     SYNTAX Gauge
	     ACCESS read-only
	     STATUS mandatory
	     DESCRIPTION
		"An estimate of the interface's current bandwidth in
		 bits per second. Current range is: 64k to 2048k."
	 ::= {msdslCurrentPerfEntry 5 }


	msdslTimeElapsed OBJECT-TYPE
	     SYNTAX INTEGER (0..899)
	     ACCESS read-only
	     STATUS mandatory
	     DESCRIPTION
		"The number of seconds that have elapsed since
		 the beginning of the current error-measurment
		 period."
	 ::= {msdslCurrentPerfEntry 6 }


	msdslValidIntervals OBJECT-TYPE
	     SYNTAX INTEGER (0..96)
	     ACCESS read-only
	     STATUS mandatory
	     DESCRIPTION
		"The number of previous intervals for which
		 valid data was collected.  The value will be 96
		 unless the interface was brought on-line within
		 the last 24 hours, in which case the value will
		 be the number of complete 15 minute intervals
		 since the interface has been online."
	 ::= {msdslCurrentPerfEntry 7 }




 -- The MSDSL Current Interval Performance Statistics Table
 --
 -- The msdsl Interval Table contains various performance statistics
 -- collected by each msdsl Interface over the previous 24 hours of
 -- operation.  The past 24 hours are broken into 96 completed
 -- 15 minute intervals.

	msdslIntervalPerfTable OBJECT-TYPE
	     SYNTAX  SEQUENCE OF MsdslIntervalPerfEntry
	     ACCESS  not-accessible
	     STATUS  mandatory
	     DESCRIPTION
		"The MSDSL Interval table."
	    ::= { msdslIntervalPerf 10 }

	msdslIntervalPerfEntry OBJECT-TYPE
	     SYNTAX  MsdslIntervalPerfEntry
	     ACCESS  not-accessible
	     STATUS  mandatory
	     DESCRIPTION
		"An entry in the msdsl Interval performance table."
	    INDEX   { msdslIntervalPerfIfIndex,
		      msdslIntervalPerfNumber }
	    ::= { msdslIntervalPerfTable 1 }

	MsdslIntervalPerfEntry ::= SEQUENCE {
	     msdslIntervalPerfIfIndex 		INTEGER,
	     msdslIntervalPerfNumber 		INTEGER,
	     msdslIntervalPerfMargin 		Gauge,
	     msdslIntervalPerfTxPwr 		Gauge,
	     msdslIntervalPerfRxGain 		Gauge
	 }

	msdslIntervalPerfIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslIntervalPerfEntry 1 }


	msdslIntervalPerfNumber OBJECT-TYPE
	     SYNTAX  INTEGER (1..96)
	     ACCESS  read-only
	     STATUS  mandatory
	     DESCRIPTION
		"A number between 1 and 96, where 1 is the most
		recently completed 15 minute interval and 96 is
		the least recently completed 15 minutes  inter-
		val   (assuming   that  all  96  intervals  are
		valid)."
	    ::= { msdslIntervalPerfEntry 2 }

	msdslIntervalPerfMargin OBJECT-TYPE
	     SYNTAX  Gauge
	     ACCESS  read-only
	     STATUS  mandatory
	     DESCRIPTION
		"The average Margin for a DSL  interface in one of the
		 previous 96, individual 15 minute, intervals."
	    ::= { msdslIntervalPerfEntry 3 }


	msdslIntervalPerfTxPwr OBJECT-TYPE
	     SYNTAX  Gauge
	     ACCESS  read-only
	     STATUS  mandatory
	     DESCRIPTION
		"The average Transmit Power on a DSL interface in one 
		 of the previous 96, individual 15 minute, intervals."
	    ::= { msdslIntervalPerfEntry 4 }


	msdslIntervalPerfRxGain OBJECT-TYPE
	     SYNTAX  Gauge
	     ACCESS  read-only
	     STATUS  mandatory
	     DESCRIPTION
		"The average RxGain on a DSL interface in one of the
		previous 96, individual 15 minute, intervals."
	    ::= { msdslIntervalPerfEntry 5 }


 -- This table is the DSL FarEnd performance Statistics
 --
 -- The MSDSL FarEnd Current Performance Statistics Table
 --
 -- Contains various statistics being collected for the
 -- current 15 minute interval.

	msdslFarEndCurrentPerfTable OBJECT-TYPE
	     SYNTAX  SEQUENCE OF MsdslFarEndCurrentPerfEntry
	     ACCESS  not-accessible
	     STATUS  mandatory
	     DESCRIPTION
		"The MSDSL Current Peformance Statistics  table."
	    ::= { msdslFarEndCurrentPerf 11 }

	msdslFarEndCurrentPerfEntry OBJECT-TYPE
	     SYNTAX  MsdslFarEndCurrentPerfEntry
	     ACCESS  not-accessible
	     STATUS  mandatory
	     DESCRIPTION
		"An entry in the MSDSL Current performance table."
	    INDEX   { msdslFarEndCurrentPerfIfIndex }
	    ::= { msdslFarEndCurrentPerfTable 1 }

	MsdslFarEndCurrentPerfEntry ::= SEQUENCE {
	     msdslFarEndCurrentPerfIfIndex 		INTEGER,
	     msdslFarEndCurrentPerfMargin 		Gauge,
	     msdslFarEndCurrentPerfTxPwr 		Gauge,
	     msdslFarEndCurrentPerfRxGain 		Gauge
	 }

	msdslFarEndCurrentPerfIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslFarEndCurrentPerfEntry 1 }


	msdslFarEndCurrentPerfMargin OBJECT-TYPE
	     SYNTAX  Gauge
	     ACCESS  read-only
	     STATUS  mandatory
	     DESCRIPTION
		"The average Margin value for the current
		 15 minute interval."
	    ::= { msdslFarEndCurrentPerfEntry 2 }


	msdslFarEndCurrentPerfTxPwr OBJECT-TYPE
	     SYNTAX  Gauge
	     ACCESS  read-only
	     STATUS  mandatory
	     DESCRIPTION
		"The average value of the Transmit power 
		in the current 15 minute interval."
	    ::= { msdslFarEndCurrentPerfEntry 3 }



	msdslFarEndCurrentPerfRxGain OBJECT-TYPE
	     SYNTAX Gauge
	     ACCESS read-only
	     STATUS mandatory
	     DESCRIPTION
		"The average value of the Receiver gain the current
		15 minute interval."
	 ::= {msdslFarEndCurrentPerfEntry 4 }


 -- The msdsl FarEnd Performance  Interval Table
 --
 -- The msdsl Interval Table contains various performance statistics
 -- collected by each msdsl Interface over the previous 24 hours of
 -- operation.  The past 24 hours are broken into 96 completed
 -- 15 minute intervals.

	msdslFarEndIntervalPerfTable OBJECT-TYPE
	     SYNTAX  SEQUENCE OF MsdslFarEndIntervalPerfEntry
	     ACCESS  not-accessible
	     STATUS  mandatory
	     DESCRIPTION
		"The MSDSL Interval table."
	    ::= { msdslFarEndIntervalPerf 12 }

	msdslFarEndIntervalPerfEntry OBJECT-TYPE
	     SYNTAX  MsdslFarEndIntervalPerfEntry
	     ACCESS  not-accessible
	     STATUS  mandatory
	     DESCRIPTION
		"An entry in the msdsl Interval performance table."
	    INDEX   { msdslFarEndIntervalPerfIfIndex,
		      msdslFarEndIntervalPerfNumber }
	    ::= { msdslFarEndIntervalPerfTable 1 }

	MsdslFarEndIntervalPerfEntry ::= SEQUENCE {
	     msdslFarEndIntervalPerfIfIndex 		INTEGER,
	     msdslFarEndIntervalPerfNumber 		INTEGER,
	     msdslFarEndIntervalPerfMargin 		Gauge,
	     msdslFarEndIntervalPerfTxPwr 		Gauge,
	     msdslFarEndIntervalPerfRxGain 		Gauge
	 }

	msdslFarEndIntervalPerfIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslFarEndIntervalPerfEntry 1 }


	msdslFarEndIntervalPerfNumber OBJECT-TYPE
	     SYNTAX  INTEGER (1..96)
	     ACCESS  read-only
	     STATUS  mandatory
	     DESCRIPTION
		"A number between 1 and 96, where 1 is the most
		recently completed 15 minute interval and 96 is
		the least recently completed 15 minutes  inter-
		val   (assuming   that  all  96  intervals  are
		valid)."
	    ::= { msdslFarEndIntervalPerfEntry 2 }

	msdslFarEndIntervalPerfMargin OBJECT-TYPE
	     SYNTAX  Gauge
	     ACCESS  read-only
	     STATUS  mandatory
	     DESCRIPTION
		"The average Margin value for the current 15 minute
		interval."
	    ::= { msdslFarEndIntervalPerfEntry 3 }


	msdslFarEndIntervalPerfTxPwr OBJECT-TYPE
	     SYNTAX  Gauge
	     ACCESS  read-only
	     STATUS  mandatory
	     DESCRIPTION
		"The average value of the Transmit power in the
		current 15 minute interval."
	    ::= { msdslFarEndIntervalPerfEntry 4 }


	msdslFarEndIntervalPerfRxGain OBJECT-TYPE
	     SYNTAX  Gauge
	     ACCESS  read-only
	     STATUS  mandatory
	     DESCRIPTION
		"The average value of the Receiver gain the current 15
		minute interval."
	    ::= { msdslFarEndIntervalPerfEntry 5 }


 -- The MSDSL DSX1 Worst Interval Table
 --
 -- The msdsl DSX1 Worst Interval Table contains various error 
 -- statistics collected by each msdsl DSX1 Interface over 
 -- the previous 24 hours of operation.  The past 24 hours 
 -- are broken into 96 completed 15 minute intervals.

	msdsldsx1WorstIntervalTable OBJECT-TYPE
	     SYNTAX  SEQUENCE OF Msdsldsx1WorstIntervalEntry
	     ACCESS  not-accessible
	     STATUS  mandatory
	     DESCRIPTION
		"The MSDSL DSX1 Worst Interval table."
	    ::= { msdsldsx1WorstInterval 13 }

	msdsldsx1WorstIntervalEntry OBJECT-TYPE
	     SYNTAX  Msdsldsx1WorstIntervalEntry
	     ACCESS  not-accessible
	     STATUS  mandatory
	     DESCRIPTION
		"An entry in the msdsl DSX1 Worst Interval table."
	    INDEX { msdsldsx1WorstIntervalIfIndex }
	    ::= { msdsldsx1WorstIntervalTable 1 }

	Msdsldsx1WorstIntervalEntry ::= SEQUENCE {
	     msdsldsx1WorstIntervalIfIndex		INTEGER,
	     msdsldsx1WorstIntervalESs			INTEGER,
	     msdsldsx1WorstIntervalUASs			INTEGER,
	     msdsldsx1WorstIntervalSESs			INTEGER,
	     msdsldsx1WorstIntervalBESs			INTEGER,
	     msdsldsx1WorstIntervalCSSs			INTEGER,
	     msdsldsx1WorstIntervalLOFC			INTEGER			
	 }

	 msdsldsx1WorstIntervalIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdsldsx1WorstIntervalEntry 1 }


	 msdsldsx1WorstIntervalESs OBJECT-TYPE
	     SYNTAX  INTEGER
	     ACCESS  read-only
	     STATUS  mandatory
	     DESCRIPTION
		"The number of Errored Seconds encountered by a
		DSL  interface in one of the previous 96, indi-
		vidual 15 minute, intervals."
	    ::= { msdsldsx1WorstIntervalEntry 2 }


	 msdsldsx1WorstIntervalUASs OBJECT-TYPE
	     SYNTAX  INTEGER
	     ACCESS  read-only
	     STATUS  mandatory
	     DESCRIPTION
		"The number of Unavailable Seconds encountered by a
		DSL  interface in one of the previous 96, indi-
		vidual 15 minute, intervals."
	    ::= { msdsldsx1WorstIntervalEntry 3 }


	 msdsldsx1WorstIntervalSESs OBJECT-TYPE
	     SYNTAX  INTEGER
	     ACCESS  read-only
	     STATUS  mandatory
	     DESCRIPTION
		"The number of Severely Errored Seconds encoun-
		tered by a DSL interface in one of the previous
		96, individual 15 minute, intervals."
	    ::= { msdsldsx1WorstIntervalEntry 4 }


	 msdsldsx1WorstIntervalBESs OBJECT-TYPE
	     SYNTAX  INTEGER
	     ACCESS  read-only
	     STATUS  mandatory
	     DESCRIPTION
		"The number of Bursty Errored Seconds encountered by a
		DSL  interface in one of the previous 96, indi-
		vidual 15 minute, intervals."
	    ::= { msdsldsx1WorstIntervalEntry 5 }


	 msdsldsx1WorstIntervalCSSs OBJECT-TYPE
	     SYNTAX  INTEGER
	     ACCESS  read-only
	     STATUS  mandatory
	     DESCRIPTION
		"The number of Controlled Slip Seconds encountered by a
		DSL  interface in one of the previous 96, indi-
		vidual 15 minute, intervals."
	    ::= { msdsldsx1WorstIntervalEntry 6 }


	 msdsldsx1WorstIntervalLOFC OBJECT-TYPE
	     SYNTAX  INTEGER
	     ACCESS  read-only
	     STATUS  mandatory
	     DESCRIPTION
		"The number of Loss of Frame Counts encountered
		by  a  MSDSL interface in one of the previous 96,
		individual 15 minute, intervals."
	    ::= { msdsldsx1WorstIntervalEntry 7 }


 -- The MSDSL G.703 Worst Interval Table
 --
 -- The msdsl G.703 Worst Interval Table contains various error 
 -- statistics - collected by each msdsl G.703 Interface over 
 -- the previous 24 hours of operation.  The past 24 hours 
 -- are broken into 96 completed 15 minute intervals.

	msdslG703WorstIntervalTable OBJECT-TYPE
	     SYNTAX  SEQUENCE OF MsdslG703WorstIntervalEntry
	     ACCESS  not-accessible
	     STATUS  mandatory
	     DESCRIPTION
		"The MSDSL G.703 Worst Interval table."
	    ::= { msdslG703WorstInterval 14 }

	msdslG703WorstIntervalEntry OBJECT-TYPE
	     SYNTAX  MsdslG703WorstIntervalEntry
	     ACCESS  not-accessible
	     STATUS  mandatory
	     DESCRIPTION
		"An entry in the msdsl G.703 Worst Interval table."
	    INDEX { msdslG703WorstIntervalIfIndex }
	    ::= { msdslG703WorstIntervalTable 1 }

	MsdslG703WorstIntervalEntry ::= SEQUENCE {
	     msdslG703WorstIntervalIfIndex		INTEGER,
	     msdslG703WorstIntervalESs			INTEGER,
	     msdslG703WorstIntervalUASs			INTEGER,
	     msdslG703WorstIntervalSESs			INTEGER,
	     msdslG703WorstIntervalBESs			INTEGER,
	     msdslG703WorstIntervalCSSs			INTEGER,
	     msdslG703WorstIntervalLOFC			INTEGER
	 }

	 msdslG703WorstIntervalIfIndex OBJECT-TYPE
	     SYNTAX  INTEGER (1..'7fffffff'h)
	     ACCESS  read-only
	     STATUS  mandatory
	     DESCRIPTION
		"The index value which uniquely identifies  the
		MSDSL  interface  to which this entry is applica-
		ble."
	    ::= { msdslG703WorstIntervalEntry 1 }


	 msdslG703WorstIntervalESs OBJECT-TYPE
	     SYNTAX  INTEGER
	     ACCESS  read-only
	     STATUS  mandatory
	     DESCRIPTION
		"The number of Errored Seconds encountered by a
		DSL  interface in one of the previous 96, indi-
		vidual 15 minute, intervals."
	    ::= { msdslG703WorstIntervalEntry 2 }


	 msdslG703WorstIntervalUASs OBJECT-TYPE
	     SYNTAX  INTEGER
	     ACCESS  read-only
	     STATUS  mandatory
	     DESCRIPTION
		"The number of Unavailable Seconds encountered by a
		DSL  interface in one of the previous 96, indi-
		vidual 15 minute, intervals."
	    ::= { msdslG703WorstIntervalEntry 3 }


	 msdslG703WorstIntervalSESs OBJECT-TYPE
	     SYNTAX  INTEGER
	     ACCESS  read-only
	     STATUS  mandatory
	     DESCRIPTION
		"The number of Severely Errored Seconds encoun-
		tered by a DSL interface in one of the previous
		96, individual 15 minute, intervals."
	    ::= { msdslG703WorstIntervalEntry 4 }


	 msdslG703WorstIntervalBESs OBJECT-TYPE
	     SYNTAX  INTEGER
	     ACCESS  read-only
	     STATUS  mandatory
	     DESCRIPTION
		"The number of Bursty Errored Seconds encountered by a
		DSL  interface in one of the previous 96, indi-
		vidual 15 minute, intervals."
	    ::= { msdslG703WorstIntervalEntry 5 }


	 msdslG703WorstIntervalCSSs OBJECT-TYPE
	     SYNTAX  INTEGER
	     ACCESS  read-only
	     STATUS  mandatory
	     DESCRIPTION
		"The number of Controlled Slip Seconds encountered by a
		DSL  interface in one of the previous 96, indi-
		vidual 15 minute, intervals."
	    ::= { msdslG703WorstIntervalEntry 6 }


	 msdslG703WorstIntervalLOFC OBJECT-TYPE
	     SYNTAX  INTEGER
	     ACCESS  read-only
	     STATUS  mandatory
	     DESCRIPTION
		"The number of Loss of Frame Counts encountered
		by  a  MSDSL interface in one of the previous 96,
		individual 15 minute, intervals."
	    ::= { msdslG703WorstIntervalEntry 7 }

 --- END OF MSDSL Status definitions


--- START OF MSDSL Configuration: Cross Connections

-- The msdsl Cross Connect Configuration group.

--      This table allows the complete mapping of time slots from any
--	WAN interface to any Network interface, and/or from any WAN interface
--	to any WAN interface. See Note 1.
--
--	The current WAN interface types are either DSX-1 or G.703.
--
--      The Cross Connect objects allow the SNMP management system to:
--       1) display the DS0 channel assignments for the network or 
--          WAN interfaces.
--
--       2) assign all of one WAN interface to the corresponding
--          network interface. (e.g. WAN Port-3 to DSL Port-3) (DS1 By-
--          pass mode).
--
--       3) assign all of one WAN interface to any Network interface.
--           (e.g. WAN Port-3 to DSL Port-8) (DS1 Cross-connect mode).
--
--       4) And/Or assign all of one WAN interface to another WAN interface.
--           (e.g. WAN Port-7 to WAN Port-8) (DS1 Cross-connect mode).(REL 2)
--
--       5) allocate any DS0 time slots on the WAN interfaces to any
--          DS0 time slots on the network interface. (DS0 Cross-connect).
--           (e.g. WAN Port1 TS-1 to DSL Port 3 TS-24).
--
--       6) And/Or allocate any DS0 time slots on the WAN interfaces to other
--          DS0 time slots on the WAN interface. (DS0 Cross-connect).
--           (e.g. WAN Port 1 TS-1, TS-2 to WAN Port 3 TS-23, TS-24). (REL 2)
--
--                      +===============+
--                      |               |
--         WAN Port 1 >-|->-=>==>==>=->-|->DSL Port 1
--                      |               |
--         WAN Port 2 >-|->-=>==>==>=->-|->DSL Port 2
--                      |               |
--         WAN Port 3 >-|->+->>->>      |-> NC
--                      |         \     |
--         WAN Port 4 >-|->+ -     >>+->|->DSL Port 4
--                      |     \         |
--         WAN Port 5 >-|->+ - ->->->+->|->DSL Port 5
--                      |     /         |
--         WAN Port 6 >-|->+ -          |-> NC
--                      |               |
--         WAN Port 7 >-|->+            |-> NC
--                      |  |            |
--         WAN Port 8 >-|->+            |-> NC
--                      |               |
--                      +===============+
--
-- 
--   The block diagram above illustrates ports that are in
--   'ds1ByPass' mode, ds1CrossConn' mode, and ds0CrossConn mode.
--
--   WAN Ports 1 and 2 are in a 'ds1ByPass' mode to DSL Ports 1 and
--   2, the data for those ports by-passes the cross connect circuitry.  
--
--   WAN Port 3 is connected in a 'ds1CrossConn' mode to DSL Port 4. Data
--   for those ports use the cross connect circuitry.  
--
--   WAN Ports 4, 5, and 6 are in a 'ds0CrossConn' mode, with
--   the resulting cross connect time slots to DSL port 5.  Data for
--   those ports use the cross connect circuitry.  
--
--   WAN Ports 7 and 8 are in 'ds1CrossConn' mode. Data for those ports
--   use the cross connect circuitry.
--
-- NOTE 1:
--   The current version of MSDSL firmware only supports WAN to
--   Network interface mapping. WAN to WAN mapping will be available
--   in Release 2.
--
-- NOTE 2:
--   Ports in any mode other than 'ds1ByPass', take their timing from
--   the system clock and may not be clocked independently.
--
-- NOTE 3:
--   It is important to note that when requesting a new connection,
--   all the necessary information used to specify a valid connection
--   must be included in the same SET PDU (i.e., multiple bindings
--   may be necessary).
--
-- When assigning a port (ds1CrossConn) or assigning time slots
--  (ds0CrossConn), it is required that the port or timeslot be 
--  available (i.e. unassigned) prior to the new assignment.
--   As an example:
--    Current 'ds1CrossConn' assignments:
--      WAN Port 2 assigned to DSL Port 4
--      WAN Port 1 assigned to DSL Port 3
--
--    New 'ds1CrossConn' assignments to be:
--      WAN Port 2 to be assigned to DSL Port 3.
--        1) user must unassign DSL Port 3 from WAN Port 1.
--        2) user assigns WAN Port 2 to DSL Port 3.
--
--    The same would hold true for individual time slots (TS)
--
-- In the case of assigning DS0 time slots (TS) between interfaces,
-- two variable bindings are required in the SET PDU in order to
-- specify the entire valid connection (i.e., one binding to set
-- msdslFracPortIfIndex, and one to set msdslFracPortIfTS).
--
-- 
-- When a user specifies a valid connection, the unit completes
-- the connection for both directions simultaneously.  For example,
-- the SET PDU contains the information for connecting WAN Port 5 TS 2
-- interface to DSL Port 8 TS 5 interface.  The unit automatically sets
-- up the connection for the 1) WAN Port 5 TS 2 to DSL Port 8 TS 5, and
-- 2) DSL Port 8 TS 5 to WAN Port 5 TS 2.
--

	msdslFracTable OBJECT-TYPE
	    SYNTAX  SEQUENCE OF MsdslFracEntry
	    ACCESS  not-accessible
	    STATUS  mandatory
	    DESCRIPTION
	       "The Paradyne MSDSL Cross Connect Table."
	    ::= { msdslConfiguration 28 }

	msdslFracEntry OBJECT-TYPE
	    SYNTAX  MsdslFracEntry
	    ACCESS  not-accessible
	    STATUS  mandatory
	    DESCRIPTION
	       "An entry in the Paradyne MSDSL Cross Connect Table."
	    INDEX   { msdslFracPortIndex, msdslFracPortTS }
	    ::= { msdslFracTable 1 }

	MsdslFracEntry ::=
	    SEQUENCE {
		msdslFracPortIndex		INTEGER,
		msdslFracPortTS			INTEGER,
		msdslFracPortIfIndex		INTEGER,
		msdslFracPortIfTS		INTEGER,
		msdslFracPortVoiceData		INTEGER
	    }

	msdslFracPortIndex OBJECT-TYPE
	    SYNTAX  INTEGER
	    ACCESS  read-only
	    STATUS  mandatory
	    DESCRIPTION
	       "  The index value which uniquely identifies the
		interface to which this entry is applicable.
		  The interface identified by a particular value
		of this index is the same interface as identified
		by the same value of ifIndex from the Interfaces
		table of MIB II (RFC 1213)."
	    ::= { msdslFracEntry 1 }

	msdslFracPortTS OBJECT-TYPE
	    SYNTAX  INTEGER (1..31)
	    ACCESS  read-write
	    STATUS  mandatory
	    DESCRIPTION
	       "  The Time Slot number associated with the interface
		identified by msdslFracPortIndex for this entry.
		  If the allocation method is ds1ByPass then this
		object is not required since the whole port specified by 
		msdslFracPortIndex will be assigned to the corresponding 
		msdslFracPortIfIndex.
		  If the allocation method is ds1CrossConn then this object
		is also not required since the whole port specified by 
		msdslFracPortIndex will be assigned to the port specified 
		by msdslFracPortIfIndex.
		  If the allocation method is ds0CrossConn, then this object 
		specifies the Time Slot associated with the interface
		identified by msdslFracPortIndex for this entry."
	    ::= { msdslFracEntry 2 }

	msdslFracPortIfIndex OBJECT-TYPE
	    SYNTAX  INTEGER
	    ACCESS  read-write
	    STATUS  mandatory
	    DESCRIPTION
	        "  An index value that uniquely identifies the interface to
                which this entry is mapped.  The interface identified by
                a particular value of this index is the same interface as
                identified by the same value of an ifIndex object instance
                   If no interface is currently using the Time Slot identified
                 by msdslFracPortTS, then this value should be zero.  This is
 		used to unassign the Time Slot. 
 		  If a single interface occupies more than one time slot, 
 		then its ifIndex value is found in multiple time slots 
 		(i.e., there are multiple entries in table with the same 
 		msdslFracPortIfIndex value)."
	    ::= { msdslFracEntry 3 }

	msdslFracPortIfTS OBJECT-TYPE
	    SYNTAX  INTEGER (1..32)
	    ACCESS  read-write
	    STATUS  mandatory
	    DESCRIPTION
	       "  The Time Slot associated with the interface
		identified by msdslFracPortIfIndex for this entry.
		  If the allocation method is ds1ByPass then this object
		is not required since the whole port specified by 
		msdslFracPortIndex will be assigned to the corresponding 
		msdslFracPortIfIndex.
		  If the allocation method is ds1CrossConn then this object
		is also not required since the whole port specified by 
		msdslFracPortIndex will be assigned to the port specified by
		msdslFracPortIfIndex.
		  If the allocation method is ds0CrossConn, then this object 
		specifies the Time Slot associated with the interface
		identified by msdslFracPortIfIndex for this entry." 
	    ::= { msdslFracEntry 4 }

	msdslFracPortVoiceData OBJECT-TYPE
	    SYNTAX  INTEGER {
			voice(1),
			data(2)		-- default
	     	}
	    ACCESS  read-write
	    STATUS  mandatory
	    DESCRIPTION
	       "The Current mode for this DS0."
	    ::= { msdslFracEntry 5 }


--
--
	msdslPortConfigAllocMethodTable OBJECT-TYPE
	    SYNTAX  SEQUENCE OF MsdslPortConfigAllocMethodEntry
	    ACCESS  not-accessible
	    STATUS  mandatory
	    DESCRIPTION
	       "The Paradyne MSDSL Cross Connect Allocation Method Table."
	    ::= { msdslConfiguration 29 }

	msdslPortConfigAllocMethodEntry  OBJECT-TYPE
	    SYNTAX  MsdslPortConfigAllocMethodEntry
	    ACCESS  not-accessible
	    STATUS  mandatory
	    DESCRIPTION
	       "An entry in the Paradyne MSDSL Cross Connect Table
	        Allocation Method"
	    INDEX   { msdslPortConfigAllocMethodIfIndex }
	    ::= { msdslPortConfigAllocMethodTable 1 }

	MsdslPortConfigAllocMethodEntry ::=
	    SEQUENCE {
		msdslPortConfigAllocMethodIfIndex	INTEGER,
		msdslPortConfigAllocMethod		INTEGER
	    }

	msdslPortConfigAllocMethodIfIndex OBJECT-TYPE
	    SYNTAX  INTEGER
	    ACCESS  read-only
	    STATUS  mandatory
	    DESCRIPTION
	       "  The index value which uniquely identifies the
		interface to which this entry is applicable.
		  The interface identified by a particular value
		of this index is the same interface as
		identified by the same value of ifIndex from 
		the Interfaces table of MIB II (RFC 1213)."
	    ::= { msdslPortConfigAllocMethodEntry 1 }

	msdslPortConfigAllocMethod OBJECT-TYPE
	    SYNTAX  INTEGER {
			  -- the following three values may
			  -- be read or written
			ds1ByPass(1),	-- default
			ds1CrossConn(2),
			ds0CrossConn(3),
			notAssigned(4),

			  -- the following value may 
			  -- be read, but not written
			disabled(5)
	     	}
	    ACCESS  read-write
	    STATUS  mandatory
	    DESCRIPTION
	       "The Current allocation method for this device.
		Where:
		    ds1ByPass:
			    In this mode the entire WAN interface 
			    is connected directly to the DSL interface.
			    This connection provides minimal delay.
			    Changing to this allocation method will 
			    automatically do the following assignments:
				    WAN port 1 >>> DSL Port 1
				    WAN port 2 >>> DSL Port 2
				    WAN port 3 >>> DSL Port 3
				    WAN port 4 >>> DSL Port 4
				    WAN port 5 >>> DSL Port 5
				    WAN port 6 >>> DSL Port 6
				    WAN port 7 >>> DSL Port 7
				    WAN port 8 >>> DSL Port 8
		    ds1CrossConn:
			    In this mode the individual WAN ports may
			    be connected to individual DSL ports through
			    the cross connect circuitry. This connection
			    must use the System Clock for the timing
			    source.  Changing to this allocation method will
			    unassign all the time slots for this interface
			    and any time slots to the connected interface.
				For example:
				    WAN port 1 >>> DSL Port 8
				    WAN port 2 >>> DSL Port 7
				    WAN port 3 >>> DSL Port 6
				    WAN port 4 >>> DSL Port 5
				    WAN port 5 >>> DSL Port 1
				    WAN port 6 >>> DSL Port 2
				    WAN port 7 >>> Not Assigned
				    WAN port 8 >>> WAN Port 7
		    ds0CrossConn:
			    This mode assigns individual time slots. Any
			    timeslot from any WAN interface may be
			    connected to any timeslot of any DSL interface.
			    Changing to this allocation method will unassign
			    all the time slots for this interface and any 
			    time slots to the connected interface.
		    notAssigned:
			    This indicates that this interface is not assigned.
			    Changing to this allocation method will unassign
			    all the time slots for this interface and any 
			    time slots to the connected interface.
		    disabled:
			    This is a Read Only value indicating that the 
			    interface is disabled.

		    NOTE: Going from one mode to another mode will unassign 
		          all the time slots for that interface and the 
			  interface it was connected to. 
			  The only exception being ds1ByPass mode.  When
			  going from any mode to ds1ByPass, all the Time
			  Slots will be assigned Network port to WAN port.
			  These assignments, however, do not use the cross
			  connect circuitry."
	    ::= { msdslPortConfigAllocMethodEntry  2 }


 --- END OF MSDSL Configuration: Cross Connections

 --
 --
 --
 --
 --- START OF MSDSL TRAP definitions

	-- Need to review the traps and decide which ones to keep.
	--
	-- Trap definitions
	--
	-- All traps sent from the DSL cards will have the MCC card's address 
	-- (in the NAP domain) in the ip-address field of the TRAP PDU.
	-- The first varbind of the trap PDU will be the ifIndex which is
	-- overloaded to specify which card in the chassis sent the trap.


	msdslMarginLow TRAP-TYPE
		ENTERPRISE msdslDevice
		VARIABLES { ifIndex }
		DESCRIPTION
		"This trap signifies that the margin estimate 
		 is below a customer set threshold value. This is a trap
		 of 'minor' class."
	::= 3

	msdslMarginNormal TRAP-TYPE
		ENTERPRISE msdslDevice
		VARIABLES { ifIndex }
		DESCRIPTION
		"This trap signifies that the margin estimate  has gone
		 above a customer set threshold value. this is a trap
		 of 'minor' class. this trap compliments the xdslMarginLow
		 trap"
	::= 103

	msdslErrorRateHigh TRAP-TYPE
		ENTERPRISE msdslDevice
		VARIABLES { ifIndex }
		DESCRIPTION
		"This trap signifies that the error rate estimates 
		 is above a customer set threshold value. This is a trap
		 of 'minor' class."
	::= 4

	msdslErrorRateNormal TRAP-TYPE
		ENTERPRISE msdslDevice
		VARIABLES { ifIndex }
		DESCRIPTION
		"This trap signifies that the error rate estimates 
		 gone below a customer set threshold value. This is a trap
		 of 'minor' class. This trap compliments the xdslErrorRateHigh
		 trap."
	::= 104

	 
	msdslTestOver TRAP-TYPE
		ENTERPRISE msdslDevice
		VARIABLES { ifIndex }
		DESCRIPTION
		"This trap signifies that the test has completed on one of the
		 ports. This trap compliments the xdslTestStart trap."
	::= 106

	msdslNTUTypeMismatch TRAP-TYPE
		ENTERPRISE msdslDevice
		VARIABLES { ifIndex }
		DESCRIPTION
		"The LTU configured  does NOT match with the NTU connected
		 to the DSL port indicated by the ifIndex."
	::= 7
END
