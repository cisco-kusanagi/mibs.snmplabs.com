--
--  MIB	definition of common VocalTec Servers parameters.
--

	VTCOMMON-MIB DEFINITIONS ::= BEGIN

	IMPORTS
	TRAP-TYPE FROM RFC-1215
		enterprises, IpAddress,	Counter, Gauge,	TimeTicks
			FROM RFC1155-SMI
		OBJECT-TYPE
			FROM RFC-1212
		DisplayString
			FROM RFC1213-MIB;

----------------------------------------------------------------------------------------

	vocaltec		OBJECT IDENTIFIER ::= { enterprises 2516 }

	vtCommonMIB		OBJECT IDENTIFIER ::= { vocaltec 1 }

	
	-- Operation modes section		

	serverOpModeTable	OBJECT-TYPE
		SYNTAX	SEQUENCE OF OpModeEntry
		ACCESS	not-accessible
		STATUS	mandatory
		DESCRIPTION	
			"List of Vocaltec servers are availabled to manageing
                        through this SNMP agent."
		::= { vtCommonMIB 1 }


	opModeEntry	OBJECT-TYPE
		SYNTAX	OpModeEntry
		ACCESS	not-accessible
		STATUS	mandatory
		DESCRIPTION	
			"Server Operation Mode table entry."
		INDEX	{ serverType, serverIPAddress }
		::= { serverOpModeTable	1 }


	OpModeEntry ::=	
		SEQUENCE {
			serverType
				INTEGER,
			serverIPAddress
				IpAddress,
			command
				INTEGER,
			currentOpMode
				INTEGER
		}


	vtServerType	OBJECT-TYPE
		SYNTAX	INTEGER	{
			other(1),
			vtgw(2),
			vgk(3)
		}
		ACCESS	not-accessible
		STATUS	mandatory
		DESCRIPTION  
			"This parameter defines the type of the Vocaltec server."
		::= { opModeEntry 1 }

	
	vtServerIPAddress  OBJECT-TYPE
		SYNTAX	IpAddress
		ACCESS	not-accessible
		STATUS	mandatory
		DESCRIPTION 
			"The IP address of Vocaltec server, that can be managed
			through this SNMP agent."
		::= { opModeEntry 2 }

	-- this	two will be coordinated	with RCAM team 

	vtCommand  OBJECT-TYPE
		SYNTAX	INTEGER	{
			rma-start(1),
			rma-kill(2),
			rma-reboot(3),
			outOfServiceGracefully(4),
			outOfService(5),
			inService(6),
			shutdownGracefully(7),
			shutdown(8),
			maintain(9)
		}
		ACCESS	not-accessible
		STATUS	mandatory
		DESCRIPTION 
			"Set request of this parameter causes the Vocaltec 
                        server to execute the appropiate command."
		::= { opModeEntry 3 }


	vtCurrentOpMode	OBJECT-TYPE
		SYNTAX	INTEGER	{
			loading(13),
			reLoading(14),
			goingInService(15),
			inService(16),
			goingOutOfService(17),
			outOfService(18),
			shuttingDown(19),
			goingMaintenance(20),
			maintenance(21),
			configurationFault(22),
			unknown(23)
		}
		ACCESS	not-accessible
		STATUS	mandatory
		DESCRIPTION 
			"This parameter displays current 
			operation mode of the Vocaltec server."
		::= { opModeEntry 4 }



	------ Trap section
	------ VocalTec	common traps

	  serverInService TRAP-TYPE
	      ENTERPRISE  vocaltec
	      VARIABLES	  { vtServerType }
	      DESCRIPTION
		  "The SNMP trap that is generated when a server operation
		  mode (vtCurrentOpMode) changed to 'inService'"
	      ::= 1

	  serverOutOfService TRAP-TYPE
	      ENTERPRISE  vocaltec
	      VARIABLES	  { vtServerType }
	      DESCRIPTION
		  "The SNMP trap that is generated when a server operation
		  mode (vtCurrentOpMode) changed to 'outOfService'"
	      ::= 2

	  serverShuttingDown TRAP-TYPE
	      ENTERPRISE  vocaltec
	      VARIABLES	  { vtServerType }
	      DESCRIPTION
		  "The SNMP trap that is generated when a server operation
		  mode (vtCurrentOpMode) changed to 'shuttingDown'"
	      ::= 3

	  serverMaintenance TRAP-TYPE
	      ENTERPRISE  vocaltec
	      VARIABLES	  { vtServerType }
	      DESCRIPTION
		  "The SNMP trap that is generated when a server operation
		  mode (vtCurrentOpMode) changed to 'maintenance'"
	      ::= 4

	  serverConfigurationFault TRAP-TYPE
	      ENTERPRISE  vocaltec
	      VARIABLES	  { vtServerType }
	      DESCRIPTION
		  "The SNMP trap that is generated when a server operation
		  mode (vtCurrentOpMode) changed to 'configurationFault'"
	      ::= 5

	  serverInTransition TRAP-TYPE
	      ENTERPRISE  vocaltec
	      VARIABLES	  { vtServerType, vtCurrentOpMode }
	      DESCRIPTION
		  "The SNMP trap that is generated when a server operation
		  mode (vtCurrentOpMode) changed to one of transition modes"
	      ::= 6

	END
