-- Copyright (C) 1999 Intel Corporation. All rights reserved.
--
-- 802.1p MIB
--
-- This mib was extracted from draft-ietf-bridge-bridgemib-04.txt.
-- It has been converted to SNMPv1.
--
-- Change History:
--
-- Version 0.01
-- Date: 08/19/1999
-- 1.  Update the dot1dTrafficClassesEnabled object and  dot1dPortNumTrafficClasses object's
--     access mode to read-only.
-- 2.  Delete dot1dPortDefaultUserPriority object.
-- 3.  Add dot1dPortGarpJoinTime , dot1dPortGarpLeaveTime and dot1dPortGarpLeaveAllTime objects
--     interval range (20..65535).

-- *****************************************************************************
-- IEEE 802.1P MIB
-- *****************************************************************************

SW-PBRD-MIB     DEFINITIONS ::= BEGIN
    IMPORTS
        Counter                     FROM RFC1155-SMI
        OBJECT-TYPE                 FROM RFC-1212
        dot1dBasePort, MacAddress   FROM RFC1493-MIB
        enterprises     FROM RFC1155-SMI;
        
    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }                

    marconi-mgmt        OBJECT IDENTIFIER ::= { golfcommon 2 }

    es2000Mgmt          OBJECT IDENTIFIER ::= { marconi-mgmt 28 }

    swL2Mgmt            OBJECT IDENTIFIER ::= { es2000Mgmt 2 }

    swVlan              OBJECT IDENTIFIER ::= { swL2Mgmt 8 }

    pBridgeMIBObjects   OBJECT IDENTIFIER ::= { swVlan 4 }

-- *****************************************************************************
-- Textual Conventions
-- *****************************************************************************
-- Declarations for SNMPv1
    EnabledStatus   ::= INTEGER { enabled(1), disabled(2) }
    TruthValue      ::= INTEGER { true(1), false(2) }
    TimeInterval    ::= INTEGER

-- *****************************************************************************
-- groups in the P-BRIDGE MIB
-- *****************************************************************************
    dot1dExtBase    OBJECT IDENTIFIER ::= { pBridgeMIBObjects 1 }
    dot1dPriority   OBJECT IDENTIFIER ::= { pBridgeMIBObjects 2 }
    dot1dGarp       OBJECT IDENTIFIER ::= { pBridgeMIBObjects 3 }
    dot1dGmrp       OBJECT IDENTIFIER ::= { pBridgeMIBObjects 4 }

-- *****************************************************************************
-- the dot1dExtBase group
-- *****************************************************************************
    dot1dDeviceCapabilities OBJECT-TYPE
        SYNTAX  INTEGER
        ACCESS  read-only
        STATUS  mandatory
        DESCRIPTION
            "Indicates the optional parts of IEEE 802.1D and 802.1Q that are
             implemented by this device and are managable through this MIB.
             Capabilities that are allowed on a per-port basis are indicated
             in dot1dPortCapabilities."
        REFERENCE
            "ISO/IEC 15802-3 Section 5.2,
             IEEE 802.1Q/D11 Section 5.2, 12.10.1.1.3/b/2"
        ::= { dot1dExtBase 1 }

    dot1dTrafficClassesEnabled OBJECT-TYPE
        SYNTAX  TruthValue
        ACCESS  read-only
        STATUS  mandatory
        DESCRIPTION
            "The value true(1) indicates that Traffic Classes are enabled on
             this bridge. When false(2), the bridge operates with a single
             priority level for all traffic."
        DEFVAL  { true }
        ::= { dot1dExtBase 2 }

    dot1dGmrpStatus OBJECT-TYPE
        SYNTAX  EnabledStatus
        ACCESS  read-write
        STATUS  mandatory
        DESCRIPTION
            "The administrative status requested by management for GMRP.
             The value enabled(1) indicates that GMRP should be enabled on
             this device, in all VLANs, on all ports for which it has not been
             specifically disabled. When disabled(2), GMRP is disabled, in all
             VLANs, on all ports and all GMRP packets will be forwarded
             transparently. This object affects both Applicant and Registrar
             state machines. A transition from disabled(2) to enabled(1) will
             cause a reset of all GMRP state machines on all ports."
-- +updated by Jemy 2000/2/10 08:38PM B14             
        DEFVAL  { disabled }
-- -        
        ::= { dot1dExtBase 3 }

    dot1dPortCapabilitiesTable OBJECT-TYPE
        SYNTAX  SEQUENCE OF Dot1dPortCapabilitiesEntry
        ACCESS  not-accessible
        STATUS  mandatory
        DESCRIPTION
            "A table that contains capabilities information about every port
             that is associated with this bridge."
        ::= { dot1dExtBase 4 }

    dot1dPortCapabilitiesEntry OBJECT-TYPE
        SYNTAX  Dot1dPortCapabilitiesEntry
        ACCESS  not-accessible
        STATUS  mandatory
        DESCRIPTION
            "A set of capabilities information about this port indexed
             by dot1dBasePort."
        INDEX   {dot1dBasePort}
        ::= { dot1dPortCapabilitiesTable 1 }

    Dot1dPortCapabilitiesEntry ::=
        SEQUENCE {
            dot1dPortCapabilities
                INTEGER
        }

    dot1dPortCapabilities OBJECT-TYPE
        SYNTAX  INTEGER
        ACCESS  read-only
        STATUS  mandatory
        DESCRIPTION
            "Indicates the parts of IEEE 802.1D and 802.1Q that are optional
             on a per-port basis that are implemented by this device and are
             managable through this MIB."
        REFERENCE
            "ISO/IEC 15802-3 Section 5.2,
             IEEE 802.1Q/D11 Section 5.2"
        ::= { dot1dPortCapabilitiesEntry 1 }

-- *****************************************************************************
-- the dot1dPriority group
-- *****************************************************************************
    dot1dPortPriorityTable OBJECT-TYPE
        SYNTAX  SEQUENCE OF Dot1dPortPriorityEntry
        ACCESS  not-accessible
        STATUS  mandatory
        DESCRIPTION
            "A table that contains information about every port that is
             associated with this transparent bridge."
        ::= { dot1dPriority 1 }

    dot1dPortPriorityEntry OBJECT-TYPE
        SYNTAX  Dot1dPortPriorityEntry
        ACCESS  not-accessible
        STATUS  mandatory
        DESCRIPTION
            "A list of the number of egress traffic classes supported for each
             port in a transparent bridge. This is indexed by dot1dBasePort."
        INDEX   { dot1dBasePort }
        ::= { dot1dPortPriorityTable 1 }

    Dot1dPortPriorityEntry ::=
        SEQUENCE {
            dot1dPortNumTrafficClasses
                INTEGER
        }

    dot1dPortNumTrafficClasses OBJECT-TYPE
        SYNTAX  INTEGER (1..8)
        ACCESS  read-only
        STATUS  mandatory
        DESCRIPTION
            "The number of egress traffic classes supported on this port.
             This object may optionally be read-only."
        ::= { dot1dPortPriorityEntry 1 }

-- *****************************************************************************
-- the dot1dGarp group
-- *****************************************************************************
    dot1dPortGarpTable OBJECT-TYPE
        SYNTAX  SEQUENCE OF Dot1dPortGarpEntry
        ACCESS  not-accessible
        STATUS  mandatory
        DESCRIPTION
            "A table of GARP control information about every bridge port.
             This is indexed by dot1dBasePort."
        ::= { dot1dGarp 1 }

    dot1dPortGarpEntry OBJECT-TYPE
        SYNTAX  Dot1dPortGarpEntry
        ACCESS  not-accessible
        STATUS  mandatory
        DESCRIPTION
            "GARP control information for a bridge port."
        INDEX   { dot1dBasePort }
        ::= { dot1dPortGarpTable 1 }

    Dot1dPortGarpEntry ::=
        SEQUENCE {
            dot1dPortGarpJoinTime
                TimeInterval,
            dot1dPortGarpLeaveTime
                TimeInterval,
            dot1dPortGarpLeaveAllTime
                TimeInterval
        }

    dot1dPortGarpJoinTime OBJECT-TYPE
        SYNTAX  TimeInterval (20..65535)
        ACCESS  read-write
        STATUS  mandatory
        DESCRIPTION
            "The GARP Join time, in centiseconds."
        DEFVAL  { 20 }
        ::= { dot1dPortGarpEntry 1 }

    dot1dPortGarpLeaveTime OBJECT-TYPE
        SYNTAX  TimeInterval (20..65535)
        ACCESS  read-write
        STATUS  mandatory
        DESCRIPTION
            "The GARP Leave time, in centiseconds."
        DEFVAL  { 60 }
        ::= { dot1dPortGarpEntry 2 }

    dot1dPortGarpLeaveAllTime OBJECT-TYPE
        SYNTAX  TimeInterval (20..65535)
        ACCESS  read-write
        STATUS  mandatory
        DESCRIPTION
            "The GARP LeaveAll time, in centiseconds."
        DEFVAL  { 1000 }
        ::= { dot1dPortGarpEntry 3 }

-- *****************************************************************************
-- The GMRP Port Configuration and Status Table
-- *****************************************************************************
    dot1dPortGmrpTable OBJECT-TYPE
        SYNTAX  SEQUENCE OF Dot1dPortGmrpEntry
        ACCESS  not-accessible
        STATUS  mandatory
        DESCRIPTION
            "A table of GMRP control and status information about every bridge port.
             Augments the dot1dBasePortTable."
        ::= { dot1dGmrp 1 }

    dot1dPortGmrpEntry OBJECT-TYPE
        SYNTAX  Dot1dPortGmrpEntry
        ACCESS  not-accessible
        STATUS  mandatory
        DESCRIPTION
            "GMRP control and status information for a bridge port."
        INDEX { dot1dBasePort}
        ::= { dot1dPortGmrpTable 1 }

    Dot1dPortGmrpEntry ::=
        SEQUENCE {
            dot1dPortGmrpStatus
                EnabledStatus,
            dot1dPortGmrpFailedRegistrations
                Counter,
            dot1dPortGmrpLastPduOrigin
                MacAddress
        }

    dot1dPortGmrpStatus OBJECT-TYPE
        SYNTAX  EnabledStatus
        ACCESS  read-write
        STATUS  mandatory
        DESCRIPTION
            "The state of GMRP operation on this port.
             The value enabled(1) indicates that GMRP is enabled on this port,
             in all VLANs, as long as dot1dGmrpStatus is also enabled for this
             device.
             When disabled(2) but dot1dGmrpStatus is still enabled for the
             device, GMRP is disabled on this port in all VLANs: any GMRP
             packets received will be silently discarded and no GMRP
             registrations will be propagated from other ports.
             This object affects all GMRP Applicant and Registrar state machines
             on this port.
             A transition from disabled(2) to enabled(1) will cause a reset of
             all GMRP state machines on this port."
        DEFVAL  { enabled }
        ::= { dot1dPortGmrpEntry 1 }

    dot1dPortGmrpFailedRegistrations OBJECT-TYPE
        SYNTAX  Counter
        ACCESS  read-only
        STATUS  mandatory
        DESCRIPTION
            "The total number of failed GMRP registrations, for any reason,
             in all VLANs, on this port."
        ::= { dot1dPortGmrpEntry 2 }

    dot1dPortGmrpLastPduOrigin OBJECT-TYPE
        SYNTAX  MacAddress
        ACCESS  read-only
        STATUS  mandatory
        DESCRIPTION
            "The Source MAC Address of the last GMRP message received on this port."
        ::= { dot1dPortGmrpEntry 3 }

END
