DATALINK-MIB DEFINITIONS ::= BEGIN

IMPORTS
 private, internet, mgmt, NetworkAddress, IpAddress,
 Counter, Gauge, TimeTicks
    FROM RFC1065-SMI
 ObjectName, enterprises
    FROM RFC1155-SMI 
 OBJECT-TYPE
    FROM RFC-1212
 DisplayString
    FROM SNMPv2-TC
 TRAP-TYPE
    FROM RFC-1215 ;




  asentria  OBJECT IDENTIFIER  ::= { enterprises 3052 }
  --1.3.6.1.4.1.3052

  datalink  OBJECT IDENTIFIER  ::= { asentria 1 }
  --1.3.6.1.4.1.3052.1 
 
  productIds  OBJECT IDENTIFIER   ::= { datalink 1 }
  --1.3.6.1.4.1.3052.1.1 
 
  productConfig  OBJECT IDENTIFIER   ::= { datalink 2 }
  --1.3.6.1.4.1.3052.1.2 
 
  unitIds  OBJECT IDENTIFIER   ::= { datalink 3 }
  --1.3.6.1.4.1.3052.1.3 
 
  serialPorts  OBJECT IDENTIFIER   ::= { datalink 4 }
  --1.3.6.1.4.1.3052.1.4 
 
  time  OBJECT IDENTIFIER   ::= { datalink 5 }
  --1.3.6.1.4.1.3052.1.5 
 
  snmpsetup  OBJECT IDENTIFIER   ::= { datalink 6 }
  --1.3.6.1.4.1.3052.1.6 
 
  passwords  OBJECT IDENTIFIER   ::= { datalink 7 }
  --1.3.6.1.4.1.3052.1.7 
 
  ftpsetup  OBJECT IDENTIFIER   ::= { datalink 8 }
  --1.3.6.1.4.1.3052.1.8 
 
  databases  OBJECT IDENTIFIER   ::= { datalink 9 }
  --1.3.6.1.4.1.3052.1.9 
 
  alarms  OBJECT IDENTIFIER   ::= { datalink 10 }
  --1.3.6.1.4.1.3052.1.10 
 
  actions  OBJECT IDENTIFIER   ::= { datalink 11 }
  --1.3.6.1.4.1.3052.1.11 
 
  controls  OBJECT IDENTIFIER   ::= { datalink 12 }
  --1.3.6.1.4.1.3052.1.12 
 
  alarmhistory  OBJECT IDENTIFIER   ::= { datalink 13 }
  --1.3.6.1.4.1.3052.1.13 

  realtimesocket OBJECT IDENTIFIER  ::= { datalink 14 }
  --1.3.6.1.4.1.3052.1.14

  iprestrictions OBJECT IDENTIFIER ::= { datalink 15 }
  --1.3.6.1.4.1.3052.1.15

  ipsetup OBJECT IDENTIFIER ::= { datalink 16 }
  --1.3.6.1.4.1.3052.1.16

  pppsetup OBJECT IDENTIFIER ::= { datalink 17 }
  --1.3.6.1.4.1.3052.1.17

  ccode OBJECT IDENTIFIER ::= { datalink 18 }
  --1.3.6.1.4.1.3052.1.18

  techsupport OBJECT IDENTIFIER     ::= { datalink 99 }
  --1.3.6.1.4.1.3052.1.99

  hardware  OBJECT IDENTIFIER   ::= { productConfig 4 } 
  --1.3.6.1.4.1.3052.1.2.4 
 
  factorysetup  OBJECT IDENTIFIER   ::= { productConfig 5 } 
  --1.3.6.1.4.1.3052.1.2.5 

  commandPassword OBJECT IDENTIFIER ::= { passwords 5 }
  --1.3.6.1.4.1.3052.1.7.5

  entireDatabase  OBJECT IDENTIFIER   ::= { databases 1 } 
  --1.3.6.1.4.1.3052.1.9.1 
 
  databaseStatus  OBJECT IDENTIFIER   ::= { entireDatabase 1 } 
  --1.3.6.1.4.1.3052.1.9.1.1 
 
  databaseFiles  OBJECT IDENTIFIER   ::= { databases 2 } 
  --1.3.6.1.4.1.3052.1.9.2 
 
  filesetup  OBJECT IDENTIFIER   ::= { databaseFiles 1 } 
  --1.3.6.1.4.1.3052.1.9.2.1 
 
  nodataAlarms  OBJECT IDENTIFIER   ::= { alarms 3 } 
  --1.3.6.1.4.1.3052.1.10.3 
 
  nodataAlarmHolidays  OBJECT IDENTIFIER   ::= { nodataAlarms 3 } 
  --1.3.6.1.4.1.3052.1.10.3.3 
 
  actionsBuzzer  OBJECT IDENTIFIER   ::= { actions 1 } 
  --1.3.6.1.4.1.3052.1.11.1 
 
  actionsTraps  OBJECT IDENTIFIER   ::= { actions 5 } 
  --1.3.6.1.4.1.3052.1.11.5 
 
  opSettings  OBJECT IDENTIFIER   ::= { controls 1 } 
  --1.3.6.1.4.1.3052.1.12.1 
 
  auxportMode  OBJECT IDENTIFIER   ::= { opSettings 6 } 
  --1.3.6.1.4.1.3052.1.12.1.6 
 
  inlineHskMode  OBJECT IDENTIFIER   ::= { auxportMode 4 } 
  --1.3.6.1.4.1.3052.1.12.1.6.4 
 
  modemSettings  OBJECT IDENTIFIER   ::= { controls 2 } 
  --1.3.6.1.4.1.3052.1.12.2 
 
  dataRelease  OBJECT IDENTIFIER   ::= { controls 3 } 
  --1.3.6.1.4.1.3052.1.12.3 
 
  otherControls  OBJECT IDENTIFIER   ::= { controls 4 } 
  --1.3.6.1.4.1.3052.1.12.4 

  ftpPush OBJECT IDENTIFIER  ::= { ftpsetup 3 }
  --1.3.6.1.4.1.3052.1.8.3

  actionQueue OBJECT IDENTIFIER ::= { alarmhistory 1 }
  --1.3.6.1.4.1.3052.1.13.1

  actionHistory OBJECT IDENTIFIER ::= { alarmhistory 2 }
  --1.3.6.1.4.1.3052.1.13.2

  ipCurrent OBJECT IDENTIFIER ::= { ipsetup 1 }
  --1.3.6.1.4.1.3052.1.16.1

  ipNew OBJECT IDENTIFIER ::= { ipsetup 2 }
  --1.3.6.1.4.1.3052.1.16.2

  pppIdentification OBJECT IDENTIFIER ::= { pppsetup 1 }
  --1.3.6.1.4.1.3052.1.17.1


datalinkThisProduct OBJECT-TYPE
  SYNTAX DisplayString
  ACCESS read-only 
  STATUS mandatory 
  DESCRIPTION 
 "This is a factory-configured string for the product name"
  ::= { productIds 1 } 
  --1.3.6.1.4.1.3052.1.1.1 
 
productname OBJECT-TYPE 
  SYNTAX DisplayString
  ACCESS read-only 
  STATUS mandatory 
  DESCRIPTION 
    "A second string which may also contain name/version info"
  ::= { productConfig 1 } 
  --1.3.6.1.4.1.3052.1.2.1 
 
systemversion OBJECT-TYPE 
  SYNTAX INTEGER
  ACCESS read-only 
  STATUS mandatory 
  DESCRIPTION 
    "system rom version number"
  ::= { productConfig 2 } 
  --1.3.6.1.4.1.3052.1.2.2 
 
appversion OBJECT-TYPE 
  SYNTAX DisplayString
  ACCESS read-only 
  STATUS mandatory 
  DESCRIPTION 
    "application version"
  ::= { productConfig 3 } 
  --1.3.6.1.4.1.3052.1.2.3 
 
numberports OBJECT-TYPE 
  SYNTAX INTEGER
  ACCESS read-only 
  STATUS mandatory 
  DESCRIPTION 
    "number of RS232 ports found"
  ::= { hardware 1 } 
  --1.3.6.1.4.1.3052.1.2.4.1 
 
netcard OBJECT-TYPE 
  SYNTAX INTEGER
  ACCESS read-only 
  STATUS mandatory 
  DESCRIPTION 
    "0 if no net card, 1 if net card found"
  ::= { hardware 2 } 
  --1.3.6.1.4.1.3052.1.2.4.2 
 
modems OBJECT-TYPE 
  SYNTAX INTEGER
  ACCESS read-only 
  STATUS mandatory 
  DESCRIPTION 
    "0 if no modem, 1 if modem was found"
  ::= { hardware 3 } 
  --1.3.6.1.4.1.3052.1.2.4.3 

networkenabled OBJECT-TYPE
  SYNTAX INTEGER
  ACCESS read-only 
  STATUS mandatory 
  DESCRIPTION 
    "0 if not enabled, 1 if enabled"
  ::= { hardware 4 }
  --1.3.6.1.4.1.3052.1.2.4.4

memorysize OBJECT-TYPE
  SYNTAX INTEGER
  ACCESS read-only 
  STATUS mandatory 
  DESCRIPTION 
    "memory size in K"
  ::= { hardware 5 }
  --1.3.6.1.4.1.3052.1.2.4.5

modemreport OBJECT-TYPE 
  SYNTAX DisplayString
  ACCESS read-write 
  STATUS mandatory 
  DESCRIPTION 
    "5-char string, speed to report for modem speed"
  ::= { factorysetup 1 } 
  --1.3.6.1.4.1.3052.1.2.5.1 
 
modemportspeed OBJECT-TYPE 
  SYNTAX INTEGER
  ACCESS read-write 
  STATUS mandatory 
  DESCRIPTION 
    "modem port baud rate 38400, 19200, etc. "
  ::= { factorysetup 2 } 
  --1.3.6.1.4.1.3052.1.2.5.2 
 
modemsetupstring OBJECT-TYPE 
  SYNTAX DisplayString
  ACCESS read-write 
  STATUS mandatory 
  DESCRIPTION 
    "modem setup string, e.g., ATe0v0s0=1"
  ::= { factorysetup 3 } 
  --1.3.6.1.4.1.3052.1.2.5.3 
 
modemcddelay OBJECT-TYPE 
  SYNTAX INTEGER
  ACCESS read-write 
  STATUS mandatory 
  DESCRIPTION 
    "seconds after CD before sending answer string"
  ::= { factorysetup 4 } 
  --1.3.6.1.4.1.3052.1.2.5.4 
 
modemtype OBJECT-TYPE 
  SYNTAX INTEGER
  ACCESS read-write 
  STATUS mandatory 
  DESCRIPTION 
    "number factory-assigned to this particular modem, manufacturer, etc."
  ::= { factorysetup 5 } 
  --1.3.6.1.4.1.3052.1.2.5.5 
 
serialnumber OBJECT-TYPE 
  SYNTAX DisplayString
  ACCESS read-write 
  STATUS mandatory 
  DESCRIPTION 
    "up to 10 chars for factory-assigned serial number"
  ::= { factorysetup 6 } 
  --1.3.6.1.4.1.3052.1.2.5.6 
 
dateofmanufacture OBJECT-TYPE 
  SYNTAX DisplayString
  ACCESS read-write 
  STATUS mandatory 
  DESCRIPTION 
    "up to 8 chars for factory-assigned date of manufacture"
  ::= { factorysetup 7 } 
  --1.3.6.1.4.1.3052.1.2.5.7 
 
databasemode OBJECT-TYPE 
  SYNTAX INTEGER
  ACCESS read-write 
  STATUS mandatory 
  DESCRIPTION 
    "database compatibility mode, 1 -normal, 2 commandset2, etc."
  ::= { productConfig 6 } 
  --1.3.6.1.4.1.3052.1.2.6 
 
datalinkSiteId OBJECT-TYPE
  SYNTAX DisplayString
  ACCESS read-write 
  STATUS mandatory 
  DESCRIPTION 
 "Site ID string"
  ::= { unitIds 1 } 
  --1.3.6.1.4.1.3052.1.3.1 
 
idByPortTable OBJECT-TYPE 
  SYNTAX SEQUENCE OF SiteByPort
  ACCESS not-accessible 
  STATUS mandatory 
  DESCRIPTION 
 "an id for type of data by port"
  ::= { unitIds 2 } 
  --1.3.6.1.4.1.3052.1.3.2 
 
sitebyport OBJECT-TYPE 
  SYNTAX SiteByPort
  ACCESS not-accessible 
  STATUS mandatory 
  DESCRIPTION 
 "entry for table"
  INDEX { siteindex } 
  ::= { idByPortTable 1 } 
  --1.3.6.1.4.1.3052.1.3.2.1 
 
siteindex OBJECT-TYPE 
  SYNTAX INTEGER
  ACCESS read-only 
  STATUS mandatory 
  DESCRIPTION 
 "index for which port"
  ::= { sitebyport 1 } 
  --1.3.6.1.4.1.3052.1.3.2.1.1 
 
siteID OBJECT-TYPE 
  SYNTAX DisplayString
  ACCESS read-write 
  STATUS mandatory 
  DESCRIPTION 
 "site id or type of data by port"
  ::= { sitebyport 2 } 
  --1.3.6.1.4.1.3052.1.3.2.1.2 
 
 
numberPorts OBJECT-TYPE 
  SYNTAX INTEGER
  ACCESS read-only 
  STATUS mandatory 
  DESCRIPTION 
 "number of RS232 ports found. "
  ::= { serialPorts 1 } 
  --1.3.6.1.4.1.3052.1.4.1 
 
portSetupTable OBJECT-TYPE 
  SYNTAX SEQUENCE OF PortSetup
  ACCESS not-accessible 
  STATUS mandatory 
  DESCRIPTION 
    "port setup table, serial params, collect data, etc."
  ::= { serialPorts 2 } 
  --1.3.6.1.4.1.3052.1.4.2 
 
portSetupEntry OBJECT-TYPE 
  SYNTAX PortSetup
  ACCESS not-accessible 
  STATUS mandatory 
  DESCRIPTION 
  "port setup table, serial params, collect data, etc."
  INDEX { portIndex } 
  ::= { portSetupTable 1 } 
  --1.3.6.1.4.1.3052.1.4.2.1 
 
portIndex OBJECT-TYPE 
  SYNTAX INTEGER
  ACCESS read-only 
  STATUS mandatory 
  DESCRIPTION 
  "index for table"
  ::= { portSetupEntry 1 } 
  --1.3.6.1.4.1.3052.1.4.2.1.1 
 
portBaud OBJECT-TYPE 
  SYNTAX INTEGER
  ACCESS read-write 
  STATUS mandatory 
  DESCRIPTION 
  "baud rate, 19200, 9600, etc."
  ::= { portSetupEntry 2 }
  --1.3.6.1.4.1.3052.1.4.2.1.2
 
portWord OBJECT-TYPE 
  SYNTAX INTEGER
  ACCESS read-write 
  STATUS mandatory 
  DESCRIPTION 
  "word length, must be 7 or 8"
  ::= { portSetupEntry 3 }
  --1.3.6.1.4.1.3052.1.4.2.1.3
 
portParity OBJECT-TYPE 
  SYNTAX DisplayString
  ACCESS read-write 
  STATUS mandatory 
  DESCRIPTION 
  "a single-char string with values of N E or O"
  ::= { portSetupEntry 4 }
  --1.3.6.1.4.1.3052.1.4.2.1.4
 
portStopbits OBJECT-TYPE 
  SYNTAX INTEGER
  ACCESS read-write 
  STATUS mandatory 
  DESCRIPTION 
  "number of stop bits, must be 1"
  ::= { portSetupEntry 5 }
  --1.3.6.1.4.1.3052.1.4.2.1.5
 
portDataStore OBJECT-TYPE 
  SYNTAX INTEGER
  ACCESS read-write 
  STATUS mandatory 
  DESCRIPTION 
  "0 data is not stored, 1 data is stored from this port"
  ::= { portSetupEntry 6 }
  --1.3.6.1.4.1.3052.1.4.2.1.6
 
portBinaryMode OBJECT-TYPE 
  SYNTAX INTEGER
  ACCESS read-write 
  STATUS mandatory 
  DESCRIPTION 
  "0 data is ASCII, 1 data is binary"
  ::= { portSetupEntry 7 }
  --1.3.6.1.4.1.3052.1.4.2.1.7
 
portWrapMode OBJECT-TYPE 
  SYNTAX INTEGER
  ACCESS read-write 
  STATUS mandatory 
  DESCRIPTION 
  "0 oldest data not overwritten, 1 older data is overwritten"
  ::= { portSetupEntry 8 }
  --1.3.6.1.4.1.3052.1.4.2.1.8
 
portHskMode OBJECT-TYPE 
  SYNTAX INTEGER
  ACCESS read-write 
  STATUS mandatory 
  DESCRIPTION 
  "HSK mode to use when buffer close to full,
   0 none, 1 xon, 2 DTR, 3 DTR and Xon"
  ::= { portSetupEntry 9 }
  --1.3.6.1.4.1.3052.1.4.2.1.9
 
portDateTimeStampMode OBJECT-TYPE 
  SYNTAX INTEGER
  ACCESS read-write 
  STATUS mandatory 
  DESCRIPTION 
  "Date/time stamp mode to use,bit mapped
   bit 0 - do date stamp
   bit 1 - include year
   bit 2 - include year 19xx or 20xx
   bit 3 - include day of week
   bit 4 - space after date
   bit 5 - include time
   bit 6 - include seconds
   bit 7 - space after time"
  ::= { portSetupEntry 10 }
  --1.3.6.1.4.1.3052.1.4.2.1.10

portPTMode OBJECT-TYPE
  SYNTAX INTEGER
  ACCESS read-write
  STATUS mandatory 
  DESCRIPTION 
  "pass-through access mode. 0=none, 1=by modem, 2=by network
   any write kills the passthrough connection.
   any write requires private community name"
  ::= { portSetupEntry 11 }
  --1.3.6.1.4.1.3052.1.4.2.1.11

portPTTime OBJECT-TYPE
  SYNTAX INTEGER
  ACCESS read-only
  STATUS mandatory 
  DESCRIPTION 
  "pass-through access mode time of this connection, in seconds"
  ::= { portSetupEntry 12 }
  --1.3.6.1.4.1.3052.1.4.2.1.12

portStoreFile OBJECT-TYPE
  SYNTAX INTEGER
  ACCESS read-write
  STATUS mandatory 
  DESCRIPTION 
  "selects which data file data from this port is stored into"
  ::= { portSetupEntry 13 }
  --1.3.6.1.4.1.3052.1.4.2.1.13

portPtStripOutputLfs OBJECT-TYPE
  SYNTAX INTEGER
  ACCESS read-write
  STATUS mandatory 
  DESCRIPTION 
  "0/1 no/yes in pass-through, strip LFs going to device on this port"
  ::= { portSetupEntry 14 }
  --1.3.6.1.4.1.3052.1.4.2.1.14

portPtStripInputLfs OBJECT-TYPE
  SYNTAX INTEGER
  ACCESS read-write
  STATUS mandatory 
  DESCRIPTION 
  "0/1 no/yes in pass-through, strip LFs coming from device on this port"
  ::= { portSetupEntry 15 }
  --1.3.6.1.4.1.3052.1.4.2.1.15

portlowDTR OBJECT-TYPE
  SYNTAX INTEGER
  ACCESS read-write
  STATUS mandatory 
  DESCRIPTION 
  "0/1 no/yes set DTR low and only raise it on SysAdmin & bypass connections"
  ::= { portSetupEntry 16 }
  --1.3.6.1.4.1.3052.1.4.2.1.16


currenttime OBJECT-TYPE 
  SYNTAX DisplayString
  ACCESS read-write 
  STATUS mandatory 
  DESCRIPTION 
    "Text string for date and time: SUN 01/02/98 12:34:27"
  ::= { time 1 } 
  --1.3.6.1.4.1.3052.1.5.1 
 
autoDstAdjust OBJECT-TYPE 
  SYNTAX INTEGER
  ACCESS read-write 
  STATUS mandatory 
  DESCRIPTION 
    "0 no adjust, 1 adjust"
  ::= { time 2 } 
  --1.3.6.1.4.1.3052.1.5.2 
 
snmpTrapsEnabled OBJECT-TYPE 
  SYNTAX INTEGER
  ACCESS read-write 
  STATUS mandatory 
  DESCRIPTION 
    "0 do not send any traps, 1 do send traps"
  ::= { snmpsetup 1 } 
  --1.3.6.1.4.1.3052.1.6.1 
 
snmpManagerTable OBJECT-TYPE 
  SYNTAX SEQUENCE OF SnmpManager
  ACCESS not-accessible 
  STATUS mandatory 
  DESCRIPTION 
    "management station names and addresses"
  ::= { snmpsetup 2 } 
  --1.3.6.1.4.1.3052.1.6.2 
 
snmpTableEntry OBJECT-TYPE 
  SYNTAX SnmpManager
  ACCESS not-accessible 
  STATUS mandatory 
  DESCRIPTION 
    "entry for snmp table"
  INDEX { snmpMgrIndex } 
  ::= { snmpManagerTable 1 } 
  --1.3.6.1.4.1.3052.1.6.2.1 
 
snmpMgrIndex OBJECT-TYPE 
  SYNTAX INTEGER
  ACCESS read-only 
  STATUS mandatory 
  DESCRIPTION 
    "index for table"
  ::= { snmpTableEntry 1 } 
  --1.3.6.1.4.1.3052.1.6.2.1.1 
 
snmpManagerIp OBJECT-TYPE 
  SYNTAX IpAddress
  ACCESS read-write 
  STATUS mandatory 
  DESCRIPTION 
    "the ip address of a manager"
  ::= { snmpTableEntry 2 } 
  --1.3.6.1.4.1.3052.1.6.2.1.2 
 
snmpManagerName OBJECT-TYPE 
  SYNTAX DisplayString
  ACCESS read-write 
  STATUS mandatory 
  DESCRIPTION 
    "the name of a manager, up to 80 chars"
  ::= { snmpTableEntry 3 } 
  --1.3.6.1.4.1.3052.1.6.2.1.3 
 
snmpTrapsAutoRepeatTime OBJECT-TYPE 
  SYNTAX INTEGER
  ACCESS read-write 
  STATUS mandatory 
  DESCRIPTION 
    "0 do not repeat, else number of minutes to repeat"
  ::= { snmpsetup 3 } 
  --1.3.6.1.4.1.3052.1.6.3 
 
snmpSendTestTrap OBJECT-TYPE 
  SYNTAX INTEGER
  ACCESS read-write 
  STATUS mandatory 
  DESCRIPTION 
    "0 on read, any Set sends test trap to all managers in table"
  ::= { snmpsetup 4 } 
  --1.3.6.1.4.1.3052.1.6.4 
 
-- password items are read-only, except prompt control

modemPasswords OBJECT-TYPE 
  SYNTAX INTEGER
  ACCESS read-write
  STATUS mandatory 
  DESCRIPTION 
    "0 no modem passwords required, 1 modem passwords are required
     write requires private community name"
  ::= { passwords 1 } 
  --1.3.6.1.4.1.3052.1.7.1 
 
tcpPasswords OBJECT-TYPE 
  SYNTAX INTEGER
  ACCESS read-write
  STATUS mandatory 
  DESCRIPTION 
    "0 no telnet/tcp passwords required, 1 passwords are required
     write requires private community name"
  ::= { passwords 2 } 
  --1.3.6.1.4.1.3052.1.7.2 
 
ftpPasswords OBJECT-TYPE 
  SYNTAX INTEGER
  ACCESS read-write
  STATUS mandatory 
  DESCRIPTION 
    "0 no ftp passwords required, 1 passwords are required
     write requires private community name"
  ::= { passwords 3 } 
  --1.3.6.1.4.1.3052.1.7.3

promptPasswords OBJECT-TYPE
  SYNTAX INTEGER
  ACCESS read-write
  STATUS mandatory 
  DESCRIPTION 
    "0 no Password: prompt, 1 -> show Password: prompt"
  ::= { passwords 4 }
  --1.3.6.1.4.1.3052.1.7.4

commandNeedsPassword OBJECT-TYPE
  SYNTAX INTEGER
  ACCESS read-write
  STATUS mandatory 
  DESCRIPTION 
    "0 not needed, 1 is needed
     write requires private community name"
  ::= { commandPassword 1 }
  --1.3.6.1.4.1.3052.1.7.5.1

commandPasswordTimeout OBJECT-TYPE
  SYNTAX INTEGER
  ACCESS read-write
  STATUS mandatory 
  DESCRIPTION 
    "1-99, number of minutes of no activity which auto logs user out"
  ::= { commandPassword 2 }
  --1.3.6.1.4.1.3052.1.7.5.2

passwordTable OBJECT-TYPE
  SYNTAX SEQUENCE OF PasswordTable
  ACCESS not-accessible
  STATUS mandatory
  DESCRIPTION
    "Table of password entries, r-w only with private comm. name"
  ::= { passwords 6 }
  --1.3.6.1.4.1.3052.1.7.6

passwordTableEntry OBJECT-TYPE
  SYNTAX PasswordTable
  ACCESS not-accessible
  STATUS mandatory
  DESCRIPTION
    "entry to password table"
  INDEX { passwordIndex }
  ::= { passwordTable 1 }
  --1.3.6.1.4.1.3052.1.7.6.1

passwordIndex OBJECT-TYPE
  SYNTAX INTEGER
  ACCESS read-only
  STATUS mandatory
  DESCRIPTION
    "index to password table"
  ::= { passwordTableEntry 1 }
  -- 1.3.6.1.4.1.3052.1.7.6.1.1

passwordCommand OBJECT-TYPE
  SYNTAX DisplayString
  ACCESS read-write
  STATUS mandatory
  DESCRIPTION
    "password for command access"
  ::= { passwordTableEntry 2 }
  -- 1.3.6.1.4.1.3052.1.7.6.1.2

passwordAccess OBJECT-TYPE
  SYNTAX DisplayString
  ACCESS read-write
  STATUS mandatory
  DESCRIPTION
    "password for pass-through access"
  ::= { passwordTableEntry 3 }
  -- 1.3.6.1.4.1.3052.1.7.6.1.3


ftpAutoDelete OBJECT-TYPE 
  SYNTAX INTEGER
  ACCESS read-write 
  STATUS mandatory 
  DESCRIPTION 
    "0 files not autodeleted, 1 deleted on reading"
  ::= { ftpsetup 1 } 
  --1.3.6.1.4.1.3052.1.8.1 
 
ftpDataMode OBJECT-TYPE 
  SYNTAX INTEGER
  ACCESS read-write 
  STATUS mandatory 
  DESCRIPTION 
    "0 normal, 1 compression mode 1, etc."
  ::= { ftpsetup 2 } 
  --1.3.6.1.4.1.3052.1.8.2 

ftpPushEnabled OBJECT-TYPE
    SYNTAX INTEGER
    ACCESS read-write
    STATUS mandatory
    DESCRIPTION
      "0-no, 1-yes, enables ftp data push"
    ::= { ftpPush 1 }
    --1.3.6.1.4.1.3052.1.8.3.1

ftpPushTiming OBJECT-TYPE
    SYNTAX INTEGER
    ACCESS read-write
    STATUS mandatory
    DESCRIPTION
      "how often data is pushed, 2-255 minutes"
    ::= { ftpPush 2 }
    --1.3.6.1.4.1.3052.1.8.3.2

ftpPushTimer OBJECT-TYPE
    SYNTAX INTEGER
    ACCESS read-write
    STATUS mandatory
    DESCRIPTION
      "timer which counts to ftpPushTiming"
    ::= { ftpPush 3 }
    --1.3.6.1.4.1.3052.1.8.3.3

ftpPushIPAddress OBJECT-TYPE
    SYNTAX IpAddress
    ACCESS read-write
    STATUS mandatory
    DESCRIPTION
      "ip address of ftp server to which we push the data"
    ::= { ftpPush 4 }
    --1.3.6.1.4.1.3052.1.8.3.4

ftpPushUser OBJECT-TYPE
    SYNTAX DisplayString
    ACCESS read-write
    STATUS mandatory
    DESCRIPTION
      "text string to send for the user id"
    ::= { ftpPush 5 }
    --1.3.6.1.4.1.3052.1.8.3.5

ftpPushPass OBJECT-TYPE
    SYNTAX DisplayString
    ACCESS read-write
    STATUS mandatory
    DESCRIPTION
      "text string to send for the ftp server password"
    ::= { ftpPush 6 }
    --1.3.6.1.4.1.3052.1.8.3.6

ftpPushAcct OBJECT-TYPE
    SYNTAX DisplayString
    ACCESS read-write
    STATUS mandatory
    DESCRIPTION
      "text string to send for the account, if used"
    ::= { ftpPush 7 }
    --1.3.6.1.4.1.3052.1.8.3.7

ftpPushDir OBJECT-TYPE
    SYNTAX DisplayString
    ACCESS read-write
    STATUS mandatory
    DESCRIPTION
      "text string to send for the directory we CWD to"
    ::= { ftpPush 8 }
    --1.3.6.1.4.1.3052.1.8.3.8

-- push table

ftppushTable OBJECT-TYPE
  SYNTAX SEQUENCE OF FtpPushTable
  ACCESS not-accessible
  STATUS mandatory
  DESCRIPTION
    "Table of ftp push enables"
  ::= { ftpPush 9 }
  --1.3.6.1.4.1.3052.1.8.3.9

ftppushTableEntry OBJECT-TYPE
  SYNTAX FtpPushTable
  ACCESS not-accessible
  STATUS mandatory
  DESCRIPTION
    "entry to ftp push table"
  INDEX { ftppushIndex }
  ::= { ftppushTable 1 }
  --1.3.6.1.4.1.3052.1.8.3.9.1

ftppushIndex OBJECT-TYPE
  SYNTAX INTEGER
  ACCESS read-only
  STATUS mandatory
  DESCRIPTION
    "index to ftp push table"
  ::= { ftppushTableEntry 1 }
  --1.3.6.1.4.1.3052.1.8.3.9.1.1

ftppushEnable OBJECT-TYPE
  SYNTAX INTEGER
  ACCESS read-write
  STATUS mandatory
  DESCRIPTION
    "enable for ftp push, indexed by file"
  ::= { ftppushTableEntry 2 }
  --1.3.6.1.4.1.3052.1.8.3.9.1.2


ftpPushAlarms OBJECT-TYPE
    SYNTAX INTEGER
    ACCESS read-write
    STATUS mandatory
    DESCRIPTION
      "0-no, 1-yes, do we push the ALARMS file"
    ::= { ftpPush 10 }
    --1.3.6.1.4.1.3052.1.8.3.10

ftpPushCount OBJECT-TYPE
    SYNTAX INTEGER
    ACCESS read-only
    STATUS mandatory
    DESCRIPTION
      "number of ftp data pushes tried since reboot"
    ::= { ftpPush 11 }
    --1.3.6.1.4.1.3052.1.8.3.11

ftpPushStatusMode OBJECT-TYPE
    SYNTAX INTEGER
    ACCESS read-write
    STATUS mandatory
    DESCRIPTION
      "0-none, 1-append, 2-replace, status file modes"
    ::= { ftpPush 12 }
    --1.3.6.1.4.1.3052.1.8.3.12

ftpPushServerName OBJECT-TYPE
    SYNTAX DisplayString
    ACCESS read-write
    STATUS mandatory
    DESCRIPTION
      "Name of the FTP Push Targer Server"
    ::= { ftpPush 13 }
    --1.3.6.1.4.1.3052.1.8.3.13


databasePfull OBJECT-TYPE
  SYNTAX INTEGER
  ACCESS read-only 
  STATUS mandatory 
  DESCRIPTION 
    "percentage full of all database"
  ::= { databaseStatus 1 } 
  --1.3.6.1.4.1.3052.1.9.1.1.1 
 
databaseSize OBJECT-TYPE 
  SYNTAX INTEGER
  ACCESS read-only 
  STATUS mandatory 
  DESCRIPTION 
    "Size of Data Storage Area, in bytes"
  ::= { databaseStatus 2 } 
  --1.3.6.1.4.1.3052.1.9.1.1.2 
 
databaseRecordsAvailable OBJECT-TYPE 
  SYNTAX INTEGER
  ACCESS read-only 
  STATUS mandatory 
  DESCRIPTION 
    "Records which are available to read, total in all files"
  ::= { databaseStatus 3 } 
  --1.3.6.1.4.1.3052.1.9.1.1.3 
 
databaseRecordsDeleted OBJECT-TYPE 
  SYNTAX INTEGER
  ACCESS read-only 
  STATUS mandatory 
  DESCRIPTION 
    "Records which are deleted, total in all files"
  ::= { databaseStatus 4 } 
  --1.3.6.1.4.1.3052.1.9.1.1.4 
 
databaseAlarmTable OBJECT-TYPE 
  SYNTAX SEQUENCE OF DatabaseAlarm
  ACCESS not-accessible 
  STATUS mandatory 
  DESCRIPTION 
    "table for levels 1 2 3 of all database alarms and actions"
  ::= { entireDatabase 2 } 
  --1.3.6.1.4.1.3052.1.9.1.2 
 
databaseAlarmEntry OBJECT-TYPE 
  SYNTAX DatabaseAlarm
  ACCESS not-accessible 
  STATUS mandatory 
  DESCRIPTION 
    "entry for database alarm config and actions table"
  INDEX { databaseAlarmIndex } 
  ::= { databaseAlarmTable 1 } 
  --1.3.6.1.4.1.3052.1.9.1.2.1 
 
databaseAlarmIndex OBJECT-TYPE
  SYNTAX INTEGER
  ACCESS read-only 
  STATUS mandatory 
  DESCRIPTION 
    "Index for table, 1 2 or 3"
  ::= { databaseAlarmEntry 1 } 
  --1.3.6.1.4.1.3052.1.9.1.2.1.1 
 
databaseAlarmActive OBJECT-TYPE 
  SYNTAX INTEGER
  ACCESS read-write 
  STATUS mandatory 
  DESCRIPTION 
    "0/1, 1 = active"
  ::= { databaseAlarmEntry 2 } 
  --1.3.6.1.4.1.3052.1.9.1.2.1.2 
 
databaseAlarmThreshold OBJECT-TYPE 
  SYNTAX INTEGER
  ACCESS read-write 
  STATUS mandatory 
  DESCRIPTION 
    "1-99, percentage full threshold level"
  ::= { databaseAlarmEntry 3 } 
  --1.3.6.1.4.1.3052.1.9.1.2.1.3 
 
databaseAlarmBeeperActions OBJECT-TYPE 
  SYNTAX INTEGER
  ACCESS read-write 
  STATUS mandatory 
  DESCRIPTION 
    "0 1 2, -> none, 1/10 or 10/10"
  ::= { databaseAlarmEntry 4 } 
  --1.3.6.1.4.1.3052.1.9.1.2.1.4 
 
databaseAlarmSerialActions OBJECT-TYPE 
  SYNTAX INTEGER
  ACCESS read-write 
  STATUS mandatory 
  DESCRIPTION 
    "bits 0-7 show which messages 1-8 are sent"
  ::= { databaseAlarmEntry 5 } 
  --1.3.6.1.4.1.3052.1.9.1.2.1.5 
 
databaseAlarmPagerActions OBJECT-TYPE 
  SYNTAX INTEGER
  ACCESS read-write 
  STATUS mandatory 
  DESCRIPTION 
    "bits 0-7 show which pagers 1-8 are used"
  ::= { databaseAlarmEntry 6 } 
  --1.3.6.1.4.1.3052.1.9.1.2.1.6 
 
databaseAlarmCalloutActions OBJECT-TYPE 
  SYNTAX INTEGER
  ACCESS read-write 
  STATUS mandatory 
  DESCRIPTION 
    "bits 0-7 show which modem callouts 1-8 are used"
  ::= { databaseAlarmEntry 7 } 
  --1.3.6.1.4.1.3052.1.9.1.2.1.7
 
databaseAlarmTrapActions OBJECT-TYPE 
  SYNTAX INTEGER
  ACCESS read-write 
  STATUS mandatory 
  DESCRIPTION 
    "0/1 for traps are sent or not"
  ::= { databaseAlarmEntry 8 } 
  --1.3.6.1.4.1.3052.1.9.1.2.1.8 

databaseAlarmFileStore OBJECT-TYPE
  SYNTAX INTEGER
  ACCESS read-write
  STATUS mandatory
  DESCRIPTION
    "0-no, 1-yes, store alarms in the ALARMS file"
 ::= { entireDatabase 3 }
 --1.3.6.1.4.1.3052.1.9.1.3

databaseAlarmFileMaxSize OBJECT-TYPE
  SYNTAX INTEGER
  ACCESS read-write
  STATUS mandatory
  DESCRIPTION
    "in K, max size for alarms file 4-32k"
 ::= { entireDatabase 4 }
 --1.3.6.1.4.1.3052.1.9.1.4


charmaskEnabled OBJECT-TYPE 
  SYNTAX INTEGER
  ACCESS read-write 
  STATUS mandatory 
  DESCRIPTION 
    "0/1 char masking enabled"
  ::= { filesetup 1 } 
  --1.3.6.1.4.1.3052.1.9.2.1.1 
 
charmask OBJECT-TYPE 
  SYNTAX DisplayString
  ACCESS read-write 
  STATUS mandatory 
  DESCRIPTION 
    "32-byte hex ascii for character masking"
  ::= { filesetup 2 } 
  --1.3.6.1.4.1.3052.1.9.2.1.2 
 
maxRecordChars OBJECT-TYPE 
  SYNTAX INTEGER
  ACCESS read-write 
  STATUS mandatory 
  DESCRIPTION 
    "max characters in an ASCII record"
  ::= { filesetup 3 } 
  --1.3.6.1.4.1.3052.1.9.2.1.3 
 
binRecordBlocking OBJECT-TYPE 
  SYNTAX INTEGER
  ACCESS read-write 
  STATUS mandatory 
  DESCRIPTION 
    "# chars max to block binary records into"
  ::= { filesetup 4 } 
  --1.3.6.1.4.1.3052.1.9.2.1.4 
 
recordCollectionTimeout OBJECT-TYPE 
  SYNTAX INTEGER
  ACCESS read-write 
  STATUS mandatory 
  DESCRIPTION 
    "# seconds to allow before terminating a record automatically"
  ::= { filesetup 5 } 
  --1.3.6.1.4.1.3052.1.9.2.1.5 
 
fileTable OBJECT-TYPE 
  SYNTAX SEQUENCE OF FileTable
  ACCESS not-accessible 
  STATUS mandatory 
  DESCRIPTION 
    "table of directory entries"
  ::= { databaseFiles 2 } 
  --1.3.6.1.4.1.3052.1.9.2.2 
 
fileTableEntry OBJECT-TYPE 
  SYNTAX FileTable
  ACCESS not-accessible 
  STATUS mandatory 
  DESCRIPTION 
    "entry for table"
  INDEX { fileTableIndex } 
  ::= { fileTable 1 } 
  --1.3.6.1.4.1.3052.1.9.2.2.1 
 
fileTableIndex OBJECT-TYPE 
  SYNTAX INTEGER
  ACCESS read-only 
  STATUS mandatory 
  DESCRIPTION 
    "index for the table"
  ::= { fileTableEntry 1 } 
  --1.3.6.1.4.1.3052.1.9.2.2.1.1 
 
fileName OBJECT-TYPE 
  SYNTAX DisplayString
  ACCESS read-only 
  STATUS mandatory 
  DESCRIPTION 
    "name of the file"
  ::= { fileTableEntry 2 } 
  --1.3.6.1.4.1.3052.1.9.2.2.1.2 
 
fileType OBJECT-TYPE 
  SYNTAX DisplayString
  ACCESS read-write 
  STATUS mandatory 
  DESCRIPTION 
    "type of data, up to 24 chars"
  ::= { fileTableEntry 3 } 
  --1.3.6.1.4.1.3052.1.9.2.2.1.3 
 
fileSize OBJECT-TYPE 
  SYNTAX INTEGER
  ACCESS read-only 
  STATUS mandatory 
  DESCRIPTION 
    "file size in bytes"
  ::= { fileTableEntry 4 } 
  --1.3.6.1.4.1.3052.1.9.2.2.1.4 
 
fileRecords OBJECT-TYPE 
  SYNTAX INTEGER
  ACCESS read-only 
  STATUS mandatory 
  DESCRIPTION 
    "file size in records"
  ::= { fileTableEntry 5 } 
  --1.3.6.1.4.1.3052.1.9.2.2.1.5 
 
fileRecordsAvailable OBJECT-TYPE 
  SYNTAX INTEGER
  ACCESS read-only 
  STATUS mandatory 
  DESCRIPTION 
    "# recs available"
  ::= { fileTableEntry 6 } 
  --1.3.6.1.4.1.3052.1.9.2.2.1.6 
 
fileRecordsDeleted OBJECT-TYPE 
  SYNTAX INTEGER
  ACCESS read-only 
  STATUS mandatory 
  DESCRIPTION 
    "# recs deleted"
  ::= { fileTableEntry 7 } 
  --1.3.6.1.4.1.3052.1.9.2.2.1.7 
 
filePercentNow OBJECT-TYPE
  SYNTAX INTEGER
  ACCESS read-only 
  STATUS mandatory 
  DESCRIPTION 
    "% of all of memory this file is, right now"
  ::= { fileTableEntry 8 } 
  --1.3.6.1.4.1.3052.1.9.2.2.1.8 
 
fileAlarms OBJECT-TYPE 
  SYNTAX SEQUENCE OF FileAlarm
  ACCESS not-accessible 
  STATUS mandatory 
  DESCRIPTION 
    "file alarms, indexed by file and threshold"
  ::= { databaseFiles 3 } 
  --1.3.6.1.4.1.3052.1.9.2.3 
 
fileAlarmEntry OBJECT-TYPE 
  SYNTAX FileAlarm
  ACCESS not-accessible 
  STATUS mandatory 
  DESCRIPTION 
    "entry to the table"
  INDEX { fileAlarmFileIndex,
        fileAlarmThreshold } 
  ::= { fileAlarms 1 } 
  --1.3.6.1.4.1.3052.1.9.2.3.1 
 
fileAlarmFileIndex OBJECT-TYPE
  SYNTAX INTEGER
  ACCESS read-only 
  STATUS mandatory 
  DESCRIPTION 
    "index for filenumber"
  ::= { fileAlarmEntry 1 } 
  --1.3.6.1.4.1.3052.1.9.2.3.1.1 
 
fileAlarmThresholdIndex OBJECT-TYPE
  SYNTAX INTEGER
  ACCESS read-only 
  STATUS mandatory 
  DESCRIPTION 
    "index for filenumber threshold"
  ::= { fileAlarmEntry 2 } 
  --1.3.6.1.4.1.3052.1.9.2.3.1.2 
 
fileAlarmActive OBJECT-TYPE 
  SYNTAX INTEGER
  ACCESS read-write 
  STATUS mandatory 
  DESCRIPTION 
    "0/1 this file alarm active"
  ::= { fileAlarmEntry 3 } 
  --1.3.6.1.4.1.3052.1.9.2.3.1.3 
 
fileAlarmThreshold OBJECT-TYPE 
  SYNTAX INTEGER
  ACCESS read-write 
  STATUS mandatory 
  DESCRIPTION 
    "1-99, threshold level"
  ::= { fileAlarmEntry 4 } 
  --1.3.6.1.4.1.3052.1.9.2.3.1.4 
 
fileAlarmBeeperActions OBJECT-TYPE 
  SYNTAX INTEGER
  ACCESS read-write 
  STATUS mandatory 
  DESCRIPTION 
    "0 1 2, none, 1/10 or 10/10"
  ::= { fileAlarmEntry 5 } 
  --1.3.6.1.4.1.3052.1.9.2.3.1.5 
 
fileAlarmSerialActions OBJECT-TYPE 
  SYNTAX INTEGER
  ACCESS read-write 
  STATUS mandatory 
  DESCRIPTION 
    "bits 0-7 show which messages 1-8 are sent"
  ::= { fileAlarmEntry 6 } 
  --1.3.6.1.4.1.3052.1.9.2.3.1.6 
 
fileAlarmPagerActions OBJECT-TYPE 
  SYNTAX INTEGER
  ACCESS read-write 
  STATUS mandatory 
  DESCRIPTION 
    "bits 0-7 show which pagers 1-8 are used"
  ::= { fileAlarmEntry 7 } 
  --1.3.6.1.4.1.3052.1.9.2.3.1.7 
 
fileAlarmCalloutActions OBJECT-TYPE 
  SYNTAX INTEGER
  ACCESS read-write 
  STATUS mandatory 
  DESCRIPTION 
    "bits 0-7 show which modem callouts 1-8 are used"
  ::= { fileAlarmEntry 8 } 
  --1.3.6.1.4.1.3052.1.9.2.3.1.8 
 
fileAlarmTrapActions OBJECT-TYPE 
  SYNTAX INTEGER
  ACCESS read-write 
  STATUS mandatory 
  DESCRIPTION 
    "0/1 for traps are sent or not"
  ::= { fileAlarmEntry 9 } 
  --1.3.6.1.4.1.3052.1.9.2.3.1.9 
 
dataAlarmTable OBJECT-TYPE 
  SYNTAX SEQUENCE OF DataAlarm
  ACCESS not-accessible 
  STATUS mandatory 
  DESCRIPTION 
    "table of read-only items for data alarm setup"
  ::= { alarms 1 } 
  --1.3.6.1.4.1.3052.1.10.1 
 
dataAlarmEntry OBJECT-TYPE 
  SYNTAX DataAlarm
  ACCESS not-accessible 
  STATUS mandatory 
  DESCRIPTION 
    "Data alarm table entry"
  INDEX { dataAlarmIndex } 
  ::= { dataAlarmTable 1 } 
  --1.3.6.1.4.1.3052.1.10.1.1 
 
dataAlarmIndex OBJECT-TYPE
  SYNTAX INTEGER
  ACCESS read-only 
  STATUS mandatory 
  DESCRIPTION 
    "index for data alarms"
  ::= { dataAlarmEntry 1 } 
  --1.3.6.1.4.1.3052.1.10.1.1.1 
 
dataAlarmActive OBJECT-TYPE 
  SYNTAX INTEGER
  ACCESS read-only 
  STATUS mandatory 
  DESCRIPTION 
    "0/1 active"
  ::= { dataAlarmEntry 2 } 
  --1.3.6.1.4.1.3052.1.10.1.1.2 
 
dataAlarmName OBJECT-TYPE
  SYNTAX DisplayString
  ACCESS read-only 
  STATUS mandatory 
  DESCRIPTION 
    "name of alarm"
  ::= { dataAlarmEntry 3 } 
  --1.3.6.1.4.1.3052.1.10.1.1.3 
 
dataAlarmCounter OBJECT-TYPE 
  SYNTAX INTEGER
  ACCESS read-only 
  STATUS mandatory 
  DESCRIPTION 
    "counter for this alarm"
  ::= { dataAlarmEntry 4 } 
  --1.3.6.1.4.1.3052.1.10.1.1.4 
 
dataAlarmThreshold OBJECT-TYPE 
  SYNTAX INTEGER
  ACCESS read-only 
  STATUS mandatory 
  DESCRIPTION 
    "threshold for this alarm"
  ::= { dataAlarmEntry 5 } 
  --1.3.6.1.4.1.3052.1.10.1.1.5 
 
dataAlarmClearMode OBJECT-TYPE 
  SYNTAX INTEGER
  ACCESS read-only 
  STATUS mandatory 
  DESCRIPTION 
    "code for clearing mode"
  ::= { dataAlarmEntry 6 } 
  --1.3.6.1.4.1.3052.1.10.1.1.6 
 
dataAlarmClearTime OBJECT-TYPE 
  SYNTAX DisplayString
  ACCESS read-only 
  STATUS mandatory 
  DESCRIPTION 
    "time of day, e.g., 01:20"
  ::= { dataAlarmEntry 7 } 
  --1.3.6.1.4.1.3052.1.10.1.1.7 
 
dataAlarmAcked OBJECT-TYPE 
  SYNTAX INTEGER
  ACCESS read-write 
  STATUS mandatory 
  DESCRIPTION 
    "0 on read, any set to ack this alarm"
  ::= { dataAlarmEntry 8 } 
  --1.3.6.1.4.1.3052.1.10.1.1.8 
 
dataAlarmBeeperActions OBJECT-TYPE 
  SYNTAX INTEGER
  ACCESS read-only
  STATUS mandatory 
  DESCRIPTION 
    "0 1 2, none, 1/10 or 10/10"
  ::= { dataAlarmEntry 9 } 
  --1.3.6.1.4.1.3052.1.10.1.1.9 
 
dataAlarmSerialActions OBJECT-TYPE 
  SYNTAX INTEGER
  ACCESS read-only
  STATUS mandatory 
  DESCRIPTION 
    "bits 0-7 show which messages 1-8 are sent"
  ::= { dataAlarmEntry 10 } 
  --1.3.6.1.4.1.3052.1.10.1.1.10 
 
dataAlarmPagerActions OBJECT-TYPE 
  SYNTAX INTEGER
  ACCESS read-only
  STATUS mandatory 
  DESCRIPTION 
    "bits 0-7 show which pagers 1-8 are used"
  ::= { dataAlarmEntry 11 } 
  --1.3.6.1.4.1.3052.1.10.1.1.11 
 
dataAlarmCalloutActions OBJECT-TYPE 
  SYNTAX INTEGER
  ACCESS read-only
  STATUS mandatory 
  DESCRIPTION 
    "bits 0-7 show which modem callouts 1-8 are used"
  ::= { dataAlarmEntry 12 } 
  --1.3.6.1.4.1.3052.1.10.1.1.12 
 
dataAlarmTrapActions OBJECT-TYPE
  SYNTAX INTEGER
  ACCESS read-only
  STATUS mandatory 
  DESCRIPTION 
    "0/1 for traps are sent or not"
  ::= { dataAlarmEntry 13 } 
  --1.3.6.1.4.1.3052.1.10.1.1.13

dataAlarmString OBJECT-TYPE
  SYNTAX DisplayString
  ACCESS read-only
  STATUS mandatory 
  DESCRIPTION 
    "last data alarm string for this alarm"
  ::= { dataAlarmEntry 14 }
  --1.3.6.1.4.1.3052.1.10.1.1.14

dataAlarmPort OBJECT-TYPE
  SYNTAX INTEGER
  ACCESS read-only
  STATUS mandatory 
  DESCRIPTION 
    "port number for last data alarm string for this alarm"
  ::= { dataAlarmEntry 15 }
  --1.3.6.1.4.1.3052.1.10.1.1.15

dataAlarmAutoClear OBJECT-TYPE
  SYNTAX INTEGER
  ACCESS read-only
  STATUS mandatory 
  DESCRIPTION 
    "0/1 disabled/enabled to auto clear counter when it reached threshold"
  ::= { dataAlarmEntry 16 }
  --1.3.6.1.4.1.3052.1.10.1.1.16


sensorAlarmTable OBJECT-TYPE 
  SYNTAX SEQUENCE OF SensorAlarm
  ACCESS not-accessible 
  STATUS mandatory 
  DESCRIPTION 
    "table of read-only items for sensor alarm setup"
  ::= { alarms 2 } 
  --1.3.6.1.4.1.3052.1.10.2 
 
sensorAlarmEntry OBJECT-TYPE 
  SYNTAX SensorAlarm
  ACCESS not-accessible 
  STATUS mandatory 
  DESCRIPTION 
    "sensor alarm table entry"
  INDEX { sensorAlarmIndex } 
  ::= { sensorAlarmTable 1 } 
  --1.3.6.1.4.1.3052.1.10.2.1 
 
sensorAlarmIndex OBJECT-TYPE
  SYNTAX INTEGER
  ACCESS read-only 
  STATUS mandatory 
  DESCRIPTION 
    "index for sensor alarms"
  ::= { sensorAlarmEntry 1 } 
  --1.3.6.1.4.1.3052.1.10.2.1.1 
 
sensorAlarmActive OBJECT-TYPE 
  SYNTAX INTEGER
  ACCESS read-write
  STATUS mandatory 
  DESCRIPTION 
    "0/1 active"
  ::= { sensorAlarmEntry 2 } 
  --1.3.6.1.4.1.3052.1.10.2.1.2 
 
sensorAlarmName OBJECT-TYPE
  SYNTAX DisplayString
  ACCESS read-write
  STATUS mandatory 
  DESCRIPTION 
    "name of alarm"
  ::= { sensorAlarmEntry 3 } 
  --1.3.6.1.4.1.3052.1.10.2.1.3 
 
sensorAlarmMode OBJECT-TYPE 
  SYNTAX INTEGER
  ACCESS read-write
  STATUS mandatory 
  DESCRIPTION 
    "0 - open active, 1 - closed active"
  ::= { sensorAlarmEntry 4 } 
  --1.3.6.1.4.1.3052.1.10.2.1.4 
 
sensorAlarmCounter OBJECT-TYPE 
  SYNTAX INTEGER
  ACCESS read-write
  STATUS mandatory 
  DESCRIPTION 
    "counter for this alarm"
  ::= { sensorAlarmEntry 5 } 
  --1.3.6.1.4.1.3052.1.10.2.1.5 
 
sensorAlarmThreshold OBJECT-TYPE 
  SYNTAX INTEGER
  ACCESS read-write
  STATUS mandatory 
  DESCRIPTION 
    "threshold for this alarm"
  ::= { sensorAlarmEntry 6 } 
  --1.3.6.1.4.1.3052.1.10.2.1.6 
 
sensorAlarmAcked OBJECT-TYPE 
  SYNTAX INTEGER
  ACCESS read-write 
  STATUS mandatory 
  DESCRIPTION 
    "0 on read, any set to ack this alarm"
  ::= { sensorAlarmEntry 7 } 
  --1.3.6.1.4.1.3052.1.10.2.1.7 
 
sensorAlarmBeeperActions OBJECT-TYPE 
  SYNTAX INTEGER
  ACCESS read-write 
  STATUS mandatory 
  DESCRIPTION 
    "0 1 2, none, 1/10 or 10/10"
  ::= { sensorAlarmEntry 8 } 
  --1.3.6.1.4.1.3052.1.10.2.1.8 
 
sensorAlarmSerialActions OBJECT-TYPE 
  SYNTAX INTEGER
  ACCESS read-write 
  STATUS mandatory 
  DESCRIPTION 
    "bits 0-7 show which messages 1-8 are sent"
  ::= { sensorAlarmEntry 9 } 
  --1.3.6.1.4.1.3052.1.10.2.1.9 
 
sensorAlarmPagerActions OBJECT-TYPE 
  SYNTAX INTEGER
  ACCESS read-write 
  STATUS mandatory 
  DESCRIPTION 
    "bits 0-7 show which pagers 1-8 are used"
  ::= { sensorAlarmEntry 10 } 
  --1.3.6.1.4.1.3052.1.10.2.1.10 
 
sensorAlarmCalloutActions OBJECT-TYPE 
  SYNTAX INTEGER
  ACCESS read-write 
  STATUS mandatory 
  DESCRIPTION 
    "bits 0-7 show which modem callouts 1-8 are used"
  ::= { sensorAlarmEntry 11 } 
  --1.3.6.1.4.1.3052.1.10.2.1.11 
 
sensorAlarmTrapActions OBJECT-TYPE 
  SYNTAX INTEGER
  ACCESS read-write 
  STATUS mandatory 
  DESCRIPTION 
    "0/1 for traps are sent or not"
  ::= { sensorAlarmEntry 12 } 
  --1.3.6.1.4.1.3052.1.10.2.1.12 

sensorAlarmState OBJECT-TYPE
  SYNTAX INTEGER
  ACCESS read-only
  STATUS mandatory 
  DESCRIPTION 
    "0-> open  1-> closed for current state"
  ::= { sensorAlarmEntry 13 }
  --1.3.6.1.4.1.3052.1.10.2.1.13

nodataAlarmStatus OBJECT-TYPE 
  SYNTAX SEQUENCE OF NodataAlarmStatus
  ACCESS not-accessible 
  STATUS mandatory 
  DESCRIPTION 
    "no data status table"
  ::= { nodataAlarms 1 } 
  --1.3.6.1.4.1.3052.1.10.3.1 
 
nodataAlarmStatusEntry OBJECT-TYPE 
  SYNTAX NodataAlarmStatus
  ACCESS not-accessible 
  STATUS mandatory 
  DESCRIPTION 
    "status table entry"
  INDEX { nodataAlarmStatusIndex } 
  ::= { nodataAlarmStatus 1 } 
  --1.3.6.1.4.1.3052.1.10.3.1.1 
 
nodataAlarmStatusIndex OBJECT-TYPE 
  SYNTAX INTEGER
  ACCESS read-only 
  STATUS mandatory 
  DESCRIPTION 
    "index for table"
  ::= { nodataAlarmStatusEntry 1 } 
  --1.3.6.1.4.1.3052.1.10.3.1.1.1 
 
nodataAlarmStatusCounter OBJECT-TYPE
  SYNTAX INTEGER
  ACCESS read-write 
  STATUS mandatory 
  DESCRIPTION 
    "the nodata counter"
  ::= { nodataAlarmStatusEntry 2 } 
  --1.3.6.1.4.1.3052.1.10.3.1.1.2 
 
nodataAlarmStatusAcked OBJECT-TYPE 
  SYNTAX INTEGER
  ACCESS read-write 
  STATUS mandatory 
  DESCRIPTION 
    "reads as 0, any write acks this alarm"
  ::= { nodataAlarmStatusEntry 3 } 
  --1.3.6.1.4.1.3052.1.10.3.1.1.3 
 
nodataTable OBJECT-TYPE 
  SYNTAX SEQUENCE OF NodataTable
  ACCESS not-accessible 
  STATUS mandatory 
  DESCRIPTION 
    "nodata table"
  ::= { nodataAlarms 2 } 
  --1.3.6.1.4.1.3052.1.10.3.2 
 
nodataTableEntry OBJECT-TYPE 
  SYNTAX NodataTable
  ACCESS not-accessible 
  STATUS mandatory 
  DESCRIPTION 
    "nodata defn. table entry"
  INDEX { nodataTablePortIndex,
        nodataTableScheduleIndex,
        nodataTableLevelIndex } 
  ::= { nodataTable 1 } 
  --1.3.6.1.4.1.3052.1.10.3.2.1 
 
nodataTablePortIndex OBJECT-TYPE
  SYNTAX INTEGER
  ACCESS not-accessible 
  STATUS mandatory 
  DESCRIPTION 
    "index by port"
  ::= { nodataTableEntry 1 } 
  --1.3.6.1.4.1.3052.1.10.3.2.1.1 
 
nodataTableScheduleIndex OBJECT-TYPE
  SYNTAX INTEGER
  ACCESS not-accessible 
  STATUS mandatory 
  DESCRIPTION 
    "index by schedule"
  ::= { nodataTableEntry 2 } 
  --1.3.6.1.4.1.3052.1.10.3.2.1.2 
 
nodataTableLevelIndex OBJECT-TYPE
  SYNTAX INTEGER
  ACCESS not-accessible 
  STATUS mandatory 
  DESCRIPTION 
    "index by level"
  ::= { nodataTableEntry 3 } 
  --1.3.6.1.4.1.3052.1.10.3.2.1.3 
 
nodataTableActive OBJECT-TYPE 
  SYNTAX INTEGER
  ACCESS read-write 
  STATUS mandatory 
  DESCRIPTION 
    "0/1 , enabled or not"
  ::= { nodataTableEntry 4 } 
  --1.3.6.1.4.1.3052.1.10.3.2.1.4 
 
nodataTableSchedule OBJECT-TYPE 
  SYNTAX DisplayString
  ACCESS read-write 
  STATUS mandatory 
  DESCRIPTION 
    "schedule, format is hh:mm-hh:mm"
  ::= { nodataTableEntry 5 } 
  --1.3.6.1.4.1.3052.1.10.3.2.1.5 
 
nodataTableThreshold OBJECT-TYPE
  SYNTAX INTEGER
  ACCESS read-write 
  STATUS mandatory 
  DESCRIPTION 
    "#minutes for no data for alarm"
  ::= { nodataTableEntry 6 } 
  --1.3.6.1.4.1.3052.1.10.3.2.1.6 
 
nodataTableBeeperActions OBJECT-TYPE 
  SYNTAX INTEGER
  ACCESS read-write 
  STATUS mandatory 
  DESCRIPTION 
    "0 1 2, none, 1/10 or 10/10"
  ::= { nodataTableEntry 7 } 
  --1.3.6.1.4.1.3052.1.10.3.2.1.7 
 
nodataTableSerialActions OBJECT-TYPE 
  SYNTAX INTEGER
  ACCESS read-write 
  STATUS mandatory 
  DESCRIPTION 
    "bits 0-7 show which messages 1-8 are sent"
  ::= { nodataTableEntry 8 } 
  --1.3.6.1.4.1.3052.1.10.3.2.1.8 
 
nodataTablePagerActions OBJECT-TYPE 
  SYNTAX INTEGER
  ACCESS read-write 
  STATUS mandatory 
  DESCRIPTION 
    "bits 0-7 show which pagers 1-8 are used"
  ::= { nodataTableEntry 9 } 
  --1.3.6.1.4.1.3052.1.10.3.2.1.9 
 
nodataTableCalloutActions OBJECT-TYPE 
  SYNTAX INTEGER
  ACCESS read-write 
  STATUS mandatory 
  DESCRIPTION 
    "bits 0-7 show which modem callouts 1-8 are used"
  ::= { nodataTableEntry 10 } 
  --1.3.6.1.4.1.3052.1.10.3.2.1.10 
 
nodataTableTrapActions OBJECT-TYPE 
  SYNTAX INTEGER
  ACCESS read-write 
  STATUS mandatory 
  DESCRIPTION 
    "0/1 for traps are sent or not"
  ::= { nodataTableEntry 11 }
  --1.3.6.1.4.1.3052.1.10.3.2.1.11
 
nodataNumberHolidays OBJECT-TYPE 
  SYNTAX INTEGER
  ACCESS read-only 
  STATUS mandatory 
  DESCRIPTION 
    "number of nodata holidays defined"
  ::= { nodataAlarmHolidays 1 } 
  --1.3.6.1.4.1.3052.1.10.3.3.1 
 
nodataHolidayTable OBJECT-TYPE 
  SYNTAX SEQUENCE OF NodataHoliday
  ACCESS not-accessible 
  STATUS mandatory 
  DESCRIPTION 
    "holiday table"
  ::= { nodataAlarmHolidays 2 } 
  --1.3.6.1.4.1.3052.1.10.3.3.2 
 
nodataHolidayTableEntry OBJECT-TYPE 
  SYNTAX NodataHoliday
  ACCESS not-accessible 
  STATUS mandatory 
  DESCRIPTION 
    "holiday table entry"
  INDEX { nodataHolidayIndex } 
  ::= { nodataHolidayTable 1 } 
  --1.3.6.1.4.1.3052.1.10.3.3.2.1 
 
nodataHolidayIndex OBJECT-TYPE 
  SYNTAX INTEGER
  ACCESS read-only 
  STATUS mandatory 
  DESCRIPTION 
    "index for holiday list"
  ::= { nodataHolidayTableEntry 1 } 
  --1.3.6.1.4.1.3052.1.10.3.3.2.1.1 
 
nodataHolidayItem OBJECT-TYPE 
  SYNTAX DisplayString
  ACCESS read-only 
  STATUS mandatory 
  DESCRIPTION 
    "holiday list item, format is mm/dd"
  ::= { nodataHolidayTableEntry 2 } 
  --1.3.6.1.4.1.3052.1.10.3.3.2.1.2 
 
nodataHolidayAdd OBJECT-TYPE 
  SYNTAX DisplayString
  ACCESS read-write 
  STATUS mandatory 
  DESCRIPTION 
    "null on read, set with holiday to add MM/DD"
  ::= { nodataAlarmHolidays 3 } 
  --1.3.6.1.4.1.3052.1.10.3.3.3 
 
nodataHolidayDelete OBJECT-TYPE 
  SYNTAX DisplayString
  ACCESS read-write 
  STATUS mandatory 
  DESCRIPTION 
    "null on read, set with holiday to delete MM/DD"
  ::= { nodataAlarmHolidays 4 } 
  --1.3.6.1.4.1.3052.1.10.3.3.4 

nodataHolidayClear OBJECT-TYPE
  SYNTAX INTEGER
  ACCESS read-write 
  STATUS mandatory 
  DESCRIPTION
  "read returns 0, write requires private community name.
    used to clear the holiday list"
  ::= { nodataAlarmHolidays 5 }
  --1.3.6.1.4.1.3052.1.10.3.3.5


scheduleAlarmTable OBJECT-TYPE 
  SYNTAX SEQUENCE OF ScheduleAlarm
  ACCESS not-accessible 
  STATUS mandatory 
  DESCRIPTION 
    "scheduled alarm table"
  ::= { alarms 4 } 
  --1.3.6.1.4.1.3052.1.10.4 
 
scheduleAlarmEntry OBJECT-TYPE 
  SYNTAX ScheduleAlarm
  ACCESS not-accessible 
  STATUS mandatory 
  DESCRIPTION 
    "schedule table entry"
  INDEX { scheduleIndex } 
  ::= { scheduleAlarmTable 1 } 
  --1.3.6.1.4.1.3052.1.10.4.1 
 
scheduleIndex OBJECT-TYPE 
  SYNTAX INTEGER
  ACCESS read-only 
  STATUS mandatory 
  DESCRIPTION 
    "day index"
  ::= { scheduleAlarmEntry 1 } 
  --1.3.6.1.4.1.3052.1.10.4.1.1 
 
scheduleActive OBJECT-TYPE 
  SYNTAX INTEGER
  ACCESS read-write 
  STATUS mandatory 
  DESCRIPTION 
    "if active or not"
  ::= { scheduleAlarmEntry 2 } 
  --1.3.6.1.4.1.3052.1.10.4.1.2 
 
scheduleTime OBJECT-TYPE 
  SYNTAX DisplayString
  ACCESS read-write 
  STATUS mandatory 
  DESCRIPTION 
    "time of day format is: hh:mm"
  ::= { scheduleAlarmEntry 3 } 
  --1.3.6.1.4.1.3052.1.10.4.1.3 
 
scheduleAcked OBJECT-TYPE 
  SYNTAX INTEGER
  ACCESS read-write 
  STATUS mandatory 
  DESCRIPTION 
    "reads 0, any set acks alarm"
  ::= { scheduleAlarmEntry 4 } 
  --1.3.6.1.4.1.3052.1.10.4.1.4 
 
scheduleBeeperActions OBJECT-TYPE 
  SYNTAX INTEGER
  ACCESS read-write 
  STATUS mandatory 
  DESCRIPTION 
    "0 1 2, none, 1/10 or 10/10"
  ::= { scheduleAlarmEntry 5 } 
  --1.3.6.1.4.1.3052.1.10.4.1.5 
 
scheduleSerialActions OBJECT-TYPE 
  SYNTAX INTEGER
  ACCESS read-write 
  STATUS mandatory 
  DESCRIPTION 
    "bits 0-7 show which messages 1-8 are sent"
  ::= { scheduleAlarmEntry 6 } 
  --1.3.6.1.4.1.3052.1.10.4.1.6 
 
schedulePagerActions OBJECT-TYPE 
  SYNTAX INTEGER
  ACCESS read-write 
  STATUS mandatory 
  DESCRIPTION 
    "bits 0-7 show which pagers 1-8 are used"
  ::= { scheduleAlarmEntry 7 } 
  --1.3.6.1.4.1.3052.1.10.4.1.7 
 
scheduleCalloutActions OBJECT-TYPE 
  SYNTAX INTEGER
  ACCESS read-write 
  STATUS mandatory 
  DESCRIPTION 
    "bits 0-7 show which modem callouts 1-8 are used"
  ::= { scheduleAlarmEntry 8 } 
  --1.3.6.1.4.1.3052.1.10.4.1.8 
 
scheduleTrapActions OBJECT-TYPE 
  SYNTAX INTEGER
  ACCESS read-write 
  STATUS mandatory 
  DESCRIPTION 
    "0/1 for traps are sent or not"
  ::= { scheduleAlarmEntry 9 } 
  --1.3.6.1.4.1.3052.1.10.4.1.9 
 
actionsBuzzerState OBJECT-TYPE 
  SYNTAX INTEGER
  ACCESS read-only 
  STATUS mandatory 
  DESCRIPTION 
    "current buzzer state 0.1.2"
  ::= { actionsBuzzer 1 } 
  --1.3.6.1.4.1.3052.1.11.1.1 
 
actionsSerialTable OBJECT-TYPE 
  SYNTAX SEQUENCE OF SerialTable
  ACCESS not-accessible 
  STATUS mandatory 
  DESCRIPTION 
    "serial message table"
  ::= { actions 2 } 
  --1.3.6.1.4.1.3052.1.11.2 
 
actionsSerialTableEntry OBJECT-TYPE 
  SYNTAX SerialTable
  ACCESS not-accessible 
  STATUS mandatory 
  DESCRIPTION 
    "serial table entry"
  INDEX { serialTableIndex } 
  ::= { actionsSerialTable 1 } 
  --1.3.6.1.4.1.3052.1.11.2.1 
 
serialTableIndex OBJECT-TYPE 
  SYNTAX INTEGER
  ACCESS read-only 
  STATUS mandatory 
  DESCRIPTION 
    "serial table index"
  ::= { actionsSerialTableEntry 1 } 
  --1.3.6.1.4.1.3052.1.11.2.1.1 
 
serialTableMessage OBJECT-TYPE 
  SYNTAX DisplayString
  ACCESS read-write 
  STATUS mandatory 
  DESCRIPTION 
    "serial table string"
  ::= { actionsSerialTableEntry 2 } 
  --1.3.6.1.4.1.3052.1.11.2.1.2 
 
actionsPagerTable OBJECT-TYPE 
  SYNTAX SEQUENCE OF PagerTable
  ACCESS not-accessible 
  STATUS mandatory 
  DESCRIPTION 
    "pager table"
  ::= { actions 3 } 
  --1.3.6.1.4.1.3052.1.11.3 
 
actionsPagerTableEntry OBJECT-TYPE 
  SYNTAX PagerTable
  ACCESS not-accessible 
  STATUS mandatory 
  DESCRIPTION 
    "pager table entry"
  INDEX { pagerTableIndex } 
  ::= { actionsPagerTable 1 } 
  --1.3.6.1.4.1.3052.1.11.3.1 
 
pagerTableIndex OBJECT-TYPE 
  SYNTAX INTEGER
  ACCESS read-only 
  STATUS mandatory 
  DESCRIPTION 
    "table index"
  ::= { actionsPagerTableEntry 1 } 
  --1.3.6.1.4.1.3052.1.11.3.1.1 
 
pagerType OBJECT-TYPE 
  SYNTAX INTEGER
  ACCESS read-write 
  STATUS mandatory 
  DESCRIPTION 
    "0-numeric, 1-alpha"
  ::= { actionsPagerTableEntry 2 } 
  --1.3.6.1.4.1.3052.1.11.3.1.2 
 
pagerPhonenumber OBJECT-TYPE 
  SYNTAX DisplayString
  ACCESS read-write 
  STATUS mandatory 
  DESCRIPTION 
    "phone number to call for pager"
  ::= { actionsPagerTableEntry 3 } 
  --1.3.6.1.4.1.3052.1.11.3.1.3 
 
pagerID OBJECT-TYPE 
  SYNTAX DisplayString
  ACCESS read-write 
  STATUS mandatory 
  DESCRIPTION 
    "ID or 2nd number to dial"
  ::= { actionsPagerTableEntry 4 } 
  --1.3.6.1.4.1.3052.1.11.3.1.4 
 
pagerDialDelay OBJECT-TYPE 
  SYNTAX INTEGER
  ACCESS read-write 
  STATUS mandatory 
  DESCRIPTION 
    "# seconds on numeric to delay between dial and send pagerID or message"
  ::= { actionsPagerTableEntry 5 } 
  --1.3.6.1.4.1.3052.1.11.3.1.5 
 
pagerHangupDelay OBJECT-TYPE 
  SYNTAX INTEGER
  ACCESS read-write 
  STATUS mandatory 
  DESCRIPTION 
    "# seconds on numeric to delay between messages and before hangup"
  ::= { actionsPagerTableEntry 6 } 
  --1.3.6.1.4.1.3052.1.11.3.1.6 
 
pagerMessage OBJECT-TYPE 
  SYNTAX DisplayString
  ACCESS read-write 
  STATUS mandatory 
  DESCRIPTION 
    "message, either alpha or numeric"
  ::= { actionsPagerTableEntry 7 } 
  --1.3.6.1.4.1.3052.1.11.3.1.7 
 
pagerSendId OBJECT-TYPE 
  SYNTAX INTEGER
  ACCESS read-write 
  STATUS mandatory 
  DESCRIPTION 
    "0/1 send unit ID or not to pager"
  ::= { actionsPagerTableEntry 8 } 
  --1.3.6.1.4.1.3052.1.11.3.1.8 
 
pagerSendReason OBJECT-TYPE 
  SYNTAX INTEGER
  ACCESS read-write 
  STATUS mandatory 
  DESCRIPTION 
    "0/1 send reason for page or not to pager"
  ::= { actionsPagerTableEntry 9 } 
  --1.3.6.1.4.1.3052.1.11.3.1.9 
 
pagerMaxAttempts OBJECT-TYPE 
  SYNTAX INTEGER
  ACCESS read-write 
  STATUS mandatory 
  DESCRIPTION 
    "max tries to be successful"
  ::= { actionsPagerTableEntry 10 } 
  --1.3.6.1.4.1.3052.1.11.3.1.10 
 
pagerAttempts OBJECT-TYPE 
  SYNTAX INTEGER
  ACCESS read-write 
  STATUS mandatory 
  DESCRIPTION 
    "current number of tries"
  ::= { actionsPagerTableEntry 11 } 
  --1.3.6.1.4.1.3052.1.11.3.1.11 
 
pagerAttemptDelay OBJECT-TYPE 
  SYNTAX INTEGER
  ACCESS read-write 
  STATUS mandatory 
  DESCRIPTION 
    "# minutes between attempts"
  ::= { actionsPagerTableEntry 12 } 
  --1.3.6.1.4.1.3052.1.11.3.1.12 
 
pagerRepeat OBJECT-TYPE 
  SYNTAX INTEGER
  ACCESS read-write 
  STATUS mandatory 
  DESCRIPTION 
    "0/1 do we repeat successful"
  ::= { actionsPagerTableEntry 13 } 
  --1.3.6.1.4.1.3052.1.11.3.1.13 
 
pagerRepeatDelay OBJECT-TYPE 
  SYNTAX INTEGER
  ACCESS read-write 
  STATUS mandatory 
  DESCRIPTION 
    "# minutes between repeats, if used"
  ::= { actionsPagerTableEntry 14 } 
  --1.3.6.1.4.1.3052.1.11.3.1.14 
 
actionsCalloutTable OBJECT-TYPE 
  SYNTAX SEQUENCE OF CalloutTable
  ACCESS not-accessible 
  STATUS mandatory 
  DESCRIPTION 
    "callout table"
  ::= { actions 4 } 
  --1.3.6.1.4.1.3052.1.11.4 
 
actionsCalloutTableEntry OBJECT-TYPE 
  SYNTAX CalloutTable
  ACCESS not-accessible 
  STATUS mandatory 
  DESCRIPTION 
    "callout table entry"
  INDEX { calloutTableIndex } 
  ::= { actionsCalloutTable 1 } 
  --1.3.6.1.4.1.3052.1.11.4.1 
 
calloutTableIndex OBJECT-TYPE 
  SYNTAX INTEGER
  ACCESS read-only 
  STATUS mandatory 
  DESCRIPTION 
    "table index"
  ::= { actionsCalloutTableEntry 1 } 
  --1.3.6.1.4.1.3052.1.11.4.1.1 
 
calloutPhonenumber OBJECT-TYPE 
  SYNTAX DisplayString
  ACCESS read-write 
  STATUS mandatory 
  DESCRIPTION 
    "phone number to call for callout"
  ::= { actionsCalloutTableEntry 2 } 
  --1.3.6.1.4.1.3052.1.11.4.1.2 
 
calloutMaxConnecttime OBJECT-TYPE 
  SYNTAX INTEGER
  ACCESS read-write 
  STATUS mandatory 
  DESCRIPTION 
    "# seconds to wait for carrier"
  ::= { actionsCalloutTableEntry 3 } 
  --1.3.6.1.4.1.3052.1.11.4.1.3 
 
calloutMessage OBJECT-TYPE 
  SYNTAX DisplayString
  ACCESS read-write 
  STATUS mandatory 
  DESCRIPTION 
   "message to send"
  ::= { actionsCalloutTableEntry 4 } 
  --1.3.6.1.4.1.3052.1.11.4.1.4 
 
calloutSendId OBJECT-TYPE 
  SYNTAX INTEGER
  ACCESS read-write 
  STATUS mandatory 
  DESCRIPTION 
    "0/1 send unit ID or not to callout"
  ::= { actionsCalloutTableEntry 5 } 
  --1.3.6.1.4.1.3052.1.11.4.1.5 
 
calloutSendReason OBJECT-TYPE 
  SYNTAX INTEGER
  ACCESS read-write 
  STATUS mandatory 
  DESCRIPTION 
    "0/1 send reason for page or not to callout"
  ::= { actionsCalloutTableEntry 6 } 
  --1.3.6.1.4.1.3052.1.11.4.1.6 
 
calloutCommandWait OBJECT-TYPE 
  SYNTAX INTEGER
  ACCESS read-write 
  STATUS mandatory 
  DESCRIPTION 
    "#seconds to wait for a command on a callout before hangup"
  ::= { actionsCalloutTableEntry 7 } 
  --1.3.6.1.4.1.3052.1.11.4.1.7 
 
calloutMaxAttempts OBJECT-TYPE 
  SYNTAX INTEGER
  ACCESS read-write 
  STATUS mandatory 
  DESCRIPTION 
    "max tries to be successful"
  ::= { actionsCalloutTableEntry 8 } 
  --1.3.6.1.4.1.3052.1.11.4.1.8 
 
calloutAttempts OBJECT-TYPE 
  SYNTAX INTEGER
  ACCESS read-write 
  STATUS mandatory 
  DESCRIPTION 
    "current number of tries"
  ::= { actionsCalloutTableEntry 9 } 
  --1.3.6.1.4.1.3052.1.11.4.1.9 
 
calloutAttemptDelay OBJECT-TYPE 
  SYNTAX INTEGER
  ACCESS read-write 
  STATUS mandatory 
  DESCRIPTION 
    "# minutes between attempts"
  ::= { actionsCalloutTableEntry 10 } 
  --1.3.6.1.4.1.3052.1.11.4.1.10 
 
calloutRepeat OBJECT-TYPE 
  SYNTAX INTEGER
  ACCESS read-write 
  STATUS mandatory 
  DESCRIPTION 
    "0/1 do we repeat successful"
  ::= { actionsCalloutTableEntry 11 } 
  --1.3.6.1.4.1.3052.1.11.4.1.11 
 
calloutRepeatDelay OBJECT-TYPE 
  SYNTAX INTEGER
  ACCESS read-write 
  STATUS mandatory 
  DESCRIPTION 
    "# minutes between repeats, if used"
  ::= { actionsCalloutTableEntry 12 } 
  --1.3.6.1.4.1.3052.1.11.4.1.12 
 
actionsTrapsEntSpecific OBJECT-TYPE 
  SYNTAX INTEGER
  ACCESS read-write 
  STATUS mandatory 
  DESCRIPTION 
    "0/1 enterprise specific traps enabled"
  ::= { actionsTraps 1 } 
  --1.3.6.1.4.1.3052.1.11.5.1 
 
actionsTrapsEntSpecCount OBJECT-TYPE 
  SYNTAX INTEGER
  ACCESS read-only 
  STATUS mandatory 
  DESCRIPTION 
    "number of enterprise specific traps sent since last re-boot"
  ::= { actionsTraps 2 } 
  --1.3.6.1.4.1.3052.1.11.5.2 
 
linefeeds OBJECT-TYPE 
  SYNTAX INTEGER
  ACCESS read-write 
  STATUS mandatory 
  DESCRIPTION 
    "0/1 are linefeeds added to CRs on command responses?"
  ::= { opSettings 1 } 
  --1.3.6.1.4.1.3052.1.12.1.1 
 
duplex OBJECT-TYPE 
  SYNTAX INTEGER
  ACCESS read-write 
  STATUS mandatory 
  DESCRIPTION 
    "0-half 1-full"
  ::= { opSettings 2 } 
  --1.3.6.1.4.1.3052.1.12.1.2 
 
response OBJECT-TYPE 
  SYNTAX INTEGER
  ACCESS read-write 
  STATUS mandatory 
  DESCRIPTION 
    "0-codes 1-words"
  ::= { opSettings 3 } 
  --1.3.6.1.4.1.3052.1.12.1.3 
 
datafilterEnabled OBJECT-TYPE 
  SYNTAX INTEGER
  ACCESS read-write 
  STATUS mandatory 
  DESCRIPTION 
    "0/1 off/on"
  ::= { opSettings 4 } 
  --1.3.6.1.4.1.3052.1.12.1.4 
 
alarmfilterEnabled OBJECT-TYPE 
  SYNTAX INTEGER
  ACCESS read-write 
  STATUS mandatory 
  DESCRIPTION 
    "0/1 off/on"
  ::= { opSettings 5 } 
  --1.3.6.1.4.1.3052.1.12.1.5 
 
operatingMode OBJECT-TYPE 
  SYNTAX INTEGER
  ACCESS read-write 
  STATUS mandatory 
  DESCRIPTION 
    "1 command 2 input/access 3 unused 4 inline 5 extmodem"
  ::= { auxportMode 1 } 
  --1.3.6.1.4.1.3052.1.12.1.6.1 
 
inlineMode OBJECT-TYPE 
  SYNTAX INTEGER
  ACCESS read-write 
  STATUS mandatory 
  DESCRIPTION 
    "1,2,3 if inline, mode 1 (N->2) mode 2 (1->2, 3->4) mode 3
     (1->2, 3->4, 5->6)"
  ::= { auxportMode 2 } 
  --1.3.6.1.4.1.3052.1.12.1.6.2 
 
inlineSource OBJECT-TYPE 
  SYNTAX INTEGER
  ACCESS read-write 
  STATUS mandatory 
  DESCRIPTION 
    "if inline and inlineMode==1, source of I/O2 inline"
  ::= { auxportMode 3 } 
  --1.3.6.1.4.1.3052.1.12.1.6.3 
 
inlineHsk2 OBJECT-TYPE 
  SYNTAX INTEGER
  ACCESS read-write 
  STATUS mandatory 
  DESCRIPTION 
    "handshake mode 0-3 for inline port I/O 2"
  ::= { inlineHskMode 1 } 
  --1.3.6.1.4.1.3052.1.12.1.6.4.1 
 
inlineHsk4 OBJECT-TYPE 
  SYNTAX INTEGER
  ACCESS read-write 
  STATUS mandatory 
  DESCRIPTION 
    "handshake mode 0-3 for inline port I/O 4"
  ::= { inlineHskMode 2 } 
  --1.3.6.1.4.1.3052.1.12.1.6.4.2 
 
inlineHsk6 OBJECT-TYPE 
  SYNTAX INTEGER
  ACCESS read-write 
  STATUS mandatory 
  DESCRIPTION 
    "handshake mode 0-3 for inline port I/O 6"
  ::= { inlineHskMode 3 } 
  --1.3.6.1.4.1.3052.1.12.1.6.4.3 
 
sureEnabled OBJECT-TYPE 
  SYNTAX INTEGER
  ACCESS read-write 
  STATUS mandatory 
  DESCRIPTION 
    "0/1 off/on"
  ::= { opSettings 7 } 
  --1.3.6.1.4.1.3052.1.12.1.7 

commandTcpipTimeout OBJECT-TYPE
    SYNTAX INTEGER
    ACCESS read-write
    STATUS mandatory
    DESCRIPTION
      "0-none, else number of no-activity minutes -> tcpip command to drop"
  ::= { opSettings 8 }
  --1.3.6.1.4.1.3052.1.12.1.8

sysadminTcpipTimeout OBJECT-TYPE
    SYNTAX INTEGER
    ACCESS read-write
    STATUS mandatory
    DESCRIPTION
      "0-none, else number of no-activity minutes -> tcpip sysadmin to drop"
  ::= { opSettings 9 }
  --1.3.6.1.4.1.3052.1.12.1.9

bypassEndchar OBJECT-TYPE
    SYNTAX INTEGER
    ACCESS read-write
    STATUS mandatory
    DESCRIPTION
      "ascii value for character to exit bypass mode. default ->27"
  ::= { opSettings 10 }
  --1.3.6.1.4.1.3052.1.12.1.10

routerAutoPing OBJECT-TYPE
    SYNTAX INTEGER
    ACCESS read-write
    STATUS mandatory
    DESCRIPTION
        "0/1 = no/yes, default is 0, do we ping the default router
         every 10 minutes?"
  ::= { opSettings 11 }
  --1.3.6.1.4.1.3052.1.12.1.11

modemParity OBJECT-TYPE 
  SYNTAX INTEGER
  ACCESS read-write 
  STATUS mandatory 
  DESCRIPTION 
    "1 7E 2 7O 3 8N"
  ::= { modemSettings 1 } 
  --1.3.6.1.4.1.3052.1.12.2.1 
 
modemUserSetup OBJECT-TYPE 
  SYNTAX DisplayString
  ACCESS read-write 
  STATUS mandatory 
  DESCRIPTION 
    "sent to modem on init before the factory setup string"
  ::= { modemSettings 2 } 
  --1.3.6.1.4.1.3052.1.12.2.2 
 
modemTapSetup OBJECT-TYPE 
  SYNTAX DisplayString
  ACCESS read-write 
  STATUS mandatory 
  DESCRIPTION 
    "sent to modem on just before doing TAP (alpha pager) protocol"
  ::= { modemSettings 3 } 
  --1.3.6.1.4.1.3052.1.12.2.3 
 
modemAnswerString OBJECT-TYPE 
  SYNTAX DisplayString
  ACCESS read-write 
  STATUS mandatory 
  DESCRIPTION 
    "sent when modem makes connection"
  ::= { modemSettings 4 } 
  --1.3.6.1.4.1.3052.1.12.2.4 
 
modemExtSetup OBJECT-TYPE 
  SYNTAX DisplayString
  ACCESS read-write 
  STATUS mandatory 
  DESCRIPTION 
    "sent to ext. modem for setup string"
  ::= { modemSettings 5 } 
  --1.3.6.1.4.1.3052.1.12.2.5 
 
modemExtSetupTime OBJECT-TYPE 
  SYNTAX INTEGER
  ACCESS read-write 
  STATUS mandatory 
  DESCRIPTION 
    "# minutes of idle time between sending ext. modem setup string"
  ::= { modemSettings 6 } 
  --1.3.6.1.4.1.3052.1.12.2.6 
 
modemInactivityTimer OBJECT-TYPE 
  SYNTAX INTEGER
  ACCESS read-write 
  STATUS mandatory 
  DESCRIPTION 
    "# minutes of no transmit which aborts a connection"
  ::= { modemSettings 7 } 
  --1.3.6.1.4.1.3052.1.12.2.7 
 
modemAutoexecString OBJECT-TYPE 
  SYNTAX DisplayString
  ACCESS read-write 
  STATUS mandatory 
  DESCRIPTION 
    "command string which auto-executes after modem connection if
     no other command within 10 seconds"
  ::= { modemSettings 8 } 
  --1.3.6.1.4.1.3052.1.12.2.8 
 
modemAutoexecEnabled OBJECT-TYPE 
  SYNTAX INTEGER
  ACCESS read-write 
  STATUS mandatory 
  DESCRIPTION 
    "0/1 autoexec enabled"
  ::= { modemSettings 9 } 
  --1.3.6.1.4.1.3052.1.12.2.9 
 
modemTimeBetweenOutbound OBJECT-TYPE 
  SYNTAX INTEGER
  ACCESS read-write 
  STATUS mandatory 
  DESCRIPTION 
    "# seconds (minimum) between outbound call attempts"
  ::= { modemSettings 10 } 
  --1.3.6.1.4.1.3052.1.12.2.10 
 
releaseMode OBJECT-TYPE 
  SYNTAX INTEGER
  ACCESS read-write 
  STATUS mandatory 
  DESCRIPTION 
    "1-Line 3-CBB 4-Xmodem"
  ::= { dataRelease 1 } 
  --1.3.6.1.4.1.3052.1.12.3.1 
 
autodeleteEnable OBJECT-TYPE 
  SYNTAX INTEGER
  ACCESS read-write 
  STATUS mandatory 
  DESCRIPTION 
    "1/2 off/on autodelete for CBB and Xmodem"
  ::= { dataRelease 2 } 
  --1.3.6.1.4.1.3052.1.12.3.2 
 
releaseCompressed OBJECT-TYPE 
  SYNTAX INTEGER
  ACCESS read-write 
  STATUS mandatory 
  DESCRIPTION 
    "1-compressed 2-decompressed"
  ::= { dataRelease 3 } 
  --1.3.6.1.4.1.3052.1.12.3.3 
 
waitMode OBJECT-TYPE 
  SYNTAX INTEGER
  ACCESS read-write 
  STATUS mandatory 
  DESCRIPTION 
    "1/2 off/on wait for 02 after 01 on rlmodes"
  ::= { otherControls 1 } 
  --1.3.6.1.4.1.3052.1.12.4.1 
 
tagMode OBJECT-TYPE 
  SYNTAX INTEGER
  ACCESS read-write 
  STATUS mandatory 
  DESCRIPTION 
    "1/2 off/on  Line/Block tag enabled"
  ::= { otherControls 2 } 
  --1.3.6.1.4.1.3052.1.12.4.2 
 
crcMode OBJECT-TYPE 
  SYNTAX INTEGER
  ACCESS read-write 
  STATUS mandatory 
  DESCRIPTION 
    "1/2 off/on add CRC to ascii releases"
  ::= { otherControls 3 } 
  --1.3.6.1.4.1.3052.1.12.4.3 
 
dleMode OBJECT-TYPE 
  SYNTAX INTEGER
  ACCESS read-write 
  STATUS mandatory 
  DESCRIPTION 
    "1/2 off/on use DLE stuffing on CBB"
  ::= { otherControls 4 } 
  --1.3.6.1.4.1.3052.1.12.4.4 
 
cbbRetransmits OBJECT-TYPE 
  SYNTAX INTEGER
  ACCESS read-write 
  STATUS mandatory 
  DESCRIPTION 
    "# times a block retransmitted in CBB mode"
  ::= { otherControls 5 } 
  --1.3.6.1.4.1.3052.1.12.4.5 
 
cbbTimeout OBJECT-TYPE 
  SYNTAX INTEGER
  ACCESS read-write 
  STATUS mandatory 
  DESCRIPTION 
    "# seconds to wait for an ack before retransmit in CBB mode"
  ::= { otherControls 6 } 
  --1.3.6.1.4.1.3052.1.12.4.6 
 
activeDatabase OBJECT-TYPE 
  SYNTAX INTEGER
  ACCESS read-write 
  STATUS mandatory 
  DESCRIPTION 
    "selects a file. ports 2001-2006 auto select this variable"
  ::= { controls 5 } 
  --1.3.6.1.4.1.3052.1.12.5 

actionCount OBJECT-TYPE
  SYNTAX INTEGER
  ACCESS read-only
  STATUS mandatory
  DESCRIPTION
    "number of active items in action table, 0-nn"
  ::= { actionQueue 1 }
  --1.3.6.1.4.1.3052.1.13.1.1

actionTable OBJECT-TYPE 
  SYNTAX SEQUENCE OF ActionTable
  ACCESS not-accessible 
  STATUS mandatory 
  DESCRIPTION 
    "action queue table"
  ::= { actionQueue 2 }
  --1.3.6.1.4.1.3052.1.13.1.2
 
actionTableEntry OBJECT-TYPE 
  SYNTAX ActionTable
  ACCESS not-accessible 
  STATUS mandatory 
  DESCRIPTION 
    "action queue entry"
  INDEX { actionTableIndex } 
  ::= { actionTable 1 }
  --1.3.6.1.4.1.3052.1.13.1.2.1
 
actionTableIndex OBJECT-TYPE 
  SYNTAX INTEGER
  ACCESS read-only 
  STATUS mandatory 
  DESCRIPTION 
    "action table entry"
  ::= { actionTableEntry 1 } 
  --1.3.6.1.4.1.3052.1.13.1.2.1.1
 
actionAcked OBJECT-TYPE 
  SYNTAX INTEGER
  ACCESS read-write 
  STATUS mandatory 
  DESCRIPTION 
    "reads 0, any set removes (acks) this action"
  ::= { actionTableEntry 2 } 
  --1.3.6.1.4.1.3052.1.13.1.2.1.2
 
actionReason OBJECT-TYPE 
  SYNTAX INTEGER
  ACCESS read-only 
  STATUS mandatory 
  DESCRIPTION 
    "code reason for action"
  ::= { actionTableEntry 3 } 
  --1.3.6.1.4.1.3052.1.13.1.2.1.3
 
actionReasonID OBJECT-TYPE 
  SYNTAX INTEGER
  ACCESS read-only 
  STATUS mandatory 
  DESCRIPTION 
    "which of the (reasons) e.g, alarm 3 vs. alarm 4"
  ::= { actionTableEntry 4 } 
  --1.3.6.1.4.1.3052.1.13.1.2.1.4
 
actionReasonLevel OBJECT-TYPE 
  SYNTAX INTEGER
  ACCESS read-only 
  STATUS mandatory 
  DESCRIPTION 
    "which of the levels for alarms which have 1-3 levels"
  ::= { actionTableEntry 5 } 
  --1.3.6.1.4.1.3052.1.13.1.2.1.5
 
actionType OBJECT-TYPE 
  SYNTAX INTEGER
  ACCESS read-only 
  STATUS mandatory 
  DESCRIPTION 
    "type of action being taken (page, callout, etc.)"
  ::= { actionTableEntry 6 } 
  --1.3.6.1.4.1.3052.1.13.1.2.1.6
 
actionTypeID OBJECT-TYPE 
  SYNTAX INTEGER
  ACCESS read-only 
  STATUS mandatory 
  DESCRIPTION 
    "which of the actions e.g, pager 3 vs. pager 4"
  ::= { actionTableEntry 7 } 
  --1.3.6.1.4.1.3052.1.13.1.2.1.7
 
actionRepeatTime OBJECT-TYPE 
  SYNTAX INTEGER
  ACCESS read-only 
  STATUS mandatory 
  DESCRIPTION 
    "#minutes between repeats of attempts of this action"
  ::= { actionTableEntry 8 } 
  --1.3.6.1.4.1.3052.1.13.1.2.1.8
 
actionAttempts OBJECT-TYPE 
  SYNTAX INTEGER
  ACCESS read-only 
  STATUS mandatory 
  DESCRIPTION 
    "# of attempts to try this action so far"
  ::= { actionTableEntry 9 } 
  --1.3.6.1.4.1.3052.1.13.1.2.1.9
 
actionNextAttempt OBJECT-TYPE 
  SYNTAX INTEGER
  ACCESS read-only 
  STATUS mandatory 
  DESCRIPTION 
    "# minutes until the next attempt of this action"
  ::= { actionTableEntry 10 } 
  --1.3.6.1.4.1.3052.1.13.1.2.1.10
 
actionTimeStamp OBJECT-TYPE 
  SYNTAX DisplayString
  ACCESS read-only 
  STATUS mandatory 
  DESCRIPTION 
    "date and time string: 02/34 12:34, or text message if no items"
  ::= { actionTableEntry 11 } 
  --1.3.6.1.4.1.3052.1.13.1.2.1.11

historyCount OBJECT-TYPE
  SYNTAX INTEGER
  ACCESS read-only
  STATUS mandatory
  DESCRIPTION
    "number of history items in history table, 0-nn"
  ::= { actionHistory 1 }
  --1.3.6.1.4.1.3052.1.13.2.1


historyTable OBJECT-TYPE 
  SYNTAX SEQUENCE OF HistoryTable
  ACCESS not-accessible 
  STATUS mandatory 
  DESCRIPTION 
    "action history table"
  ::= { actionHistory 2 }
  --1.3.6.1.4.1.3052.1.13.2.2
 
historyTableEntry OBJECT-TYPE 
  SYNTAX HistoryTable
  ACCESS not-accessible 
  STATUS mandatory 
  DESCRIPTION 
    "history queue entry"
  INDEX { historyTableIndex } 
  ::= { historyTable 1 } 
  --1.3.6.1.4.1.3052.1.13.2.2.1
 
historyTableIndex OBJECT-TYPE 
  SYNTAX INTEGER
  ACCESS read-only 
  STATUS mandatory 
  DESCRIPTION 
    "history table entry"
  ::= { historyTableEntry 1 } 
  --1.3.6.1.4.1.3052.1.13.2.2.1.1
 
historyEntryType OBJECT-TYPE 
  SYNTAX INTEGER
  ACCESS read-write 
  STATUS mandatory 
  DESCRIPTION 
    "type of entry (e.g., modem fail, pager pass, etc.)"
  ::= { historyTableEntry 2 } 
  --1.3.6.1.4.1.3052.1.13.2.2.1.2
 
historyReason OBJECT-TYPE 
  SYNTAX INTEGER
  ACCESS read-only 
  STATUS mandatory 
  DESCRIPTION 
    "code reason for history"
  ::= { historyTableEntry 3 } 
  --1.3.6.1.4.1.3052.1.13.2.2.1.3
 
historyReasonID OBJECT-TYPE 
  SYNTAX INTEGER
  ACCESS read-only 
  STATUS mandatory 
  DESCRIPTION 
    "which of the (reasons) e.g, alarm 3 vs. alarm 4"
  ::= { historyTableEntry 4 } 
  --1.3.6.1.4.1.3052.1.13.2.2.1.4
 
historyReasonLevel OBJECT-TYPE 
  SYNTAX INTEGER
  ACCESS read-only 
  STATUS mandatory 
  DESCRIPTION 
    "which of the levels for alarms which have 1-3 levels"
  ::= { historyTableEntry 5 } 
  --1.3.6.1.4.1.3052.1.13.2.2.1.5
 
historyType OBJECT-TYPE 
  SYNTAX INTEGER
  ACCESS read-only 
  STATUS mandatory 
  DESCRIPTION 
    "type of history being taken (page, callout, etc.)"
  ::= { historyTableEntry 6 } 
  --1.3.6.1.4.1.3052.1.13.2.2.1.6
 
historyTypeID OBJECT-TYPE 
  SYNTAX INTEGER
  ACCESS read-only 
  STATUS mandatory 
  DESCRIPTION 
    "which of the historys e.g, pager 3 vs. pager 4"
  ::= { historyTableEntry 7 } 
  --1.3.6.1.4.1.3052.1.13.2.2.1.7
 
historyTimeStamp OBJECT-TYPE 
  SYNTAX DisplayString
  ACCESS read-only 
  STATUS mandatory 
  DESCRIPTION 
    "date and time string: 02/34 12:34, or text message if no items"
  ::= { historyTableEntry 8 } 
  --1.3.6.1.4.1.3052.1.13.2.2.1.8
 
historyClearLog OBJECT-TYPE 
  SYNTAX INTEGER
  ACCESS read-write 
  STATUS mandatory 
  DESCRIPTION 
    "reads 0,   any set clears all history log items"
  ::= { historyTableEntry 9 } 
  --1.3.6.1.4.1.3052.1.13.2.2.1.9

lastCalloutPageReason OBJECT-TYPE
    SYNTAX DisplayString
    ACCESS read-only
    STATUS mandatory
    DESCRIPTION
      "the reason string for the last callout or page, or NONE if never used"
    ::= { alarmhistory 3 }
   --1.3.6.1.4.1.3052.1.13.3

rtsShowAnswer OBJECT-TYPE
    SYNTAX INTEGER
    ACCESS read-write
    STATUS deprecated
    DESCRIPTION
      "0-no 1-yes, show answer string on connection (deprecated)"
    ::= { realtimesocket 1 }
    --1.3.6.1.4.1.3052.1.14.1

rtsNeedPassword OBJECT-TYPE
    SYNTAX INTEGER
    ACCESS read-only
    STATUS deprecated
    DESCRIPTION
      "0-no 1-yes, need password on RTS connection (deprecated)"
    ::= { realtimesocket 2 }
    --1.3.6.1.4.1.3052.1.14.2

rtsWaitXon OBJECT-TYPE
    SYNTAX INTEGER
    ACCESS read-write
    STATUS deprecated
    DESCRIPTION
      "0-no 1-yes, wait for Xon after connection before sending data (deprecated)"
    ::= { realtimesocket 3 }
    --1.3.6.1.4.1.3052.1.14.3

rtsIdleTimeout OBJECT-TYPE
    SYNTAX INTEGER
    ACCESS read-write
    STATUS deprecated
    DESCRIPTION
      "0-255, 0-none, 1-255 #idle minutes no data = shutdown socket (deprecated)"
    ::= { realtimesocket 4 }
    --1.3.6.1.4.1.3052.1.14.4

rtsEmptyClose OBJECT-TYPE
    SYNTAX INTEGER
    ACCESS read-write
    STATUS deprecated
    DESCRIPTION
      "0->no, 1-> yes, when file empty close socket (polling, not rt data) (deprecated)"
    ::= { realtimesocket 5 }
    --1.3.6.1.4.1.3052.1.14.5

-- rts table
-- revised in mib version 1.07 to configure all rts options on a per-port basis

rtsTable OBJECT-TYPE
  SYNTAX SEQUENCE OF RtsTable
  ACCESS not-accessible 
  STATUS mandatory 
  DESCRIPTION 
    "real time socket table"
  ::= { realtimesocket 6 }
  --1.3.6.1.4.1.3052.1.14.6
 
rtsTableEntry OBJECT-TYPE
  SYNTAX RtsTable
  ACCESS not-accessible 
  STATUS mandatory 
  DESCRIPTION 
    "rts table entry"
  INDEX { rtsTableIndex }
  ::= { rtsTable 1 }
  --1.3.6.1.4.1.3052.1.14.6.1
 
rtsTableIndex OBJECT-TYPE
  SYNTAX INTEGER
  ACCESS read-only 
  STATUS mandatory 
  DESCRIPTION 
    "rts table entry index"
  ::= { rtsTableEntry 1 }
  --1.3.6.1.4.1.3052.1.14.6.1.1

rtsNoStore OBJECT-TYPE
  SYNTAX INTEGER
  ACCESS read-write 
  STATUS mandatory 
  DESCRIPTION 
    "0-allow storage, 1-don't store data when RTS socket not connected"
  ::= { rtsTableEntry 2 }
  --1.3.6.1.4.1.3052.1.14.6.1.2

rtsDenied OBJECT-TYPE
  SYNTAX INTEGER
  ACCESS read-write 
  STATUS mandatory 
  DESCRIPTION 
    "0-don't allow, 1=yes allow this rts socket to connect"
  ::= { rtsTableEntry 3 }
  --1.3.6.1.4.1.3052.1.14.6.1.3

rtsSocketState OBJECT-TYPE
  SYNTAX INTEGER
  ACCESS read-only
  STATUS mandatory 
  DESCRIPTION 
    "0-closed, 1-wait for pass, 2-wait for xon, 3=open for data"
  ::= { rtsTableEntry 4 }
  --1.3.6.1.4.1.3052.1.14.6.1.4

rtsPortShowAnswer OBJECT-TYPE
    SYNTAX INTEGER
    ACCESS read-write
    STATUS mandatory
    DESCRIPTION
      "0-no 1-yes, show answer string on connection"
  ::= { rtsTableEntry 5 }
  --1.3.6.1.4.1.3052.1.14.6.1.5

rtsPortNeedPassword OBJECT-TYPE
    SYNTAX INTEGER
    ACCESS read-only
    STATUS mandatory
    DESCRIPTION
      "0-no 1-yes, need password on RTS connection"
  ::= { rtsTableEntry 6 }
  --1.3.6.1.4.1.3052.1.14.6.1.6

rtsPortWaitXon OBJECT-TYPE
    SYNTAX INTEGER
    ACCESS read-write
    STATUS mandatory
    DESCRIPTION
      "0-no 1-yes, wait for Xon after connection before sending data"
  ::= { rtsTableEntry 7 }
  --1.3.6.1.4.1.3052.1.14.6.1.7

rtsPortIdleTimeout OBJECT-TYPE
    SYNTAX INTEGER
    ACCESS read-write
    STATUS mandatory
    DESCRIPTION
      "0-255, 0-none, 1-255 #idle minutes no data = shutdown socket"
  ::= { rtsTableEntry 8 }
  --1.3.6.1.4.1.3052.1.14.6.1.8

rtsPortEmptyClose OBJECT-TYPE
    SYNTAX INTEGER
    ACCESS read-write
    STATUS mandatory
    DESCRIPTION
      "0->no, 1-> yes, when file empty close socket (polling, not rt data)"
  ::= { rtsTableEntry 9 }
  --1.3.6.1.4.1.3052.1.14.6.1.9

iprestrictTable OBJECT-TYPE
  SYNTAX SEQUENCE OF IpRestrictTable
  ACCESS not-accessible 
  STATUS mandatory 
  DESCRIPTION 
    "ip restrictions table"
  ::= { iprestrictions 1 }
  --1.3.6.1.4.1.3052.1.15.1
 
iprestrictTableEntry OBJECT-TYPE
  SYNTAX IpRestrictTable
  ACCESS not-accessible 
  STATUS mandatory 
  DESCRIPTION 
    "ip restriction table entry"
  INDEX { iprestrictTableIndex }
  ::= { iprestrictTable 1 }
  --1.3.6.1.4.1.3052.1.15.1.1
 
iprestrictTableIndex OBJECT-TYPE
  SYNTAX INTEGER
  ACCESS read-only 
  STATUS mandatory 
  DESCRIPTION 
    "ip restrict table entry index"
  ::= { iprestrictTableEntry 1 }
  --1.3.6.1.4.1.3052.1.15.1.1.1

iprestrictIpAddress OBJECT-TYPE
  SYNTAX IpAddress
  ACCESS read-only
  STATUS mandatory 
  DESCRIPTION 
    "an ip address which forces a restriction or allowance for an ip range"
  ::= { iprestrictTableEntry 2 }
  --1.3.6.1.4.1.3052.1.15.1.1.2

suspendIPRestrictions OBJECT-TYPE
    SYNTAX INTEGER
    ACCESS read-write
    STATUS mandatory
    DESCRIPTION
    "read returns 0, writing requires the private community name.
     default is 0
     set to 1 to suspend IP restrictions while loading the list
     set back to 0 to allow the restrictions to be used."
  ::= { iprestrictions 2 }
  --1.3.6.1.4.1.3052.1.15.2


killIPRestrictions OBJECT-TYPE
    SYNTAX INTEGER
    ACCESS read-write
    STATUS mandatory
    DESCRIPTION
    "read returns 0, writing requires the private community name.
     any set removes all entries from the IP restrcition list."
  ::= { iprestrictions 3 }
  --1.3.6.1.4.1.3052.1.15.3

addIPRestrictions OBJECT-TYPE
    SYNTAX IpAddress
    ACCESS read-write
    STATUS mandatory
    DESCRIPTION
    "read returns 0, writing requires the private community name.
     any set adds an entry to the IP restriction list
     note that list is no re-sorted, so must add in order"
  ::= { iprestrictions 4 }
  --1.3.6.1.4.1.3052.1.15.4

ipCurrentStatic OBJECT-TYPE
    SYNTAX INTEGER
    ACCESS read-only
    STATUS mandatory
    DESCRIPTION
    "1=static, 0=dynamic"
  ::= { ipCurrent 1 }
  --1.3.6.1.4.1.3052.1.16.1.1

ipCurrentAddress OBJECT-TYPE
    SYNTAX IpAddress
    ACCESS read-only
    STATUS mandatory
    DESCRIPTION
    "current IP address"
  ::= { ipCurrent 2 }
  --1.3.6.1.4.1.3052.1.16.1.2

ipCurrentSubnetMask OBJECT-TYPE
    SYNTAX IpAddress
    ACCESS read-only
    STATUS mandatory
    DESCRIPTION
    "current subnet mask"
  ::= { ipCurrent 3 }
  --1.3.6.1.4.1.3052.1.16.1.3

ipCurrentDefaultRouter OBJECT-TYPE
    SYNTAX IpAddress
    ACCESS read-only
    STATUS mandatory
    DESCRIPTION
    "current default router"
  ::= { ipCurrent 4 }
  --1.3.6.1.4.1.3052.1.16.1.4

ipNewStatic OBJECT-TYPE
    SYNTAX INTEGER
    ACCESS read-write
    STATUS mandatory
    DESCRIPTION
    "1=static, 0=dynamic.  write requires private community name."
  ::= { ipNew 1 }
  --1.3.6.1.4.1.3052.1.16.2.1


ipNewAddress OBJECT-TYPE
    SYNTAX IpAddress
    ACCESS read-write
    STATUS mandatory
    DESCRIPTION
    "read=current new address, write requires private community name."
  ::= { ipNew 2 }
  --1.3.6.1.4.1.3052.1.16.2.2

ipNewSubnetMask OBJECT-TYPE
    SYNTAX IpAddress
    ACCESS read-write
    STATUS mandatory
    DESCRIPTION
    "read=current new subnet mask, write requires private community name."
  ::= { ipNew 3 }
  --1.3.6.1.4.1.3052.1.16.2.3

ipNewDefaultRouter OBJECT-TYPE
    SYNTAX IpAddress
    ACCESS read-write
    STATUS mandatory
    DESCRIPTION
    "read=current new default router, write requires private community name."
  ::= { ipNew 4 }
  --1.3.6.1.4.1.3052.1.16.2.4

ipNewSetup OBJECT-TYPE
    SYNTAX INTEGER
    ACCESS read-write
    STATUS mandatory
    DESCRIPTION
    "read=0.
     write requires private community name.
     any write causes the current object values for ipNewStatic,
     ipNewAddress, ipNewSubnetMask and ipNewDefaultRouter to be used.
     Causes the unit to re-initialize its network stacks
     with these new values.  Changes to ipNewStatic, ipNewAddress,
     ipNewSubnetMask and ipNewDefaultRouter
     do not affect the network stack until ipNewSetup is written with
     some value:"
  ::= { ipNew 5 }
  --1.3.6.1.4.1.3052.1.16.2.5


-- ppp setup

pppIDString OBJECT-TYPE
  SYNTAX DisplayString
  ACCESS read-write
  STATUS mandatory
  DESCRIPTION
    "sent in ppp up trap to provide host identification string"
  ::= { pppIdentification 1 }
  --1.3.6.1.4.1.3052.1.17.1.1

pppIPAddress OBJECT-TYPE
  SYNTAX IpAddress
  ACCESS read-only
  STATUS mandatory
  DESCRIPTION
    "sent in ppp up trap to provide host identification by IP address"
  ::= { pppIdentification 2 }
  --1.3.6.1.4.1.3052.1.17.1.2

-- ccode support

ccodeLoaded OBJECT-TYPE
  SYNTAX INTEGER
  ACCESS read-only
  STATUS mandatory
  DESCRIPTION
    "0/1, no/yes, is ccode loaded"
  ::= { ccode 1 }
  --1.3.6.1.4.1.3052.1.18.1

ccodeRunning OBJECT-TYPE
  SYNTAX INTEGER
  ACCESS read-only
  STATUS mandatory
  DESCRIPTION
    "0/1, no/yes, is ccode running"
  ::= { ccode 2 }
  --1.3.6.1.4.1.3052.1.18.2

ccodeStackMainWas OBJECT-TYPE
  SYNTAX INTEGER
  ACCESS read-only
  STATUS mandatory
  DESCRIPTION
    "# of bytes of stack used by main app, last time run"
  ::= { ccode 3 }
  --1.3.6.1.4.1.3052.1.18.3

ccodeStackMainNow OBJECT-TYPE
  SYNTAX INTEGER
  ACCESS read-only
  STATUS mandatory
  DESCRIPTION
    "# of bytes of stack used by main app, this time run"
  ::= { ccode 4 }
  --1.3.6.1.4.1.3052.1.18.4

ccodeStackT2Was OBJECT-TYPE
  SYNTAX INTEGER
  ACCESS read-only
  STATUS mandatory
  DESCRIPTION
    "# of bytes of stack used by 2nd task of app, last time run"
  ::= { ccode 5 }
  --1.3.6.1.4.1.3052.1.18.5

ccodeStackT2Was2 OBJECT-TYPE
  SYNTAX INTEGER
  ACCESS read-only
  STATUS mandatory
  DESCRIPTION
    "# of bytes of stack used by 2nd task of app, this time run"
  ::= { ccode 6 }
  --1.3.6.1.4.1.3052.1.18.6



-- tech support variables, for technical support use only
techsupportInt1 OBJECT-TYPE
    SYNTAX INTEGER
    ACCESS read-write
    STATUS mandatory
    DESCRIPTION
    "a debugging integer for technical support use only.  Do not use"
    ::= { techsupport 1 }
  --1.3.6.1.4.1.3052.1.99.1

techsupportInt2 OBJECT-TYPE
    SYNTAX INTEGER
    ACCESS read-write
    STATUS mandatory
    DESCRIPTION
    "a debugging integer for technical support use only.  Do not use"
    ::= { techsupport 2 }
  --1.3.6.1.4.1.3052.1.99.2

techsupportInt3 OBJECT-TYPE
    SYNTAX INTEGER
    ACCESS read-write
    STATUS mandatory
    DESCRIPTION
    "a debugging integer for technical support use only.  Do not use"
    ::= { techsupport 3 }
  --1.3.6.1.4.1.3052.1.99.3

techsupportInt4 OBJECT-TYPE
    SYNTAX INTEGER
    ACCESS read-write
    STATUS mandatory
    DESCRIPTION
    "a debugging integer for technical support use only.  Do not use"
    ::= { techsupport 4 }
  --1.3.6.1.4.1.3052.1.99.4

techsupportInt5 OBJECT-TYPE
    SYNTAX INTEGER
    ACCESS read-write
    STATUS mandatory
    DESCRIPTION
    "a debugging integer for technical support use only.  Do not use"
    ::= { techsupport 5 }
  --1.3.6.1.4.1.3052.1.99.5


-- TRAP DEFINITIONS


datalinkDbasePfullTrap   TRAP-TYPE
  ENTERPRISE asentria
  VARIABLES { databaseAlarmIndex, databasePfull }
  DESCRIPTION 
                "The datalinkDbasePfullTrap is issued when
                 the database reaches a pre-determined
                 threshold level, which
                 causes a trap."
  ::= 501

datalinkFilePfullTrap   TRAP-TYPE
  ENTERPRISE asentria
  VARIABLES { fileAlarmFileIndex, fileAlarmThresholdIndex, filePercentNow }
  DESCRIPTION 
                "The datalinkFilePfullTrap is issued when
                 one of the data files reaches a pre-determined
                 threshold level, which
                 causes a trap."
  ::= 502

datalinkDataAlarmTrap   TRAP-TYPE
  ENTERPRISE asentria
  VARIABLES { dataAlarmIndex, dataAlarmName, dataAlarmString, dataAlarmPort }
  DESCRIPTION 
                "The datalinkDataAlarmTrap is issued when
                 one of the data alarms reaches a pre-determined
                 threshold level, which
                 causes a trap."
  ::= 503

datalinkSensorAlarmTrap   TRAP-TYPE
  ENTERPRISE asentria
  VARIABLES { sensorAlarmIndex, sensorAlarmName, sensorAlarmState }
  DESCRIPTION 
                "The datalinkSensorAlarmTrap is issued when
                 one of the External Sensors is triggered for a
                 pre-determined threshold amount of time, which
                 causes a trap."
  ::= 504

datalinkNoDataAlarmTrap   TRAP-TYPE
  ENTERPRISE asentria
  VARIABLES { nodataTablePortIndex, nodataTableScheduleIndex,
              nodataTableLevelIndex, nodataAlarmStatusCounter,
              nodataTableThreshold  }
  DESCRIPTION 
                "The datalinkNoDataAlarmTrap is issued when
                 one of the ports receives no input data for a
                 pre-determined threshold amount of time, which
                 causes a trap."
  ::= 505


datalinkSchedTrap   TRAP-TYPE
  ENTERPRISE asentria
  VARIABLES { scheduleIndex } 
  DESCRIPTION 
                "The datalinkSchedTrap is issued when a scheduled event
                 causes a trap."
  ::= 506

datalinkImmediateTrap   TRAP-TYPE
  ENTERPRISE asentria
  DESCRIPTION 
                "The datalinkImmediateTrap is issued when the dotrap command
                 is used to issue a test trap to all snmp managers"
  ::= 507

datalinkPPPupTrap  TRAP-TYPE
  ENTERPRISE asentria
  VARIABLES { pppIDString, pppIPAddress }
  DESCRIPTION 
                "The datalinkPPPupTrap is issued when the PPP interface is
                 brought up and the ppp connection has been established"
  ::= 509




  SiteByPort ::= 
   SEQUENCE { 
      siteindex
          INTEGER,
      siteID
          DisplayString
 } 


  PortSetup ::= 
   SEQUENCE { 
      portIndex
          INTEGER,
      portBaud
          INTEGER,
      portWord
          INTEGER,
      portParity
          DisplayString,
      portStopbits
          INTEGER,
      portDataStore
          INTEGER,
      portBinaryMode
          INTEGER,
      portWrapMode
          INTEGER,
      portHskMode
          INTEGER,
      portDateTimeStampMode
          INTEGER,
      portPTMode
          INTEGER,
      portPTTime
          INTEGER,
      portStoreFile
          INTEGER,
      portPtStripOutputLfs
          INTEGER,
      portPtStripInputLfs
          INTEGER,
      portlowDTR
          INTEGER
 } 


  SnmpManager ::= 
   SEQUENCE { 
      snmpMgrIndex
          INTEGER,
      snmpManagerIp
          IpAddress,
      snmpManagerName
          DisplayString
 } 



  FtpPushTable ::=
  SEQUENCE {
       ftppushIndex
            INTEGER,
       ftppushEnable
            INTEGER
}

  DatabaseAlarm ::= 
   SEQUENCE { 
      databaseAlarmIndex
          INTEGER,
      databaseAlarmActive
          INTEGER,
      databaseAlarmThreshold
          INTEGER,
      databaseAlarmBeeperActions
          INTEGER,
      databaseAlarmSerialActions
          INTEGER,
      databaseAlarmPagerActions
          INTEGER,
      databaseAlarmCalloutActions
          INTEGER,
      databaseAlarmTrapActions
          INTEGER
 } 


  FileTable ::= 
   SEQUENCE { 
      fileTableIndex
          INTEGER,
      fileName
          DisplayString,
      fileType
          DisplayString,
      fileSize
          INTEGER,
      fileRecords
          INTEGER,
      fileRecordsAvailable
          INTEGER,
      fileRecordsDeleted
          INTEGER,
      filePercentNow
          INTEGER
 } 


  FileAlarm ::= 
   SEQUENCE { 
      fileAlarmFileIndex
          INTEGER,
      fileAlarmThresholdIndex
          INTEGER,
      fileAlarmActive
          INTEGER,
      fileAlarmThreshold
          INTEGER,
      fileAlarmBeeperActions
          INTEGER,
      fileAlarmSerialActions
          INTEGER,
      fileAlarmPagerActions
          INTEGER,
      fileAlarmCalloutActions
          INTEGER,
      fileAlarmTrapActions
          INTEGER
 } 


  DataAlarm ::= 
   SEQUENCE { 
      dataAlarmIndex
          INTEGER,
      dataAlarmActive
          INTEGER,
      dataAlarmName
          DisplayString,
      dataAlarmCounter
          INTEGER,
      dataAlarmThreshold
          INTEGER,
      dataAlarmClearMode
          INTEGER,
      dataAlarmClearTime
          DisplayString,
      dataAlarmAcked
          INTEGER,
      dataAlarmBeeperActions
          INTEGER,
      dataAlarmSerialActions
          INTEGER,
      dataAlarmPagerActions
          INTEGER,
      dataAlarmCalloutActions
          INTEGER,
      dataAlarmTrapActions
          INTEGER,
      dataAlarmString
          DisplayString,
      dataAlarmAutoClear
          INTEGER
 } 


  SensorAlarm ::= 
   SEQUENCE { 
      sensorAlarmIndex
          INTEGER,
      sensorAlarmActive
          INTEGER,
      sensorAlarmName
          DisplayString,
      sensorAlarmMode
          INTEGER,
      sensorAlarmCounter
          INTEGER,
      sensorAlarmThreshold
          INTEGER,
      sensorAlarmAcked
          INTEGER,
      sensorAlarmBeeperActions
          INTEGER,
      sensorAlarmSerialActions
          INTEGER,
      sensorAlarmPagerActions
          INTEGER,
      sensorAlarmCalloutActions
          INTEGER,
      sensorAlarmTrapActions
          INTEGER,
      sensorAlarmState
          INTEGER
 } 


  NodataAlarmStatus ::= 
   SEQUENCE { 
      nodataAlarmStatusIndex
          INTEGER,
      nodataAlarmStatusCounter
          INTEGER,
      nodataAlarmStatusAcked
          INTEGER
 } 


  NodataTable ::= 
   SEQUENCE { 
      nodataTablePortIndex
          INTEGER,
      nodataTableScheduleIndex
          INTEGER,
      nodataTableLevelIndex
          INTEGER,
      nodataTableActive
          INTEGER,
      nodataTableSchedule
          DisplayString,
      nodataTableThreshold
          INTEGER,
      nodataTableBeeperActions
          INTEGER,
      nodataTableSerialActions
          INTEGER,
      nodataTablePagerActions
          INTEGER,
      nodataTableCalloutActions
          INTEGER,
      nodataTableTrapActions
          INTEGER
 } 


  NodataHoliday ::= 
   SEQUENCE { 
      nodataHolidayIndex
          INTEGER,
      nodataHolidayItem
          DisplayString
 } 


  ScheduleAlarm ::= 
   SEQUENCE { 
      scheduleIndex
          INTEGER,
      scheduleActive
          INTEGER,
      scheduleTime
          DisplayString,
      scheduleAcked
          INTEGER,
      scheduleBeeperActions
          INTEGER,
      scheduleSerialActions
          INTEGER,
      schedulePagerActions
          INTEGER,
      scheduleCalloutActions
          INTEGER,
      scheduleTrapActions
          INTEGER
 } 


  SerialTable ::= 
   SEQUENCE { 
      serialTableIndex
          INTEGER,
      serialTableMessage
          DisplayString
 } 


  PagerTable ::= 
   SEQUENCE { 
      pagerTableIndex
          INTEGER,
      pagerType
          INTEGER,
      pagerPhonenumber
          DisplayString,
      pagerID
          DisplayString,
      pagerDialDelay
          INTEGER,
      pagerHangupDelay
          INTEGER,
      pagerMessage
          DisplayString,
      pagerSendId
          INTEGER,
      pagerSendReason
          INTEGER,
      pagerMaxAttempts
          INTEGER,
      pagerAttempts
          INTEGER,
      pagerAttemptDelay
          INTEGER,
      pagerRepeat
          INTEGER,
      pagerRepeatDelay
          INTEGER
 } 


  CalloutTable ::= 
   SEQUENCE { 
      calloutTableIndex
          INTEGER,
      calloutPhonenumber
          DisplayString,
      calloutMaxConnecttime
          INTEGER,
      calloutMessage
          DisplayString,
      calloutSendId
          INTEGER,
      calloutSendReason
          INTEGER,
      calloutCommandWait
          INTEGER,
      calloutMaxAttempts
          INTEGER,
      calloutAttempts
          INTEGER,
      calloutAttemptDelay
          INTEGER,
      calloutRepeat
          INTEGER,
      calloutRepeatDelay
          INTEGER
 } 


  ActionTable ::= 
   SEQUENCE { 
      actionTableIndex
          INTEGER,
      actionAcked
          INTEGER,
      actionReason
          INTEGER,
      actionReasonID
          INTEGER,
      actionReasonLevel
          INTEGER,
      actionType
          INTEGER,
      actionTypeID
          INTEGER,
      actionRepeatTime
          INTEGER,
      actionAttempts
          INTEGER,
      actionNextAttempt
          INTEGER,
      actionTimeStamp
          DisplayString
 } 


  HistoryTable ::= 
   SEQUENCE { 
      historyTableIndex
          INTEGER,
      historyEntryType
          INTEGER,
      historyReason
          INTEGER,
      historyReasonID
          INTEGER,
      historyReasonLevel
          INTEGER,
      historyType
          INTEGER,
      historyTypeID
          INTEGER,
      historyTimeStamp
          DisplayString,
      historyClearLog
          INTEGER
 } 

    RtsTable ::=
    SEQUENCE {
      rtsTableIndex
        INTEGER,
      rtsNoStore
        INTEGER,
      rtsDenied
        INTEGER,
      rtsSocketState
        INTEGER,
     rtsPortShowAnswer
        INTEGER,
     rtsPortNeedPassword
        INTEGER,
     rtsPortWaitXon
        INTEGER,
     rtsPortIdleTimeout
        INTEGER,
     rtsPortEmptyClose
        INTEGER
 }

    IpRestrictTable ::=
    SEQUENCE {
      iprestrictTableIndex
         INTEGER,
      iprestrictIpAddress
         IpAddress
}

END
