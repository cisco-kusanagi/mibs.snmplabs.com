--			Ascend mibstm1int MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSTM1INT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsTM1InterfaceProfile  OBJECT IDENTIFIER ::= { configuration 154}

	-- The mibsTM1InterfaceProfile table
	--
	-- This table contains parameters for the mibsTM1InterfaceProfile profile
	--

    mibsTM1InterfaceProfileTable	OBJECT-TYPE
	SYNTAX		SEQUENCE OF MibsTM1InterfaceProfileEntry
	ACCESS		not-accessible
	STATUS		mandatory
	DESCRIPTION	"A list of mibsTM1InterfaceProfile profile entries."
	::= { mibsTM1InterfaceProfile 1 }

    mibsTM1InterfaceProfileEntry	OBJECT-TYPE
	SYNTAX		MibsTM1InterfaceProfileEntry
	ACCESS		not-accessible
	STATUS		mandatory
	DESCRIPTION	"A mibsTM1InterfaceProfile entry containing objects that
			 maps to the parameters of mibsTM1InterfaceProfile profile."
	INDEX		{ sTM1InterfaceProfile-Shelf-o, sTM1InterfaceProfile-Slot-o, sTM1InterfaceProfile-Item-o }
	::= { mibsTM1InterfaceProfileTable 1 }

    MibsTM1InterfaceProfileEntry ::=
	SEQUENCE {
	    sTM1InterfaceProfile-Shelf-o
		INTEGER,
	    sTM1InterfaceProfile-Slot-o
		INTEGER,
	    sTM1InterfaceProfile-Item-o
		INTEGER,
	    sTM1InterfaceProfile-Name
		DisplayString,
	    sTM1InterfaceProfile-PhysicalAddress-Shelf
		INTEGER,
	    sTM1InterfaceProfile-PhysicalAddress-Slot
		INTEGER,
	    sTM1InterfaceProfile-PhysicalAddress-ItemNumber
		INTEGER,
	    sTM1InterfaceProfile-LimControl-PrimaryLpm
		INTEGER,
	    sTM1InterfaceProfile-LimControl-ActiveLine
		INTEGER,
	    sTM1InterfaceProfile-LineParams-Name
		DisplayString,
	    sTM1InterfaceProfile-LineParams-PhysicalAddress-Shelf
		INTEGER,
	    sTM1InterfaceProfile-LineParams-PhysicalAddress-Slot
		INTEGER,
	    sTM1InterfaceProfile-LineParams-PhysicalAddress-ItemNumber
		INTEGER,
	    sTM1InterfaceProfile-LineParams-Enabled
		INTEGER,
	    sTM1InterfaceProfile-LineParams-AuPointer
		INTEGER,
	    sTM1InterfaceProfile-LineParams-Signaling
		INTEGER,
	    sTM1InterfaceProfile-LineParams-LoopTiming
		INTEGER,
	    sTM1InterfaceProfile-LineParams-Loopback
		INTEGER,
	    sTM1InterfaceProfile-LineParams-ApsConfigName
		DisplayString,
	    sTM1InterfaceProfile-Action-o
		INTEGER
	}

    sTM1InterfaceProfile-Shelf-o	OBJECT-TYPE
	SYNTAX	INTEGER
	ACCESS	read-only
	STATUS	mandatory
	DESCRIPTION	""
	::= { mibsTM1InterfaceProfileEntry 1 }

    sTM1InterfaceProfile-Slot-o	OBJECT-TYPE
	SYNTAX	INTEGER
	ACCESS	read-only
	STATUS	mandatory
	DESCRIPTION	""
	::= { mibsTM1InterfaceProfileEntry 2 }

    sTM1InterfaceProfile-Item-o	OBJECT-TYPE
	SYNTAX	INTEGER
	ACCESS	read-only
	STATUS	mandatory
	DESCRIPTION	""
	::= { mibsTM1InterfaceProfileEntry 3 }

    sTM1InterfaceProfile-Name	OBJECT-TYPE
	SYNTAX	DisplayString
	ACCESS	read-write
	STATUS	mandatory
	DESCRIPTION	"Name of Channelized STM1 Interface profile"
	::= { mibsTM1InterfaceProfileEntry 4 }

    sTM1InterfaceProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibsTM1InterfaceProfileEntry 5 }

    sTM1InterfaceProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibsTM1InterfaceProfileEntry 6 }

    sTM1InterfaceProfile-PhysicalAddress-ItemNumber	OBJECT-TYPE
	SYNTAX	INTEGER
	ACCESS	read-write
	STATUS	mandatory
	DESCRIPTION	"A number that specifies an addressable entity within the context of shelf and slot."
	::= { mibsTM1InterfaceProfileEntry 7 }

    sTM1InterfaceProfile-LimControl-PrimaryLpm	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"Which LPM is the primary control for the interface"
	::= { mibsTM1InterfaceProfileEntry 8 }

    sTM1InterfaceProfile-LimControl-ActiveLine	OBJECT-TYPE
	SYNTAX	INTEGER {
		    workingLine (1),
		    protectionLine (2),
		    backupLine (3)
		}
	ACCESS	read-write
	STATUS	mandatory
	DESCRIPTION	"Administrative request for current active line or line interface"
	::= { mibsTM1InterfaceProfileEntry 9 }

    sTM1InterfaceProfile-LineParams-Name	OBJECT-TYPE
	SYNTAX	DisplayString
	ACCESS	read-write
	STATUS	mandatory
	DESCRIPTION	"Name of STM network line."
	::= { mibsTM1InterfaceProfileEntry 10 }

    sTM1InterfaceProfile-LineParams-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibsTM1InterfaceProfileEntry 11 }

    sTM1InterfaceProfile-LineParams-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibsTM1InterfaceProfileEntry 12 }

    sTM1InterfaceProfile-LineParams-PhysicalAddress-ItemNumber	OBJECT-TYPE
	SYNTAX	INTEGER
	ACCESS	read-write
	STATUS	mandatory
	DESCRIPTION	"A number that specifies an addressable entity within the context of shelf and slot."
	::= { mibsTM1InterfaceProfileEntry 13 }

    sTM1InterfaceProfile-LineParams-Enabled	OBJECT-TYPE
	SYNTAX	INTEGER {
		    no (1),
		    yes (2)
		}
	ACCESS	read-write
	STATUS	mandatory
	DESCRIPTION	"TRUE if the link is enabled, otherwise FALSE."
	::= { mibsTM1InterfaceProfileEntry 14 }

    sTM1InterfaceProfile-LineParams-AuPointer	OBJECT-TYPE
	SYNTAX	INTEGER {
		    au3Pointer (2),
		    au4Pointer (3)
		}
	ACCESS	read-write
	STATUS	mandatory
	DESCRIPTION	"The AU pointer used by this STM-1 link."
	::= { mibsTM1InterfaceProfileEntry 15 }

    sTM1InterfaceProfile-LineParams-Signaling	OBJECT-TYPE
	SYNTAX	INTEGER {
		    sonet (2),
		    sdh (3),
		    japan (4)
		}
	ACCESS	read-write
	STATUS	mandatory
	DESCRIPTION	"The STM signaling to use on this STM link."
	::= { mibsTM1InterfaceProfileEntry 20 }

    sTM1InterfaceProfile-LineParams-LoopTiming	OBJECT-TYPE
	SYNTAX	INTEGER {
		    no (1),
		    yes (2)
		}
	ACCESS	read-write
	STATUS	mandatory
	DESCRIPTION	"TRUE if the line is to use loop timing, otherwise FALSE."
	::= { mibsTM1InterfaceProfileEntry 16 }

    sTM1InterfaceProfile-LineParams-Loopback	OBJECT-TYPE
	SYNTAX	INTEGER {
		    noLoopback (1),
		    lineLoopback (2),
		    localLoopback (3)
		}
	ACCESS	read-write
	STATUS	mandatory
	DESCRIPTION	"Loopback mode"
	::= { mibsTM1InterfaceProfileEntry 17 }

    sTM1InterfaceProfile-LineParams-ApsConfigName	OBJECT-TYPE
	SYNTAX	DisplayString
	ACCESS	read-write
	STATUS	mandatory
	DESCRIPTION	"APS Config Profile name, specifies APS configuration profile that defines a protection group for this line."
	::= { mibsTM1InterfaceProfileEntry 19 }

    sTM1InterfaceProfile-Action-o	OBJECT-TYPE
	SYNTAX	INTEGER {
		    noAction (1),
		    createProfile (2),
		    deleteProfile (3)
		}
	ACCESS	read-write
	STATUS	mandatory
	DESCRIPTION	""
	::= { mibsTM1InterfaceProfileEntry 18 }


	-- The mibsTM1InterfaceProfile__path_params table
	--
	-- This table contains parameters for the mibsTM1InterfaceProfile__path_params profile
	--

    mibsTM1InterfaceProfile-PathParamsTable	OBJECT-TYPE
	SYNTAX		SEQUENCE OF MibsTM1InterfaceProfile-PathParamsEntry
	ACCESS		not-accessible
	STATUS		mandatory
	DESCRIPTION	"A list of mibsTM1InterfaceProfile__path_params profile entries."
	::= { mibsTM1InterfaceProfile 2 }

    mibsTM1InterfaceProfile-PathParamsEntry	OBJECT-TYPE
	SYNTAX		MibsTM1InterfaceProfile-PathParamsEntry
	ACCESS		not-accessible
	STATUS		mandatory
	DESCRIPTION	"A mibsTM1InterfaceProfile__path_params entry containing objects that
			 maps to the parameters of mibsTM1InterfaceProfile__path_params profile."
	INDEX		{ sTM1InterfaceProfile-PathParams-Shelf-o, sTM1InterfaceProfile-PathParams-Slot-o, sTM1InterfaceProfile-PathParams-Item-o, sTM1InterfaceProfile-PathParams-Index-o }
	::= { mibsTM1InterfaceProfile-PathParamsTable 1 }

    MibsTM1InterfaceProfile-PathParamsEntry ::=
	SEQUENCE {
	    sTM1InterfaceProfile-PathParams-Shelf-o
		INTEGER,
	    sTM1InterfaceProfile-PathParams-Slot-o
		INTEGER,
	    sTM1InterfaceProfile-PathParams-Item-o
		INTEGER,
	    sTM1InterfaceProfile-PathParams-Index-o
		INTEGER,
	    sTM1InterfaceProfile-PathParams-Name
		DisplayString,
	    sTM1InterfaceProfile-PathParams-Stm0Profile-Name
		DisplayString,
	    sTM1InterfaceProfile-PathParams-Stm0Profile-PhysicalAddress-Shelf
		INTEGER,
	    sTM1InterfaceProfile-PathParams-Stm0Profile-PhysicalAddress-Slot
		INTEGER,
	    sTM1InterfaceProfile-PathParams-Stm0Profile-PhysicalAddress-ItemNumber
		INTEGER,
	    sTM1InterfaceProfile-PathParams-Stm0Profile-Enabled
		INTEGER,
	    sTM1InterfaceProfile-PathParams-Stm0Profile-TributaryMapping
		INTEGER,
	    sTM1InterfaceProfile-PathParams-Ds3Profile-Name
		DisplayString,
	    sTM1InterfaceProfile-PathParams-Ds3Profile-PhysicalAddress-Shelf
		INTEGER,
	    sTM1InterfaceProfile-PathParams-Ds3Profile-PhysicalAddress-Slot
		INTEGER,
	    sTM1InterfaceProfile-PathParams-Ds3Profile-PhysicalAddress-ItemNumber
		INTEGER,
	    sTM1InterfaceProfile-PathParams-Ds3Profile-Enabled
		INTEGER,
	    sTM1InterfaceProfile-PathParams-Ds3Profile-FrameType
		INTEGER,
	    sTM1InterfaceProfile-PathParams-Ds3Profile-LineLength
		INTEGER,
	    sTM1InterfaceProfile-PathParams-Ds3Profile-Loopback
		INTEGER,
	    sTM1InterfaceProfile-PathParams-Ds3Profile-StatusChangeTrapEnable
		INTEGER
	}

    sTM1InterfaceProfile-PathParams-Shelf-o	OBJECT-TYPE
	SYNTAX	INTEGER
	ACCESS	read-only
	STATUS	mandatory
	DESCRIPTION	""
	::= { mibsTM1InterfaceProfile-PathParamsEntry 1 }

    sTM1InterfaceProfile-PathParams-Slot-o	OBJECT-TYPE
	SYNTAX	INTEGER
	ACCESS	read-only
	STATUS	mandatory
	DESCRIPTION	""
	::= { mibsTM1InterfaceProfile-PathParamsEntry 2 }

    sTM1InterfaceProfile-PathParams-Item-o	OBJECT-TYPE
	SYNTAX	INTEGER
	ACCESS	read-only
	STATUS	mandatory
	DESCRIPTION	""
	::= { mibsTM1InterfaceProfile-PathParamsEntry 3 }

    sTM1InterfaceProfile-PathParams-Index-o	OBJECT-TYPE
	SYNTAX	INTEGER
	ACCESS	read-only
	STATUS	mandatory
	DESCRIPTION	""
	::= { mibsTM1InterfaceProfile-PathParamsEntry 4 }

    sTM1InterfaceProfile-PathParams-Name	OBJECT-TYPE
	SYNTAX	DisplayString
	ACCESS	read-write
	STATUS	mandatory
	DESCRIPTION	"Name of Channelized STS1 Link profile"
	::= { mibsTM1InterfaceProfile-PathParamsEntry 5 }

    sTM1InterfaceProfile-PathParams-Stm0Profile-Name	OBJECT-TYPE
	SYNTAX	DisplayString
	ACCESS	read-write
	STATUS	mandatory
	DESCRIPTION	"Name of Channelized SONET/SDH Path profile"
	::= { mibsTM1InterfaceProfile-PathParamsEntry 6 }

    sTM1InterfaceProfile-PathParams-Stm0Profile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibsTM1InterfaceProfile-PathParamsEntry 7 }

    sTM1InterfaceProfile-PathParams-Stm0Profile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibsTM1InterfaceProfile-PathParamsEntry 8 }

    sTM1InterfaceProfile-PathParams-Stm0Profile-PhysicalAddress-ItemNumber	OBJECT-TYPE
	SYNTAX	INTEGER
	ACCESS	read-write
	STATUS	mandatory
	DESCRIPTION	"A number that specifies an addressable entity within the context of shelf and slot."
	::= { mibsTM1InterfaceProfile-PathParamsEntry 9 }

    sTM1InterfaceProfile-PathParams-Stm0Profile-Enabled	OBJECT-TYPE
	SYNTAX	INTEGER {
		    no (1),
		    yes (2)
		}
	ACCESS	read-write
	STATUS	mandatory
	DESCRIPTION	"TRUE if the link is enabled, otherwise FALSE."
	::= { mibsTM1InterfaceProfile-PathParamsEntry 10 }

    sTM1InterfaceProfile-PathParams-Stm0Profile-TributaryMapping	OBJECT-TYPE
	SYNTAX	INTEGER {
		    vc11AsyncMapping (2),
		    vc11ByteSyncMapping (3),
		    vc12AsyncMapping (5),
		    vc12ByteSyncMapping (6),
		    vc3AsyncMapping (8)
		}
	ACCESS	read-write
	STATUS	mandatory
	DESCRIPTION	"The VT/VC mapping to be performed by this link"
	::= { mibsTM1InterfaceProfile-PathParamsEntry 11 }

    sTM1InterfaceProfile-PathParams-Ds3Profile-Name	OBJECT-TYPE
	SYNTAX	DisplayString
	ACCESS	read-write
	STATUS	mandatory
	DESCRIPTION	"Name of DS3 line."
	::= { mibsTM1InterfaceProfile-PathParamsEntry 12 }

    sTM1InterfaceProfile-PathParams-Ds3Profile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibsTM1InterfaceProfile-PathParamsEntry 13 }

    sTM1InterfaceProfile-PathParams-Ds3Profile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibsTM1InterfaceProfile-PathParamsEntry 14 }

    sTM1InterfaceProfile-PathParams-Ds3Profile-PhysicalAddress-ItemNumber	OBJECT-TYPE
	SYNTAX	INTEGER
	ACCESS	read-write
	STATUS	mandatory
	DESCRIPTION	"A number that specifies an addressable entity within the context of shelf and slot."
	::= { mibsTM1InterfaceProfile-PathParamsEntry 15 }

    sTM1InterfaceProfile-PathParams-Ds3Profile-Enabled	OBJECT-TYPE
	SYNTAX	INTEGER {
		    no (1),
		    yes (2)
		}
	ACCESS	read-write
	STATUS	mandatory
	DESCRIPTION	"TRUE if the line is enabled, otherwise FALSE."
	::= { mibsTM1InterfaceProfile-PathParamsEntry 16 }

    sTM1InterfaceProfile-PathParams-Ds3Profile-FrameType	OBJECT-TYPE
	SYNTAX	INTEGER {
		    m13 (1),
		    cBitParity (2)
		}
	ACCESS	read-write
	STATUS	mandatory
	DESCRIPTION	"Determines the DS3 frame format, also known as the DS3 application."
	::= { mibsTM1InterfaceProfile-PathParamsEntry 17 }

    sTM1InterfaceProfile-PathParams-Ds3Profile-LineLength	OBJECT-TYPE
	SYNTAX	INTEGER {
		    n-0225 (1),
		    n-226450 (2)
		}
	ACCESS	read-write
	STATUS	mandatory
	DESCRIPTION	"The length in feet of the Rx and Tx lines to a DSX-3 cross connect. Double these values for direct connection."
	::= { mibsTM1InterfaceProfile-PathParamsEntry 18 }

    sTM1InterfaceProfile-PathParams-Ds3Profile-Loopback	OBJECT-TYPE
	SYNTAX	INTEGER {
		    noLoopback (1),
		    lineLoopback (2),
		    localLoopback (3)
		}
	ACCESS	read-write
	STATUS	mandatory
	DESCRIPTION	"Loopback mode."
	::= { mibsTM1InterfaceProfile-PathParamsEntry 19 }

    sTM1InterfaceProfile-PathParams-Ds3Profile-StatusChangeTrapEnable	OBJECT-TYPE
	SYNTAX	INTEGER {
		    no (1),
		    yes (2)
		}
	ACCESS	read-write
	STATUS	mandatory
	DESCRIPTION	"When set to No, do not send dsx3LineStatusChangeTrapEnable trap. If Yes, send traps. The default is No."
	::= { mibsTM1InterfaceProfile-PathParamsEntry 21 }


	-- The mibsTM1InterfaceProfile__path_params__master_ds1_index table
	--
	-- This table contains parameters for the mibsTM1InterfaceProfile__path_params__master_ds1_index profile
	--

    mibsTM1InterfaceProfile-PathParams-MasterDs1IndexTable	OBJECT-TYPE
	SYNTAX		SEQUENCE OF MibsTM1InterfaceProfile-PathParams-MasterDs1IndexEntry
	ACCESS		not-accessible
	STATUS		mandatory
	DESCRIPTION	"A list of mibsTM1InterfaceProfile__path_params__master_ds1_index profile entries."
	::= { mibsTM1InterfaceProfile 20 }

    mibsTM1InterfaceProfile-PathParams-MasterDs1IndexEntry	OBJECT-TYPE
	SYNTAX		MibsTM1InterfaceProfile-PathParams-MasterDs1IndexEntry
	ACCESS		not-accessible
	STATUS		mandatory
	DESCRIPTION	"A mibsTM1InterfaceProfile__path_params__master_ds1_index entry containing objects that
			 maps to the parameters of mibsTM1InterfaceProfile__path_params__master_ds1_index profile."
	INDEX		{ sTM1InterfaceProfile-PathParams-MasterDs1Index-Shelf-o, sTM1InterfaceProfile-PathParams-MasterDs1Index-Slot-o, sTM1InterfaceProfile-PathParams-MasterDs1Index-Item-o, sTM1InterfaceProfile-PathParams-MasterDs1Index-Index-o, sTM1InterfaceProfile-PathParams-MasterDs1Index-Index1-o }
	::= { mibsTM1InterfaceProfile-PathParams-MasterDs1IndexTable 1 }

    MibsTM1InterfaceProfile-PathParams-MasterDs1IndexEntry ::=
	SEQUENCE {
	    sTM1InterfaceProfile-PathParams-MasterDs1Index-Shelf-o
		INTEGER,
	    sTM1InterfaceProfile-PathParams-MasterDs1Index-Slot-o
		INTEGER,
	    sTM1InterfaceProfile-PathParams-MasterDs1Index-Item-o
		INTEGER,
	    sTM1InterfaceProfile-PathParams-MasterDs1Index-Index-o
		INTEGER,
	    sTM1InterfaceProfile-PathParams-MasterDs1Index-Index1-o
		INTEGER,
	    sTM1InterfaceProfile-PathParams-MasterDs1Index
		INTEGER
	}

    sTM1InterfaceProfile-PathParams-MasterDs1Index-Shelf-o	OBJECT-TYPE
	SYNTAX	INTEGER
	ACCESS	read-only
	STATUS	mandatory
	DESCRIPTION	""
	::= { mibsTM1InterfaceProfile-PathParams-MasterDs1IndexEntry 1 }

    sTM1InterfaceProfile-PathParams-MasterDs1Index-Slot-o	OBJECT-TYPE
	SYNTAX	INTEGER
	ACCESS	read-only
	STATUS	mandatory
	DESCRIPTION	""
	::= { mibsTM1InterfaceProfile-PathParams-MasterDs1IndexEntry 2 }

    sTM1InterfaceProfile-PathParams-MasterDs1Index-Item-o	OBJECT-TYPE
	SYNTAX	INTEGER
	ACCESS	read-only
	STATUS	mandatory
	DESCRIPTION	""
	::= { mibsTM1InterfaceProfile-PathParams-MasterDs1IndexEntry 3 }

    sTM1InterfaceProfile-PathParams-MasterDs1Index-Index-o	OBJECT-TYPE
	SYNTAX	INTEGER
	ACCESS	read-only
	STATUS	mandatory
	DESCRIPTION	""
	::= { mibsTM1InterfaceProfile-PathParams-MasterDs1IndexEntry 4 }

    sTM1InterfaceProfile-PathParams-MasterDs1Index-Index1-o	OBJECT-TYPE
	SYNTAX	INTEGER
	ACCESS	read-only
	STATUS	mandatory
	DESCRIPTION	""
	::= { mibsTM1InterfaceProfile-PathParams-MasterDs1IndexEntry 5 }

    sTM1InterfaceProfile-PathParams-MasterDs1Index	OBJECT-TYPE
	SYNTAX	INTEGER
	ACCESS	read-write
	STATUS	mandatory
	DESCRIPTION	"The item index of the Master T1/E1 profile to use on the DS1 link."
	::= { mibsTM1InterfaceProfile-PathParams-MasterDs1IndexEntry 6 }

END
