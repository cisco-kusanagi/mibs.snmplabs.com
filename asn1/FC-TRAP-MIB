FC-TRAP-MIB DEFINITIONS ::= BEGIN
IMPORTS
    enterprises, Counter
        FROM RFC1155-SMI
    OBJECT-TYPE
        FROM RFC-1212
    DisplayString
        FROM RFC1213-MIB
    NOTIFICATION-TYPE, MODULE-IDENTITY, ObjectName, Integer32, Counter32, snmpModules
        FROM SNMPv2-SMI
    pepName, devName, sbProducerHost, sbProducerPort
        FROM AGGREGATED-EXT-MIB
    fCServer, fCApp, fCDescText
        FROM FC-DS1-MIB
    TruthValue, DisplayString, TestAndIncr, TimeStamp, RowStatus
        FROM SNMPv2-TC;

        lucent          OBJECT IDENTIFIER  ::=  {  enterprises  1751  }
        products        OBJECT IDENTIFIER  ::=  {  lucent  1  }
        softSwitch      OBJECT IDENTIFIER  ::=  {  products 1198  }
	    fcDeviceServer  OBJECT IDENTIFIER  ::=  {  softSwitch 9 }
    
        fcTraps  MODULE-IDENTITY    
            LAST-UPDATED "240701"
            ORGANIZATION "Lucent Technologies"    
            CONTACT-INFO 
                    ""    
            DESCRIPTION
                "The MIB module for entities implementing the xxxx
                protocol."  

    ::=  {  fcDeviceServer 0 }

    -- The traps group. Listed below are the traps currently supported by SPINS


fcSwitchRegnError NOTIFICATION-TYPE
    OBJECTS { fCServer } 
    STATUS current
    DESCRIPTION
        "Registration of FC Server with the switch for FC API services 
        has failed.
        VARIABLE DEFINITIONS: 
            1. FCServer - FC server in the alarm origin field
                    
        Severity: CRITICAL"
                    
    ::= { fcTraps  1 }

fCSwitchRegnSucc NOTIFICATION-TYPE
    OBJECTS { fCServer } 
    STATUS current
    DESCRIPTION
        "Registration of FC Server with the switch for FC API services 
        is successful.
        VARIABLE DEFINITIONS: 
            1. FCServer - FC Server in the alarm origin field
                    
            Severity: INFO"
                    
    ::= { fcTraps  2 }

fcAddLLCNodeError NOTIFICATION-TYPE                
    OBJECTS { fCServer  }
    STATUS current
    DESCRIPTION
        "The second step of registration with the switch (add_LLC_Node) 
         has failed.
        VARIABLE DEFINITIONS: 
            1. FCServer - FC Server in the alarm origin field
                     
            Severity: CRITICAL"
                     
    ::= { fcTraps  3 }

fcAddLLCNodeSucc NOTIFICATION-TYPE
    OBJECTS { fCServer  }
    STATUS current
    DESCRIPTION
        "The second step of registration with the switch (add_LLC_Node) is 
        successful.
        VARIABLE DEFINITIONS: 
            1. fCServer - FC Server in the alarm origin field
                           
            Severity: INFO"
                     
    ::= { fcTraps  4 }

fcAppStartSucc NOTIFICATION-TYPE
    OBJECTS { fCServer,fCApp }
    STATUS current
    DESCRIPTION
        "fC Application has been started successfully by the FC Server.
         VARIBLE DEFINITIONS:
            1. fCServer - FC Server in the alarm origin field
            2. fCApp - FC Application ID to identify the application
                        
            Severity: INFO"
                        
    ::= { fcTraps  5 }

fcAppEndSucc NOTIFICATION-TYPE
    OBJECTS { fCServer,fCApp }
    STATUS current
    DESCRIPTION
        "FC Application has ended successfully by the FC Server.
         VARIBLE DEFINITIONS:
            1. fCServer - FC Server in the alarm origin field
            2. fCApp - FC Application ID to identify the application
            Severity: INFO"
                        
    ::= { fcTraps  6 }

fcAppStartError NOTIFICATION-TYPE
    OBJECTS { fCServer,fCApp }
    STATUS current
    DESCRIPTION
        "FC Application has failed to started by the FC Server.
         VARIBLE DEFINITIONS:
            1. fCServer - FC Server in the alarm origin field
            2. fCApp - FC Application ID to identify the application
            Severity: MAJOR"
                        
    ::= { fcTraps  7 }
   
fcAppInfoError NOTIFICATION-TYPE             
    OBJECTS { fCServer,fCApp,fCDescText }
    STATUS current
    DESCRIPTION
        "The FC Application has sent an Informational alarm to the FC Server.
         VARIBLE DEFINITIONS:
            1. fCServer - FC Server in the alarm origin field
            2. fCApp - FC Application ID to identify the application
            3. fCDescText - Application Alarm description text
            Severity: INFO"
                        
    ::= { fcTraps  8 }

fcAppMajorError NOTIFICATION-TYPE
    OBJECTS { fCServer,fCApp,fCDescText }
    STATUS current
    DESCRIPTION
        "The FC Application has sent a Major alarm to the FC Server.
        VARIBLE DEFINITIONS:
            1. fCServer - FC Server in the alarm origin field
            2. fCApp - FC Application ID to identify the application
            3. fCDescText - Application Alarm description text
                        
            Severity: MAJOR"
                 
    ::= { fcTraps  9 }

fcAppCritError NOTIFICATION-TYPE             
    OBJECTS { fCServer,fCApp,fCDescText }
    STATUS current
    DESCRIPTION
        "The FC Application has sent a Critical alarm to the FC Server.
           VARIBLE DEFINITIONS:
               1. FCServer - FC Server in the alarm origin field
               2. FCApp - FC Application ID to identify the application
               3. FCDescText - Application Alarm description text
                      Severity: CRITICAL"
                        
    ::= { fcTraps  10 }  

fcUnparsedEvent  NOTIFICATION-TYPE             
    OBJECTS { fCDescText }
    STATUS current
    DESCRIPTION
        "The FC Application has sent a Critical alarm to the FC Server.
           VARIBLE DEFINITIONS:
               1. FCDescText - Application Alarm description text
                      Severity: CRITICAL"
                        
    ::= { fcTraps  11 } 
 
END
