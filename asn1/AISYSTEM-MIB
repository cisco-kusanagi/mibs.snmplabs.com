AISYSTEM-MIB DEFINITIONS ::=  BEGIN

-- Applied Innovation System MIB definitions

IMPORTS
    MODULE-IDENTITY, OBJECT-TYPE,
    enterprises, IpAddress
					FROM SNMPv2-SMI
    TEXTUAL-CONVENTION,
    DateAndTime, DisplayString, TruthValue
					FROM SNMPv2-TC;

    PositiveInteger ::= INTEGER (0..2147483647)

-- group object IDs

aii	OBJECT IDENTIFIER ::= { enterprises 539 }

aiSystem   MODULE-IDENTITY
    LAST-UPDATED "200108151000Z"
    ORGANIZATION "Applied Innovation Incorporated"
    CONTACT-INFO
        "        Engineering MIB Administrator

        Postal:  Applied Innovation Inc.
                 5800 Innovation Drive
                 Dublin, OH 43016

           Tel:  614/798-2000
           Fax:  614/798-1770
        E-mail:  snmp@aiinet.com"
    DESCRIPTION
        "The System MIB Module for AI Equipment"
    REVISION	"200108151000Z"
    DESCRIPTION "Added switchedEthernetPort1000 to the AIIHwIntType
		types and SFP to the AIIConnType types."
    REVISION	"200106281500Z"
    DESCRIPTION "Increased adherence to SMIv2.  Deprecated copperGBIC
		in favor of more appropriate generic GBIC type."
    REVISION	"200105222000Z"
    DESCRIPTION "Added aiSystemCmdReboot and
		aiSystemStatusLastConfig."
    REVISION    "9910250000Z"
    DESCRIPTION "Corrected the descriptions for aiSystemLastTrapMsg
                 and aiSystemLastTrapSequenceNum.
                 Added aiSystemModuleTable and aiSystemStatumTable."
    REVISION    "9810300000Z"
    DESCRIPTION "The initial revision of this module."
    ::= { aii 8 }

-- System Group

AIIHwIntType ::= TEXTUAL-CONVENTION
    STATUS	current
    DESCRIPTION
	"This data type is used as the syntax of the hardware
	interface type object(aiSysSTHwIntType) of the AII Statum
	Discovery Table."
    SYNTAX	INTEGER {
		    noHwIfType(0),
		    serialSyncAsync(1),
		    serialSync(2),
		    serialAsync(3),
		    discreteIn(4),
		    discreteOut(5),
		    ethernetPort10(6),
		    ethernetPort100(7),
		    ethernetPort10-100(8),
		    hubbedEthernetPort10(9),
		    hubbedEthernetPort100(10),
		    hubbedEthernetPort10-100(11),
		    modem56K(12),
		    hubbedFiber1310(13),
		    hubbedFiber1550(14),
		    temperatureProbe(15),
		    power(16),
		    fan(17),
		    ethernetPort1000(18),
		    fiber850(19),
		    fiber1310(20),
		    analogIn(21),
		    switchedEthernetPort10(22),
		    switchedEthernetPort100(23),
		    switchedEthernetPort10-100(24),
		    switchedFiber1310(25),
		    switchedFiber1550(26),
		    luxChannel10G(27),
		    switchedEthernetPort1000(28),
          serialSyncAsyncnoDSR(29),
          serialAsyncnoDSR(30)
		}

AIIConnType ::= TEXTUAL-CONVENTION
    STATUS	current
    DESCRIPTION
	"This data type is used as the syntax of the connector type
	object(aiSysSTConnType) of the AII Statum Discovery Table."
    SYNTAX	INTEGER {
		    noConnType(0),     -- Internal statums of a device
		    propConnType(1),   -- Nonstandard connectors
		    db9(2),
		    db25(3),
		    rj11(4),
		    rj45(5),
		    coax(6),
		    aui(7),
		    sc(8),		-- Fiber Connector
		    vhdci(9),		-- AI232 Connector
		    scsi2(10),		-- AI296 Connector
		    copperGBIC(11), -- deprecated
		    gbic(12),		-- GBIC slot
		    sfp(13)		-- SFP slot
		}

-- Implementation of this group is mandatory for all equipment
-- produced by Applied Innovation Inc. that supports SNMP management.

aiSystemSendsStatusTraps OBJECT-TYPE
    SYNTAX	TruthValue
    MAX-ACCESS	read-only
    STATUS	current
    DESCRIPTION
	"This flag indicates whether or not this agent sends traps
	when its ports change status.  The TruthValue syntax defines
	values of true(1) and false(2)."
    ::= { aiSystem 1 }

aiSystemLastTrapSequenceNum OBJECT-TYPE
    SYNTAX	INTEGER (0..4294967295)
    MAX-ACCESS	read-only
    STATUS	current
    DESCRIPTION
	"This is the sequence number of the last trap sent by this
	agent.  The sequence number starts at zero following a
	hardware reset or power-up.  When the sequence number reaches
	0xffffffff, it rolls over to 0 on the next trap.  If the agent
	supports trap sequence numbers, it must include the trap
	sequence number when it sends traps and it must notify the CLC
	via a window transaction after each trap.

	When this varbind appears in a trap, this is the sequence
	number of that trap."
    ::= { aiSystem 2 }

aiSystemLastTrapMsg OBJECT-TYPE
    SYNTAX	DisplayString
    MAX-ACCESS	read-only
    STATUS	current
    DESCRIPTION
	"The message text which was inserted in the last trap sent by
	this agent.  If this agent does not support traps, the string
	is blank.

	When this varbind appears in a trap, the value is the message
	for that trap."
    ::= { aiSystem 3 }


-- Discovery tables

aiSystemDisc	OBJECT IDENTIFIER ::= { aiSystem 4 }

aiSystemDiscVersion OBJECT-TYPE
    SYNTAX	INTEGER (0..32767)
    MAX-ACCESS	read-only
    STATUS	current
    DESCRIPTION
	"The version of the aiSystem discovery tables supported by the
	SNMP agent.  Each time modifications are made to the syntax of
	any part of this MIB under the aiSystemDisc branch, the
	version number must be incremented.

	For example, if a new column is added to a table or a new
	value is added to an enum object, the version must be
	incremented.  If a description is changed or an object name is
	changed, the version is not incremented."
    ::= { aiSystemDisc 1 }

aiSystemDiscLastChanged OBJECT-TYPE
    SYNTAX	DateAndTime
    MAX-ACCESS	read-only
    STATUS	current
    DESCRIPTION
	"The date and time of the last change to any object under the
	aiSystemDisc branch of this MIB.

	The DateAndTime type is a structured OCTET STRING, defined in
	v2-tc.my (SNMPv2 Textual Conventions)."
    ::= { aiSystemDisc 2 }

-- System Module Table
-- This table identifies all modules that are part of the system.

aiSysDiscModuleTable OBJECT-TYPE
    SYNTAX	SEQUENCE OF AiSysModuleTableEntry
    MAX-ACCESS	not-accessible
    STATUS	current
    DESCRIPTION
	"A table of modules in the system."
    ::= { aiSystemDisc 3 }

aiSysModuleTableEntry OBJECT-TYPE
    SYNTAX	AiSysModuleTableEntry
    MAX-ACCESS	not-accessible
    STATUS	current
    DESCRIPTION
	"Information unique to a particular module."
    INDEX { IMPLIED aiSysMTIndex }
    ::= { aiSysDiscModuleTable 1 }

AiSysModuleTableEntry ::=
    SEQUENCE {
	aiSysMTIndex		OBJECT IDENTIFIER,
	aiSysMTProductName	DisplayString,
	aiSysMTSerialNumber	DisplayString,
	aiSysMTManufDate	DisplayString
    }

aiSysMTIndex OBJECT-TYPE
    SYNTAX	OBJECT IDENTIFIER
    MAX-ACCESS	read-only
    STATUS	current
    DESCRIPTION
	"The index for the module or submodule described in this row.
	The top-level module's oid is always 1.1.  Submodules nest
	within the top-level module (e.g. 1.1.1, 1.1.2,...) and may
	have submodules nested within them to an arbitrary level(e.g.
	1.1.1.1, 1.1.1.2,...).

	Each hardware component which has a product code that can be
	read or inferred by the SNMP agent may appear as a row in this
	table.  The nesting of modules within modules describes the
	hierarchy of the hardware components that make up the
	top-level module."
    ::= { aiSysModuleTableEntry 1 }

aiSysMTProductName OBJECT-TYPE
    SYNTAX	DisplayString
    MAX-ACCESS	read-only
    STATUS	current
    DESCRIPTION
	"The product name of the module.  This is the name from the
	module's auto-id part, if it has one."
    ::= { aiSysModuleTableEntry 2 }

aiSysMTSerialNumber OBJECT-TYPE
    SYNTAX	DisplayString
    MAX-ACCESS	read-only
    STATUS	current
    DESCRIPTION
	"The serial number of the module.  This is the serial number
	from the module's auto-id part, if it has one."
    ::= { aiSysModuleTableEntry 3 }

aiSysMTManufDate OBJECT-TYPE
    SYNTAX	DisplayString
    MAX-ACCESS	read-only
    STATUS	current
    DESCRIPTION
	"The date of manufacture of the module.  This is the
	manufacture date from the module's auto-id part, if it has
	one."
    ::= { aiSysModuleTableEntry 4 }


-- System Statum Table
-- This table identifies all the statums that are part of the system.
--
-- A 'statum' is a monitorable item belonging to the system, such as a
-- link, port, I/O point, or even a virtual 'port' or 'point'.  A
-- statum can be monitored via SNMP operations to read its status.

aiSysDiscStatumTable OBJECT-TYPE
    SYNTAX	SEQUENCE OF AiSysStatumTableEntry
    MAX-ACCESS	not-accessible
    STATUS	current
    DESCRIPTION
	"A table of statums in the system."
    ::= { aiSystemDisc 4 }

aiSysStatumTableEntry OBJECT-TYPE
    SYNTAX	AiSysStatumTableEntry
    MAX-ACCESS	not-accessible
    STATUS	current
    DESCRIPTION
	"Information unique to a particular statum."
    INDEX { IMPLIED aiSysSTIndex }
    ::= { aiSysDiscStatumTable 1 }

AiSysStatumTableEntry ::=
    SEQUENCE {
	aiSysSTIndex		OBJECT IDENTIFIER,
	aiSysSTLabel		DisplayString,
	aiSysSTFaceplateModule	OBJECT IDENTIFIER,
	aiSysSTFaceplateOpening	INTEGER,
	aiSysSTOpeningIndex	INTEGER,
	aiSysSTHwIntType	AIIHwIntType,
	aiSysSTConnType		AIIConnType,
	aiSysSTMonTabIndex	INTEGER
    }

aiSysSTIndex OBJECT-TYPE
    SYNTAX	OBJECT IDENTIFIER
    MAX-ACCESS	read-only
    STATUS	current
    DESCRIPTION
	"The index for the statum described in this row.  This is a
	module table index (aiSysMTIndex) with a unique statum number
	appended (e.g. 1.1.1.2.1, 1.1.1.2.2,... where 1.1.1.2 is the
	module table index and 1, 2,... are statum numbers).

	The module table identifier is from the parent module that
	contains the port or point associated with this entry, or the
	top-level module, if this statum is not associated with a
	specific hardware assembly."
    ::= { aiSysStatumTableEntry 1 }

aiSysSTLabel OBJECT-TYPE
    SYNTAX	DisplayString
    MAX-ACCESS	read-only
    STATUS	current
    DESCRIPTION
	"A label that uniquely identifies this statum within its
	faceplate."
    ::= { aiSysStatumTableEntry 2 }

aiSysSTFaceplateModule OBJECT-TYPE
    SYNTAX	OBJECT IDENTIFIER
    MAX-ACCESS	read-only
    STATUS	current
    DESCRIPTION
	"The module table index (aiSysMTIndex) of the module table
	entry associated with the faceplate that this statum's
	connector extends from.  This may be the module this statum is
	nested under or any other module, including the top-level
	module of the system."
    ::= { aiSysStatumTableEntry 3 }

aiSysSTFaceplateOpening OBJECT-TYPE
    SYNTAX	INTEGER (0..32767)
    MAX-ACCESS	read-only
    STATUS	current
    DESCRIPTION
	"The identifier of the faceplate opening that this statum's
	connector extends from.  Each opening in a given faceplate
	must have a unique numeric identifier."
    ::= { aiSysStatumTableEntry 4 }

aiSysSTOpeningIndex OBJECT-TYPE
    SYNTAX	INTEGER (0..32767)
    MAX-ACCESS	read-only
    STATUS	current
    DESCRIPTION
	"A number that identifies the index of the statum in its
	opening identified in aiSysSTFaceplateOpening.  If only one
	statum is accessible from an opening then that statum has an
	opening index of 1.  If more than one statum is accessible
	through an opening, then the first statum is given the index
	of 1.  Each successive statum for an opening has an index of
	one greater than the previous statum's opening index."
    ::= { aiSysStatumTableEntry 5 }

aiSysSTHwIntType OBJECT-TYPE
    SYNTAX	AIIHwIntType
    MAX-ACCESS	read-only
    STATUS	current
    DESCRIPTION
	"Identifies the hardware interface type for the statum."
    ::= { aiSysStatumTableEntry 6 }

aiSysSTConnType OBJECT-TYPE
    SYNTAX	AIIConnType
    MAX-ACCESS	read-only
    STATUS	current
    DESCRIPTION
	"Identifies the connector type for the statum.  If a statum is
	internal to the device, aiSysSTFaceplateOpening equal to 0,
	then its connector type should be 'noConnType'.  If a statum
	has a proprietary connector then its connector type should be
	'propConnType'."
    ::= { aiSysStatumTableEntry 7 }

aiSysSTMonTabIndex OBJECT-TYPE
    SYNTAX	INTEGER (0..32767)
    MAX-ACCESS	read-only
    STATUS	current
    DESCRIPTION
	"The index into the table which is used to monitor the status
	of the statum (e.g. statums of type serialSync should have
	their aiLinkTable index identified)."
    ::= { aiSysStatumTableEntry 8 }

-- System Trap Table
-- This table contains all the device IP addresses to which traps are sent.
--

aiSystemManagerTable OBJECT-TYPE
    SYNTAX	SEQUENCE OF AISystemManagerTableEntry
    MAX-ACCESS	not-accessible
    STATUS	current
    DESCRIPTION
	"Table of IP addresses to which SNMP traps will be sent,
	indexed by an integer."
    ::= {aiSystem 5}

aiSystemManagerTableEntry OBJECT-TYPE
    SYNTAX	AISystemManagerTableEntry
    MAX-ACCESS	not-accessible
    STATUS	current
    DESCRIPTION
	"Entry of aiSystemManagerTable."
    INDEX { aisysManagerIndex }
    ::= { aiSystemManagerTable 1 }

AISystemManagerTableEntry ::=
    SEQUENCE {
	aisysManagerIndex	PositiveInteger,
	aisysManagerAddress	IpAddress
    }

aisysManagerIndex OBJECT-TYPE
    SYNTAX	PositiveInteger
    MAX-ACCESS	read-only
    STATUS	current
    DESCRIPTION
	"Index into this table of SNMP managers."
    ::= { aiSystemManagerTableEntry 1 }

aisysManagerAddress OBJECT-TYPE
    SYNTAX	IpAddress
    MAX-ACCESS	read-write
    STATUS	current
    DESCRIPTION
	"SNMP manager IP address.  0.0.0.0 indicates an unused entry."
    ::= { aiSystemManagerTableEntry 2 }

aiSystemCmdReboot OBJECT-TYPE
    SYNTAX	INTEGER {up(1), boot(2)}
    MAX-ACCESS	read-write
    STATUS	current
    DESCRIPTION
	"Configured boot status of the system. A write of boot(2) when
	this object is in up(1) state will cause the system to
	reboot. Any other write will have no effect."
    ::= { aiSystem 6 }

aiSystemStatusLastConfig OBJECT-TYPE
    SYNTAX	OCTET STRING (SIZE(0..32))
    MAX-ACCESS	read-only
    STATUS	current
    DESCRIPTION
	"An md5sum hash of the current configuration file.  This will
	be used as a timestamp of a sort by the management station."
    ::= { aiSystem 7 }

END
