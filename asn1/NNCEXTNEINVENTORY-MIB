-------------------------------------------------------------------------------
-- file: nncExtNEInventory.mib 
--
-- description:
--	This file contains the SNMP definitions for the NEInventory area.
--
-- history:
--	31A1225 / 98.10.06 / Nitin Gugle / Creation from V1.0 of 
--                                         MIBTemplate.mib
--      31A1225 / 98.11.02 / Nitin Gugle / Updated to incorporate changes suggested
--                                         during review.
--      31A1225 / 99.05.19 / jayanthi    / Added resetCause and moved some 
--                                         TCs to GNI0006. Also, added more
--                                         info to description field of some
--                                         objects. 
--
-- %%history-start%%
-- 1999.06.04 jayanthi 31A1286: Kan2 Merge Create Script 
-- 1999.06.15 jayanthi P.285550: added restartCause and moved some TCs to 
--   GNI0006.mib. 
-- %%history-end%%
--
-- Copyright 1998, 1999 Newbridge Networks Corporation.  All Rights Reserved
-------------------------------------------------------------------------------
NNCEXTNEINVENTORY-MIB DEFINITIONS ::= BEGIN

    IMPORTS

    MODULE-IDENTITY, OBJECT-TYPE
      FROM SNMPv2-SMI
    MODULE-COMPLIANCE, OBJECT-GROUP
      FROM SNMPv2-CONF
    DisplayString, TEXTUAL-CONVENTION
      FROM SNMPv2-TC
    NncSwBank, NncSwStatus
      FROM NNCGNI0006-MIB
    entPhysicalIndex, entPhysicalEntry
      FROM ENTITY-MIB
    nncExtensions
      FROM NNCGNI0001-SMI;
		
    nncExtNEInventory MODULE-IDENTITY	--all NNC modules have the prefix nncExt

		LAST-UPDATED 	"9904151645Z"
		ORGANIZATION 	"Newbridge Networks Corporation"
		CONTACT-INFO
            			"Newbridge Networks Corporation
             			Postal: 600 March Road
                     		Kanata, Ontario
                     		Canada K2K 2E6

             			Phone:  +1 613 591 3600
             			Fax:    +1 613 591 3680"
		
		DESCRIPTION	"This module contains definition for monitoring the inventory
                of network elements in a network. The module can be used to query the 
                information of different network elements for information such as identity,
                associated identity numbers, software banks, software in the banks and their
                status."
	
	::= { nncExtensions 69 } 


	nncExtNEInventoryObjects OBJECT IDENTIFIER 	      ::=    { nncExtNEInventory 1 }
	nncExtNEInventoryGroups OBJECT IDENTIFIER             ::=    { nncExtNEInventory 2 }
	nncExtNEInventoryCompliances OBJECT IDENTIFIER        ::=    { nncExtNEInventory 3 }

 
--------------------------------------------------------------------------------
-- Object Definitions
--
-- This MIB module contains the following tables:
-- nncNEInventoryTable	
-- nncAssemblySwBankTable
--------------------------------------------------------------------------------

-- The nncNEInventoryTable

  nncNEInventoryTable OBJECT-TYPE
    SYNTAX            SEQUENCE OF NncNEInventoryTableEntry
    MAX-ACCESS        not-accessible
    STATUS            current
    DESCRIPTION       "The nncNEInventoryTable contains objects of interest to
                      the network inventory manager." 
    ::= { nncExtNEInventoryObjects 1 }


  nncNEInventoryTableEntry OBJECT-TYPE
    SYNTAX            NncNEInventoryTableEntry
    MAX-ACCESS        not-accessible
    STATUS            current
    DESCRIPTION       "This is an entry in the nncNEInventoryTable."
    AUGMENTS          { entPhysicalEntry }
    ::= { nncNEInventoryTable 1 }

  NncNEInventoryTableEntry ::= SEQUENCE{
    nncNEInvAssemblyName               DisplayString,
    nncNEInvSerialNumber               DisplayString,
    nncNEInvAssemblyIdentity           DisplayString,
    nncNEInvMktgPartNo                 DisplayString,
    nncNEInvEnggPartNo                 DisplayString,
    nncNEInvRestartCause               DisplayString,
    nncNEInvAssemblyNoOfSwBanks        INTEGER,
    nncNEInvAssemblyActiveSwBank       NncSwBank,
    nncNEInvAssemblyNextActiveSwBank   NncSwBank
    }


  nncNEInvAssemblyName OBJECT-TYPE
    SYNTAX          DisplayString
    MAX-ACCESS      read-only
    STATUS          current
    DESCRIPTION     "Describes textually the generally used name of the assembly as used
                    on local craft interface. This is a string available from the system
                    software."
    ::= { nncNEInventoryTableEntry 1 }


  nncNEInvSerialNumber OBJECT-TYPE
    SYNTAX          DisplayString 
    MAX-ACCESS      read-only
    STATUS          current
    DESCRIPTION     "The serial number of the assembly. It is variable length string.
                    It is unique across the customer orderable entities and may be 
                    shared by multiple assemblies. If an entity does not have this 
                    number, default value is returned."
    DEFVAL          { ''H } 
    ::= { nncNEInventoryTableEntry 2 }


  nncNEInvAssemblyIdentity OBJECT-TYPE
    SYNTAX          DisplayString (SIZE (0..12)) 
    MAX-ACCESS      read-only
    STATUS          current
    DESCRIPTION     "Describes the identity of the assembly. The format is HHHHLLLLRRVV 
                    where HHHHLLLL is the card identity. HHHH refers to Card Identifier 
                    (High Word), LLLL refers to Card Identifier(Low Word). RR is the
                    major revision and VV is the minor revision.  If an entity does not 
                    have this number, default value is returned."
                
    DEFVAL          { ''H } 
    ::= { nncNEInventoryTableEntry 3 }


  nncNEInvMktgPartNo OBJECT-TYPE
    SYNTAX          DisplayString (SIZE (0..17))
    MAX-ACCESS      read-only
    STATUS          current
    DESCRIPTION     "The marketing part number(90 level). Some customer non-orderable 
                    assemblies do not have this number and are expected to return the 
                    default value. The marketing number is of format 90-SSSS-VV-CC-MMM 
                    where SSSS is sequence number, VV is the variant, CC is customer 
                    code and MMM is manufacturing code."
    DEFVAL          { ''H } 
    ::= { nncNEInventoryTableEntry 4 }


  nncNEInvEnggPartNo OBJECT-TYPE
    SYNTAX          DisplayString (SIZE (0..18))
    MAX-ACCESS      read-only
    STATUS          current
    DESCRIPTION     "Describes the engineering part number(87 level). Every assembly is  
                    expected to have this number. The format is 87-SSSS-VV-PR where SSSS 
                    is assembly number, VV is variant, P is copper platform and R is 
                    revision. Default value is returned whenever there is a failure to 
                    get this information.  For example, if a card is configured but not 
                    installed, then a default value is returned."
    DEFVAL          { ''H }
    ::= { nncNEInventoryTableEntry 5 }

 nncNEInvRestartCause OBJECT-TYPE
    SYNTAX          DisplayString
    MAX-ACCESS      read-only
    STATUS          current
    DESCRIPTION     "Indicates the cause of the most recent restart for an assembly.  
                    Assemblies that do not have this information are expected to return 
                    a default value."
    DEFVAL          { ''H }
    ::= { nncNEInventoryTableEntry 6 }


  nncNEInvAssemblyNoOfSwBanks OBJECT-TYPE
    SYNTAX          INTEGER (0..31)
    MAX-ACCESS      read-only
    STATUS          current
    DESCRIPTION     "Describes the total number of software banks on this assembly 
                    including the boot bank. For example: assemblies that have processors 
                    have three banks. The enumeration starts with zero to indicate absence 
                    of any software bank on the assembly."
    DEFVAL          { 0 } 
    ::= { nncNEInventoryTableEntry 7 }


  nncNEInvAssemblyActiveSwBank OBJECT-TYPE
    SYNTAX          NncSwBank
    MAX-ACCESS      read-only
    STATUS          current
    DESCRIPTION     "Indicates the software bank which is current and active. The default
                    value of NotApplicable(0) indicates the entity without software 
                    banks.  On the other hand, if there is a failure to obtain this  
                    information, Unknown(257) is returned.  For example, if a card is 
                    configured but not installed, Unknown(257) is returned."
    DEFVAL          { 0 }
    ::= { nncNEInventoryTableEntry 8 }


  nncNEInvAssemblyNextActiveSwBank OBJECT-TYPE
    SYNTAX          NncSwBank
    MAX-ACCESS      read-only
    STATUS          current
    DESCRIPTION     "Indicates the software bank which will be active when the card 
                    resets.  The default value of NotApplicable(0) indicates the entity 
                    without software banks.  On the other hand, if there is a failure to  
                    obtain this information, Unknown(257) is returned.  For example, if  
                    a card is configured but not installed, Unknown(257) is returned."
    DEFVAL          { 0 }
    ::= { nncNEInventoryTableEntry 9 }



  --The nncAssemblySwBanksTable

  nncAssemblySwBanksTable OBJECT-TYPE
    SYNTAX            SEQUENCE OF NncAssemblySwBanksTableEntry
    MAX-ACCESS        not-accessible
    STATUS            current
    DESCRIPTION       "The nncAssemblySwBanksTable contains objects of interest in the 
                      software banks to the network inventory manager. An assembly may  
                      have software banks and these banks are numbered from 1 till the  
                      total software banks on the assembly. An assembly with no software  
                      bank has nncNEInvAssemblyNoOfSwBanks equal to zero. The banks on the 
                      assembly may store a software generic. The bank which holds the 
                      currently running software is indicated by 
                      nncNEInvAssemblyActiveSwBank. The same software bank or any other 
                      software bank may be the 'Next' bank which becomes 'Active' upon 
                      reset. The next bank for the given assembly can be retrieved by  
                      doing a get against instance of the nncNEInvAssemblyNextActiveSwBank.
                      Each of these banks can be identified distinctly with the 
                      entPhysicalIndex of the assembly and the software bank number on 
                      the assembly."
    ::= { nncExtNEInventoryObjects 2 }


  nncAssemblySwBanksTableEntry OBJECT-TYPE
    SYNTAX            NncAssemblySwBanksTableEntry
    MAX-ACCESS        not-accessible
    STATUS            current

    DESCRIPTION       "This is an entry in the nncAssemblySwBanksTable."
    INDEX             { entPhysicalIndex, nncAssemblySwBankNumber }
    ::= { nncAssemblySwBanksTable 1 }

                           
  NncAssemblySwBanksTableEntry ::= SEQUENCE{
    nncAssemblySwBankNumber       INTEGER,
    nncAssemblySwBankGeneric      DisplayString,
    nncAssemblySwBankStatus       NncSwStatus
    }


  nncAssemblySwBankNumber OBJECT-TYPE
    SYNTAX          INTEGER (1..31)
    MAX-ACCESS      read-only
    STATUS          current
    DESCRIPTION     "Refers to the software bank number of interest. The bank numbers should 
                    start with 1 and should extend to the total number of banks on the assembly.
                    For assemblies with no software banks there are no entries in this table."
    ::= { nncAssemblySwBanksTableEntry 1 }


  nncAssemblySwBankGeneric OBJECT-TYPE
    SYNTAX          DisplayString (SIZE (12))
    MAX-ACCESS      read-only
    STATUS          current
    DESCRIPTION     "The software generic in the software bank. The format of the generic 
                    software number is ZAABCD-EF-GH where ZAAB comprises of the product 
                    identifier, C is the target type and is 1 for target load and S for 
                    simulator. The D is the product release number, E is the build type 
                    and is R for R&D internal load, F for field trials, H for hardened 
                    product loads and D for demo loads. F is the dot release number and 
                    GH is the maintenance build and minor build number. This is available 
                    from system software. If the software bank is empty, the default string
                    'CheckBankSts' is returned. If software generic is not available 
                    because the card does not have software banks or because the card is 
                    not installed, NoSuchName is returned."
     ::= { nncAssemblySwBanksTableEntry 2 }


  nncAssemblySwBankStatus OBJECT-TYPE
    SYNTAX          NncSwStatus
    MAX-ACCESS      read-only
    STATUS          current
    DESCRIPTION     "The status of the software in the software bank. NoSuchName is 
                    expected to be returned for status of a software bank that does 
                    not exist or if the information is not available. "

    ::= { nncAssemblySwBanksTableEntry 3 } 


--------------------------------------------------------------------------------
-- Conformance Group Definitions
--------------------------------------------------------------------------------
 
  nncNEPhysInventoryGroup OBJECT-GROUP
    OBJECTS {
    nncNEInvAssemblyName,        
    nncNEInvSerialNumber,     
    nncNEInvAssemblyIdentity,     
    nncNEInvMktgPartNo,       
    nncNEInvEnggPartNo,       
    nncNEInvRestartCause,
    nncNEInvAssemblyNoOfSwBanks,
    nncNEInvAssemblyActiveSwBank,
    nncNEInvAssemblyNextActiveSwBank
    }
   STATUS      current
   DESCRIPTION "Collection of objects providing the physical network element inventory information."
   ::= { nncExtNEInventoryGroups 1 }
  
  
  nncNEPhysAssemblySwBankGroup OBJECT-GROUP
    OBJECTS {
    nncAssemblySwBankNumber,
    nncAssemblySwBankGeneric,
    nncAssemblySwBankStatus  
    }
    STATUS      current
    DESCRIPTION "Collection of objects providing the assembly bank information."
    ::= { nncExtNEInventoryGroups 2 }
  
  
--------------------------------------------------------------------------------
-- Compliance Statements (mandatory)
--------------------------------------------------------------------------------

  nncNEInvCompliance       MODULE-COMPLIANCE
    STATUS      current
    DESCRIPTION "The compliance statement for Newbridge SNMP entities which are network 
                 elements containing associated inventory information."
    MODULE
      MANDATORY-GROUPS{
        nncNEPhysInventoryGroup,
        nncNEPhysAssemblySwBankGroup
        }
    ::= { nncExtNEInventoryCompliances 1 }

--------------------------------------------------------------------------------
END -- DEFINITION OF NNCEXTNETWORKINVENTORY-MIB
--------------------------------------------------------------------------------



--------------------------------------------------------------------------------
--      MINUTES-BEGIN
--              REVIEW-DATE  "1998.10.24"
--              BODY  "
--
--      
--      TO:     Frank Chen*, Claudette Gauthier*, Iqbal Pandher*, 
--              Mark Weedmark*, Randy Jones*, David Fowler
--      FROM:   Nitin Gugle*

--
--      A meeting was held on 1998.10.24 to review ATMStatistics.mib.
--      Attendees are marked with * in the TO and CC lists above.
--
--      Outcome
--
--      It was the consensus of the review team that this file is 
--      acceptable with the indicated modifications
--
--      Actions:
--              A1 - Nitin Gugle to update nncExtNEInventory as described in Decision D1.
--
--                   Response              Status               Closed
--                   1998.11.09        Updated nncExtNEInventory.mib according to D1.
--
--      Decisions:
--      D1 -    NEInventory.mib shall be updated as follows:
--              a. Line 26 Update the LAST-UPDATED field
--              b. In module DESCRIPTION field, add text reduce the scope to 
--                 to Network Element.
--              c. Change nncNEInventoryObjects to be  nncExtNEInventoryObjects. The
--                 same applies to all of the main definitions.
--              d. Enhance NncSWStatus DESCRIPTION to describe the difference between
--                 error and problem.
--              e. Change NncSWStatus "ok" to (2) and let errors count up from there.
--              f. DESCRIPTION clause for nncNEInventoryTable object. Delete last two
--                 sentences and add explict text for default values in each object.
--              g. nncNEInvAssemblyName: Nitin to investigate specification of a variable 
--                 length string.
--              h. DESCRIPTION clause of nncNEInvAssemblyName; Add comment that the name is 
--                 the one used on the local craft interface.
--              i. For Assembly Serial Number, paste into the DESCRIPTION the description 
--                 of the serial number format from HQP0021.
--              j. To specify the meaning of HHHHHLLLL in the DESCRIPTION of 
--                 nncNEInvAssemblyIdentity.
--              k. DESCRIPTION of nncNEInvMktgPartNo; claify "Some assemblies..." as those
--                 which are not customer orderable.
--              l. For nncNEInvAssemblyNoOfSWBanks, change range to 0-31 and clarify the
--                 meaning of '0' in it.
--              m. For nncNEInvAssemblyActiveBank and nncNEInvAssemblyNextActiveBank 
--                 specify that a default value of '0' indicates an entity without banks.
--              n. Whereever the word Banks have been used, replace it with SwBanks.
--              o. For nncAssemblyBanksTable remove DEFVAL.
--              p. In the DESCRIPTION clause of nncAssemblyBanksTable add a detailed 
--                 description of our software storage model complete with the usage of 
--                 current and next banks.
--              q. Ensure through out the module that there is "white space" on each side
--                 of the ::= operator.
--              r. For nncAssemblyBankNumber, change range to 1..31 and explain the
--                 reason for that range.
--              s. To the DESCRIPTION clause of nncAssemblyBankGenericSW add the description
--                 of a software generic from our SQP0020 document. Also, clarify what is returned
--                 as a generic for an empty bank.
--              t. For nncAssemblyBankSWStatus  remove the DEFVAL because noSuchName will be 
--                 returned for any status for a bank that does not exist.
--
--      "
--
--      END-MINUTES
-------------------------------------------------------------------------------
--      Review Minutes
-------------------------------------------------------------------------------
--      MINUTES-BEGIN
--              REVIEW-DATE  "1999.04.15"
--              BODY  "
--
--
--      TO:     AtmSw
--      FROM:   Jayanthi Venkatasubba
--
--      A EDR was announced on 99.04.15 to review nncExtNEInventory.mib,the 
--      area interface definition for the Inventory area in the system region.
--
--      Outcome
--
--      This file was found to be acceptable with the indicated modifications.
--
--      Actions:
--              A1 - Jayanthi to update nncExtNEInventory as described in Decision D1.
--
--                   Response              Status               Closed
--                   1999.05.31        Updated nncExtNEInventory.mib according to D1.
--
--      Decisions:
--      D1 -    NEInventory.mib shall be updated as follows:
--              a. remove references to 36170.
--              b. add restartCause to nncNEPhysInventoryGroup in Conformance Group
--                 Definitions section.
--
--      END-MINUTES
