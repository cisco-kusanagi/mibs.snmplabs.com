Wellfleet-IFP-MIB DEFINITIONS ::= BEGIN


    IMPORTS

      Counter, Gauge
        FROM RFC1155-SMI
      OBJECT-TYPE
        FROM RFC-1212
      wfIfpGroup
        FROM Wellfleet-COMMON-MIB;

    wfIfpDrvCfgTable OBJECT-TYPE
        SYNTAX   SEQUENCE OF WfIfpDrvCfgEntry
        ACCESS   not-accessible
        STATUS   mandatory
        DESCRIPTION
                "Internet Fowarding Processor(IFP) Configuration Record"
        ::= { wfIfpGroup 1 }

    wfIfpDrvCfgEntry  OBJECT-TYPE
        SYNTAX   WfIfpDrvCfgEntry
        ACCESS   not-accessible
        STATUS   mandatory
        DESCRIPTION
                "Information about a particular driver"
        INDEX    { wfIfpDrvCfgSlot }
        ::= { wfIfpDrvCfgTable 1 }

    WfIfpDrvCfgEntry ::= SEQUENCE {
         wfIfpDrvCfgState
             INTEGER,
         wfIfpDrvCfgSlot
             INTEGER,
         wfIfpDrvCfgHeartbeatPeriod
             INTEGER,
         wfIfpDrvCfgHiPriQueRdEnable
             INTEGER,
         wfIfpDrvCfgLoPriQueRdEnable
             INTEGER,
         wfIfpDrvCfgPortDrainEnable
             INTEGER,
        wfIfpDrvCfgSspPktTypeI
             INTEGER,
        wfIfpDrvCfgSspPktTypeII
             INTEGER,
        wfIfpDrvCfgCap0PktTypeI
             INTEGER,
        wfIfpDrvCfgCap0PktTypeII
             INTEGER,
        wfIfpDrvCfgCap1PktTypeI
             INTEGER,
        wfIfpDrvCfgCap1PktTypeII
             INTEGER,
        wfIfpDrvCfgAtmPktTypeI
             INTEGER,
        wfIfpDrvCfgAtmPktTypeII
             INTEGER,
        wfIfpDrvCfgMax2kBufferCnt
             INTEGER,
         wfIfpDrvCfgMax8kBufferCnt
             INTEGER,
         wfIfpDrvCfgBufferOffset
             INTEGER,
         wfIfpDrvCfgCapHiPriQueClip
             INTEGER,
         wfIfpDrvCfgCapLoPriQueClip
             INTEGER,
         wfIfpDrvCfgAtmHiPriQueClip
             INTEGER,
         wfIfpDrvCfgAtmLoPriQueClip
             INTEGER,
         wfIfpDrvCfgSspHiPriQueClip
             INTEGER,
         wfIfpDrvCfgSspLoPriQueClip
             INTEGER,
         wfIfpDrvCfgMcastHiPriClip
             INTEGER,
         wfIfpDrvCfgMcastLoPriClip
             INTEGER,
         wfIfpDrvCfgRspActiveStreamMask
             INTEGER,
         wfIfpDrvCfgToSspLoPriInterval
             INTEGER,
         wfIfpDrvCfgToSspLoPriPktCnt
             INTEGER
        }

    wfIfpDrvCfgState OBJECT-TYPE
        SYNTAX   INTEGER {
                     up(1),
                     down(2),
                     init(3),
                     notpresent(20)
                 }
        ACCESS   read-write
        STATUS   mandatory
        DESCRIPTION
                "Driver state parameter. "
        DEFVAL   { notpresent }
        ::= { wfIfpDrvCfgEntry 1 }

    wfIfpDrvCfgSlot OBJECT-TYPE
        SYNTAX   INTEGER(1..12)
        ACCESS   read-only
        STATUS   mandatory
        DESCRIPTION
                 "Slot number -- instance id."
        ::= { wfIfpDrvCfgEntry 2 }

    wfIfpDrvCfgHeartbeatPeriod OBJECT-TYPE
        SYNTAX   INTEGER 
        ACCESS   read-write
        STATUS   mandatory
        DESCRIPTION
                 "The timer period, in seconds, which defines how often 
                  heartbeat messages are send to the IFP. A value of zero
                  disables the heartbeat service."
        DEFVAL   { 3 }
        ::= { wfIfpDrvCfgEntry 3 }

    wfIfpDrvCfgHiPriQueRdEnable OBJECT-TYPE
        SYNTAX   INTEGER {
                     enablehicap1(1),
                     enablehicap2(2),
                     enablehicap3(4),
                     enablehicap4(8),
                     enablehicap5(16),
                     enablehissp0(32),
                     enablehissp1(64),
                     enablehiatmp120(128),
                     enablehiatmp121(256),
                     enablehimcast(512),
                     enablehiall(1023)
                 }
        ACCESS   read-write
        STATUS   mandatory
        DESCRIPTION
                "Debug mode parameter enables reading and process of hi
                 priority outbound queues. The queue enable is a bit
                 mask [9:0] and is described as the following

                      Enable CAP1      0x00000001
                      Enable CAP2      0x00000002
                      Enable CAP3      0x00000004
                      Enable CAP4      0x00000008
                      Enable CAP5      0x00000010
                      Enable SSP0      0x00000020
                      Enable SSP1      0x00000040
                      Enable Atm0      0x00000080
                      Enable Atm1      0x00000100
                      Enable Mcast     0x00000200

                 Multiple queues can be enabled by oring the selected
                 bits together"
        DEFVAL  { enablehiall }
        ::= { wfIfpDrvCfgEntry 4 }

    wfIfpDrvCfgLoPriQueRdEnable OBJECT-TYPE
        SYNTAX   INTEGER {
                     enablelocap1(1),
                     enablelocap2(2),
                     enablelocap3(4),
                     enablelocap4(8),
                     enablelocap5(16),
                     enablelossp0(32),
                     enablelossp1(64),
                     enableloatm0(128),
                     enableloatm1(256),
                     enablelomcast(512),
                     enableloall(1023)  
                 }
        ACCESS   read-write
        STATUS   mandatory
        DESCRIPTION
                "Debug mode parameter enables reading and process of lo
                 priority outbound queues. The queue enable is a bit
                 mask [9:0] and is described as the following

                      Enable CAP1    0x00000001
                      Enable CAP2    0x00000002
                      Enable CAP3    0x00000004
                      Enable CAP4    0x00000008
                      Enable CAP5    0x00000010
                      Enable SSP0    0x00000020
                      Enable SSP1    0x00000040
                      Enable Atm0    0x00000080
                      Enable Atm1    0x00000100
                      Enable Mcast   0x00000200

                 Multiple queues can be enabled by oring the selected
                 bits together"
        DEFVAL { enableloall }
        ::= { wfIfpDrvCfgEntry 5   }

    wfIfpDrvCfgPortDrainEnable OBJECT-TYPE
        SYNTAX   INTEGER {
                     enabledraincap1(1),
                     enabledraincap2(2),
                     enabledraincap3(4),
                     enabledraincap4(8),
                     enabledraincap5(16),
                     enabledrainssp0(32),
                     enabledrainssp1(64),
                     enabledrainatm0(128),
                     enabledrainatm1(256),
                     enabledrainmcast(512),
                     enabledrainalll(1023)
                 }
        ACCESS   read-write
        STATUS   mandatory
        DESCRIPTION
                "Debug mode parameter enables the draining of outbound
                 queues for a given port without sending data to the
                 linecard. 1 bit per output port.

                      Enable drain CAP1     0x00000001
                      Enable drain CAP2     0x00000002
                      Enable drain CAP3     0x00000004
                      Enable drain CAP4     0x00000008
                      Enable drain CAP5     0x00000010
                      Enable drain SSP0     0x00000020
                      Enable drain SSP1     0x00000040
                      Enable drain Atm0     0x00000080
                      Enable drain Atm1     0x00000100

                 Multiple queues can be enabled by oring the selected
                 bits together"
        ::= { wfIfpDrvCfgEntry 6 }

    wfIfpDrvCfgSspPktTypeI OBJECT-TYPE
        SYNTAX   INTEGER(0..65536)
        ACCESS   read-write
        STATUS   mandatory
        DESCRIPTION
                "  "
        DEFVAL  { 33 }
         ::= { wfIfpDrvCfgEntry 7 }


    wfIfpDrvCfgSspPktTypeII OBJECT-TYPE
        SYNTAX   INTEGER(0..65536)
        ACCESS   read-write
        STATUS   mandatory
        DESCRIPTION
                "  "
        ::= { wfIfpDrvCfgEntry 8 }


    wfIfpDrvCfgCap0PktTypeI OBJECT-TYPE
        SYNTAX   INTEGER(0..65536)
        ACCESS   read-write
        STATUS   mandatory
        DESCRIPTION
                "  "
        DEFVAL  { 33 }
        ::= { wfIfpDrvCfgEntry 9 }


    wfIfpDrvCfgCap0PktTypeII OBJECT-TYPE
        SYNTAX   INTEGER(0..65536)
        ACCESS   read-write
        STATUS   mandatory
        DESCRIPTION
                " "
        ::= { wfIfpDrvCfgEntry 10 }


    wfIfpDrvCfgCap1PktTypeI OBJECT-TYPE
        SYNTAX   INTEGER(0..65536)
        ACCESS   read-write
        STATUS   mandatory
        DESCRIPTION
                " "
        DEFVAL  { 33 }
        ::= { wfIfpDrvCfgEntry 11 }


    wfIfpDrvCfgCap1PktTypeII OBJECT-TYPE
        SYNTAX   INTEGER(0..65536)
        ACCESS   read-write
        STATUS   mandatory
        DESCRIPTION
                " "
        ::= { wfIfpDrvCfgEntry 12 }


    wfIfpDrvCfgAtmPktTypeI  OBJECT-TYPE
        SYNTAX   INTEGER(0..65536)
        ACCESS   read-write
        STATUS   mandatory
        DESCRIPTION
                "   "
        DEFVAL  { 2048 }
        ::= { wfIfpDrvCfgEntry 13 }


    wfIfpDrvCfgAtmPktTypeII  OBJECT-TYPE
        SYNTAX   INTEGER(0..65536)
        ACCESS   read-write
        STATUS   mandatory
        DESCRIPTION
                "   "
        DEFVAL  { 34525 }
        ::= { wfIfpDrvCfgEntry 14 }


    wfIfpDrvCfgMax2kBufferCnt OBJECT-TYPE
        SYNTAX   INTEGER(0..65536)
        ACCESS   read-write
        STATUS   mandatory
        DESCRIPTION
                "Number of 2Kbyte buffers to carve from Buffer Memory"
        DEFVAL  { 1536 }
        ::= { wfIfpDrvCfgEntry 15 }

    wfIfpDrvCfgMax8kBufferCnt OBJECT-TYPE
        SYNTAX   INTEGER(0..65536)
        ACCESS   read-write
        STATUS   mandatory
        DESCRIPTION
                "Number of 8Kbyte buffers to carve from buffer memory"
        DEFVAL  { 128 }
        ::= { wfIfpDrvCfgEntry 16 }

    wfIfpDrvCfgBufferOffset OBJECT-TYPE
        SYNTAX   INTEGER(0..1024)
        ACCESS   read-write
        STATUS   mandatory
        DESCRIPTION
                "Buffer offset in bytes, where forwarding engine begins
                 to process received frames"
        DEFVAL  { 32 }
        ::= { wfIfpDrvCfgEntry 17 }

    wfIfpDrvCfgCapHiPriQueClip OBJECT-TYPE
        SYNTAX   INTEGER(1..1023)
        ACCESS   read-write
        STATUS   mandatory
        DESCRIPTION
                "The queue clip threshold for all high priority outbound
                 queues destined for channelized access slots"
        DEFVAL  { 1023 }
        ::= { wfIfpDrvCfgEntry 18 }

    wfIfpDrvCfgCapLoPriQueClip OBJECT-TYPE
        SYNTAX   INTEGER(1..1023)
        ACCESS   read-write
        STATUS   mandatory
        DESCRIPTION
                "The queue clip threshold for all low priority outbound
                 queues destined for channelized access slots"
        DEFVAL  { 1023 }
        ::= { wfIfpDrvCfgEntry 19 }

    wfIfpDrvCfgAtmHiPriQueClip OBJECT-TYPE
        SYNTAX   INTEGER(1..1023)
        ACCESS   read-write
        STATUS   mandatory
        DESCRIPTION
                "The queue clip threshold for all high priority outbound
                 queues destined for ATM OC-12 slots"
        DEFVAL  { 1023 }
        ::= { wfIfpDrvCfgEntry 20 }

    wfIfpDrvCfgAtmLoPriQueClip OBJECT-TYPE
        SYNTAX   INTEGER(1..1023)
        ACCESS   read-write
        STATUS   mandatory
        DESCRIPTION
                "The queue clip threshold for all low priority outbound
                 queues destined for ATM OC-12 slots"
         DEFVAL  { 1023 }
        ::= { wfIfpDrvCfgEntry 21 }

    wfIfpDrvCfgSspHiPriQueClip OBJECT-TYPE
        SYNTAX   INTEGER(1..1023)
        ACCESS   read-write
        STATUS   mandatory
        DESCRIPTION
                "The queue clip threshold for all high priority outbound
                 queues destined for system service processor slots"
        DEFVAL  { 1023 }
        ::= { wfIfpDrvCfgEntry 22 }

    wfIfpDrvCfgSspLoPriQueClip OBJECT-TYPE
        SYNTAX   INTEGER(1..1023)
        ACCESS   read-write
        STATUS   mandatory
        DESCRIPTION
                "The queue clip threshold for all low priority outbound
                 queues destined for system service processor slots"
        DEFVAL  { 1023 }
        ::= { wfIfpDrvCfgEntry 23 }

    wfIfpDrvCfgMcastHiPriClip OBJECT-TYPE
        SYNTAX   INTEGER(1..2047)
        ACCESS   read-write
        STATUS   mandatory
        DESCRIPTION
                "The queue clip threshold for all high priority outbound
                 multicast traffic"
        DEFVAL  { 2047 }
        ::= { wfIfpDrvCfgEntry 24 }

    wfIfpDrvCfgMcastLoPriClip OBJECT-TYPE
        SYNTAX   INTEGER(1..2047)
        ACCESS   read-write
        STATUS   mandatory
        DESCRIPTION
                "The queue clip threshold for all low priority outbound
                 multicast traffic"
        DEFVAL  { 2047 }
        ::= { wfIfpDrvCfgEntry 25 }

    wfIfpDrvCfgRspActiveStreamMask OBJECT-TYPE
        SYNTAX   INTEGER
        ACCESS   read-write
        STATUS   mandatory
        DESCRIPTION
                "Bitmask 1 to 31, each bit representing a RSP instruction
                 stream. If a bit is set the corresponding RSP stream is
                 started"
        DEFVAL  { -1 }
        ::= { wfIfpDrvCfgEntry 26 }

    wfIfpDrvCfgToSspLoPriInterval OBJECT-TYPE
        SYNTAX   INTEGER (10..1000)
        ACCESS   read-write
        STATUS   mandatory
        DESCRIPTION
                "Interval (msec) for Rate control of Lo Priority Packets 
                 destined for the SSP. Maximim of wfIfpDrvCfgToSspLoPriPktCnt 
                 packets transmitted to SSP during the interval"
        DEFVAL  { 10 }
        ::= { wfIfpDrvCfgEntry 27 }

    wfIfpDrvCfgToSspLoPriPktCnt OBJECT-TYPE
        SYNTAX   INTEGER (10..1000)
        ACCESS   read-write
        STATUS   mandatory
        DESCRIPTION
                "Maximum number of packets sent to the SSP during the 
                 wfIfpDrvCfgToSspLoPriInterval Rate control interval"
        DEFVAL  { 100 }
        ::= { wfIfpDrvCfgEntry 28 }


    wfIfpStatsTable OBJECT-TYPE
        SYNTAX   SEQUENCE OF WfIfpStatsEntry
        ACCESS   not-accessible
        STATUS   mandatory
        DESCRIPTION
                "Internet Fowarding Processor(IFP) Statistics Record"
        ::= { wfIfpGroup 2 }

    wfIfpStatsEntry  OBJECT-TYPE
        SYNTAX   WfIfpStatsEntry
        ACCESS   not-accessible
        STATUS   mandatory
        DESCRIPTION
                "Information about a particular driver"
        INDEX    { wfIfpStatsSlot }
        ::= { wfIfpStatsTable 1 }

    WfIfpStatsEntry ::= SEQUENCE {
         wfIfpStatsSlot
             INTEGER,
         wfIfpStatsCap0HiPriQueDepth
             Counter,
         wfIfpStatsCap0LoPriQueDepth
             Counter,
         wfIfpStatsCap1HiPriQueDepth
             Counter,
         wfIfpStatsCap1LoPriQueDepth
             Counter,
         wfIfpStatsCap2HiPriQueDepth
             Counter,
         wfIfpStatsCap2LoPriQueDepth
             Counter,
         wfIfpStatsCap3HiPriQueDepth
             Counter,
         wfIfpStatsCap3LoPriQueDepth
             Counter,
         wfIfpStatsCap4HiPriQueDepth
             Counter,
         wfIfpStatsCap4LoPriQueDepth
             Counter,
         wfIfpStatsAtm0HiPriQueDepth
             Counter,
         wfIfpStatsAtm0LoPriQueDepth
             Counter,
         wfIfpStatsAtm1HiPriQueDepth
             Counter,
         wfIfpStatsAtm1LoPriQueDepth
             Counter,
         wfIfpStatsSsp0HiPriQueDepth
             Counter,
         wfIfpStatsSsp0LoPriQueDepth
             Counter,
         wfIfpStatsSsp1HiPriQueDepth
             Counter,
         wfIfpStatsSsp1LoPriQueDepth
             Counter,
         wfIfpStatsMcastHiPriQueDepth
             Counter,
         wfIfpStatsMcastLoPriQueDepth
             Counter,
         wfIfpStatsCap0HiPriQueClips
             Counter,
         wfIfpStatsCap0LoPriQueClips
             Counter,
         wfIfpStatsCap1HiPriQueClips
             Counter,
         wfIfpStatsCap1LoPriQueClips
             Counter,
         wfIfpStatsCap2HiPriQueClips
             Counter,
         wfIfpStatsCap2LoPriQueClips
             Counter,
         wfIfpStatsCap3HiPriQueClips
             Counter,
         wfIfpStatsCap3LoPriQueClips
             Counter,
         wfIfpStatsCap4HiPriQueClips
             Counter,
         wfIfpStatsCap4LoPriQueClips
             Counter,
         wfIfpStatsAtm0HiPriQueClips
             Counter,
         wfIfpStatsAtm0LoPriQueClips
             Counter,
         wfIfpStatsAtm1HiPriQueClips
             Counter,
         wfIfpStatsAtm1LoPriQueClips
             Counter,
         wfIfpStatsSsp0HiPriQueClips
             Counter,
         wfIfpStatsSsp0LoPriQueClips
             Counter,
         wfIfpStatsSsp1HiPriQueClips
             Counter,
         wfIfpStatsSsp1LoPriQueClips
             Counter,
         wfIfpStatsMcastHiPriQueClips
             Counter,
         wfIfpStatsMcastLoPriQueClips
             Counter,
         wfIfpStatsSspLoPriDrops
             Counter,
         wfIfpStatsRecvCrcErrors
             Counter,
         wfIfpStatsBuf2kStackPtr
             Counter,
         wfIfpStatsBuf8kStackPtr
             Counter,
         wfIfpStatsBuf2kStackLimit
             Counter,
         wfIfpStatsBuf8kStackLimit
             Counter,
         wfIfpStatsRspState
             INTEGER,
         wfIfpStatsRspActiveStreamMask
             INTEGER,
         wfIfpStatsBadDesc
             Counter,
         wfIfpStatsDispatchMiss
             Counter,
         wfIfpStatsSspDeliversHi
             Counter,
         wfIfpStatsSspDeliversLo
             Counter,
         wfIfpStatsSspIpDeliversHi
             Counter,
         wfIfpStatsSspIpDeliversLo
             Counter,
         wfIfpStatsIpBlackHoleDrops
             Counter,
         wfIfpStatsRspBypassSent
             Counter,
         wfIfpStatsDpiBoflsSent
             Counter,
         wfIfpStatsSspRspQosTx
             Counter,
         wfIfpStatsSspRspBcastQosTx
             Counter,
         wfIfpStatsCongCtrlClips
             Counter,
         wfIfpStatsCap0CrcInterrupts
             Counter,
         wfIfpStatsSspCrcInterrupts
             Counter,
         wfIfpStatsCap1CrcInterrupts
             Counter,
         wfIfpStatsTpCrcInterrupts
             Counter,
         wfIfpStatsMaxEofInterrupts
             Counter,
         wfIfpStats2kFlowControlInd
             Counter,
         wfIfpStats8kFlowControlInd
             Counter,
         wfIfpStatsPrimInputSlotMask
             Gauge,
         wfIfpStatsSecInputSlotMask
             Gauge,
         wfIfpStatsSspLongFlowCtrl
             Counter,
         wfIfpStatsToSspRateCtrlClips
             Counter
    }

    wfIfpStatsSlot OBJECT-TYPE
        SYNTAX   INTEGER(1..12)
        ACCESS   read-only
        STATUS   mandatory
        DESCRIPTION
                "The slot number of the Internet Fowarding Processor
                 which is the instance id of the statistics record."
        ::= { wfIfpStatsEntry 1 }

    wfIfpStatsCap0HiPriQueDepth OBJECT-TYPE
        SYNTAX   Counter
        ACCESS   read-only
        STATUS   mandatory
        DESCRIPTION
                "The instantaneous queue depth, as measured in
                 descriptors, of the access port zero high priority
                 queue"
       ::= { wfIfpStatsEntry 2 }

    wfIfpStatsCap0LoPriQueDepth OBJECT-TYPE
        SYNTAX   Counter
        ACCESS   read-only
        STATUS   mandatory
        DESCRIPTION
                "The instantaneous queue depth, as measured in
                 descriptors, of the access port zero low priority
                 queue"
       ::= { wfIfpStatsEntry 3 }

    wfIfpStatsCap1HiPriQueDepth OBJECT-TYPE
        SYNTAX   Counter
        ACCESS   read-only
        STATUS   mandatory
        DESCRIPTION
                "The instantaneous queue depth, as measured in
                 descriptors, of the access port one high priority
                 queue"
       ::= { wfIfpStatsEntry 4 }

    wfIfpStatsCap1LoPriQueDepth OBJECT-TYPE
        SYNTAX   Counter
        ACCESS   read-only
        STATUS   mandatory
        DESCRIPTION
                "The instantaneous queue depth, as measured in
                 descriptors, of the access port one low priority
                 queue"
       ::= { wfIfpStatsEntry 5 }

    wfIfpStatsCap2HiPriQueDepth OBJECT-TYPE
        SYNTAX   Counter
        ACCESS   read-only
        STATUS   mandatory
        DESCRIPTION
                "The instantaneous queue depth, as measured in
                 descriptors, of the access port two high priority
                 queue"
       ::= { wfIfpStatsEntry 6 }

    wfIfpStatsCap2LoPriQueDepth OBJECT-TYPE
        SYNTAX   Counter
        ACCESS   read-only
        STATUS   mandatory
        DESCRIPTION
                "The instantaneous queue depth, as measured in
                 descriptors, of the access port two low priority
                 queue"
       ::= { wfIfpStatsEntry 7 }

    wfIfpStatsCap3HiPriQueDepth OBJECT-TYPE
        SYNTAX   Counter
        ACCESS   read-only
        STATUS   mandatory
        DESCRIPTION
                "The instantaneous queue depth, as measured in
                 descriptors, of the access port three high priority
                 queue"
       ::= { wfIfpStatsEntry 8 }

    wfIfpStatsCap3LoPriQueDepth OBJECT-TYPE
        SYNTAX   Counter
        ACCESS   read-only
        STATUS   mandatory
        DESCRIPTION
                "The instantaneous queue depth, as measured in
                 descriptors, of the access port three low priority
                 queue"
       ::= { wfIfpStatsEntry 9 }


    wfIfpStatsCap4HiPriQueDepth OBJECT-TYPE
        SYNTAX   Counter
        ACCESS   read-only
        STATUS   mandatory
        DESCRIPTION
                "The instantaneous queue depth, as measured in
                 descriptors, of the access port four high priority
                 queue"
       ::= { wfIfpStatsEntry 10 }

    wfIfpStatsCap4LoPriQueDepth OBJECT-TYPE
        SYNTAX   Counter
        ACCESS   read-only
        STATUS   mandatory
        DESCRIPTION
                "The instantaneous queue depth, as measured in
                 descriptors, of the access port four low priority
                 queue"
       ::= { wfIfpStatsEntry 11 }

    wfIfpStatsAtm0HiPriQueDepth OBJECT-TYPE
        SYNTAX   Counter
        ACCESS   read-only
        STATUS   mandatory
        DESCRIPTION
                "The instantaneous queue depth, as measured in
                 descriptors, of trunk port zero high priority
                 queue"
       ::= { wfIfpStatsEntry 12 }

    wfIfpStatsAtm0LoPriQueDepth OBJECT-TYPE
        SYNTAX   Counter
        ACCESS   read-only
        STATUS   mandatory
        DESCRIPTION
                "The instantaneous queue depth, as measured in
                 descriptors, of the trunk port zero low priority
                 queue"
       ::= { wfIfpStatsEntry 13 }

    wfIfpStatsAtm1HiPriQueDepth OBJECT-TYPE
        SYNTAX   Counter
        ACCESS   read-only
        STATUS   mandatory
        DESCRIPTION
                "The instantaneous queue depth, as measured in
                 descriptors, of trunk port one high priority
                 queue"
       ::= { wfIfpStatsEntry 14 }

    wfIfpStatsAtm1LoPriQueDepth OBJECT-TYPE
        SYNTAX   Counter
        ACCESS   read-only
        STATUS   mandatory
        DESCRIPTION
                "The instantaneous queue depth, as measured in
                 descriptors, of the trunk port one low priority
                 queue"
       ::= { wfIfpStatsEntry 15 }

    wfIfpStatsSsp0HiPriQueDepth OBJECT-TYPE
        SYNTAX   Counter
        ACCESS   read-only
        STATUS   mandatory
        DESCRIPTION
                "The instantaneous queue depth, as measured in
                 descriptors, of SSP port zero high priority
                 queue"
       ::= { wfIfpStatsEntry 16 }

    wfIfpStatsSsp0LoPriQueDepth OBJECT-TYPE
        SYNTAX   Counter
        ACCESS   read-only
        STATUS   mandatory
        DESCRIPTION
                "The instantaneous queue depth, as measured in
                 descriptors, of SSP port zero low priority
                 queue"
       ::= { wfIfpStatsEntry 17 }

    wfIfpStatsSsp1HiPriQueDepth OBJECT-TYPE
        SYNTAX   Counter
        ACCESS   read-only
        STATUS   mandatory
        DESCRIPTION
                "The instantaneous queue depth, as measured in
                 descriptors, of SSP port one high priority
                 queue"
       ::= { wfIfpStatsEntry 18 }

    wfIfpStatsSsp1LoPriQueDepth OBJECT-TYPE
        SYNTAX   Counter
        ACCESS   read-only
        STATUS   mandatory
        DESCRIPTION
                "The instantaneous queue depth, as measured in
                 descriptors, of SSP port one low priority
                 queue"
        ::= { wfIfpStatsEntry 19 }

    wfIfpStatsMcastHiPriQueDepth OBJECT-TYPE
        SYNTAX   Counter
        ACCESS   read-only
        STATUS   mandatory
        DESCRIPTION
                "The instantaneous queue depth, as measured in
                 descriptors, of the multicast high priority
                 queue"
        ::= { wfIfpStatsEntry 20 }

    wfIfpStatsMcastLoPriQueDepth OBJECT-TYPE
        SYNTAX   Counter
        ACCESS   read-only
        STATUS   mandatory
        DESCRIPTION
                "The instantaneous queue depth, as measured in
                 descriptors, of the multicast low priority
                 queue"
        ::= { wfIfpStatsEntry 21 }

    wfIfpStatsCap0HiPriQueClips OBJECT-TYPE
        SYNTAX   Counter
        ACCESS   read-only
        STATUS   mandatory
        DESCRIPTION
                "The number of descriptors clipped because the
                 clip threshold was execeeded for the access port zero
                 high priority queue."
        ::= { wfIfpStatsEntry 22 }

    wfIfpStatsCap0LoPriQueClips OBJECT-TYPE
        SYNTAX   Counter
        ACCESS   read-only
        STATUS   mandatory
        DESCRIPTION
                "The number of descriptors clipped because the
                 clip threshold was execeeded for the access port zero
                 low priority queue."
        ::= { wfIfpStatsEntry 23 }

    wfIfpStatsCap1HiPriQueClips OBJECT-TYPE
        SYNTAX   Counter
        ACCESS   read-only
        STATUS   mandatory
        DESCRIPTION
                "The number of descriptors clipped because the
                 clip threshold was execeeded for the access port one
                 high priority queue."
        ::= { wfIfpStatsEntry 24 }

    wfIfpStatsCap1LoPriQueClips OBJECT-TYPE
        SYNTAX   Counter
        ACCESS   read-only
        STATUS   mandatory
        DESCRIPTION
                "The number of descriptors clipped because the
                 clip threshold was execeeded for the access port one
                 low priority queue."
        ::= { wfIfpStatsEntry 25 }

    wfIfpStatsCap2HiPriQueClips OBJECT-TYPE
        SYNTAX   Counter
        ACCESS   read-only
        STATUS   mandatory
        DESCRIPTION
                "The number of descriptors clipped because the
                 clip threshold was execeeded for the access port two
                 high priority queue."
        ::= { wfIfpStatsEntry 26 }

    wfIfpStatsCap2LoPriQueClips OBJECT-TYPE
        SYNTAX   Counter
        ACCESS   read-only
        STATUS   mandatory
        DESCRIPTION
                "The number of descriptors clipped because the
                 clip threshold was execeeded for the access port two
                 low priority queue."
        ::= { wfIfpStatsEntry 27 }

    wfIfpStatsCap3HiPriQueClips OBJECT-TYPE
        SYNTAX   Counter
        ACCESS   read-only
        STATUS   mandatory
        DESCRIPTION
                "The number of descriptors clipped because the
                 clip threshold was execeeded for the access port three
                 high priority queue."
        ::= { wfIfpStatsEntry 28 }

    wfIfpStatsCap3LoPriQueClips OBJECT-TYPE
        SYNTAX   Counter
        ACCESS   read-only
        STATUS   mandatory
        DESCRIPTION
                "The number of descriptors clipped because the
                 clip threshold was execeeded for the access port three
                 low priority queue."
        ::= { wfIfpStatsEntry 29 }

    wfIfpStatsCap4HiPriQueClips OBJECT-TYPE
        SYNTAX   Counter
        ACCESS   read-only
        STATUS   mandatory
        DESCRIPTION
                "The number of descriptors clipped because the
                 clip threshold was execeeded for the access port four
                 high priority queue."
        ::= { wfIfpStatsEntry 30 }

    wfIfpStatsCap4LoPriQueClips OBJECT-TYPE
        SYNTAX   Counter
        ACCESS   read-only
        STATUS   mandatory
        DESCRIPTION
                "The number of descriptors clipped because the
                 clip threshold was execeeded for the access port four
                 low priority queue."
        ::= { wfIfpStatsEntry 31 }

    wfIfpStatsAtm0HiPriQueClips OBJECT-TYPE
        SYNTAX   Counter
        ACCESS   read-only
        STATUS   mandatory
        DESCRIPTION
                "The number of descriptors clipped because the
                 clip threshold was execeeded for the trunk port
                 zero high priority queue."
        ::= { wfIfpStatsEntry 32 }

    wfIfpStatsAtm0LoPriQueClips OBJECT-TYPE
        SYNTAX   Counter
        ACCESS   read-only
        STATUS   mandatory
        DESCRIPTION
                "The number of descriptors clipped because the
                 clip threshold was execeeded for the trunk port
                 zero low priority queue."
       ::= { wfIfpStatsEntry 33 }

    wfIfpStatsAtm1HiPriQueClips OBJECT-TYPE
        SYNTAX   Counter
        ACCESS   read-only
        STATUS   mandatory
        DESCRIPTION
                "The number of descriptors clipped because the
                 clip threshold was execeeded for the trunk port
                 one high priority queue."
        ::= { wfIfpStatsEntry 34 }

    wfIfpStatsAtm1LoPriQueClips OBJECT-TYPE
        SYNTAX   Counter
        ACCESS   read-only
        STATUS   mandatory
        DESCRIPTION
                "The number of descriptors clipped because the
                 clip threshold was execeeded for the trunk port
                 one low priority queue."
       ::= { wfIfpStatsEntry 35 }

    wfIfpStatsSsp0HiPriQueClips OBJECT-TYPE
        SYNTAX   Counter
        ACCESS   read-only
        STATUS   mandatory
        DESCRIPTION
                "The number of descriptors clipped because the
                 clip threshold was execeeded for the SSP port zero
                 high priority queue."
       ::= { wfIfpStatsEntry 36 }

    wfIfpStatsSsp0LoPriQueClips OBJECT-TYPE
        SYNTAX   Counter
        ACCESS   read-only
        STATUS   mandatory
        DESCRIPTION
                "The number of descriptors clipped because the
                 clip threshold was execeeded for the SSP port zero
                 low priority queue."
        ::= { wfIfpStatsEntry 37 }

    wfIfpStatsSsp1HiPriQueClips OBJECT-TYPE
        SYNTAX   Counter
        ACCESS   read-only
        STATUS   mandatory
        DESCRIPTION
                "The number of descriptors clipped because the
                 clip threshold was execeeded for the SSP port one
                 high priority queue."
       ::= { wfIfpStatsEntry 38 }

    wfIfpStatsSsp1LoPriQueClips OBJECT-TYPE
        SYNTAX   Counter
        ACCESS   read-only
        STATUS   mandatory
        DESCRIPTION
                "The number of descriptors clipped because the
                 clip threshold was execeeded for the SSP port one
                 low priority queue."
       ::= { wfIfpStatsEntry 39 }

    wfIfpStatsMcastHiPriQueClips OBJECT-TYPE
        SYNTAX   Counter
        ACCESS   read-only
        STATUS   mandatory
        DESCRIPTION
                "The number of descriptors clipped because the
                 clip threshold was execeeded for the multicast
                 low priority queue."
       ::= { wfIfpStatsEntry 40 }

    wfIfpStatsMcastLoPriQueClips OBJECT-TYPE
        SYNTAX   Counter
        ACCESS   read-only
        STATUS   mandatory
        DESCRIPTION
                "The number of descriptors clipped because the
                 clip threshold was execeeded for the multicast
                 low priority queue."
       ::= { wfIfpStatsEntry 41 }

    wfIfpStatsSspLoPriDrops OBJECT-TYPE
        SYNTAX   Counter
        ACCESS   read-only
        STATUS   mandatory
        DESCRIPTION
                "The number of descriptors clipped because the
                 clip threshold was execeeded for the SSP port one
                 low priority queue."
       ::= { wfIfpStatsEntry 42 }

    wfIfpStatsRecvCrcErrors OBJECT-TYPE
        SYNTAX   Counter
        ACCESS   read-only
        STATUS   mandatory
        DESCRIPTION
                "The number of CRC errors detected on incomming packets
                 from all ports CAP0,CAP1,ATMP12 & all SSP paths"
       ::= { wfIfpStatsEntry 43 }

    wfIfpStatsBuf2kStackPtr OBJECT-TYPE
        SYNTAX   Counter
        ACCESS   read-only
        STATUS   mandatory
        DESCRIPTION
                "The 2Kbyte buffer pool stack pointer, indicating how many
                 2Kbyte buffers are presently available"
       ::= { wfIfpStatsEntry 44 }

    wfIfpStatsBuf8kStackPtr OBJECT-TYPE
        SYNTAX   Counter
        ACCESS   read-only
        STATUS   mandatory
        DESCRIPTION
                "The 8Kbyte buffer pool stack pointer, indicating how many
                 8Kbyte buffers are presently available"
       ::= { wfIfpStatsEntry 45 }

    wfIfpStatsBuf2kStackLimit OBJECT-TYPE
        SYNTAX   Counter
        ACCESS   read-only
        STATUS   mandatory
        DESCRIPTION
                "The 2Kbyte buffer pool stack limit, indicating the
                 maximum number of 2Kbyte buffers available for this pool"
       ::= { wfIfpStatsEntry 46 }

    wfIfpStatsBuf8kStackLimit OBJECT-TYPE
        SYNTAX   Counter
        ACCESS   read-only
        STATUS   mandatory
        DESCRIPTION
                "The 8Kbyte buffer pool stack limit, indicating the
                 maximum number of 8Kbyte buffers available for this pool"
        ::= { wfIfpStatsEntry 47 }

    wfIfpStatsRspState OBJECT-TYPE
        SYNTAX   INTEGER {
                 down(4),
                 nofwd(3),
                 init(2),
                 up(1) 
        }
        ACCESS   read-only
        STATUS   mandatory
        DESCRIPTION
                 " Reflects the actual state of the RSP forwarding engine
                   0:dead, 1:Up, 2:init, -1:fwd streams down"
        ::= { wfIfpStatsEntry 48 }

    wfIfpStatsRspActiveStreamMask OBJECT-TYPE
        SYNTAX   INTEGER
        ACCESS   read-only
        STATUS   mandatory
        DESCRIPTION
                 " Bit mask of active RSP instruction streams. Each bit
                   set to a one indicates the stream is active"
        ::= { wfIfpStatsEntry 49 }

    wfIfpStatsBadDesc OBJECT-TYPE
        SYNTAX   Counter
        ACCESS   read-only
        STATUS   mandatory
        DESCRIPTION
                 " Number of packets read by the RSP with the error
                   bit set which are dropped"
        ::= { wfIfpStatsEntry 50 }

    wfIfpStatsDispatchMiss OBJECT-TYPE
        SYNTAX   Counter
        ACCESS   read-only
        STATUS   mandatory
        DESCRIPTION
                 " Number of packets received, which miss the fowarding
                   dispatch table lookup and are dropped"
        ::= { wfIfpStatsEntry 51 }

    wfIfpStatsSspDeliversHi OBJECT-TYPE
        SYNTAX   Counter
        ACCESS   read-only
        STATUS   mandatory
        DESCRIPTION
                 " Number of packets received, which are sent to the SSP
                   for processing - Hi Priority"
        ::= { wfIfpStatsEntry 52 }

    wfIfpStatsSspDeliversLo OBJECT-TYPE
        SYNTAX   Counter
        ACCESS   read-only
        STATUS   mandatory
        DESCRIPTION
                 " Number of packets received, which are sent to the SSP
                   for processing - Lo Priority"
        ::= { wfIfpStatsEntry 53 }

    wfIfpStatsSspIpDeliversHi OBJECT-TYPE
        SYNTAX   Counter
        ACCESS   read-only
        STATUS   mandatory
        DESCRIPTION
                 " Number of IP packets recieved, which are sent to the SSP
                   for further processing - Hi Priority"
        ::= { wfIfpStatsEntry 54 }

    wfIfpStatsSspIpDeliversLo OBJECT-TYPE
        SYNTAX   Counter
        ACCESS   read-only
        STATUS   mandatory
        DESCRIPTION
                 " Number of IP packets recieved, which are sent to the SSP
                   for further processing - Lo Priority"
        ::= { wfIfpStatsEntry 55 }

    wfIfpStatsIpBlackHoleDrops OBJECT-TYPE
        SYNTAX   Counter
        ACCESS   read-only
        STATUS   mandatory
        DESCRIPTION
                 " Total number of Packets Dropped as a result of the
 		   IP DA Lookup determining a next hop host that has
                   yet been resolved. "
        ::= { wfIfpStatsEntry 56 }

    wfIfpStatsRspBypassSent OBJECT-TYPE
        SYNTAX   Counter
        ACCESS   read-only
        STATUS   mandatory
        DESCRIPTION
                 " Number of outboud packets received which have the 
                   Bypass bit set in the descriptor (i.e. host originated
                   traffic)"
        ::= { wfIfpStatsEntry 57 }

    wfIfpStatsDpiBoflsSent OBJECT-TYPE
        SYNTAX   Counter
        ACCESS   read-only
        STATUS   mandatory
        DESCRIPTION
                 " Number of data path interconnect BOFL frames sent to the
                   SSP"
        ::= { wfIfpStatsEntry 58 }

    wfIfpStatsSspRspQosTx OBJECT-TYPE
        SYNTAX   Counter
        ACCESS   read-only
        STATUS   mandatory
        DESCRIPTION
                 " Number of SSP packets sent to RSP for delivery to the 
                   Network via the TX Qos Path"
        ::= { wfIfpStatsEntry 59 }

    wfIfpStatsSspRspBcastQosTx OBJECT-TYPE
        SYNTAX   Counter
        ACCESS   read-only
        STATUS   mandatory
        DESCRIPTION
                 " Number of SSP packets sent to RSP for Broadcast delivery 
                   to the Network via the TX Qos Path"
        ::= { wfIfpStatsEntry 60 }

    wfIfpStatsCongCtrlClips OBJECT-TYPE
        SYNTAX   Counter
        ACCESS   read-only
        STATUS   mandatory
        DESCRIPTION
                 " Total number of Packets Clipped by the Congestion Ctrl
                   clip mechanism on this IFP CXP."
        ::= { wfIfpStatsEntry 61 }

    wfIfpStatsCap0CrcInterrupts OBJECT-TYPE
        SYNTAX   Counter
        ACCESS   read-only
        STATUS   mandatory
        DESCRIPTION
                 " Number of CRC interrupt indications on CAP0 DPI port"
        ::= { wfIfpStatsEntry 62 }

    wfIfpStatsSspCrcInterrupts OBJECT-TYPE
        SYNTAX   Counter
        ACCESS   read-only
        STATUS   mandatory
        DESCRIPTION
                 " Number of CRC interrupt indications on SSP DPI port"
        ::= { wfIfpStatsEntry 63 }

    wfIfpStatsCap1CrcInterrupts OBJECT-TYPE
        SYNTAX   Counter
        ACCESS   read-only
        STATUS   mandatory
        DESCRIPTION
                 " Number of CRC interrupt indications on CAP1 DPI port"
        ::= { wfIfpStatsEntry 64 }

    wfIfpStatsTpCrcInterrupts OBJECT-TYPE
        SYNTAX   Counter
        ACCESS   read-only
        STATUS   mandatory
        DESCRIPTION
                 " Number of CRC interrupt indications on the Trunk
                   DPI port"
        ::= { wfIfpStatsEntry 65 }

    wfIfpStatsMaxEofInterrupts OBJECT-TYPE
        SYNTAX   Counter
        ACCESS   read-only
        STATUS   mandatory
        DESCRIPTION
                 " Total number of interrupt indications for frames 
                   received in excess of 7168 bytes"
        ::= { wfIfpStatsEntry 66 }

    wfIfpStats2kFlowControlInd OBJECT-TYPE
        SYNTAX   Counter
        ACCESS   read-only
        STATUS   mandatory
        DESCRIPTION
                 " Total number of flow control indications received for
                   the 2K buffer pool. This is essentially a count of the
                   number of times the 2K buffer pool was depleted."
        ::= { wfIfpStatsEntry 67 }

    wfIfpStats8kFlowControlInd OBJECT-TYPE
        SYNTAX   Counter
        ACCESS   read-only
        STATUS   mandatory
        DESCRIPTION
                 " Total number of flow control indications received for
                   the 8K buffer pool. This is essentially a count of the
                   number of times the 8K buffer pool was depleted."
        ::= { wfIfpStatsEntry 68 }

    wfIfpStatsPrimInputSlotMask OBJECT-TYPE
        SYNTAX   Gauge
        ACCESS   read-only
        STATUS   mandatory
        DESCRIPTION
                " Bit mask of primary input slots handled by this IFP driver."
        ::= { wfIfpStatsEntry 69 }

    wfIfpStatsSecInputSlotMask OBJECT-TYPE
        SYNTAX   Gauge
        ACCESS   read-only
        STATUS   mandatory
        DESCRIPTION
                " Bit mask of secondary input slots handled by this IFP driver."
        ::= { wfIfpStatsEntry 70 }

    wfIfpStatsSspLongFlowCtrl OBJECT-TYPE
        SYNTAX   Counter
        ACCESS   read-only
        STATUS   mandatory
        DESCRIPTION
                 " Total number of Indications that the SSP Flow Control 
                   has been set for an long period of time."
        ::= { wfIfpStatsEntry 71 }

    wfIfpStatsToSspRateCtrlClips OBJECT-TYPE
        SYNTAX   Counter
        ACCESS   read-only
        STATUS   mandatory
        DESCRIPTION
                 " Total number of SSP destined Lo Priority Packets Clipped 
                   by RSP ToSSP Rate Control." 
        ::= { wfIfpStatsEntry 72 }

    wfIfpDrvCongCfgTable OBJECT-TYPE
        SYNTAX   SEQUENCE OF WfIfpDrvCongCfgEntry
        ACCESS   not-accessible
        STATUS   mandatory
        DESCRIPTION
                 "Internet Forwarding Processor (IFP) Congestion Table."
        ::= { wfIfpGroup 3 }

    wfIfpDrvCongCfgEntry OBJECT-TYPE
        SYNTAX   WfIfpDrvCongCfgEntry
        ACCESS   not-accessible
        STATUS   mandatory
        DESCRIPTION
                 "An entry in the Congestion Table."
        INDEX    { wfIfpDrvCongCfgIndex }
        ::= { wfIfpDrvCongCfgTable 1 }

    WfIfpDrvCongCfgEntry ::= SEQUENCE {
        wfIfpDrvCongCfgDelete
            INTEGER,
        wfIfpDrvCongCfgIndex
            INTEGER,
        wfIfpDrvCongCfgInternServClass
            INTEGER,
        wfIfpDrvCongCfgDropPreference
            INTEGER,
        wfIfpDrvCongCfgWmDropThreshold
            INTEGER
    }

    wfIfpDrvCongCfgDelete OBJECT-TYPE
        SYNTAX  INTEGER {
                    create(1),
                    delete(2)
                }
        ACCESS  read-write
        STATUS  mandatory
        DESCRIPTION
                "Create/delete MIB instance parameter."
        DEFVAL  { create }
        ::= { wfIfpDrvCongCfgEntry 1 }

    wfIfpDrvCongCfgIndex OBJECT-TYPE
        SYNTAX   INTEGER(1..2147483647)
        ACCESS   read-only
        STATUS   mandatory
        DESCRIPTION
                 "Index of entry -- instance id."
        ::= { wfIfpDrvCongCfgEntry 2 }

    wfIfpDrvCongCfgInternServClass OBJECT-TYPE
        SYNTAX   INTEGER(0..7)
        ACCESS   read-write
        STATUS   mandatory
        DESCRIPTION
                 "Internal Service Class parameter."
        DEFVAL { 7 }
        ::= { wfIfpDrvCongCfgEntry 3 }

    wfIfpDrvCongCfgDropPreference OBJECT-TYPE
        SYNTAX   INTEGER(0..1)
        ACCESS   read-write
        STATUS   mandatory
        DESCRIPTION
                 "Drop Preference parameter."
        DEFVAL { 1 }
        ::= { wfIfpDrvCongCfgEntry 4 }

    wfIfpDrvCongCfgWmDropThreshold OBJECT-TYPE
        SYNTAX   INTEGER(0..7)
        ACCESS   read-write
        STATUS   mandatory
        DESCRIPTION
                 "Watermark Drop Threshold parameter. Entries will
                  be written to the internal congestion control
                  table for all watermark values between 0 and
                  wfIfpDrvCongCfgWmDropThreshold."
        DEFVAL { 0 }
        ::= { wfIfpDrvCongCfgEntry 5 } 
        

    END  -- Wellfleet-IFP-MIB
