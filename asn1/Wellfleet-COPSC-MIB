Wellfleet-COPSC-MIB DEFINITIONS ::= BEGIN

-- Created by mdl2asn version 3.1
-- Creation date: Wed Aug 30 16:47:08 EDT 1995


    IMPORTS

      IpAddress, Gauge
        FROM RFC1155-SMI
      OBJECT-TYPE
        FROM RFC-1212
      DisplayString
        FROM RFC1213-MIB
      wfCopsCGroup
        FROM Wellfleet-COMMON-MIB;

    wfCopsCBase         OBJECT IDENTIFIER ::= { wfCopsCGroup 1 }

    wfCopsCDelete OBJECT-TYPE
        SYNTAX	INTEGER {
    		    created(1),
    		    deleted(2)
    		}
        ACCESS	read-write
        STATUS	mandatory
        DESCRIPTION
                "Create/Delete parameter"
        DEFVAL	{ created }
        ::= { wfCopsCBase 1 }

    wfCopsCDisable OBJECT-TYPE
        SYNTAX	INTEGER {
    		    enabled(1),
    		    disabled(2)
    		}
        ACCESS	read-write
        STATUS	mandatory
        DESCRIPTION
                "Enable/Disable parameter"
        DEFVAL	{ enabled }
        ::= { wfCopsCBase 2 }

    wfCopsCState OBJECT-TYPE
        SYNTAX	INTEGER {
                    up(1),
                    localrecovery(2),
                    init(3),
                    down(4),
                    notpresent(5)
    		}
        ACCESS	read-only
        STATUS	mandatory
        DESCRIPTION
                "State parameter"
        DEFVAL	{ notpresent }
        ::= { wfCopsCBase 3 }

    wfCopsCCurrentSlotMask OBJECT-TYPE
        SYNTAX  Gauge
        ACCESS  read-only
        STATUS  mandatory
        DESCRIPTION
                "Slot mask indicating which slots COPS
                Client is currently up and running.
                The MSBit represents slot 1, the next most
                significant bit represents slot 2, and so on...
                Slots can be 1-14.  Default is all slots on a BCN."
        DEFVAL  { 0 }
        ::= { wfCopsCBase 4 }

    wfCopsCSoloSlot OBJECT-TYPE
        SYNTAX  INTEGER(1..14)
        ACCESS  read-only
        STATUS  mandatory
        DESCRIPTION
                "The current soloist slot."
        ::= { wfCopsCBase 5 }

    wfCopsCSoloSlotMask OBJECT-TYPE
        SYNTAX  Gauge
        ACCESS  read-write
        STATUS  mandatory
        DESCRIPTION
                "Slot mask for which slots soloist is eligible
                to run on.  The MSBit represents slot 1, the
                next most significant bit represents slot 2,
                and so on...  Slots can be 1-14.
                Default is all slots on a BCN."
        DEFVAL  { 4294705152 }
        ::= { wfCopsCBase 6 }

    wfCopsCDebugLogFilter OBJECT-TYPE
        SYNTAX  INTEGER
        ACCESS  read-write
        STATUS  mandatory
        DESCRIPTION
                "Turn logging ON or OFF for COPS Client
                 debugging messages. The bit position is used to
                 represent a COPS Client module:
                 CopsC_LOG_COPS_PROCESSING      0x0001 - COPS processing."
        DEFVAL { 0 }
        ::= { wfCopsCBase 7 }

    wfCopsCIPAddr OBJECT-TYPE
        SYNTAX	IpAddress
        ACCESS	read-write
        STATUS	mandatory
        DESCRIPTION
                "Client's IP Address."
        ::= { wfCopsCBase 8 }

    wfCopsCID OBJECT-TYPE
        SYNTAX	DisplayString
        ACCESS	read-write
        STATUS	mandatory
        DESCRIPTION
                "COPS Client's ID."
        ::= { wfCopsCBase 9 }



    wfCopsSvrTable OBJECT-TYPE
        SYNTAX	SEQUENCE OF WfCopsSvrEntry
        ACCESS	not-accessible
        STATUS	mandatory
        DESCRIPTION
                "This tabulates the COPS Servers to contact."
        ::= { wfCopsCGroup 2 }

    wfCopsSvrEntry OBJECT-TYPE
        SYNTAX	WfCopsSvrEntry
        ACCESS	not-accessible
        STATUS	mandatory
        DESCRIPTION
                "Entry summary."
        INDEX	{ wfCopsSvrIPAddr }
        ::= { wfCopsSvrTable 1 }

    WfCopsSvrEntry ::= SEQUENCE {
    	    wfCopsSvrDelete
    		INTEGER,
    	    wfCopsSvrDisable
    		INTEGER,
    	    wfCopsSvrIPAddr
    		IpAddress,
    	    wfCopsSvrPriority
    		INTEGER,
            wfCopsSvrConnState
                INTEGER,
    	    wfCopsSvrConnTimer
    		INTEGER,
    	    wfCopsSvrConnRetryCount
    		INTEGER,
    	    wfCopsSvrKeepAliveTimer
    		INTEGER,
    	    wfCopsSvrReportTimer
    		INTEGER,
    	    wfCopsSvrTCPKeepAliveInterval
    		INTEGER,
    	    wfCopsSvrTCPKeepAliveRetryTimeOut
    		INTEGER,
    	    wfCopsSvrTCPKeepAliveMaxRetryCount
    		INTEGER,
            wfCopsSvrRemotePort
		INTEGER
        }

    wfCopsSvrDelete OBJECT-TYPE
        SYNTAX	INTEGER {
    		    created(1),
    		    deleted(2)
    		}
        ACCESS	read-write
        STATUS	mandatory
        DESCRIPTION
                "Create/Delete parameter"
        DEFVAL	{ created }
        ::= { wfCopsSvrEntry 1 }

    wfCopsSvrDisable OBJECT-TYPE
        SYNTAX	INTEGER {
    		    enabled(1),
    		    disabled(2)
    		}
        ACCESS	read-write
        STATUS	mandatory
        DESCRIPTION
                "Enable/Disable parameter"
        DEFVAL	{ enabled }
        ::= { wfCopsSvrEntry 2 }

    wfCopsSvrIPAddr OBJECT-TYPE
        SYNTAX	IpAddress
        ACCESS	read-only
        STATUS	mandatory
        DESCRIPTION
                "Server's IP Address."
        ::= { wfCopsSvrEntry 3 }

    wfCopsSvrPriority OBJECT-TYPE
        SYNTAX	INTEGER
        ACCESS  read-write
        STATUS  mandatory
        DESCRIPTION
              "Priority for being the active server.  Higher value wins.  Server IP Address will be used as tie-breaker."
        DEFVAL  { 1 }
        ::= { wfCopsSvrEntry 4 }

    wfCopsSvrConnState OBJECT-TYPE
        SYNTAX  INTEGER {
                    serverready(1),
                    connnegotiation(2),
                    connrecovery(3),
                    servercontacted(4),
                    noconn(5)
                }
        ACCESS  read-only
        STATUS  mandatory
        DESCRIPTION
                "State of server connection."
        DEFVAL  { noconn }
        ::= { wfCopsSvrEntry 5 }

    wfCopsSvrConnTimer OBJECT-TYPE
        SYNTAX	INTEGER(1..65535)
        ACCESS	read-write
        STATUS	mandatory
        DESCRIPTION
                "Time period between connection retries, in seconds."
        DEFVAL	{ 30 }
        ::= { wfCopsSvrEntry 6 }

    wfCopsSvrConnRetryCount OBJECT-TYPE
        SYNTAX  INTEGER(1..10)
        ACCESS  read-write
        STATUS  mandatory
        DESCRIPTION
                "Connection attempt retry before giving up on server."
        DEFVAL  { 3 }
        ::= { wfCopsSvrEntry 7 }

    wfCopsSvrKeepAliveTimer OBJECT-TYPE
        SYNTAX	INTEGER(1..65535)
        ACCESS	read-write
        STATUS	mandatory
        DESCRIPTION
                "Time period between sending of Keep Alives, in seconds."
        DEFVAL	{ 60 }
        ::= { wfCopsSvrEntry 8 }

    wfCopsSvrReportTimer OBJECT-TYPE
        SYNTAX	INTEGER(1..65535)
        ACCESS	read-write
        STATUS	mandatory
        DESCRIPTION
                "Time period between sending of Reports, in seconds."
        DEFVAL	{ 360 }
        ::= { wfCopsSvrEntry 9 }

    wfCopsSvrTCPKeepAliveInterval OBJECT-TYPE
        SYNTAX	INTEGER(0..65535)
        ACCESS	read-write
        STATUS	mandatory
        DESCRIPTION
                "KeepAlive packets will be sent into inactive, established
                 TCP connections after this time interval (in seconds).
                 A time of zero disables this keepalive feature."
        DEFVAL	{ 60 }
        ::= { wfCopsSvrEntry 10 }

    wfCopsSvrTCPKeepAliveRetryTimeOut OBJECT-TYPE
        SYNTAX	INTEGER(0..65535)
        ACCESS	read-write
        STATUS	mandatory
        DESCRIPTION
                "TCP Keep Alive retransmit timeout period, in seconds.
                 This is the interval at which unacknowledged Keep Alive
                 messages will be retransmitted.  If the Interval Timer
                 is set to zero, this timer is ignored.  If the Interval
                 Timer is non-zero and this timer IS zero, no Keep Alives
                 are sent and the session is terminated upon expiration
                 of the Interval Timer."
        DEFVAL	{ 60 }
        ::= { wfCopsSvrEntry 11 }

    wfCopsSvrTCPKeepAliveMaxRetryCount OBJECT-TYPE
        SYNTAX	INTEGER(0..65535)
        ACCESS	read-write
        STATUS	mandatory
        DESCRIPTION
                "Number of unacknowledged Keep Alive messages retransmitted
                 before the TCP session is terminated.  If this count is set
                 to zero, only one Keep Alive message will be sent."
        DEFVAL	{ 4 }
        ::= { wfCopsSvrEntry 12 }

    wfCopsSvrRemotePort OBJECT-TYPE
        SYNTAX  INTEGER(1..65535)
        ACCESS  read-write
        STATUS  mandatory
        DESCRIPTION
                "Server's Remote TCP Port."
        DEFVAL  { 3288 }
        ::= { wfCopsSvrEntry 13 }

    END  -- Wellfleet-COPSC-MIB
