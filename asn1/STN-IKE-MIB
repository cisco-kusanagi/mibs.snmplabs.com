-- *****************************************************************
--
-- stn-ike.mib:  
--                Spring Tide Networks IKE MIB file.
--
--
--      Copyright (c) 1999, 2000 by Spring Tide Networks, Inc.
--                      ALL RIGHTS RESERVED       
--
-- *****************************************************************

-- MIB Object definitions for Spring Tide Network IKE 


STN-IKE-MIB DEFINITIONS ::= BEGIN

    IMPORTS
        MODULE-IDENTITY,
        OBJECT-TYPE,
        IpAddress,
        Integer32
                FROM SNMPv2-SMI

        TimeStamp
                FROM SNMPv2-TC

        MODULE-COMPLIANCE 
                FROM SNMPv2-CONF
        
        stnSystems
                FROM SPRING-TIDE-NETWORKS-SMI;


    stnIKE MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION
                "Initial version of this MIB module."
        ::= { stnSystems 8 }


    --
    -- Top Level STN IKE MIB Objects
    --
    stnIkeObjects           OBJECT IDENTIFIER ::= { stnIKE 1 }
    stnIkeMibConformance    OBJECT IDENTIFIER ::= { stnIKE 2 }

    stnIkePreferences       OBJECT IDENTIFIER ::= { stnIkeObjects 1 }
    stnIkeSharedSecrets     OBJECT IDENTIFIER ::= { stnIkeObjects 2 }
    stnIkeCertificates      OBJECT IDENTIFIER ::= { stnIkeObjects 3 }


    --
    -- STN IKE Preference Table
    --

    stnIkePreferenceTable OBJECT-TYPE
        SYNTAX        SEQUENCE OF StnIkePreferenceEntry
        MAX-ACCESS    not-accessible
        STATUS        current
        DESCRIPTION   "A list of IKE Preference entries."
        ::= { stnIkePreferences 1 }
 
    stnIkePreferenceEntry OBJECT-TYPE
        SYNTAX          StnIkePreferenceEntry
        MAX-ACCESS      not-accessible
        STATUS          current
        DESCRIPTION     "Entry contains information about a particular 
                        IKE preference."  
        INDEX           { stnIkePrefPeerAddress, stnIkePrefTransform }
        ::= { stnIkePreferenceTable 1 }
 
    StnIkePreferenceEntry ::= 
        SEQUENCE {
            stnIkePrefPeerAddress       IpAddress,
            stnIkePrefTransform         Integer32,
            stnIkePrefPeerPort          Integer32,
            stnIkePrefHash              INTEGER,
            stnIkePrefEncryption        INTEGER,
            stnIkePrefAuthentication    INTEGER,
            stnIkePrefDHGroup           Integer32,
            stnIkePrefMode              INTEGER,
            stnIkePrefLifeTime          TimeStamp,
            stnIkePrefLifeBytes         Integer32,
	        stnIkePrefCertAlias         OCTET STRING,
	        stnIkePrefServiceName       OCTET STRING
                }

    stnIkePrefPeerAddress OBJECT-TYPE
        SYNTAX          IpAddress
        MAX-ACCESS      read-only
        STATUS          current
        DESCRIPTION     "Remote IP address"
        ::= { stnIkePreferenceEntry 1 }

    stnIkePrefTransform OBJECT-TYPE
        SYNTAX          Integer32
        MAX-ACCESS      read-only
        STATUS          current
        DESCRIPTION     "Preference number"
        ::= { stnIkePreferenceEntry 2 }

    stnIkePrefPeerPort OBJECT-TYPE
        SYNTAX          Integer32
        MAX-ACCESS      read-only
        STATUS          current
        DESCRIPTION     "Remote UDP port number"
        DEFVAL          { 500 }
        ::= { stnIkePreferenceEntry 3 }

    stnIkePrefHash OBJECT-TYPE
        SYNTAX          INTEGER {
                            hmac-md5(1),
                            hmac-sha(2)
                        }
        MAX-ACCESS      read-only
        STATUS          current
        DESCRIPTION     "Hash algorithm"
        DEFVAL          { hmac-md5 }
        ::= { stnIkePreferenceEntry 4 }

    stnIkePrefEncryption OBJECT-TYPE
        SYNTAX          INTEGER {
                            des-cbc(1),
                            idea-cbc(2),
                            blowfish-cbc(3),
                            rc5-r16-b64-cbc(4),
                            des3-cbc(5)
                        }
        MAX-ACCESS      read-only
        STATUS          current
        DESCRIPTION     "Encryption Alogrithm"
        DEFVAL          { des-cbc }
        ::= { stnIkePreferenceEntry 5 }

    stnIkePrefAuthentication OBJECT-TYPE
        SYNTAX          INTEGER {
                            shared(1),
                            dss-sig(2),
                            rsa-sig(3),
                            rsa-enc(4)
                        }
        MAX-ACCESS      read-only
        STATUS          current
        DESCRIPTION     "Authentication Method"
        DEFVAL          { shared }
        ::= { stnIkePreferenceEntry 6 }

    stnIkePrefDHGroup OBJECT-TYPE
        SYNTAX          Integer32
        MAX-ACCESS      read-only
        STATUS          current
        DESCRIPTION     "Diffie-Hellman group"
        DEFVAL          { 1 }
        ::= { stnIkePreferenceEntry 7 }

    stnIkePrefMode OBJECT-TYPE
        SYNTAX          INTEGER {
                            main(2),            
                            aggressive(4)
                        }
        MAX-ACCESS      read-only
        STATUS          current
        DESCRIPTION     "Mode of Phase 1 negotiations"
        DEFVAL          { main }
        ::= { stnIkePreferenceEntry 8 }

    stnIkePrefLifeTime OBJECT-TYPE
        SYNTAX          TimeStamp
        MAX-ACCESS      read-only
        STATUS          current
        DESCRIPTION     "Lifetime in minutes"
        ::= { stnIkePreferenceEntry 9 }

    stnIkePrefLifeBytes OBJECT-TYPE
        SYNTAX          Integer32 
        MAX-ACCESS      read-only
        STATUS          current
        DESCRIPTION     "Lifetime in kilobytes"
        ::= { stnIkePreferenceEntry 10 }

    stnIkePrefCertAlias OBJECT-TYPE
        SYNTAX          OCTET STRING (SIZE(0..1024))
        MAX-ACCESS      read-only
        STATUS          current
        DESCRIPTION     "Alias of certificate to use"
        ::= { stnIkePreferenceEntry 11 }

    stnIkePrefServiceName OBJECT-TYPE
        SYNTAX          OCTET STRING (SIZE(0..1024))
        MAX-ACCESS      read-only
        STATUS          current
        DESCRIPTION     "Service name for IKE session"
        ::= { stnIkePreferenceEntry 12 }


    --
    -- STN IKE Shared Secret Table
    --

    stnIkeSharedSecretTable OBJECT-TYPE
        SYNTAX        SEQUENCE OF StnIkeSharedSecretEntry
        MAX-ACCESS    not-accessible
        STATUS        current
        DESCRIPTION   "A list of IKE Shared Secret entries."
        ::= { stnIkeSharedSecrets 1 }
 
    stnIkeSharedSecretEntry OBJECT-TYPE
        SYNTAX          StnIkeSharedSecretEntry
        MAX-ACCESS      not-accessible
        STATUS          current
        DESCRIPTION     "Entry contains information about a particular 
                        IKE shared secret."  
        INDEX           { stnIkeSSPeerAddress }
        ::= { stnIkeSharedSecretTable 1 }
 
    StnIkeSharedSecretEntry ::= 
        SEQUENCE {
                stnIkeSSPeerAddress         IpAddress,
                stnIkeSSSecret              OCTET STRING
        }


    stnIkeSSPeerAddress OBJECT-TYPE
        SYNTAX          IpAddress
        MAX-ACCESS      read-only
        STATUS          current
        DESCRIPTION     "Remote IP address"
        ::= { stnIkeSharedSecretEntry 1 }

    stnIkeSSSecret OBJECT-TYPE
        SYNTAX          OCTET STRING (SIZE(0..1024))
        MAX-ACCESS      not-accessible
        STATUS          current
        DESCRIPTION     "Shared secret"
        ::= { stnIkeSharedSecretEntry 2 }

    --
    -- STN IKE Certificate cache table
    --

    stnIkeCertificateTable OBJECT-TYPE
        SYNTAX        SEQUENCE OF StnIkeCertificateEntry
        MAX-ACCESS    not-accessible
        STATUS        current
        DESCRIPTION   "A list of certificates currently in the IKE
	               certificate cache"
        ::= { stnIkeCertificates 1 }
 
    stnIkeCertificateEntry OBJECT-TYPE
        SYNTAX          StnIkeCertificateEntry
        MAX-ACCESS      not-accessible
        STATUS          current
        DESCRIPTION     "Entry contains information about a particular 
                        IKE certificate."  
        INDEX           { stnIkeCertificateIndex }
        ::= { stnIkeCertificateTable 1 }
 
    StnIkeCertificateEntry ::= 
        SEQUENCE {
                stnIkeCertificateIndex      Integer32,
		        stnIkeCertificateType       INTEGER,
                stnIkeCertificateAlias      OCTET STRING,
		        stnIkeCertificateDN         OCTET STRING,
		        stnIkeCertificateAltName    OCTET STRING,
		        stnIkeCertificateIssuer     OCTET STRING
        }

    stnIkeCertificateIndex OBJECT-TYPE
        SYNTAX          Integer32
        MAX-ACCESS      read-only
        STATUS          current
        DESCRIPTION     "Index in certificate cache"
        ::= { stnIkeCertificateEntry 1 }

    stnIkeCertificateType OBJECT-TYPE
        SYNTAX          INTEGER {
                            mine(1),
                            root(2),
                            crl(3)
                        }
        MAX-ACCESS      read-only
        STATUS          current
        DESCRIPTION     "Type of certificate"
        ::= { stnIkeCertificateEntry 2 }

    stnIkeCertificateAlias OBJECT-TYPE
        SYNTAX          OCTET STRING (SIZE(0..1024))
        MAX-ACCESS      read-only
        STATUS          current
        DESCRIPTION     "Certificate alias"
        ::= { stnIkeCertificateEntry 3 }

    stnIkeCertificateDN OBJECT-TYPE
        SYNTAX          OCTET STRING (SIZE(0..1024))
        MAX-ACCESS      read-only
        STATUS          current
        DESCRIPTION     "Certificate distinguished name"
        ::= { stnIkeCertificateEntry 4 }

    stnIkeCertificateAltName OBJECT-TYPE
        SYNTAX          OCTET STRING (SIZE(0..1024))
        MAX-ACCESS      read-only
        STATUS          current
        DESCRIPTION     "Certificate alternative name"
        ::= { stnIkeCertificateEntry 5 }

    stnIkeCertificateIssuer OBJECT-TYPE
        SYNTAX          OCTET STRING (SIZE(0..1024))
        MAX-ACCESS      read-only
        STATUS          current
        DESCRIPTION     "Certificate issuer"
        ::= { stnIkeCertificateEntry 6 }

END
