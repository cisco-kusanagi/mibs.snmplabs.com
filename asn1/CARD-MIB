CARD-MIB 

          DEFINITIONS ::= BEGIN

          -- This file contains the definition of the card mib for Coriolis Networks.
          -- The card mib describes the attributes of cards (management modules,
          -- switch modules, DCPMs and I/O modules) in a network element. Some of these
          -- atributes might make sense for certain types of cards only.

          IMPORTS
                  Unsigned32, OBJECT-TYPE, MODULE-IDENTITY
                      FROM SNMPv2-SMI
                  card, coriolisMibs
                      FROM CORIOLIS-MIB
		            TruthValue
                      FROM SNMPv2-TC
                  TRAP-TYPE
                      FROM RFC-1215;

          cardMIB MODULE-IDENTITY
              LAST-UPDATED "0007270000Z"
              ORGANIZATION "Coriolis Networks"
              CONTACT-INFO
                      "        Shubhra Garg

                       Postal: 330 Codman Hill Road,
                               Boxboro MA, 01719.

                          Tel: +1 978 264 1904
                          Fax: +1 978 264 1929

                       E-mail: shubhra@coriolisnet.com"
              DESCRIPTION
                      "The MIB module for cards in coriolis boxes"
              ::= { card 1 }
                     
          -- Scalar describing the number of active cards in the system

          cardCount OBJECT-TYPE
          SYNTAX INTEGER(1..26)
          MAX-ACCESS read-only
          STATUS current
          DESCRIPTION
          " The number of active cards in the device"
          ::= { card 2 }

          -- Table containing card info that is stored in the EEProm

          cardEEPromTable OBJECT-TYPE
          SYNTAX SEQUENCE OF CardEEPromEntry
          MAX-ACCESS not-accessible
          STATUS current
          DESCRIPTION
          "The table containing various kinds of card information"
          ::= { card 3 }

          cardEEPromEntry OBJECT-TYPE
          SYNTAX CardEEPromEntry
          MAX-ACCESS not-accessible
          STATUS current
          DESCRIPTION
          "Entry containing information about a card in the system."
          INDEX { slotNo }
          ::= { cardEEPromTable 1 }

          CardEEPromEntry ::= SEQUENCE {
           slotNo
           INTEGER,
           cardSIDFVer 
           OCTET STRING,
           cardHwType 
           INTEGER,
           cardHwSubType
           OCTET STRING,
		   cardImageType
		   INTEGER,
           cardMACaddressNum 
           INTEGER,
           cardMacAddress 
           OCTET STRING,
		   cardAssemblyClass
		   INTEGER,
		   cardAssemblyId
		   OCTET STRING,
		   cardAssemblyTabNum
		   INTEGER,
           cardAssemblyRev
		   Unsigned32,
		   cardbrchecksum
		   INTEGER,
         cardSIDInfoVersion
         Unsigned32,
           cardSerialNum 
           OCTET STRING,
           cardAssemblyNumString 
           OCTET STRING,
           cardAssemblyRevString
           OCTET STRING,
           cardCLEICode 
           OCTET STRING,
           cardCLEIECICode 
           OCTET STRING,
           cardChecksum 
           INTEGER
          }

		  slotNo OBJECT-TYPE
          SYNTAX INTEGER(1..26)
          MAX-ACCESS not-accessible
          STATUS current
          DESCRIPTION
          "This variable is used as an index in all card tables"
          ::= { cardEEPromEntry 1 }

          cardSIDFVer OBJECT-TYPE
          SYNTAX OCTET STRING (SIZE(1))
          MAX-ACCESS read-only
          STATUS current
          DESCRIPTION
          " SID ROM Version of the SID-ROM format which represents the 
            1st 20 bytes with a 1 byte value. This variable is used only 
            during the boot process when a sanity check is made. If the 
            current version is 0xF0 (which indicates the initial version), 
            then the next version would be 0xE1 and so on."
          ::= { cardEEPromEntry 2 }

          cardHwType OBJECT-TYPE
          SYNTAX INTEGER {
             mm(1),
             smOSU(2),
             rx1310(4),
             tx1310(5),
             rxDWDM(6),
             txDWDM(7),
             eth16(8),
             atmOC3c(9),
             atmOC12c(10),
             tdmDS1(11),
             tdmDS3(12),
             tdmOC3c(13),
             tdmOC12c(14),
             gigio(16),
			 smOTU(17),
			 dwdmOSU(18),
			 thirteenTenOSU(19),
			 csOSU(20),
            oauEth16Gig1FX(21),
            fmOTU(22),
            dwdmOSU14(23),
            thirteenTenOSU14(24),
            oauEth16DS1Fx(25),
            oauGig4Fx(26),
            posOC12c(27),
            posOC48c(28)
          }
          MAX-ACCESS read-only
          STATUS current
          DESCRIPTION
          " An object which uniquely identifies the card type."
          ::= { cardEEPromEntry 3 }

          cardHwSubType OBJECT-TYPE
          SYNTAX OCTET STRING (SIZE(1))
          MAX-ACCESS read-only
          STATUS current
          DESCRIPTION
            "Identifies the functional revision of this card. 
             Example: Suppose a card's hardware could be configured with  internal 
             or external timing modes and suppose firmware initialization differed 
             depending on the type of timing mode configured on the card hardware, 
             then the value of the hardware subtype object could be used by firmware 
             to initialize to the appropriate timing mode."
          ::= { cardEEPromEntry 4 }

		  cardImageType OBJECT-TYPE
		  SYNTAX INTEGER(0|3|4|5)
		  MAX-ACCESS read-only
		  STATUS current
		  DESCRIPTION
		  "An object which identifies the bootrom and system images to running on a card.
         This object only applies to card types with on-board processor. The values are:

         0 - card without CPU or image.
         3 - Management Module
         4 - OptiFlow 3000/3500 Switch Module  and OptiFlow 5000/5500 Switch Module
         5 - OptiFlow 1010 (Pizza Box)"

		  ::= { cardEEPromEntry 5 }

          cardMACaddressNum OBJECT-TYPE
          SYNTAX INTEGER(0..64)
          MAX-ACCESS read-only
          STATUS current
          DESCRIPTION
          " Indicates the number of MAC Addresses allocated to this 
            module. Current values range from 0 to 64. This value is 
            0 when not applicable."
          ::= { cardEEPromEntry 6 }

          cardMacAddress OBJECT-TYPE
          SYNTAX OCTET STRING(SIZE(6))
          MAX-ACCESS read-only
          STATUS current
          DESCRIPTION
          " Stores the starting MAC Address for this module. All 6 
            bytes are zero when not applicable. "
          ::= { cardEEPromEntry 7 }

		  cardAssemblyClass OBJECT-TYPE
		  SYNTAX INTEGER (1..99)
		  MAX-ACCESS read-only
		  STATUS current
		  DESCRIPTION
		  " Identifies the hardware class. This field is a duplicate of 
         the assembly class portion of the assembly number. It is stored 
         and displayed in Binary Encoded Decimal (BCD) format. The following
         list provide some of the Assembly Class and its description:

         04	Mechanical Assembly Drawing (Legacy Only)
         10	Discrete Resistors
         11	Resistor Networks    
         14	Capacitors
         16	Crystals
         17	Oscillators
         18	Magnetic Modules (inductors, filters, ferrites, power chokes, transformers)
         20	Active Components
         21	Transistors, Diodes, FET's
         22	Mechanical Hardware (Legacy Only)
         23	Connectors
         24	Electromechanical  Components (switches, motors, fans)
         26	Circuit Protection Devices (Fuses, PTC)
         27	Power Components (power supplies, fuses, line filters)
         30	LED's
         31	Logic Components
         32	Memory
         34	Application Specific
         36	Optical Component (Active, Passive)
         38	Programmable Device (Raw device prior to programming)
         40	Module Assemblies (Secondary Assy Required i.e., Optics)
         42	Mechanical Fasteners (Screws, Washers, Nuts, Tywraps)
         43	Labels
         44	Wire & Cable
         46	Packaging (Shipping Materials)
         47	Manuals (HW, SW, Release Notes, Misc)
         50	PCB Assemblies
         51	Schematic
         54	Printed Circuit Boards
         60	Cable Assemblies
         70	Mechanical / Electromechanical Assemblies (Chassis, Fan Tray)
         72	Fabricated Components
         74	Sub Assembly (Legacy Only)
         75	Finished Assembly 
         80	PLD Files
         82	FPGA Code 
         84	Operational Software
         85	Programmed Device Assembly
         86	PLD Daisy Chain Test File
         99	Rework Instructions "
		  ::= { cardEEPromEntry 8 }

		  cardAssemblyId OBJECT-TYPE
		  SYNTAX OCTET STRING
		  MAX-ACCESS read-only
		  STATUS current
		  DESCRIPTION
		  "Identifies the module type. This field is a duplicate of the 
         assembly identifier portion of the assembly number. It is 
         stored and displayed in Binary Encoded Decimal (BCD) format. It
         has the following format:

         NN -1234 -NN  RevNo
          |    |    |    |____ Part Revision Number
          |    |    |      
          |    |    |_________ Suffix    = PartID (01-99)
          |    |
          |    |______________ Main Body = Sequential No. (0001 - 9999)
          |
          |___________________ Prefix    = Part Class Number or Tab Number (01 - 99)."

		  ::= { cardEEPromEntry 9 }

		  cardAssemblyTabNum OBJECT-TYPE
          SYNTAX INTEGER(1..99)
          MAX-ACCESS read-only
          STATUS current
          DESCRIPTION
          " This field is a duplicate of the assembly tab number portion 
            of the assembly number. It is stored and displayed in Binary 
            Encoded Decimal (BCD) format. For Example, a Part Number like
            '60-3456-01' has the Tab Number -01. All new parts are released
            a tab number of -01. If a new member of a family of harwareType
            is introduced, then the tab number would be incremented. Its
            range is 01 - 99."
          ::= { cardEEPromEntry 10 }

          cardAssemblyRev OBJECT-TYPE
          SYNTAX Unsigned32
          MAX-ACCESS read-only
          STATUS current
          DESCRIPTION
          " Identifies the assembly revision of the module. This field 
            is a duplicate of the assembly revision field. It is stored 
            and displayed in Binary Encoded Decimal (BCD) format. For example,
            a typical AssemblyID would be like '54-0001-01 Rev 2'."
          ::= { cardEEPromEntry 11 } 

		  cardbrchecksum OBJECT-TYPE
		  SYNTAX INTEGER
		  MAX-ACCESS read-only
          STATUS current
          DESCRIPTION
          " Contains a checksum calculated over the first 16 bytes of 
            SID ROM data."
          ::= { cardEEPromEntry 12 } 

		  cardSIDInfoVersion OBJECT-TYPE
		  SYNTAX Unsigned32
		  MAX-ACCESS read-only
          STATUS current
          DESCRIPTION
          "Reflects the revision level of the information portion of
           the SID-ROM data."
          ::= { cardEEPromEntry 13 }

          cardSerialNum OBJECT-TYPE
          SYNTAX OCTET STRING(SIZE(0..12))
          MAX-ACCESS read-only
          STATUS current
          DESCRIPTION
          " Stores a 12 digit serial number associated with a module.
           (example: PLX1100-0100)."
          ::= { cardEEPromEntry 14 }   

          cardAssemblyNumString OBJECT-TYPE
          SYNTAX OCTET STRING(SIZE(0..20))
          MAX-ACCESS read-only
          STATUS current
          DESCRIPTION
          " Module's assembly number."
          ::= { cardEEPromEntry 15 }

          cardAssemblyRevString OBJECT-TYPE
          SYNTAX OCTET STRING(SIZE(0..3))
          MAX-ACCESS read-only
          STATUS current
          DESCRIPTION
          "Revision level of the card."
          ::= { cardEEPromEntry 16 }      

          cardCLEICode OBJECT-TYPE
          SYNTAX OCTET STRING(SIZE(0..10))
          MAX-ACCESS read-only
          STATUS current
          DESCRIPTION
          " Stores an ASCII String duplicating CLEI (Common Language
            Equipment Identifier ) Code encoded into 
            the bar code. 10 ASCII characters of CLEI code "
          ::= { cardEEPromEntry 17 }

          cardCLEIECICode OBJECT-TYPE
          SYNTAX OCTET STRING(SIZE(0..6))
          MAX-ACCESS read-only
          STATUS current
          DESCRIPTION
          " Stores an ASCII String duplicating CLEI ECI (Equipment Catalog Item)
            Code encoded into the bar code. Bar Code in numeric form "
          ::= { cardEEPromEntry 18 }

          cardChecksum OBJECT-TYPE
          SYNTAX INTEGER
          MAX-ACCESS read-only
          STATUS current
          DESCRIPTION
          " Contains a checksum calculated over the  previous 252 bytes 
            of SID ROM data."
          ::= { cardEEPromEntry 19 }

          -- The Slot table

          slotTable OBJECT-TYPE
          SYNTAX SEQUENCE OF SlotEntry
          MAX-ACCESS not-accessible
          STATUS current
          DESCRIPTION
          "The slot table"
          ::= { card 4 }

          slotEntry OBJECT-TYPE
          SYNTAX SlotEntry
          MAX-ACCESS not-accessible
          STATUS current
          DESCRIPTION
          "Entry containing information about a slot in the system."
          INDEX { slotNo }
          ::= { slotTable 1 }

          SlotEntry ::= SEQUENCE {
            slotAdminState
            INTEGER,
            slotOperState
            INTEGER,
            slotType
            INTEGER,
            slotCardType
            INTEGER,
            slotConnectionSize
            INTEGER,
            slotSMSlot
            INTEGER,
            slotInsertState
            INTEGER,
            slotFileState
            INTEGER,
            slotModuleChangeStatus
            INTEGER,
	        slotModuleTempStatus
	        INTEGER,
			slotIoCardStatus
			INTEGER,
			slotFlashThreshold
			INTEGER,
			slotFlashSectorsOverThreshold
			INTEGER
          }

          slotAdminState OBJECT-TYPE
          SYNTAX INTEGER {
            disabled(0),
            enabled(1)
          }
          MAX-ACCESS read-write
          STATUS current
          DESCRIPTION
          " The slot admin state "
          ::= { slotEntry 1}

          slotOperState OBJECT-TYPE
          SYNTAX INTEGER {
            removed(0),
            syncWait(1),
            synced(2),
            syncFailed(3),
            configStarted(4),
            configFailed(5),
            configed(6),
            ready(7),
            waitSM(8),
            waitDeconfig(9),
            designModeReady(10)
          }
          MAX-ACCESS read-only
          STATUS current
          DESCRIPTION
          " The slot oper state.
            removed           - card not in slot and not connected
            syncWait          - card in slot waiting for syncPoint
            synced            - card passed a syncPoint
            syncFailed        - card failed a syncPoint 
            configStarted     - configuration started
            configFailed      - configuration failed
            configed          - configuration passed 
            ready             - card ready for normal operation 
            waitSM            - card waiting for SM reboot
            waitDeconfig      - waiting for deconfiguration to complete
            designModeReady   - card is configured but removed."
          ::= { slotEntry 2}

          slotType OBJECT-TYPE
          SYNTAX INTEGER {
               mmSlot(1), 
 	            optiFlow3xSMSlot(2),  
 	            optiFlow5xSMSlot(3), 
 	            regularIOSlot(4),
 	            optiFlow3xSlotNumber1(5), 
 	            colorSeparator(6), 
 	            optiFlow3xOpticsSlot(7), 
 	            optiFlow5xOpticsSlotType1(8), 
 	            optiFlow5xOpticsSlotType2(9), 
 	            optiFlow5xFramerModuleSlot(10), 
               oauEth(11),
               oauGig(12),
 	            oauMM(13),
 	            oauSM(14), 
 	            oauOptics(15) 
          }
          MAX-ACCESS read-write
          STATUS current
          DESCRIPTION
          " The type of slot for this device. The following is a list of
 	         different kinds of slots:
 	
 	         1 - MMSlot (9,10 for optiFlow3X and 13,14 for optiFlow5x)
 	         2 - optiFlow3xSMSlot (goes into slot 12)
 	         3 - optiFlow5xSMSlot (goes into slots 7,9,18,20)
 	         4 - regularIOSlot (goes into slots 3-6 in optiFlow3x,
 	                           1-6, 21-26 in optiFlow5x)
 	         The different types of cards that goes into this regular
 	         IO Slot are:
 	            A - 10/100 Ethernet
 	            B - Gigbit Ethernet
 	            C - DS1 TDM
 	            D - DS3 TDM
 	            E - OC12 ATM/POS
 	            F - OC12 TDM
 	            G - OC3 ATM
 	            H - OC48 POS
 	            I - Color Separator
 	
 	         5 - optiFlow3xSlotNumber1
 	         The different types of cards that goes into this slot are:
 	            A - DS1 TDM
 	            B - DS3 TDM
 	            C - OC12 TDM
 	
 	         6 - optiFlow5x IO
 	            This type of slot takes:
 	            A - OC12 TDM (slots 5 and 21)
 	
 	         7 - optiFlow3x OpticsSlot (slots 11 and 12)               
 	         This slot takes in:
 	            A - 1310TxRx
 	            B - 8 different cards with different lambdas (optiFlow3x OADM optics)
 	            C - 1550 TxRx
 	
 	         8 - optiFlow5x OpticsSlotType1 (slots 12 and 15 - Tx Only)
 	         This slot takes in:
 	            A - 1310 Tx / DWDM
 	            B - 8 different cards with different lambdas for DWDM Tx
 	            C - 1310 Tx
 	            D - 1550 Tx
 	
 	         9 - optiFlow5x OpticsSlotType2 (slots 11 and 16 - Rx only)
 	         This slot takes in:
 	            A - 1310 Rx / DWDM
 	            B - 8 different cards with different lambdas for DWDM Rx
 	            C - 1310 Rx
 	
 	         10 - optiFlow5x FM (goes into slots 8, 10, 17 and 19) 
 	
 	         11 - colorSeparator (goes into slot 2 for OptiFlow3x)               
 	
 	         For an OAU, the slots are abstracted in the following manner:
 	         Slot 1 - IO (Eth16)
 	         Slot 2 - IO (GigIo)
 	         Slot 3 - MM
 	         Slot 4 - SM
 	         Slot 5 - OpRxTx"
          ::= { slotEntry 3}

          slotCardType OBJECT-TYPE
          SYNTAX INTEGER {
             mm(1),
             smOSU(2),
             smISM(3),
             rx1310(4),
             tx1310(5),
             rxDWDM(6),
             txDWDM(7),
             eth16(8),
             atmOC3c(9),
             atmOC12c(10),
             tdmDS1(11),
             tdmDS3(12),
             tdmOC3c(13),
             tdmOC12c(14),
             islgmac(15),
             gigio(16),
			 smOTU(17),
			 dwdmOSU(18),
			 thirteenTenOSU(19),
			 csOSU(20),
		oauEth16Gig1Fx(21),
		oauFmOTU(22),
		osu14DWDM(23),
		thirteenTenOSU14(24),
		oauEth16Ds1Fx(25),
		oauGig4Fx(26),
		posOC12c(27),
		posOC48c(28),
      fifteenFiftyOSU14(29),
      tx1550(30),
      oau1550Eth16Gig1Fx(31)
          }
          MAX-ACCESS read-write
          STATUS current
          DESCRIPTION
          " The type of card in the slot "
          ::= { slotEntry 4}

          slotConnectionSize OBJECT-TYPE
          SYNTAX INTEGER {
            auto(0),
            sm8(1),
            sm16(2)
          }
          MAX-ACCESS read-write
          STATUS current
          DESCRIPTION
          " The connection size to SM "
          ::= { slotEntry 5}

          slotSMSlot OBJECT-TYPE
          SYNTAX INTEGER
          MAX-ACCESS read-write
          STATUS current
          DESCRIPTION
          " SM slot that this slot is connected to "
          ::= { slotEntry 6}

          slotInsertState OBJECT-TYPE
          SYNTAX INTEGER {
            false(0),
            true(1)
          }
          MAX-ACCESS read-only
          STATUS current
          DESCRIPTION
          " Whether a card is present in the slot or not "
          ::= { slotEntry 7}

          slotFileState OBJECT-TYPE
          SYNTAX INTEGER {
            created(1),
            ready(2),
            locked(3)
          }
          MAX-ACCESS read-only
          STATUS current
          DESCRIPTION
          " File locked or not  "
          ::= { slotEntry 8}

          slotModuleChangeStatus OBJECT-TYPE
          SYNTAX INTEGER {
            inserted(1),
            removed(2),
            failure(3),
            failover(4),
	    configured(5),
	    syncpointFailure(6),
	    configFailure(7),
	    configDeleted(8),
	    configFailCardTypeMismatch(9),
	    configFailSMNotAvailable(10),
	    configFailOutOfSwitchPorts(11),
	    moduleConfigurationCorrupt(12),
	    warmBoot(13)
          }
          MAX-ACCESS accessible-for-notify
          STATUS current
          DESCRIPTION
          " This variable is sent out in a module change event to 
            communicate what happened to the module.The 'FAILURE' 
		      and 'FAILOVER' values are used by the mmr task to report 
            failover events.  The 'INSERTED' and 'REMOVED' values are
            used by AI to report module configuration and de-configuration 
            events. The 'INSERTED' event will change to be reported whenever 
            a card is inserted.  The 'CONFIGURED' event will be reported 
            when the card completes chassis configuration.  The 'REMOVED' 
            event will be reported whenever a card is removed. 
			   The events 'SYNCPOINT_FAILURE' and 'CONFIG_FAILURE' will be 
            reported when a card fails syncPoints or chassis configuration 
            respectively.  The event 'CONFIG_DELETED' will be reported when 
            a card configuration file is deleted (indicating the card 
            configuration has been lost). "
          ::= { slotEntry 9}

          slotModuleTempStatus OBJECT-TYPE
          SYNTAX INTEGER {
			     hot (1),
			     normal (2)
	                    }
          MAX-ACCESS accessible-for-notify
          STATUS current
          DESCRIPTION
          "Indicates the temperature status of the module in the slot"
          ::= { slotEntry 10 }

          slotIoCardStatus OBJECT-TYPE
	      SYNTAX INTEGER {
	        unresponsive (1),
			responsive (2)
			}  
	      MAX-ACCESS  accessible-for-notify
	      STATUS  current
	      DESCRIPTION
		  "Indicates the responsiveness status of the module in the slot"
	      ::= { slotEntry 11 }

          slotFlashThreshold OBJECT-TYPE
	      SYNTAX INTEGER
	      MAX-ACCESS  accessible-for-notify
	      STATUS  current
	      DESCRIPTION
		  "Indicates the flash threshold, applicable for only the active 
         and standby management modules"
	      ::= { slotEntry 12 }

          slotFlashSectorsOverThreshold OBJECT-TYPE
	      SYNTAX INTEGER
	      MAX-ACCESS  accessible-for-notify
	      STATUS  current
	      DESCRIPTION
		  "Indicates the number of sectors over threshold, applicable for 
         only the active and standby MMs"
	      ::= { slotEntry 13 }


          -- The TDM IO card table

          tdmIoCardTable OBJECT-TYPE
          SYNTAX SEQUENCE OF TdmIoCardEntry
          MAX-ACCESS not-accessible
          STATUS current
          DESCRIPTION
          "The table for TDM IO cards"
          ::= { card 5 }

          tdmIoCardEntry OBJECT-TYPE
          SYNTAX TdmIoCardEntry
          MAX-ACCESS not-accessible
          STATUS current
          DESCRIPTION
          "Entry containing information about an TDM IO module - DS1/DS3/E1/E3"
          INDEX { slotNo }
          ::= { tdmIoCardTable 1 }

          TdmIoCardEntry ::= SEQUENCE {            
            tdmIoCardType
              INTEGER,
            tdmIoCardOperState
              INTEGER,
            tdmIoCardMode
              INTEGER,
            tdmIoCardConfiguredPorts
              Unsigned32,
            tdmIoCardRowStatus
              INTEGER,
            tdmIoCardNumPMIntervals
			  Unsigned32
          }

          tdmIoCardType OBJECT-TYPE
          SYNTAX INTEGER {
            ds1(1),
			ds3(2),
			oc3(3),
			oc12(4),
			e1(5),
			e3(6)
          }
          MAX-ACCESS read-write
          STATUS current
          DESCRIPTION
          "The type of the TDM IO module"
          ::= {tdmIoCardEntry 1}

          tdmIoCardOperState OBJECT-TYPE
          SYNTAX INTEGER {
            up(1),
            down(2)
          }
          MAX-ACCESS read-only
          STATUS current
          DESCRIPTION
          "The oper state of the TDM IO module"
          ::= {tdmIoCardEntry 2}

          tdmIoCardMode OBJECT-TYPE
          SYNTAX INTEGER {
            unchannelized(1),
            channelized(2),
	    sts1mode(3),
	    au3mode(4),
	    ds3ClearChannel(5),
            ds3Channelized(6)
          }
          MAX-ACCESS read-write
          STATUS current
          DESCRIPTION
          "Whether this is an unchannelized or channelized module"
          ::= {tdmIoCardEntry 3}

          tdmIoCardConfiguredPorts OBJECT-TYPE
          SYNTAX Unsigned32
          MAX-ACCESS read-only
          STATUS current
          DESCRIPTION
          "Bitmap of ports configured on the module. The bit positions of
		   the 1 bits in the binary form of this number give the ports 
		   configured in this card. For example, if all the 3 ports of a DS3
         card are configured, you'll get a value of 14 which in binary gives 1110.
         If 1st and 3rd are configured, you'll see 10 (1010). For a DS1 card, if
         all 16 ports are configured, you'll a value of 131070. The number of 1's
         in the binary representation of the value gives the number of configured 
         ports."
          ::= {tdmIoCardEntry 4}

          tdmIoCardRowStatus OBJECT-TYPE
          SYNTAX INTEGER {
            active(1),
            notInService(2),
            createAndGo(4),
            createAndWait(5),
            destroy(6)
          }
          MAX-ACCESS read-write
          STATUS current
          DESCRIPTION
          " This variable is used to create or delete instances of TDM IO cards.
            This variable subsumes the admin state variable, and once the row is
            created, its value returns the admin state of the card"
          ::= {tdmIoCardEntry 5}

		  tdmIoCardNumPMIntervals OBJECT-TYPE
		  SYNTAX Unsigned32
		  MAX-ACCESS read-write
		  STATUS current
		  DESCRIPTION
		  "This is the number of performance monitoring intervals for
		   the ports on this card"
		   ::= {tdmIoCardEntry 6}	  


          -- The ethernet card table

          etherCardTable OBJECT-TYPE
          SYNTAX SEQUENCE OF EtherCardEntry
          MAX-ACCESS not-accessible
          STATUS current
          DESCRIPTION
          "The table for ethernet cards"
          ::= { card 6 }

          etherCardEntry OBJECT-TYPE
          SYNTAX EtherCardEntry
          MAX-ACCESS not-accessible
          STATUS current
          DESCRIPTION
          "Entry containing information about an ethernet module"
          INDEX { slotNo }
          ::= { etherCardTable 1 }

          EtherCardEntry ::= SEQUENCE {
            etherCardOperState
              INTEGER,
            etherCardActivePortMask
              INTEGER,
            etherCardPhyResetState
			  INTEGER,
            etherCardRowStatus
              INTEGER
          }

          etherCardOperState OBJECT-TYPE
          SYNTAX INTEGER {
		     up(1),
			 down(2)
		  }	  
          MAX-ACCESS read-only
          STATUS current
          DESCRIPTION
          " The oper state of the ethernet module "
          ::= {etherCardEntry 1}

          etherCardActivePortMask OBJECT-TYPE
          SYNTAX INTEGER(0..65535)
          MAX-ACCESS read-only
          STATUS current
          DESCRIPTION
          " This returns a mask of active ports.  An active port is one that has been 
            created via a Port Create MO.  A value of 1 in bit position N-1 indicates 
            that port N has been created. For example, if port 1 has been created, then 
            bit 0 is asserted. Since there are 16 ports, this can take the range of values 
            from 0 to 65535."
          ::= {etherCardEntry 2}

          etherCardPhyResetState OBJECT-TYPE
          SYNTAX INTEGER {
		     inReset(1),
			 outOfReset(2)
		  }	  
          MAX-ACCESS read-write
          STATUS current
          DESCRIPTION
          " The phy reset state of the module "
          ::= {etherCardEntry 3}

          etherCardRowStatus OBJECT-TYPE
          SYNTAX INTEGER {
            active(1),
            notInService(2),
            createAndGo(4),
            createAndWait(5),
            destroy(6)
          }
          MAX-ACCESS read-write
          STATUS current
          DESCRIPTION
          " This variable is used to create or delete instances of ethernet cards.
            This variable subsumes the admin state variable, and once the row is
            created, its value returns the admin state of the card"
          ::= {etherCardEntry 4}


          -- The atm card table

          atmCardTable OBJECT-TYPE
          SYNTAX SEQUENCE OF AtmCardEntry
          MAX-ACCESS not-accessible
          STATUS current
          DESCRIPTION
          "The table for atm cards"
          ::= { card 7 }

          atmCardEntry OBJECT-TYPE
          SYNTAX AtmCardEntry
          MAX-ACCESS not-accessible
          STATUS current
          DESCRIPTION
          "Entry containing information about an atm module"
          INDEX { slotNo }
          ::= { atmCardTable 1 }

          AtmCardEntry ::= SEQUENCE {
            atmCardOperState
              INTEGER,
            atmCardActivePortMask
              INTEGER,
            atmCardRowStatus
              INTEGER
          }

          atmCardOperState OBJECT-TYPE
          SYNTAX INTEGER {
		     up(1),
			 down(2)
		  }	  
          MAX-ACCESS read-only
          STATUS current
          DESCRIPTION
          " The oper state of the atm module "
          ::= {atmCardEntry 1}

          atmCardActivePortMask OBJECT-TYPE
          SYNTAX INTEGER(0..3)
          MAX-ACCESS read-only
          STATUS current
          DESCRIPTION
          "This returns a mask of active ports.  An active port is one that has been 
            created via a Port Create MO.  A value of 1 in bit position N-1 indicates 
            that port N has been created. For example, if port 1 has been created, then 
            bit 0 is asserted. Since there are 2 ports for an ATM card, this can take 
            the range of values from 0 to 3."
          ::= {atmCardEntry 2}

          atmCardRowStatus OBJECT-TYPE
          SYNTAX INTEGER {
            active(1),
            notInService(2),
            createAndGo(4),
            createAndWait(5),
            destroy(6)
          }
          MAX-ACCESS read-write
          STATUS current
          DESCRIPTION
          " This variable is used to create or delete instances of atm cards.
            This variable subsumes the admin state variable, and once the row is
            created, its value returns the admin state of the card"
          ::= {atmCardEntry 3}

          -- The optical card table

          opticalCardTable OBJECT-TYPE
          SYNTAX SEQUENCE OF OpticalCardEntry
          MAX-ACCESS not-accessible
          STATUS current
          DESCRIPTION
          "The table for optical cards"
          ::= { card 8 }

          opticalCardEntry OBJECT-TYPE
          SYNTAX OpticalCardEntry
          MAX-ACCESS not-accessible
          STATUS current
          DESCRIPTION
          "Entry containing information about an optical module"
          INDEX { slotNo }
          ::= { opticalCardTable 1 }

          OpticalCardEntry ::= SEQUENCE {
            opticalCardSlotType
			  INTEGER,
            opticalCardOpticsType
              INTEGER,
            opticalCardRowStatus
              INTEGER
          }

          opticalCardSlotType OBJECT-TYPE
          SYNTAX INTEGER {
		     rxOTU(1),
			 txOTU(2),
			 txRxOSU(3),
			 txRxOSU14(4),
			 oauEth16Gig1(5)
		  }	  
          MAX-ACCESS read-write
          STATUS current
          DESCRIPTION
          " The type of module - transmitter or receiver "
          ::= { opticalCardEntry 1 }

          opticalCardOpticsType OBJECT-TYPE
          SYNTAX INTEGER {
		     dwdm(1),
			 thirteenTen(2),
          fifteenFifty(3),
          thirteenTenFifteenFifty(4)
		  }	  
          MAX-ACCESS read-write
          STATUS current
          DESCRIPTION
          " The type of optics on the module "
          ::= { opticalCardEntry 2 }

          opticalCardRowStatus OBJECT-TYPE
          SYNTAX INTEGER {
            createAndGo(4),
            destroy(6)
          }
          MAX-ACCESS read-write
          STATUS current
          DESCRIPTION
          " This variable is used to create or delete instances of optical cards"
          ::= {opticalCardEntry 3}

          -- The POS card table

          posCardTable OBJECT-TYPE
          SYNTAX SEQUENCE OF PosCardEntry
          MAX-ACCESS not-accessible
          STATUS current
          DESCRIPTION
          "The table for pos cards"
          ::= { card 9 }

          posCardEntry OBJECT-TYPE
          SYNTAX PosCardEntry
          MAX-ACCESS not-accessible
          STATUS current
          DESCRIPTION
          "Entry containing information about an pos module"
          INDEX { slotNo }
          ::= { posCardTable 1 }

          PosCardEntry ::= SEQUENCE {
            posCardActivePortMask Unsigned32,
            posCardPhyResetState  INTEGER
          }

          posCardActivePortMask OBJECT-TYPE
          SYNTAX Unsigned32
          MAX-ACCESS read-only
          STATUS current
          DESCRIPTION
          " Bitmap describing the active ports on this pos module "
          ::= {posCardEntry 1}

          posCardPhyResetState OBJECT-TYPE
          SYNTAX INTEGER {
		     inReset(1),
			  outOfReset(2)
		      }	  
          MAX-ACCESS read-write
          STATUS current
          DESCRIPTION
          " The phy reset state of the module "
          ::= {posCardEntry 2}

          -- Definition of the module status change trap

          moduleStatusChange TRAP-TYPE
          ENTERPRISE coriolisMibs
          VARIABLES { slotModuleChangeStatus, cardHwType }
          DESCRIPTION
          " Change in the operational state of a module.
            1 means the module went down, 2 means it went up "
          ::= 2

	  moduleTempChange	TRAP-TYPE
	      ENTERPRISE	coriolisMibs
	      VARIABLES	{slotModuleTempStatus}
	      DESCRIPTION
	         "Indicates temperature (hot/normal) in the chassis."
	      ::= 44

	 ioCardStatusChange  TRAP-TYPE
	      ENTERPRISE coriolisMibs
	      VARIABLES { slotIoCardStatus }
	      DESCRIPTION
		  "Indicates the failure of IO card to respond."
	      ::= 45

	 emFlashLife	TRAP-TYPE
	     ENTERPRISE	coriolisMibs
	     VARIABLES	{ slotFlashThreshold, slotFlashSectorsOverThreshold }
	     DESCRIPTION
		 "Flash End-of-life alarm."
	     ::= 46

          END
