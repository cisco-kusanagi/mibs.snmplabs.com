CXDSP-MIB DEFINITIONS ::= BEGIN

IMPORTS
	Counter         FROM  RFC1155-SMI
	OBJECT-TYPE     FROM  RFC-1212
	DisplayString   FROM  RFC1213-MIB
	cxDsp, SapIndex, Alias
			FROM  CXProduct-SMI;

--  Global Constants
X25Address                      ::=  DisplayString (SIZE (0..15))
   
-- DSP layer
DspCuAddress                    ::= INTEGER  (1..254)           
DspDevAddress        ::= INTEGER  (1..254)              
	
DspRowStatus                    ::= INTEGER     {                               
		invalid (1),
		valid   (2)
		}

-- DSP circuit type. It could be Single/Multiple user, Circuit Request
DspCircuitType ::= INTEGER {
				singusr-noreqcirc       (1),
				singusr-reqcirc         (2),              
				multuser-reqcirc        (3),
				mes-usr-reqcirc         (4)
		}

DspOperationalMode  ::=   INTEGER {
	    offline                                     (1),
	    online                                              (2)
      }

DspPartner      ::= INTEGER {
				terminal-terminal                       (1),
				host-terminal                           (2)
		}
		
 
PacketSize      ::=     INTEGER {
				bytes16         (4),
				bytes32         (5),
				bytes64         (6),
				bytes128                (7),
				bytes256                (8),
				bytes512                (9),
				bytes1024       (10),
				bytes2048       (11),
				bytes4096       (12)
				}

ThruputClass    ::=     INTEGER {
				bps75                   (3),
				bps150          (4),
				bps300          (5),
				bps600          (6),
				bps1200         (7),
				bps2400         (8),
				bps4800         (9),
				bps9600         (10),
				bps19200                (11),
				bps38400                (12),
				bps64000                (13)
				}
                            

--  Service Access Point Configuration Table
--      parameters required to configure the link service access point
--      controls available to manipulate DSP services.          

dspSapTable                             OBJECT-TYPE
      SYNTAX                            SEQUENCE OF DspSapEntry
      ACCESS                            not-accessible
      STATUS                            mandatory
      DESCRIPTION
		"A  table  containing configuration information  
			 about all the service access point."
				::= { cxDsp 1 }

dspSapEntry                     OBJECT-TYPE
	SYNTAX                          DspSapEntry
	ACCESS                          not-accessible
	STATUS                          mandatory
	DESCRIPTION
			"The parameters for a particular service access point."
	INDEX                   {
				 dspSapNumber
				 }
			::= { dspSapTable 1 }

DspSapEntry ::=
	SEQUENCE {
-- Parameters
		dspSapNumber                    SapIndex,
		dspSapRowStatus                 DspRowStatus,
		dspSapType                      INTEGER,
		dspSapAlias             Alias,
		dspSapCompanionAlias            Alias,
		dspSapSnalcRef                          INTEGER,
		dspSapEbcdicAsciiMode   INTEGER,    
 -- Control
		dspSapControl           INTEGER,
-- Status
		dspSapOperationalMode   DspOperationalMode 
-- Statistics
}

 -- The Objects for the Service Access Point Configuration Table
dspSapNumber                            OBJECT-TYPE
	SYNTAX                  SapIndex
		ACCESS                  read-only
	STATUS                  mandatory
	DESCRIPTION
	  "Identifies  the  service  access   point by a numerical  value.  
	  This value is used as a index in the saps table. Values are unique
	  per  service access point."
			::= { dspSapEntry 1 }

dspSapRowStatus         OBJECT-TYPE
	SYNTAX                  DspRowStatus    
	ACCESS                  read-write
	STATUS                  mandatory
	DESCRIPTION
		"Indicates  whether the particular service  access
		point is configured within the MIB  Service access 
				point entries (rows) may be created by  setting  this  
				object  value  to  'valid',  or deleted  by changing  this
				object value to  'invalid'.  Whether  or  not  the  row   
				actually disappears is left to the implementation  so  this
		object  may  actually read as 'invalid'  for  some arbitrary 
				length of time."
		::= { dspSapEntry 2 }

dspSapType                      OBJECT-TYPE
		SYNTAX                          INTEGER {
									lower   (1),
									upper   (2)
								}
		ACCESS                          read-write
		STATUS                          mandatory
		DESCRIPTION
					"Identifies the service access point by type:'lower'
		identifies a SAP leading to a physical X25 port. 
		'Upper'         identifies a SAP acting as an internal 
		inter-layer logical port."
		DEFVAL          { lower }
			::={ dspSapEntry 3 }

dspSapAlias             OBJECT-TYPE
	SYNTAX          Alias
	ACCESS          read-write
	STATUS          mandatory
	DESCRIPTION
			"Identifies the service access point by a  textual
			name.  Names are unique per service access point."
		::= { dspSapEntry 4 }

dspSapCompanionAlias    OBJECT-TYPE
	SYNTAX          Alias
	ACCESS          read-write
	STATUS          mandatory
	DESCRIPTION
			"Identifies the  `lower' service access  point  that
			will communicate with this service access point by
			a textual name.
			Names are unique per service access point. Used to
			bind the DSP Sap with the X25 sap."
	::= { dspSapEntry 5 }

dspSapSnalcRef          OBJECT-TYPE
	SYNTAX  INTEGER  (0..8)
	ACCESS  read-write
	STATUS  mandatory
	DESCRIPTION
		"Identifies which upper sap is associated to the lower sap within the DSP
		module. Applies only to lower DSP saps (X25 sap)."
	DEFVAL		{ 0 }
	::={ dspSapEntry 6 }

dspSapEbcdicAsciiMode   OBJECT-TYPE     
	SYNTAX          INTEGER     {
				encdicMode      (1),
				asciiMode       (2)
			}
	ACCESS          read-write
	STATUS          mandatory
	DESCRIPTION
			"Indicates the character set used  by the device defined
		 for this association. The character set could be a 
		EBCDIC or ASCII."
	DEFVAL          { encdicMode }
	::= { dspSapEntry  7 }           
	
-- gap (8) to gap (19) for future Parameters
 -- Control
dspSapControl                   OBJECT-TYPE
	SYNTAX                  INTEGER        {
					clearStats      (1)
			}
	ACCESS          write-only
	STATUS                  mandatory
	DESCRIPTION
		"Control associated with the specified service access point."
	::= { dspSapEntry  20}
      
-- gap (21) to gap (29) for future Parameters
-- Status
dspSapOperationalMode   OBJECT-TYPE
	SYNTAX          DspOperationalMode
	ACCESS          read-only
	STATUS          mandatory
	DESCRIPTION
			"Identifies the service access point as being
			active or non-active with the new configuration."
	::={ dspSapEntry  30 }

-- gap (31) to gap (39) for future Parameters
-- Statistics
   
--   3270 Controller Unit Family Configuration Table
--      The table contains information about the terminal controller unit configurated in the
--      system. Such informations include the controller unit address,  type, how many devices are 
--      connected to it, etc...

dspCuTable              OBJECT-TYPE
	 SYNTAX                 SEQUENCE OF DspCuEntry
	ACCESS          not-accessible
	STATUS                  mandatory
	DESCRIPTION
		"A  table  containing configuration information  about
		all the 3270 controller units."
	::= { cxDsp 2 }

dspCuEntry              OBJECT-TYPE
	SYNTAX          DspCuEntry
	ACCESS          not-accessible
	STATUS          mandatory
	DESCRIPTION
			"The parameters for a particular controller unit."       
	INDEX  {  
			dspCuSapNumber,
				dspCuAddress
		} 
	::= { dspCuTable 1 }

DspCuEntry ::=
	SEQUENCE {
-- Parameters
	dspCuSapNumber              SapIndex,
	dspCuAddress            DspCuAddress,
	dspCuRowStatus                  DspRowStatus,           
	dspCuType                       INTEGER,
	dspCuCallingX25Address X25Address,
	dspCuCalledX25Address  X25Address,
	dspCuDSPCircuitType     DspCircuitType,
	dspCuWindow             INTEGER,
	dspCuUserData           DisplayString,
	dspCuFacility           OCTET STRING,
	dspCuApplicationId              INTEGER,
	dspCuReqMode                    INTEGER,
	dspCuPacketSize         PacketSize,
	dspCuThroughput ThruputClass,
	dspCuPartner            DspPartner,
-- Control              
   dspCuControl         INTEGER,
-- Status
	dspCuState              INTEGER,
	dspCuOperationalMode            DspOperationalMode,
-- Statistics
	dspCuX25CallRequest             Counter,
	dspCuX25CallAccept              Counter,
	dspCuClears                     Counter,
	dspCuClearsInd                  Counter,
	dspCuInvToClear                         Counter
}
   
-- The Objects for the Service Access Point Configuration Table
-- Parameters
dspCuSapNumber          OBJECT-TYPE
	SYNTAX                  SapIndex
	ACCESS          read-only
	STATUS                  mandatory
	DESCRIPTION
		"Identifies  the sap associated with this controller unit. 
		Each controller unit has an address and the address has to 
		be unique with one sap. However, the address is not required 
		to be unique between saps This object is an index in the 
		sap Table. Values are unique."
	::= { dspCuEntry 1 }

dspCuAddress            OBJECT-TYPE
	SYNTAX          DspCuAddress
	ACCESS          read-only
	STATUS                  mandatory
	DESCRIPTION
		"Identifies the address of this controller unit.
		 The address has to be unique for a specified sap."
	::= { dspCuEntry 2 }

dspCuRowStatus          OBJECT-TYPE
	SYNTAX          DspRowStatus
	ACCESS          read-write
	STATUS          mandatory
	DESCRIPTION
			"Indicates  whether the particular service  access point is 
		configured within the MIB. Controller unit  entries (rows)
		 may be created by  setting  this  object  value  to  'valid',  
		or deleted   by   changing  this  object  value to 'invalid'. 
		Whether  or  not  the  row   actually disappears is left to the 
		implementation  so  this object  may  actually read as 'invalid'  
		for  some arbitrary length of time."
	::= { dspCuEntry 3 }

dspCuType       OBJECT-TYPE
	SYNTAX          INTEGER      {
				termInterfaceUnit    (1),
				hostInterfaceUnit    (2)
			}
	ACCESS          read-write
	STATUS          mandatory
	DESCRIPTION
			"Identifies  the  type of controller: either TIU or HIU."
	DEFVAL          { termInterfaceUnit }
	::= { dspCuEntry 4 }

dspCuCallingX25Address   OBJECT-TYPE
	SYNTAX          X25Address
	ACCESS          read-write
	STATUS          mandatory
	DESCRIPTION
			"Identifies the X25 address of this sap.  This address is unique for all 
		devices  attached to this sap, TIU side"
	::= { dspCuEntry  5 }

dspCuCalledX25Address   OBJECT-TYPE
	SYNTAX          X25Address
	ACCESS          read-write
	STATUS          mandatory
	DESCRIPTION
			"Identifies the X25 address of the remote device."
	::= { dspCuEntry  6 }


dspCuDSPCircuitType     OBJECT-TYPE
	SYNTAX          DspCircuitType  
	ACCESS          read-write
	STATUS          mandatory
	DESCRIPTION
			"Identifies the connection as being either only one connection or 
		multiple DSP connections  per X.25 virtual circuit  The valid values follow:
		singUsr-NoReq Circ  - single user per X25 svc, no circuit request. The LCN 
					          is 0.
		singUsr-ReqCirc     - single user per X25 svc, circuit request. The LCN is
					          negociated during the connection establishment.
		multUser-ReqCirc    - multiple user per X25 svc. Each user has a LCN and 
					          the LCN is negociated individually.
		MES-Usr-ReqCirc		- Modified Bisync single user per X25 svc, circuit request.
                              The LCN is negociated during the connection establishment."
	DEFVAL          { singUsr-NoReqCirc }     
	::= { dspCuEntry  8 }

 dspCuWindow OBJECT-TYPE
	SYNTAX  INTEGER (1..7)
	ACCESS  read-write
	STATUS  mandatory
	DESCRIPTION
		"Defines the receive window size used for packets.  At the source side, it 
	defines the window for packets received from the source interface.  At the
	destination side, it defines the window for packets transmitted to the
	the source side, it defines the window for packets transmitted to the source interface.
	At the destination side, it defines the window for packets received from the destination 
	interface. Allowable value are '1'-'7' for modulo 8."
	DEFVAL { 7 }
	::= { dspCuEntry  9}

dspCuUserData OBJECT-TYPE
	SYNTAX  DisplayString (SIZE (0..12))
	ACCESS  read-write
	STATUS  mandatory
	DESCRIPTION
		"The user data put in the call user data field of  call request packets."
	::= { dspCuEntry  10 }

dspCuFacility OBJECT-TYPE
	SYNTAX  OCTET STRING
	ACCESS  read-write
	STATUS  mandatory       
	DESCRIPTION
		"Specifies the facility codes and facility parameters put in the facilities field of the call
		 call request packet during call set-up.
		The maximum number of facility codes and parameters that may be specified is 20."
	::= { dspCuEntry 11 }

dspCuApplicationId              OBJECT-TYPE     
	SYNTAX          INTEGER     (0..255) 
	ACCESS          read-write
	STATUS          mandatory
	DESCRIPTION
			"Indicates an application running on the host associated
		 with the controller unit/device."
	DEFVAL  { 0 }
	::= { dspCuEntry  12 }

dspCuReqMode            OBJECT-TYPE   
	SYNTAX          INTEGER     {
			fixedClassCrm           (1),
			specificClassCrm        (2),
			nonSpecificClassCrm     (3),
			associateDeviceCrm      (4)
			}
	ACCESS          read-only
	STATUS          mandatory
	DESCRIPTION
		"Identifies the connection request mode. The 
		following modes are available :
		Fixed Class Crm : destination is selected automatically
		Specific Class Crm : select a destination by cu/dev
					      addresses.    
		Non-Specific Class Crm : select a destination by 
						address and application ID.
		Associated Device Crm : associate a device with an
						existing connection.
		The terminal DSP uese the Only the 'fixedClassCrm' 
		could be supported by this implementation."
	DEFVAL          { fixedClassCrm }       
	::= { dspCuEntry  13 }

	      
 dspCuPacketSize        OBJECT-TYPE
	SYNTAX          PacketSize 
	ACCESS          read-write
	STATUS          mandatory
	DESCRIPTION
		"The receive and transmit packet size."
	DEFVAL {  bytes128 }
	::= { dspCuEntry 14 }

 dspCuThroughput        OBJECT-TYPE
	SYNTAX          ThruputClass
	ACCESS          read-write
	STATUS          mandatory
	DESCRIPTION
		"The receive and transmit throughput class across the line. "
	DEFVAL { bps9600 }
	::= { dspCuEntry 15 }

  dspCuPartner          OBJECT-TYPE
	SYNTAX          DspPartner
		ACCESS          read-write
	STATUS                  mandatory
	DESCRIPTION
		"This object identifies the knowledge  DSP has about its BSC partner layer 
		and applies to the controllers acting as Terminal Interface. In normal conditions,
		the DSP and BSC layers are configured both having the same interface type (HIU 
		or TIU). This is the default configuration and it enables the controller the be 
		the initiator of the X25 connection. The host can't establish an X25 connection 
		in this configuration. 
		When the Host is the call establishment initiator, this object could be 
		configured as Host (HIU) type and the local BSC as (TIU), meaning that the DSP 
		will behave as a HIU during the call establishment. This object is used just 
		during the call establishment.  There are the following options available: 
		terminal-terminal       DSP and BSC layers are configured as hosts.
		host-terminal           DSP is configured as host and behaves as a terminal. BSC is configured  
		                        as a  terminal."
	DEFVAL { terminal-terminal }
	::= { dspCuEntry  16 }
	
-- gap (22) to gap (24) for future Parameters
-- Control
dspCuControl            OBJECT-TYPE
	SYNTAX            INTEGER        {
				clearStats         (1)
			}
	ACCESS          write-only
	STATUS                  mandatory
	DESCRIPTION
		"Control associated with the specified service access point."
	::= { dspCuEntry  25}

-- gap (20) to gap (29) for future Parameters
-- Status
dspCuState              OBJECT-TYPE
	SYNTAX  INTEGER        {
			idle                    (1),
			x25-connecting          (2),
			x25-wait-endtoend            (3),       
			x25-connected           (4),
			 unknown                (5)     
			}
	ACCESS           read-only
	STATUS                  mandatory
	DESCRIPTION
		"Control associated with the specified service access point."
	::= { dspCuEntry  30}
		
dspCuOperationalMode     OBJECT-TYPE
	SYNTAX          DspOperationalMode 
	ACCESS          read-only
	STATUS          mandatory
	DESCRIPTION
			"Identifies the controller unit as being
			active or non-active with the new configuration."
	::={ dspCuEntry 31 }

-- gap (30) to gap (39) for future Parameters
-- Statistics
dspCuX25CallRequest             OBJECT-TYPE
	SYNTAX          Counter        
	ACCESS          read-only
	STATUS                  mandatory
	DESCRIPTION
		"Identifies the number of  X25 Call Request packets received
		 by this controller."  
	::= { dspCuEntry  40 }
		
dspCuX25CallAccept              OBJECT-TYPE
	SYNTAX          Counter        
	ACCESS          read-only
	STATUS                  mandatory
	DESCRIPTION
		"Identifies the number of  X25 Call Accept  packets received 
		 by  this  controller."  
	::= { dspCuEntry  41 }

dspCuClears             OBJECT-TYPE
	SYNTAX          Counter        
	ACCESS          read-only
	STATUS                  mandatory
	DESCRIPTION
		"Identifies the number of Clear Request received from the SNALC layer."
		::= { dspCuEntry  42 }

dspCuClearsInd          OBJECT-TYPE
	SYNTAX          Counter        
	ACCESS          read-only
	STATUS                  mandatory
	DESCRIPTION
		"Identifies the number of Clear Indications sent to the SNALC layer."
		::= { dspCuEntry  43 }

dspCuInvToClear         OBJECT-TYPE
	SYNTAX          Counter        
	ACCESS          read-only
	STATUS                  mandatory
	DESCRIPTION
		"Identifies the number of INVITATION TO CLEAR packets 
		received  by this controller."  
	::= { dspCuEntry  44 }
 --  Devices Configuration Table
--      each device is attached to a controller unit. This table contains parameters
--      specifical to different devices atatched to 3270 controller unit family.

dspDevTable             OBJECT-TYPE
	SYNTAX                  SEQUENCE OF DspDevEntry
	ACCESS          not-accessible
	STATUS                  mandatory
	DESCRIPTION
		"A  table  containing configuration information  about
		all the devices controlled by this module. "
	::= { cxDsp 3 }

dspDevEntry             OBJECT-TYPE
	SYNTAX          DspDevEntry
	ACCESS          not-accessible
	STATUS          mandatory    
	DESCRIPTION
			"The parameters for a particular controller unit."       
	INDEX   { 
			dspDevSapNumber,
			dspDevCuAddress,
				dspDevAddress
			}
	::= { dspDevTable 1 }

DspDevEntry ::=
	SEQUENCE {
-- Parameters
	dspDevSapNumber         SapIndex,
	dspDevCuAddress                 DspCuAddress,
	dspDevAddress                   DspDevAddress,
	dspDevRowStatus                 INTEGER,
	dspDevUCN                       INTEGER,
	dspDevRemoteCuAddress           DspCuAddress,
	dspDevRemoteDevAddress  DspDevAddress,
	dspDevFormatSize                INTEGER,        
   dspDevAttPrnt                                INTEGER, 
	dspDevCharSet                   INTEGER,
	dspDevColour                    INTEGER,
	dspDevTTextSupport              INTEGER,
	dspDevDPmode                    INTEGER, 
	
-- Control                
	dspDevControl 		          	  INTEGER,

-- State        
	dspDevOperationalMode           DspOperationalMode, 
	dspDevState                     INTEGER,
	dspDevStatus                    INTEGER,
	dspDevSense                     INTEGER,

-- Statistics
	dspDevCommand                           Counter,
	dspDevResponse                          Counter,                 
	dspDevCmdRspUndel                       Counter,
	dspDevCmdRspUndelReason 					 INTEGER,                
	dspDevCmdRspAbort                       Counter,
	dspDevCmdRspAbortReason 					INTEGER,        
	dspDevStatStatus                        Counter,        
	dspDevAck                                       Counter,
	dspDevInvToClear                        Counter,                        
	dspDevInvClearReason            INTEGER,
	dspDevReset                                     Counter,
	dspDevResetReason                       INTEGER,
	dspDevCircuitEnabled            Counter,                        
   dspDevCircuitRequest         Counter,
	dspDevCircuitDisconnect                 Counter
}
   
--  Parameters
dspDevSapNumber         OBJECT-TYPE
	SYNTAX                  SapIndex
	ACCESS                  read-only
	STATUS                  mandatory
	DESCRIPTION
			"Identifies  the  sap to which  this device 
		is attached to. "
	::= { dspDevEntry  1 }

dspDevCuAddress                 OBJECT-TYPE
	SYNTAX                  DspCuAddress
	ACCESS                  read-only
	STATUS                  mandatory
	DESCRIPTION
		"Identifies  the  address of the controller unit
		 to which  this device is attached. "
	::= { dspDevEntry 2 }

dspDevAddress                   OBJECT-TYPE
	SYNTAX                  DspDevAddress
	ACCESS                  read-only
	STATUS                  mandatory
	DESCRIPTION
		"Identifies the address of this device.  The 
		address has to be unique for a specified for 
		a controller unit."
	::= { dspDevEntry 3 }

dspDevRowStatus                 OBJECT-TYPE
	SYNTAX                  INTEGER {
						invalid        (1),
						valid          (2)
					}
	ACCESS                  read-write
	STATUS                  mandatory
	DESCRIPTION
			"Indicates  whether the particular service  access
			point is configured within the MIB. Controller unit  
		entries (rows) may be created by  setting  this  object  
		value  to  'valid',  or deleted   by   changing  this  
		object value to 'invalid'. Whether  or  not  the  row   
		actually disappears is left to the implementation  so  this
			object  may  actually read as 'invalid'  for  some
			arbitrary length of time."
	::= { dspDevEntry 4 }

dspDevUCN               OBJECT-TYPE
	SYNTAX          INTEGER (0..128)
	ACCESS          read-only
	STATUS          mandatory
	DESCRIPTION
			"Identifies  a specific connection. "
	DEFVAL  { 128 }
	::= { dspDevEntry 5 }

dspDevRemoteCuAddress           OBJECT-TYPE
	SYNTAX          DspCuAddress
	ACCESS          read-write
	STATUS          mandatory
	DESCRIPTION
			" Identifies  the  address of remote controller unit
		 to which  this device is connected. This object is set 
		to 0 if no connection is established. "
	DEFVAL  { 0 }
	::= { dspDevEntry 6 }

dspDevRemoteDevAddress  OBJECT-TYPE
	SYNTAX          DspDevAddress
	ACCESS          read-write
	STATUS          mandatory
	DESCRIPTION
			" Identifies  the  address of remote controller unit
		 to which  this device is connected. This object is set 
		to 0 if no connection is established. "
	DEFVAL  { 0 }
	::= { dspDevEntry 7 }

dspDevFormatSize                OBJECT-TYPE
	SYNTAX          INTEGER  {
					char480         (1),
					char960         (2),
					char1920        (3),    
					char2560        (4),
					char3440        (5),
					char3564        (6),
					charReserved1   (7),    
					charReserved2   (8)             
				}
	ACCESS                  read-write
	STATUS                  mandatory
	DESCRIPTION
			"Describes the number of characters suported by the device."
	DEFVAL          { char3440 }
	::= { dspDevEntry 8 }

dspDevAttPrnt                   OBJECT-TYPE
	SYNTAX          INTEGER  {
					noPrinterAttached       (1),
					printerAttached         (2)
				}
	ACCESS                  read-write
	STATUS                  mandatory
	DESCRIPTION
			"Identifies wheather  the device has a printer attached. 
		The device could  be  a display in order to have a printer 
		attached."
	DEFVAL          { noPrinterAttached}
	::= { dspDevEntry 9 }

dspDevCharSet                   OBJECT-TYPE
	SYNTAX          INTEGER  {
					noneCharSet             (1),
					aplCharSet              (2),
					textCharSet             (3),
					aplTextCharSet          (4)
				}
	ACCESS                  read-write
	STATUS                  mandatory
	DESCRIPTION
			"Identifies  the support of different character sets. "
	DEFVAL          { textCharSet }
	::= { dspDevEntry 10 }

dspDevColour                    OBJECT-TYPE
	SYNTAX          INTEGER  {
					colourSuport            (1),
					noColourSuport          (2)
				}
	ACCESS                  read-write
	STATUS                  mandatory
	DESCRIPTION
			"Identifies wheather  the device  supports colours. "
	DEFVAL          { noColourSuport }      
	::= { dspDevEntry  11 }

dspDevTTextSupport              OBJECT-TYPE
	SYNTAX          INTEGER  {
					transparentText         (1),
					nonTransparentText      (2)
				}
	ACCESS                  read-write
	STATUS                  mandatory
	DESCRIPTION
			"Identifies whether it  the device supports transparent text."
	DEFVAL          { nonTransparentText }
	::= { dspDevEntry 12 }

dspDevDPmode                    OBJECT-TYPE
	SYNTAX          INTEGER  {
					display         (1),
					printer         (2)
				}
	ACCESS                  read-write
	STATUS                  mandatory
	DESCRIPTION
			"Identifies wheather  the device is a display or printer."
	DEFVAL          { display }
	::= { dspDevEntry 13 }

-- gap (12) to gap (19) for future Parameters
-- Control                                      

-- Control
dspDevControl            OBJECT-TYPE
	SYNTAX            INTEGER        {
				clearStats         (1)
			}
	ACCESS          write-only
	STATUS                  mandatory
	DESCRIPTION
		"Control associated with the specified service access point."
	::= { dspDevEntry  20}
	

-- gap (21) to gap (29) for future Parameters
-- Status
dspDevOperationalMode   OBJECT-TYPE
	SYNTAX                  DspOperationalMode 
	ACCESS                  read-only
	STATUS                  mandatory
	DESCRIPTION
			"Identifies the controller unit as being active or non-active 
		with the new configuration."
	::={ dspDevEntry 30 }

dspDevState             OBJECT-TYPE
	SYNTAX          INTEGER {
				idle                                    (1),
			 x25-connected          (2),
			 wait-circuit-request    (3),
			wait-circuit-enabled     (4),
			wait-status               (5),
			connected                       (6),
				disconnecting                   (7)     
			 }
	ACCESS          read-only
	STATUS          mandatory
	DESCRIPTION
			"Indicates  the state of the conection.  The state 'invalid'
		means there is no connection. The state 'conected' means 
		the connection is established."
	::= { dspDevEntry 31}

dspDevStatus                    OBJECT-TYPE
	SYNTAX          INTEGER  
	ACCESS                  read-only
	STATUS                  mandatory
	DESCRIPTION
			"This object contains the 'Status' byte, defined by the BSC 
		protocol for 3270 controller unit family. This object and the 
		'bscDevSense '  contain the result of the last operations 
		performed on the device. The controller unit is responsable to 
		set properly this byte."
	::= { dspDevEntry 32 }
      
dspDevSense                     OBJECT-TYPE
	SYNTAX          INTEGER  
	ACCESS                  read-only
	STATUS                  mandatory               
	DESCRIPTION
			"This object contains the 'Sense' byte, defined by the BSC 
		protocol for 3270 controller unit family.  This object and 
		the 'bscDevSense '  contain the result of the last operations 
		performed on the device. The controller unit is responsable to 
		set properly this byte."
	::= { dspDevEntry 33 }

-- gap (30) to gap (39) for future Parameters
-- Statistics

dspDevCommand   OBJECT-TYPE     
	SYNTAX          Counter        
	ACCESS          read-only
	STATUS                  mandatory
	DESCRIPTION
		"Identifies the number of COMAMND packets sent/received
		by the device. Only the host sends the COMMAND packets.
		The host DSP counts the number of packets sent. The
		 terminal DSP counts the number of packets received." 
::= { dspDevEntry  41 }     

dspDevResponse          OBJECT-TYPE     
	SYNTAX          Counter        
	ACCESS          read-only
	STATUS                  mandatory
	DESCRIPTION
		"Identifies the number of RESPONSE  packets sent/received
		by the device. Only the termianl sends RESPONSE packets.
		The host DSP counts the number of packets received. The
		 terminal DSP counts the number of packets sent." 
 ::= { dspDevEntry  42 }     

dspDevCmdRspUndel    OBJECT-TYPE
	SYNTAX          Counter        
	ACCESS          read-only
	STATUS      mandatory
	DESCRIPTION
		"Identifies the number of COMAMND/RESPONSE
UNDELIVERED packets. This object notifies how many packets
were rejected by this device. The host DSP counts the number 
of  COMMAND ABORTED packets received. The terminal DSP
counts the number of RESPONSE ABORTED packets received.. The
error code of the last received packet (COMMAND/REPONSE) is 
kept by the object 'dspDevCmdRspUndelReason'. " 
	::= { dspDevEntry  43 }

dspDevCmdRspUndelReason OBJECT-TYPE
	SYNTAX          INTEGER 			{
 					eot			(1),
 					rvi			(2),
 					ff				(3),
 					timeout		(4),
 					nak			(5),
 					wack			(6),
 					reserved		(7),
 					invalid		(8),
 					ur				(9)
 					}	
	ACCESS          read-only
	STATUS                  mandatory
	DESCRIPTION
		"This object keeps the error code of the last COMAMND/RESPONSE
		UNDELIVERED packet received. When conected to another Memotec 
		device, only the 'wack' reason code could be received. All other
		error codes are managed locally by BSC."
	::= { dspDevEntry  44 }

dspDevCmdRspAbort       OBJECT-TYPE
	SYNTAX          Counter        
	ACCESS          read-only
	STATUS                  mandatory
	DESCRIPTION
		"Identifies the number of COMAMND/RESPONSE ABORTED packets. 
		This object notifies how many packets were aborted  by this device.
		The host DSP counts the number of COMMAND ABORTED packets
		received. The terminal DSP counts the number of RESPONSE ABORTED
		packets received.. The error code of the last received packet 
		(COMMAND/REPONSE) is kept by the object dspDevCmdRspAbortReason. " 
	::= { dspDevEntry  45 }

dspDevCmdRspAbortReason   OBJECT-TYPE
	SYNTAX          INTEGER   			{
							ff				(3),
							timeout		(4),
							nak			(5),
							ste			(10)
							}
	ACCESS          read-only
	STATUS                  mandatory
	DESCRIPTION
		"This object keeps the error code of the last COMAMND/RESPONSE
		ABORTED packet received. When conected to another Memotec 
		device, all the abort cases are managed locally by BSC." 
	::= { dspDevEntry  46 }

dspDevStatStatus                OBJECT-TYPE
	SYNTAX          Counter        
	ACCESS          read-only        
	STATUS                  mandatory
	DESCRIPTION
		"Identifies the number of STATUS packets sent/received. Only the terminal
		sends this packet. The terminal DSP counts the number of packets sent. The
host DSP counts the number of packets received."  
	::= { dspDevEntry  47 }

dspDevAck               OBJECT-TYPE
	SYNTAX          Counter        
	ACCESS          read-only
	STATUS            mandatory
	DESCRIPTION
		"Identifies the number of ACK packets sent by the device. Both host and 
terminal DSPs can sent ACK packets."  
	::= { dspDevEntry  48 }
      
 dspDevInvToClear       OBJECT-TYPE
	SYNTAX          Counter        
	ACCESS          read-only
	STATUS                  mandatory
	DESCRIPTION
		"Identifies the number of INVITATION TO CLEAR  packets received
		 by the device."
	::= { dspDevEntry  49 }

dspDevInvClearReason    OBJECT-TYPE
	SYNTAX          INTEGER  		{
 							userInitiated		(1),
							unidentPkt			(16),
							invStateTrans		(17),
							invDqFormat			(18),
							invDataFormat 		(19),
							timeout				(32),
							facility				(33)
							}     
	ACCESS          read-only
	STATUS                  mandatory
	DESCRIPTION
		"This object keeps the error code of the last COMAMND/RESPONSE
		ABORTED packet received."
	::= { dspDevEntry  50 }

dspDevReset             OBJECT-TYPE
	SYNTAX          Counter        
	ACCESS          read-only
	STATUS                  mandatory
	DESCRIPTION
		"Identifies the number of  RESET packets received by the device."  
	::= { dspDevEntry  51 }

dspDevResetReason       OBJECT-TYPE
	SYNTAX          INTEGER		{
							unidentDqPkt			(16),
							seqErr					(17),
							invDqFormat				(18),
							invDataFormat			(19)	
					 		}
	ACCESS          read-only
	STATUS                  mandatory
	DESCRIPTION
		"This object keeps the error code of the last RESET packet received.."
	::= { dspDevEntry  52 }

dspDevCircuitEnabled    OBJECT-TYPE
	SYNTAX          Counter        
	ACCESS          read-only
	STATUS                  mandatory
	DESCRIPTION
		"Identifies the number of  CIRCUIT ENABLED packets received by 
the device."  
	::= { dspDevEntry  53 }

 dspDevCircuitRequest           OBJECT-TYPE
	SYNTAX          Counter        
	ACCESS          read-only
	STATUS                  mandatory
	DESCRIPTION
		"Identifies the number of CIRCUIT REQUEST packets received by 
the device."
	::= { dspDevEntry  54 }
   
 dspDevCircuitDisconnect        OBJECT-TYPE
	SYNTAX          Counter        
	ACCESS          read-only
	STATUS                  mandatory
	DESCRIPTION
		"Identifies the number of  DISCONNECT packets received by 
the device."  
	::= { dspDevEntry  55 }
	 
		
END
