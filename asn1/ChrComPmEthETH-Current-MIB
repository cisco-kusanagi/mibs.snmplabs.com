ChrComPmEthETH-Current-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmEth				FROM  Chromatis-MIB
	chrComIfifIndex					FROM  ChrComIfifTable-MIB
	TruthValue				FROM  ChrTyp-MIB
	Gauge32				FROM  SNMPv2-SMI;

-- chrComPmEthETH-Current Table

chrComPmEthETH-CurrentTable		OBJECT-TYPE
	SYNTAX		SEQUENCE OF ChrComPmEthETH-CurrentEntry
	MAX-ACCESS	not-accessible
	STATUS		current
	DESCRIPTION
	""
	::= { chrComPmEth 10}

chrComPmEthETH-CurrentEntry		OBJECT-TYPE
	SYNTAX		ChrComPmEthETH-CurrentEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "ETH-Current"
	::= { chrComPmEthETH-CurrentTable  1 }

ChrComPmEthETH-CurrentEntry  ::=
	SEQUENCE  {
	chrComPmEthSuspectedInterval	TruthValue,
	chrComPmEthElapsedTime		Unsigned32	(0..4294967295),
	chrComPmEthSuppressedIntrvls	Gauge32			(0..4294967295),
	chrComPmEthdot3StatsFCSErrors	Gauge32			(0..4294967295),
	chrComPmEthdot3StatsLateCollisions	Gauge32			(0..4294967295),
	chrComPmEthdot3StatsFrameTooLongs	Gauge32			(0..4294967295),
	chrComPmEthdot3StatsInternalMacReceiveErrors Gauge32			(0..4294967295),
	chrComPmEthifInOctets		Gauge32			(0..4294967295),
	chrComPmEthifInUcastPkts		Gauge32			(0..4294967295),
	chrComPmEthifInDiscards		Gauge32			(0..4294967295),
	chrComPmEthifInErrors		Gauge32			(0..4294967295),
	chrComPmEthifOutOctets		Gauge32			(0..4294967295),
	chrComPmEthifOutUcastPkts		Gauge32			(0..4294967295),
	chrComPmEthifInMulticastPkts	Gauge32			(0..4294967295),
	chrComPmEthifInBroadcastPkts	Gauge32			(0..4294967295),
	chrComPmEthifOutMulticastPkts	Gauge32			(0..4294967295),
	chrComPmEthifOutBroadcastPkts	Gauge32			(0..4294967295),
	chrComPmEthchrFrames64Bytes	Gauge32			(0..4294967295),
	chrComPmEthchrFrames65to127Bytes	Gauge32			(0..4294967295),
	chrComPmEthchrFrames128to256Bytes	Gauge32			(0..4294967295),
	chrComPmEthchrFrames257to512Bytes	Gauge32			(0..4294967295),
	chrComPmEthchrFrames513to1024Bytes	Gauge32			(0..4294967295),
	chrComPmEthchrFrames1024toMaxBytes	Gauge32			(0..4294967295),
	chrComPmEthResetPmCountersAction	TruthValue
}

chrComPmEthSuspectedInterval 	OBJECT-TYPE
	SYNTAX		TruthValue
	MAX-ACCESS 	read-only
	STATUS 		current
	DESCRIPTION
	""
	::= { chrComPmEthETH-CurrentEntry  1 }

chrComPmEthElapsedTime 	OBJECT-TYPE
	SYNTAX		Unsigned32	(0..4294967295)
	MAX-ACCESS 	read-only
	STATUS 		current
	DESCRIPTION
	""
	::= { chrComPmEthETH-CurrentEntry  2 }

chrComPmEthSuppressedIntrvls 	OBJECT-TYPE
	SYNTAX		Gauge32			(0..4294967295)
	MAX-ACCESS 	read-only
	STATUS 		current
	DESCRIPTION
	""
	::= { chrComPmEthETH-CurrentEntry  3 }

chrComPmEthdot3StatsFCSErrors 	OBJECT-TYPE
	SYNTAX		Gauge32			(0..4294967295)
	MAX-ACCESS 	read-only
	STATUS 		current
	DESCRIPTION
	""
	::= { chrComPmEthETH-CurrentEntry  4 }

chrComPmEthdot3StatsLateCollisions 	OBJECT-TYPE
	SYNTAX		Gauge32			(0..4294967295)
	MAX-ACCESS 	read-only
	STATUS 		current
	DESCRIPTION
	""
	::= { chrComPmEthETH-CurrentEntry  5 }

chrComPmEthdot3StatsFrameTooLongs 	OBJECT-TYPE
	SYNTAX		Gauge32			(0..4294967295)
	MAX-ACCESS 	read-only
	STATUS 		current
	DESCRIPTION
	""
	::= { chrComPmEthETH-CurrentEntry  6 }

chrComPmEthdot3StatsInternalMacReceiveErrors 	OBJECT-TYPE
	SYNTAX		Gauge32			(0..4294967295)
	MAX-ACCESS 	read-only
	STATUS 		current
	DESCRIPTION
	""
	::= { chrComPmEthETH-CurrentEntry  7 }

chrComPmEthifInOctets 	OBJECT-TYPE
	SYNTAX		Gauge32			(0..4294967295)
	MAX-ACCESS 	read-only
	STATUS 		current
	DESCRIPTION
	""
	::= { chrComPmEthETH-CurrentEntry  8 }

chrComPmEthifInUcastPkts 	OBJECT-TYPE
	SYNTAX		Gauge32			(0..4294967295)
	MAX-ACCESS 	read-only
	STATUS 		current
	DESCRIPTION
	""
	::= { chrComPmEthETH-CurrentEntry  9 }

chrComPmEthifInDiscards 	OBJECT-TYPE
	SYNTAX		Gauge32			(0..4294967295)
	MAX-ACCESS 	read-only
	STATUS 		current
	DESCRIPTION
	""
	::= { chrComPmEthETH-CurrentEntry  10 }

chrComPmEthifInErrors 	OBJECT-TYPE
	SYNTAX		Gauge32			(0..4294967295)
	MAX-ACCESS 	read-only
	STATUS 		current
	DESCRIPTION
	""
	::= { chrComPmEthETH-CurrentEntry  11 }

chrComPmEthifOutOctets 	OBJECT-TYPE
	SYNTAX		Gauge32			(0..4294967295)
	MAX-ACCESS 	read-only
	STATUS 		current
	DESCRIPTION
	""
	::= { chrComPmEthETH-CurrentEntry  12 }

chrComPmEthifOutUcastPkts 	OBJECT-TYPE
	SYNTAX		Gauge32			(0..4294967295)
	MAX-ACCESS 	read-only
	STATUS 		current
	DESCRIPTION
	""
	::= { chrComPmEthETH-CurrentEntry  13 }

chrComPmEthifInMulticastPkts 	OBJECT-TYPE
	SYNTAX		Gauge32			(0..4294967295)
	MAX-ACCESS 	read-only
	STATUS 		current
	DESCRIPTION
	""
	::= { chrComPmEthETH-CurrentEntry  14 }

chrComPmEthifInBroadcastPkts 	OBJECT-TYPE
	SYNTAX		Gauge32			(0..4294967295)
	MAX-ACCESS 	read-only
	STATUS 		current
	DESCRIPTION
	""
	::= { chrComPmEthETH-CurrentEntry  15 }

chrComPmEthifOutMulticastPkts 	OBJECT-TYPE
	SYNTAX		Gauge32			(0..4294967295)
	MAX-ACCESS 	read-only
	STATUS 		current
	DESCRIPTION
	""
	::= { chrComPmEthETH-CurrentEntry  16 }

chrComPmEthifOutBroadcastPkts 	OBJECT-TYPE
	SYNTAX		Gauge32			(0..4294967295)
	MAX-ACCESS 	read-only
	STATUS 		current
	DESCRIPTION
	""
	::= { chrComPmEthETH-CurrentEntry  17 }

chrComPmEthchrFrames64Bytes 	OBJECT-TYPE
	SYNTAX		Gauge32			(0..4294967295)
	MAX-ACCESS 	read-only
	STATUS 		current
	DESCRIPTION
	""
	::= { chrComPmEthETH-CurrentEntry  18 }

chrComPmEthchrFrames65to127Bytes 	OBJECT-TYPE
	SYNTAX		Gauge32			(0..4294967295)
	MAX-ACCESS 	read-only
	STATUS 		current
	DESCRIPTION
	""
	::= { chrComPmEthETH-CurrentEntry  19 }

chrComPmEthchrFrames128to256Bytes 	OBJECT-TYPE
	SYNTAX		Gauge32			(0..4294967295)
	MAX-ACCESS 	read-only
	STATUS 		current
	DESCRIPTION
	""
	::= { chrComPmEthETH-CurrentEntry  20 }

chrComPmEthchrFrames257to512Bytes 	OBJECT-TYPE
	SYNTAX		Gauge32			(0..4294967295)
	MAX-ACCESS 	read-only
	STATUS 		current
	DESCRIPTION
	""
	::= { chrComPmEthETH-CurrentEntry  21 }

chrComPmEthchrFrames513to1024Bytes 	OBJECT-TYPE
	SYNTAX		Gauge32			(0..4294967295)
	MAX-ACCESS 	read-only
	STATUS 		current
	DESCRIPTION
	""
	::= { chrComPmEthETH-CurrentEntry  22 }

chrComPmEthchrFrames1024toMaxBytes 	OBJECT-TYPE
	SYNTAX		Gauge32			(0..4294967295)
	MAX-ACCESS 	read-only
	STATUS 		current
	DESCRIPTION
	""
	::= { chrComPmEthETH-CurrentEntry  23 }

chrComPmEthResetPmCountersAction 	OBJECT-TYPE
	SYNTAX		TruthValue
	MAX-ACCESS 	read-write
	STATUS 		current
	DESCRIPTION
	""
	::= { chrComPmEthETH-CurrentEntry  24 }


END
