-- *****************************************************************
--
-- STN-SYSTEM-MIB.mib:  
--      Spring Tide Networks System MIB file.
--
--
--      Copyright (c) 1999, 2000 by Spring Tide Networks, Inc.
--                      ALL RIGHTS RESERVED       
--
-- *****************************************************************

-- MIB Object definitions for Spring Tide Network System

STN-SYSTEM-MIB DEFINITIONS ::= BEGIN

    IMPORTS
        MODULE-IDENTITY,
        OBJECT-TYPE,
        IpAddress,
        Unsigned32,
        Integer32
                FROM SNMPv2-SMI

        DisplayString,
        TruthValue
                FROM SNMPv2-TC

        MODULE-COMPLIANCE
                FROM SNMPv2-CONF

        stnSystems
                FROM SPRING-TIDE-NETWORKS-SMI;


    stnSystemMIB        MODULE-IDENTITY
       LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION
                "STN System MIB."
        ::= { stnSystems 4 }


    --
    -- Top Level STN System MIB Objects
    --
    stnSystemMIBObjects     OBJECT IDENTIFIER ::= { stnSystemMIB 1 }
    stnSystemMIBConformance OBJECT IDENTIFIER ::= { stnSystemMIB 2 }

    stnSysTimeGroup     OBJECT IDENTIFIER ::= { stnSystemMIBObjects 1 }
    stnSysAttrGroup     OBJECT IDENTIFIER ::= { stnSystemMIBObjects 2 }
    stnSysServersGroup  OBJECT IDENTIFIER ::= { stnSystemMIBObjects 3 }
    stnSysCfgCtrlGroup  OBJECT IDENTIFIER ::= { stnSystemMIBObjects 4 }


    --
    -- STN System Time Group
    --
    stnUTCOffset OBJECT-TYPE
        SYNTAX          Unsigned32
        MAX-ACCESS      read-only
        STATUS          current
        DESCRIPTION     "Specifies the number of hours to add or subtract
                         from the universal time constant (UTC) when
                         converting to local time."
        DEFVAL          { 0 }
        ::= { stnSysTimeGroup 1 }

    stnDaylightTime OBJECT-TYPE
        SYNTAX          TruthValue
        MAX-ACCESS      read-only
        STATUS          current
        DESCRIPTION     "Specifies whether the system should adjust local
                         time to compensate for daylight savings time."
        DEFVAL          { 1 }
        ::= { stnSysTimeGroup 2 }

    stnTimeSource OBJECT-TYPE
        SYNTAX          INTEGER {
                                internal(1),
                                external-NTP(2),
                                external-RC868(3),
                                all(4)
                                }
        MAX-ACCESS      read-only
        STATUS          current
        DESCRIPTION     "Specifies which sources the system should use
                         attempting to obtain the current time."
        DEFVAL          { all }
        ::= { stnSysTimeGroup 3 }

    stnRFC868Server OBJECT-TYPE
        SYNTAX          IpAddress
        MAX-ACCESS      read-only
        STATUS          current
        DESCRIPTION     "If an NTP server is to be used as a time source,
                         this value specifies the IP address of the server
                         to query."
        ::= { stnSysTimeGroup 4 }

    stnNTPServer OBJECT-TYPE
        SYNTAX          IpAddress
        MAX-ACCESS      read-only
        STATUS          current
        DESCRIPTION     "If an RFC-868 server is to be used as a time
                         source this value specifies the IP address of the
                         server to query."
        ::= { stnSysTimeGroup 5 }

    stnQueryTime OBJECT-TYPE
        SYNTAX          INTEGER (0..600)
        MAX-ACCESS      read-only
        STATUS          current
        DESCRIPTION     "Specifies the time in seconds that the ETS should 
                         continue an external query for a network based time
                         server."
        DEFVAL          { 300 }
        ::= { stnSysTimeGroup 6 }

    --
    -- STN System Attribute Group
    --

    stnDeviceIPAddress OBJECT-TYPE
        SYNTAX          IpAddress
        MAX-ACCESS      read-only
        STATUS          current
        DESCRIPTION     "The main IP address of the ETS."
        ::= { stnSysAttrGroup 1 }

    stnDeviceSubnetMask OBJECT-TYPE
        SYNTAX          IpAddress
        MAX-ACCESS      read-only
        STATUS          current
        DESCRIPTION     "The IP subnet mask of the ETS."
        ::= { stnSysAttrGroup 2 }

    stnSocketDelay OBJECT-TYPE
        SYNTAX          INTEGER (0..60)
        MAX-ACCESS      read-only
        STATUS          current
        DESCRIPTION     "The number of seconds that the ETS will wait
                         on a socket while sending and receiving data
                         to or from the management application before
                         considering the socket dead."
        DEFVAL          {5}
        ::= { stnSysAttrGroup 3 }

    stnDumpMode OBJECT-TYPE
        SYNTAX          INTEGER {
                                none(1),
                                core(2),
                                context(3),
                                log(4)
                                }
        MAX-ACCESS      read-only
        STATUS          current
        DESCRIPTION     "Specifies the type of crash dump to execute 
                        following a crash."
        DEFVAL          {none}
        ::= { stnSysAttrGroup 4 }

    --
    -- STN System Servers Group
    --

    stnTelnetServerEnabled OBJECT-TYPE
        SYNTAX          TruthValue
        MAX-ACCESS      read-only
        STATUS          current
        DESCRIPTION     "Enable Telnet support for external communications."
        DEFVAL          {true}
        ::= { stnSysServersGroup 1 }

    stnFTPServerEnabled OBJECT-TYPE
        SYNTAX          TruthValue
        MAX-ACCESS      read-only
        STATUS          current
        DESCRIPTION     "Enable FTP support for external communications."
        DEFVAL          {true}
        ::= { stnSysServersGroup 2 }

    stnDNSServerEnabled OBJECT-TYPE
        SYNTAX          TruthValue
        MAX-ACCESS      read-only
        STATUS          current
        DESCRIPTION     "Enable DNS support."
        DEFVAL          {false}
        ::= { stnSysServersGroup 3 }


    --
    -- STN System Configuration Control Group
    --
    stnSysCfgCtrlNfsHost OBJECT-TYPE
        SYNTAX          IpAddress
        MAX-ACCESS      read-only
        STATUS          current
        DESCRIPTION     "Specifies the IP address of an NFS server which
                         can optionally be used for automatic backup
                         of configuration files."
        ::= { stnSysCfgCtrlGroup 1 }

    stnSysCfgCtrlNfsPath OBJECT-TYPE
        SYNTAX          DisplayString (SIZE(0..128))
        MAX-ACCESS      read-only
        STATUS          current
        DESCRIPTION     "Specifies the path to  an NFS server which
                         can optionally be used for automatic backup
                         of configuration files."
        ::= { stnSysCfgCtrlGroup 2 }

    stnSysCfgCtrlCommitToFlashTimeout OBJECT-TYPE
        SYNTAX          Integer32
        MAX-ACCESS      read-only
        STATUS          current
        DESCRIPTION     "Specifies the amount of time in seconds the system
                         will wait before saving committed configuration
                         changes to flash disk."
        DEFVAL          { 20 }
        ::= { stnSysCfgCtrlGroup 3 }

    --
    --
    -- Conformance information
    --
    --

END
