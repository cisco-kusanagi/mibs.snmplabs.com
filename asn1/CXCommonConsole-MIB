CXCommonConsole-MIB DEFINITIONS ::= BEGIN

IMPORTS
	OBJECT-TYPE     FROM RFC-1212
	DisplayString           FROM RFC1213-MIB

--  Proprietary Imports
	cxCommonConsole, Alias  
				FROM CXProduct-SMI;

cxCcInactivityTimer     OBJECT-TYPE
	SYNTAX  INTEGER
	ACCESS  read-write
	STATUS  mandatory
	DESCRIPTION
"Determines the amount of time (in seconds) that the Common Console will 
wait for input before terminating a user session. The user must logon 
again and start a new session to continue.

Range of Values: 10 - 65,535

Default Value: 300

Configuration Changed: operative"
	DEFVAL          { 300 }
	::= { cxCommonConsole 1 }

cxCcPassword            OBJECT-TYPE
	SYNTAX  DisplayString (SIZE (6..16))
	ACCESS  write-only
	STATUS  mandatory
	DESCRIPTION
"Determines the password required to logon through the CX1000 console port 
to the Common Console module. The password must be between 6 and 16 
alphanumeric characters in length.

Default Value: supervisor

Configuration Changed: operative"
	DEFVAL  { "Supervisor" }
	::= { cxCommonConsole 2 }


cxCcPrompt              OBJECT-TYPE
	SYNTAX  DisplayString (SIZE (1..16))
	ACCESS  read-write
	STATUS  mandatory
	DESCRIPTION
"Determines the prompt that will appear after logging on to and 
establishing a session with the Common Console to prompt the user for the 
next command.

Range of Values: from 1 to 16 alphanumeric characters

Default Value: Common Console

Configuration Changed: operative"
	DEFVAL  { "Common Console" }
	::= { cxCommonConsole 3 }

cxCcLogDevice   OBJECT-TYPE
	SYNTAX  INTEGER {
				disabled        (1),
				enabled (2)
				}
	ACCESS  read-write
	STATUS  mandatory
	DESCRIPTION
"Establishes the operational status (enabled or disabled) of the logging 
device within the chassis. If enabled, the Common Console will send 
system-generated messages to a log located in 'cxCcLogDeviceSlot'.

Options:
disabled (1): no events written to the log file

enabled (2): events written to the log file

Default Value: enabled (2)

Related Objects:
cxCcLogDeviceSlot

Configuration Changed: operative"
	DEFVAL  { enabled }
	::= { cxCommonConsole 4 }

cxCcLogDeviceSlot       OBJECT-TYPE
	SYNTAX  INTEGER
	ACCESS  read-write
	STATUS  mandatory
	DESCRIPTION
"Establishes the physical slot number in the local chassis where the 
logging device is located. All log messages produced locally are routed to 
this slot. However, if this slot is more than one hop away from the 
current Common Console, messages are discarded. If the value of this 
object is set to '0', the console considers that there is no logging 
device in this chassis and sends log messages to all endpoints connected 
to the local User Interface.

Range of Values: 1 - 16

Default Value: 0

Configuration Changed: operative"
	DEFVAL  { 0 }
	::= { cxCommonConsole 5 }

cxCcQueueDepth  OBJECT-TYPE
	SYNTAX  INTEGER (1..128)
	ACCESS  read-write
	STATUS  mandatory
	DESCRIPTION
"Determines the maximum number of log messages that are retained in the 
console device output when the console device is flow-controlled 
(XOFF'ed). Once the maximum number of log messages is attained, the Common 
Console module discards new log messages targeted for the console device.

Range of Values: 0 - 218

Default Value: 0

Configuration Changed: administrative"
	DEFVAL  { 0 }
	::= { cxCommonConsole 6 }

cxCcRemoteTable OBJECT-TYPE
	SYNTAX  SEQUENCE OF CxCcRemoteEntry
	ACCESS  not-accessible
	STATUS  mandatory
	DESCRIPTION
"A table containing the locally defined network access required to connect 
to the remote Common Console module."
	::= { cxCommonConsole 7 }

	cxCcRemoteEntry         OBJECT-TYPE
		SYNTAX  CxCcRemoteEntry
		ACCESS  not-accessible
		STATUS  mandatory
		DESCRIPTION
"Entry defining the network access."
		INDEX { cxCcRemoteIndex }
		::= { cxCcRemoteTable 1 }

	CxCcRemoteEntry ::=
		SEQUENCE {
			cxCcRemoteIndex
				INTEGER,
			cxCcRemoteDestAlias
				Alias,
			cxCcRemoteRowStatus
				INTEGER
			}


	cxCcRemoteIndex         OBJECT-TYPE
		SYNTAX  INTEGER
		ACCESS  read-only
		STATUS  mandatory
		DESCRIPTION
"Index for table management only. No other MIB object refers to this 
index."
		::= { cxCcRemoteEntry 1 }

	cxCcRemoteDestAlias OBJECT-TYPE
		SYNTAX  Alias
		ACCESS  read-write
		STATUS  mandatory
		DESCRIPTION
"Identifies the name used to query the IAM module to resolve the location 
of this network service.

Range of Values: 0 to 15 alphanumeric characters beginning with an 
alphabetic character

Configuration Changed: operative"
		::= { cxCcRemoteEntry 2 }

	cxCcRemoteRowStatus OBJECT-TYPE
		SYNTAX  INTEGER {
					invalid         (1),
					valid           (2)
					}
		ACCESS  read-write
		STATUS  mandatory
		DESCRIPTION
"Indicates if this entry in the table is valid. The entry may be deleted 
when this object is set to 'invalid'. Once deleted, the entry can not be 
read back.

Options:
invalid (1): entry can be deleted

valid (2): entry is still in use and should not be deleted

Default Value: valid (2)

Configuration Changed: administrative"
		::= { cxCcRemoteEntry 3 }

END
