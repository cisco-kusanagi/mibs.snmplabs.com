MC2350-MIB DEFINITIONS ::= BEGIN

-- MC2350-MIB
--    Ver02   2003.08.20
--                      mib@bpus.konicaminolta.us

--  3.0   Initial Release
--  3.10  Modified Version
--  3.10A	(MQI - 10/14/02 SM) mltTonerTypeCount syntax to counter32.
--  3.10B	(MQI - 10/31/02 SM) corrections to file based on Augusta MIB spec.
--  3.10C	(MQI - 02/13/03 SM) correction to file based on Augusta MIB Spec ver2.7.
--          mltPrtOverlay & mltPrtColorMatching groups removed.
--  ver01   (07/30/03 S.Makam) Based of 3.10C; for MC2350 KM re-brand product. 
--			changed the name of the MIB module from "MQI-MIB" to "MC2350-MIB".
--	ver02	(08/20/03 S.Makam) changed emial ID for re-brand.
   

-- This Private MIB has the basic information which Network
-- Management Utility (PageScope netcare etc.) refers to.
-- The device that has network interface should implement 
-- this private MIB. 
                                                                        

IMPORTS


	TEXTUAL-CONVENTION FROM SNMPv2-TC
   TimeTicks, enterprises, NetworkAddress,
   IpAddress, Counter            FROM RFC1155-SMI
   DateAndTime                   FROM SNMPv2-TC
   OBJECT-TYPE                   FROM RFC-1212
   Counter32, Integer32                     FROM SNMPv2-SMI
   DisplayString, PhysAddress    FROM RFC1213-MIB
   hrDeviceIndex                 FROM HOST-RESOURCES-MIB;

    minolta            OBJECT IDENTIFIER ::= { enterprises 2590 }
    mltMgmt            OBJECT IDENTIFIER ::= { minolta 1 }
    mltDirectory       OBJECT IDENTIFIER ::= { minolta 2 }

    mltMib             OBJECT IDENTIFIER ::= { mltMgmt 1 }

    mltSystem          OBJECT IDENTIFIER ::= { mltMib 1 }
    mltInterface       OBJECT IDENTIFIER ::= { mltMib 2 }
    mltDevice          OBJECT IDENTIFIER ::= { mltMib 3 }
    mltJob             OBJECT IDENTIFIER ::= { mltMib 4 }

    mltPrinter         OBJECT IDENTIFIER ::= { mltSystem 1 }
    mltSysMib          OBJECT IDENTIFIER ::= { mltSystem 5 }

    mltNetwork        OBJECT IDENTIFIER ::= { mltInterface 1 }
    mltNetworkMib     OBJECT IDENTIFIER ::= { mltNetwork 5 }

    mltJobManagement   OBJECT IDENTIFIER ::= { mltJob 1 }


  CodedCharSet ::= TEXTUAL-CONVENTION
      STATUS     mandatory
      DESCRIPTION
         "A coded character set value that specifies both a set of
          characters that may be used and an encoding (as one or more
          octets) that is used to represent the characters in the
          set. These values are to be used to identify the encoding
          employed for strings in the MIB where this is not fixed by
          the MIB.
          "
      -- This is a type 3 enumeration.
      SYNTAX     INTEGER {
        other(1)               -- used if the designated coded
                               -- character set is not currently in
                               -- the enumeration
      -- See IANA Registry for standard character sets in the
      -- MIBenum range of 3-999.

      -- See IANA Registry for Unicode and vendor-supplied
      -- combinations of ISO collections and character sets based
      -- on Unicode in the MIBenum range of 1000-1999.
      -- See IANA Registry for vendor developed character sets
      -- in the MIBenum range of 2000-xxxx.
   }


--
-- Private Printer MIB 
--

    mltPrinterMib      OBJECT IDENTIFIER ::= { mltPrinter 6 }
       mltPrtMibInfo    OBJECT IDENTIFIER ::= { mltPrinterMib 1 }
       mltPrtCommand    OBJECT IDENTIFIER ::= { mltPrinterMib 4 }
       mltPrtConfig     OBJECT IDENTIFIER ::= { mltPrinterMib 5 }
       mltPrtFont       OBJECT IDENTIFIER ::= { mltPrinterMib 6 }
       mltPrtPaper      OBJECT IDENTIFIER ::= { mltPrinterMib 7 }
       mltPrtRemotePanel   OBJECT IDENTIFIER ::= { mltPrinterMib 10 }


-- mltPrtMibInfo Group
--  The standardization version of Private PrinterMIB.


    mltPrtMibVersion  OBJECT-TYPE
        SYNTAX     DisplayString (SIZE (0..7))
        ACCESS     read-only
        STATUS     mandatory
        DESCRIPTION
        " 
        The standardization version of MIB implemented in a printer.
        This indicates the version of the Private Printer
        MIB that is implemented.
        There are some mib objects that indicate the Mib Version.
        (mltSysMibVersion, mltPrtMibVersion, mltScnMibVersion,
        mltNetMibVersion, mltJmMibVersion) But, the each mib version 
        should be same version. 
        Especially, the each major versions must be same.
        
        A string specifying Printer MIB Standard specification
        version. General form is ##.XX.  
        ## is indicating major revision, and XX is 
        minor revision. Decimal point is ASCII-coded period.
        "  
    ::= { mltPrtMibInfo 1 }


-- mltPrtCommand Group

-- The command information for performing various commands
-- to a printer, control of printing job, and printing of
-- ConfigPage, etc. are included.

     mltPrtCommandTable  OBJECT-TYPE
        SYNTAX     SEQUENCE OF MltPrtCommandEntry
        ACCESS     not-accessible
        STATUS     mandatory
        DESCRIPTION
        "
        The table for showing the command information of 
        printer relation. This table must be implemented 
        even if no function in this table are supported 
        by a model. 
        "
    ::= { mltPrtCommand 1 }

    mltPrtCommandEntry OBJECT-TYPE
        SYNTAX      MltPrtCommandEntry
        ACCESS      not-accessible
        STATUS      mandatory
        DESCRIPTION
        "
        An entry exists in this table for each
        device entry in the hostmib device table whose type
        is 'printer'.
        "
      INDEX  { hrDeviceIndex }
      ::= {mltPrtCommandTable 1 }

    MltPrtCommandEntry ::= SEQUENCE {
        mltPrtCommandOnline        INTEGER,
        mltPrtCommandJobCancel     INTEGER,
        mltPrtCommandJobProceed    INTEGER
        }

    mltPrtCommandOnline  OBJECT-TYPE
        SYNTAX   INTEGER{
                    notSupported (0),
                    onLine (1),
                    offLine (2)
                    }
        ACCESS   read-write
        STATUS   mandatory
        DESCRIPTION
        "
        Indicate printer online or offline.
        If printer has no online button,
        this value should be notSupported (0) as read-only.
        "
        ::= { mltPrtCommandEntry 1 }

    mltPrtCommandJobCancel  OBJECT-TYPE
         SYNTAX   INTEGER{
                    notSupported (0),
                    notCancel (1),
                    jobCancel (2)
                    }
         ACCESS   read-write
         STATUS   mandatory
         DESCRIPTION
         "
         Command of cancel job.
         If printer has not job cancel function,
         this value should be notSupported (0) as read-only.
         In normal condition, this value should 
         be notCancel (1). If canceling job, 
         set this object jobCancel (2).
         "
         ::= { mltPrtCommandEntry 2 }

    mltPrtCommandJobProceed  OBJECT-TYPE
        SYNTAX   INTEGER{
                    notSupported (0),
                    notProceed (1),
                    jobProceed (2)
                    }
        ACCESS   read-write
        STATUS   mandatory
        DESCRIPTION
        "
        Command of proceeds.
        If printer has not proceed function,
        this value should be notSupported (0) as read-only.
        In normal condition, this value should 
        be notProceed (1). If proceeding job, 
        set this object proceed (2).
        "
        ::= { mltPrtCommandEntry 3 }


    mltPrtPrintPageTable  OBJECT-TYPE
        SYNTAX     SEQUENCE OF MltPrtPrintPageEntry
        ACCESS     not-accessible
        STATUS     mandatory
        DESCRIPTION
        "
        A table of printable configuration print.
        If a printer does not support print the test pages 
        from network access, this table needs not to be implemented.
        "
        ::= { mltPrtCommand 2 }

    mltPrtPrintPageEntry OBJECT-TYPE
        SYNTAX      MltPrtPrintPageEntry
        ACCESS      not-accessible
         STATUS      mandatory
         DESCRIPTION
          "Information about printer's configuration prints.
           Entries may exist in the table for each device
           index whose device type is 'printer'.
          "
        INDEX  { hrDeviceIndex, mltPrtPrintPageIndex }
        ::= {mltPrtPrintPageTable 1 }

    MltPrtPrintPageEntry ::= SEQUENCE {
        mltPrtPrintPageIndex     INTEGER,
        mltPrtPrintPageName      DisplayString,
        mltPrtPrintCommand       INTEGER
        }

    mltPrtPrintPageIndex  OBJECT-TYPE
        SYNTAX   INTEGER (0..65535) 
        ACCESS   read-only
        STATUS   mandatory
        DESCRIPTION
        "
        Index for uniquely distinguishing the page held within a printer.
        Although the value of index depends on an implementation, 
        "
        ::= { mltPrtPrintPageEntry 1 }

    mltPrtPrintPageName  OBJECT-TYPE
        SYNTAX   DisplayString (SIZE(0..31))
        ACCESS   read-only
        STATUS   mandatory
        DESCRIPTION
        "
        The name of the page, which can be printed.
        The value that should be implemented depends
        on an implementation of a model and it should
        be common with a manual etc.
        "
        ::= { mltPrtPrintPageEntry 2 }

     mltPrtPrintCommand  OBJECT-TYPE
        SYNTAX   INTEGER{
                    supported (1),
                    print (2)
                    }
        ACCESS   read-write
        STATUS   mandatory
        DESCRIPTION
        "
        Command of print page.
        In normal condition , this value should 
        be supported (1).
        If print page, set this object print (2).
        "
       ::= { mltPrtPrintPageEntry 3 }


-- mltPrtConfig Group

-- This group shows the various setup information of a printer.

    mltPrtSysConfigTable  OBJECT-TYPE
        SYNTAX     SEQUENCE OF MltPrtSysConfigEntry
        ACCESS     not-accessible
        STATUS     mandatory
        DESCRIPTION
        "
         A table of configurations for printer.
         This table must be implemented even if 
         no functions in this table are supported.
        "
    ::= { mltPrtConfig 1 }

    mltPrtSysConfigEntry OBJECT-TYPE
        SYNTAX      MltPrtSysConfigEntry
        ACCESS      not-accessible
        STATUS      mandatory
        DESCRIPTION
        "
        An entry exists in this table for each
        device entry in the hostmib device table whose type
        is 'printer'.
        "
        INDEX  { hrDeviceIndex }
        ::= {mltPrtSysConfigTable 1 }

    MltPrtSysConfigEntry ::= SEQUENCE {
        mltPrtJobLanguage    INTEGER,
        mltPrtPowerSave      INTEGER,
        mltPrtAutoContinue   INTEGER,
        mltPrtPaperTimeOut   INTEGER,
        mltPrtPsErrorPrint   INTEGER
        }

    mltPrtJobLanguage  OBJECT-TYPE
        SYNTAX   INTEGER {
                    auto (0),
                    pcl (1),
                    ps (2),
                    gdi (3),
                    linePrinter(4),
                    --   Reserved 5 - 6. 
                    other (7)
                    }
        ACCESS   read-write
        STATUS   mandatory
        DESCRIPTION
        "
        Configuration printer job language.
        Only in the case that a printer has a function of
        setting(changing) this default printer language, 
        this object is implemented as RW. 
        In the other case, this object should be implemented as RO.

        In case of PCL/PS printer, default value is Auto(0).
        If necessary, PCL(1)/PS(2) is changeable.
        In case of printer has only one interpreter (PCL or PS),
        this object should be pcl(1) or ps (2) as RO.
        In case of GDI printer, this value is GDI(3) (RO).
        "
        ::= { mltPrtSysConfigEntry 1 }

    mltPrtPowerSave  OBJECT-TYPE
        SYNTAX   INTEGER
        ACCESS   read-write
        STATUS   mandatory
        DESCRIPTION
        "
        Timer value setting before the power save mode is 
        asserted. Unit is minutes.
        If '0' is selected, the controller doesn't enter
        Power Save mode.
        If this value is -1, printer doesn't support power save mode.
        If out of spec value is set, Error is returned.
        "
             ::= { mltPrtSysConfigEntry 2 }

    mltPrtAutoContinue  OBJECT-TYPE
        SYNTAX   INTEGER{
                    notSupported (0),
                    off (1),
                    ac0Sec (2),
                    ac10Sec (3),
                    ac20Sec (4),
                    ac30Sec (5),
                    ac60Sec (6),
                    ac90Sec (7),
                    ac120Sec (8)
                    }
        ACCESS   read-write
        STATUS   mandatory
        DESCRIPTION
        "
        The setting whether printing will automatically
        recover or not when an Error or Caution occurred.

        If a device support only the value of 1(off) and 2(ac0Sec),
        this implementation is allowed.
        "
        ::= { mltPrtSysConfigEntry 3 }

    mltPrtPaperTimeOut  OBJECT-TYPE
        SYNTAX   INTEGER{
                    notSupported(0),
                    off (1),
                    proceedJob (2),
                    cancelJob (3)
                    }
         ACCESS   read-write
         STATUS   mandatory
         DESCRIPTION
         "
         Setting which decides whether automatic recover
         should be proceed or not when an error related to paper 
         occurred.
         "
         ::= { mltPrtSysConfigEntry 4 }

    mltPrtPsErrorPrint  OBJECT-TYPE
        SYNTAX   INTEGER{
                    notSupported (0),
                    off (1),
                    on (2)
                    }
        ACCESS   read-write
        STATUS   mandatory
        DESCRIPTION
        "
        The setting whether the printer prints PostScript Error
        Page when PostScript Error occurred during job processing.
        About PS error, since it is the function of a printer
        controller, all the devices with PS should be implemented
        If a device has no PostScript interpreter, this value
        should be always notSupported(0) as RO.
        "
        ::= { mltPrtSysConfigEntry 5 }


    mltPrtPrintConfigTable  OBJECT-TYPE
        SYNTAX     SEQUENCE OF MltPrtPrintConfigEntry
        ACCESS     not-accessible
        STATUS     mandatory
        DESCRIPTION
        "
        A table of configurations for printer.
        This table must be implemented even if 
        no functions in this table are supported.
        "
    ::= { mltPrtConfig 2 }

    mltPrtPrintConfigEntry OBJECT-TYPE
        SYNTAX      MltPrtPrintConfigEntry
        ACCESS      not-accessible
        STATUS      mandatory
        DESCRIPTION
        "
        An entry exists in this table for each
        device entry in the hostmib device table whose type
        is 'printer'
        "
        INDEX  { hrDeviceIndex }
        ::= { mltPrtPrintConfigTable 1 }

    MltPrtPrintConfigEntry ::= SEQUENCE {
         mltPrtCopies       INTEGER,
         mltPrtPaperSize    INTEGER,
         mltPrtPaperSource  INTEGER,
         mltPrtFineArt      INTEGER,
         mltPrtTonerSave    INTEGER
         }

    mltPrtCopies  OBJECT-TYPE
        SYNTAX   INTEGER
        ACCESS   read-write
        STATUS   mandatory
        DESCRIPTION
        "
        The number of printing copies.
        If set value is over limit, printer should return error.

        About device which has no PCL interpreter, 
        This value should be -1, because of no default copies setting.
        "
        ::= { mltPrtPrintConfigEntry 1 }

    mltPrtPaperSize   OBJECT-TYPE
        SYNTAX   INTEGER
        ACCESS   read-write
        STATUS   mandatory
        DESCRIPTION
        "
        Paper size of printing.
        The value of the mltPaperSizeIndex corresponding to
        the current paper size.

        About device which has no PCL interpreter, 
        This value should be -1, because of no default paper size setting.
        "
        ::= { mltPrtPrintConfigEntry 2 }

    mltPrtPaperSource  OBJECT-TYPE
        SYNTAX   INTEGER
        ACCESS   read-write
        STATUS   mandatory
        DESCRIPTION
        "
        Feeders for printing.
        The value of prtInputIndex corresponding to the default
        input sub-unit: that is, this object selects the default
        source of input media.
        If value is 0, this means 'Auto'.

        About device which has no PCL interpreter, 
        This value should be -1, because of no default paper source setting.
        "
        ::= { mltPrtPrintConfigEntry 3 }

    mltPrtFineArt  OBJECT-TYPE
        SYNTAX   INTEGER{
                    notSupported (0),
                    on (1),            -- Use 2step setting
                    offSwitch (2),     -- Use 2step setting
                    dark (3),          -- Use 4step setting
                    medium (4),        -- Use 4step setting
                    light (5),         -- Use 4step setting
                    offStep (6)        -- Use 4step setting
                    }
        ACCESS   read-write
        STATUS   mandatory
        DESCRIPTION
        "
        Smooting setting.
        If printer has no smoothing function, this value should 
        be notSupported(0) and RO.

        If printer supports only On/Off , this value should be 
        on(1) or offSwitch(2).

        If printer supports 4 steps, this value should be 
        dark(3), medium(4), light(5) and  offStep(6). 
        "
        ::= { mltPrtPrintConfigEntry 4 }

    mltPrtTonerSave  OBJECT-TYPE
        SYNTAX   INTEGER{
                    notSupported (0),
                    on (1),
                    off (2)
                    }
        ACCESS   read-write
        STATUS   mandatory
        DESCRIPTION
        "
        Toner saving setting.
        If printer is not supporting toner save function,
        this value should be notSupported(0) and RO.

        If printer is supporting toner save function,
        this value should be on(1) or off(2) and RW.
        "
        ::= { mltPrtPrintConfigEntry 5 }


-- mltPrtFont Group

-- Includes the information about the font, which a printer holds.
-- The printer that does not have a font, such as GDI,
-- does not need to implement this group.


    mltPrtPclFontTable  OBJECT-TYPE
        SYNTAX     SEQUENCE OF MltPrtPclFontEntry
        ACCESS     not-accessible
        STATUS     mandatory
        DESCRIPTION
        "
        This table shows PCL font information of printer has.
        Since it is a function peculiar to PCL, it is not necessary 
        to implement this table in the device in which PCL is not 
        installed or PCL font management function is not installed.
        "
        ::= { mltPrtFont 1 }

    mltPrtPclFontEntry OBJECT-TYPE
        SYNTAX      MltPrtPclFontEntry
        ACCESS      not-accessible
        STATUS      mandatory
        DESCRIPTION
        "
        Information about printer's PCL fonts.
        Entries may exist in the table for each device
        index whose device type is 'printer'.
        "
        INDEX  { hrDeviceIndex, mltPrtPclFontIndex }
      ::= {mltPrtPclFontTable 1 }

    MltPrtPclFontEntry ::= SEQUENCE {
        mltPrtPclFontIndex  INTEGER,
        mltPrtPclFontName   DisplayString,
        mltPrtPclFontNumber INTEGER,
        mltPrtPclFontSource INTEGER
        }

    mltPrtPclFontIndex  OBJECT-TYPE
        SYNTAX   INTEGER (1..65535) 
        ACCESS   read-only
        STATUS   mandatory
        DESCRIPTION
        "
        A unique value used to identify this entry. 
        "
        ::= { mltPrtPclFontEntry 1 }

    mltPrtPclFontName  OBJECT-TYPE
        SYNTAX   DisplayString (SIZE(0..63)) 
        ACCESS   read-only
        STATUS   mandatory
        DESCRIPTION
        "
        The name of PCL Font. 
        "
        ::= { mltPrtPclFontEntry 2 }

    mltPrtPclFontNumber  OBJECT-TYPE
        SYNTAX   INTEGER(0..65535) 
        ACCESS   read-only
        STATUS   mandatory
        DESCRIPTION
        "
        The number of PCL Font. 
        The number for managing the font, which a printer holds inside.
        "
        ::= { mltPrtPclFontEntry 3 }

    mltPrtPclFontSource  OBJECT-TYPE
        SYNTAX   INTEGER{
                    unknown (0),
                    internalRom (1),
                    internalHd (2),
                    downLoadRam (3),
                    downLoadHd (4),
                    downLoadFlashRom (5)
                    }
        ACCESS   read-only
        STATUS   mandatory
        DESCRIPTION
        "
        The information of a place that PCL font exists.
        "
        ::= { mltPrtPclFontEntry 4 }

    mltPrtPsFontTable  OBJECT-TYPE
        SYNTAX     SEQUENCE OF MltPrtPsFontEntry
        ACCESS     not-accessible
        STATUS     mandatory
        DESCRIPTION
        "
        This table shows PostScript font information of printer has.
        Since it is a function peculiar to PS, it is not necessary 
        to implement this table in the device in which PS is not installed.
        "
        ::= { mltPrtFont 2 }

    mltPrtPsFontEntry OBJECT-TYPE
        SYNTAX      MltPrtPsFontEntry
        ACCESS      not-accessible
        STATUS      mandatory
        DESCRIPTION
        "
        Information about printer's PS fonts.
        Entries may exist in the table for each device
        index whose device type is 'printer'.
        "
      INDEX  { hrDeviceIndex, mltPrtPsFontIndex }
      ::= { mltPrtPsFontTable 1 }

    MltPrtPsFontEntry ::= SEQUENCE {
        mltPrtPsFontIndex  INTEGER,
        mltPrtPsFontName   DisplayString,
        mltPrtPsFontNumber INTEGER,
        mltPrtPsFontSource INTEGER
        }

    mltPrtPsFontIndex  OBJECT-TYPE
        SYNTAX   INTEGER (1..65535) 
        ACCESS   read-only
        STATUS   mandatory
        DESCRIPTION
        "
        A unique value used to identify this entry. 
        "
        ::= { mltPrtPsFontEntry 1 }

    mltPrtPsFontName  OBJECT-TYPE
        SYNTAX   DisplayString (SIZE(0..63)) 
        ACCESS   read-only
        STATUS   mandatory
        DESCRIPTION
        "
        The name of PS Font. 
        "
        ::= { mltPrtPsFontEntry 2 }

    mltPrtPsFontNumber  OBJECT-TYPE
        SYNTAX   INTEGER(0..65535) 
        ACCESS   read-only
        STATUS   mandatory
        DESCRIPTION
        "
        The number of PS Font. 
        This number is used in order to administrate
        printer's fonts.
        If a printer does not manage this number, 
        this value should be implemented same as mltPrtPsFontIndex.
        "
        ::= { mltPrtPsFontEntry 3 }

    mltPrtPsFontSource  OBJECT-TYPE
        SYNTAX   INTEGER{
                    unknown (0),
                    internalRom (1),
                    internalHd (2),
                    downLoadRam (3),
                    downLoadHd (4),
                    downLoadFlashRom (5)
                    }
        ACCESS   read-only
        STATUS   mandatory
        DESCRIPTION
        "
        The information of a place that PS font exists
        "
        ::= { mltPrtPsFontEntry 4 }

    mltPrtSymbolSetTable  OBJECT-TYPE
        SYNTAX     SEQUENCE OF MltPrtSymbolSetEntry
        ACCESS     not-accessible
        STATUS     mandatory
        DESCRIPTION
        "
         This table shows symbol sets a printer has. 
         If no function in this table is supported by a device,
         this table needs not to be implemented.
         "
        ::= { mltPrtFont 3 }

    mltPrtSymbolSetEntry OBJECT-TYPE
        SYNTAX      MltPrtSymbolSetEntry
        ACCESS      not-accessible
        STATUS      mandatory
        DESCRIPTION
        "
        Information about printer's symbol sets.
        Entries may exist in the table for each device
        index whose device type is 'printer'.
        "
      INDEX  { hrDeviceIndex, mltPrtSymbolSetIndex }
      ::= {mltPrtSymbolSetTable 1 }

    MltPrtSymbolSetEntry ::= SEQUENCE {
        mltPrtSymbolSetIndex  INTEGER,
        mltPrtSymbolSetName   DisplayString,
        mltPrtCharSetID       INTEGER
        }

    mltPrtSymbolSetIndex  OBJECT-TYPE
        SYNTAX   INTEGER (1..65535) 
        ACCESS   read-only
        STATUS   mandatory
        DESCRIPTION
        "
        A unique value used to identify this entry. 
        "
        ::= { mltPrtSymbolSetEntry  1 }

    mltPrtSymbolSetName  OBJECT-TYPE
        SYNTAX   DisplayString (SIZE(0..31)) 
        ACCESS   read-only
        STATUS   mandatory
        DESCRIPTION
        "
        The name of SymbolSet (CodedCharSet). 
        "
        ::= { mltPrtSymbolSetEntry 2 }

    mltPrtCharSetID  OBJECT-TYPE
        SYNTAX   INTEGER(0..65535) 
        ACCESS   read-only
        STATUS   mandatory
        DESCRIPTION
        "
        The ID of Code CharSet. 
        Refer to the following URL that IANA administrates 
        regarding character code sets:
        http://www.iana.org/assignments/character-sets
        "
        ::= { mltPrtSymbolSetEntry 3 }


-- mltPrtPaperSize Group

-- Includes the information of the paper size, which a printer can print.
-- The paper size showing here should be the size, which printer controller
-- can process (size can specified by a driver).


    mltPrtPaperSizeTable  OBJECT-TYPE
        SYNTAX     SEQUENCE OF MltPrtPaperSizeEntry
        ACCESS     not-accessible
        STATUS     mandatory
        DESCRIPTION
        "
        A table of the printer selectable paper sizes.
        Even if a printer can not recognize the supportable paper, 
        one object ('unknown' or 'other') must be loaded at least. 
        "
        ::= { mltPrtPaper 1 }

    mltPrtPaperSizeEntry OBJECT-TYPE
        SYNTAX      MltPrtPaperSizeEntry
        ACCESS      not-accessible
        STATUS      mandatory
        DESCRIPTION
        "
        An entry exists in this table for each
        device entry in the hostmib device table whose type
        is 'printer'
        "
        INDEX  { hrDeviceIndex, mltPaperSizeIndex }
        ::= {mltPrtPaperSizeTable 1 }

    MltPrtPaperSizeEntry ::= SEQUENCE {
        mltPaperSizeIndex   INTEGER,
        mltPaperSizeName    DisplayString,
        mltPaperFeedDir     INTEGER
        }

    mltPaperSizeIndex  OBJECT-TYPE
        SYNTAX   INTEGER (1..65535) 
        ACCESS   read-only
        STATUS   mandatory
        DESCRIPTION
        "
        A unique value used to identify this entry. 
        "
        ::= { mltPrtPaperSizeEntry  1 }

    mltPaperSizeName  OBJECT-TYPE
        SYNTAX   DisplayString (SIZE(0..31)) 
        ACCESS   read-only
        STATUS   mandatory
        DESCRIPTION
        "
        The name of paper size.
        e.g., letter, legal, A4, B5 etc. 
        "
        ::= { mltPrtPaperSizeEntry  2 }

    mltPaperFeedDir  OBJECT-TYPE
        SYNTAX   INTEGER{
                    other (0),  -- unknown feed direction
                        -- (In the case of supporting both of SEF and LEF)
                    sef (1),   -- Portrait(short edge Feed)
                    lef (2)    -- Landscape(long edge feed) 
                    }
        ACCESS   read-only
        STATUS   mandatory
        DESCRIPTION
        "
        This value shows paper feeding orientation.
        "
        ::= { mltPrtPaperSizeEntry  3 }


-- mltPrtRemotePanel Group

-- Includes the information of the panel of a printer.
-- The implementation of this group should be indispensable
-- when the button that is possible to operate is set to a 
-- printer or a printer controller, and also when remote
-- control is possible.
-- As for the virtual console in the case of not having a
-- physical button, it depends on the implementation of a
-- model and should not require as a standard.


     mltPrtRemotePanelButtonTable  OBJECT-TYPE
        SYNTAX     SEQUENCE OF MltPrtRemotePanelButtonEntry
        ACCESS     not-accessible
        STATUS     optional
        DESCRIPTION
        "
        A table of printer's remote operational panel button.
        "
        ::= { mltPrtRemotePanel 1 }

    mltPrtRemotePanelButtonEntry OBJECT-TYPE
        SYNTAX      MltPrtRemotePanelButtonEntry
        ACCESS      not-accessible
        STATUS      optional
        DESCRIPTION
        "
        An entry exists in this table for each
        device entry in the hostmib device table whose type
        is `printer'
        "
        INDEX  { hrDeviceIndex, mltPrtPanelButtonIndex}
        ::= {mltPrtRemotePanelButtonTable 1 }

    MltPrtRemotePanelButtonEntry ::= SEQUENCE {
        mltPrtPanelButtonIndex       INTEGER,
        mltPrtPanelButtonName        DisplayString,
        mltPrtPanelButtonPush        INTEGER,
        mltPrtPanelButtonDescr       DisplayString
        }

    mltPrtPanelButtonIndex  OBJECT-TYPE
        SYNTAX   INTEGER(0..65535)
        ACCESS   read-only
        STATUS   optional
        DESCRIPTION
        "
        A unique value used by the operational panel button  
        to identify table 
        "
        ::= { mltPrtRemotePanelButtonEntry 1 }

    mltPrtPanelButtonName  OBJECT-TYPE
        SYNTAX   DisplayString (SIZE(0..31))
        ACCESS   read-only
        STATUS   optional
        DESCRIPTION
        "
        The name of panel button.
        "
        ::= { mltPrtRemotePanelButtonEntry 2 }

    mltPrtPanelButtonPush   OBJECT-TYPE
        SYNTAX   INTEGER{
                    noAction (0),
                    push (1),
                    longPush (2),
                    shiftPush (3)
                    }
        ACCESS   read-write
        STATUS   optional
        DESCRIPTION
        "
        This value indicates panel button status, and make 
        pushing button.

        noAction (0)  -- indicate steady.
        push (1)       -- To set 1 means push panel button.
        longPush (2)   -- To set 2 means push button long time.
        shiftPush (3)  -- To set 3 means push panel bottom and shift
                          button same time.
        "
        ::= { mltPrtRemotePanelButtonEntry 3 }
   
    mltPrtPanelButtonDescr  OBJECT-TYPE
        SYNTAX   DisplayString (SIZE(0..127))
        ACCESS   read-only
        STATUS   optional
        DESCRIPTION
        "
        An explanation of panel button function etc.
        "
        ::= { mltPrtRemotePanelButtonEntry 4 }


--
-- Private System MIB 
--


mltSysMibVersion  OBJECT-TYPE
    SYNTAX    DisplayString (SIZE(0..7))
    ACCESS    read-only
    STATUS    mandatory
    DESCRIPTION
        "
         The version information of Standard MIB specification.

         This indicates the version of the Private System MIB 
         which is implemented. 

         General form is AA.BC.
         AA is indicating major revision, and B and C is 
         minor revision. Decimal point is ASCII-coded period.
        "
    ::= { mltSysMib 1 }


    mltSysGeneralInfo          OBJECT IDENTIFIER ::= { mltSysMib 2 }
    mltSysContact              OBJECT IDENTIFIER ::= { mltSysMib 3 }
    mltSysVersion              OBJECT IDENTIFIER ::= { mltSysMib 5 }
    mltSysComponent            OBJECT IDENTIFIER ::= { mltSysMib 6 }
    mltSysCounter              OBJECT IDENTIFIER ::= { mltSysMib 7 }

-- mltSysGeneralInfo Group
-- This group shows the general information of system.  

mltSysPriorityDevice  OBJECT-TYPE
    SYNTAX     INTEGER
    ACCESS     read-write
    STATUS     mandatory
    DESCRIPTION
        "This object shows the function which operates with
         highest priority in a system.
         When it can set up by user choice etc., it should be RW.
         If setup change is impossible from MIB, the implementation
         of RO is acceptable.
         There is no function with highest priority or no preference
         order of function, implement RO as 0.
        "
    ::= { mltSysGeneralInfo 2 }


mltSysCurrentDateTime  OBJECT-TYPE
    SYNTAX     DateAndTime
    ACCESS     read-write
    STATUS     mandatory
    DESCRIPTION
        "Time, which is set in the system and specifies by DateAndTime
         If not having a clock function, implement 0x00 in all Bytes.
        "
    ::= { mltSysGeneralInfo 4 }

-- mltSysContact Group
-- This group shows the contact information of system
-- which is used by PageScope/PageScopeLight.
-- In addition, link these items with the display item of PageScopeLight.
-- Moreover, when it has different value for every shipment destination,
-- the default value should be changed by the shipment destination setup 
-- of a system.


mltSysContactSiteName  OBJECT-TYPE
    SYNTAX    DisplayString(SIZE(0..64))
    ACCESS    read-write
    STATUS    mandatory
    DESCRIPTION
        "The name of a support contact for system.
         If device cannot support this object, device should
         be implement '-' as read-only
        "
    ::= { mltSysContact 1 }

mltSysContactInfo  OBJECT-TYPE
    SYNTAX    DisplayString(SIZE(0..128))
    ACCESS    read-write
    STATUS    mandatory
    DESCRIPTION
        "Explanation of a support contact for system.
         Default value shall be a blank, and a service person
         or a user shall input it.

         If device cannot support this object, device should
         be implement '-' as read-only
        "
    ::= { mltSysContact 2 }

mltSysProductHelpURL  OBJECT-TYPE
    SYNTAX    DisplayString(SIZE(0..128))
    ACCESS    read-write
    STATUS    mandatory
    DESCRIPTION
        "URL of the support contact for system.

         If device cannot support this object, device should
         be implement '-' as read-only
        "
    ::= { mltSysContact 3 }

mltSysCorpURL  OBJECT-TYPE
    SYNTAX    DisplayString(SIZE(0..128))
    ACCESS    read-write
    STATUS    mandatory
    DESCRIPTION
        "URL of the company which provides a system.

         If device cannot support this object, device should
         be implement '-' as read-only
        "
    ::= { mltSysContact 4 }

mltSysSuppliesInfo  OBJECT-TYPE
    SYNTAX    DisplayString(SIZE(0..128))
    ACCESS    read-write
    STATUS    mandatory
    DESCRIPTION
        "A telephone number or E-mail addresses for 
         the supplies and accessories, etc.
         In the support contact in which a system has.
         Default shall be a blank, and a service person
         or a user shall input it.

         If device cannot support this object, device should
         be implement '-' as read-only
        "
    ::= { mltSysContact 5 }


-- mltSysVersion Group

--  This group shows the version of ROM and F/W etc. 
--  in which a system has. 
--  Display the version information in which all detection
--  is possible in a system.
--  Also display the version information of Options, such as NIC.
--  However, if a system can get no version information,
--  this table needs not to implement.


mltSysVersionTable  OBJECT-TYPE
    SYNTAX    SEQUENCE OF MltSysVersionEntry
    ACCESS    not-accessible
    STATUS    mandatory
    DESCRIPTION
        "The table for showing ROM and F/W version in which a system has. 
        "
    ::= { mltSysVersion 1 }

mltSysVersionEntry OBJECT-TYPE
    SYNTAX    MltSysVersionEntry
    ACCESS    not-accessible
    STATUS    mandatory
    DESCRIPTION
        "The version information of FW or ROM.
        "
    INDEX  { mltSysVersionIndex }
    ::= { mltSysVersionTable 1 }

    MltSysVersionEntry ::= SEQUENCE {
        mltSysVersionIndex        INTEGER,
        mltSysVerName             DisplayString,
        mltSysVersionCode         DisplayString,
        mltSysVerDescr            DisplayString
    }

mltSysVersionIndex  OBJECT-TYPE
    SYNTAX     INTEGER
    ACCESS     read-only
    STATUS     mandatory
    DESCRIPTION
        "Index for uniquely showing the version information
         in which a system has. The number and the order of
         index depends on an implementation of a model.
         Implement the maximum number of index of ROM and F/W
         which is possible to detect/display, regardless of
         the availability of installation of Option etc.
         The number of indexes to hold shall be always fixed
         regardless of the option installation state.
        "
    ::= { mltSysVersionEntry 1 }

mltSysVerName  OBJECT-TYPE
    SYNTAX     DisplayString(SIZE(0..31))
    ACCESS     read-only
    STATUS     mandatory
    DESCRIPTION
        "The name of the function which shows a version.
         For example,
         'MSC/Panel ROM Version', 'Printer ROM Version', etc.
        "
    ::= { mltSysVersionEntry 2 }

mltSysVersionCode  OBJECT-TYPE
    SYNTAX     DisplayString(SIZE(0..31))
    ACCESS     read-only
    STATUS     mandatory
    DESCRIPTION
        "The version of ROM and F/W.
         It shall be written by 15 or less characters.
         '[Product Code(4)]-[Block Code(2)][Stage Code(1)]
          [Specification Code(1)]-[Change Management Code(2)]
          -[Shipment Destination Code(2)]' supports.
         For corresponding to the other written methods,
         it was made into the maximum 31 characters, on the 
         definition. When the value cannot acquire although
         index is set by Option etc., display '-' (hyphen).
        "
    ::= { mltSysVersionEntry 3 }

mltSysVerDescr  OBJECT-TYPE
    SYNTAX     DisplayString(SIZE(0..31))
    ACCESS     read-only
    STATUS     mandatory
    DESCRIPTION
        "Explanation of a version. 
         As for the contents to indicate, depends on an 
         implementation of a model. However, 
         since not supporting this object is not acceptable,
         implement Null (Zero-Length) at least.
        "
    ::= { mltSysVersionEntry 4 }


-- mltSysComponent Group

-- This group shows the structure information of a system. 

mltSysCompConfigID  OBJECT-TYPE
    SYNTAX    INTEGER
    ACCESS    read-only
    STATUS    mandatory
    DESCRIPTION
        "Shows the ID by the combination of the structure of Device.
         A project should prepare ID which is worth for the number
         of combination, such as Option.

         If system has no option or cannot detect option installed,
         this value should be always 0.
        "
    ::= { mltSysComponent 1 }


mltSysInputTrayTable  OBJECT-TYPE
    SYNTAX    SEQUENCE OF MltSysInputTrayEntry
    ACCESS    not-accessible
    STATUS    mandatory
    DESCRIPTION
        "The table for showing the information of Input tray 
         that is installed in a system.
         As a principle, the un-acquirable information shall be
         displayed if there is only prtInputTable, and this table
         is premised on that PrinterMIB is being implemented.
         It shall display about InputTray which is installed
         like prtInputTable.

         If a system does not have a printer engine (has no input
         tray and no PrinterMIB), this table does not need to
         implement.
        "
    ::= { mltSysComponent 2 }

mltSysInputTrayEntry OBJECT-TYPE
    SYNTAX    MltSysInputTrayEntry
    ACCESS    not-accessible
    STATUS    mandatory
    DESCRIPTION
        "The information of paper input tray.
        "
    INDEX  { mltSysInputTrayIndex }
    ::= { mltSysInputTrayTable 1 }

    MltSysInputTrayEntry ::= SEQUENCE {
        mltSysInputTrayIndex                INTEGER,
        mltSysInputTrayRefIndex             INTEGER,
        mltSysInputTrayName                 DisplayString,
        mltSysInputTrayCapacitySence        INTEGER,
        mltSysInputTraySpecialPaper         INTEGER,
        mltSysInputTrayPaperAttribute       INTEGER
    }

mltSysInputTrayIndex  OBJECT-TYPE
    SYNTAX    INTEGER
    ACCESS    read-only
    STATUS    mandatory
    DESCRIPTION
        "Index for showing InputTray in a system.
         Index depends on the state of the implementation of
         a model, and shall be taken the amount which is worth
         for the number of InputTray in the order from 1.
        "
    ::= { mltSysInputTrayEntry 1 }

mltSysInputTrayRefIndex  OBJECT-TYPE
    SYNTAX    INTEGER
    ACCESS    read-only
    STATUS    mandatory
    DESCRIPTION
        "The value of prtInputIndex of a tray which
         mltSysInputTrayIndex shows.
        "
    ::= { mltSysInputTrayEntry 2 }

mltSysInputTrayName  OBJECT-TYPE
    SYNTAX    DisplayString(SIZE(0..15))
    ACCESS    read-write
    STATUS    mandatory
    DESCRIPTION
        "The name of InputTray.
         Default value depends on a model. In principle,
         use the name unified by DriverUI.
         Set of the character string up to 15 characters
         shall be possible.
         implementation of RO is also accepted when there are 
         capacity restrictions of NVRAM.

         Since this item is the value used when a user does
         a remote management, it is not necessary to link it
         with a setup of a printer engine.
         SNMP agent holds value, and should just provide the
         convenience to the user who remote accesses.
        "
    ::= { mltSysInputTrayEntry 3 }

mltSysInputTrayCapacitySence  OBJECT-TYPE
    SYNTAX    INTEGER {
                  noSensor    (0),
                  emptyOnly   (1),
                  nearEmpty   (2),
                  linearSense (3)
              }
    ACCESS    read-only
    STATUS    mandatory
    DESCRIPTION
        "This item shows the detection method of paper residual 
         quantity, and is used for distinction of the value
         displayed in prtInputCurrentLevel. The details of a 
         residual quantity display are indicated to 
         prtInputCurrentLevel.
        "
    ::= { mltSysInputTrayEntry 4 }

mltSysInputTraySpecialPaper  OBJECT-TYPE
    SYNTAX    INTEGER {
        other (0),
        unknown (1),
        plainPaper (10),
        plainPaper-NotFor2Sided (11),
        plainPaper-Recycled (12),
        plainPaper-Exclusive (14),
        plainPaper-Color (16),
        thick (20),
        thick1 (22),
        thick1-2side (23),
        thick2 (24),
        thick2-2side (25),
        thick3 (26),
        thick3-2side (27),
        ohp (30),
        thin (36),
        envelope (40),
        envelope-2side (41),
        label (42),
        postCard (44),
        letterHead(46),
        tab (48)
                }
    ACCESS    read-write
    STATUS    mandatory
    DESCRIPTION
        "Shows the media type of InputTray. 
         If this value is RW and when a setup is changed by MIB,
         it shall be reflected in a setup of a printer engine.
         In a unavoidable case, the access way may be RO.
        "
    ::= { mltSysInputTrayEntry 5 }

mltSysInputTrayPaperAttribute  OBJECT-TYPE
    SYNTAX    INTEGER {
                notSupported (0),
                s0-normalPaper (1),
                s1-recyclePaper (2),
                s2-specialPaper (3),
                s3-reusePaper (4)
                }
    ACCESS    read-write
    STATUS    optional
    DESCRIPTION
        "Shows the paper attribute of InputTray. 
         If this value is RW and when a setup is changed by MIB,
         it shall be reflected in a setup of a printer engine.
         In a unavoidable case, the access way may be RO.
        "
    ::= { mltSysInputTrayEntry 6 }


mltSysOutputTrayTable  OBJECT-TYPE
    SYNTAX    SEQUENCE OF MltSysOutputTrayEntry
    ACCESS    not-accessible
    STATUS    mandatory
    DESCRIPTION
        "The table for showing the information of OutputTray
         relation in a system. Index shall be mltSysOutputTrayIndex.
         This table is for displaying the tray information of
         OutputOption (Finisher), and shall not include the
         function information of Finisher.
         If a system does not have a printer engine 
         (has no output tray and no PrinterMIB),
         this table may not be implemented.
        "
    ::= { mltSysComponent 3 }

mltSysOutputTrayEntry OBJECT-TYPE
    SYNTAX    MltSysOutputTrayEntry
    ACCESS    not-accessible
    STATUS    mandatory
    DESCRIPTION
        "The information of paper output tray.
        "
    INDEX  { mltSysOutputTrayIndex }
    ::= { mltSysOutputTrayTable 1 }

    MltSysOutputTrayEntry ::= SEQUENCE {
        mltSysOutputTrayIndex              INTEGER,
        mltSysOutputTrayRefIndex           INTEGER,
        mltSysOutputTrayDefaultName        DisplayString,
        mltSysOutputTrayNickName           DisplayString,
        mltSysOutputTrayType               INTEGER
    }

mltSysOutputTrayIndex  OBJECT-TYPE
    SYNTAX    INTEGER
    ACCESS    read-only
    STATUS    mandatory
    DESCRIPTION
        "Index for showing OutputTray in a system. 
         Index depends on the implementation of a model,
         and shall be taken the amount which is worth for
         the number of Output in the order from 1.
         In principle, when the top tray is set as 1, 
         index shall be increased in progress of going to 
         the lower part. As for the middle processing tray
         that does not become papers' final output destination,
         is not treated as OutputTray.
        "
    ::= { mltSysOutputTrayEntry 1 }

mltSysOutputTrayRefIndex  OBJECT-TYPE
    SYNTAX    INTEGER
    ACCESS    read-only
    STATUS    mandatory
    DESCRIPTION
        "Value of prtOutputIndex of the tray which 
         mltSysOutputTrayIndex shows.
        "
    ::= { mltSysOutputTrayEntry 2 }

mltSysOutputTrayDefaultName  OBJECT-TYPE
    SYNTAX    DisplayString(SIZE(0..31))
    ACCESS    read-only
    STATUS    mandatory
    DESCRIPTION
        "The name of OutputTray. Unify with the notation of
         a manual or a driver.
        "
    ::= { mltSysOutputTrayEntry 3 }

mltSysOutputTrayNickName  OBJECT-TYPE
    SYNTAX    DisplayString(SIZE(0..15))
    ACCESS    read-write
    STATUS    mandatory
    DESCRIPTION
        "The name of OutputTray in which a user can set up.
         In MailBin, use it in order to indicate a user's
         name, etc. which each Tray set up.
         The recommendation default is the same as mltSysOutputTrayDefaultName.

         Set of the character string up to 15 characters shall be possible,
         and neither retrenchment of the number of characters
         which can be written in, nor implementation of RO
         shall be accepted.
         However, the implementation of RO is accepted only
         to the thing without MailBin as OutputOption.
         Moreover, being reflected in the display screen of
         a printer driver is desirable.
         Since this item is the value used when a user does
         a remote management, it is not necessary to link it
         with a setup of a printer engine. SNMP agent holds value,
         and should just provide the convenience to the user who
         remote accesses.

         If device cannot support this function, this object 
         should be '-' as ReadOnly.
        "
    ::= { mltSysOutputTrayEntry 4 }

mltSysOutputTrayType  OBJECT-TYPE
    SYNTAX    INTEGER {
                  other        (0),
                  standardBin  (1),
                  sortBin      (3),
                  mailBox      (4),
                  fixedMailBin (5)
              }
    ACCESS    read-only
    STATUS    mandatory
    DESCRIPTION
        "Shows the type of tray in OutputTray. 
         This is an item for judging whether it is MailBin,
         and it is used in order to judge whether the writing
         of NickName should be possible.
        "
    ::= { mltSysOutputTrayEntry 5 }

-- mltSysCounter Group

--   Group of the counter relation corresponding to the account
--   management system. 
--
--   It shall have the following 3 groups.
--   1. mltSysCounterConfig Group
--        The setup item relevant to whole counter
--   2. mltSysSystemCounter Group
--        The counter item which a device has
--
--   In addition, Syntax of all the counters defined in
--   mltSysCounterGroup shall be Integer32, and when a model
--   does not support the defined counter, should implement -1.
--

    mltSysCounterConfig    OBJECT IDENTIFIER ::= { mltSysCounter 1 }
    mltSysSystemCounter    OBJECT IDENTIFIER ::= { mltSysCounter 2 }

-- mltSysCounterConfig Group

mltSysSupportedCounterType  OBJECT-TYPE
    SYNTAX    INTEGER
    ACCESS    read-only
    STATUS    mandatory
    DESCRIPTION
        "Shows the type of a counter installed in a system.
         The counter which a system has can specify by referring
         to this.
         Displays the counter to support with Bitmap and shows
         the supporting counter by the total.

         Bit    Value    CounterType
         ---    -----    ---------------
          0        1     GeneralCounter
          1        2     PrintFunctionCounter
          2        4     SendFunctionCounter
          3        8     PapersSizeCounter
          4       16     DivCounter
          5       32     TonerLifeCounter

         It becomes 63 when implementing all the counters.
        "
    ::= { mltSysCounterConfig 1 }

mltSysDuplexCountMode  OBJECT-TYPE
    SYNTAX    INTEGER {
                  unknown (0),
                  singleCount (1),
                  doubleCount (2)
              }
    ACCESS    read-write
    STATUS    mandatory
    DESCRIPTION
        "Sets up whether Duplex printing is counted two times
         to TotalCounter at the time.
         This setup is reflected to all TotalCounters.
         This object may be implemented with RO access.
         If a system doesn't have this setting (e.g. printer), 
         the value of the static count mode (1 or 2) must be implemented.
         Basically this value must not be '0'.
         This is also applied to mtSysLargeSizeCountMode and
         mltSysLargeSizeMode same.
        "
    ::= { mltSysCounterConfig 2 }

mltSysLargeSizeCountMode  OBJECT-TYPE
    SYNTAX    INTEGER {
                  unknown (0),
                  singleCount (1),
                  doubleCount (2)
              }
    ACCESS    read-write
    STATUS    mandatory
    DESCRIPTION
        "Sets up whether LargeSize is counted two times
         to TotalCounter at the time.
         This setup is reflected to all TotalCounters.
         This object may be implemented with RO access.
         This setting is the item of a service choice. 
         A setup of a service choice is reflected to this object.
         Also enable operation from PageScope.
         Management of the access rights supports by PageScope side.
        "
    ::= { mltSysCounterConfig 3 }

mltSysLargeSizeType  OBJECT-TYPE
    SYNTAX    INTEGER {
                  noLargeSize (0),
                  typeA       (1),
                  typeB       (2),
                  typeC       (3)
              }
    ACCESS    read-write
    STATUS    mandatory
    DESCRIPTION
        "Sets up the type of paper counted as LargeSize.

         noLargeSize(0): indicates that the count of LargeSize is
                         not performed or not detect large size type.
         typeA(1): For US is 11x17,
                   For EU is A3,
                   For Japan is A3.
         typeB(2): For US is 11x17,
                   For EU is A3/B4,
                   For Japan is A3/B4.
         typeC(3): For US is 11x17/11x14/8.5x14,
                   For EU is A3/B4,
                   For Japan A3/B4.

         This object may be implemented with RO access.
         The choice item of EP-NET. 
         Also enable operation from PageScope.

        "
    ::= { mltSysCounterConfig 4 }


mltSysColorCountSupportType  OBJECT-TYPE
    SYNTAX    INTEGER
    ACCESS    read-only
    STATUS    mandatory
    DESCRIPTION
        "It is shown what kind of counter by the color is supported.
         The color counter which a device supports can be specified
         by referring to this. Displays the type of counter to
         support with Bitmap and shows the supporting counter by
         the total. The type counter that is shown in here shall
         be held by the color-related counter.

         Bit    Value    CounterType
         ---    -----    -----------------
          0        1     reserved
          1        2     bw               --The monochrome counter
                                          --in a color machine
          2        4     fourColor  (4c)  --Full color
                                          -- (All of C, M, Y, and K are used)
          3        8     threeColor (3c)  --Monochrome color 
                                          --(monochrome is taken out using
                                          -- three colors of C, M, and Y)
          4       16     cmy              --CMY:  (using any 1 color of C/M/Y)

          5       32     rgb              --RGB: (using three colors of CMY)

          6       64     monoColor        --The total of 3C, CMY, and RGB

          7      128     paperPath        --PaperPath counter

        "
    ::= { mltSysCounterConfig 5 }

-- mltSysSystemCounter Group

--  The counter group which should have in order 
--  that the system grasps the whole counter state.

    mltSysGeneralCounter    OBJECT IDENTIFIER ::= { mltSysSystemCounter 1 }



-- mltSysGeneralCounter Group

--  The counter group which all devices have to implement.
--  Especially the total counter is indispensable.
--  About Large and Duplex, in the device which does not have
--  that function, it always shall be the implementation of -1.


mltSysTotalCount  OBJECT-TYPE
    SYNTAX    Integer32
    ACCESS    read-only
    STATUS    mandatory
    DESCRIPTION
        "The total print count of a system.
         Displays the total of Copy, Print, and Receiving Job.
         About the count method of Duplex and LargeSize,
         it depends on a setup. A count shall be an output count.   
         About a color machine, it shall be the total of all
         color classifications.
        "
    ::= { mltSysGeneralCounter 1 }

mltSysLargeSizeCount  OBJECT-TYPE
    SYNTAX    Integer32
    ACCESS    read-only
    STATUS    mandatory
    DESCRIPTION
        "The total print count of LargeSize paper.
         About the type of LargeSize, it depends on
         a setup of mltSysLargeSizeType.
         When the setup of mltSysLargeSizeType is noCount(0),
         this counter always shall be -1.
         In addition, also in the system without A4 machine, etc.,
         this counter should be -1.
        "
    ::= { mltSysGeneralCounter 2 }

mltSysDuplexCount  OBJECT-TYPE
    SYNTAX    Integer32
    ACCESS    read-only
    STATUS    mandatory
    DESCRIPTION
        "The total print count of Duplex (back). 
         In the system without Duplex mechanism, it should be -1.
        "
    ::= { mltSysGeneralCounter 3 }

mltSysLargeDuplexCount  OBJECT-TYPE
    SYNTAX    Integer32
    ACCESS    read-only
    STATUS    mandatory
    DESCRIPTION
        "The total print count of LargeSize, and also Duplex (back).
         About the type of LargeSize, it depends on a setup of
         mltSysLargeSizeType. 
         When the setup of mltSysLargeSizeType is noCount(0),
         this counter always shall be -1.
         In addition, in the system of A4 machine or in the 
         system without Duplex, this counter always should be -1.
        "
    ::= { mltSysGeneralCounter 4 }

mltSysSendTotalCount  OBJECT-TYPE
    SYNTAX    Integer32
    ACCESS    read-only
    STATUS    mandatory
    DESCRIPTION
        "Total count scaned as a transmitting function in the system.
         It shall be the total of mltSysSendScanCount.
         In the device without Scan function, it always shall be -1.
        "
    ::= { mltSysGeneralCounter 5 }

mltSysTotalJamCount  OBJECT-TYPE
    SYNTAX    Integer32
    ACCESS    read-only
    STATUS    mandatory
    DESCRIPTION
        "The number of times of Jam occurred in the system.
         It shall be the total of all Jam counters.
         (including ADF jams).
        "
    ::= { mltSysGeneralCounter 6 }

mltSysTotalTroubleCount  OBJECT-TYPE
    SYNTAX    Integer32
    ACCESS    read-only
    STATUS    mandatory
    DESCRIPTION
        "The number of times of Trouble (FatalError) occurred in
         the system. It shall be the total of all Trouble counters.
        "
    ::= { mltSysGeneralCounter 7 }



mltSysPrintFunctionCounterTable  OBJECT-TYPE
    SYNTAX    SEQUENCE OF MltSysPrintFunctionCounterEntry
    ACCESS    not-accessible
    STATUS    optional
    DESCRIPTION
        "The table for showing the counter by the color and function.
         In the monochrome machine of a single function, 
         it is not necessary to implement.
        "
    ::= { mltSysSystemCounter 2 }

mltSysPrintFunctionCounterEntry OBJECT-TYPE
    SYNTAX    MltSysPrintFunctionCounterEntry
    ACCESS    not-accessible
    STATUS    optional
    DESCRIPTION
        "The counters of color and print functions.
        "
    INDEX  { mltSysPrintFunctionColorIndex, mltSysPrintFunctionIndex }
    ::= { mltSysPrintFunctionCounterTable 1 }

    MltSysPrintFunctionCounterEntry ::= SEQUENCE {
        mltSysPrintFunctionColorIndex              INTEGER,
        mltSysPrintFunctionIndex                   INTEGER,
        mltSysPrintFunctionColorType               INTEGER,
        mltSysPrintFunctionType                    INTEGER,
        mltSysPrintFunctionTotalCount              Integer32,
        mltSysPrintFunctionDuplexCount             Integer32,
        mltSysPrintFunctionLargeSizeCount          Integer32,
        mltSysPrintFunctionLargeDuplexCount        Integer32
    }

mltSysPrintFunctionColorIndex  OBJECT-TYPE
    SYNTAX    INTEGER
    ACCESS    read-only
    STATUS    optional
    DESCRIPTION
        "Index for showing the color in the counter
         by color/function.
         By the color, index shall be attached in the
         order of the following.

          No.   Function
         --------------------
           1    BW
           2    4C
           3    3C
           4    CMY
           5    RGB
           6    MonoColor

        "
    ::= { mltSysPrintFunctionCounterEntry 1 }

mltSysPrintFunctionIndex  OBJECT-TYPE
    SYNTAX    INTEGER
    ACCESS    read-only
    STATUS    optional
    DESCRIPTION
        "Index for showing the function in the counter
         by color/function.
         By the function, index shall be attached in the
         order of the following.
        
          No.   Function
         --------------------
           1    copy
           2    printer
           3    received Job
           4    fax received  Job
           5    reportPrint

         Although classifying into printer/receive Job/fax
         receive job as a printing function is recommended,
         the implementation of multiple counting as a printer
         function is also accepted.
        "
    ::= { mltSysPrintFunctionCounterEntry 2 }

mltSysPrintFunctionColorType  OBJECT-TYPE
    SYNTAX    INTEGER {
                  bw         (1),
                  fourColor  (2),
                  threeColor (3),
                  cmy        (4),
                  rgb        (5),
                  monoColor  (6),
                  paperPath  (7)
              }
    ACCESS    read-only
    STATUS    optional
    DESCRIPTION
        "Shows the color mode in the counter by color/function.
        "
    ::= { mltSysPrintFunctionCounterEntry 3 }

mltSysPrintFunctionType  OBJECT-TYPE
    SYNTAX    INTEGER {
                  copyFunction       (1),
                  printFunction      (2),
                  receiveFunction    (3),
                  faxReceiveFunction (4),
                  reportPrint (5)
              }
    ACCESS    read-only
    STATUS    optional
    DESCRIPTION
        "Shows the function in the counter by color/function.
         Although classifying into printer/receive Job/fax
         receive job as a printing function is recommended,
         the implementation of multiple counting as a printer
         function is also accepted.
        "
    ::= { mltSysPrintFunctionCounterEntry 4 }

mltSysPrintFunctionTotalCount  OBJECT-TYPE
    SYNTAX    Integer32
    ACCESS    read-only
    STATUS    optional
    DESCRIPTION
        "The total print count in a specified function.
         About the count method, complies with GeneralCounter
        "
    ::= { mltSysPrintFunctionCounterEntry 5 }

mltSysPrintFunctionDuplexCount  OBJECT-TYPE
    SYNTAX    Integer32
    ACCESS    read-only
    STATUS    optional
    DESCRIPTION
        "The print count of Duplex (back) in a specified function.
         The print count of the LargeSize paper in
         a specified function.
         About the count method, complies with GeneralCounter.
        "
    ::= { mltSysPrintFunctionCounterEntry 6 }

mltSysPrintFunctionLargeSizeCount  OBJECT-TYPE
    SYNTAX    Integer32
    ACCESS    read-only
    STATUS    optional
    DESCRIPTION
        "The print count of the LargeSize paper in
         a specified function.
         About the count method, complies with GeneralCounter.
        "
    ::= { mltSysPrintFunctionCounterEntry 7 }

mltSysPrintFunctionLargeDuplexCount  OBJECT-TYPE
    SYNTAX    Integer32
    ACCESS    read-only
    STATUS    optional
    DESCRIPTION
        "The print count of LargeSize and Duplex (back)
         in a specified function.
         About the count method, complies with GeneralCounter.
        "
    ::= { mltSysPrintFunctionCounterEntry 8 }


mltSysSizeCounterTable  OBJECT-TYPE
    SYNTAX    SEQUENCE OF MltSysSizeCounterEntry
    ACCESS    not-accessible
    STATUS    mandatory
    DESCRIPTION
        "The table of the counter by the paper sizes (types).
         The model which supports plural paper sizes has
         to implement.
         Regardless of shipment destination, having a counter
         to all the paper sizes that can be printed is recommended.
         By implementation, implementing different size counter
         by shipment destination is also accepted.
         It shall also have index by the functions so that
         it can correspond to the counter by sizes by the functions.
        "
    ::= { mltSysSystemCounter 4 }

mltSysSizeCounterEntry  OBJECT-TYPE
    SYNTAX    MltSysSizeCounterEntry
    ACCESS    not-accessible
    STATUS    mandatory
    DESCRIPTION
        "The information of paper size counters.
        "
    INDEX  { mltSysSizeFunctionIndex, mltSysSizeTypeIndex }
    ::= { mltSysSizeCounterTable 1 }

    MltSysSizeCounterEntry ::= SEQUENCE {
        mltSysSizeFunctionIndex      INTEGER,
        mltSysSizeTypeIndex          INTEGER,
        mltSysSizeFunction           INTEGER,
        mltSysSizeType               INTEGER,
        mltSysSizeCount              Integer32
    }

mltSysSizeFunctionIndex  OBJECT-TYPE
    SYNTAX    INTEGER
    ACCESS    read-only
    STATUS    mandatory
    DESCRIPTION
        "Index for showing the function which becomes
         the count object in the counter by paper sizes.
         Although Index shall be attached in the order of
         the following by the function, having Index by
         fixation shall not require.

          No.   Function
         --------------------
           1    Total 
        "
    ::= { mltSysSizeCounterEntry 1 }

mltSysSizeTypeIndex  OBJECT-TYPE
    SYNTAX    INTEGER
    ACCESS    read-only
    STATUS    mandatory
    DESCRIPTION
        "Index for showing the paper which becomes
         the count object in the counter by paper sizes.
         Only the type of corresponding paper shall be
         taken in the order from 1.
        Using fixed index for every paper does not require.
        "
    ::= { mltSysSizeCounterEntry 2 }

mltSysSizeFunction  OBJECT-TYPE
    SYNTAX    INTEGER {
                  total               (0)
              }
    ACCESS    read-only
    STATUS    mandatory
    DESCRIPTION
        "Shows the function which becomes the count
         object in the counter by paper size.
        "
    ::= { mltSysSizeCounterEntry 3 }

mltSysSizeType  OBJECT-TYPE
    SYNTAX    INTEGER {
                  otherPaperSize (0),
                  unknownPaperSize (1),
                  --            2 to 10   reserved
                  a0 (11),
                  a1 (12),
                  a2 (13),
                  a3 (14),
                  a4 (15),
                  a5 (16),
                  a6 (17),
                  --             18 to 20  reserved
                  b0 (21),
                  b1 (22),
                  b2 (23),
                  b3 (24),
                  b4 (25),
                  b5 (26),
                  b6 (27),
                  --             29 to 29  reserved
                  us12x14 (30),  -- 12x14
                  ledger (31),   -- 11x17
                  us11x15 (32),  -- 11x15
                  us11x14 (33),  -- 11x14
                  comp (34),     -- computer  10-1/8x14
                  us10x14 (35),  -- 10x14
                  us9-1by4x14 (36), -- 9-1/4x14
                  legal (37),    -- 8-1/2x14
                  us8-1by4x11-3by4 (38), -- 8-1/4x11-3/4
                  letter (39),  -- 8-1/2x11
                  govermentLetter (40), -- 8x10-1/2
                  quarto (41), -- 8x10
                  executive (42),  -- 7-1/4x10-1/2
                  statement (43),  -- 5-1/2x8-1/2
                  --             44 to 49  reserved
                  fls (50),
                  fls0 (51),
                  fls1 (52),
                  fls2 (53),
                  fls3 (54),
                  --             55 to 60  reserved
                  hagaki (61),
                  oufuku-Hagaki (62),
                  envelopeB5 (63),
                  envelopeCom10 (64),
                  envelopeC5 (65),
                  envelopeDL (66),
                  envelopeMonarch (67),
                  envelopeC6 (68),
                  -- 
                  youkei-0Gou (70),
                  youkei-4Gou (71),
                  youkei-6Gou (72),
                  --
                  choukei-3Gou (83),
                  choukei-4Gou (84),
                  --
                  kakugata-3Gou (93),
                  --
                  special0 (100),  
                  special1 (101),
                  special2 (102),
                  special3 (103),
                  special4 (104),
                  special5 (106),
                  --
                  a3W (114),
                  a4W (115),
                  a5W (116),
                  a6W (117),
                     -- Paper attribute
                  otherPaperAttribute (199),
                  unknownPaperAttribute (200),
                  plain (201),
                  exclusive (202),
                  notFor2Sided (203),
                  specialPaper (204),
                  cover  (205),
                  inserter (206),
                  reuse (207),
                  -- Media Type
                  otherMediaType (208),
                  unknownMediaType (209),
                  plainPaper (210),
                  plainPaper-2side (211),
                  plainPaper-Recycled (212),
                  plainPaper-Exclusive (214),
                  plainPaper-Color (216),
                  thick1 (222),
                  thick1-2side (223),
                  thick2 (224),
                  thick2-2side (225),
                  thick3 (226),
                  thick3-2side (227),
                  ohp (230),
                  thin (236),
                  envelope (240),
                  envelope-2side (241),
                  label (242),
                  postCard (244),
                  letterHead (246),
                  tab (248)
                  }
    ACCESS    read-only
    STATUS    mandatory
    DESCRIPTION
        "Shows the paper which becomes the count object
         in the counter by paper sizes.
        "
    ::= { mltSysSizeCounterEntry 4 }

mltSysSizeCount  OBJECT-TYPE
    SYNTAX    Integer32
    ACCESS    read-only
    STATUS    mandatory
    DESCRIPTION
        "The number of print of the specified function
         and specified size, media type, or attribute.
        "
    ::= { mltSysSizeCounterEntry 5 }


mltSysTonerLifeCounterTable  OBJECT-TYPE
    SYNTAX    SEQUENCE OF MltSysTonerLifeCounterEntry
    ACCESS    not-accessible
    STATUS    optional
    DESCRIPTION
        "The table of toner life counter.
        "
    ::= { mltSysSystemCounter 5 }

mltSysTonerLifeCounterEntry  OBJECT-TYPE
    SYNTAX    MltSysTonerLifeCounterEntry
    ACCESS    not-accessible
    STATUS    optional
    DESCRIPTION
        "The information of toner life counters.
        "
    INDEX  { mltSysTonerTypeIndex }
    ::= { mltSysTonerLifeCounterTable 1 }

    MltSysTonerLifeCounterEntry ::= SEQUENCE {
        mltSysTonerTypeIndex        INTEGER,
        mltSysTonerType             INTEGER,
        mltTonerTypeCount           Counter32
    }

mltSysTonerTypeIndex  OBJECT-TYPE
    SYNTAX    INTEGER
    ACCESS    read-only
    STATUS    optional
    DESCRIPTION
        "Index for Toner used as the count object in TonerLife 
         counter being shown.
        "
    ::= { mltSysTonerLifeCounterEntry 1 }

mltSysTonerType   OBJECT-TYPE
    SYNTAX    INTEGER {
                  other (0),
                  cyan (1),
                  magenta (2),
                  yellow (3),
                  black (4) 
                  }
    ACCESS    read-only
    STATUS    optional
    DESCRIPTION
        "Toner used as the count object in TonerLife counter is shown.
        "
    ::= { mltSysTonerLifeCounterEntry 2 }

mltTonerTypeCount  OBJECT-TYPE
    SYNTAX    Counter32
    ACCESS    read-only
    STATUS    optional
    DESCRIPTION
        "TonerLife count.
         This is used for calculation of Coverage, 
         by the amount of Toner consumption, etc.
         by counting Dot number used for every Toner.
         1unit is 2M Dots.
        "
    ::= { mltSysTonerLifeCounterEntry 3 }


--
-- Private Network MIB
--


    mltNetMibVersion  OBJECT-TYPE
    SYNTAX     DisplayString (SIZE(0..7))
    ACCESS     read-only
    STATUS     mandatory
    DESCRIPTION
        "         
         The standardization version of MIB implemented in Network.
         This indicates the version of the Private Network MIB.

         General form is AA.BC.
         AA is indicating major revision, and B and C is 
         minor revision. Decimal point is ASCII-coded period.
        " 
    ::= { mltNetworkMib 1 }


    mltNetGeneral       OBJECT IDENTIFIER ::= { mltNetworkMib 2 }
    mltNetProtocol      OBJECT IDENTIFIER ::= { mltNetworkMib 3 }

    mltNetCommand       OBJECT IDENTIFIER ::= { mltNetworkMib 5 }
    mltNetSnmp          OBJECT IDENTIFIER ::= { mltNetworkMib 6 }
    mltNetTcpip         OBJECT IDENTIFIER ::= { mltNetworkMib 7 }
    mltNetNetWare       OBJECT IDENTIFIER ::= { mltNetworkMib 8 }
    mltNetAppleTalk     OBJECT IDENTIFIER ::= { mltNetworkMib 9 }
    mltNetSmb           OBJECT IDENTIFIER ::= { mltNetworkMib 10 }

-- mltNetGeneral Group

-- The general information that Network has is included.
-- It shall have the followings as general information.
-- 1.   Version information of NetworkInterface
-- 2.   Hardware address
-- 3.   Cable related information


   mltNetGeneralTable  OBJECT-TYPE
    SYNTAX    SEQUENCE OF MltNetGeneralEntry
    ACCESS    not-accessible
    STATUS    mandatory
    DESCRIPTION
        "
        Table for showing the general information of
        Network relation. 
        "
    ::= { mltNetGeneral 1 }

   mltNetGeneralEntry OBJECT-TYPE
    SYNTAX    MltNetGeneralEntry
    ACCESS    not-accessible
    STATUS    mandatory
    DESCRIPTION
        "
        General information of network interface.
        "
    INDEX  { mltNetGeneralIndex }
    ::= { mltNetGeneralTable 1 }

    MltNetGeneralEntry ::= SEQUENCE {
        mltNetGeneralIndex       INTEGER,
        mltNetFirmVersion        DisplayString,
        mltNetHardwareAddress    PhysAddress,
        mltNetSerialNumber       DisplayString,
        mltNetSupportedConnector INTEGER,
        mltNetCurrentConnector   INTEGER,
        mltNetSpeedConfig        INTEGER,
        mltNetInterfaceType      INTEGER,
        mltNetIfDescr            DisplayString
    }

   mltNetGeneralIndex  OBJECT-TYPE
    SYNTAX     INTEGER
    ACCESS     read-only
    STATUS     mandatory
    DESCRIPTION
           "
            Index for showing NetworkInterface installed to a device. 
            Basically, it shall take the same value with ifIndex. 
           "
       ::= { mltNetGeneralEntry 1 }

   mltNetFirmVersion  OBJECT-TYPE
    SYNTAX    DisplayString(SIZE(0..7))
    ACCESS    read-only
    STATUS    mandatory
    DESCRIPTION
        "
        Shows the FW version of NetworkInterface. 
        Write it as ##.xx.
        ## shall be a major version and xx shall
        be a minor version.
        If there is no original FW of NetworkInterface, 
        implement character strings of '-' (hyphen).
        "
    ::= { mltNetGeneralEntry 2 }

   mltNetHardwareAddress  OBJECT-TYPE
    SYNTAX    PhysAddress
    ACCESS    read-write
    STATUS    mandatory
    DESCRIPTION
        "
        MAC address of NetworkInterface. (Hardware address)
        In the device of our company, it was made into RW since 
        MAC address needs to be written at the time of shipment.
        Implement as RO when the writing of MAC address is unnecessary.
        Moreover, in a management tool side, be sure to handle it as RO.
        "
    ::= { mltNetGeneralEntry 3 }

   mltNetSerialNumber  OBJECT-TYPE
    SYNTAX    DisplayString(SIZE(0..15))
    ACCESS    read-write
    STATUS    mandatory
    DESCRIPTION
        "
        The serial number of NetworkInterface.
        Implement '-' (hyphen) in the device without a serial number.
        In the device of our company, it was made into RW since serial 
        number may need to be written at the time of shipment.
        Implement as RO when the writing of serial number is unnecessary.
        Moreover, in a management tool side, be sure to handle it as RO.
        "
    ::= { mltNetGeneralEntry 4 }

   mltNetSupportedConnector  OBJECT-TYPE
    SYNTAX     INTEGER
    ACCESS     read-only
    STATUS     mandatory
    DESCRIPTION
            "
            An integer bitmap value specifying network connector 
            information. Each bit in the integer is defined as follows.

            bit   Value     Connector
            ---   -----     ---------
            0       1      Reserved
            1       2      Ethernet AUI     -- 10Base5
            2       4      Ethernet BNC     -- 10Base2
            3       8      Ethernet RJ45    -- 10/100BaseT
            4      16      Ethernet Fiber   -- 10/100BaseF
            5      32      Reserved
            6      64      Reserved
            7     128      TokenRing STP(DB-15)
            8     256      TokenRing UTP(RJ-45)
            9     512      TokenRing Fiber
           10    1024      Reserved
           11    2048      wirelessA  -- 802.11a
           12    4096      wirelessB  -- 802.11b
           13    8132      blueTooth 
           14   16364      ieee1394   -- IP over IEEE1394 

           "
       ::= { mltNetGeneralEntry 5 }

   mltNetCurrentConnector  OBJECT-TYPE
    SYNTAX    INTEGER {
                 notWorking (0),
                 etherAUI (1),
                 etherBNC (2),
                 etherRJ (3),
                 etherFiber (4),

                 tokenSTP (7),
                 tokenUTP (8),
                 tokenFiber (9),

                 wirelessA (11),  -- 802.11a
                 wirelessB (12),  -- 802.11b
                 blueTooth (13),
                 ieee1394 (14)
              }
    ACCESS    read-only
    STATUS    mandatory
    DESCRIPTION
        "
        Shows the connector that is working on NetworkInterface.
        "
    ::= { mltNetGeneralEntry 6 }

   mltNetSpeedConfig  OBJECT-TYPE
    SYNTAX    INTEGER {
                 other (0),
                 autoDetectEther (1),
                 et10MbpsHalfDuplex (2),
                 et10MbpsFullDuplex (3),
                 et100MbpsHalfDuplex (4),
                 et100MbpsFullDuplex (5),
                 etGbpsHalfDuplex (6),
                 etGbpsFullDuplex (7),

                 autoDetectToken (10),
                 tr4Mbps (11),
                 tr16Mbps (12),
                 tr32Mbps (13),

                 autoDetectWireless (20),
                 wireless1Mbps (21),
                 wireless2Mbps (22),
                 wireless5-5Mbps (23),
                 wireless11Mbps (24)
              }
    ACCESS    read-write
    STATUS    mandatory
    DESCRIPTION
        "
        Sets up the speed of NetworkInterface. 
        Refer to ifSpeed for checking the present speed of operation.

        If this setting can not be set from Network access, a device
        should implement a current set value with RO access.
        "
    ::= { mltNetGeneralEntry 7 }

   mltNetInterfaceType  OBJECT-TYPE
    SYNTAX    INTEGER {
                 other (0),
                 ieee1284 (1),
                 ieee1394 (2),
                 usb (3),

                 dual1284 (10),
                 dpo (11),
                 psio (12),

                 onBoardDPO (100),
                 noPhysicalNIC (101),
                 onBoard (102),
                 onBoardOneChip (103),
                 onBoardPSIO (104),

                 pciNonIntelligent (201),
                 pciIntelligent (202)
              }
    ACCESS    read-only
    STATUS    mandatory
    DESCRIPTION
        "
        Shows the type of NetworkInterface.
        "
    ::= { mltNetGeneralEntry 8 }

   mltNetIfDescr  OBJECT-TYPE
    SYNTAX    DisplayString(SIZE(0..63))
    ACCESS    read-only
    STATUS    mandatory
    DESCRIPTION
        "
        Explanation of NetworkInterface. 
        Shows the type of port and the version information. 
        The name to indicate is determined at Project side 
        and implementation of NullString is not accepted.
        Even if a device have a no description about this,
        '-' need to be implemented.
        "
    ::= { mltNetGeneralEntry 9 }


-- mltNetProtocol Group

-- The information of NetworkProtocol that 
-- NetworkInterface has is included.

   mltNetProtocolTable  OBJECT-TYPE
    SYNTAX    SEQUENCE OF MltNetProtocolEntry
    ACCESS    not-accessible
    STATUS    mandatory
    DESCRIPTION
        "
        The table for showing the protocol information 
        which NetworkInterface supports. 
        "
    ::= { mltNetProtocol 1 }

   mltNetProtocolEntry OBJECT-TYPE
    SYNTAX    MltNetProtocolEntry
    ACCESS    not-accessible
    STATUS    mandatory
    DESCRIPTION
        "
        The information of protocol.
        "
    INDEX  { mltNetProtocolIfIndex, mltNetProtocolIndex }
    ::= { mltNetProtocolTable 1 }

    MltNetProtocolEntry ::= SEQUENCE {
        mltNetProtocolIfIndex   INTEGER,
        mltNetProtocolIndex     INTEGER,
        mltNetProtocolType      INTEGER,
        mltNetProtocolDescr     DisplayString,
        mltNetProtocolVer       DisplayString,
        mltNetProtocolOnOff     INTEGER
        }

   mltNetProtocolIfIndex  OBJECT-TYPE
    SYNTAX     INTEGER
    ACCESS     read-only
    STATUS     mandatory
    DESCRIPTION
           "
            Index for showing NetworkInterface that a system has. 
            The value of index shall be the same value with 
            mltNetGeneralIndex (ifIndex).
           "
       ::= { mltNetProtocolEntry 1 }

   mltNetProtocolIndex  OBJECT-TYPE
    SYNTAX     INTEGER
    ACCESS     read-only
    STATUS     mandatory
    DESCRIPTION
           "
            Index for uniquely showing the protocol which
            a system supports. Index shall be assigned in 
            the following order is recommended.

            No. Protocol
            --------------------
            1   TCP/IP
            2   NetWare(IPX/SPX)
            3   AppleTalk
            4   SMB

           "
       ::= { mltNetProtocolEntry 2 }

   mltNetProtocolType  OBJECT-TYPE
    SYNTAX    INTEGER {
                unknown (0),
                tcp-ip  (1),
                netWare (2),
                appleTalk (3),
                smb     (4),
                other   (7)
              }
    ACCESS    read-only
    STATUS    mandatory
    DESCRIPTION
        "
        Shows the type of supporting protocol. 
        "
    ::= { mltNetProtocolEntry 3 }

   mltNetProtocolDescr  OBJECT-TYPE
    SYNTAX   DisplayString (SIZE(0..15))
    ACCESS   read-only
    STATUS     mandatory
    DESCRIPTION
        "
        Description that shows a protocol. 
        Although the value to indicate shall depend on 
        an implementation, the general protocol name, 
        such as 'TCP/IP', 'NetWare', etc., shall be indicated 
        in principle. Implementation of Null is not accepted.
        "
    ::= { mltNetProtocolEntry 4 }

   mltNetProtocolVer  OBJECT-TYPE
    SYNTAX  DisplayString (SIZE(0..15))
    ACCESS  read-only
    STATUS  mandatory
    DESCRIPTION
        "
        The version of the implemented protocol stack. 
        Implement '-' (hyphen) when there is no version notation. 
        Implementation of Null is not accepted.
        "
    ::= { mltNetProtocolEntry 5 }

   mltNetProtocolOnOff  OBJECT-TYPE
    SYNTAX  INTEGER {
            notSupported (0),
            enable (1),
            disable (2)
            }  
    ACCESS  read-write
    STATUS  mandatory
    DESCRIPTION
        "
        Sets up a states display of On and Off of 
        the function of each protocol. 
        If this setting can not be set from Network access, 
        a device should implement a current set value with RO access.
        "
    ::= { mltNetProtocolEntry 6 }


-- mltNetCommand Group

-- The various command information which 
-- NetworkInterface has is included.

   mltNetCommandTable  OBJECT-TYPE
    SYNTAX    SEQUENCE OF MltNetCommandEntry
    ACCESS    not-accessible
    STATUS    mandatory
    DESCRIPTION
        "
        The table for showing the command information 
        which NetworkInterface supports. 
        "
    ::= { mltNetCommand 1 }

   mltNetCommandEntry OBJECT-TYPE
    SYNTAX    MltNetCommandEntry
    ACCESS    not-accessible
    STATUS    mandatory
    DESCRIPTION
        "
        The information of command for network interface.
        "
    INDEX  { mltNetCommandIfIndex }
    ::= { mltNetCommandTable  1 }

    MltNetCommandEntry ::= SEQUENCE {
        mltNetCommandIfIndex        INTEGER,
        mltNetCommandReset          INTEGER,
        mltNetCommandDefault        INTEGER,
        mltNetCommandPrintNicConfig INTEGER,
        mltNetCommandStartupConfig  INTEGER,
        mltNetCommandDownLoad       INTEGER
    }

   mltNetCommandIfIndex  OBJECT-TYPE
    SYNTAX     INTEGER
    ACCESS     read-only
    STATUS     mandatory
    DESCRIPTION
        "
        Index for uniquely showing the destination of command. 
        The value of index shall be the same value with 
        mltNetGeneralIndex (ifIndex).
        "
    ::= { mltNetCommandEntry 1 }

   mltNetCommandReset  OBJECT-TYPE
    SYNTAX    INTEGER {
                notSupported (0),
                supported (1),
                reset (2)
              }
    ACCESS    read-only
    STATUS    mandatory
    DESCRIPTION
        "
        The command that performs independent reset of 
        NetworkInterface. 

        When reset(2) is set, an agent side shall surely 
        return Reply. Implementation that performs Reset 
        immediately without returning Reply is not accepted. 
        Return Reply of an error, when Reset command is invalid.
        After reset(2) is set, about the timing which is 
        actually performing Reset depends on an implementation, 
        and it shall not be defined in MIB.
        "
    ::= { mltNetCommandEntry 2 }

   mltNetCommandDefault  OBJECT-TYPE
    SYNTAX    INTEGER {
                notSupported (0),
                supported (1),
                resetToDefault (2)
              }
    ACCESS    read-write
    STATUS    mandatory
    DESCRIPTION
        "
        The command for returning a setup about 
        NetworkInterface to FactoryDefault. 

        When resetToDefault(2) is set, an agent side 
        shall surely return Reply.
        In principle, when resetToDefault(2) is set, 
        about the timing in which the setup returns to 
        default depends on an implementation and it does 
        not define in MIB.
        "
    ::= { mltNetCommandEntry 3 }

   mltNetCommandPrintNicConfig  OBJECT-TYPE
    SYNTAX    INTEGER {
                notSupported (10),
                supported (11),
                printing (12)
              }
    ACCESS    read-only
    STATUS    mandatory
    DESCRIPTION
        "
        The command for making it perform the output of 
        ConfigPage which Network Interface has at the 
        time of normal operation. 

        Independent ConfigPage of two or more kinds of 
        Network is not considered.
        "
    ::= { mltNetCommandEntry 4 }

   mltNetCommandStartupConfig  OBJECT-TYPE
    SYNTAX    INTEGER {
                notSupported (10),
                supported (11),
                printStartUp (12)
              }
    ACCESS    read-only
    STATUS    mandatory
    DESCRIPTION
        "
        The command that sets up the availability of 
        the output of ConfigPage of NetworkInterface 
        at the time of starting. 

        Independent StartupPage of two or more kinds of 
        Network is not considered.
        "
    ::= { mltNetCommandEntry 5 }

   mltNetCommandDownLoad  OBJECT-TYPE
    SYNTAX    INTEGER {
                notSupported (0),
                notDownLoad (1),
                downLoading (2)
              }
    ACCESS    read-only
    STATUS    mandatory
    DESCRIPTION
        "
        The command that sets up the mode that updates 
        FW of NetworkInterface.

        Since this setup needs to operate with Admin authority, 
        do not perform both display and writing at the management 
        tool side.
        "
    ::= { mltNetCommandEntry 6 }


--  mltNetSnmp Group

-- SNMP related information that NetworkInterface has is included.

   mltNetSnmpCommTable  OBJECT-TYPE
    SYNTAX    SEQUENCE OF MltNetSnmpCommEntry
    ACCESS    not-accessible
    STATUS    mandatory
    DESCRIPTION
        "
        The table for showing the information of Community 
        of SNMP which a system has. 
        
        In addition, Community name shall be the common to 
        the whole system on the premise, and shall not have 
        independent Community for every NetworkInterface.
        In having Community independently by Intelligent NIC etc., 
        it shall have NetworkMIB independently to each and is not 
        managed by unified agent.
        "
    ::= { mltNetSnmp 1 }

   mltNetSnmpCommEntry OBJECT-TYPE
    SYNTAX    MltNetSnmpCommEntry
    ACCESS    not-accessible
    STATUS    mandatory
    DESCRIPTION
        "
        "
    INDEX  { mltNetSnmpCommIndex }
    ::= { mltNetSnmpCommTable 1 }

    MltNetSnmpCommEntry ::= SEQUENCE {
        mltNetSnmpCommIndex         INTEGER,
        mltNetSnmpCommName          DisplayString,
        mltNetSnmpCommAccessRight   INTEGER
    }

   mltNetSnmpCommIndex  OBJECT-TYPE
    SYNTAX     INTEGER
    ACCESS     read-only
    STATUS     mandatory
    DESCRIPTION
       "
        Index for identifying each SNMP community.
        Although about Community number to support, 
        Community name, and each access rights are 
        dependent on an implementation, having the 
        following three Communities is recommended.
        
        public (RO)
        private (RW)
        admin (RW)

        It shall be indispensable at least to have 
        public (RW) or to have the two of public (RO) 
        and private (RW).
       "
       ::= { mltNetSnmpCommEntry 1 }

   mltNetSnmpCommName  OBJECT-TYPE
    SYNTAX    DisplayString(SIZE(0..15))
    ACCESS    read-write
    STATUS    mandatory
    DESCRIPTION
        "
        Community name of SNMP. Having the above-mentioned 
        name as default is recommended. This item does not 
        accept the implementation of RO. Community name has 
        to be changeable.

        But if Community name can not be changeable, 
        'public' or 'private' is recommended to be implemented 
        as Community name with RO access.
        "
    ::= { mltNetSnmpCommEntry 2 }

   mltNetSnmpCommAccessRight  OBJECT-TYPE
    SYNTAX    INTEGER {
                none (0),
                readOnly (1),
                writeOnly (2),
                readWrite (3)
              }
    ACCESS    read-write
    STATUS    mandatory
    DESCRIPTION
        "
        Shows the access rights of SNMP community. 
        If this setting can not be set from Network access, 
        a device should implement a current set value with RO access.
        "
    ::= { mltNetSnmpCommEntry 3 }


   mltNetSnmpTrapTable  OBJECT-TYPE
    SYNTAX    SEQUENCE OF MltNetSnmpTrapEntry
    ACCESS    not-accessible
    STATUS    mandatory
    DESCRIPTION
        "
        The table for showing the information of 
        destination of Trap of SNMP.

        When it does not have Trap function of SNMP, 
        this Table does not need to implement.
        "
    ::= { mltNetSnmp 2 }

   mltNetSnmpTrapEntry OBJECT-TYPE
    SYNTAX    MltNetSnmpTrapEntry
    ACCESS    not-accessible
    STATUS    mandatory
    DESCRIPTION
        "
        "
    INDEX  { mltNetSnmpTrapIfIndex, mltNetSnmpTrapIndex }
    ::= { mltNetSnmpTrapTable 1 }

    MltNetSnmpTrapEntry ::= SEQUENCE {
        mltNetSnmpTrapIfIndex       INTEGER,
        mltNetSnmpTrapIndex         INTEGER,
        mltNetSnmpTrapCommunity     DisplayString,
        mltNetSnmpTrapIpAddress     IpAddress,
        mltNetSnmpTrapIpxAddress    DisplayString,
        mltNetSnmpTrapOnOff         INTEGER
        }

   mltNetSnmpTrapIfIndex  OBJECT-TYPE
    SYNTAX     INTEGER
    ACCESS     read-only
    STATUS     mandatory
    DESCRIPTION
        "
        The index for uniquely showing the NetworkInterface 
        which becomes the sender of Trap. 
        The value of index shall be the same value with 
        mltNetGeneralIndex (ifIndex).
        "
       ::= { mltNetSnmpTrapEntry 1 }

   mltNetSnmpTrapIndex  OBJECT-TYPE
    SYNTAX     INTEGER
    ACCESS     read-only
    STATUS     mandatory
    DESCRIPTION
        "
        The index for uniquely showing the destination of Trap. 
        In Default, it shall have at least one TrapAddress in a Table.
        "
       ::= { mltNetSnmpTrapEntry 2 }

   mltNetSnmpTrapCommunity  OBJECT-TYPE
    SYNTAX    DisplayString(SIZE(0..15))
    ACCESS    read-write
    STATUS    mandatory
    DESCRIPTION
        "
        Community name at the time of transmitting Trap. 
        In Default, it shall have public.
        If this setting can not be set from Network access, 
        a device should implement this value with RO access.
        "
    ::= { mltNetSnmpTrapEntry 3 }

   mltNetSnmpTrapIpAddress  OBJECT-TYPE
    SYNTAX    IpAddress
    ACCESS    read-write
    STATUS    mandatory
    DESCRIPTION
        "
        IP address of Trap destination. 
        It shall be 255.255.255.255 (BroadCast) in Default.
        If this setting can not be set from Network access, 
        a device should implement this value with RO access.
        "
    ::= { mltNetSnmpTrapEntry 4 }

   mltNetSnmpTrapIpxAddress  OBJECT-TYPE
    SYNTAX    DisplayString(SIZE(0..31))
    ACCESS    read-write
    STATUS    mandatory
    DESCRIPTION
        "
        IPX address of the destination of Trap.
        It shall be 'FFFFFFFF:FFFFFFFFFFFFFFFF' in Default.

        When it does not have Trap transmitting function in IPX, 
        the character string of '-' (hyphen) shall be displayed.
        If this setting can not be set from Network access, 
        a device should implement this value with RO access.
        "
    ::= { mltNetSnmpTrapEntry 5 }

   mltNetSnmpTrapOnOff  OBJECT-TYPE
    SYNTAX    INTEGER {
                on (1),
                off (2)
              }
    ACCESS    read-write
    STATUS    mandatory
    DESCRIPTION
        "
        On/Off of transmission of Trap is controlled. 
        If this setting can not be set from Network access, 
        a device should implement this value with RO access.
        "
    ::= { mltNetSnmpTrapEntry 6 }


-- mltNetTcpip Group

   mltNetTcpipGeneral   OBJECT IDENTIFIER ::= { mltNetTcpip 1 }
   mltNetLpd            OBJECT IDENTIFIER ::= { mltNetTcpip 2 }
   mltNetFtpd           OBJECT IDENTIFIER ::= { mltNetTcpip 6 }
   mltNetHttpd          OBJECT IDENTIFIER ::= { mltNetTcpip 8 }
   mltNetSmtpClient     OBJECT IDENTIFIER ::= { mltNetTcpip 13 }
   mltNetIpp            OBJECT IDENTIFIER ::= { mltNetTcpip 14 }
   mltNetSlp            OBJECT IDENTIFIER ::= { mltNetTcpip 17 }

-- mltNetUpnp           OBJECT IDENTIFIER ::= { mltNetTcpip 21 }
--   This group is reserved for future extensions.


-- mltNetTcpipGeneral Group

-- The general information of TCP/IP relation that NetworkInterface has is 
-- included. The following items shall be defined.
-- About IPv6, it shall not take into consideration by definition of MIB of 
-- this version. It shall be examined when the necessity for IPv6 support 
-- comes out.


   mltNetTcpipGeneralTable  OBJECT-TYPE
    SYNTAX    SEQUENCE OF MltNetTcpipGeneralEntry
    ACCESS    not-accessible
    STATUS    mandatory
    DESCRIPTION
        "
    Table with the basic information of TCP/IP relation which
    NetworkInterface has. 
        "
    ::= { mltNetTcpipGeneral 1 }

   mltNetTcpipGeneralEntry OBJECT-TYPE
    SYNTAX    MltNetTcpipGeneralEntry
    ACCESS    not-accessible
    STATUS    mandatory
    DESCRIPTION
        "
        "
    INDEX  { mltNetTcpipIfIndex }
    ::= { mltNetTcpipGeneralTable 1 }

    MltNetTcpipGeneralEntry ::= SEQUENCE {
        mltNetTcpipIfIndex              INTEGER,
        mltNetTcpipDefault              INTEGER,
        mltNetTcpipAddress              IpAddress,
        mltNetTcpipSubnet               IpAddress,
        mltNetTcpipGateway              IpAddress,
        mltNetTcpipUseBootProtocol      INTEGER,
        mltNetTcpipBootProtocolEnable   INTEGER,
        mltNetTcpipAddressServer        IpAddress,
        mltNetTcpipRawPortNumber        INTEGER,
        mltNetTcpipSupportService       INTEGER,
        mltNetTcpipDnsSupport           INTEGER,
        mltNetTcpipDnsHostName          DisplayString,
        mltNetTcpipDnsDomainName        DisplayString
         }

   mltNetTcpipIfIndex  OBJECT-TYPE
    SYNTAX     INTEGER
    ACCESS     read-only
    STATUS     mandatory
    DESCRIPTION
        "
    Index for uniquely showing NetworkInterface which IP address 
    is set up. The value of index shall be the same value with 
    mltNetGeneralIndex (ifIndex).
        "
       ::= { mltNetTcpipGeneralEntry 1 }

   mltNetTcpipDefault  OBJECT-TYPE
    SYNTAX  INTEGER {
            notSupported (0),
            supported (1),
            resetToDefault (2)
            }  
    ACCESS  read-only
    STATUS  mandatory
    DESCRIPTION
        "
    The command that returns all setup about TCP/IP to FactoryDefault. 

    When resetToDefault(2) is set, an agent side shall surely 
    return Reply. In principle, when resetToDefault(2) is set, 
    about the timing in which the setup returns to default 
    depends on an implementation and it does not define in MIB.
        "
    ::= { mltNetTcpipGeneralEntry 2 }

   mltNetTcpipAddress  OBJECT-TYPE
    SYNTAX    IpAddress
    ACCESS    read-write
    STATUS    mandatory
    DESCRIPTION
        "
        IP address of NetworkInterface.

        If this setting can not be set from Network access, 
        a device should implement this value with RO access.
        "
    ::= { mltNetTcpipGeneralEntry 3 }

   mltNetTcpipSubnet  OBJECT-TYPE
    SYNTAX    IpAddress
    ACCESS    read-write
    STATUS    mandatory
    DESCRIPTION
        "
        Subnet mask of NetworkInterface.

        If this setting can not be set from Network access, 
        a device should implement this value with RO access.
        "
    ::= { mltNetTcpipGeneralEntry 4 }

   mltNetTcpipGateway  OBJECT-TYPE
    SYNTAX    IpAddress
    ACCESS    read-write
    STATUS    mandatory
    DESCRIPTION
        "
        DefaultGateway of NetworkInterface.

        If this setting can not be set from Network access, 
        a device should implement this value with RO access.
        "
    ::= { mltNetTcpipGeneralEntry 5 }

   mltNetTcpipUseBootProtocol  OBJECT-TYPE
    SYNTAX  INTEGER {
            neverUse (0),
            useWhenNoAddress (1),
            useEveryTime (2)
            }  
    ACCESS  read-write
    STATUS  mandatory
    DESCRIPTION
        "
        Specifies the IP address acquisition method of 
        NetworkInterface. 
        The value taken by default depends on the implementation 
        of a model.

        If this setting can not be set from Network access, 
        a device should implement this value with RO access.
        "
    ::= { mltNetTcpipGeneralEntry 6 }

   mltNetTcpipBootProtocolEnable  OBJECT-TYPE
    SYNTAX     INTEGER
    ACCESS     read-write
    STATUS     mandatory
    DESCRIPTION
        "
        Bitmap for specifying BootProtocol used in order to determine 
        the IP address of NetworkInterface. The value that should have 
        by Default depends on the implementation of a model.
        
        An integer bitmap value specifying bootProtocols. 
        Each bit in the integer is defined as follows.

           bit   Value     Type
           ---   -----     ---------
            0       1      Arp & Ping
            1       2      RARP
            2       4      BootP
            3       8      DHCP
            4      16      AutoIP
        
        If this setting can not be set from Network access, 
        a device should implement this value with RO access.
        "
    ::= { mltNetTcpipGeneralEntry 7 }

   mltNetTcpipAddressServer  OBJECT-TYPE
    SYNTAX    IpAddress
    ACCESS    read-only
    STATUS    mandatory
    DESCRIPTION
        "
        IP address of Server which offered IP address when 
        IP address was acquired by bootProtocol.
        When it is manually inputted or Address in NVRAM is used, 
        '0.0.0.0' shall be inputted for this value. 
        This value shall be held even if turning a power supply off.
        "
    ::= { mltNetTcpipGeneralEntry 8}

   mltNetTcpipRawPortNumber  OBJECT-TYPE
    SYNTAX     INTEGER
    ACCESS     read-write
    STATUS     mandatory
    DESCRIPTION
        "
        Port number for RAW socket printing.
        Default shall be '9100'.
        In addition, two or more RAW Port printings shall not be supported.

        If this setting can not be set from Network access, 
        a device should implement this value with RO access.
        "
       ::= { mltNetTcpipGeneralEntry 9 }

   mltNetTcpipSupportService  OBJECT-TYPE
    SYNTAX     INTEGER
    ACCESS     read-write
    STATUS     mandatory
    DESCRIPTION
        "
        In NetworkInterface, shows the service supported on TCP/IP by Bitmap. 

        An integer bitmap value specifying TCP/IP support service 
        information. Each bit in the integer is defined as follows.

            bit   Value     Service
            ---   -----     ---------
             0       1        Reserved
             1       2        Reserved
             2       4      LPD
             3       8        Reserved for LPR
             4      16      telnet
             5      32        Reserved for telnet client
             6      64      ftp server
             7     128      ftp client
             8     256      http server
             9     512        Reserved for http client
            10    1024        Reserved for POP3 server
            11    2048      POP3 client
            12    4096        Reserved for SMTP server
            13    8132      SMTP client
            14   16364      ipp
            15   32768        Reserved
            16   65536        Reserved
            17  131072      slp
            18  262144        Reserved for IMAP server
            19  524288      IMAP client
            20 1048576          Reserved 
            21 2097152          Reserved for UPnP

           "
     ::= { mltNetTcpipGeneralEntry 10 }

   mltNetTcpipDnsSupport  OBJECT-TYPE
    SYNTAX  INTEGER {
            notSupported (0),
            use (1),
            noUse (2)
            }  
    ACCESS  read-only
    STATUS  mandatory
    DESCRIPTION
        "
        Sets up the availability of use of DNS. 
        The following value shall be used.
        When DNS is not being supported, always takes 0.
        When supporting, Default shall be noUse(2).

        If this setting can not be set from Network access, 
        a device should implement this value with RO access.
        "
    ::= { mltNetTcpipGeneralEntry 11 }

   mltNetTcpipDnsHostName  OBJECT-TYPE
    SYNTAX    DisplayString(SIZE(0..63))
    ACCESS    read-write
    STATUS    mandatory
    DESCRIPTION
        "
        The host name of NetworkInterface used by DNS. 
        Default in the case of supporting DNS is Null (size =0).
        When DNS is not being supported, implement '-' (hyphen)
        and shall be RO.

        If this setting can not be set from Network access, 
        a device should implement this value with RO access.
        "
    ::= { mltNetTcpipGeneralEntry 12 }

   mltNetTcpipDnsDomainName  OBJECT-TYPE
    SYNTAX    DisplayString(SIZE(0..63))
    ACCESS    read-write
    STATUS    mandatory
    DESCRIPTION
        "
        Domain name to which NetworkInterface used by DNS belongs. 
        Default in the case of supporting DNS is Null (size =0).
        When DNS is not being supported, implement '-' (hyphen) 
        and shall be RO.

        If this setting can not be set from Network access, 
        a device should implement this value with RO access.
        "
    ::= { mltNetTcpipGeneralEntry 13 }


   mltNetTcpipDnsTable  OBJECT-TYPE
    SYNTAX    SEQUENCE OF MltNetTcpipDnsEntry
    ACCESS    not-accessible
    STATUS    mandatory
    DESCRIPTION
        "
        The table for showing DNS Server. 
        "
    ::= { mltNetTcpipGeneral 2 }

   mltNetTcpipDnsEntry OBJECT-TYPE
    SYNTAX    MltNetTcpipDnsEntry
    ACCESS    not-accessible
    STATUS    mandatory
    DESCRIPTION
        "
        "
    INDEX  { mltNetTcpipDnsIfIndex, mltNetTcpipDnsServerIndex }
    ::= { mltNetTcpipDnsTable 1 }

   MltNetTcpipDnsEntry ::= SEQUENCE {
        mltNetTcpipDnsIfIndex       INTEGER,
        mltNetTcpipDnsServerIndex   INTEGER,
        mltNetTcpipDnsServerAddress IpAddress
         }

   mltNetTcpipDnsIfIndex  OBJECT-TYPE
    SYNTAX     INTEGER
    ACCESS     read-only
    STATUS     mandatory
    DESCRIPTION
        "
        The index for uniquely showing NetworkInterface to which 
        IP address is set. The value of index shall be the same 
        value with mltNetGeneralIndex (ifIndex).
        "
       ::= { mltNetTcpipDnsEntry 1 }

   mltNetTcpipDnsServerIndex  OBJECT-TYPE
    SYNTAX     INTEGER
    ACCESS     read-only
    STATUS     mandatory
    DESCRIPTION
        "
        The index for uniquely showing each DNS Server. 
        It shall have at least one or more Indexes as Default. 
        The number of Indexes depends on an implementation.
        "
       ::= { mltNetTcpipDnsEntry 2 }

   mltNetTcpipDnsServerAddress  OBJECT-TYPE
    SYNTAX    IpAddress
    ACCESS    read-write
    STATUS    mandatory
    DESCRIPTION
        "
        IP address of DNS Server.

        If this setting can not be set from Network access, 
        a device should implement this value with RO access.
        "
       ::= { mltNetTcpipDnsEntry 3 }


-- mltNetLpd Group

-- The information of LPD relation which NetworkInterface has is included. 
-- The following items shall be defined. 
-- When it does not have the function of LPD, 
-- it is not necessary to implement this Group.

   mltNetLpdGeneralTable  OBJECT-TYPE
    SYNTAX    SEQUENCE OF MltNetLpdGeneralEntry
    ACCESS    not-accessible
    STATUS    mandatory
    DESCRIPTION
        "
        The table for showing the general information of lpd. 
        "
    ::= { mltNetLpd 1 }
        
   mltNetLpdGeneralEntry OBJECT-TYPE
    SYNTAX    MltNetLpdGeneralEntry
    ACCESS    not-accessible
    STATUS    mandatory
    DESCRIPTION
        "
        "
    INDEX  { mltNetLpdIfIndex }
    ::= { mltNetLpdGeneralTable 1 }

   MltNetLpdGeneralEntry ::= SEQUENCE {
        mltNetLpdIfIndex    INTEGER,
        mltNetLpdEnable     INTEGER,
        mltNetLpdPort       INTEGER
         }

   mltNetLpdIfIndex  OBJECT-TYPE
    SYNTAX     INTEGER
    ACCESS     read-only
    STATUS     mandatory
    DESCRIPTION
        "
        The index for uniquely specifying NetworkInterface to 
        which lpd is set. 
        The value of index shall be the same value with 
        mltNetGeneralIndex (ifIndex).
        "
       ::= { mltNetLpdGeneralEntry 1 }

   mltNetLpdEnable  OBJECT-TYPE
    SYNTAX  INTEGER {
            enable (1),
            disable (2)
            }  
    ACCESS  read-write
    STATUS  mandatory
    DESCRIPTION
        "
        Sets up Enable/Disable of service of lpd.
        "
       ::= { mltNetLpdGeneralEntry 2 }

   mltNetLpdPort  OBJECT-TYPE
    SYNTAX     INTEGER
    ACCESS     read-write
    STATUS     mandatory
    DESCRIPTION
        "
        Specifies Port number which lpd uses. Default is 515.
        "
       ::= { mltNetLpdGeneralEntry 3 }

   mltNetLpdQueueTable  OBJECT-TYPE
    SYNTAX    SEQUENCE OF MltNetLpdQueueEntry
    ACCESS    not-accessible
    STATUS    mandatory
    DESCRIPTION
        "
        The table for showing the information of Queue of lpd. 
        "
    ::= { mltNetLpd 2 }

   mltNetLpdQueueEntry OBJECT-TYPE
    SYNTAX    MltNetLpdQueueEntry
    ACCESS    not-accessible
    STATUS    mandatory
    DESCRIPTION
        "
        "
    INDEX  { mltNetLpdQueueIfIndex, mltNetLpdQueueIndex }
    ::= { mltNetLpdQueueTable 1 }

   MltNetLpdQueueEntry ::= SEQUENCE {
        mltNetLpdQueueIfIndex   INTEGER,
        mltNetLpdQueueIndex     INTEGER,
        mltNetLpdQueueName      DisplayString,
        mltNetLpdQueueDescr     DisplayString,
        mltNetLpdQueueFilter    INTEGER,
        mltNetLpdQueueBanner    INTEGER,
        mltNetLpdQueueEnable    INTEGER
         }

   mltNetLpdQueueIfIndex  OBJECT-TYPE
    SYNTAX     INTEGER
    ACCESS     read-only
    STATUS     mandatory
    DESCRIPTION
        "
        The index for uniquely specifying NetworkInterface to 
        which each Queue is set. 
        The value of index shall be the same value with 
        mltNetGeneralIndex (ifIndex).
        "
       ::= { mltNetLpdQueueEntry 1 }

   mltNetLpdQueueIndex  OBJECT-TYPE
    SYNTAX     INTEGER
    ACCESS     read-only
    STATUS     mandatory
    DESCRIPTION
        "
        The index for uniquely showing Queue set up for 
        every NetworkInterface. 
        The number of Indexes depends on an implementation.
        "
       ::= { mltNetLpdQueueEntry 2 }

   mltNetLpdQueueName  OBJECT-TYPE
    SYNTAX    DisplayString(SIZE(0..15))
    ACCESS    read-write
    STATUS    mandatory
    DESCRIPTION
        "
        The name of Queue used at the time of printing by lpd. 
        The value of Default depends on a model. 
        Default shall be '-' (hyphen) when printing function 
        has no relation to the name of Queue.
        "
    ::= { mltNetLpdQueueEntry 3 }

   mltNetLpdQueueDescr  OBJECT-TYPE
    SYNTAX    DisplayString(SIZE(0..31))
    ACCESS    read-write
    STATUS    mandatory
    DESCRIPTION
        "
        It recommends describing the information which serves 
        as help when a user performs a setup for lpr printing.
        "
    ::= { mltNetLpdQueueEntry 4 }

   mltNetLpdQueueFilter  OBJECT-TYPE
    SYNTAX     INTEGER
    ACCESS     read-only
    STATUS     mandatory
    DESCRIPTION
        "
        Selects Filter function set as Queue by Bitmap. 
        When there is no Filter function in Queue, shall always be 0.
        
        Each bit in the integer is defined as follows.

            bit   Value     Filter
            ---   -----     ---------
             0       1      FF (Form Feed)
             1       2      LF (Line Feed)
             2       4      CR (Carriage Return)
             3       8      PS (Add PostScript Header)
             4      16        reserved
             5      32      rejectPS
             6      64      rejectPCL
             7     128      rejectASCIIt

        "
     ::= { mltNetLpdQueueEntry 5 }

   mltNetLpdQueueBanner  OBJECT-TYPE
    SYNTAX  INTEGER {
            noBanner (0),
            ascii (1),
            pcl (2),
            ps (3)
            }  
    ACCESS  read-only
    STATUS  mandatory
    DESCRIPTION
        "
        A setup of BannerPage set in Queue. 
        "
    ::= { mltNetLpdQueueEntry 6 }

   mltNetLpdQueueEnable  OBJECT-TYPE
    SYNTAX  INTEGER {
            enable (1),
            disable (2)
            }  
    ACCESS  read-only
    STATUS  mandatory
    DESCRIPTION
        "
        Sets up Enable/Disable of each Queue.
        "
       ::= { mltNetLpdQueueEntry 7 }

-- mltNetFtpd Group

-- The information on FTP Server relation which NetworkInterface has 
-- is included. The following items shall be defined. 
-- In the system without FTP Server function, 
-- it is not necessary to implement this Group.


   mltNetFtpdGeneralTable  OBJECT-TYPE
    SYNTAX    SEQUENCE OF MltNetFtpdGeneralEntry
    ACCESS    not-accessible
    STATUS    mandatory
    DESCRIPTION
        "
        The table for showing the general information of FTP Server. 
        "
    ::= { mltNetFtpd 1 }

   mltNetFtpdGeneralEntry OBJECT-TYPE
    SYNTAX    MltNetFtpdGeneralEntry
    ACCESS    not-accessible
    STATUS    mandatory
    DESCRIPTION
        "
        "
    INDEX  { mltNetFtpdIfIndex }
    ::= { mltNetFtpdGeneralTable 1 }

   MltNetFtpdGeneralEntry ::= SEQUENCE {
        mltNetFtpdIfIndex   INTEGER,
        mltNetFtpdEnable    INTEGER,
        mltNetFtpdPort      INTEGER
         }

   mltNetFtpdIfIndex  OBJECT-TYPE
    SYNTAX     INTEGER
    ACCESS     read-only
    STATUS     mandatory
    DESCRIPTION
        "
        The index for uniquely specifying NetworkInterface to 
        which FTP server is set up. The value of index shall 
        be the same value with mltNetGeneralIndex (ifIndex).
        "
       ::= { mltNetFtpdGeneralEntry 1 }

   mltNetFtpdEnable  OBJECT-TYPE
    SYNTAX  INTEGER {
            enable (1),
            disable (2)
            }  
    ACCESS  read-write
    STATUS  mandatory
    DESCRIPTION
        "
        Sets up Enable/Disable of service of FTP. 
        "
       ::= { mltNetFtpdGeneralEntry 2 }

   mltNetFtpdPort  OBJECT-TYPE
    SYNTAX     INTEGER
    ACCESS     read-write
    STATUS     mandatory
    DESCRIPTION
        "
        Specifies Port number which FTP Server uses. Default is 21.
        "
       ::= { mltNetFtpdGeneralEntry 3 }


   mltNetFtpdConfigTable  OBJECT-TYPE
    SYNTAX    SEQUENCE OF MltNetFtpdConfigEntry
    ACCESS    not-accessible
    STATUS    mandatory
    DESCRIPTION
        "
        The table for showing the User information connectable to FTPServer. 
        "
    ::= { mltNetFtpd 2 }

   mltNetFtpdConfigEntry OBJECT-TYPE
    SYNTAX    MltNetFtpdConfigEntry
    ACCESS    not-accessible
    STATUS    mandatory
    DESCRIPTION
        "
        "
    INDEX  { mltNetFtpdConfigIfIndex, mltNetFtpdUserIndex }
    ::= { mltNetFtpdConfigTable 1 }

   MltNetFtpdConfigEntry ::= SEQUENCE {
        mltNetFtpdConfigIfIndex INTEGER,
        mltNetFtpdUserIndex     INTEGER,
        mltNetFtpdUser          DisplayString,
        mltNetFtpdUserPassWd    DisplayString,
        mltNetFtpdCapability    INTEGER,
        mltNetFtpdDescr         DisplayString
         }

   mltNetFtpdConfigIfIndex  OBJECT-TYPE
    SYNTAX     INTEGER
    ACCESS     read-only
    STATUS     mandatory
    DESCRIPTION
        "
        The Index for uniquely specifying NetworkInterface to 
        which each User considers as an object. 
        The value of index shall be the same value with 
        mltNetGeneralIndex (ifIndex).
        "
    ::= { mltNetFtpdConfigEntry 1 }

   mltNetFtpdUserIndex  OBJECT-TYPE
    SYNTAX     INTEGER
    ACCESS     read-only
    STATUS     mandatory
    DESCRIPTION
        "
        The index for uniquely showing the User. 
        The number of Indexes depends on an implementation.
        "
    ::= { mltNetFtpdConfigEntry  2 }

   mltNetFtpdUser  OBJECT-TYPE
    SYNTAX    DisplayString(SIZE(0..15))
    ACCESS    read-only
    STATUS    mandatory
    DESCRIPTION
        "
        Login user name of FTP Server.
        "
    ::= { mltNetFtpdConfigEntry 3 }

   mltNetFtpdUserPassWd  OBJECT-TYPE
    SYNTAX    DisplayString(SIZE(0..15))
    ACCESS    read-only
    STATUS    mandatory
    DESCRIPTION
        "
        Password of FTP Server. 
        When it is gotten, applying scramble to value is not accepted. 
        About security, support by the management tool side.
        "
    ::= { mltNetFtpdConfigEntry 4 }

   mltNetFtpdCapability  OBJECT-TYPE
    SYNTAX     INTEGER
    ACCESS     read-only
    STATUS     mandatory
    DESCRIPTION
        "
        Shows the function permitted to each user on FTP Server by Bitmap.
        
        An integer bitmap value specifying FTP function
        information. Each bit in the integer is defined as follows.

            bit   Value     Filter
            ---   -----     ---------
             0       1      putting job & No Filter
             1       2      putting job & CR-LF invert
             2       4      get (status or job or Driver)
             3       8      put NIC Firmware
             4      16      put Printer Font
             5      32      reserved

        "
     ::= { mltNetFtpdConfigEntry 5 }  

   mltNetFtpdDescr  OBJECT-TYPE
    SYNTAX    DisplayString(SIZE(0..31))
    ACCESS    read-write
    STATUS    mandatory
    DESCRIPTION
        "
        Explanation etc. of the function set to each user is indicated.
        "
    ::= { mltNetFtpdConfigEntry 6 }

-- mltNetHttpd Group

-- The information of HTTP Server relation which 
-- NetworkInterface has is included. 
-- The following items shall be defined. 
-- In addition, in this item, the item of IPP 
-- relation shall not be the object.


   mltNetHttpdGeneralTable  OBJECT-TYPE
    SYNTAX    SEQUENCE OF MltNetHttpdGeneralEntry
    ACCESS    not-accessible
    STATUS    mandatory
    DESCRIPTION
        "
        The table for showing the general information about HTTP Server. 
        "
    ::= { mltNetHttpd 1 }

   mltNetHttpdGeneralEntry OBJECT-TYPE
    SYNTAX    MltNetHttpdGeneralEntry
    ACCESS    not-accessible
    STATUS    mandatory
    DESCRIPTION
        "
        "
    INDEX  { mltNetHttpdIfIndex }
    ::= { mltNetHttpdGeneralTable 1 }

   MltNetHttpdGeneralEntry ::= SEQUENCE {
        mltNetHttpdIfIndex  INTEGER,
        mltNetHttpdEnable   INTEGER,
        mltNetHttpdPort     INTEGER,
        mltNetHttpdDescr    DisplayString
         }


   mltNetHttpdIfIndex  OBJECT-TYPE
    SYNTAX     INTEGER
    ACCESS     read-only
    STATUS     mandatory
    DESCRIPTION
        "
        Index for uniquely showing NetworkInterface to 
        which HTTP Server is set up. 
        The value of index shall be the same value with 
        mltNetGeneralIndex (ifIndex).
        "
       ::= { mltNetHttpdGeneralEntry 1 }

   mltNetHttpdEnable  OBJECT-TYPE
    SYNTAX  INTEGER {
            enable (1),
            disable (2)
            }  
    ACCESS  read-write
    STATUS  mandatory
    DESCRIPTION
        "
        Sets up Enable/Disable of service of HTTP Server. 
        "
       ::= { mltNetHttpdGeneralEntry 2 }

   mltNetHttpdPort  OBJECT-TYPE
    SYNTAX     INTEGER
    ACCESS     read-write
    STATUS     mandatory
    DESCRIPTION
        "
        The port number which HTTP Server uses. Default is 80.
        "
       ::= { mltNetHttpdGeneralEntry 3 }

   mltNetHttpdDescr  OBJECT-TYPE
    SYNTAX    DisplayString(SIZE(0..31))
    ACCESS    read-write
    STATUS    mandatory
    DESCRIPTION
        "
        Indicates the information, such as a version of HTTP Server.
        "
    ::= { mltNetHttpdGeneralEntry 4 }

-- mltNetSmtpClient Group

-- The information of SMTP relation which NetworkInterface has is included. 
-- The following items shall be defined. 
-- In the system without a mail transmitting function, 
-- it is not necessary to implement this Group.
-- In a definition of this MIB, it considers as the outside of an object 
-- about address information


   mltNetSmtpGeneralTable  OBJECT-TYPE
    SYNTAX    SEQUENCE OF MltNetSmtpGeneralEntry
    ACCESS    not-accessible
    STATUS    mandatory
    DESCRIPTION
        "
        The table for showing the general information of SMTP. 
        "
    ::= { mltNetSmtpClient 1 }

   mltNetSmtpGeneralEntry OBJECT-TYPE
    SYNTAX    MltNetSmtpGeneralEntry
    ACCESS    not-accessible
    STATUS    mandatory
    DESCRIPTION
        "
        "
    INDEX  { mltNetSmtpIfIndex }
    ::= { mltNetSmtpGeneralTable 1 }

   MltNetSmtpGeneralEntry ::= SEQUENCE {
        mltNetSmtpIfIndex       INTEGER,
        mltNetSmtpEnable        INTEGER,
        mltNetSmtpServerAddress DisplayString,
        mltNetSmtpPort          INTEGER
        }

   mltNetSmtpIfIndex  OBJECT-TYPE
    SYNTAX     INTEGER
    ACCESS     read-only
    STATUS     mandatory
    DESCRIPTION
        "
        The index for uniquely specifying NetworkInterface to 
        which SMTP is set. 
        The value of Index shall be the same value with 
        mltNetGeneralIndex (ifIndex).
        "
       ::= { mltNetSmtpGeneralEntry 1 }

   mltNetSmtpEnable  OBJECT-TYPE
    SYNTAX     INTEGER{
            enable (1),
            disable (2)
            }  
    ACCESS     read-write
    STATUS     mandatory
    DESCRIPTION
        "
        Sets up Enable/Disable of service of SMTP. 
        "
       ::= { mltNetSmtpGeneralEntry 2 }

   mltNetSmtpServerAddress  OBJECT-TYPE
    SYNTAX     DisplayString(SIZE(0..63))
    ACCESS     read-only
    STATUS     mandatory
    DESCRIPTION
        "
        Shows the IP address of SMTP Server. 
        Considering about specification by Domain name, 
        it is made into DisplayString.
        In the case of specifying by the IP address, 
        it shall be handled as a character string of maximum 15 
        characters of 'xxx.xxx.xxx.xxx'.
        Whether to accept a setup by Domain name is dependent 
        on an implementation of a model.
        "
       ::= { mltNetSmtpGeneralEntry 3 }

   mltNetSmtpPort  OBJECT-TYPE
    SYNTAX     INTEGER
    ACCESS     read-write
    STATUS     mandatory
    DESCRIPTION
        "
        Specifies Port number which SMTP uses. Default is 25.
        "
       ::= { mltNetSmtpGeneralEntry 4 }


   mltNetSmtpAccountTable OBJECT-TYPE
    SYNTAX    SEQUENCE OF MltNetSmtpAccountEntry
    ACCESS    not-accessible
    STATUS    mandatory
    DESCRIPTION
        "
        The table for showing Account information of SMTP. 
        "
    ::= { mltNetSmtpClient 2 }

   mltNetSmtpAccountEntry OBJECT-TYPE
    SYNTAX    MltNetSmtpAccountEntry 
    ACCESS    not-accessible
    STATUS    mandatory
    DESCRIPTION
        "
        "
    INDEX  { mltNetSmtpAccountIfIndex, mltNetSmtpAccountIndex }
    ::= { mltNetSmtpAccountTable 1 }

   MltNetSmtpAccountEntry ::= SEQUENCE {
        mltNetSmtpAccountIfIndex    INTEGER,
        mltNetSmtpAccountIndex      INTEGER,
        mltNetSmtpFromAddress       DisplayString,
        mltNetSmtpReplyAddress      DisplayString,
        mltNetSmtpConnTimeout       INTEGER,
        mltNetSmtpPurpose           INTEGER,
        mltNetSmtpDescription       DisplayString
        }

   mltNetSmtpAccountIfIndex  OBJECT-TYPE
    SYNTAX     INTEGER
    ACCESS     read-only
    STATUS     mandatory
    DESCRIPTION
        "
        The index for uniquely specifying NetworkInterface to 
        which each From setup makes into the object. 
        The value of Index shall be the same value with 
        mltNetGeneralIndex (ifIndex).
        "
       ::= { mltNetSmtpAccountEntry  1 }

   mltNetSmtpAccountIndex  OBJECT-TYPE
    SYNTAX     INTEGER
    ACCESS     read-only
    STATUS     mandatory
    DESCRIPTION
        "
        The index for uniquely showing e-mail From address setup. 
        Although the number of index depends on an implementation, 
        index of the number of functions in which EP-NET and 
        Scan function etc. are supporting needs to be prepared in Default.
        "
       ::= { mltNetSmtpAccountEntry  2 }

   mltNetSmtpFromAddress  OBJECT-TYPE
    SYNTAX     DisplayString(SIZE(0..129))
    ACCESS     read-write
    STATUS     mandatory
    DESCRIPTION
        "
        The address of From Field used by SMTP.
        "
       ::= { mltNetSmtpAccountEntry  3 }

   mltNetSmtpReplyAddress  OBJECT-TYPE
    SYNTAX     DisplayString(SIZE(0..129))
    ACCESS     read-write
    STATUS     mandatory
    DESCRIPTION
        "
        The address of RepryTo used by SMTP.
        "
       ::= { mltNetSmtpAccountEntry  4 }

   mltNetSmtpConnTimeout  OBJECT-TYPE
    SYNTAX     INTEGER
    ACCESS     read-write
    STATUS     mandatory
    DESCRIPTION
        "
        Timeout setup in SMTP. A unit is second. 
        It shall be possible to set the number between 30-300. 
        Default is 60 (seconds).
        "
       ::= { mltNetSmtpAccountEntry  5 }

   mltNetSmtpPurpose  OBJECT-TYPE
    SYNTAX     INTEGER {
            other (0),
            epNet (1),
            scanFunction (2)
            }  
    ACCESS     read-only
    STATUS     mandatory
    DESCRIPTION
        "
        Displays the use of From setup of SMTP. 
        "
       ::= { mltNetSmtpAccountEntry  6 }

   mltNetSmtpDescription  OBJECT-TYPE
    SYNTAX     DisplayString(SIZE(0..31))
    ACCESS     read-write
    STATUS     mandatory
    DESCRIPTION
        "
        Description of each From setup. 
        Default is dependent on an implementation.
        "
       ::= { mltNetSmtpAccountEntry 7 }


-- mltNetIpp Group

-- The information of IPP relation which NetworkInterface has is included. 
-- In the system without IPP function, it is not necessary to implement 
-- this Group.
-- All IPP MIB is optional. 


    mltNetIppGeneral
            OBJECT IDENTIFIER ::= { mltNetIpp 1 }   
    mltNetIppPrtDescrAttribute
            OBJECT IDENTIFIER ::= { mltNetIpp 2 }
    mltNetIppJobTemplateAttribute 
            OBJECT IDENTIFIER ::= { mltNetIpp 3 }

-- mltNetIppGeneral Group

   mltNetIppGeneralTable  OBJECT-TYPE
    SYNTAX    SEQUENCE OF MltNetIppGeneralEntry
    ACCESS    not-accessible
    STATUS    optional
    DESCRIPTION
        "
        The table for showing the general information of IPP. 
        "
    ::= { mltNetIppGeneral 1 }


   mltNetIppGeneralEntry  OBJECT-TYPE
    SYNTAX    MltNetIppGeneralEntry
    ACCESS    not-accessible
    STATUS    optional
    DESCRIPTION
        "
        "
    INDEX  { mltNetIppGeneralIfIndex }
    ::= { mltNetIppGeneralTable 1 }

   MltNetIppGeneralEntry ::= SEQUENCE {
        mltNetIppGeneralIfIndex     INTEGER,
        mltNetIppServiceEnable      INTEGER,
        mltNetIppDefaultPortIndex   INTEGER
        }

   mltNetIppGeneralIfIndex  OBJECT-TYPE
    SYNTAX     INTEGER
    ACCESS     read-only
    STATUS     optional
    DESCRIPTION
        "
        The index for uniquely specifying NetworkInterface to 
        which IPP is set.   
        The value of Index shall be the same value with 
        mltNetGeneralIndex (ifIndex).
        "
       ::= { mltNetIppGeneralEntry 1 }

   mltNetIppServiceEnable  OBJECT-TYPE
    SYNTAX     INTEGER{
            enable (1),
            disable (2)
            }  
    ACCESS     read-write
    STATUS     optional
    DESCRIPTION
        "
        Sets up Enable/Disable of service of IPP
        "
       ::= { mltNetIppGeneralEntry 2 }

   mltNetIppDefaultPortIndex  OBJECT-TYPE
    SYNTAX     INTEGER
    ACCESS     read-write
    STATUS     optional
    DESCRIPTION
        "
        mltNetIppPortIndex which shows Default Port number used by IPP.
        "
       ::= { mltNetIppGeneralEntry 3 }


   mltNetIppPortTable OBJECT-TYPE
    SYNTAX    SEQUENCE OF MltNetIppPortEntry
    ACCESS    not-accessible
    STATUS    optional
    DESCRIPTION
        "
        The table for showing Port information of IPP. 
        "
    ::= { mltNetIppGeneral 2 }

   mltNetIppPortEntry  OBJECT-TYPE
    SYNTAX    MltNetIppPortEntry
    ACCESS    not-accessible
    STATUS    optional
    DESCRIPTION
        "
        "
    INDEX  { mltNetIppPortIfIndex, mltNetIppPortIndex }
    ::= { mltNetIppPortTable 1 }

   MltNetIppPortEntry ::= SEQUENCE {
        mltNetIppPortIfIndex    INTEGER,
        mltNetIppPortIndex      INTEGER,
        mltNetIppPortNumber     INTEGER
        }

   mltNetIppPortIfIndex  OBJECT-TYPE
    SYNTAX     INTEGER
    ACCESS     read-only
    STATUS     optional
    DESCRIPTION
        "
        The index for uniquely specifying NetworkInterface to 
        which IPP is set. 
        The value of Index shall be the same value with 
        mltNetGeneralIndex (ifIndex).
        "
       ::= { mltNetIppPortEntry 1 }

   mltNetIppPortIndex  OBJECT-TYPE
    SYNTAX     INTEGER
    ACCESS     read-only
    STATUS     optional
    DESCRIPTION
        "
        The index for uniquely showing Port.
        "
       ::= { mltNetIppPortEntry 2 }

   mltNetIppPortNumber  OBJECT-TYPE
    SYNTAX     INTEGER
    ACCESS     read-only
    STATUS     optional
    DESCRIPTION
        "
        Port number. '631' is supported at least.
        "
       ::= { mltNetIppPortEntry 3 }


-- mltnetIppPrtDescrAttribute Group

-- The information of the Printer Description 
-- Attribute relation of IPP is included.

   mltNetIppPrtDescGeneralTable  OBJECT-TYPE
    SYNTAX    SEQUENCE OF MltNetIppPrtDescGeneralEntry
    ACCESS    not-accessible
    STATUS    optional
    DESCRIPTION
        "
        The table for showing the general information about
        Printer Description Attribute of IPP.
        "
    ::= { mltNetIppPrtDescrAttribute 1 }

   mltNetIppPrtDescGeneralEntry OBJECT-TYPE
    SYNTAX    MltNetIppPrtDescGeneralEntry
    ACCESS    not-accessible
    STATUS    optional
    DESCRIPTION
        "
        "
    INDEX  { mltIppPrtDescGeneralIfIndex }
    ::= { mltNetIppPrtDescGeneralTable 1 }

   MltNetIppPrtDescGeneralEntry ::= SEQUENCE {
        mltIppPrtDescGeneralIfIndex     INTEGER,
        mltIppPrtName                   DisplayString,
        mltIppPrtMoreInfo               DisplayString,
        mltIppPrtState                  INTEGER,
        mltIppCharSetConfiguredIndex    INTEGER,
        mltIppNaturalLanguageConfiguredIndex    INTEGER,
        mltIppDocFormatDefaultIndex     INTEGER,
        mltIppPrinterIsAcceptingJobs   INTEGER,
        mltIppQueuedJobCount            Counter,
        mltIppColorSupported            INTEGER,
        mltIppPdlOverrideSupported      INTEGER,
        mltIppPrinterUpTime             TimeTicks,
        mltIppPrtLocation               DisplayString,
        mltIppPrinterCurrentTime        DateAndTime
          }

   mltIppPrtDescGeneralIfIndex  OBJECT-TYPE
    SYNTAX     INTEGER
    ACCESS     read-only
    STATUS     optional
    DESCRIPTION
        "
        Index for uniquely specifying NetworkInterface 
        to which IPP is set. 
        The value of index shall be the same value 
        with mltNetGeneralIndex (ifIndex).
        "
       ::= { mltNetIppPrtDescGeneralEntry 1 }

   mltIppPrtName  OBJECT-TYPE
    SYNTAX     DisplayString(SIZE(0..127))
    ACCESS     read-write
    STATUS     optional
    DESCRIPTION
        "
        'printer-name' attribute is shown.
        "
       ::= { mltNetIppPrtDescGeneralEntry 2 }

   mltIppPrtMoreInfo  OBJECT-TYPE
    SYNTAX     DisplayString(SIZE(0..127))
    ACCESS     read-write
    STATUS     optional
    DESCRIPTION
        "
        'printer-more-info' attribute is shown.
        "
       ::= { mltNetIppPrtDescGeneralEntry 3 }

   mltIppPrtState  OBJECT-TYPE
    SYNTAX     INTEGER{
                    idle(3),
                    processing(4),
                    stopped(5)
                    }
    ACCESS     read-only
    STATUS     optional
    DESCRIPTION
        "
        'printer-state' attribute is shown.
        "
       ::= { mltNetIppPrtDescGeneralEntry 4 }

   mltIppCharSetConfiguredIndex  OBJECT-TYPE
    SYNTAX     INTEGER
    ACCESS     read-only
    STATUS     optional
    DESCRIPTION
        "
        Index which shows 'charset-configured.'
        "
       ::= { mltNetIppPrtDescGeneralEntry 5 }

   mltIppNaturalLanguageConfiguredIndex  OBJECT-TYPE
    SYNTAX     INTEGER
    ACCESS     read-only
    STATUS     optional
    DESCRIPTION
        "
        'natural-language-configured' attribute is shown.
        "
       ::= { mltNetIppPrtDescGeneralEntry 6 }

   mltIppDocFormatDefaultIndex  OBJECT-TYPE
    SYNTAX     INTEGER
    ACCESS     read-write
    STATUS     optional
    DESCRIPTION
        "
        'document-format-default' attribute is shown.
        "
       ::= { mltNetIppPrtDescGeneralEntry 7 }


   mltIppPrinterIsAcceptingJobs  OBJECT-TYPE
    SYNTAX     INTEGER{
                    enable(1),
                    disable(2)
                    }
    ACCESS     read-write
    STATUS     optional
    DESCRIPTION
        "
        'printer-is-accepting-jobs' attribute is shown. 
        "
       ::= { mltNetIppPrtDescGeneralEntry 8 }

   mltIppQueuedJobCount  OBJECT-TYPE
    SYNTAX     Counter
    ACCESS     read-only
    STATUS     optional
    DESCRIPTION
        "
        'queued-job-count' attribute is shown.
        "
       ::= { mltNetIppPrtDescGeneralEntry 9 }

   mltIppColorSupported  OBJECT-TYPE
    SYNTAX     INTEGER{
                    enable(1),
                    disable(2)
                    }
    ACCESS     read-only
    STATUS     optional
    DESCRIPTION
        "
        'color-supported' attribute is shown.
        "
       ::= { mltNetIppPrtDescGeneralEntry 10 }

   mltIppPdlOverrideSupported  OBJECT-TYPE
    SYNTAX     INTEGER{
                    attempted(3),
                    notAttempted(4)
                    }
    ACCESS     read-only
    STATUS     optional
    DESCRIPTION
        "
        'pdl-override-supported' attribute is shown. 
        "
       ::= { mltNetIppPrtDescGeneralEntry 11 }

   mltIppPrinterUpTime  OBJECT-TYPE
    SYNTAX     TimeTicks
    ACCESS     read-only
    STATUS     optional
    DESCRIPTION
        "
        'printer-up-time' attribute is shown.
        "
       ::= { mltNetIppPrtDescGeneralEntry 12 }

   mltIppPrtLocation  OBJECT-TYPE
    SYNTAX     DisplayString(SIZE(0..127))
    ACCESS     read-write
    STATUS     optional
    DESCRIPTION
        "
        'printer-location' attribute is shown.
        "
       ::= { mltNetIppPrtDescGeneralEntry 13 }
       
    mltIppPrinterCurrentTime  OBJECT-TYPE
    SYNTAX     DateAndTime
    ACCESS     read-only
    STATUS     optional
    DESCRIPTION
        "
        'printer-current-up-time' attribute is shown.
        "
       ::= { mltNetIppPrtDescGeneralEntry 21 }

   mltIppUriSupportedTable  OBJECT-TYPE
    SYNTAX    SEQUENCE OF MltIppUriSupportedEntry
    ACCESS    not-accessible
    STATUS    optional
    DESCRIPTION
        "
        The table for showing 'printer-uri-authentication-supported' 
        and 'printer-uri-security-supported' to 'printer-uri-supported' 
        attribute and each 'printer-uri'. 
        "
    ::= { mltNetIppPrtDescrAttribute 2 }

   mltIppUriSupportedEntry OBJECT-TYPE
    SYNTAX    MltIppUriSupportedEntry
    ACCESS    not-accessible
    STATUS    optional
    DESCRIPTION
        "
        "
    INDEX  { mltIppUriIfIndex, mltIppUriIndex }
    ::= { mltIppUriSupportedTable 1 }

   MltIppUriSupportedEntry ::= SEQUENCE {
        mltIppUriIfIndex        INTEGER,
        mltIppUriIndex          INTEGER,
        mltIppUri               DisplayString,
        mltIppUriSecurity       INTEGER,
        mltIppUriAuthentication INTEGER
        }

   mltIppUriIfIndex  OBJECT-TYPE
    SYNTAX     INTEGER
    ACCESS     read-only
    STATUS     optional
    DESCRIPTION
        "
        Index for uniquely specifying NetworkInterface 
        to which IPP is set. 
        The value of index shall be the same value with 
        mltNetGeneralIndex (ifIndex).
        "
       ::= { mltIppUriSupportedEntry 1 }

   mltIppUriIndex  OBJECT-TYPE
    SYNTAX     INTEGER
    ACCESS     read-only
    STATUS     optional
    DESCRIPTION
        "
        Index for uniquely showing 'printer-uri'.
        "
       ::= { mltIppUriSupportedEntry 2 }

   mltIppUri  OBJECT-TYPE
    SYNTAX     DisplayString(SIZE(0..127))
    ACCESS     read-only
    STATUS     optional
    DESCRIPTION
        "
        'printer-uri' to support is shown.
        "
       ::= { mltIppUriSupportedEntry 3 }

   mltIppUriSecurity  OBJECT-TYPE
    SYNTAX     INTEGER{
                    none(3),
                    ssl3(4),
                    tls(5)
                    }
    ACCESS     read-only
    STATUS     optional
    DESCRIPTION
        "
        'printer-uri-security' to 'printer-uri' to support is shown.
        "
       ::= { mltIppUriSupportedEntry 4 }

   mltIppUriAuthentication  OBJECT-TYPE
    SYNTAX     INTEGER{
                    none(3),
                    requestingUserName(4),
                    basic(5),
                    digest(6),
                    certificate(7)
                    }
    ACCESS     read-only
    STATUS     optional
    DESCRIPTION
        "
        'printer-uri-authentication' to 'printer-uri' to support is shown.
        This item is an IPP Ver1.1 support item. 
        In implementation of IPP Ver1.0, 
        it is not necessary to implement this item.
        "
       ::= { mltIppUriSupportedEntry 5 }


   mltIppPrtStateReasonsTable  OBJECT-TYPE
    SYNTAX    SEQUENCE OF MltIppPrtStateReasonsEntry
    ACCESS    not-accessible
    STATUS    optional
    DESCRIPTION
        "
        The table which shows 'printer-state-reasons' attribute.
        "
    ::= { mltNetIppPrtDescrAttribute 3 }

   mltIppPrtStateReasonsEntry OBJECT-TYPE
    SYNTAX    MltIppPrtStateReasonsEntry
    ACCESS    not-accessible
    STATUS    optional
    DESCRIPTION
        "
        "
    INDEX  { mltIppPrtStateReasonIfIndex, mltIppPrtStateReasonIndex }
    ::= { mltIppPrtStateReasonsTable 1 }

   MltIppPrtStateReasonsEntry ::= SEQUENCE {
        mltIppPrtStateReasonIfIndex INTEGER,
        mltIppPrtStateReasonIndex   INTEGER,
        mltIppPrinterStateReason    INTEGER,
        mltIppPrtStateReasonSuffix  INTEGER
        }

   mltIppPrtStateReasonIfIndex  OBJECT-TYPE
    SYNTAX     INTEGER
    ACCESS     read-only
    STATUS     optional
    DESCRIPTION
        "
        The index for uniquely specifying NetworkInterface 
        to which IPP is set. The value of index shall be 
        the same value with mltNetGeneralIndex (ifIndex).
        "
       ::= { mltIppPrtStateReasonsEntry 1 }

   mltIppPrtStateReasonIndex  OBJECT-TYPE
    SYNTAX     INTEGER
    ACCESS     read-only
    STATUS     optional
    DESCRIPTION
        "
        Index for uniquely showing 'printer-state-reasons'.
        "
       ::= { mltIppPrtStateReasonsEntry 2 }

   mltIppPrinterStateReason  OBJECT-TYPE
    SYNTAX     INTEGER{
                    other(2),
                    none(3),
                    mediaNeeded(4),
                    mediaJam(5),
                    movingToPaused(6),
                    paused(7),
                    shutDown(8),
                    connectingToDevice(9),
                    timedOut(10),
                    stopping(11),
                    stoppedPartly(12),
                    tonerLow(13),
                    tonerEmpty(14),
                    spoolAreaFull(15),
                    coverOpen(16),
                    interlockOpen(17),
                    doorOpen(18),
                    inputTrayMissing(19),
                    mediaLow(20),
                    mediaEmpty(21),
                    outputTrayMissing(22),
                    outputAreaAlmostFull(23),
                    outputAreaFull(24),
                    markerSupplyLow(25),
                    markerSupplyEmpty(26),
                    markerWasteAlmostFull(27),
                    markerWasteFull(28),
                    fuserOverTemp(29),
                    fuserUnderTemp(30),
                    opcNearEndOfLife(31),
                    opcLifeOver(32),
                    developerLow(33),
                    developerEmpty(34),
                    interpreterResourceUnavailable(35)
                    }
    ACCESS     read-only
    STATUS     optional
    DESCRIPTION
        "
        'printer-state-reasons' attribute is shown. 
        mltIppPrtStateReasonSuffix shows suffix of 
        '-report', '-warning', and '-error'
        "
       ::= { mltIppPrtStateReasonsEntry 3 }

   mltIppPrtStateReasonSuffix  OBJECT-TYPE
    SYNTAX     INTEGER{
                    report(3),
                    warning(4),
                    error(5)
                    }
    ACCESS     read-only
    STATUS     optional
    DESCRIPTION
        "
        Three suffixes ('-report', '-warning', and '-error') 
        of 'printer-state-reasons' attribute are shown.
        "
       ::= { mltIppPrtStateReasonsEntry 4 }


   mltIppVersionsSupportedTable  OBJECT-TYPE
    SYNTAX    SEQUENCE OF MltIppVersionsSupportedEntry
    ACCESS    not-accessible
    STATUS    optional
    DESCRIPTION
        "
        Table which shows 'ipp-versions-supported.' 
        This item is an IPP Ver1.1 support item. 
        In implementation of IPP Ver1.0, 
        it is not necessary to implement this item.
        "
    ::= { mltNetIppPrtDescrAttribute 4 }

   mltIppVersionsSupportedEntry OBJECT-TYPE
    SYNTAX    MltIppVersionsSupportedEntry
    ACCESS    not-accessible
    STATUS    optional
    DESCRIPTION
        "
        "
    INDEX  { mltIppVersionIfIndex, mltIppVersionIndex }
    ::= { mltIppVersionsSupportedTable 1 }

   MltIppVersionsSupportedEntry ::= SEQUENCE {
        mltIppVersionIfIndex    INTEGER,
        mltIppVersionIndex      INTEGER,
        mltIppVersionType       INTEGER
        }

   mltIppVersionIfIndex  OBJECT-TYPE
    SYNTAX     INTEGER
    ACCESS     read-only
    STATUS     optional
    DESCRIPTION
        "
        The index for uniquely specifying NetworkInterface 
        to which IPP is set. 
        The value of index shall be the same value 
        with mltNetGeneralIndex (ifIndex).
        "
       ::= { mltIppVersionsSupportedEntry 1 }

   mltIppVersionIndex  OBJECT-TYPE
    SYNTAX     INTEGER
    ACCESS     read-only
    STATUS     optional
    DESCRIPTION
        "
        Index for uniquely showing 'ipp-version'.
        "
       ::= { mltIppVersionsSupportedEntry 2 }

   mltIppVersionType  OBJECT-TYPE
    SYNTAX     INTEGER{
                    ipp10(3),
                    ipp11(4)
                    }
    ACCESS     read-only
    STATUS     optional
    DESCRIPTION
        "
        'ipp-version' to support is shown
        "
       ::= { mltIppVersionsSupportedEntry 3 }


   mltIppOperationSupportedTable  OBJECT-TYPE
    SYNTAX    SEQUENCE OF MltIppOperationSupportedEntry
    ACCESS    not-accessible
    STATUS    optional
    DESCRIPTION
        "
        Table which has 'operation-supported' attribute.
        "
    ::= { mltNetIppPrtDescrAttribute 5 }

   mltIppOperationSupportedEntry OBJECT-TYPE
    SYNTAX    MltIppOperationSupportedEntry
    ACCESS    not-accessible
    STATUS    optional
    DESCRIPTION
        "
        "
    INDEX  { mltIppOperationIfIndex, mltIppOperationIndex }
    ::= { mltIppOperationSupportedTable 1 }

   MltIppOperationSupportedEntry ::= SEQUENCE {
        mltIppOperationIfIndex  INTEGER,
        mltIppOperationIndex    INTEGER,
        mltIppOperationType     INTEGER,
        mltIppOperationEnable   INTEGER
        }

   mltIppOperationIfIndex  OBJECT-TYPE
    SYNTAX     INTEGER
    ACCESS     read-only
    STATUS     optional
    DESCRIPTION
        "
        The index for uniquely specifying NetworkInterface 
        to which IPP is set. 
        The value of index shall be the same value 
        with mltNetGeneralIndex (ifIndex).
        "
       ::= { mltIppOperationSupportedEntry 1 }

   mltIppOperationIndex  OBJECT-TYPE
    SYNTAX     INTEGER
    ACCESS     read-only
    STATUS     optional
    DESCRIPTION
        "
        Index which shows 'operation' to support.
        "
       ::= { mltIppOperationSupportedEntry 2 }

   mltIppOperationType  OBJECT-TYPE
    SYNTAX     INTEGER{
                printJob(2),
                printURI(3),
                validateJob(4),
                createJob(5),
                sendDocument(6),
                sendURI(7),
                cancelJob(8),
                getJobAttributes(9),
                getJobs(10),
                getPrinterAttributes(11),
                holdJobs(12),
                releaseJob(13),
                restartJob(14),
                -- (15)  reserved for a future operation 
                pausePrinter(16),
                resumePrinter(17),
                purgeJobs(18)
                }
    ACCESS     read-only
    STATUS     optional
    DESCRIPTION
        "
        Type of 'operation' is shown
        "
       ::= { mltIppOperationSupportedEntry 3 }

   mltIppOperationEnable  OBJECT-TYPE
    SYNTAX     INTEGER{
                    enable(1),
                    disable(2)
                    }
    ACCESS     read-write
    STATUS     optional
    DESCRIPTION
        "
        This shows Opeartor's Enable/Disable.
        "
       ::= { mltIppOperationSupportedEntry 4 }


   mltIppCharSetSupportedTable  OBJECT-TYPE
    SYNTAX    SEQUENCE OF MltIppCharSetSupportedEntry
    ACCESS    not-accessible
    STATUS    optional
    DESCRIPTION
        "
        Table which shows 'charset-supported.'
        "
    ::= { mltNetIppPrtDescrAttribute 6 }

   mltIppCharSetSupportedEntry OBJECT-TYPE
    SYNTAX    MltIppCharSetSupportedEntry
    ACCESS    not-accessible
    STATUS    optional
    DESCRIPTION
        "
        "
    INDEX  { mltIppCharSetIfIndex, mltIppCharSetIndex }
    ::= { mltIppCharSetSupportedTable 1 }

   MltIppCharSetSupportedEntry ::= SEQUENCE {
        mltIppCharSetIfIndex    INTEGER,
        mltIppCharSetIndex      INTEGER,
        mltIppCharSetName       DisplayString,
        mltIppCharSetCode       INTEGER
        }

   mltIppCharSetIfIndex  OBJECT-TYPE
    SYNTAX     INTEGER
    ACCESS     read-only
    STATUS     optional
    DESCRIPTION
        "
        The index for uniquely specifying NetworkInterface 
        to which IPP is set. 
        The value of index shall be the same value 
        with mltNetGeneralIndex (ifIndex).
        "
       ::= { mltIppCharSetSupportedEntry 1 }

   mltIppCharSetIndex  OBJECT-TYPE
    SYNTAX     INTEGER
    ACCESS     read-only
    STATUS     optional
    DESCRIPTION
        "
        Index for uniquely showing 'charset'.
        "
       ::= { mltIppCharSetSupportedEntry 2 }

   mltIppCharSetName  OBJECT-TYPE
    SYNTAX     DisplayString(SIZE(0..127))
    ACCESS     read-only
    STATUS     optional
    DESCRIPTION
        "
        A parameter should follow regulation of IANA of the following.
        http://www.iana.org/assignments/character-set
        "
       ::= { mltIppCharSetSupportedEntry 3 }

   mltIppCharSetCode  OBJECT-TYPE
    SYNTAX     INTEGER
    ACCESS     read-only
    STATUS     optional
    DESCRIPTION
        "
        The code of 'charset' to support
        A parameter should follow regulation of IANA of the following.
        http://www.iana.org/assignments/character-set
        "
       ::= { mltIppCharSetSupportedEntry 4 }


   mltIppNaturalLanguageSupportedTable  OBJECT-TYPE
    SYNTAX    SEQUENCE OF MltIppNaturalLanguageSupportedEntry
    ACCESS    not-accessible
    STATUS    optional
    DESCRIPTION
        "
        Table which shows 'generated-natural-language-supported' attribute.
        "
    ::= { mltNetIppPrtDescrAttribute 7 }

   mltIppNaturalLanguageSupportedEntry OBJECT-TYPE
    SYNTAX    MltIppNaturalLanguageSupportedEntry
    ACCESS    not-accessible
    STATUS    optional
    DESCRIPTION
        "
        "
    INDEX  { mltIppNaturalLangIfIndex, mltIppNaturalLangIndex }
    ::= { mltIppNaturalLanguageSupportedTable 1 }

   MltIppNaturalLanguageSupportedEntry ::= SEQUENCE {
        mltIppNaturalLangIfIndex    INTEGER,
        mltIppNaturalLangIndex      INTEGER,
        mltIppNaturalLangName       DisplayString
        }

   mltIppNaturalLangIfIndex  OBJECT-TYPE
    SYNTAX     INTEGER
    ACCESS     read-only
    STATUS     optional
    DESCRIPTION
        "
        The index for uniquely specifying NetworkInterface 
        to which IPP is set. 
        The value of index shall be the same value 
        with mltNetGeneralIndex (ifIndex).
        "
       ::= { mltIppNaturalLanguageSupportedEntry 1 }

   mltIppNaturalLangIndex  OBJECT-TYPE
    SYNTAX     INTEGER
    ACCESS     read-only
    STATUS     optional
    DESCRIPTION
        "
        Index for uniquely showing 'natural-language'.
        "
       ::= { mltIppNaturalLanguageSupportedEntry 2 }

   mltIppNaturalLangName  OBJECT-TYPE
    SYNTAX     DisplayString(SIZE(0..127))
    ACCESS     read-only
    STATUS     optional
    DESCRIPTION
        "
        The name of 'natural-language' to support. 
        "
       ::= { mltIppNaturalLanguageSupportedEntry 3 }


   mltIppDocFormatSupportedTable  OBJECT-TYPE
    SYNTAX    SEQUENCE OF MltIppDocFormatSupportedEntry
    ACCESS    not-accessible
    STATUS    optional
    DESCRIPTION
        "
        Table which shows 'document-format-supported' attribute.
        "
    ::= { mltNetIppPrtDescrAttribute 8 }

   mltIppDocFormatSupportedEntry OBJECT-TYPE
    SYNTAX    MltIppDocFormatSupportedEntry
    ACCESS    not-accessible
    STATUS    optional
    DESCRIPTION
        "
        "
    INDEX  { mltIppDocFormatIfIndex, mltIppDocFormatIndex }
    ::= { mltIppDocFormatSupportedTable 1 }

   MltIppDocFormatSupportedEntry ::= SEQUENCE {
        mltIppDocFormatIfIndex  INTEGER,
        mltIppDocFormatIndex    INTEGER,
        mltIppDocFormatName     DisplayString
        }

   mltIppDocFormatIfIndex  OBJECT-TYPE
    SYNTAX     INTEGER
    ACCESS     read-only
    STATUS     optional
    DESCRIPTION
        "
        The index for uniquely specifying NetworkInterface 
        to which IPP is set. 
        The value of index shall be the same value 
        with mltNetGeneralIndex (ifIndex).
        "
       ::= { mltIppDocFormatSupportedEntry 1 }

   mltIppDocFormatIndex  OBJECT-TYPE
    SYNTAX     INTEGER
    ACCESS     read-only
    STATUS     optional
    DESCRIPTION
        "
        The index for uniquely showing 'document-format'.
        "
       ::= { mltIppDocFormatSupportedEntry 2 }

   mltIppDocFormatName  OBJECT-TYPE
    SYNTAX     DisplayString(SIZE(0..127))
    ACCESS     read-only
    STATUS     optional
    DESCRIPTION
        "
        The name of 'document-format' to support is shown
        "
       ::= { mltIppDocFormatSupportedEntry 3 }

   mltIppCompressionSupportedTable  OBJECT-TYPE
    SYNTAX    SEQUENCE OF MltIppCompressionSupportedEntry
    ACCESS    not-accessible
    STATUS    optional
    DESCRIPTION
        "
        Table which shows 'compression-supported.'
        "
    ::= { mltNetIppPrtDescrAttribute 10 }

   mltIppCompressionSupportedEntry OBJECT-TYPE
    SYNTAX    MltIppCompressionSupportedEntry
    ACCESS    not-accessible
    STATUS    optional
    DESCRIPTION
        "
        "
    INDEX  { mltIppCompressionIfIndex, mltIppCompressionIndex }
    ::= { mltIppCompressionSupportedTable 1 }

   MltIppCompressionSupportedEntry ::= SEQUENCE {
        mltIppCompressionIfIndex    INTEGER,
        mltIppCompressionIndex      INTEGER,
        mltIppCompressionType       INTEGER
        }

   mltIppCompressionIfIndex  OBJECT-TYPE
    SYNTAX     INTEGER
    ACCESS     read-only
    STATUS     optional
    DESCRIPTION
        "
        Index for uniquely specifying NetworkInterface 
        to which IPP is set. 
        The value of index shall be the same value with 
        mltNetGeneralIndex (ifIndex).
        "
       ::= { mltIppCompressionSupportedEntry 1 }

   mltIppCompressionIndex  OBJECT-TYPE
    SYNTAX     INTEGER
    ACCESS     read-only
    STATUS     optional
    DESCRIPTION
        "
        Index for uniquely showing 'compression'.
        "
       ::= { mltIppCompressionSupportedEntry 2 }

   mltIppCompressionType  OBJECT-TYPE
    SYNTAX     INTEGER{
                    none(3),
                    deflate(4),
                    gzip(5),
                    compress(6)
                    }
    ACCESS     read-only
    STATUS     optional
    DESCRIPTION
        "
        'compression' currently supported is shown.
        "
       ::= { mltIppCompressionSupportedEntry 3 }


-- mltIppJobTemplateAttribute Group  

   mltNetIppJobTemplateGeneralTable  OBJECT-TYPE
    SYNTAX    SEQUENCE OF MltNetIppJobTemplateGeneralEntry
    ACCESS    not-accessible
    STATUS    optional
    DESCRIPTION
        "
        The table for showing the general information about 
        Job Template Attribute of IPP. 
        "
    ::= { mltNetIppJobTemplateAttribute 1 }

   mltNetIppJobTemplateGeneralEntry  OBJECT-TYPE
    SYNTAX    MltNetIppJobTemplateGeneralEntry
    ACCESS    not-accessible
    STATUS    optional
    DESCRIPTION
        "
        "
    INDEX  { mltIppJobTemplateGeneralIfIndex }
    ::= { mltNetIppJobTemplateGeneralTable 1 }


    MltNetIppJobTemplateGeneralEntry ::= SEQUENCE {
        mltIppJobTemplateGeneralIfIndex     INTEGER,
        mltIppJobPriorityDefault            INTEGER,
        mltIppJobPrioritySupported          INTEGER,
        mltIppJobHoldUntilDefault           INTEGER,
        mltIppJobSheetsDefault              INTEGER,
        mltIppCopiesDefault                 INTEGER,
        mltIppCopiesMaxSupported            INTEGER,
        mltIppFinishingsDefault             INTEGER,
        mltIppPageRangesSupported           INTEGER,
        mltIppSidesDefault                  INTEGER,
        mltIppNumberUpDefault               INTEGER,
        mltIppOrientationRequestedDefault   INTEGER,
        mltIppMediaDefault                  INTEGER,
        mltIppPrinterResolutionDefault      INTEGER,
        mltIppPrintQualityDefault           INTEGER
        }

   mltIppJobTemplateGeneralIfIndex  OBJECT-TYPE
    SYNTAX     INTEGER
    ACCESS     read-only
    STATUS     optional
    DESCRIPTION
        "The index for uniquely specifying NetworkInterface to 
         which IPP is set. The value of index shall be the same
         value with mltNetGeneralIndex (ifIndex).
        "
       ::= { mltNetIppJobTemplateGeneralEntry 1 }
 
   mltIppJobPriorityDefault  OBJECT-TYPE
    SYNTAX     INTEGER
    ACCESS     read-only
    STATUS     optional
    DESCRIPTION
        "'job-priority-default' attribute is shown.
        "
       ::= { mltNetIppJobTemplateGeneralEntry 2 }

   mltIppJobPrioritySupported  OBJECT-TYPE
    SYNTAX     INTEGER
    ACCESS     read-only
    STATUS     optional
    DESCRIPTION
        "'job-priority-supported' attribute is shown.
        "
       ::= { mltNetIppJobTemplateGeneralEntry 3 }

   mltIppJobHoldUntilDefault  OBJECT-TYPE
    SYNTAX     INTEGER
    ACCESS     read-only
    STATUS     optional
    DESCRIPTION
        "'job-hold-until-default' attribute is shown.
        "
       ::= { mltNetIppJobTemplateGeneralEntry 4 }

   mltIppJobSheetsDefault  OBJECT-TYPE
    SYNTAX     INTEGER
    ACCESS     read-only
    STATUS     optional
    DESCRIPTION
        "'ipp-job-sheets-default' attribute is shown.
        "
       ::= { mltNetIppJobTemplateGeneralEntry 5 }

   mltIppCopiesDefault  OBJECT-TYPE
    SYNTAX     INTEGER
    ACCESS     read-write
    STATUS     optional
    DESCRIPTION
        "'copies-default' attribute is shown.
        "
       ::= { mltNetIppJobTemplateGeneralEntry 6 }

   mltIppCopiesMaxSupported  OBJECT-TYPE
    SYNTAX     INTEGER
    ACCESS     read-only
    STATUS     optional
    DESCRIPTION
        "'copies-supported' attribute is shown.
         Since MIN value is surely 1, only MAX is shown.
        "
       ::= { mltNetIppJobTemplateGeneralEntry 7 }

   mltIppFinishingsDefault  OBJECT-TYPE
    SYNTAX     INTEGER
    ACCESS     read-only
    STATUS     optional
    DESCRIPTION
        "'finishings-default' attribute is shown.
        "
       ::= { mltNetIppJobTemplateGeneralEntry 8 }

   mltIppPageRangesSupported  OBJECT-TYPE
    SYNTAX     INTEGER{
                    enable (1),
                    disable (2)
                    }
    ACCESS     read-only
    STATUS     optional
    DESCRIPTION
        "'page-ranges-supported' attribute is shown. 
        "
       ::= { mltNetIppJobTemplateGeneralEntry 9 }

   mltIppSidesDefault  OBJECT-TYPE
    SYNTAX     INTEGER
    ACCESS     read-write
    STATUS     optional
    DESCRIPTION
        "'sides-default' attribute is shown.
        "
       ::= { mltNetIppJobTemplateGeneralEntry 10 }

   mltIppNumberUpDefault  OBJECT-TYPE
    SYNTAX     INTEGER
    ACCESS     read-only
    STATUS     optional
    DESCRIPTION
        "'number-up-default' attribute is shown.
        "
       ::= { mltNetIppJobTemplateGeneralEntry 11 }

   mltIppOrientationRequestedDefault  OBJECT-TYPE
    SYNTAX     INTEGER
    ACCESS     read-write
    STATUS     optional
    DESCRIPTION
        "'orientation-requested-default' attribute is shown.
        "
       ::= { mltNetIppJobTemplateGeneralEntry 12 }

   mltIppMediaDefault  OBJECT-TYPE
    SYNTAX     INTEGER
    ACCESS     read-write
    STATUS     optional
    DESCRIPTION
        "'media-default' attribute is shown.
        "
       ::= { mltNetIppJobTemplateGeneralEntry 13 }

   mltIppPrinterResolutionDefault  OBJECT-TYPE
    SYNTAX     INTEGER
    ACCESS     read-write
    STATUS     optional
    DESCRIPTION
        "'printer-resolution-default' attribute is shown.
        "
       ::= { mltNetIppJobTemplateGeneralEntry 14 }

   mltIppPrintQualityDefault  OBJECT-TYPE
    SYNTAX     INTEGER
    ACCESS     read-write
    STATUS     optional
    DESCRIPTION
        "'print-quality-default' attribute is shown.
        "
       ::= { mltNetIppJobTemplateGeneralEntry 15 }

   mltIppJobHoldUntilSupportedTable  OBJECT-TYPE
    SYNTAX    SEQUENCE OF MltIppJobHoldUntilSupportedEntry
    ACCESS    not-accessible
    STATUS    optional
    DESCRIPTION
        "
        Table which shows 'job-hold-until-supported' attribute.
        "
    ::= { mltNetIppJobTemplateAttribute 2 }

   mltIppJobHoldUntilSupportedEntry  OBJECT-TYPE
    SYNTAX    MltIppJobHoldUntilSupportedEntry
    ACCESS    not-accessible
    STATUS    optional
    DESCRIPTION
        "
        "
    INDEX  { mltIppJobHoldUntilIfIndex, mltIppJobHoldUntilIndex }
    ::= { mltIppJobHoldUntilSupportedTable 1 }

   MltIppJobHoldUntilSupportedEntry ::= SEQUENCE {
    mltIppJobHoldUntilIfIndex   INTEGER,
    mltIppJobHoldUntilIndex     INTEGER,
    mltIppJobHoldUntilType      INTEGER
    }

   mltIppJobHoldUntilIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltIppJobHoldUntilSupportedEntry 1 }

   mltIppJobHoldUntilIndex  OBJECT-TYPE
    SYNTAX     INTEGER
    ACCESS     read-only
    STATUS     optional
    DESCRIPTION
        "Index for uniquely showing 'job-hold-until'.
        "
       ::= { mltIppJobHoldUntilSupportedEntry 2 }

   mltIppJobHoldUntilType  OBJECT-TYPE
    SYNTAX     INTEGER{
                    noHold (3),
                    indefinite (4),
                    dayTime (5),
                    evening (6),
                    night (7),
                    weekend (8),
                    secondShift (9),
                    thirdShift (10)
                }
    ACCESS     read-only
    STATUS     optional
    DESCRIPTION
        "Type of 'job-hold-until' to support. 
        "
       ::= { mltIppJobHoldUntilSupportedEntry 3 }


   mltIppJobSheetsSupportedTable  OBJECT-TYPE
    SYNTAX    SEQUENCE OF MltIppJobSheetsSupportedEntry
    ACCESS    not-accessible
    STATUS    optional
    DESCRIPTION
        "
        Table which shows 'ipp-job-sheets-supported'.
        "
    ::= { mltNetIppJobTemplateAttribute 3 }

   mltIppJobSheetsSupportedEntry  OBJECT-TYPE
    SYNTAX    MltIppJobSheetsSupportedEntry
    ACCESS    not-accessible
    STATUS    optional
    DESCRIPTION
        "
        "
    INDEX  { mltIppJobSheetsIfIndex, mltIppJobSheetsIndex }
    ::= { mltIppJobSheetsSupportedTable 1 }

  MltIppJobSheetsSupportedEntry ::= SEQUENCE {
    mltIppJobSheetsIfIndex  INTEGER,
    mltIppJobSheetsIndex    INTEGER,
    mltIppJobSheetsType     INTEGER
    }

   mltIppJobSheetsIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltIppJobSheetsSupportedEntry 1 }

   mltIppJobSheetsIndex  OBJECT-TYPE
    SYNTAX     INTEGER
    ACCESS     read-only
    STATUS     optional
    DESCRIPTION
        "Index for uniquely showing 'job-sheets'.
        "
       ::= { mltIppJobSheetsSupportedEntry 2 }

   mltIppJobSheetsType  OBJECT-TYPE
    SYNTAX     INTEGER{
                    none (3),
                    standard(4)
                    }
    ACCESS     read-only
    STATUS     optional
    DESCRIPTION
        "Type of 'job-sheets' to support is shown.
        "
       ::= { mltIppJobSheetsSupportedEntry 3 }


   mltIppFinishingsSupportedTable  OBJECT-TYPE
    SYNTAX    SEQUENCE OF MltIppFinishingsSupportedEntry
    ACCESS    not-accessible
    STATUS    optional
    DESCRIPTION
        "
        Table which shows 'finishings-supported'. 
        "
    ::= { mltNetIppJobTemplateAttribute 4 }

   mltIppFinishingsSupportedEntry  OBJECT-TYPE
    SYNTAX    MltIppFinishingsSupportedEntry
    ACCESS    not-accessible
    STATUS    optional
    DESCRIPTION
        "
        "
    INDEX  { mltIppFinishingsIfIndex, mltIppFinishingsIndex }
    ::= { mltIppFinishingsSupportedTable 1 }

   MltIppFinishingsSupportedEntry ::= SEQUENCE {
    mltIppFinishingsIfIndex INTEGER,
    mltIppFinishingsIndex   INTEGER,
    mltIppFinishingsType    INTEGER
    }

   mltIppFinishingsIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltIppFinishingsSupportedEntry 1 }

   mltIppFinishingsIndex  OBJECT-TYPE
    SYNTAX     INTEGER
    ACCESS     read-only
    STATUS     optional
    DESCRIPTION
        "Index for uniquely showing 'finishings'.
        "
       ::= { mltIppFinishingsSupportedEntry 2 }

   mltIppFinishingsType  OBJECT-TYPE
    SYNTAX     INTEGER{
                none (3),
                staple (4),
                punch (5),
                cover (6),
                bind (7),
                saddle-stitch (8),
                edge-stitch (9),
                            -- 10-19:reserved for future generic finishing values
                staple-top-left (20),
                staple-bottom-left (21),
                staple-top-right (22),
                staple-bottom-right (23),
                edge-stitch-left (24),
                edge-stitch-top (25),
                edge-stitch-right (26),
                edge-stitch-bottom (27),
                staple-dual-left (28),
                staple-dual-top (29),
                staple-dual-right (30),
                staple-dual-bottom (31)
                }
    ACCESS     read-only
    STATUS     optional
    DESCRIPTION
        "Type of 'finishings' to support. 
        "
       ::= { mltIppFinishingsSupportedEntry 3 }


   mltIppSidesSupportedTable  OBJECT-TYPE
    SYNTAX    SEQUENCE OF MltIppSidesSupportedEntry
    ACCESS    not-accessible
    STATUS    optional
    DESCRIPTION
        "
        Table which shows 'sides-supported' attribute. 
        "
    ::= { mltNetIppJobTemplateAttribute 5 }

   mltIppSidesSupportedEntry  OBJECT-TYPE
    SYNTAX    MltIppSidesSupportedEntry
    ACCESS    not-accessible
    STATUS    optional
    DESCRIPTION
        "
        "
    INDEX  { mltIppSidesIfIndex, mltIppSidesIndex }
    ::= { mltIppSidesSupportedTable 1 }

   MltIppSidesSupportedEntry ::= SEQUENCE {
    mltIppSidesIfIndex  INTEGER,
    mltIppSidesIndex    INTEGER,
    mltIppSidesType     INTEGER
    }

   mltIppSidesIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltIppSidesSupportedEntry 1 }

   mltIppSidesIndex  OBJECT-TYPE
    SYNTAX     INTEGER
    ACCESS     read-only
    STATUS     optional
    DESCRIPTION
        "Index for uniquely showing 'sides'.
        "
       ::= { mltIppSidesSupportedEntry 2 }

   mltIppSidesType  OBJECT-TYPE
    SYNTAX     INTEGER{
                one-sided (3),
                two-sided-long-edge (4),
                two-sided-short-edge (5)
                }
    ACCESS     read-only
    STATUS     optional
    DESCRIPTION
        "Type of 'sides' to support
        "
       ::= { mltIppSidesSupportedEntry 3 }


   mltIppNumberUpSupportedTable  OBJECT-TYPE
    SYNTAX    SEQUENCE OF MltIppNumberUpSupportedEntry
    ACCESS    not-accessible
    STATUS    optional
    DESCRIPTION
        "
        Table which shows 'number-up-supported'.
        "
    ::= { mltNetIppJobTemplateAttribute 6 }

   mltIppNumberUpSupportedEntry  OBJECT-TYPE
    SYNTAX    MltIppNumberUpSupportedEntry
    ACCESS    not-accessible
    STATUS    optional
    DESCRIPTION
        "
        "
    INDEX  { mltIppNumberUpIfIndex, mltIppNumberUpIndex }
    ::= { mltIppNumberUpSupportedTable 1 }

   MltIppNumberUpSupportedEntry ::= SEQUENCE {
    mltIppNumberUpIfIndex   INTEGER,
    mltIppNumberUpIndex     INTEGER,
    mltIppNumberUpType      INTEGER
    }

   mltIppNumberUpIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltIppNumberUpSupportedEntry 1 }

   mltIppNumberUpIndex  OBJECT-TYPE
    SYNTAX     INTEGER
    ACCESS     read-only
    STATUS     optional
    DESCRIPTION
        "Index for uniquely showing 'number-up'.
        "
       ::= { mltIppNumberUpSupportedEntry 2 }

   mltIppNumberUpType  OBJECT-TYPE
    SYNTAX     INTEGER{
                num1Up (1),
                num2Up (2),
                num4Up (3),
                num9Up (4),
                num16Up (5)
                }
    ACCESS     read-only
    STATUS     optional
    DESCRIPTION
        "The 'number-up' value to support is shown. 
        "
       ::= { mltIppNumberUpSupportedEntry 3 }


   mltIppOrientationRequestedSupportedTable  OBJECT-TYPE
    SYNTAX    SEQUENCE OF MltIppOrientationRequestedSupportedEntry
    ACCESS    not-accessible
    STATUS    optional
    DESCRIPTION
        "
        'orientation-requested-supported' attribute is shown.
        "
    ::= { mltNetIppJobTemplateAttribute 7 }

   mltIppOrientationRequestedSupportedEntry  OBJECT-TYPE
    SYNTAX    MltIppOrientationRequestedSupportedEntry
    ACCESS    not-accessible
    STATUS    optional
    DESCRIPTION
        "
        "
    INDEX  { mltIppOrientationRequestedIfIndex, mltIppOrientationRequestedIndex }
    ::= { mltIppOrientationRequestedSupportedTable 1 }

   MltIppOrientationRequestedSupportedEntry ::= SEQUENCE {
    mltIppOrientationRequestedIfIndex   INTEGER,
    mltIppOrientationRequestedIndex     INTEGER,
    mltIppOrientationRequestedType      INTEGER
    }

   mltIppOrientationRequestedIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltIppOrientationRequestedSupportedEntry 1 }

   mltIppOrientationRequestedIndex OBJECT-TYPE
    SYNTAX     INTEGER
    ACCESS     read-only
    STATUS     optional
    DESCRIPTION
        "Index for uniquely showing 'orientation-requested'.
        "
       ::= { mltIppOrientationRequestedSupportedEntry 2 }

   mltIppOrientationRequestedType OBJECT-TYPE
    SYNTAX     INTEGER{
                portrait (3),
                landscape (4),
                reverse-landscape (5),
                reverse-portrait (6)
                }
    ACCESS     read-only
    STATUS     optional
    DESCRIPTION
        "Type of 'orientation-requested' to support. 
        "
       ::= { mltIppOrientationRequestedSupportedEntry 3 }


   mltIppMediaSupportedTable  OBJECT-TYPE
    SYNTAX    SEQUENCE OF MltIppMediaSupportedEntry
    ACCESS    not-accessible
    STATUS    optional
    DESCRIPTION
        "
        Table which shows 'media-supported' attribute. 
        "
    ::= { mltNetIppJobTemplateAttribute 8 }

   mltIppMediaSupportedEntry  OBJECT-TYPE
    SYNTAX    MltIppMediaSupportedEntry
    ACCESS    not-accessible
    STATUS    optional
    DESCRIPTION
        "
        "
    INDEX  { mltIppMediaIfIndex, mltIppMediaIndex }
    ::= { mltIppMediaSupportedTable 1 }

   MltIppMediaSupportedEntry ::= SEQUENCE {
    mltIppMediaIfIndex      INTEGER,
    mltIppMediaIndex        INTEGER,
    mltIppMediaName         OCTET STRING,
    mltIppMediaType         OCTET STRING,
    mltIppMediaColor        OCTET STRING,
    mltIppMediaInputTray    OCTET STRING
    }

   mltIppMediaIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltIppMediaSupportedEntry 1 }

   mltIppMediaIndex  OBJECT-TYPE
    SYNTAX     INTEGER
    ACCESS     read-only
    STATUS     optional
    DESCRIPTION
        "Index for uniquely showing 'media'.
        "
       ::= { mltIppMediaSupportedEntry 2 }

   mltIppMediaName  OBJECT-TYPE
    SYNTAX     OCTET STRING (SIZE(0..63))
    ACCESS     read-only
    STATUS     optional
    DESCRIPTION
        "The name of 'media' currently supported.
         Refer to Bergman, R, 'Media Size Standardized Names',
         PWG Draft Standard D0.5, March 26, 2001.
        "
       ::= { mltIppMediaSupportedEntry 3 }

   mltIppMediaType  OBJECT-TYPE
    SYNTAX     OCTET STRING (SIZE(0..63))
    ACCESS     read-only
    STATUS     optional
    DESCRIPTION
        "mediatype of 'media' currently supported.
        "
       ::= { mltIppMediaSupportedEntry 4 }

   mltIppMediaColor  OBJECT-TYPE
    SYNTAX     OCTET STRING (SIZE(0..63))
    ACCESS     read-only
    STATUS     optional
    DESCRIPTION
        "The color of 'media' currently supported.
        "
       ::= { mltIppMediaSupportedEntry 5 }

   mltIppMediaInputTray  OBJECT-TYPE
    SYNTAX     OCTET STRING (SIZE(0..63))
    ACCESS     read-only
    STATUS     optional
    DESCRIPTION
        "Tray to which 'media' currently supported is set.
        "
       ::= { mltIppMediaSupportedEntry 6 }


   mltPrinterResolutionSupportedTable  OBJECT-TYPE
    SYNTAX    SEQUENCE OF MltPrinterResolutionSupportedEntry
    ACCESS    not-accessible
    STATUS    optional
    DESCRIPTION
        "
        Table which shows 'printer-resolution-supported'. 
        "
    ::= { mltNetIppJobTemplateAttribute 9 }

   mltPrinterResolutionSupportedEntry  OBJECT-TYPE
    SYNTAX    MltPrinterResolutionSupportedEntry
    ACCESS    not-accessible
    STATUS    optional
    DESCRIPTION
        "
        "
    INDEX  { mltPrinterResolutionIfIndex, mltPrinterResolutionIndex }
    ::= { mltPrinterResolutionSupportedTable 1 }

   MltPrinterResolutionSupportedEntry ::= SEQUENCE {
    mltPrinterResolutionIfIndex     INTEGER,
    mltPrinterResolutionIndex       INTEGER,
    mltPrinterResolutionFeedDir     Integer32,
    mltPrinterResolutionXFeedDir    Integer32,
    mltPrinterResolutionUnit        INTEGER
    }

   mltPrinterResolutionIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltPrinterResolutionSupportedEntry 1 }

   mltPrinterResolutionIndex  OBJECT-TYPE
    SYNTAX     INTEGER
    ACCESS     read-only
    STATUS     optional
    DESCRIPTION
        "Index for uniquely showing 'printer-resolution'.
        "
       ::= { mltPrinterResolutionSupportedEntry 2 }

   mltPrinterResolutionFeedDir  OBJECT-TYPE
    SYNTAX     Integer32
    ACCESS     read-only
    STATUS     optional
    DESCRIPTION
        "The value of Feed direction of 'printer-resolution' to support.
        "
       ::= { mltPrinterResolutionSupportedEntry 3 }

   mltPrinterResolutionXFeedDir  OBJECT-TYPE
    SYNTAX     Integer32
    ACCESS     read-only
    STATUS     optional
    DESCRIPTION
        "The value of XFeed direction of 'printer-resolution' to support.
        "
       ::= { mltPrinterResolutionSupportedEntry 4 }

   mltPrinterResolutionUnit  OBJECT-TYPE
    SYNTAX     INTEGER{
                other (1),
                tenThousandthsOfInches (3),
                micrometers (4)
                }
    ACCESS     read-only
    STATUS     optional
    DESCRIPTION
        "Unit of 'printer-resolution' to support . 
        "
       ::= { mltPrinterResolutionSupportedEntry 5 }


   mltPrintQualitySupportedTable  OBJECT-TYPE
    SYNTAX    SEQUENCE OF MltPrintQualitySupportedEntry
    ACCESS    not-accessible
    STATUS    optional
    DESCRIPTION
        "
        Table which shows 'print-quality-supported' attribute
        "
    ::= { mltNetIppJobTemplateAttribute 10 }

   mltPrintQualitySupportedEntry  OBJECT-TYPE
    SYNTAX    MltPrintQualitySupportedEntry
    ACCESS    not-accessible
    STATUS    optional
    DESCRIPTION
        "
        "
    INDEX  { mltPrintQualityIfIndex, mltPrintQualityIndex }
    ::= { mltPrintQualitySupportedTable 1 }

   MltPrintQualitySupportedEntry ::= SEQUENCE {
    mltPrintQualityIfIndex  INTEGER,
    mltPrintQualityIndex    INTEGER,
    mltPrintQualityType     INTEGER
    }

   mltPrintQualityIfIndex  OBJECT-TYPE
    SYNTAX     INTEGER
    ACCESS     read-only
    STATUS     optional
    DESCRIPTION
        "The index for uniquely specifying NetworkInterface to
         which IPP is set. The value of index shall be the same
         value with mltNetGeneralIndex (ifIndex).
        "
       ::= { mltPrintQualitySupportedEntry 1 }

   mltPrintQualityIndex  OBJECT-TYPE
    SYNTAX     INTEGER
    ACCESS     read-only
    STATUS     optional
    DESCRIPTION
        "Index for uniquely showing 'print-quality'.
        "
       ::= { mltPrintQualitySupportedEntry 2 }

   mltPrintQualityType  OBJECT-TYPE
    SYNTAX     INTEGER{
                draft (3),
                normal (4),
                high (5)
                }
    ACCESS     read-only
    STATUS     optional
    DESCRIPTION
        "Type of 'print-quality' to support. 
        "
       ::= { mltPrintQualitySupportedEntry 3 }

-- mltNetSlp Group

-- The information of SLP relation which NetworkInterface has is included.
-- The following items shall be defined. In the system without SLP function,
-- it is not necessary to implement this Group.


   mltNetSlpGeneralTable  OBJECT-TYPE
    SYNTAX    SEQUENCE OF MltNetSlpGeneralEntry
    ACCESS    not-accessible
    STATUS    mandatory
    DESCRIPTION
        "
        Table for showing the general information of SLP. 
        "
    ::= { mltNetSlp 1 }

   mltNetSlpGeneralEntry OBJECT-TYPE
    SYNTAX    MltNetSlpGeneralEntry
    ACCESS    not-accessible
    STATUS    mandatory
    DESCRIPTION
        "
        "
    INDEX  { mltNetSlpIfIndex }
    ::= { mltNetSlpGeneralTable 1 }

   MltNetSlpGeneralEntry ::= SEQUENCE {
    mltNetSlpIfIndex            INTEGER,
    mltNetSlpEnable             INTEGER,
    mltNetSlpPortNumber         INTEGER,
    mltNetSlpMTU                INTEGER,
    mltNetSlpTTL                INTEGER,
    mltNetSlpBroadcastSupport   INTEGER
         }

   mltNetSlpIfIndex  OBJECT-TYPE
    SYNTAX     INTEGER
    ACCESS     read-only
    STATUS     mandatory
    DESCRIPTION
        "The index for uniquely specifying NetworkInterface to which SLP is set.
         The value of index shall be the same value with mltNetGeneralIndex (ifIndex).
        "
       ::= { mltNetSlpGeneralEntry 1 }


   mltNetSlpEnable  OBJECT-TYPE
    SYNTAX     INTEGER{
                enable (1),
                disable (2)
                }
    ACCESS     read-write
    STATUS     mandatory
    DESCRIPTION
        "Enable/Disable of service of SLP is set up. 
        "
       ::= { mltNetSlpGeneralEntry 2 }

   mltNetSlpPortNumber  OBJECT-TYPE
    SYNTAX     INTEGER
    ACCESS     read-write
    STATUS     mandatory
    DESCRIPTION
        "Port number of SLP is shown. 
         Default is 427.
        "
       ::= { mltNetSlpGeneralEntry 3 }

   mltNetSlpMTU  OBJECT-TYPE
    SYNTAX     INTEGER
    ACCESS     read-write
    STATUS     mandatory
    DESCRIPTION
        "MTU value of LP gas is shown.
         Default shall be 1400.
        "
       ::= { mltNetSlpGeneralEntry 4 }

   mltNetSlpTTL  OBJECT-TYPE
    SYNTAX     INTEGER
    ACCESS     read-write
    STATUS     mandatory
    DESCRIPTION
        "TTL value of SLP is shown.
         Default shall be 255.
        "
       ::= { mltNetSlpGeneralEntry 5 }

   mltNetSlpBroadcastSupport  OBJECT-TYPE
    SYNTAX     INTEGER{
                broadcastOnly (1),
                multicastOnly (2),
                both (3)
                }
    ACCESS     read-write
    STATUS     mandatory
    DESCRIPTION
        "Support of multicasting and broadcasting is shown.
        "
       ::= { mltNetSlpGeneralEntry 6 }


   mltNetSlpConfigTable  OBJECT-TYPE
    SYNTAX    SEQUENCE OF MltNetSlpConfigEntry
    ACCESS    not-accessible
    STATUS    mandatory
    DESCRIPTION
        "
        The table for showing the setup information of SLP.  
        "
    ::= { mltNetSlp 2 }

   mltNetSlpConfigEntry OBJECT-TYPE
    SYNTAX    MltNetSlpConfigEntry
    ACCESS    not-accessible
    STATUS    mandatory
    DESCRIPTION
        "
        "
    INDEX  { mltNetSlpConfigIfIndex, mltNetSlpIndex }
    ::= { mltNetSlpConfigTable 1 }

   MltNetSlpConfigEntry ::= SEQUENCE {
    mltNetSlpConfigIfIndex  INTEGER,
    mltNetSlpIndex          INTEGER,
    mltNetSlpService        DisplayString,
    mltNetSlpScope          DisplayString,
    mltNetSlpLifetime       INTEGER
         }

   mltNetSlpConfigIfIndex  OBJECT-TYPE
    SYNTAX     INTEGER
    ACCESS     read-only
    STATUS     mandatory
    DESCRIPTION
        "The index for uniquely specifying NetworkInterface to which SLP is set.
         The value of index shall be the same value with mltNetGeneralIndex (ifIndex).
        "
       ::= { mltNetSlpConfigEntry 1 }

   mltNetSlpIndex  OBJECT-TYPE
    SYNTAX     INTEGER
    ACCESS     read-only
    STATUS     mandatory
    DESCRIPTION
        "Index for showing a specific entry.
         Default is 1.
        "
       ::= { mltNetSlpConfigEntry 2 }

   mltNetSlpService  OBJECT-TYPE
    SYNTAX     DisplayString(SIZE(0..31))
    ACCESS     read-only
    STATUS     mandatory
    DESCRIPTION
        "The character string which shows the service registered into DA.
         Example: 'service:printer:help'

        "
       ::= { mltNetSlpConfigEntry 3 }

   mltNetSlpScope  OBJECT-TYPE
    SYNTAX     DisplayString(SIZE(0..31))
    ACCESS     read-write
    STATUS     mandatory
    DESCRIPTION
        "The character string which shows the scope of SLP.
         Default character string is 'default'.
        "
       ::= { mltNetSlpConfigEntry 4 }

   mltNetSlpLifetime  OBJECT-TYPE
    SYNTAX     INTEGER
    ACCESS     read-write
    STATUS     mandatory
    DESCRIPTION
        "The value which shows LifeTime of a registration.
         A unit is second. Default is 10800 (3 hours).
        "
       ::= { mltNetSlpConfigEntry 5 }

-- mltNetNetWareGroup

-- NetWare related information which NetworkInterface has is included.
-- The following items shall be defined as NetWare relation.

-- Notes: About NDPS, since details are unknown at present,
-- it is not defined in this version. About NDPS,
-- a definition shall be added after making it clear that
-- how much items needs to be set up by a user.


   mltNetNwGeneralTable  OBJECT-TYPE
    SYNTAX    SEQUENCE OF MltNetNwGeneralEntry
    ACCESS    not-accessible
    STATUS    mandatory
    DESCRIPTION
        "Table with the basic information of NetWare relation
         which NetworkInterface has
        "
    ::= { mltNetNetWare 1 }


   mltNetNwGeneralEntry OBJECT-TYPE
    SYNTAX    MltNetNwGeneralEntry
    ACCESS    not-accessible
    STATUS    mandatory
    DESCRIPTION
        "
        "
    INDEX  { mltNetNwIfIndex }
    ::= { mltNetNwGeneralTable 1 }

   MltNetNwGeneralEntry ::= SEQUENCE {
    mltNetNwIfIndex         INTEGER,
    mltNetNwDefault         INTEGER,
    mltNetNwFrameTypeConfig INTEGER,
    mltNetNwPrintMode       INTEGER
         }

   mltNetNwIfIndex  OBJECT-TYPE
    SYNTAX     INTEGER
    ACCESS     read-only
    STATUS     mandatory
    DESCRIPTION
        "The index for uniquely showing NetworkInterface.
         The value of index shall be the same value with mltNetGeneralIndex (ifIndex).
        "
       ::= { mltNetNwGeneralEntry 1 }

   mltNetNwDefault  OBJECT-TYPE
    SYNTAX     INTEGER{
                notSupported (0),
                supported (1),
                resetToDefault (2)
                }
    ACCESS     read-only
    STATUS     mandatory
    DESCRIPTION
        "The command which restores all setup about NetWare to FactoryDefault. 

         When resetToDefault(2) is set, an agent side shall surely return Reply.
         In principle, when resetToDefault(2) is set, about the timing
         in which the setup returns to default depends on an implementation
         and it does not define in MIB.
        "
       ::= { mltNetNwGeneralEntry 2 }

   mltNetNwFrameTypeConfig  OBJECT-TYPE
    SYNTAX     INTEGER
    ACCESS     read-write
    STATUS     mandatory
    DESCRIPTION
        "A setup of FrameType used by NetWare (IPX). 
         It is set by using Bitmap of the following.
         1 (Auto-Sense) is recommended for the Default.
         Although Auto-Sense and other value do not exist together,
         about Binding two or more FrameTypes simultaneously,
         it is dependent on the implementation of a model.

              Bit  Value      FrameType
              ---- ----       ----------
               0     1        Reserved
               1     2        802.3
               2     4        EthernetII
               3     8        802.3-SNAP
               4    16        802.2 (4)
               5    32        Reserved
               6    64        802.5-TokenRing
               7   128        TokenRing-SNAP

        "
       ::= { mltNetNwGeneralEntry 3 }

   mltNetNwPrintMode  OBJECT-TYPE
    SYNTAX     INTEGER{
                pServerMode (1),
                nPrinterMode (2)
                }
    ACCESS     read-write
    STATUS     mandatory
    DESCRIPTION
        "The mode of NetworkInterface used by NetWare is set up.
        Default shall be pServerMode(1). When not supporting NPrinter,
         it shall be the implementation of RO.
        "
       ::= { mltNetNwGeneralEntry 4 }


   mltNetNwFrameTable  OBJECT-TYPE
    SYNTAX    SEQUENCE OF MltNetNwFrameEntry
    ACCESS    not-accessible
    STATUS    optional
    DESCRIPTION
        "The information of FrameType which is working in NetWare is shown.
        "
    ::= { mltNetNetWare 2 }

   mltNetNwFrameEntry OBJECT-TYPE
    SYNTAX    MltNetNwFrameEntry
    ACCESS    not-accessible
    STATUS    optional
    DESCRIPTION
        "
        "
    INDEX  { mltNetNwFrameIfIndex, mltNetNwFrameIndex }
    ::= { mltNetNwFrameTable 1 }

   MltNetNwFrameEntry ::= SEQUENCE {
    mltNetNwFrameIfIndex    INTEGER,
    mltNetNwFrameIndex      INTEGER,
    mltNetNwFrameType       INTEGER,
    mltNetNwNetworkNumber   OCTET STRING
         }

   mltNetNwFrameIfIndex  OBJECT-TYPE
    SYNTAX     INTEGER
    ACCESS     read-only
    STATUS     optional
    DESCRIPTION
        "The index for uniquely showing NetworkInterface.
         The value of index shall be the same value with mltNetGeneralIndex (ifIndex).
        "
       ::= { mltNetNwFrameEntry 1 }

   mltNetNwFrameIndex  OBJECT-TYPE
    SYNTAX     INTEGER
    ACCESS     read-only
    STATUS     optional
    DESCRIPTION
        "Index for showing FrameType which is operating by NetworkInterface.
        "
       ::= { mltNetNwFrameEntry 2 }

   mltNetNwFrameType  OBJECT-TYPE
    SYNTAX     INTEGER{
                ethernet8023 (1),
                ethernetII (2),
                ethernetSnap (3),
                ethernet8022 (4),
                tokenRing8025 (6),
                tokenRingSnap (7)
                }
    ACCESS     read-only
    STATUS     optional
    DESCRIPTION
        "FrameType is shown.
        "
       ::= { mltNetNwFrameEntry 3 }

   mltNetNwNetworkNumber  OBJECT-TYPE
    SYNTAX     OCTET STRING(SIZE(0..8))
    ACCESS     read-only
    STATUS     optional
    DESCRIPTION
        "Network number which each FrameType is using is displayed.
         The notation of a number is indicated by Hexadecimal numbers.
        "
       ::= { mltNetNwFrameEntry 4 }



   mltNetNwPserverTable  OBJECT-TYPE
    SYNTAX    SEQUENCE OF MltNetNwPserverEntry
    ACCESS    not-accessible
    STATUS    mandatory
    DESCRIPTION
        "The table for showing the setup of PrintServer. 
        "
    ::= { mltNetNetWare 3 }

   mltNetNwPserverEntry OBJECT-TYPE
    SYNTAX    MltNetNwPserverEntry
    ACCESS    not-accessible
    STATUS    mandatory
    DESCRIPTION
        "
        "
    INDEX  { mltNetNwPsIfIndex, mltNetNwPsIndex }
    ::= { mltNetNwPserverTable 1 }

   MltNetNwPserverEntry ::= SEQUENCE {
    mltNetNwPsIfIndex       INTEGER,
    mltNetNwPsIndex         INTEGER,
    mltNetNwPsName          DisplayString,
    mltNetNwPsPasswd        DisplayString,
    mltNetNwPsMode          INTEGER,
    mltNetNwPsPrefFServer   DisplayString,
    mltNetNwPsPrefTree      DisplayString,
    mltNetNwPsPrefContext   DisplayString,
    mltNetNwPsPollingRate   INTEGER
         }

   mltNetNwPsIfIndex  OBJECT-TYPE
    SYNTAX     INTEGER
    ACCESS     read-only
    STATUS     mandatory
    DESCRIPTION
        "The index for uniquely showing NetworkInterface.
         The value of index shall be the same value with mltNetGeneralIndex (ifIndex).
        "
       ::= { mltNetNwPserverEntry 1 }

   mltNetNwPsIndex  OBJECT-TYPE
    SYNTAX     INTEGER
    ACCESS     read-only
    STATUS     mandatory
    DESCRIPTION
        "Index for uniquely showing PrintServer.
         The number of indexes depends on an implementation.
        The number of indexes which can be implemented and
         the number of defaults depends on an implementation.
        "
       ::= { mltNetNwPserverEntry 2 }

   mltNetNwPsName  OBJECT-TYPE
    SYNTAX     DisplayString(SIZE(0..63))
    ACCESS     read-write
    STATUS     mandatory
    DESCRIPTION
        "The name of PrintServer.
         Default is dependent on an implementation.
        "
       ::= { mltNetNwPserverEntry 3 }

   mltNetNwPsPasswd  OBJECT-TYPE
    SYNTAX     DisplayString(SIZE(0..63))
    ACCESS     read-write
    STATUS     mandatory
    DESCRIPTION
        "Password of PrintServer.
         Default is Null.
         When it is gotten, applying scramble to value is not accepted.
         About security, support by the management tool side.
        "
       ::= { mltNetNwPserverEntry 4 }

   mltNetNwPsMode  OBJECT-TYPE
    SYNTAX     INTEGER{
                both (0),
                binderyMode (1),
                ndsMode (2)
                }
    ACCESS     read-write
    STATUS     mandatory
    DESCRIPTION
        "The mode in which PrintServer supports is shown.
        "
       ::= { mltNetNwPserverEntry 5 }

   mltNetNwPsPrefFServer  OBJECT-TYPE
    SYNTAX     DisplayString(SIZE(0..47))
    ACCESS     read-write
    STATUS     mandatory
    DESCRIPTION
        "Value of Preferred FileServer used in Bindery mode.
         It shall be NullString when set only to NDS mode.
         In the system which does not set up PreferredFileServer,
         implement '-' (hyphen) and shall be RO.
        "
       ::= { mltNetNwPserverEntry 6 }

   mltNetNwPsPrefTree  OBJECT-TYPE
    SYNTAX     DisplayString(SIZE(0..63))
    ACCESS     read-write
    STATUS     mandatory
    DESCRIPTION
        "Value of Preferred Tree used in NDS mode.
         It shall be NullString when set only to Bindery mode.
         In the system which does not set up PreferredTree,
         implement 'N/A' and shall be RO.
        "
       ::= { mltNetNwPserverEntry 7 }

   mltNetNwPsPrefContext  OBJECT-TYPE
    SYNTAX     DisplayString(SIZE(0..191))
    ACCESS     read-write
    STATUS     mandatory
    DESCRIPTION
        "Value of Preferred Context used in NDS mode.
         It shall be NullString when set only to Bindery mode.
         In the system which does not set up PreferredContext,
         implement 'N/A' and shall be RO.
        "
       ::= { mltNetNwPserverEntry 8 }

   mltNetNwPsPollingRate  OBJECT-TYPE
    SYNTAX     INTEGER
    ACCESS     read-write
    STATUS     mandatory
    DESCRIPTION
        "
        The interval at which PrinteServer scans Queue. Unit is second.
        Range which can be set up shall be 1 - 65535. Default is 1 (second).
        "
       ::= { mltNetNwPserverEntry 9 }



   mltNetNwQueueTable  OBJECT-TYPE
    SYNTAX    SEQUENCE OF MltNetNwQueueEntry
    ACCESS    not-accessible
    STATUS    mandatory
    DESCRIPTION
        "Table which shows the information of Queue which NetworkInterface has managed. 
        "
    ::= { mltNetNetWare 4 }

   mltNetNwQueueEntry OBJECT-TYPE
    SYNTAX    MltNetNwQueueEntry
    ACCESS    not-accessible
    STATUS    mandatory
    DESCRIPTION
        "
        "
    INDEX  { mltNetNwQueueIndex }
    ::= { mltNetNwQueueTable 1 }

   MltNetNwQueueEntry ::= SEQUENCE {
    mltNetNwQueueIndex      INTEGER,
    mltNetNwQueueName       DisplayString,
    mltNetNwQueueRefIfIndex INTEGER,
    mltNetNwQueueRefPsIndex INTEGER,
    mltNetNwQueueStatus     INTEGER
         }

   mltNetNwQueueIndex  OBJECT-TYPE
    SYNTAX     INTEGER
    ACCESS     read-only
    STATUS     mandatory
    DESCRIPTION
        "The index for uniquely showing Queue.
        "
       ::= { mltNetNwQueueEntry 1 }

   mltNetNwQueueName  OBJECT-TYPE
    SYNTAX     DisplayString(SIZE(0..63))
    ACCESS     read-only
    STATUS     mandatory
    DESCRIPTION
        "The name of Queue.
        "
       ::= { mltNetNwQueueEntry 2 }

   mltNetNwQueueRefIfIndex  OBJECT-TYPE
    SYNTAX     INTEGER
    ACCESS     read-only
    STATUS     mandatory
    DESCRIPTION
        "NetworkInterface which is managing Queue is shown.
         Use the value of mltNetNwPsIfIndex.
        "
       ::= { mltNetNwQueueEntry 3 }

   mltNetNwQueueRefPsIndex  OBJECT-TYPE
    SYNTAX     INTEGER
    ACCESS     read-only
    STATUS     mandatory
    DESCRIPTION
        "PrintServer which is managing Queue is shown.
         Use the value of mltNetNwPsIndex.
        "
       ::= { mltNetNwQueueEntry 4 }

   mltNetNwQueueStatus  OBJECT-TYPE
    SYNTAX     INTEGER{
                unknown (0),
                available(1),
                allocated (2),
                inUse (3)
                }
    ACCESS     read-only
    STATUS     mandatory
    DESCRIPTION
        "The state of Queue is shown. 
        "
       ::= { mltNetNwQueueEntry 5 }



   mltNetNwNPrinterTable  OBJECT-TYPE
    SYNTAX    SEQUENCE OF MltNetNwNPrinterEntry
    ACCESS    not-accessible
    STATUS    mandatory
    DESCRIPTION
        "Table which shows the information of NPrinter
         which NetworkInterface is managing. 
         In the system without Nprinter function,
         it is not necessary to implement this table.
        "
    ::= { mltNetNetWare 5 }

   mltNetNwNPrinterEntry OBJECT-TYPE
    SYNTAX    MltNetNwNPrinterEntry
    ACCESS    not-accessible
    STATUS    mandatory
    DESCRIPTION
        "
        "
    INDEX  { mltNetNwNPrinterIfIndex, mltNetNwNPrinterIndex }
    ::= { mltNetNwNPrinterTable 1 }

   MltNetNwNPrinterEntry ::= SEQUENCE {
    mltNetNwNPrinterIfIndex INTEGER,
    mltNetNwNPrinterIndex   INTEGER,
    mltNetNwNPrinterName    DisplayString,
    mltNetNwNPrinterNumber  INTEGER
         }

   mltNetNwNPrinterIfIndex  OBJECT-TYPE
    SYNTAX     INTEGER
    ACCESS     read-only
    STATUS     mandatory
    DESCRIPTION
        "The index for uniquely showing NetworkInterface.
         The value of index shall be the same value with mltNetGeneralIndex (ifIndex).
        "
       ::= { mltNetNwNPrinterEntry 1 }

   mltNetNwNPrinterIndex  OBJECT-TYPE
    SYNTAX     INTEGER
    ACCESS     read-only
    STATUS     mandatory
    DESCRIPTION
        "Index for uniquely showing Nprinter.
        "
       ::= { mltNetNwNPrinterEntry 2 }

   mltNetNwNPrinterName  OBJECT-TYPE
    SYNTAX     DisplayString(SIZE(0..63))
    ACCESS     read-write
    STATUS     mandatory
    DESCRIPTION
        "The name of Nprinter.
        "
       ::= { mltNetNwNPrinterEntry 3 }

   mltNetNwNPrinterNumber  OBJECT-TYPE
    SYNTAX     INTEGER
    ACCESS     read-write
    STATUS     mandatory
    DESCRIPTION
        "Printer number of NPrinter. Default shall be 1.
        "
       ::= { mltNetNwNPrinterEntry 4 }



-- mltNetAppleTalk Group

-- AppleTalk related information which NetworkInterface has is included.


   mltNetAppleTalkGeneralTable  OBJECT-TYPE
    SYNTAX    SEQUENCE OF MltNetAppleTalkGeneralEntry
    ACCESS    not-accessible
    STATUS    mandatory
    DESCRIPTION
        "Table with the basic information of AppleTalk relation
         which NetworkInterface has. 
        "
    ::= { mltNetAppleTalk 1 }

   mltNetAppleTalkGeneralEntry OBJECT-TYPE
    SYNTAX    MltNetAppleTalkGeneralEntry
    ACCESS    not-accessible
    STATUS    mandatory
    DESCRIPTION
        "
        "
    INDEX  { mltNetAtIfIndex }
    ::= { mltNetAppleTalkGeneralTable 1 }

   MltNetAppleTalkGeneralEntry ::= SEQUENCE {
    mltNetAtIfIndex     INTEGER,
    mltNetAtDefault     INTEGER,
    mltNetAtNetNumber   INTEGER,
    mltNetAtNodeNumber  INTEGER,
    mltNetAtDesiredZone DisplayString,
    mltNetAtCurrentZone DisplayString
         }


   mltNetAtIfIndex  OBJECT-TYPE
    SYNTAX     INTEGER
    ACCESS     read-only
    STATUS     mandatory
    DESCRIPTION
        "The index for uniquely showing NetworkInterface.
         The value of index shall be the same value with mltNetGeneralIndex (ifIndex).
        "
       ::= { mltNetAppleTalkGeneralEntry 1 }

   mltNetAtDefault  OBJECT-TYPE
    SYNTAX     INTEGER{
                notSupported (0),
                supported (1),
                resetToDefault (2)
                }
    ACCESS     read-write
    STATUS     mandatory
    DESCRIPTION
        "The command which restores all setup about AppleTalk to FactoryDefault.

         When resetToDefault(2) is set, an agent side shall surely return Reply.
         In principle, when resetToDefault(2) is set, about the timing
         in which the setup returns to default depends on an implementation
         and it does not define in MIB.
        "
       ::= { mltNetAppleTalkGeneralEntry 2 }

   mltNetAtNetNumber  OBJECT-TYPE
    SYNTAX     INTEGER
    ACCESS     read-only
    STATUS     mandatory
    DESCRIPTION
        "NetworkNumber in Network of AppleTalk.
         Display the value acquired at the time of Apple Talk starting.
         When it is unknown, shall be -2 (unknown).
        "
       ::= { mltNetAppleTalkGeneralEntry 3 }

   mltNetAtNodeNumber  OBJECT-TYPE
    SYNTAX     INTEGER
    ACCESS     read-only
    STATUS     mandatory
    DESCRIPTION
        "Node Number in Network of AppleTalk.
         Display the value acquired at the time of Apple Talk starting.
         When it is unknown, shall be -2 (unknown).
        "
       ::= { mltNetAppleTalkGeneralEntry 4 }

   mltNetAtDesiredZone  OBJECT-TYPE
    SYNTAX     DisplayString(SIZE(0..31))
    ACCESS     read-write
    STATUS     mandatory
    DESCRIPTION
        "Setting value of Zone name in Apple Talk.
         Default shall be '*'.
        "
       ::= { mltNetAppleTalkGeneralEntry 5 }

   mltNetAtCurrentZone  OBJECT-TYPE
    SYNTAX     DisplayString(SIZE(0..31))
    ACCESS     read-only
    STATUS     mandatory
    DESCRIPTION
        "Zone name to which device is operating.
         In environment of operation, it may differ from the above-mentioned value.
        "
       ::= { mltNetAppleTalkGeneralEntry 6 }


   mltNetAtPrinterTable  OBJECT-TYPE
    SYNTAX    SEQUENCE OF MltNetAtPrinterEntry
    ACCESS    not-accessible
    STATUS    mandatory
    DESCRIPTION
        "The table for showing the setup of AppleTalkPrinter. 
        "
    ::= { mltNetAppleTalk 2 }

   mltNetAtPrinterEntry OBJECT-TYPE
    SYNTAX    MltNetAtPrinterEntry
    ACCESS    not-accessible
    STATUS    mandatory
    DESCRIPTION
        "
        "
    INDEX  { mltNetAtPrinterIfIndex, mltNetAtPrinterIndex }
    ::= { mltNetAtPrinterTable 1 }

   MltNetAtPrinterEntry ::= SEQUENCE {
    mltNetAtPrinterIfIndex  INTEGER,
    mltNetAtPrinterIndex    INTEGER,
    mltNetAtPrinterName     DisplayString,
    mltNetAtPrinterType     DisplayString
         }

   mltNetAtPrinterIfIndex  OBJECT-TYPE
    SYNTAX     INTEGER
    ACCESS     read-only
    STATUS     mandatory
    DESCRIPTION
        "The index for uniquely showing NetworkInterface.
         The value of index shall be the same value with mltNetGeneralIndex (ifIndex).
        "
       ::= { mltNetAtPrinterEntry 1 }

   mltNetAtPrinterIndex OBJECT-TYPE
    SYNTAX     INTEGER
    ACCESS     read-only
    STATUS     mandatory
    DESCRIPTION
        "The index for uniquely showing AppleTalkPrinter.
         The number of indexed depends on an implementation.
        "
       ::= { mltNetAtPrinterEntry 2 }

   mltNetAtPrinterName OBJECT-TYPE
    SYNTAX     DisplayString(SIZE(0..32))
    ACCESS     read-write
    STATUS     mandatory
    DESCRIPTION
        "The name of AppleTalkPrinter.
         When performing the operation, the name in an actual
         operation environment should be shown.
        "
       ::= { mltNetAtPrinterEntry 3 }

   mltNetAtPrinterType OBJECT-TYPE
    SYNTAX     DisplayString(SIZE(0..31))
    ACCESS     read-only
    STATUS     mandatory
    DESCRIPTION
        "Type of AppleTalk Printer. Default is 'LaserWriter'.
        "
       ::= { mltNetAtPrinterEntry 4 }


-- mltNetSmb Group

-- SMB related information which NetworkInterface has is included.

   mltNetSmbGeneralTable  OBJECT-TYPE
    SYNTAX    SEQUENCE OF MltNetSmbGeneralEntry
    ACCESS    not-accessible
    STATUS    mandatory
    DESCRIPTION
        "The table with the basic information of SMB relation
         which NetworkInterface has. 
        "
    ::= { mltNetSmb 1 }

   mltNetSmbGeneralEntry OBJECT-TYPE
    SYNTAX    MltNetSmbGeneralEntry
    ACCESS    not-accessible
    STATUS    mandatory
    DESCRIPTION
        "
        "
    INDEX  { mltNetSmbIfIndex }
    ::= { mltNetSmbGeneralTable 1 }

   MltNetSmbGeneralEntry ::= SEQUENCE {
    mltNetSmbIfIndex                INTEGER,
    mltNetSmbDefault                INTEGER,
    mltNetSmbWorkGroupName          DisplayString,
    mltNetSmbHostName               DisplayString,
    mltNetSmbWinsSupport            INTEGER,
    mltNetSmbWinsPrimaryServer      IpAddress,
    mltNetSmbWinsSecondaryServer    IpAddress
         }

   mltNetSmbIfIndex  OBJECT-TYPE
    SYNTAX     INTEGER
    ACCESS     read-only
    STATUS     mandatory
    DESCRIPTION
        "The index for uniquely showing NetworkInterface.
         The value of index shall be the same value with mltNetGeneralIndex (ifIndex).
        "
       ::= { mltNetSmbGeneralEntry 1 }

   mltNetSmbDefault  OBJECT-TYPE
    SYNTAX     INTEGER{
                notSupported (0),
                supported (1),
                resetToDefault (2)
                }
    ACCESS     read-write
    STATUS     mandatory
    DESCRIPTION
        "The command which restores all setup about SMB to FactoryDefault. 

         When resetToDefault(2) is set, an agent side shall surely return Reply.
         In principle, when resetToDefault(2) is set, about the timing
         in which the setup returns to default depends on an implementation
         and it does not define in MIB.
        "
       ::= { mltNetSmbGeneralEntry 2 }

   mltNetSmbWorkGroupName  OBJECT-TYPE
    SYNTAX     DisplayString(SIZE(0..31))
    ACCESS     read-write
    STATUS     mandatory
    DESCRIPTION
        "WorkGroup name in Windows Network. Default shall be 'WORKGROUP'.
         Only the implementation of capital letters is accepted about this item.
        "
       ::= { mltNetSmbGeneralEntry 3 }

   mltNetSmbHostName  OBJECT-TYPE
    SYNTAX     DisplayString(SIZE(0..31))
    ACCESS     read-write
    STATUS     mandatory
    DESCRIPTION
        "Host name in Windows Network. Default is dependent on an implementation.
         Only the implementation of capital letters is accepted about this item
        "
       ::= { mltNetSmbGeneralEntry 4 }

   mltNetSmbWinsSupport  OBJECT-TYPE
    SYNTAX     INTEGER{
                notSupported (0),
                enable (1),
                disable (2)
                }
    ACCESS     read-only
    STATUS     mandatory
    DESCRIPTION
        "Sets up the availability of use of WINS.
         Default is disable(2).
        "
       ::= { mltNetSmbGeneralEntry 5 }

   mltNetSmbWinsPrimaryServer  OBJECT-TYPE
    SYNTAX     IpAddress
    ACCESS     read-only
    STATUS     mandatory
    DESCRIPTION
        "Sets up PrimaryServer of Wins. Default is 0.0.0.0
        "
       ::= { mltNetSmbGeneralEntry 6 }

   mltNetSmbWinsSecondaryServer  OBJECT-TYPE
    SYNTAX     IpAddress
    ACCESS     read-only
    STATUS     mandatory
    DESCRIPTION
        "Sets up Secondary Server of Wins. Default is 0.0.0.0.
        "
       ::= { mltNetSmbGeneralEntry 7 }



   mltNetSmbPrinterTable  OBJECT-TYPE
    SYNTAX    SEQUENCE OF MltNetSmbPrinterEntry
    ACCESS    not-accessible
    STATUS    mandatory
    DESCRIPTION
        "The table which has the information of Printer relation in SMB. 
        "
    ::= { mltNetSmb 2 }


   mltNetSmbPrinterEntry OBJECT-TYPE
    SYNTAX    MltNetSmbPrinterEntry
    ACCESS    not-accessible
    STATUS    mandatory
    DESCRIPTION
        "
        "
    INDEX  { mltNetSmbPrinterIfIndex, mltNetSmbPrinterIndex }
    ::= { mltNetSmbPrinterTable 1 }

   MltNetSmbPrinterEntry ::= SEQUENCE {
    mltNetSmbPrinterIfIndex INTEGER,
    mltNetSmbPrinterIndex   INTEGER,
    mltNetSmbPrinterName    DisplayString,
    mltNetSmbPrinterDescr   DisplayString
         }


   mltNetSmbPrinterIfIndex  OBJECT-TYPE
    SYNTAX     INTEGER
    ACCESS     read-only
    STATUS     mandatory
    DESCRIPTION
        "The index for uniquely showing NetworkInterface.
         The value of index shall be the same value with mltNetGeneralIndex (ifIndex).
        "
       ::= { mltNetSmbPrinterEntry 1 }

   mltNetSmbPrinterIndex OBJECT-TYPE
    SYNTAX     INTEGER
    ACCESS     read-only
    STATUS     mandatory
    DESCRIPTION
        "Index for uniquely showing Printer in SMB.
         The number of indexes depends on an implementation.
        "
       ::= { mltNetSmbPrinterEntry 2 }

   mltNetSmbPrinterName OBJECT-TYPE
    SYNTAX     DisplayString(SIZE(0..31))
    ACCESS     read-write
    STATUS     mandatory
    DESCRIPTION
        "Printer name in SMB. Default is dependent on the implementation of a model.
         About the availability of Printer name change shall also be dependent on
         an implementation.
        "
       ::= { mltNetSmbPrinterEntry 3 }

   mltNetSmbPrinterDescr OBJECT-TYPE
    SYNTAX     DisplayString(SIZE(0..31))
    ACCESS     read-only
    STATUS     mandatory
    DESCRIPTION
        "Explanation of Printer.
         About the written contents is dependent on the implementation of
         a model; however, implementation of NullString is not accepted.
         At least input the character string which is same as Default Printer name.
        "
       ::= { mltNetSmbPrinterEntry 4 }

--
-- Private Job Management MIB
--


 mltJmMibVersion  OBJECT-TYPE
    SYNTAX    DisplayString (SIZE(0..7))
    ACCESS    read-only
    STATUS    mandatory
    DESCRIPTION
        "The standardization version of MIB implemented in JobManagement relation.
         This indicates the version of the Private Job Management MIB that
         is implemented. 
         There are some mib objects that indicate the Mib Version. 
         (mltSysMibVersion, mltPrtMibVersion, mltScnMibVersion, mltNetMiIbVersion,
         mltJmMibVersion) But, the each mib version should be same version. 
         Especially, the each major versions must be same.

         The version information of Standard MIB specification.
         General form is AA.BC.
         AA is indicating major revision, and B and C is 
         minor revision. Decimal point is ASCII-coded period.
        "
    ::= { mltJobManagement 1 }

-- If device cannot support all mandatory items of  private 
-- Job Management MIB, this version code should not be implemented.


   mltJmGeneral      OBJECT IDENTIFIER ::= { mltJobManagement 2 }
   mltJmJob          OBJECT IDENTIFIER ::= { mltJobManagement 3 }
   mltJmReport       OBJECT IDENTIFIER ::= { mltJobManagement 4 }


--  mltJmGeneral Group

   mltJmGeneralTable  OBJECT-TYPE
    SYNTAX    SEQUENCE OF MltJmGeneralEntry
    ACCESS    not-accessible
    STATUS    mandatory
    DESCRIPTION
        "
         This table indicates the general information about
         Job Management.
         This table contains the number of active jobs, oldest/newest
         jobs, the number of preservation of a history, and so on. 
        "
    ::= { mltJmGeneral 1 }

   mltJmGeneralEntry OBJECT-TYPE
    SYNTAX    MltJmGeneralEntry
    ACCESS    not-accessible
    STATUS    mandatory
    DESCRIPTION
        "
        "
    INDEX  { mltJmGeneralJobSetIndex }
    ::= { mltJmGeneralTable 1 }

    MltJmGeneralEntry ::= SEQUENCE {
        mltJmGeneralJobSetIndex           INTEGER,
        mltJmGeneralNumberOfActiveJobs    INTEGER,
        mltJmGeneralOldestActiveJobIndex  INTEGER,
        mltJmGeneralNewestActiveJobIndex  INTEGER,
        mltJmGeneralJobPersistence        INTEGER,
        mltJmGeneralJobSetType            INTEGER
    }

   mltJmGeneralJobSetIndex  OBJECT-TYPE
       SYNTAX     INTEGER
       ACCESS     read-only
       STATUS     mandatory
       DESCRIPTION
           "
            A unique value for each job set in this MIB. 
            JobSet shows the system of the serial number used for Job management.

            In managing a serial number to 1 by all the functions of 
            a device according to 'Job management standard specifications',
            it sets the number of JobSets to 1.
            In managing a serial number for every functional classification,
            only the number of functional classifications shall have JobSet.
           "
       ::= { mltJmGeneralEntry 1 }

   mltJmGeneralNumberOfActiveJobs  OBJECT-TYPE
       SYNTAX     INTEGER
       ACCESS     read-only
       STATUS     mandatory
       DESCRIPTION
           "
            The current number of 'active' jobs in the mltJmJobTable.
            when the device has no active jobs, this value should be 0.

            The device that cannot support to count active jobs
            should implement (-2) as fixed value. 
           "
       ::= { mltJmGeneralEntry 2 }

   mltJmGeneralOldestActiveJobIndex  OBJECT-TYPE
       SYNTAX     INTEGER
       ACCESS     read-only
       STATUS     mandatory
       DESCRIPTION
           "
            The mltJmJobIndex of the oldest job that is still in 
            one of the 'active' states.
            In other words, the index of the 'active' job that has 
            been in the job tables the longest.

            If there are no active jobs, this value should be 0.

            The device that cannot support to count active jobs
            should implement (-2) as fixed value. 
           "
       ::= { mltJmGeneralEntry 3 }

   mltJmGeneralNewestActiveJobIndex  OBJECT-TYPE
       SYNTAX     INTEGER
       ACCESS     read-only
       STATUS     mandatory
       DESCRIPTION
           "
            The mltJmJobIndex of the newest job that is in one of the
            'active' states.
            In other words, the index of the 'active' job that has been
            most recently added to the job tables.

            If there are no active jobs, this value should be 0.

            The device that cannot support to count active jobs
            should implement (-2) as fixed value. 
           "
       ::= { mltJmGeneralEntry 4 }

   mltJmGeneralJobPersistence  OBJECT-TYPE
       SYNTAX     INTEGER
       ACCESS     read-only
       STATUS     mandatory
       DESCRIPTION
           "The number holding the information (Index) on Job
            is specified after an end of Job.
            About the number which should hold the history information
            on Job, it shall be dependent on implementation of a model.

            If a device can not support this, '-2'(Not Support) should
            be implemented.
           "
       ::= { mltJmGeneralEntry 5 }

   mltJmGeneralJobSetType  OBJECT-TYPE
       SYNTAX    INTEGER {
                 mfpAll (0),
                 copy (1),
                 print (2),
                 receiveJob (3),
                 sendJob (4),
                 faxReceive (5),
                 faxSend (6),
                 other (7)
                 }
       ACCESS     read-only
       STATUS     mandatory
       DESCRIPTION
           "
            The type of JobSet.
           "
       ::= { mltJmGeneralEntry 6 }


--  mltJmJob Group

-- This group shows the detailed information of jobs.

   mltJmJobTable  OBJECT-TYPE
       SYNTAX    SEQUENCE OF MltJmJobEntry
       ACCESS    not-accessible
       STATUS    mandatory
       DESCRIPTION
           "
            The table indicates the detailed information of jobs.
           "
       ::= { mltJmJob 1 }

   mltJmJobEntry OBJECT-TYPE
    SYNTAX    MltJmJobEntry
    ACCESS    not-accessible
    STATUS    mandatory
    DESCRIPTION
        "
        "
    INDEX  { mltJmJobJobSetIndex, mltJmJobIndex }
    ::= { mltJmJobTable 1 }

    MltJmJobEntry ::= SEQUENCE {
       mltJmJobJobSetIndex    INTEGER,
       mltJmJobIndex          INTEGER,
       mltJmJobFunction       INTEGER,
       mltJmJobStatus         INTEGER,
       mltJmJobReceivedTime   DateAndTime,
       mltJmJobCompleteTime   DateAndTime,
       mltJmJobPriority       INTEGER,
       mltJmJobDivNumber      INTEGER,
       mltJmJobOwner          DisplayString,
       mltJmJobType           INTEGER,
       mltJmJobName           DisplayString,
       mltJmJobDocPageNumbers    Integer32,
       mltJmJobDocCopyNumbers    Integer32,
       mltJmJobPageSize       INTEGER,
       mltJmJobDestination    DisplayString,
       mltJmJobDataSize       Integer32,
       mltJmJobColorMode      INTEGER,
       mltJmJobFormat         INTEGER,
       mltJmJobXResolution    INTEGER,
       mltJmJobYResolution    INTEGER,
       mltJmJobDuplex         INTEGER,
       mltJmJobOutputPages    Integer32,
       mltJmJobOutputSheets   Integer32,
       mltJmJobMediaType      INTEGER
       }


   mltJmJobJobSetIndex  OBJECT-TYPE
    SYNTAX    INTEGER
    ACCESS    read-only
    STATUS    mandatory
    DESCRIPTION
        "
        A unique value for each job set in this MIB. 
        JobSet shows the system of the serial number used for Job management.

        This index is the same as mltJmGeneralJobSetIndex.
        "
    ::= { mltJmJobEntry 1 }

   mltJmJobIndex  OBJECT-TYPE
    SYNTAX    INTEGER(1..65535)
    ACCESS    read-only
    STATUS    mandatory
    DESCRIPTION
        "
        The sequential, monotonously increasing identifier index for
        the job generated by the device when that device accepted the job. [

        This Index shall hold also in power supply On./Off.
        After attainment is automatically re-started from 1 to maximum.
        "
    ::= { mltJmJobEntry 2 }

   mltJmJobFunction  OBJECT-TYPE
    SYNTAX    INTEGER {
                 unknown (0),
                 copy (1),
                 print (2),
                 receiveJob (3),
                 sendJob (4),
                 faxReceive (5),
                 faxSend (6),
                 other (7)
              }
    ACCESS    read-only
    STATUS    mandatory
    DESCRIPTION
        "
        This value indicates the function of job sender.

        receiveJob(3) may include FAX and iFAX jobs.
        "
    ::= { mltJmJobEntry 3 }


   mltJmJobStatus  OBJECT-TYPE
    SYNTAX    INTEGER {
                unknown (0),
                other (1),
                cancelRequest (2),
                puaseRequest (3),
                restartRequest (4),

                pending (10),
                pendingHeld (11),
                pendingPaused (12),

                processing (20),
                sending (21),
                receiving (22),
                printing (23),
                scanning (24),
                processingStopped (25),

                completed (30),
                caution (31),
                aborted (32),
                canceled (33)
              }
    ACCESS    read-write
    STATUS    mandatory
    DESCRIPTION
        "
        This value indicates the status of job.
        "
    ::= { mltJmJobEntry 4 }

   mltJmJobReceivedTime  OBJECT-TYPE
    SYNTAX     DateAndTime
    ACCESS     read-only
    STATUS     mandatory
    DESCRIPTION
        "
        Registration time of Job.
        About TimeZone, it is not indispensable.

        When you cannot perform acquisition of time information, 
        be referred to as Null (Zero-Length).
        "
    ::= { mltJmJobEntry 6 }

   mltJmJobCompleteTime  OBJECT-TYPE
    SYNTAX     DateAndTime
    ACCESS     read-only
    STATUS     mandatory
    DESCRIPTION
        "Completion time of Job.
        About TimeZone, it is not indispensable.

        When you await and completion time cannot be 
        written by Job etc., be referred to as Null (Zero-Length).
        "
    ::= { mltJmJobEntry 7 }


   mltJmJobPriority  OBJECT-TYPE
    SYNTAX    INTEGER {
                 notSupported (0),
                 lowestPriority (1),
                 lowPriority (2),
                 normalPriority (3),
                 highPriority (4),
                 highestPriority (5)
              }
    ACCESS    read-write
    STATUS    mandatory
    DESCRIPTION
        "
        It is used when controlling the priority of Job.
        
        When device cannot support to  change of a priority,
        this value should be notSupported (0) as RO.

        When device support to change of a priority, 
        it uses the value of 1 to 5. In this case, 
        implementation as RW is mandatory.
        "
    ::= { mltJmJobEntry 8 }

   mltJmJobDivNumber  OBJECT-TYPE
    SYNTAX    INTEGER
    ACCESS    read-only
    STATUS    mandatory
    DESCRIPTION
        "
        The division number of job.
        0-999 is used.

        When the device does not perform division control,
        this value should be (-2). (-2) means unknown. 
        "
    ::= { mltJmJobEntry 9 }

   mltJmJobOwner  OBJECT-TYPE
    SYNTAX    DisplayString(SIZE(0..63))
    ACCESS    read-only
    STATUS    mandatory
    DESCRIPTION
        "
        The owner of job.
        If device cannot detect the name of owner ,
        this value should be '-', of 'unknown'.
        The implementation of zero-length is not accepted.
        "
    ::= { mltJmJobEntry 10 }

   mltJmJobType  OBJECT-TYPE
    SYNTAX    INTEGER {
                 other (0),
                 eMail (11),
                 iFaxSend (12),
                 scanToServer (13),
                 scanToPC (14),
                 scanToHDD (15),
                 twain (16),

                 normalPrint (20),
                 ippPrint (21),
                 securePrint (22),
                 timerPrint (23),
                 printToHDD (24),
                 proofAndPrint (25),

                 reportPrint (29),

                 iFaxReceive (31),

                 normalCopy (40),

                 faxRecieved (51),
                 faxSend (52)
              }
    ACCESS    read-only
    STATUS    mandatory
    DESCRIPTION
        "
        The type of job.
        When the job type is not detected, 
        this value should be other(0).
        "
    ::= { mltJmJobEntry 11 }

   mltJmJobName  OBJECT-TYPE
    SYNTAX    DisplayString(SIZE(0..31))
    ACCESS    read-only
    STATUS    mandatory
    DESCRIPTION
        "
        The name of job.
        If device cannot detect job name,
        this value should be '-', of 'unknown'.
        The implementation of zero-length is not accepted.
        "
    ::= { mltJmJobEntry 12 }

   mltJmJobDocPageNumbers  OBJECT-TYPE
    SYNTAX    Integer32
    ACCESS    read-only
    STATUS    mandatory
    DESCRIPTION
        "
        The page numbers of job.
        When device cannot detect page numbers
        this value should be (-2).
        "
    ::= { mltJmJobEntry 13 }

   mltJmJobDocCopyNumbers  OBJECT-TYPE
    SYNTAX    Integer32
    ACCESS    read-only
    STATUS    mandatory
    DESCRIPTION
        "
        Number of copies of Job.
        When device cannot detect the number of copies,
        this value should be (-2).
        "
    ::= { mltJmJobEntry 14 }

   mltJmJobPageSize  OBJECT-TYPE
    SYNTAX    INTEGER {
                  otherPaperSize (0),
                  unknownPaperSize (1),
                  --            2 to 10: reserved
                  a0 (11),
                  a1 (12),
                  a2 (13),
                  a3 (14),
                  a4 (15),
                  a5 (16),
                  a6 (17),
                  --             18 to 20 : reserved
                  b0 (21),
                  b1 (22),
                  b2 (23),
                  b3 (24),
                  b4 (25),
                  b5 (26),
                  b6 (27),
                  --             29 to 29 : reserved
                  us12x14 (30),  -- 12x14
                  ledger (31),   -- 11x17
                  us11x15 (32),  -- 11x15
                  us11x14 (33),  -- 11x14
                  comp (34),     -- computer, 10-1/8x14
                  us10x14 (35),  -- 10x14
                  us9-1by4x14 (36), -- 9-1/4x14
                  legal (37),    -- 8-1/2x14
                  us8-1by4x11-3by4 (38), -- 8-1/4x11-3/4
                  letter (39),  -- 8-1/2x11
                  govLetter (40), -- 8x10-1/2
                  quarto (41), -- 8x10
                  executive (42),  -- 7-1/4x10-1/2
                  statement (43),  -- 5-1/2x8-1/2
                  govRegal (44),
                  us3x5 (46),
                  us4x6 (47),
                  --        
                  fls (50),
                  fls0 (51),
                  fls1 (52),
                  fls2 (53),
                  fls3 (54),
                  --             55 to 60 : reserved
                  hagaki (61),
                  oufuku-Hagaki (62),
                  envelopeB5 (63),
                  envelopeCom10 (64),
                  envelopeC5 (65),
                  envelopeDL (66),
                  envelopeMonarch (67),
                  envelopeC6 (68),
                  -- 
                  youkei-0Gou (70),
                  youkei-1Gou (71),
                  youkei-4Gou (74),
                  youkei-6Gou (76),
                  --
                  choukei-3Gou (83),
                  choukei-4Gou (84),
                  --
                  kakugata-3Gou (93),
                  --
                  a3W (114),
                  a4W (115),
                  a5W (116),
                  a6W (117)
                  }
    ACCESS    read-only
    STATUS    mandatory
    DESCRIPTION
        "
        The paper/picture size of Job.
        In case of output job, this value shows output paper size.
        Incase of scanned job,  this value shows the size of picture.
        In Job of mixed size, the last page should be displayed.
        "
    ::= { mltJmJobEntry 15 }

   mltJmJobDestination  OBJECT-TYPE
    SYNTAX    DisplayString(SIZE(0..63))
    ACCESS    read-only
    STATUS    mandatory
    DESCRIPTION
        "
        The destination of job.
        If destination is unknown, this value should be '-'.
        "
    ::= { mltJmJobEntry 16 }

   mltJmJobDataSize  OBJECT-TYPE
    SYNTAX    Integer32
    ACCESS    read-only
    STATUS    optional
    DESCRIPTION
        "
        The data size of job. A unit is KByte.
        In case of printing job, this value should be the size of 
        printing date.
        In case of send job, this value should be not the size of picture
        but the size of transefered data.

        When the device cannot detect data size, this value should be (-2).
        "
    ::= { mltJmJobEntry 18 }

   mltJmJobColorMode  OBJECT-TYPE
    SYNTAX    INTEGER {
                other (0),
                unknown (1),
                color (2),
                grayScale (3),
                blackWhite (4)
              }
    ACCESS    read-only
    STATUS    optional
    DESCRIPTION
        "
        The type of color mode.
        "
    ::= { mltJmJobEntry 19 }

   mltJmJobFormat  OBJECT-TYPE
    SYNTAX    INTEGER {
                other (0),
                unknown (1),
                raw (2),
                tiff (3),
                tiff-MH (4),
                tiff-MR (5),
                tiff-MMR (6),
                jpeg (7),
                pdf (8),
                pcl (9),
                postScript (10),
                gdi (11),
                linePrinter (12)
              }
    ACCESS    read-only
    STATUS    optional
    DESCRIPTION
        "
        The data format of job.
        "
    ::= { mltJmJobEntry 20 }

   mltJmJobXResolution  OBJECT-TYPE
    SYNTAX    INTEGER
    ACCESS    read-only
    STATUS    optional
    DESCRIPTION
        "
        Resolution of the X direction of Job.
        A unit is dpi.
        "
    ::= { mltJmJobEntry 21 }

   mltJmJobYResolution  OBJECT-TYPE
    SYNTAX    INTEGER
    ACCESS    read-only
    STATUS    optional
    DESCRIPTION
        "
        Resolution of the Y direction of Job.
        A unit is dpi.
        "
    ::= { mltJmJobEntry 22 }

   mltJmJobDuplex  OBJECT-TYPE
    SYNTAX    INTEGER {
                on (1),
                off (2)
              }
    ACCESS    read-only
    STATUS    optional
    DESCRIPTION
        "
        A duplex setting of job.
        "
    ::= { mltJmJobEntry 23 }

   mltJmJobOutputPages  OBJECT-TYPE
    SYNTAX    Integer32
    ACCESS    read-only
    STATUS    optional
    DESCRIPTION
        "
        The page numbers which the output ended in Job.
        If a device can not recognize this information,
        '-2'(Not Support) should be implemented.
        "
    ::= { mltJmJobEntry 25 }

   mltJmJobOutputSheets  OBJECT-TYPE
    SYNTAX    Integer32
    ACCESS    read-only
    STATUS    optional
    DESCRIPTION
        "
        The sheets numbers which the output ended in Job.
        If a device can not recognize this information,
        '-2'(Not Support) should be implemented.
        "
    ::= { mltJmJobEntry 26 }

   mltJmJobMediaType  OBJECT-TYPE
    SYNTAX    INTEGER {
                  -- Media Type
                  otherMediaType (208),
                  unknownMediaType (209),
                  plainPaper (210),
                  plainPaper2side (211),
                  plainPaperRecycled (212),
                   plainPaperExclusive (214),
                  plainPaperColor (216),
                  thick1 (222),
                  thick1-2side (223),
                  thick2 (224),
                  thick2-2side (225),
                  thick3 (226),
                  thick3-2side (227),
                  ohp (230),
                  thin (236),
                  envelope (240),
                  envelope-2side (241),
                  label (242),
                  postCard (244),
                  letterHead (246),
                  tab (248)
                  }
    ACCESS    read-only
    STATUS    mandatory
    DESCRIPTION
        "
        The media type of job.
        "
    ::= { mltJmJobEntry 27 }

-- mltJmReport Group

   mltJmReportTable  OBJECT-TYPE
       SYNTAX    SEQUENCE OF MltJmReportEntry
       ACCESS    not-accessible
       STATUS    mandatory
       DESCRIPTION
           "
            Table for setting up the report of job history
            management information.

            If a device does not support all this functions, 
            this table needs not to be implemented.
           "
       ::= { mltJmReport 1 }
   
   mltJmReportEntry OBJECT-TYPE
    SYNTAX    MltJmReportEntry
    ACCESS    not-accessible
    STATUS    mandatory
    DESCRIPTION
        "
        "
    INDEX  { mltJmReportIndex }
    ::= { mltJmReportTable 1 }

    MltJmReportEntry ::= SEQUENCE {
        mltJmReportIndex     INTEGER,
        mltJmReportAddress   DisplayString,
        mltJmKeepAliveCount  INTEGER,
        mltJmReportInterval  INTEGER,
        mltJmReporIntervalSelection   INTEGER,
        mltJmReportRequest  INTEGER
       }

   mltJmReportIndex  OBJECT-TYPE
    SYNTAX    INTEGER
    ACCESS    read-only
    STATUS    mandatory
    DESCRIPTION
        "
        A unique value for each report destinations. 
        "
    ::= { mltJmReportEntry 1 }

   mltJmReportAddress  OBJECT-TYPE
    SYNTAX    DisplayString(SIZE(0..129))
    ACCESS    read-write
    STATUS    mandatory
    DESCRIPTION
        "
        E-mail address of report destination.
        "
    ::= {  mltJmReportEntry 2 }

   mltJmKeepAliveCount  OBJECT-TYPE
    SYNTAX    INTEGER
    ACCESS    read-write
    STATUS    mandatory
    DESCRIPTION
        "
        The counter that controls existence of transmission 
        to Job history information.

        Default shall set to 0 and, in 0, it shall not transmit to the specified address.
        A positive number is set when demanding transmission of Job history information.
        Transmission will be stopped, if it subtracts every 1 and is set to 0,
        whenever this counter will pass on the 1st.

        The side that demands transmission of Job history information 
        makes transmission continue by rewriting this counter periodically.

        Moreover, when E-mail environment is not ready
        (grade to which the SMTP server is not set), display -1.
        When there is no transmitting control function, this value should be -3.
        "
    ::= { mltJmReportEntry 3 }

   mltJmReportInterval  OBJECT-TYPE
    SYNTAX    INTEGER{
                notSend (0),
                each1 (1),
                each10 (2),
                each50 (3),
                each100 (4),
                each250 (5),
                each500 (6)
                }
    ACCESS    read-write
    STATUS    optional
    DESCRIPTION
        "
        The number of cases that transmits Job history at once is set up.
        "
    ::= { mltJmReportEntry 5 }

   mltJmReporIntervalSelection  OBJECT-TYPE
    SYNTAX    INTEGER{
                notSend (0),
                each1 (1),
                each10 (2),
                each50 (3),
                each100 (4),
                each250 (5),
                each500 (6)
                }
    ACCESS    read-only
    STATUS    optional
    DESCRIPTION
        "
        The maximum of the number of cases to which 
        once transmits Job history is shown.
        "
    ::= { mltJmReportEntry 6 }


   mltJmReportRequest  OBJECT-TYPE
    SYNTAX    INTEGER
    ACCESS    read-write
    STATUS    optional
    DESCRIPTION
        "
        The request command of reporting job history.
        
        default : 0
        send request : 1
        "
    ::= { mltJmReportEntry 7 }

END
