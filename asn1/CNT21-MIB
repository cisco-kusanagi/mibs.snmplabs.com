--
--	    Computer Network Technology, Corp.
--		6000 Nathan Lane North 
--		Plymouth, Minnesota  55442
--
--		  phone:  (763) 268-6000
--		    fax:  (763) 268-6800
--		support:  1-800-NET-TECH
--		  email:  cnt.com
--
--
--	MIB Version:     2.1
--	Product Family:  CNT Zeus(2) Mib-2(1) 
--
-- +------------+ if you change this mib, you increment the version number.
-- | Attention! | Also, this MIB is supported the by i/f aggregation agent,
-- +------------+ and that agent must also be compiled with this mib version.
--
-- This mib support RFC 2233 64 bits counter.
-- Version 2.1: Changed Syntax for compiling with SimpleSoft in Strict mode. 10/2001

CNT21-MIB DEFINITIONS ::= BEGIN

	IMPORTS
		Counter, Gauge, TimeTicks, enterprises
			 FROM RFC1155-SMI
		Counter32, Unsigned32, Integer32, MODULE-IDENTITY, Counter64
                         FROM SNMPv2-SMI
		OBJECT-TYPE
			 FROM RFC-1212
		DisplayString, PhysAddress
			 FROM RFC1213-MIB
		TruthValue, TimeStamp
			 FROM SNMPv2-TC
                IANAifType
                         FROM IANAifType-MIB
		cnt2Mib2 FROM CNT2-MIB;

         cnt2Interface  MODULE-IDENTITY
                LAST-UPDATED "0110230000Z"
		ORGANIZATION "Computer Network Technology Corporation"
                CONTACT-INFO "Computer Network Technology Technical Support
                              6000 Nathan Lane North
                              Plymouth, Minnesota  55442
                              telephone:  (763) 268-6000
                              fax: (763) 268-6800
                              support: 1-800-NET-TECH"
                DESCRIPTION  "This defines the CNT Interface MIB."
                REVISION     "0110230000Z"
                DESCRIPTION  "Created."
                ::= { enterprises cnt(333) cnt2(2) cnt2Subagent(1) 2 }


---     cnt             OBJECT IDENTIFIER ::= { enterprises 333 }
---     cnt2            OBJECT IDENTIFIER ::= { cnt 2 }
---     cnt2Mib2        OBJECT IDENTIFIER ::= { cnt2 1 }
---     cnt2Interfaces  OBJECT IDENTIFIER ::= { cnt2Mib2 2 }


          -- the Interfaces group

          cnt2Interfaces       OBJECT IDENTIFIER ::= { cnt2Mib2 2 }

          cnt2IfNumTable OBJECT-TYPE
              SYNTAX  SEQUENCE OF Cnt2IfNumEntry
              MAX-ACCESS  not-accessible
              STATUS  current
              DESCRIPTION
                      "A list of interface entries.  The number of
                      entries is given by the value of cnt2IfNumber."
              ::= { cnt2Interfaces 1 }

          cnt2IfNumEntry OBJECT-TYPE
              SYNTAX  Cnt2IfNumEntry
              MAX-ACCESS  not-accessible
              STATUS  current
              DESCRIPTION
                      "An interface entry containing objects at the
                      subnetwork layer and below for a particular
                      interface."
              INDEX   { cnt2IfNumIndex }
              ::= { cnt2IfNumTable 1 }

          Cnt2IfNumEntry ::=
              SEQUENCE {
                    cnt2IfNumIndex
                        Integer32,
                    cnt2IfNum
                        Integer32
              }
  
          cnt2IfNumIndex OBJECT-TYPE
              SYNTAX  Integer32
              MAX-ACCESS  read-only
              STATUS  current
              DESCRIPTION
                      "The slot number 1-12 for this table entry."
              ::= { cnt2IfNumEntry 1 }
   
          cnt2IfNum OBJECT-TYPE
              SYNTAX  Integer32
              MAX-ACCESS  read-only
              STATUS  current
              DESCRIPTION
                      "The number of network interfaces (regardless of
                      their current state) present on this slot."
              ::= { cnt2IfNumEntry 2 }


          -- the Interfaces table

          -- The Interfaces table contains information on the entity's
          -- interfaces.  Each interface is thought of as being
          -- attached to a `subnetwork'.  Note that this term should
          -- not be confused with `subnet' which refers to an
          -- addressing partitioning scheme used in the Internet suite
          -- of protocols.

          cnt2IfTable OBJECT-TYPE
              SYNTAX  SEQUENCE OF Cnt2IfEntry
              MAX-ACCESS  not-accessible
              STATUS  deprecated
              DESCRIPTION
                      "A list of interface entries.  The number of
                       entries is given by the value of cnt2IfNumber."
              ::= { cnt2Interfaces 2 }
  
          cnt2IfEntry OBJECT-TYPE
              SYNTAX  Cnt2IfEntry
              MAX-ACCESS  not-accessible
              STATUS  deprecated
              DESCRIPTION
                      "An interface entry containing objects at the
                      subnetwork layer and below for a particular
                      interface."
              INDEX   { cnt2IfSlotIndex, cnt2IfIndex }
              ::= { cnt2IfTable 1 }
  
          Cnt2IfEntry ::=
              SEQUENCE {
                  cnt2IfSlotIndex
                      Integer32,
                  cnt2IfIndex
                      Integer32,
                  cnt2IfDescr
                        DisplayString,
                  cnt2IfType
                      Integer32,
                  cnt2IfMtu
                      Integer32,
                  cnt2IfSpeed
                      Unsigned32,
                  cnt2IfPhysAddress
                      -- PhysAddress,
                      OCTET STRING (SIZE (32)),
                  cnt2IfAdminStatus
                      Integer32,
                  cnt2IfOperStatus
                      Integer32,
                  cnt2IfLastChange
                      TimeTicks,
                  cnt2IfInOctets
                      Counter32,
                  cnt2IfInUcastPkts
                      Counter32,
                  cnt2IfInNUcastPkts
                      Counter32,
                  cnt2IfInDiscards
                      Counter32,
                  cnt2IfInErrors
                      Counter32,
                  cnt2IfInUnknownProtos
                      Counter32,
                  cnt2IfOutOctets
                      Counter32,
                  cnt2IfOutUcastPkts
                      Counter32,
                  cnt2IfOutNUcastPkts
                      Counter32,
                  cnt2IfOutDiscards
                      Counter32,
                  cnt2IfOutErrors
                      Counter32,
                  cnt2IfOutQLen
                      Unsigned32,
                  cnt2IfSpecific
                      OBJECT IDENTIFIER
              }

          cnt2IfSlotIndex OBJECT-TYPE
              SYNTAX  Integer32
              MAX-ACCESS  read-only
              STATUS  deprecated
              DESCRIPTION
                      "The slot number 1-12 for this table entry."
              ::= { cnt2IfEntry 1 }
 
          cnt2IfIndex OBJECT-TYPE
              SYNTAX  Integer32
              MAX-ACCESS  read-only
              STATUS  deprecated
              DESCRIPTION
                      "A unique value for each interface.  Its value
                      ranges between 1 and the value of cnt2IfNumber.
                      The value for each interface must remain constant
                      at least from one re-initialization of the entity's
                      network management system to the next re-
                      initialization."
              ::= { cnt2IfEntry 2 }

          cnt2IfDescr OBJECT-TYPE
              SYNTAX  DisplayString (SIZE (0..255))
              MAX-ACCESS  read-only
              STATUS  deprecated
              DESCRIPTION
                      "A textual string containing information about the
                      interface.  This string should include the name of
                      the manufacturer, the product name and the version
                      of the hardware interface."
              ::= { cnt2IfEntry 3 }

          cnt2IfType OBJECT-TYPE
              SYNTAX  INTEGER {
                          other(1),          -- none of the following
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           -- T-1
                          e1(19),            -- european equiv. of T-1
                          basicISDN(20),
                          primaryISDN(21),   -- proprietary serial
                          propPointToPointSerial(22),
                          ppp(23),
                          softwareLoopback(24),
                          eon(25),            -- CLNP over IP [11]
                          ethernet-3Mbit(26),
                          nsip(27),           -- XNS over IP
                          slip(28),           -- generic SLIP
                          ultra(29),          -- ULTRA technologies
                          ds3(30),            -- T-3
                          sip(31),            -- SMDS
                          frame-relay(32),
                          rs232(33),
                          parallel-port(34),
                          arcnet(35),
                          arcnet-plus(36),
                          atm(37),
                          miox25(38),
                          sonet(39),
                          x25ple(40),
                          iso8802-llc(41),
                          localtalk(42),
                          smds-dxi(43),
                          frame-relay-dce(44),
                          v35(45),
                          hssi(46),
                          hippi(47),
                          modem(48),
                          atm-all5(49),
                          sonet-path(50),
                          sonet-vt(51),
                          smds-intercarrier(52),
                          prop-virtual-term(53),
                          prop-multiplexing(54),
                          ieee80212(55),
                          fibreChannel(56),
                          hippiInterface(57),
                          frameRelayInterconnect(58),
                          aflane8023(59),
                          aflane8025(60),
                          cctEmul(61),
                          fastEther(62),
                          isdn(63),
                          v11(64),
                          v36(65),
                          g703at64k(66),
                          g703at2mb(67),
                          qllc(68),
                          fastEtherFX(69),
                          channel(70),
                          ieee80211(71),
                          ibm370parChan(72),
                          escon(73),
                          dlsw(74),
                          isdns(75),
                          isdnu(76),
                          lapd(77),
                          ipSwitch(78),
                          rsrb(79),
                          atmLogical(80),
                          ds0(81),
                          ds0Bundle(82),
                          bsc(83),
                          async(84),
                          cnr(85),
                          iso88025Dtr(86),
                          eplrs(87),
                          arap(88),
                          propCnls(89),
                          hostPad(90),
                          termPad(91),
                          frameRealyMPI(92),
                          x213(93),
                          adsl(94),
                          radsl(95),
                          sdsl(96),
                          vdsl(97),
                          iso88025CRFPInt(98),
                          myrinet(99),
                          voiceEM(100),
                          voiceFXO(101),
                          voiceFXS(102),
                          voiceEncap(103),
                          voiceOverIp(104),
                          atmDxi(105),
                          atmFuni(106),
                          atmIma(107),
                          pppMultilinkBundle(108),
                          ipOverCdlc(109),
                          ipOverClaw(110),
                          stackToStack(111),
                          virtualIpAddress(112),
                          mpc(113),
                          ipOverAtm(114),
                          iso88025Fiber(115),
                          tdlc(116),
                          gigabitEthernet(117),
                          escon-local(256),
                          escon-remote(257),
                          switch-unicast(258),
                          switch-multicast(259),
                          switch-broadcast(260),
                          escon-srdf(261),
                          scsi-2(262),
                          scsi-3(263)
                      }
              MAX-ACCESS  read-only
              STATUS  deprecated
              DESCRIPTION
                      "The type of interface, distinguished according to
                      the physical/link protocol(s) immediately `below'
                      the network layer in the protocol stack."
              ::= { cnt2IfEntry 4 }

          cnt2IfMtu OBJECT-TYPE
              SYNTAX  Integer32
              MAX-ACCESS  read-only
              STATUS  deprecated
              DESCRIPTION
                      "The size of the largest datagram which can be
                      sent/received on the interface, specified in
                      octets.  For interfaces that are used for
                      transmitting network datagrams, this is the size
                      of the largest network datagram that can be sent
                      on the interface."
              ::= { cnt2IfEntry 5 }

          cnt2IfSpeed OBJECT-TYPE
              SYNTAX  Unsigned32
              MAX-ACCESS  read-only
              STATUS  deprecated
              DESCRIPTION
                      "An estimate of the interface's current bandwidth
                      in bits per second.  For interfaces which do not
                      vary in bandwidth or for those where no accurate
                      estimation can be made, this object should contain
                      the nominal bandwidth."
              ::= { cnt2IfEntry 6 }
  
          cnt2IfPhysAddress OBJECT-TYPE
              -- SYNTAX  PhysAddress
              SYNTAX  OCTET STRING (SIZE(32))
              MAX-ACCESS  read-only
              STATUS  deprecated
              DESCRIPTION
                      "The interface's address at the protocol layer
                      immediately `below' the network layer in the
                      protocol stack.  For interfaces which do not have
                      such an address (e.g., a serial line), this object
                      should contain an octet string of zero length."
              ::= { cnt2IfEntry 7 }
  
          cnt2IfAdminStatus OBJECT-TYPE
              SYNTAX  INTEGER {
                          up(1),       -- ready to pass packets
                          down(2),
                          testing(3)   -- in some test mode
                      }
              MAX-ACCESS  read-write
              STATUS  deprecated
              DESCRIPTION
                      "The desired state of the interface.  The
                      testing(3) state indicates that no operational
                      packets can be passed."
              ::= { cnt2IfEntry 8 }

          cnt2IfOperStatus OBJECT-TYPE
                SYNTAX  INTEGER {
                          up(1),       -- ready to pass packets
                          down(2),
                          testing(3),  -- in some test mode
                          unknown(4),
                          dormant(5)   -- intended state
                      }
              MAX-ACCESS  read-only
              STATUS  deprecated
              DESCRIPTION
                      "The current operational state of the interface.
                      The testing(3) state indicates that no operational
                      packets can be passed."
              ::= { cnt2IfEntry 9 }

          cnt2IfLastChange OBJECT-TYPE
              SYNTAX  TimeTicks
              MAX-ACCESS  read-only
              STATUS  deprecated
              DESCRIPTION
                      "The value of sysUpTime at the time the interface
                      entered its current operational state.  If the
                      current state was entered prior to the last re-
                      initialization of the local network management
                      subsystem, then this object contains a zero
                      value."
              ::= { cnt2IfEntry 10 }

          cnt2IfInOctets OBJECT-TYPE
              SYNTAX  Counter32
              MAX-ACCESS  read-only
              STATUS  deprecated
              DESCRIPTION
                      "The total number of octets received on the
                      interface, including framing characters."
              ::= { cnt2IfEntry 11 }

          cnt2IfInUcastPkts OBJECT-TYPE
              SYNTAX  Counter32
              MAX-ACCESS  read-only
              STATUS  deprecated
              DESCRIPTION
                      "The number of subnetwork-unicast packets
                      delivered to a higher-layer protocol."
              ::= { cnt2IfEntry 12 }

          cnt2IfInNUcastPkts OBJECT-TYPE
              SYNTAX  Counter32
              MAX-ACCESS  read-only
              STATUS  deprecated
              DESCRIPTION
                      "The number of non-unicast (i.e., subnetwork-
                      broadcast or subnetwork-multicast) packets
                      delivered to a higher-layer protocol."
              ::= { cnt2IfEntry 13 }
  
          cnt2IfInDiscards OBJECT-TYPE
              SYNTAX  Counter32
              MAX-ACCESS  read-only
              STATUS  deprecated
              DESCRIPTION
                      "The number of inbound packets which were chosen
                      to be discarded even though no errors had been
                      detected to prevent their being deliverable to a
                      higher-layer protocol.  One possible reason for
                      discarding such a packet could be to free up
                      buffer space."
              ::= { cnt2IfEntry 14 }
  
          cnt2IfInErrors OBJECT-TYPE
              SYNTAX  Counter32
              MAX-ACCESS  read-only
              STATUS  deprecated
              DESCRIPTION
                      "The number of inbound packets that contained
                      errors preventing them from being deliverable to a
                      higher-layer protocol."
              ::= { cnt2IfEntry 15 }
  
          cnt2IfInUnknownProtos OBJECT-TYPE
              SYNTAX  Counter32
              MAX-ACCESS  read-only
              STATUS  deprecated
              DESCRIPTION
                      "The number of packets received via the interface
                      which were discarded because of an unknown or
                      unsupported protocol."
              ::= { cnt2IfEntry 16 }
  
          cnt2IfOutOctets OBJECT-TYPE
              SYNTAX  Counter32
              MAX-ACCESS  read-only
              STATUS  deprecated
              DESCRIPTION
                      "The total number of octets transmitted out of the
                      interface, including framing characters."
              ::= { cnt2IfEntry 17 }
  
          cnt2IfOutUcastPkts OBJECT-TYPE
              SYNTAX  Counter32
              MAX-ACCESS  read-only
              STATUS  deprecated
              DESCRIPTION
                      "The total number of packets that higher-level
                      protocols requested be transmitted to a
                      subnetwork-unicast address, including those that
                      were discarded or not sent."
              ::= { cnt2IfEntry 18 }
  
          cnt2IfOutNUcastPkts OBJECT-TYPE
              SYNTAX  Counter32
              MAX-ACCESS  read-only
              STATUS  deprecated
              DESCRIPTION
                      "The total number of packets that higher-level
                      protocols requested be transmitted to a non-
                      unicast (i.e., a subnetwork-broadcast or
                      subnetwork-multicast) address, including those
                      that were discarded or not sent."
              ::= { cnt2IfEntry 19 }
  
          cnt2IfOutDiscards OBJECT-TYPE
              SYNTAX  Counter32
              MAX-ACCESS  read-only
              STATUS  deprecated
              DESCRIPTION
                    "The number of outbound packets which were chosen
                      to be discarded even though no errors had been
                      detected to prevent their being transmitted.  One
                      possible reason for discarding such a packet could
                      be to free up buffer space."
              ::= { cnt2IfEntry 20 }
  
          cnt2IfOutErrors OBJECT-TYPE
              SYNTAX  Counter32
              MAX-ACCESS  read-only
              STATUS  deprecated
              DESCRIPTION
                    "The number of outbound packets that could not be
                    transmitted because of errors."
              ::= { cnt2IfEntry 21 }

          cnt2IfOutQLen OBJECT-TYPE
              SYNTAX  Unsigned32
              MAX-ACCESS  read-only
              STATUS  deprecated
              DESCRIPTION
                      "The length of the output packet queue (in
                      packets)."
              ::= { cnt2IfEntry 22 }

          cnt2IfSpecific OBJECT-TYPE
              SYNTAX  OBJECT IDENTIFIER
              MAX-ACCESS  read-only
              STATUS  deprecated
              DESCRIPTION
                      "A reference to MIB definitions specific to the
                      particular media being used to realize the
                      interface.  For example, if the interface is
                      realized by an ethernet, then the value of this
                      object refers to a document defining objects
                      specific to ethernet.  If this information is not
                      present, its value should be set to the OBJECT
                      IDENTIFIER { 0 0 }, which is a syntatically valid
                      object identifier, and any conformant
                      implementation of ASN.1 and BER must be able to
                      generate and recognize this value."
              ::= { cnt2IfEntry 23 }


          -- the Interfaces table

          -- The Interfaces table contains information on the entity's
          -- interfaces.  Each interface is thought of as being
          -- attached to a `subnetwork'.  Note that this term should
          -- not be confused with `subnet' which refers to an
          -- addressing partitioning scheme used in the Internet suite
          -- of protocols.

          cnt2XIfTable OBJECT-TYPE
              SYNTAX  SEQUENCE OF Cnt2XIfEntry
              MAX-ACCESS  not-accessible
              STATUS  current
              DESCRIPTION
                      "A list of interface entries.  The number of
                       entries is given by the value of cnt2XIfNumber."
              ::= { cnt2Interfaces 3 }
  
  
          cnt2XIfEntry OBJECT-TYPE
              SYNTAX  Cnt2XIfEntry
              MAX-ACCESS  not-accessible
              STATUS  current
              DESCRIPTION
                      "An interface entry containing objects at the
                      subnetwork layer and below for a particular
                      interface."
              INDEX   { cnt2XIfSlotIndex, cnt2XIfIndex }
              ::= { cnt2XIfTable 1 }
  
          Cnt2XIfEntry ::=
              SEQUENCE {
                  cnt2XIfSlotIndex
                      Integer32,
                  cnt2XIfIndex
                      Integer32,
                  cnt2XIfDescr
                        DisplayString,
                  cnt2XIfName
                        DisplayString,
                  cnt2XIfIANAType
                      IANAifType,
                  cnt2XIfCntType
                      Integer32,
                  cnt2XIfMtu
                      Integer32,
                  cnt2XIfSpeed
                      Unsigned32,
                  cnt2XIfPhysAddress
                      -- PhysAddress,
                      OCTET STRING (SIZE(32)),
                  cnt2XIfAdminStatus
                      Integer32,
                  cnt2XIfOperStatus
                      Integer32,
                  cnt2XIfLastChange
                      TimeTicks,
                  cnt2XIfLinkUpDownTrapEnable
		      Integer32,
                  cnt2XIfPromiscuousMode
		      TruthValue,
                  cnt2XIfConnectorType
                      TruthValue,
                  cnt2XIfAlias
                      DisplayString,
                  cnt2XIfInOctets
                      Counter64,
                  cnt2XIfInUcastPkts
                      Counter32,
                  cnt2XIfInMulticastPkts
                      Counter32,
                  cnt2XIfInBroadcastPkts
                      Counter32,
                  cnt2XIfInDiscards
                      Counter32,
                  cnt2XIfInErrors
                      Counter32,
                  cnt2XIfInUnknownProtos
                      Counter32,
                  cnt2XIfOutOctets
                      Counter64,
                  cnt2XIfOutUcastPkts
                      Counter32,
                  cnt2XIfOutMulticastPkts
                      Counter32,
                  cnt2XIfOutBroadcastPkts
                      Counter32,
                  cnt2XIfOutDiscards
                      Counter32,
                  cnt2XIfOutErrors
                      Counter32,
                  cnt2XIfCounterDiscontinuityTime
                      TimeStamp
              }

          cnt2XIfSlotIndex OBJECT-TYPE
              SYNTAX  Integer32
              MAX-ACCESS  read-only
              STATUS  current
              DESCRIPTION
                      "The slot number 1-4 for this table entry."
              ::= { cnt2XIfEntry 1 }
 
          cnt2XIfIndex OBJECT-TYPE
              SYNTAX  Integer32
              MAX-ACCESS  read-only
              STATUS  current
              DESCRIPTION
                      "A unique value for each interface.  Its value
                      ranges between 1 and the value of cnt2IfNumber.
                      The value for each interface must remain constant
                      at least from one re-initialization of the entity's
                      network management system to the next re-
                      initialization."
              ::= { cnt2XIfEntry 2 }
  
          cnt2XIfDescr OBJECT-TYPE
              SYNTAX  DisplayString (SIZE (0..255))
              MAX-ACCESS  read-only
              STATUS  current
              DESCRIPTION
                      "A textual string containing information about the
                      interface.  This string should include the name of
                      the manufacturer, the product name and the version
                      of the hardware interface."
              ::= { cnt2XIfEntry 3 }
  
          cnt2XIfName OBJECT-TYPE
              SYNTAX  DisplayString (SIZE (0..255))
              MAX-ACCESS  read-only
              STATUS  current
              DESCRIPTION
                      "A textual string containing information about the
                      interface.  This string should include the name of
                      the manufacturer, the product name and the version
                      of the hardware interface."
              ::= { cnt2XIfEntry 4 }

          cnt2XIfIANAType OBJECT-TYPE
              SYNTAX  IANAifType
              MAX-ACCESS  read-only
              STATUS  current
              DESCRIPTION
               "The type of interface.  Additional values for ifType
               are assigned by the Internet Assigned Numbers
               Authority (IANA), through updating the syntax of the
               IANAifType textual convention."
              ::= { cnt2XIfEntry 5 }

          cnt2XIfCntType OBJECT-TYPE
              SYNTAX  INTEGER {
                          other(1),          -- none of the following
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           -- T-1
                          e1(19),            -- european equiv. of T-1
                          basicISDN(20),
                          primaryISDN(21),   -- proprietary serial
                          propPointToPointSerial(22),
                          ppp(23),
                          softwareLoopback(24),
                          eon(25),            -- CLNP over IP [11]
                          ethernet-3Mbit(26),
                          nsip(27),           -- XNS over IP
                          slip(28),           -- generic SLIP
                          ultra(29),          -- ULTRA technologies
                          ds3(30),            -- T-3
                          sip(31),            -- SMDS
                          frame-relay(32),
                          rs232(33),
                          parallel-port(34),
                          arcnet(35),
                          arcnet-plus(36),
                          atm(37),
                          miox25(38),
                          sonet(39),
                          x25ple(40),
                          iso8802-llc(41),
                          localtalk(42),
                          smds-dxi(43),
                          frame-relay-dce(44),
                          v35(45),
                          hssi(46),
                          hippi(47),
                          modem(48),
                          atm-all5(49),
                          sonet-path(50),
                          sonet-vt(51),
                          smds-intercarrier(52),
                          prop-virtual-term(53),
                          prop-multiplexing(54),
                          ieee80212(55),
                          fibreChannel(56),
                          hippiInterface(57),
                          frameRelayInterconnect(58),
                          aflane8023(59),
                          aflane8025(60),
                          cctEmul(61),
                          fastEther(62),
                          isdn(63),
                          v11(64),
                          v36(65),
                          g703at64k(66),
                          g703at2mb(67),
                          qllc(68),
                          fastEtherFX(69),
                          channel(70),
                          ieee80211(71),
                          ibm370parChan(72),
                          escon(73),
                          dlsw(74),
                          isdns(75),
                          isdnu(76),
                          lapd(77),
                          ipSwitch(78),
                          rsrb(79),
                          atmLogical(80),
                          ds0(81),
                          ds0Bundle(82),
                          bsc(83),
                          async(84),
                          cnr(85),
                          iso88025Dtr(86),
                          eplrs(87),
                          arap(88),
                          propCnls(89),
                          hostPad(90),
                          termPad(91),
                          frameRealyMPI(92),
                          x213(93),
                          adsl(94),
                          radsl(95),
                          sdsl(96),
                          vdsl(97),
                          iso88025CRFPInt(98),
                          myrinet(99),
                          voiceEM(100),
                          voiceFXO(101),
                          voiceFXS(102),
                          voiceEncap(103),
                          voiceOverIp(104),
                          atmDxi(105),
                          atmFuni(106),
                          atmIma(107),
                          pppMultilinkBundle(108),
                          ipOverCdlc(109),
                          ipOverClaw(110),
                          stackToStack(111),
                          virtualIpAddress(112),
                          mpc(113),
                          ipOverAtm(114),
                          iso88025Fiber(115),
                          tdlc(116),
                          gigabitEthernet(117),
                          escon-local(256),
                          escon-remote(257),
                          switch-unicast(258),
                          switch-multicast(259),
                          switch-broadcast(260),
                          escon-srdf(261),
                          scsi-2(262),
                          scsi-3(263)
                      }
              MAX-ACCESS  read-only
              STATUS  current
              DESCRIPTION
                      "The type of interface, distinguished according to
                      the physical/link protocol(s) immediately `below'
                      the network layer in the protocol stack."
              ::= { cnt2XIfEntry 6 }

          cnt2XIfMtu OBJECT-TYPE
              SYNTAX  Integer32
              MAX-ACCESS  read-only
              STATUS  current
              DESCRIPTION
                      "The size of the largest datagram which can be
                      sent/received on the interface, specified in
                      octets.  For interfaces that are used for
                      transmitting network datagrams, this is the size
                      of the largest network datagram that can be sent
                      on the interface."
              ::= { cnt2XIfEntry 7 }

          cnt2XIfSpeed OBJECT-TYPE
              SYNTAX  Unsigned32
              MAX-ACCESS  read-only
              STATUS  current
              DESCRIPTION
                      "An estimate of the interface's current bandwidth
                      in bits per second.  For interfaces which do not
                      vary in bandwidth or for those where no accurate
                      estimation can be made, this object should contain
                      the nominal bandwidth."
              ::= { cnt2XIfEntry 8 }
  
          cnt2XIfPhysAddress OBJECT-TYPE
              -- SYNTAX  PhysAddress
              SYNTAX  OCTET STRING (SIZE(32))
              MAX-ACCESS  read-only
              STATUS  current
              DESCRIPTION
                      "The interface's address at the protocol layer
                      immediately `below' the network layer in the
                      protocol stack.  For interfaces which do not have
                      such an address (e.g., a serial line), this object
                      should contain an octet string of zero length."
              ::= { cnt2XIfEntry 9 }
  
          cnt2XIfAdminStatus OBJECT-TYPE
              SYNTAX  INTEGER {
                          up(1),       -- ready to pass packets
                          down(2),
                          testing(3)   -- in some test mode
                      }
              MAX-ACCESS  read-write
              STATUS  current
              DESCRIPTION
                      "The desired state of the interface.  The
                      testing(3) state indicates that no operational
                      packets can be passed."
              ::= { cnt2XIfEntry 10 }

          cnt2XIfOperStatus OBJECT-TYPE
                SYNTAX  INTEGER {
                          up(1),       -- ready to pass packets
                          down(2),
                          testing(3),  -- in some test mode
                          unknown(4),
                          dormant(5)   -- intended state
                      }
              MAX-ACCESS  read-only
              STATUS  current
              DESCRIPTION
                      "The current operational state of the interface.
                      The testing(3) state indicates that no operational
                      packets can be passed."
              ::= { cnt2XIfEntry 11 }

          cnt2XIfLastChange OBJECT-TYPE
              SYNTAX  TimeTicks
              MAX-ACCESS  read-only
              STATUS  current
              DESCRIPTION
                      "The value of sysUpTime at the time the interface
                      entered its current operational state.  If the
                      current state was entered prior to the last re-
                      initialization of the local network management
                      subsystem, then this object contains a zero
                      value."
              ::= { cnt2XIfEntry 12 }
  	  cnt2XIfLinkUpDownTrapEnable  OBJECT-TYPE
      	      SYNTAX      INTEGER { enabled(1), disabled(2) }
              MAX-ACCESS  	  read-write
              STATUS      current
              DESCRIPTION
            	 	"Indicates whether linkUp/linkDown traps should be
              		generated for this interface.
              		By default, this object should have the value
              		enabled(1) for interfaces which do not operate on
              		'top' of any other interface (as defined in the
              		ifStackTable), and disabled(2) otherwise."
      		::= { cnt2XIfEntry 13 }

   	  cnt2XIfPromiscuousMode  OBJECT-TYPE
       		SYNTAX      TruthValue
       		MAX-ACCESS      read-write
       		STATUS      current
       		DESCRIPTION
               "This object has a value of false(2) if this interface
               only accepts packets/frames that are addressed to this
               station.  This object has a value of true(1) when the
               station accepts all packets/frames transmitted on the
               media.  The value true(1) is only legal on certain
               types of media.  If legal, setting this object to a
               value of true(1) may require the interface to be reset
               before becoming effective.

               The value of ifPromiscuousMode does not affect the
               reception of broadcast and multicast packets/frames by
               the interface."
       		::= { cnt2XIfEntry 14 }

  cnt2XIfConnectorType   OBJECT-TYPE
      SYNTAX      TruthValue
      MAX-ACCESS      read-only
      STATUS      current
      DESCRIPTION
              "This object has the value 'true(1)' if the interface
              sublayer has a physical connector and the value
              'false(2)' otherwise."
      ::= { cnt2XIfEntry 15 }

  cnt2XIfAlias   OBJECT-TYPE
      SYNTAX      DisplayString (SIZE(0..64))
      MAX-ACCESS      read-write
      STATUS      current
      DESCRIPTION
              "This object is an 'alias' name for the interface as
              specified by a network manager, and provides a non-
              volatile 'handle' for the interface.

              On the first instantiation of an interface, the value
              of ifAlias associated with that interface is the
              zero-length string.  As and when a value is written
              into an instance of ifAlias through a network

              management set operation, then the agent must retain
              the supplied value in the ifAlias instance associated
              with the same interface for as long as that interface
              remains instantiated, including across all re-
              initializations/reboots of the network management
              system, including those which result in a change of
              the interface's ifIndex value.

              An example of the value which a network manager might
              store in this object for a WAN interface is the
              (Telco's) circuit number/identifier of the interface.

              Some agents may support write-access only for
              interfaces having particular values of ifType.  An
              agent which supports write access to this object is
              required to keep the value in non-volatile storage,
              but it may limit the length of new values depending on
              how much storage is already occupied by the current
              values for other interfaces."
      ::= { cnt2XIfEntry 16 }
  
          cnt2XIfInOctets OBJECT-TYPE
              SYNTAX  Counter64
              MAX-ACCESS  read-only
              STATUS  current
              DESCRIPTION
                      "The total number of octets received on the
                      interface, including framing characters."
              ::= { cnt2XIfEntry 17 }
  
          cnt2XIfInUcastPkts OBJECT-TYPE
              SYNTAX  Counter32
              MAX-ACCESS  read-only
              STATUS  current
              DESCRIPTION
                      "The number of subnetwork-unicast packets
                      delivered to a higher-layer protocol."
              ::= { cnt2XIfEntry 18 }
 
   cnt2XIfInMulticastPkts OBJECT-TYPE
       SYNTAX      Counter32
       MAX-ACCESS      read-only
       STATUS      current 
       DESCRIPTION
               "The number of packets, delivered by this sub-layer to
               a higher (sub-)layer, which were addressed to a
               multicast address at this sub-layer.  For a MAC layer
               protocol, this includes both Group and Functional
               addresses.

               Discontinuities in the value of this counter can occur
               at re-initialization of the management system, and at
               other times as indicated by the value of
               ifCounterDiscontinuityTime."
       ::= { cnt2XIfEntry 19 }

   cnt2XIfInBroadcastPkts OBJECT-TYPE
       SYNTAX      Counter32
       MAX-ACCESS  read-only
       STATUS      current
       DESCRIPTION
               "The number of packets, delivered by this sub-layer to
               a higher (sub-)layer, which were addressed to a
               broadcast address at this sub-layer.  

               Discontinuities in the value of this counter can occur
               at re-initialization of the management system, and at
               other times as indicated by the value of

               ifCounterDiscontinuityTime."
       ::= { cnt2XIfEntry 20 } 

          cnt2XIfInDiscards OBJECT-TYPE
              SYNTAX  Counter32
              MAX-ACCESS  read-only
              STATUS  current
              DESCRIPTION
                      "The number of inbound packets which were chosen
                      to be discarded even though no errors had been
                      detected to prevent their being deliverable to a
                      higher-layer protocol.  One possible reason for
                      discarding such a packet could be to free up
                      buffer space."
              ::= { cnt2XIfEntry 21 }
  
          cnt2XIfInErrors OBJECT-TYPE
              SYNTAX  Counter32
              MAX-ACCESS  read-only
              STATUS  current
              DESCRIPTION
                      "The number of inbound packets that contained
                      errors preventing them from being deliverable to a
                      higher-layer protocol."
              ::= { cnt2XIfEntry 22 }
  
          cnt2XIfInUnknownProtos OBJECT-TYPE
              SYNTAX  Counter32
              MAX-ACCESS  read-only
              STATUS  current
              DESCRIPTION
                      "The number of packets received via the interface
                      which were discarded because of an unknown or
                      unsupported protocol."
              ::= { cnt2XIfEntry 23 }
  
          cnt2XIfOutOctets OBJECT-TYPE
              SYNTAX  Counter64
              MAX-ACCESS  read-only
              STATUS  current
              DESCRIPTION
                      "The total number of octets transmitted out of the
                      interface, including framing characters."
              ::= { cnt2XIfEntry 24 }
  
          cnt2XIfOutUcastPkts OBJECT-TYPE
              SYNTAX  Counter32
              MAX-ACCESS  read-only
              STATUS  current
              DESCRIPTION
                      "The total number of packets that higher-level
                      protocols requested be transmitted to a
                      subnetwork-unicast address, including those that
                      were discarded or not sent."
              ::= { cnt2XIfEntry 25 }
  
          cnt2XIfOutMulticastPkts OBJECT-TYPE
              SYNTAX  Counter32
              MAX-ACCESS  read-only
              STATUS  current
              DESCRIPTION
                      "The total number of packets that higher-level
                      protocols requested be transmitted to a non-
                      unicast (i.e., a subnetwork-broadcast or
                      subnetwork-multicast) address, including those
                      that were discarded or not sent."
              ::= { cnt2XIfEntry 26 }
  
  cnt2XIfOutBroadcastPkts OBJECT-TYPE
      SYNTAX      Counter32
      MAX-ACCESS      read-only
      STATUS      current
      DESCRIPTION
              "The total number of packets that higher-level
              protocols requested be transmitted, and which were
              addressed to a broadcast address at this sub-layer,
              including those that were discarded or not sent.  

              Discontinuities in the value of this counter can occur
              at re-initialization of the management system, and at
              other times as indicated by the value of
              ifCounterDiscontinuityTime."
      ::= { cnt2XIfEntry 27 }

          cnt2XIfOutDiscards OBJECT-TYPE
              SYNTAX  Counter32
              MAX-ACCESS  read-only
              STATUS  current
              DESCRIPTION
                    "The number of outbound packets which were chosen
                      to be discarded even though no errors had been
                      detected to prevent their being transmitted.  One
                      possible reason for discarding such a packet could
                      be to free up buffer space."
              ::= { cnt2XIfEntry 28 }
  
          cnt2XIfOutErrors OBJECT-TYPE
              SYNTAX  Counter32
              MAX-ACCESS  read-only
              STATUS  current
              DESCRIPTION
                    "The number of outbound packets that could not be
                    transmitted because of errors."
              ::= { cnt2XIfEntry 29 }

   cnt2XIfCounterDiscontinuityTime OBJECT-TYPE
       SYNTAX      TimeStamp
       MAX-ACCESS  read-only
       STATUS      current
       DESCRIPTION
               "The value of sysUpTime on the most recent occasion at
               which any one or more of this interface's counters
               suffered a discontinuity.  The relevant counters are
               the specific instances associated with this interface
               of any Counter32 or Counter64 object contained in the
               ifTable or ifXTable.  If no such discontinuities have
               occurred since the last re-initialization of the local
               management subsystem, then this object contains a zero
               value."
       ::= { cnt2XIfEntry 30 }
 
 
          END
