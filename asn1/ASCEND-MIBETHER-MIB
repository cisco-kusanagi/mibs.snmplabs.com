--			Ascend mibether MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBETHER-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibethernetInterfaceProfile  OBJECT IDENTIFIER ::= { configuration 76}

	-- The mibethernetInterfaceProfile table
	--
	-- This table contains parameters for the mibethernetInterfaceProfile profile
	--

    mibethernetInterfaceProfileTable	OBJECT-TYPE
	SYNTAX		SEQUENCE OF MibethernetInterfaceProfileEntry
	ACCESS		not-accessible
	STATUS		mandatory
	DESCRIPTION	"A list of mibethernetInterfaceProfile profile entries."
	::= { mibethernetInterfaceProfile 1 }

    mibethernetInterfaceProfileEntry	OBJECT-TYPE
	SYNTAX		MibethernetInterfaceProfileEntry
	ACCESS		not-accessible
	STATUS		mandatory
	DESCRIPTION	"A mibethernetInterfaceProfile entry containing objects that
			 maps to the parameters of mibethernetInterfaceProfile profile."
	INDEX		{ ethernetInterfaceProfile-Shelf-o, ethernetInterfaceProfile-Slot-o, ethernetInterfaceProfile-Item-o }
	::= { mibethernetInterfaceProfileTable 1 }

    MibethernetInterfaceProfileEntry ::=
	SEQUENCE {
	    ethernetInterfaceProfile-Shelf-o
		INTEGER,
	    ethernetInterfaceProfile-Slot-o
		INTEGER,
	    ethernetInterfaceProfile-Item-o
		INTEGER,
	    ethernetInterfaceProfile-InterfaceAddress-Shelf
		INTEGER,
	    ethernetInterfaceProfile-InterfaceAddress-Slot
		INTEGER,
	    ethernetInterfaceProfile-InterfaceAddress-ItemNumber
		INTEGER,
	    ethernetInterfaceProfile-LinkStateEnabled
		INTEGER,
	    ethernetInterfaceProfile-Enabled
		INTEGER,
	    ethernetInterfaceProfile-EtherIfType
		INTEGER,
	    ethernetInterfaceProfile-Filter
		INTEGER,
	    ethernetInterfaceProfile-BridgingEnabled
		INTEGER,
	    ethernetInterfaceProfile-FilterName
		DisplayString,
	    ethernetInterfaceProfile-DuplexMode
		INTEGER,
	    ethernetInterfaceProfile-PppoeOptions-Pppoe
		INTEGER,
	    ethernetInterfaceProfile-PppoeOptions-BridgeNonPppoe
		INTEGER,
	    ethernetInterfaceProfile-BridgingOptions-BridgingGroup
		INTEGER,
	    ethernetInterfaceProfile-BridgingOptions-DialOnBroadcast
		INTEGER,
	    ethernetInterfaceProfile-BridgingOptions-IpxSpoofing
		INTEGER,
	    ethernetInterfaceProfile-BridgingOptions-SpoofingTimeout
		INTEGER,
	    ethernetInterfaceProfile-BridgingOptions-Fill2
		INTEGER,
	    ethernetInterfaceProfile-BridgingOptions-BridgeType
		INTEGER,
	    ethernetInterfaceProfile-BridgingOptions-Egress
		INTEGER,
	    ethernetInterfaceProfile-MediaSpeedMbit
		INTEGER,
	    ethernetInterfaceProfile-AutoNegotiate
		INTEGER,
	    ethernetInterfaceProfile-Action-o
		INTEGER
	}

    ethernetInterfaceProfile-Shelf-o	OBJECT-TYPE
	SYNTAX	INTEGER
	ACCESS	read-only
	STATUS	mandatory
	DESCRIPTION	""
	::= { mibethernetInterfaceProfileEntry 1 }

    ethernetInterfaceProfile-Slot-o	OBJECT-TYPE
	SYNTAX	INTEGER
	ACCESS	read-only
	STATUS	mandatory
	DESCRIPTION	""
	::= { mibethernetInterfaceProfileEntry 2 }

    ethernetInterfaceProfile-Item-o	OBJECT-TYPE
	SYNTAX	INTEGER
	ACCESS	read-only
	STATUS	mandatory
	DESCRIPTION	""
	::= { mibethernetInterfaceProfileEntry 3 }

    ethernetInterfaceProfile-InterfaceAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibethernetInterfaceProfileEntry 4 }

    ethernetInterfaceProfile-InterfaceAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibethernetInterfaceProfileEntry 5 }

    ethernetInterfaceProfile-InterfaceAddress-ItemNumber	OBJECT-TYPE
	SYNTAX	INTEGER
	ACCESS	read-write
	STATUS	mandatory
	DESCRIPTION	"A number that specifies an addressable entity within the context of shelf and slot."
	::= { mibethernetInterfaceProfileEntry 6 }

    ethernetInterfaceProfile-LinkStateEnabled	OBJECT-TYPE
	SYNTAX	INTEGER {
		    no (1),
		    yes (2)
		}
	ACCESS	read-write
	STATUS	mandatory
	DESCRIPTION	"TRUE if the link state is honored, otherwise FALSE."
	::= { mibethernetInterfaceProfileEntry 7 }

    ethernetInterfaceProfile-Enabled	OBJECT-TYPE
	SYNTAX	INTEGER {
		    no (1),
		    yes (2)
		}
	ACCESS	read-write
	STATUS	mandatory
	DESCRIPTION	"TRUE if the interface is enabled, otherwise FALSE."
	::= { mibethernetInterfaceProfileEntry 8 }

    ethernetInterfaceProfile-EtherIfType	OBJECT-TYPE
	SYNTAX	INTEGER {
		    aui (1),
		    coax (2),
		    utp (3)
		}
	ACCESS	read-only
	STATUS	mandatory
	DESCRIPTION	"The type of phyical interrface, UTP, COAX, AUI"
	::= { mibethernetInterfaceProfileEntry 9 }

    ethernetInterfaceProfile-Filter	OBJECT-TYPE
	SYNTAX	INTEGER
	ACCESS	read-write
	STATUS	mandatory
	DESCRIPTION	"This field is for non-tnt only"
	::= { mibethernetInterfaceProfileEntry 10 }

    ethernetInterfaceProfile-BridgingEnabled	OBJECT-TYPE
	SYNTAX	INTEGER {
		    no (1),
		    yes (2)
		}
	ACCESS	read-write
	STATUS	mandatory
	DESCRIPTION	"TRUE if this interface is to support bridging."
	::= { mibethernetInterfaceProfileEntry 11 }

    ethernetInterfaceProfile-FilterName	OBJECT-TYPE
	SYNTAX	DisplayString
	ACCESS	read-write
	STATUS	mandatory
	DESCRIPTION	"The name of this filter. All filters are referenced by name so a name must be assigned to active filters."
	::= { mibethernetInterfaceProfileEntry 12 }

    ethernetInterfaceProfile-DuplexMode	OBJECT-TYPE
	SYNTAX	INTEGER {
		    fullDuplex (1),
		    halfDuplex (2)
		}
	ACCESS	read-write
	STATUS	mandatory
	DESCRIPTION	"Set the 100BaseT physical interface to full or half duplex mode. Only valid for the 100BaseT port."
	::= { mibethernetInterfaceProfileEntry 13 }

    ethernetInterfaceProfile-PppoeOptions-Pppoe	OBJECT-TYPE
	SYNTAX	INTEGER {
		    no (1),
		    yes (2)
		}
	ACCESS	read-write
	STATUS	mandatory
	DESCRIPTION	"Enable or disable the ability to establish PPP over Ethernet session over this interface."
	::= { mibethernetInterfaceProfileEntry 14 }

    ethernetInterfaceProfile-PppoeOptions-BridgeNonPppoe	OBJECT-TYPE
	SYNTAX	INTEGER {
		    no (1),
		    yes (2)
		}
	ACCESS	read-write
	STATUS	mandatory
	DESCRIPTION	"States wheather to bridge all other protocols except PPPoE on this interface or not."
	::= { mibethernetInterfaceProfileEntry 15 }

    ethernetInterfaceProfile-BridgingOptions-BridgingGroup	OBJECT-TYPE
	SYNTAX	INTEGER
	ACCESS	read-write
	STATUS	mandatory
	DESCRIPTION	"Select the bridging group for this connection. Group 0 disables bridging. All packets not routed will be bridged to interfaces belonging to the same group."
	::= { mibethernetInterfaceProfileEntry 16 }

    ethernetInterfaceProfile-BridgingOptions-DialOnBroadcast	OBJECT-TYPE
	SYNTAX	INTEGER {
		    no (1),
		    yes (2)
		}
	ACCESS	read-write
	STATUS	mandatory
	DESCRIPTION	"Enable/disable outdial when broadcast frames are received."
	::= { mibethernetInterfaceProfileEntry 17 }

    ethernetInterfaceProfile-BridgingOptions-IpxSpoofing	OBJECT-TYPE
	SYNTAX	INTEGER {
		    none (1),
		    clientSpoofing (2),
		    serverSpoofing (3)
		}
	ACCESS	read-write
	STATUS	mandatory
	DESCRIPTION	"Selects the IPX spoofing mode when bridging."
	::= { mibethernetInterfaceProfileEntry 18 }

    ethernetInterfaceProfile-BridgingOptions-SpoofingTimeout	OBJECT-TYPE
	SYNTAX	INTEGER
	ACCESS	read-write
	STATUS	mandatory
	DESCRIPTION	"IPX NetWare connection timeout value."
	::= { mibethernetInterfaceProfileEntry 19 }

    ethernetInterfaceProfile-BridgingOptions-Fill2	OBJECT-TYPE
	SYNTAX	INTEGER
	ACCESS	read-only
	STATUS	mandatory
	DESCRIPTION	"filler to get to 32 bit boundary"
	::= { mibethernetInterfaceProfileEntry 20 }

    ethernetInterfaceProfile-BridgingOptions-BridgeType	OBJECT-TYPE
	SYNTAX	INTEGER {
		    transparentBridging (1),
		    ipxClientBridging (2),
		    noBridging (3)
		}
	ACCESS	read-write
	STATUS	mandatory
	DESCRIPTION	"For the P25 user interface."
	::= { mibethernetInterfaceProfileEntry 21 }

    ethernetInterfaceProfile-BridgingOptions-Egress	OBJECT-TYPE
	SYNTAX	INTEGER {
		    no (1),
		    yes (2)
		}
	ACCESS	read-write
	STATUS	mandatory
	DESCRIPTION	"Enable/disable Egress on this interface. This interface will become the exit path for all packets destined to the network."
	::= { mibethernetInterfaceProfileEntry 22 }

    ethernetInterfaceProfile-MediaSpeedMbit	OBJECT-TYPE
	SYNTAX	INTEGER {
		    n-10mb (1),
		    n-100mb (2)
		}
	ACCESS	read-write
	STATUS	mandatory
	DESCRIPTION	"Set the BaseT physical interface media speed to 100mb or 10mb. Only valid for the BaseT port on an ether3-card."
	::= { mibethernetInterfaceProfileEntry 23 }

    ethernetInterfaceProfile-AutoNegotiate	OBJECT-TYPE
	SYNTAX	INTEGER {
		    no (1),
		    yes (2)
		}
	ACCESS	read-write
	STATUS	mandatory
	DESCRIPTION	"Set the auto-negotiation option. Only valid for enet3nd-card."
	::= { mibethernetInterfaceProfileEntry 24 }

    ethernetInterfaceProfile-Action-o	OBJECT-TYPE
	SYNTAX	INTEGER {
		    noAction (1),
		    createProfile (2),
		    deleteProfile (3)
		}
	ACCESS	read-write
	STATUS	mandatory
	DESCRIPTION	""
	::= { mibethernetInterfaceProfileEntry 25 }

END
