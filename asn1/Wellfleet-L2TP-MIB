-- @(#)WSCCS q/mibs-l2tp.mib 1.1 4/16/97 
Wellfleet-L2TP-MIB DEFINITIONS ::= BEGIN


    IMPORTS

      IpAddress
        FROM RFC1155-SMI
      OBJECT-TYPE
        FROM RFC-1212
      DisplayString
        FROM RFC1213-MIB
      wfL2TPGroup
        FROM Wellfleet-COMMON-MIB;

-- ========================================================================

    wfTunnelAuthTable OBJECT-TYPE
        SYNTAX	SEQUENCE OF WfTunnelAuthEntry
        ACCESS	not-accessible
        STATUS	mandatory
        DESCRIPTION
                "Infomation used for tunnel authentication between the LAC and LNS"
        ::= { wfL2TPGroup 1 }

    wfTunnelAuthEntry OBJECT-TYPE
        SYNTAX	WfTunnelAuthEntry
        ACCESS	not-accessible
        STATUS	mandatory
        DESCRIPTION
                "An entry defining a tunnel authentication entity"
        INDEX	{ wfTunnelAuthSlot,
                  wfTunnelAuthInstance }
        ::= { wfTunnelAuthTable 1 }

    WfTunnelAuthEntry ::= SEQUENCE {
            wfTunnelAuthDelete
                INTEGER,
            wfTunnelAuthDisable
                INTEGER,
            wfTunnelAuthSlot
                INTEGER,
            wfTunnelAuthInstance
                INTEGER,
            wfTunnelAuthSecret
                DisplayString 
        }

    wfTunnelAuthDelete OBJECT-TYPE
        SYNTAX	INTEGER {
    		    created(1),
    		    deleted(2)
    		}
        ACCESS	read-write
        STATUS	mandatory
        DESCRIPTION
                "Creation and deletion flag for this record"
        DEFVAL	{ created }
        ::= { wfTunnelAuthEntry 1 }

    wfTunnelAuthDisable OBJECT-TYPE
        SYNTAX	INTEGER {
    		    enabled(1),
    		    disabled(2)
    		}
        ACCESS	read-write
        STATUS	mandatory
        DESCRIPTION
                "Disable/Enable the usage of this tunnel authentication entry"
        DEFVAL	{ enabled }
        ::= { wfTunnelAuthEntry 2 }

    wfTunnelAuthSlot OBJECT-TYPE
        SYNTAX  INTEGER
        ACCESS  read-only
        STATUS  mandatory
        DESCRIPTION
                "Slot corresponding to this L2TP configuration"
        ::= { wfTunnelAuthEntry 3 }

    wfTunnelAuthInstance OBJECT-TYPE
        SYNTAX	INTEGER
        ACCESS	read-only
        STATUS	mandatory
        DESCRIPTION
                "The instance index of the authentication entry"
        ::= { wfTunnelAuthEntry 4 }

    wfTunnelAuthSecret OBJECT-TYPE
        SYNTAX	DisplayString
        ACCESS	read-write
        STATUS	mandatory
        DESCRIPTION
                "The tunnel authentication shared secret"
        ::= { wfTunnelAuthEntry 5 }

-- ========================================================================

    wfL2TPTable OBJECT-TYPE
        SYNTAX	SEQUENCE OF WfL2TPEntry
        ACCESS	not-accessible
        STATUS	mandatory
        DESCRIPTION
                "Configuration info for L2TP subsystem running on the slot"
        ::= { wfL2TPGroup 2 }

    wfL2TPEntry OBJECT-TYPE
        SYNTAX	WfL2TPEntry
        ACCESS	not-accessible
        STATUS	mandatory
        DESCRIPTION
                "There is a per slot L2TP entry for every slot configured with L2TP"
        INDEX	{ wfL2TPSlot }
        ::= { wfL2TPTable 1 }

    WfL2TPEntry ::= SEQUENCE {
            wfL2TPDelete
                INTEGER,
            wfL2TPDisable
                INTEGER,
            wfL2TPLnsAddr
                IpAddress,
            wfL2TPIPstate
                INTEGER,
            wfL2TPSlot
                INTEGER,
            wfL2TPReceiveWindowSize
                INTEGER,
            wfL2TPRetransmitTimer
                INTEGER,
            wfL2TPMaxRetransmit
                INTEGER,
            wfL2TPHelloTimer
                INTEGER,
            wfL2TPAckTimer
                INTEGER,
            wfL2TPAckLastNPkts
                INTEGER,
            wfL2TPLnsHostName
                DisplayString, 
            wfL2TPTunnelInfo
                INTEGER,
            wfL2TPSessionInfo
                INTEGER,
            wfL2TPDebugFlag
                INTEGER,
            wfL2TPMaxSession
                INTEGER,
            wfL2TPPortCfgMask
                INTEGER,
            wfL2TPIpAddr
                IpAddress,
            wfL2TPIpCctNum
                INTEGER,
            wfL2TPTunnelDataFlowControl
                INTEGER,
            wfL2TPRemoveDomainName
                INTEGER,
            wfL2TPDomainNameDelimiter
                DisplayString,
            wfL2TPNsaOrigin
                INTEGER,
            wfL2TPNsaPrimaryDNS
                IpAddress,
            wfL2TPNsaSecondaryDNS
                IpAddress,
            wfL2TPNsaPrimaryNBNS
                IpAddress,
            wfL2TPNsaSecondaryNBNS
                IpAddress
        }

    wfL2TPDelete OBJECT-TYPE
        SYNTAX	INTEGER {
    		    created(1),
    		    deleted(2)
    		}
        ACCESS	read-write
        STATUS	mandatory
        DESCRIPTION
                "Creation and deletion flag for this record"
        DEFVAL	{ created }
        ::= { wfL2TPEntry 1 }

    wfL2TPDisable OBJECT-TYPE
        SYNTAX	INTEGER {
    		    enabled(1),
    		    disabled(2)
    		}
        ACCESS	read-write
        STATUS	mandatory
        DESCRIPTION
                "`Enable/Disable L2TP'"
        DEFVAL	{ enabled }
        ::= { wfL2TPEntry 2 }

    wfL2TPLnsAddr OBJECT-TYPE
        SYNTAX	IpAddress
        ACCESS	read-write
        STATUS	mandatory
        DESCRIPTION
                "`IP address of the LNS (Note: this must be unique per slot)'"
        ::= { wfL2TPEntry 3 }

    wfL2TPIPstate OBJECT-TYPE
        SYNTAX	INTEGER
        ACCESS	read-only
        STATUS	mandatory
        DESCRIPTION
                "`State of WAN IP address for the LNS'"
        ::= { wfL2TPEntry 4 }

    wfL2TPSlot OBJECT-TYPE
        SYNTAX	INTEGER
        ACCESS	read-only
        STATUS	mandatory
        DESCRIPTION
                "Slot on which L2TP is configured"
        ::= { wfL2TPEntry 5 }

    wfL2TPReceiveWindowSize OBJECT-TYPE
        SYNTAX  INTEGER
        ACCESS  read-write
        STATUS  mandatory
        DESCRIPTION
                "The recieve window size for tunnel creation in the slot"
        DEFVAL  { 4 }
        ::= { wfL2TPEntry 6 }

    wfL2TPRetransmitTimer OBJECT-TYPE
        SYNTAX  INTEGER
        ACCESS  read-write
        STATUS  mandatory
        DESCRIPTION
                "The time period in sec to wait for an ACK before retransmission." 
        DEFVAL  { 1 }
        ::= { wfL2TPEntry 7 }

    wfL2TPMaxRetransmit OBJECT-TYPE
        SYNTAX  INTEGER
        ACCESS  read-write
        STATUS  mandatory
        DESCRIPTION
                "The max number of retransmission allowed."
        DEFVAL  { 5 }
        ::= { wfL2TPEntry 8 }

    wfL2TPHelloTimer OBJECT-TYPE
        SYNTAX  INTEGER
        ACCESS  read-write
        STATUS  mandatory
        DESCRIPTION
                "The time period in sec of tunnel inactivity before sending a Hello.
                 The draft says 60sec."
        DEFVAL  { 60 }
        ::= { wfL2TPEntry 9 }

    wfL2TPAckTimer OBJECT-TYPE
        SYNTAX  INTEGER
        ACCESS  read-write
        STATUS  mandatory
        DESCRIPTION
                "The max amount of delay in mini-seconds before sending an Ack."
        DEFVAL  { 250 }
        ::= { wfL2TPEntry 10 }

    wfL2TPAckLastNPkts OBJECT-TYPE
        SYNTAX  INTEGER 
        ACCESS  read-write
        STATUS  mandatory
        DESCRIPTION
                ""
        DEFVAL  { 200 }
        ::= { wfL2TPEntry 11 }

    wfL2TPLnsHostName OBJECT-TYPE
        SYNTAX  DisplayString
        ACCESS  read-write
        STATUS  mandatory
        DESCRIPTION
                "To host name used in the Host Name AVP of the LNS" 
        ::= { wfL2TPEntry 12 }

    wfL2TPTunnelInfo OBJECT-TYPE
        SYNTAX  INTEGER {
                    enabled(1),
                    disabled(2)
                }
        ACCESS  read-write
        STATUS  mandatory
        DESCRIPTION
                "To enable or disable the creation of TunnelInfoEntry." 
        DEFVAL  { enabled }
        ::= { wfL2TPEntry 13 }

    wfL2TPSessionInfo OBJECT-TYPE
        SYNTAX  INTEGER {
                    enabled(1),
                    disabled(2)
                }
        ACCESS  read-write
        STATUS  mandatory
        DESCRIPTION
                "To enable or disable the creation of SessionInfoEntry." 
        DEFVAL  { enabled }
        ::= { wfL2TPEntry 14 }

    wfL2TPDebugFlag OBJECT-TYPE
        SYNTAX  INTEGER
        ACCESS  read-write
        STATUS  mandatory
        DESCRIPTION
                "The switch to control the level of debug info" 
        DEFVAL  { 0 }
        ::= { wfL2TPEntry 15 }

    wfL2TPMaxSession OBJECT-TYPE
        SYNTAX  INTEGER
        ACCESS  read-write
        STATUS  mandatory
        DESCRIPTION
                "The max session/call allowed" 
        DEFVAL  { 100 }
        ::= { wfL2TPEntry 16 }

    wfL2TPPortCfgMask OBJECT-TYPE
        SYNTAX  INTEGER
        ACCESS  read-write
        STATUS  mandatory
        DESCRIPTION
                "Used by SM to indicate the port being configured with L2TP" 
        DEFVAL  { 0 }
        ::= { wfL2TPEntry 17 }

    wfL2TPIpAddr OBJECT-TYPE
        SYNTAX  IpAddress
        ACCESS  read-write
        STATUS  mandatory
        DESCRIPTION
                "IP address of the L2TP_IP interface for the slot"
        ::= { wfL2TPEntry 18 }

    wfL2TPIpCctNum OBJECT-TYPE
        SYNTAX  INTEGER
        ACCESS  read-write
        STATUS  mandatory
        DESCRIPTION
                "The circuit number of the L2TP_IP interface for the slot"
        DEFVAL  { 0 }
        ::= { wfL2TPEntry 19 }

    wfL2TPTunnelDataFlowControl OBJECT-TYPE
        SYNTAX	INTEGER {
    		    enabled(1),
    		    disabled(2)
    		}
        ACCESS	read-write
        STATUS	mandatory
        DESCRIPTION
                "This object determines whether or not L2TP is
                 to use flow control on the tunneled data packets. "
        DEFVAL	{ disabled }
        ::= { wfL2TPEntry 20 }

    wfL2TPRemoveDomainName OBJECT-TYPE
        SYNTAX	INTEGER {
    		    enabled(1),
    		    disabled(2)
    		}
        ACCESS	read-write
        STATUS	mandatory
        DESCRIPTION
                "This object determines whether or not to remove the
                 domain name from the complete username (before RADIUS
				 authentication)."
        DEFVAL	{ enabled }
        ::= { wfL2TPEntry 21 }

    wfL2TPDomainNameDelimiter OBJECT-TYPE
        SYNTAX	DisplayString
        ACCESS	read-write
        STATUS	mandatory
        DESCRIPTION
                "This character identifies the delimiter used to separate
                 the domain name from the username and is used in conjunction
				 with the RemoveDomainName feature above."
        DEFVAL	{ "@" }
        ::= { wfL2TPEntry 22 }


    wfL2TPNsaOrigin OBJECT-TYPE
        SYNTAX	INTEGER {
    		    disabled(1),
		    local(2),
    		    radius(3)
    		}
        ACCESS	read-write
        STATUS	mandatory
        DESCRIPTION
                "This object determines where the Name Server Addresses will
                 originate from, or if the feature is to be disabled.  It can
                 take on the following values and meaning: 
                 1 indicates Name Server Addresses are to be disabled. 
                 2 indicates Local origin from Site Manager. 
                 3 indicates remote origin from a RADIUS Server."
        DEFVAL	{ disabled }
        ::= { wfL2TPEntry 23 }

    wfL2TPNsaPrimaryDNS OBJECT-TYPE
        SYNTAX	IpAddress
        ACCESS	read-write
        STATUS	mandatory
        DESCRIPTION
                "Primary DNS Server Address"
        ::= { wfL2TPEntry 24 }

    wfL2TPNsaSecondaryDNS OBJECT-TYPE
        SYNTAX	IpAddress
        ACCESS	read-write
        STATUS	mandatory
        DESCRIPTION
                "Secondary DNS Server Address"
        ::= { wfL2TPEntry 25 }

    wfL2TPNsaPrimaryNBNS OBJECT-TYPE
        SYNTAX	IpAddress
        ACCESS	read-write
        STATUS	mandatory
        DESCRIPTION
                "Primary NBNS Server Address"
        ::= { wfL2TPEntry 26 }

    wfL2TPNsaSecondaryNBNS OBJECT-TYPE
        SYNTAX	IpAddress
        ACCESS	read-write
        STATUS	mandatory
        DESCRIPTION
                "Secondary NBNS Server Address"
        ::= { wfL2TPEntry 27 }


-- ========================================================================


    wfTunnelCircuitTable OBJECT-TYPE
        SYNTAX	SEQUENCE OF WfTunnelCircuitEntry
        ACCESS	not-accessible
        STATUS	mandatory
        DESCRIPTION
                "The circuit entry used for L2TP on the slot"
        ::= { wfL2TPGroup 3 }

    wfTunnelCircuitEntry OBJECT-TYPE
        SYNTAX	WfTunnelCircuitEntry
        ACCESS	not-accessible
        STATUS	mandatory
        DESCRIPTION
                "An entry defining circuits specified for L2TP "
        INDEX	{ wfTunnelCircuitNum }
        ::= { wfTunnelCircuitTable 1 }

    WfTunnelCircuitEntry ::= SEQUENCE {
            wfTunnelCircuitDelete
                INTEGER,
            wfTunnelCircuitNum
                INTEGER,
            wfTunnelCircuitSlot
                INTEGER
        }

    wfTunnelCircuitDelete OBJECT-TYPE
        SYNTAX	INTEGER {
    		    created(1),
    		    deleted(2)
    		}
        ACCESS	read-write
        STATUS	mandatory
        DESCRIPTION
                "Creation and deletion flag for this record"
        DEFVAL	{ created }
        ::= { wfTunnelCircuitEntry 1 }

    wfTunnelCircuitNum OBJECT-TYPE
        SYNTAX	INTEGER
        ACCESS	read-only
        STATUS	mandatory
        DESCRIPTION
                "Tunnel Circuit Number"
        ::= { wfTunnelCircuitEntry 2 }

    wfTunnelCircuitSlot OBJECT-TYPE
        SYNTAX  INTEGER
        ACCESS  read-write
        STATUS  mandatory
        DESCRIPTION
                "The slot on which tunnel Circuit resides" 
        ::= { wfTunnelCircuitEntry 3 }


-- ========================================================================

    wfL2TPStatsTable OBJECT-TYPE
        SYNTAX  SEQUENCE OF WfL2TPStatsEntry
        ACCESS  not-accessible
        STATUS  mandatory
        DESCRIPTION
                ""
        ::= { wfL2TPGroup 4 }

    wfL2TPStatsEntry OBJECT-TYPE
        SYNTAX  WfL2TPStatsEntry
        ACCESS  not-accessible
        STATUS  mandatory
        DESCRIPTION
                "An entry storing L2TP statistics"
        INDEX   { wfL2TPStatsSlot }
        ::= { wfL2TPStatsTable 1 }

    WfL2TPStatsEntry ::= SEQUENCE {
	wfL2TPStatsCreate
                INTEGER,
	wfL2TPStatsSlot
                INTEGER,
	wfL2TPStatsIpAddress
                IpAddress,
	wfL2TPStatsValidSccrq
                INTEGER,
	wfL2TPStatsValidScccn
                INTEGER,
	wfL2TPStatsValidIcrq
                INTEGER,
	wfL2TPStatsValidIccn
                INTEGER,
	wfL2TPStatsInvalidSccrq
                INTEGER,
	wfL2TPStatsInvalidScccn
                INTEGER,
	wfL2TPStatsInvalidIcrq
                INTEGER,
	wfL2TPStatsInvalidIccn
                INTEGER,
	wfL2TPStatsSuccessTunnelAuth
                INTEGER,
	wfL2TPStatsSuccessSessionAuth
                INTEGER,
	wfL2TPStatsFailTunnelAuth
                INTEGER,
	wfL2TPStatsFailSessionAuth
                INTEGER,
	wfL2TPStatsActiveTunnelCount
                INTEGER,
	wfL2TPStatsActiveSessionCount
                INTEGER,
    wfL2TPStatsDropInCtrlPktCount
                INTEGER,
    wfL2TPStatsDropInPayloadPktCount
                INTEGER,
    wfL2TPStatsHelloPktTxCount
                INTEGER,
    wfL2TPStatsHelloPktRxCount
                INTEGER,
    wfL2TPStatsCdnPktTxCount
                INTEGER,
    wfL2TPStatsCdnPktRxCount
                INTEGER,
    wfL2TPStatsStopCCNPktTxCount
                INTEGER,
    wfL2TPStatsStopCCNPktRxCount
                INTEGER
	}

      wfL2TPStatsCreate  OBJECT-TYPE
        SYNTAX  INTEGER {
                    created(1),
                    deleted(2)
                }
        ACCESS  read-write
        STATUS  mandatory
        DESCRIPTION
                "Creation and deletion flag for this record"
        DEFVAL  { created }
        ::= { wfL2TPStatsEntry 1 }

      wfL2TPStatsSlot OBJECT-TYPE  
        SYNTAX  INTEGER
        ACCESS  read-only
        STATUS  mandatory
        DESCRIPTION
                "Enable and disable flag for this record"
        ::= { wfL2TPStatsEntry 2 }

      wfL2TPStatsIpAddress  OBJECT-TYPE
        SYNTAX  IpAddress
        ACCESS  read-only
        STATUS  mandatory
        DESCRIPTION
                "L2TP LNS IP address"
        ::= { wfL2TPStatsEntry 3 }

      wfL2TPStatsValidSccrq  OBJECT-TYPE
        SYNTAX  INTEGER
        ACCESS  read-only
        STATUS  mandatory
        DESCRIPTION
                "L2TP Stats"
        ::= { wfL2TPStatsEntry 4 }

      wfL2TPStatsValidScccn  OBJECT-TYPE
        SYNTAX  INTEGER
        ACCESS  read-only
        STATUS  mandatory
        DESCRIPTION
                "L2TP Stats"
        ::= { wfL2TPStatsEntry 5 }

      wfL2TPStatsValidIcrq  OBJECT-TYPE
        SYNTAX  INTEGER
        ACCESS  read-only
        STATUS  mandatory
        DESCRIPTION
                "L2TP Stats"
        ::= { wfL2TPStatsEntry 6 }

      wfL2TPStatsValidIccn  OBJECT-TYPE
        SYNTAX  INTEGER
        ACCESS  read-only
        STATUS  mandatory
        DESCRIPTION
                "L2TP Stats"
        ::= { wfL2TPStatsEntry 7 }

      wfL2TPStatsInvalidSccrq  OBJECT-TYPE
        SYNTAX  INTEGER
        ACCESS  read-only
        STATUS  mandatory
        DESCRIPTION
                "L2TP Stats"
        ::= { wfL2TPStatsEntry 8 }

      wfL2TPStatsInvalidScccn  OBJECT-TYPE
        SYNTAX  INTEGER
        ACCESS  read-only
        STATUS  mandatory
        DESCRIPTION
                "L2TP Stats"
        ::= { wfL2TPStatsEntry 9 }

      wfL2TPStatsInvalidIcrq  OBJECT-TYPE
        SYNTAX  INTEGER
        ACCESS  read-only
        STATUS  mandatory
        DESCRIPTION
                "L2TP Stats"
        ::= { wfL2TPStatsEntry 10 }

      wfL2TPStatsInvalidIccn   OBJECT-TYPE
        SYNTAX  INTEGER
        ACCESS  read-only
        STATUS  mandatory
        DESCRIPTION
                "L2TP Stats"
        ::= { wfL2TPStatsEntry 11 }

      wfL2TPStatsSuccessTunnelAuth  OBJECT-TYPE
        SYNTAX  INTEGER
        ACCESS  read-only
        STATUS  mandatory
        DESCRIPTION
                "L2TP Stats"
        ::= { wfL2TPStatsEntry 12 }

      wfL2TPStatsSuccessSessionAuth  OBJECT-TYPE
        SYNTAX  INTEGER
        ACCESS  read-only
        STATUS  mandatory
        DESCRIPTION
                "L2TP Stats"
        ::= { wfL2TPStatsEntry 13 }

      wfL2TPStatsFailTunnelAuth  OBJECT-TYPE
        SYNTAX  INTEGER
        ACCESS  read-only
        STATUS  mandatory
        DESCRIPTION
                "L2TP Stats"
        ::= { wfL2TPStatsEntry 14 }

      wfL2TPStatsFailSessionAuth  OBJECT-TYPE
        SYNTAX  INTEGER
        ACCESS  read-only
        STATUS  mandatory
        DESCRIPTION
                "L2TP Stats"
        ::= { wfL2TPStatsEntry 15 }

      wfL2TPStatsActiveTunnelCount  OBJECT-TYPE
        SYNTAX  INTEGER
        ACCESS  read-only
        STATUS  mandatory
        DESCRIPTION
                "L2TP Stats"
        ::= { wfL2TPStatsEntry 16 }

      wfL2TPStatsActiveSessionCount  OBJECT-TYPE
        SYNTAX  INTEGER
        ACCESS  read-only
        STATUS  mandatory
        DESCRIPTION
                "L2TP Stats"
        ::= { wfL2TPStatsEntry 17 }

      wfL2TPStatsDropInCtrlPktCount  OBJECT-TYPE
        SYNTAX  INTEGER
        ACCESS  read-only
        STATUS  mandatory
        DESCRIPTION
                "Total number of invalid L2TP control pkts being dropped."
        ::= { wfL2TPStatsEntry 18 }

      wfL2TPStatsDropInPayloadPktCount  OBJECT-TYPE
        SYNTAX  INTEGER
        ACCESS  read-only
        STATUS  mandatory
        DESCRIPTION
                "Total number of invalid L2TP payload lpkts being dropped."
        ::= { wfL2TPStatsEntry 19 }

      wfL2TPStatsHelloPktTxCount  OBJECT-TYPE
        SYNTAX  INTEGER
        ACCESS  read-only
        STATUS  mandatory
        DESCRIPTION
                "Total number of HELLO pkts transmitted."
        ::= { wfL2TPStatsEntry 20 }

      wfL2TPStatsHelloPktRxCount  OBJECT-TYPE
        SYNTAX  INTEGER
        ACCESS  read-only
        STATUS  mandatory
        DESCRIPTION
                "Total number of HELLO pkts received."
        ::= { wfL2TPStatsEntry 21 }

      wfL2TPStatsCdnPktTxCount  OBJECT-TYPE
        SYNTAX  INTEGER
        ACCESS  read-only
        STATUS  mandatory
        DESCRIPTION
                "Total number of CDN pkts transmitted."
        ::= { wfL2TPStatsEntry 22 }

      wfL2TPStatsCdnPktRxCount  OBJECT-TYPE
        SYNTAX  INTEGER
        ACCESS  read-only
        STATUS  mandatory
        DESCRIPTION
                "Total number of CDN pkts received."
        ::= { wfL2TPStatsEntry 23 }

      wfL2TPStatsStopCCNPktTxCount  OBJECT-TYPE
        SYNTAX  INTEGER
        ACCESS  read-only
        STATUS  mandatory
        DESCRIPTION
                "Total number of StopCCN pkts transmitted."
        ::= { wfL2TPStatsEntry 24 }

      wfL2TPStatsStopCCNPktRxCount  OBJECT-TYPE
        SYNTAX  INTEGER
        ACCESS  read-only
        STATUS  mandatory
        DESCRIPTION
                "Total number of StopCCN pkts received."
        ::= { wfL2TPStatsEntry 25 }

-- ========================================================================

     wfL2TPTunnelInfoTable OBJECT-TYPE
        SYNTAX  SEQUENCE OF WfL2TPTunnelInfoEntry 
        ACCESS  not-accessible
        STATUS  mandatory
        DESCRIPTION
                "Infomation related to the active tunnel"
        ::= { wfL2TPGroup 5 }

     wfL2TPTunnelInfoEntry OBJECT-TYPE	
        SYNTAX  WfL2TPTunnelInfoEntry
        ACCESS  not-accessible
        STATUS  mandatory
        DESCRIPTION
                "Info entry for each active L2TP tunnel"
        INDEX   { wfL2TPTunnelInfoSlot,
                  wfL2TPTunnelInfoLnsTunnelId }
        ::= { wfL2TPTunnelInfoTable 1 }

     WfL2TPTunnelInfoEntry ::= SEQUENCE {
	wfL2TPTunnelInfoSlot
                INTEGER,
	wfL2TPTunnelInfoLnsTunnelId
                INTEGER,
        wfL2TPTunnelInfoLacTunnelId
                INTEGER,
	wfL2TPTunnelInfoLnsAddress
                IpAddress,
	wfL2TPTunnelInfoLacAddress
                IpAddress,
	wfL2TPTunnelInfoFramingCap
                INTEGER,
	wfL2TPTunnelInfoBearerCap
                INTEGER,
	wfL2TPTunnelInfoLacVendorName
                DisplayString,
	wfL2TPTunnelInfoLacHostName
                DisplayString,
	wfL2TPTunnelInfoRecvWindowSize
                INTEGER,
	wfL2TPTunnelInfoActiveSessionCount
                INTEGER,
	wfL2TPTunnelInfoFirmwareRevision
                INTEGER
	}

     wfL2TPTunnelInfoSlot OBJECT-TYPE
        SYNTAX  INTEGER
        ACCESS  read-only
        STATUS  mandatory
        DESCRIPTION
                "Slot nubmer"
        ::= { wfL2TPTunnelInfoEntry 1 }

     wfL2TPTunnelInfoLnsTunnelId OBJECT-TYPE
        SYNTAX  INTEGER
        ACCESS  read-only
        STATUS  mandatory
        DESCRIPTION
                "The tunnel ID assigned by LNS"
        ::= { wfL2TPTunnelInfoEntry 2 }

     wfL2TPTunnelInfoLacTunnelId OBJECT-TYPE
        SYNTAX  INTEGER
        ACCESS  read-only
        STATUS  mandatory
        DESCRIPTION
                "The tunnel ID  assigned by LAC"
        ::= { wfL2TPTunnelInfoEntry 3 }

     wfL2TPTunnelInfoLnsAddress OBJECT-TYPE
        SYNTAX  IpAddress
        ACCESS  read-only
        STATUS  mandatory
        DESCRIPTION
                "IP address of the tunnel LNS endpoint"
        ::= { wfL2TPTunnelInfoEntry 4 }

     wfL2TPTunnelInfoLacAddress OBJECT-TYPE
        SYNTAX  IpAddress
        ACCESS  read-only
        STATUS  mandatory
        DESCRIPTION
                "IP address of the tunnel LAC endpoint"
        ::= { wfL2TPTunnelInfoEntry 5 }

     wfL2TPTunnelInfoFramingCap OBJECT-TYPE
        SYNTAX  INTEGER
        ACCESS  read-only
        STATUS  mandatory
        DESCRIPTION
                "1 = Synchronous, 2 = Asynchronous, 3 = Both"
        ::= { wfL2TPTunnelInfoEntry 6 }

     wfL2TPTunnelInfoBearerCap OBJECT-TYPE
        SYNTAX  INTEGER
        ACCESS  read-only
        STATUS  mandatory
        DESCRIPTION
                "1 = Digital, 2 = Analog, 3 = Both"
        ::= { wfL2TPTunnelInfoEntry 7 }

     wfL2TPTunnelInfoLacVendorName OBJECT-TYPE
        SYNTAX  DisplayString
        ACCESS  read-only
        STATUS  mandatory
        DESCRIPTION
                "The Vendor Name used in the tunnel SCCRQ message"
        ::= { wfL2TPTunnelInfoEntry 8 }

     wfL2TPTunnelInfoLacHostName OBJECT-TYPE
        SYNTAX  DisplayString
        ACCESS  read-only
        STATUS  mandatory
        DESCRIPTION
                "The Host name used in the tunnel SCCRQ message"
        ::= { wfL2TPTunnelInfoEntry 9 }

     wfL2TPTunnelInfoRecvWindowSize OBJECT-TYPE
        SYNTAX  INTEGER
        ACCESS  read-only
        STATUS  mandatory
        DESCRIPTION
                "The Receive Window Size used in the tunnel SCCRQ message"
        ::= { wfL2TPTunnelInfoEntry 10 }

     wfL2TPTunnelInfoActiveSessionCount OBJECT-TYPE
        SYNTAX  INTEGER
        ACCESS  read-only
        STATUS  mandatory
        DESCRIPTION
                "The total number of active session in the tunnel"
        ::= { wfL2TPTunnelInfoEntry 11 }

     wfL2TPTunnelInfoFirmwareRevision OBJECT-TYPE
        SYNTAX  INTEGER
        ACCESS  read-only
        STATUS  mandatory
        DESCRIPTION
                "The Firmware Revision used in the tunnel SCCRQ message"
        ::= { wfL2TPTunnelInfoEntry 12 }


-- ========================================================================

     wfL2TPSessionInfoTable OBJECT-TYPE
        SYNTAX  SEQUENCE OF WfL2TPSessionInfoEntry
        ACCESS  not-accessible
        STATUS  mandatory
        DESCRIPTION
                "Infomation related to the active session"
        ::= { wfL2TPGroup 6 }

     wfL2TPSessionInfoEntry OBJECT-TYPE
        SYNTAX  WfL2TPSessionInfoEntry
        ACCESS  not-accessible
        STATUS  mandatory
        DESCRIPTION
                "Info entry for each active L2TP session"
        INDEX   { wfL2TPSessionInfoSlot,
                  wfL2TPSessionInfoLnsTunnelId,
                  wfL2TPSessionInfoLnsCallId }
        ::= { wfL2TPSessionInfoTable 1 }

     WfL2TPSessionInfoEntry ::= SEQUENCE {
	wfL2TPSessionInfoSlot
                INTEGER,
	wfL2TPSessionInfoLnsTunnelId
                INTEGER,
	wfL2TPSessionInfoLacTunnelId
                INTEGER,
	wfL2TPSessionInfoLnsCallId
                INTEGER,
	wfL2TPSessionInfoLacCallId
                INTEGER,
	wfL2TPSessionInfoCallSerialNum
                DisplayString,
	wfL2TPSessionInfoCallBearerType
                INTEGER,
	wfL2TPSessionInfoDialingNum
                DisplayString,
	wfL2TPSessionInfoDialedNum
                DisplayString,
	wfL2TPSessionInfoSubAddress
                DisplayString,
	wfL2TPSessionInfoConnectSpeed
                INTEGER,
	wfL2TPSessionInfoFramingType
                INTEGER,
	wfL2TPSessionInfoLocalRecvPktWindow
                INTEGER,
	wfL2TPSessionInfoRemoteRecvPktWindow
                INTEGER,
	wfL2TPSessionInfoPhysicalChannelId
                INTEGER,
	wfL2TPSessionInfoNextSendSeq
                INTEGER,
	wfL2TPSessionInfoNextSendSeqAck
                INTEGER,
	wfL2TPSessionInfoNextRecvSeq
                INTEGER,
	wfL2TPSessionInfoNextRecvSeqAck
                INTEGER,
	wfL2TPSessionInfoAssignedIpAddress
                IpAddress,
	wfL2TPSessionInfoUsername
                DisplayString,
	wfL2TPSessionInfoTxPackets
                INTEGER,
	wfL2TPSessionInfoRxPackets
                INTEGER,
	wfL2TPSessionInfoConnectTime
                INTEGER
	}

     wfL2TPSessionInfoSlot OBJECT-TYPE
        SYNTAX  INTEGER
        ACCESS  read-only
        STATUS  mandatory
        DESCRIPTION
                "The slot nubmer where the session resides"
        ::= { wfL2TPSessionInfoEntry 1 }

     wfL2TPSessionInfoLnsTunnelId OBJECT-TYPE
        SYNTAX  INTEGER
        ACCESS  read-only
        STATUS  mandatory
        DESCRIPTION
                "Tunnel ID of the tunnel that the session is on."
        ::= { wfL2TPSessionInfoEntry 2 }

     wfL2TPSessionInfoLacTunnelId OBJECT-TYPE
        SYNTAX  INTEGER
        ACCESS  read-only
        STATUS  mandatory
        DESCRIPTION
                "Tunnel ID of the tunnel that the session is on."
        ::= { wfL2TPSessionInfoEntry 3 }

     wfL2TPSessionInfoLnsCallId OBJECT-TYPE
        SYNTAX  INTEGER
        ACCESS  read-only
        STATUS  mandatory
        DESCRIPTION
                "The call ID assigned by the LNS"
        ::= { wfL2TPSessionInfoEntry 4 }

     wfL2TPSessionInfoLacCallId OBJECT-TYPE
        SYNTAX  INTEGER
        ACCESS  read-only
        STATUS  mandatory
        DESCRIPTION
                "The call ID assigned by the LAC in the ICRQ message"
        ::= { wfL2TPSessionInfoEntry 5 }

     wfL2TPSessionInfoCallSerialNum OBJECT-TYPE
        SYNTAX  DisplayString
        ACCESS  read-only
        STATUS  mandatory
        DESCRIPTION
                "The Call Serial Number used in the ICRQ message"
        ::= { wfL2TPSessionInfoEntry 6 }

     wfL2TPSessionInfoCallBearerType OBJECT-TYPE
        SYNTAX  INTEGER
        ACCESS  read-only
        STATUS  mandatory
        DESCRIPTION
                "The Bearer Type used in the ICRQ message"
        ::= { wfL2TPSessionInfoEntry 7 }

     wfL2TPSessionInfoDialingNum OBJECT-TYPE
        SYNTAX  DisplayString
        ACCESS  read-only
        STATUS  mandatory
        DESCRIPTION
                "The Dialing Number used in the ICRQ message"
        ::= { wfL2TPSessionInfoEntry 8 }

     wfL2TPSessionInfoDialedNum OBJECT-TYPE
        SYNTAX  DisplayString
        ACCESS  read-only
        STATUS  mandatory
        DESCRIPTION
                "The Dialed Number used in the ICRQ message"
        ::= { wfL2TPSessionInfoEntry 9 }

     wfL2TPSessionInfoSubAddress OBJECT-TYPE
        SYNTAX  DisplayString
        ACCESS  read-only
        STATUS  mandatory
        DESCRIPTION
                "The subaddress used in the ICRQ message"
        ::= { wfL2TPSessionInfoEntry 10 }

     wfL2TPSessionInfoConnectSpeed OBJECT-TYPE
        SYNTAX  INTEGER
        ACCESS  read-only
        STATUS  mandatory
        DESCRIPTION
                "The Connect Speed used in the ICCN message"
        ::= { wfL2TPSessionInfoEntry 11 }

     wfL2TPSessionInfoFramingType OBJECT-TYPE
        SYNTAX  INTEGER
        ACCESS  read-only
        STATUS  mandatory
        DESCRIPTION
                "The Framing Type used in the ICCN message"
        ::= { wfL2TPSessionInfoEntry 12 }

     wfL2TPSessionInfoLocalRecvPktWindow OBJECT-TYPE
        SYNTAX  INTEGER
        ACCESS  read-only
        STATUS  mandatory
        DESCRIPTION
                "This object contains the local Send Window Size."
        ::= { wfL2TPSessionInfoEntry 13 }

     wfL2TPSessionInfoRemoteRecvPktWindow OBJECT-TYPE
        SYNTAX  INTEGER
        ACCESS  read-only
        STATUS  mandatory
        DESCRIPTION
                "This object contains the remote receive window size."
        ::= { wfL2TPSessionInfoEntry 14 }

     wfL2TPSessionInfoPhysicalChannelId OBJECT-TYPE
        SYNTAX  INTEGER
        ACCESS  read-only
        STATUS  mandatory
        DESCRIPTION
                "This object contains the physical channel identifier 
                 for the session."
        ::= { wfL2TPSessionInfoEntry 15 }

     wfL2TPSessionInfoNextSendSeq OBJECT-TYPE
        SYNTAX  INTEGER
        ACCESS  read-only
        STATUS  mandatory
        DESCRIPTION
                "This object contains the next send sequence number for
                 for this session."
        ::= { wfL2TPSessionInfoEntry 16 }

     wfL2TPSessionInfoNextSendSeqAck OBJECT-TYPE
        SYNTAX  INTEGER
        ACCESS  read-only
        STATUS  mandatory
        DESCRIPTION
                "This object contains the next send acknowledgement
                 for this session."
        ::= { wfL2TPSessionInfoEntry 17 }

     wfL2TPSessionInfoNextRecvSeq OBJECT-TYPE
        SYNTAX  INTEGER
        ACCESS  read-only
        STATUS  mandatory
        DESCRIPTION
                "This object contains the next receive sequence number
                 for this session."
        ::= { wfL2TPSessionInfoEntry 18 }

     wfL2TPSessionInfoNextRecvSeqAck OBJECT-TYPE
        SYNTAX  INTEGER
        ACCESS  read-only
        STATUS  mandatory
        DESCRIPTION
                "This object contains the next receive acknowledgement
                 for this session."
        ::= { wfL2TPSessionInfoEntry 19 }


     wfL2TPSessionInfoAssignedIpAddress OBJECT-TYPE
        SYNTAX  IpAddress
        ACCESS  read-only
        STATUS  mandatory
        DESCRIPTION
                "Address assigned to this session."
        ::= { wfL2TPSessionInfoEntry 20 }

     wfL2TPSessionInfoUsername OBJECT-TYPE
        SYNTAX  DisplayString
        ACCESS  read-only
        STATUS  mandatory
        DESCRIPTION
                "User tunnelled within this session."
        ::= { wfL2TPSessionInfoEntry 21 }

     wfL2TPSessionInfoTxPackets OBJECT-TYPE
        SYNTAX  INTEGER
        ACCESS  read-only
        STATUS  mandatory
        DESCRIPTION
                "Number of outbound data packets for this session."
        ::= { wfL2TPSessionInfoEntry 22 }

     wfL2TPSessionInfoRxPackets OBJECT-TYPE
        SYNTAX  INTEGER
        ACCESS  read-only
        STATUS  mandatory
        DESCRIPTION
                "Number of inbound data packets for this session."
        ::= { wfL2TPSessionInfoEntry 23 }

     wfL2TPSessionInfoConnectTime OBJECT-TYPE
        SYNTAX  INTEGER
        ACCESS  read-only
        STATUS  mandatory
        DESCRIPTION
                "Time the session was started"
        ::= { wfL2TPSessionInfoEntry 24 }

-- ========================================================================


    wfTunnelLineTable OBJECT-TYPE
        SYNTAX  SEQUENCE OF WfTunnelLineEntry
        ACCESS  not-accessible
        STATUS  mandatory
        DESCRIPTION
                "The line entry used for L2TP on the slot"
        ::= { wfL2TPGroup 7 }

    wfTunnelLineEntry OBJECT-TYPE
        SYNTAX  WfTunnelLineEntry
        ACCESS  not-accessible
        STATUS  mandatory
        DESCRIPTION
                "An entry defining lines specified for L2TP "
        INDEX   { wfTunnelLineNum }
        ::= { wfTunnelLineTable 1 }

    WfTunnelLineEntry ::= SEQUENCE {
            wfTunnelLineDelete
                INTEGER,
            wfTunnelLineNum
                INTEGER,
            wfTunnelLineSlot
                INTEGER
        }

    wfTunnelLineDelete OBJECT-TYPE
        SYNTAX  INTEGER {
                    created(1),
                    deleted(2)
                }
        ACCESS  read-write
        STATUS  mandatory
        DESCRIPTION
                "Creation and deletion flag for this record"
        DEFVAL  { created }
        ::= { wfTunnelLineEntry 1 }

    wfTunnelLineNum OBJECT-TYPE
        SYNTAX  INTEGER
        ACCESS  read-only
        STATUS  mandatory
        DESCRIPTION
                "Tunnel Line Number"
        ::= { wfTunnelLineEntry 2 }

    wfTunnelLineSlot OBJECT-TYPE
        SYNTAX  INTEGER
        ACCESS  read-write
        STATUS  mandatory
        DESCRIPTION
                "The slot on which tunnel Line resides"
        ::= { wfTunnelLineEntry 3 }


-- ========================================================================


    END  -- Wellfleet-L2TP-MIB
