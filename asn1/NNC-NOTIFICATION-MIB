-- @(#)Notification.mib	9.2 01/20/99
-- file: Notification.mib
--
-- description:
--  This file contains the SNMP definitions for the Alarm area.  It
--  encapsulates Newbridge alarms and trouble tickets into traps.
--
-- History:
--  0.1 / 1997-01-31 / Connie Chang/ Creation
--  1.0 / 1997-02-10 / Connie Chang/ Updated from SNMPv1 to SNMPv2
--                                   after Reviewed
--  1.1 / 1997-04-22 / Satvinder Singh Bawa/ Update to comply with SQP0053
--
-- Copyright 1997 Newbridge Networks Corporation.  All rights reserved.
-------------------------------------------------------------------------------

NNC-NOTIFICATION-MIB DEFINITIONS ::= BEGIN
  IMPORTS
	MODULE-COMPLIANCE, OBJECT-GROUP FROM SNMPv2-CONF
		DisplayString FROM SNMPv2-TC
    IpAddress
      FROM RFC1155-SMI
    MODULE-IDENTITY, OBJECT-TYPE, TimeTicks, NOTIFICATION-TYPE
      FROM SNMPv2-SMI
    TEXTUAL-CONVENTION
      FROM SNMPv2-TC
    nncExtensions
      FROM NNCGNI00X1-SMI;

        nncExtNotif  MODULE-IDENTITY
                LAST-UPDATED    "9704220000Z"
                ORGANIZATION    "Newbridge Networks Corporation"
                CONTACT-INFO
                                "Newbridge Networks Corporation
                                Postal: 600 March Road
                                Kanata, Ontario
                                Canada K2K 2E6

                                Phone:  +1 613 591 3600
                                Fax:    +1 613 591 3680"

                DESCRIPTION     "This MIB module contains information
                                 regarding Alarm and Trouble Ticket
                                 information forwarding as Notifications."

     ::= { nncExtensions 44 }

        nncExtNotifObjects OBJECT IDENTIFIER     ::=    { nncExtNotif 1 }
        nncExtNotifType    OBJECT IDENTIFIER     ::=    { nncExtNotif 2 }
        nncExtNotifGroups OBJECT IDENTIFIER      ::=    { nncExtNotif 3 }
        nncExtNotifCompliances OBJECT IDENTIFIER ::=    { nncExtNotif 4 }
        nncExtNotifAlarmType OBJECT IDENTIFIER   ::=    { nncExtNotifType 1 }
        nncExtNotifAlarmType-v1Trap OBJECT IDENTIFIER  
						 ::=    { nncExtNotifAlarmType 0 }
        nncExtNotifTroubleTicketType OBJECT IDENTIFIER
                                                 ::=    { nncExtNotifType 2 }
        nncExtNotifTroubleTicketType-v1Trap OBJECT IDENTIFIER
                                                 ::=    { nncExtNotifTroubleTicketType 0 }
        nncExtNotifHeartBeatType OBJECT IDENTIFIER
						 ::=    { nncExtNotifType 3 }
        nncExtNotifHeartBeatType-v1Trap OBJECT IDENTIFIER
						 ::=    { nncExtNotifHeartBeatType 0 }

--
-- Type definitions
--
-- CPSS Network Address Type
  CpssAddress ::= TEXTUAL-CONVENTION
  STATUS          current
  DESCRIPTION     "Type to be used for CPSS address information
                   written into a string."
  SYNTAX          OCTET STRING (SIZE (0..15))

-- String Type
  StringType  ::= TEXTUAL-CONVENTION
  STATUS          current
  DESCRIPTION     "Type used to forward various text fields."
  SYNTAX          DisplayString (SIZE (0..30))

-- Parameter String Type
  ParameterStringType  ::= TEXTUAL-CONVENTION
  STATUS                   current
  DESCRIPTION              "Type used to forward various text fields."
  SYNTAX                   DisplayString (SIZE (0..40))

  -- Newbridge Node Types

  NBNodeType ::= TEXTUAL-CONVENTION
  STATUS         current
  DESCRIPTION    "Newbridge node type related to event."
  SYNTAX         INTEGER {
                       nd4601         (2),    -- 4601 Mainstreet
                       nd46020        (3),    -- 46020 Mainstreet
                       ndTAP          (4),    -- 3500 MainStreet
                       nd3600         (5),    -- 3600 MainStreet
                       nd3612         (6),    -- 3612 MainStreet
                       nd3624         (7),    -- 3624 MainStreet
                       nd3630         (8),    -- 3630 MainStreet
                       nd5601         (9),    -- 5601 MainStreet
                       nd5602        (10),    -- 5602 MainStreet
                       nd5610        (11),    -- 5610 MainStreet
                       nd4601A       (12),    -- 4601A Mainstreet
                       nd3645SU      (13),    -- 3645 SU MainStreet
                       nd3645PU      (14),    -- 3645 PU MainStreet
                       ndGeneric     (15),    -- Generic Node
                       ndDEXCS1S     (16),    -- DEX CS1S
                       nd3645DS3     (17),    -- 3645 DS3
                       ndA3606V      (19),    -- 3606 voice-data variant
                       ndA3606D      (20),    -- 3606 data-only variant
                       ndConnectExec (21),    -- Connect Exec Gateway process
                       nd36120       (22),    -- FASTbus node
                       nd3645E3      (23),    -- E3 node
                       nd36150       (24),    -- 36150 node
                       nd3664        (25),    -- 3664 MainStreet
                       ndTDAX100     (26),    -- TDAX node
                       ndDACSII      (27),    -- DACS II node
                       ndDEXCS1L     (28),    -- DSC DEX CS1L node
                       ndDACSIIProxyAgent(29), -- DACS II Proxy Agent Node
                       ndGenericDCS  (30),    -- DCS MGR
                       nd46020DN     (31),    -- 4602 Delegate NetworkStation
                       nd46020CN     (32),    -- 4602 Customer NetworkStation
                       nd46020RT     (33),    -- 4602 Router   NetworkStation
                       nd3620        (34),    -- 3620 MainStreet
                       nd36170       (35),    -- 36170 ATMnet
                       nd48020       (42),    -- Customer Service Mgmt. Server
                       ndDCS31       (43),    -- Fully Managed DCS 31 Node
                       ndDCS33       (44),    -- Fully Managed DCS 33 Node
                       ndFRATM       (45),    -- 36120-FRATM Mainstreet
                       nd3620Rtr     (54),    -- 3620 Router
                       ndStatsCollector(55),    -- Stats Collector Node
                       ndMVNMatm      (56),   -- Crosskeys MVNM atm node
                       nd3600PLUS    (57),    -- 3600+
                       ndISDNAccess  (58),    -- ISDN access node
                       ndEmMgr       (59),    -- Element Manager Node
                       ndEmGeneric   (60),    -- Element Managed nodes
                       nd2902        (61),    -- 2902 Node
                       nd3606IDSU    (62),    -- 3606/iDSU DDS node
                       nd36130       (63),    -- MainStreetXpress 36130
                       nd1630SX      (64),    -- lcatel 1630 SX
                       nd36125       (65),    -- MainStreetXpress 36125
                       nd36160       (66),    -- 36160 Node - CSI
                       nd36110-8     (67),    -- 36110 node (8 ports)
                       nd36110-20    (68),    -- 36110 node (20 ports)
                       nd36111-24    (69),    -- 36111 node (24 ports)
                       nd36111-80    (70),    -- 336111 node (80 ports)
                       ndIAG         (71),    -- MNSC Imported Access Group
                       ndLAG         (72),    -- MNSC Local Access Group
                       ndMNSC        (73),    -- MNSC NetworkStation
                       ndMNSC-DN     (74),    -- MNSC Delegate NetworkStation
                       ndMNSC-CN     (75),    -- MNSC Customer NetworkStation
                       nd36177       (76)     -- 36177 ATMnet 
                      }

   --
   --
   -- Heartbeat Type
   --
   --

   -- SysDescr Type
   SysDescrType ::= TEXTUAL-CONVENTION
   STATUS                  current
   DESCRIPTION             "Heartbeat SysDescr."
   SYNTAX                  DisplayString (SIZE (0..50))

   --
   --
   -- Alarm Types
   --
   -- Alarm Priority Type

   AlmPriorityType ::= TEXTUAL-CONVENTION
   STATUS              current
   DESCRIPTION         "Different alarm priorities."
   SYNTAX              INTEGER {
                         diagn    (1),
                         minor    (2),
                         major    (3),
                         critical (4)
                      }

   -- A text string stored in unsigned char format for alarm description
   AlmInfoType ::= TEXTUAL-CONVENTION
   STATUS          current
   DESCRIPTION     "Alarm description."
   SYNTAX          StringType

   --
   --
   -- Trouble Ticket Types
   --
   --

   -- Trouble Ticket Fault Location Type
   TTFaultLocationType ::= TEXTUAL-CONVENTION
   STATUS                  current
   DESCRIPTION             "Fault location."
   SYNTAX                  DisplayString (SIZE (0..50))

   -- Trouble Ticket Priority Type
   TTPriorityType ::= TEXTUAL-CONVENTION
   STATUS             current
   DESCRIPTION        "Trouble Ticket Priority."
   SYNTAX             INTEGER {
                         warning  (1),
                         minor    (2),
                         major    (3),
                         critical (4)
                      }

   -- Trouble Ticket Fault Status Type

   TTFaultStatusType ::= TEXTUAL-CONVENTION
   STATUS                current
   DESCRIPTION           "Trouble Ticket Fault Status."
   SYNTAX                INTEGER {
                         recovery      (1), -- In process of recovery
                         isolate       (2), -- In process of fault isolation
                         maintenanc    (3), -- Fixing the isolated fault
                         verify        (4), -- System thinks fault is fixed
                         cleared       (5), -- User verified the fault is fixed
                         user          (6), -- Trouble ticket created by user
                         custom        (7), -- Custom node logged ticket
                         tdaxNode      (8), -- Alarm message from TDAX node
                         dcsNode       (9), -- Alarm message from DCS Manager
                         administrative(10)  -- Administrative
                      }

   -- Trouble Ticket Fault Reason Type

   -- Hardware problems

   TThardwareFaultType ::= TEXTUAL-CONVENTION
   STATUS                  current
   DESCRIPTION         "Trouble Ticket hardware fault."
   SYNTAX              INTEGER {
                       psFailure (1),          -- Power Supply Failure
                       wrongCdInSlot (2),      -- Wrong Card In Slot
                       wrongModOnCd (3),       -- Wrong Module On Card
                       devFailure (4),         -- Device Failure
                       cdFailure (5),          -- Card Failure
                       tailEndCircGone (6),    -- Tail End Circuit Gone
                       cableFailure (7),       -- Cable Failure
                       ringGenFailure (8),     -- Ringing Generator Failure
                       modemIsBusted (9),      -- Modem Is Busted
                       slotIsEmpty (10),       -- Slot Is Empty
                       nvmIntegrityError (11), -- NVM Integrity Error
                       ramIntegrityError (12), -- RAM Integrity Error
                       romIntegrityError (13), -- ROM Integrity Error
                       activitySwitch (14),    -- Activity Switch
                       nodeProblem (15),       -- Node Problem
                       reconcileProblem (16),  -- Reconcile Problem
                       devProblem (17),        -- Device Problem
                       cableProblem (18)      -- Cable Problem
                      }

   -- Software problems

   TTsoftwareFaultType ::= TEXTUAL-CONVENTION
   STATUS                  current
   DESCRIPTION         "Trouble Ticket software fault."
   SYNTAX              INTEGER {
                       alarmQOverflow (1),   -- Alarm Queue Overflow
                       unsupportedCd (2),    -- Unsupported Card
                       unsupportedMod (3),   -- Unsupported Module
                       notConfigLocally (4), -- Not Configured Locally
                       unsupportedStatus (5), -- Unsupported Status
                       alarmProblem (6),     -- Alarm Problem
                       busiedOut (7),        -- Busied Out
                       maximumHops (8),      -- Maximum Hops
                       swDownloadProblem (9) -- Software Download Problem
                      }

   -- Communication problems

   TTcommFaultType ::= TEXTUAL-CONVENTION
   STATUS                  current
   DESCRIPTION         "Trouble Ticket communications fault."
   SYNTAX              INTEGER {
                       cannotTalkToNode (1) -- Cannot Talk To Node
                      }

   -- User problems

   TTuserFaultType ::= TEXTUAL-CONVENTION
   STATUS                  current
   DESCRIPTION         "Trouble Ticket user fault."
   SYNTAX              INTEGER {
                       createdByUser (1),    -- Created By User
                       createdBySystem (2)  -- Created By System
                      }

   -- Custom Node problems
   TTcustomNodeFaultType ::= TEXTUAL-CONVENTION
   STATUS                  current
   DESCRIPTION         "Trouble Ticket custom node fault."
   SYNTAX              INTEGER {
                        gfcAlarm(1),
                        customNodeLog(2)
                       }

   -- LAN node problems

   TTlanNodeFaultType ::= TEXTUAL-CONVENTION
   STATUS                  current
   DESCRIPTION         "Trouble Ticket lan node fault."
   SYNTAX              INTEGER {
                       systemTable     (1),
                       interfaceRow    (2),
                       lanTrap         (3),
                       circuitGroup    (4),
                       lanPath         (5)
                      }

   -- Connect Exec problems

   TTconnectExecFaultType ::= TEXTUAL-CONVENTION
   STATUS                  current
   DESCRIPTION         "Trouble Ticket connect exec fault."
   SYNTAX              INTEGER {
                       mibOutOfSync   (1),   -- MIB Out Of Sync
                       noReload       (2),   -- No Reload
                       reloadMIB      (3),   -- Reload MIB
                       pathProblem    (4),   -- Path Problem
                       chgsrvQOverflow (5),  -- Change Server Queue Overflow
                       abnormalShutdown (6), -- Abnormal Shutdown
                       updateStarted  (7),   -- Update Started
                       reloadAbort    (8)   -- Reload Abort
                      }

   -- TDAX Node problems
   TTtDaxNodeFaultType ::= TEXTUAL-CONVENTION
   STATUS                  current
   DESCRIPTION         "Trouble Ticket T DAX node fault."
   SYNTAX              INTEGER {
                        nodeAlarm  (1),
                        shelfAlarm (2),
                        cardAlarm (3),
                        portAlarm (4)
                       }

   -- DCS Manager problems
   TTdcsNodeFaultType ::= TEXTUAL-CONVENTION
   STATUS                  current
   DESCRIPTION         "Trouble Ticket DCS node fault."
   SYNTAX              INTEGER {
                        nodeAlarm  (1),
                        shelfAlarm (2),
                        cardAlarm  (3),
                        portAlarm  (4)
                       }

   -- Administrative problems

   TTadminFaultType ::= TEXTUAL-CONVENTION
   STATUS                  current
   DESCRIPTION         "Trouble Ticket administrative fault."
   SYNTAX              INTEGER {
                       passwdViolation (1),   -- Password Violation
                       licenseViolation (2),  -- License Violation
                       invalidLicenseKey (3) -- Invalid License Key
                      }

   -- SSDH Ring Problems

   TTssdhRingFaultType ::= TEXTUAL-CONVENTION
   STATUS                  current
   DESCRIPTION         "Trouble Ticket sonet ring fault."
   SYNTAX              INTEGER {
                        upsrProblem(1)
                       }


  -- External Alarm reception
  TTextNodeFaultType ::= TEXTUAL-CONVENTION
   STATUS                  current
   DESCRIPTION         "Trouble Ticket external alarm fault."
   SYNTAX              INTEGER {
                         nodeAlarm   (1),
                         shelfAlarm  (2),
                         cardAlarm   (3),
                         deviceAlarm (4),
                         fanAlarm    (5)
                       }

   -- Congestion Problems

   TTcongestionFaultType ::= TEXTUAL-CONVENTION
   STATUS                  current
   DESCRIPTION         "Trouble Ticket congestion fault."
   SYNTAX              INTEGER {
                        none(1),
                        mild(2),
                        severe(3)
                       }

   -- Object Definitions
   --
   nncNodeInfo   OBJECT-TYPE
                 SYNTAX  SEQUENCE OF NncNodeInfo
                 MAX-ACCESS  not-accessible
                 STATUS  current
                 DESCRIPTION
                   "Node information shared by all trap types."
                 ::= { nncExtNotifObjects 1 }


   NncNodeInfo   ::= SEQUENCE {
                       nncNodeIPAddr          IpAddress,
                       nncNodeCPSSAddr        CpssAddress,
                       nncNodeType            NBNodeType,
                       nncNodeFullName        StringType
                     }

  nncNodeIPAddr       OBJECT-TYPE
                      SYNTAX IpAddress
                      MAX-ACCESS read-only
                      STATUS current
                      DESCRIPTION
                        "Node IP Address"
                      ::= { nncNodeInfo 1 }

  nncNodeCPSSAddr     OBJECT-TYPE
                      SYNTAX CpssAddress
                      MAX-ACCESS read-only
                      STATUS current
                      DESCRIPTION
                        "Node CPSS Address"
                      ::= { nncNodeInfo 2 }

  nncNodeType         OBJECT-TYPE
                      SYNTAX NBNodeType
                      MAX-ACCESS read-only
                      STATUS current
                      DESCRIPTION
                        "Node type used in Newbridge network"
                      ::= { nncNodeInfo 3 }

  nncNodeFullName     OBJECT-TYPE
                      SYNTAX StringType
                      MAX-ACCESS read-only
                      STATUS current
                      DESCRIPTION
                        "Node full name"
                      ::= { nncNodeInfo 4 }


   nncAlmInfo        OBJECT-TYPE
                 SYNTAX  SEQUENCE OF NncAlmInfo
                 MAX-ACCESS  not-accessible
                 STATUS  current
                 DESCRIPTION
                   "Alarm information shared by all alarm trap types."
                 ::= { nncExtNotifObjects 2 }


   NncAlmInfo        ::= SEQUENCE {
                     nncAlmDateAndTime         TimeTicks,
                     nncAlmPriority            AlmPriorityType,
                     nncAlmText                StringType,
                     nncAlmSubcode             StringType,
                     nncAlmParms               ParameterStringType
                  }


  nncAlmDateAndTime   OBJECT-TYPE
                      SYNTAX TimeTicks
                      MAX-ACCESS read-only
                      STATUS current
                      DESCRIPTION
                        "Alarm trap created date and time."
                      ::= { nncAlmInfo 1 }

  nncAlmPriority      OBJECT-TYPE
                      SYNTAX AlmPriorityType
                      MAX-ACCESS read-only
                      STATUS current
                      DESCRIPTION
                        "Alarm priority"
                      ::= { nncAlmInfo 2 }

  nncAlmText        OBJECT-TYPE
                      SYNTAX StringType
                      MAX-ACCESS read-only
                      STATUS current
                      DESCRIPTION
                        "Alarm description string stored in unsigned char format
                        "
                      ::= { nncAlmInfo 3 }


   nncTTInfo        OBJECT-TYPE
                     SYNTAX  SEQUENCE OF NncTTInfo
                     MAX-ACCESS  not-accessible
                     STATUS  current
                     DESCRIPTION
                       "Trouble ticket information shared by all trouble ticket
                        trap types."
                     ::= { nncExtNotifObjects 3 }


  NncTTInfo        ::= SEQUENCE {
                     nncTTDateAndTime       TimeTicks,
                     nncTTPriority          TTPriorityType,
                     nncTTFaultLocation     TTFaultLocationType,
                     nncTTFaultStatus       TTFaultStatusType,
                     nncTTOwner             StringType
                   }


   nncTTFaultType  OBJECT-TYPE
                     SYNTAX  SEQUENCE OF NncTTFaultType
                     MAX-ACCESS  not-accessible
                     STATUS  current
                     DESCRIPTION
                       "Trouble ticket fault reasons shared by all trouble
                        tickets."
                     ::= { nncExtNotifObjects 4 }

  NncTTFaultType   ::= SEQUENCE {
                     nncTThardwareFaultType  TThardwareFaultType,
                     nncTTsoftwareFaultType  TTsoftwareFaultType,
                     nncTTcommFaultType  TTcommFaultType,
                     nncTTuserFaultType  TTuserFaultType,
                     nncTTcustomNodeFaultType  TTcustomNodeFaultType,
                     nncTTlanNodeFaultType  TTlanNodeFaultType,
                     nncTTconnectExecFaultType  TTconnectExecFaultType,
                     nncTTtDaxNodeFaultType  TTtDaxNodeFaultType,
                     nncTTdcsNodeFaultType  TTdcsNodeFaultType,
                     nncTTadminFaultType  TTadminFaultType,
                     nncTTssdhRingFaultType  TTssdhRingFaultType,
                     nncTTextNodeFaultType  TTextNodeFaultType,
                     nncTTcongestionFaultType  TTcongestionFaultType
                     }

  nncTTDateAndTime   OBJECT-TYPE
                     SYNTAX TimeTicks
                     MAX-ACCESS read-only
                     STATUS current
                     DESCRIPTION
                      "Trouble ticket trap creation date and time as
                       seconds elapsed since 1 Jan, 1970 UTC."
                     ::= { nncTTInfo 1 }

  nncTTPriority      OBJECT-TYPE
                     SYNTAX TTPriorityType
                     MAX-ACCESS read-only
                     STATUS current
                     DESCRIPTION
                      "Trouble ticket priority."
                     ::= { nncTTInfo 2 }

  nncTTFaultLocation OBJECT-TYPE
                     SYNTAX TTFaultLocationType
                     MAX-ACCESS read-only
                     STATUS current
                     DESCRIPTION
                     "Location of problem resulting in the trouble ticket."
                     ::= { nncTTInfo 3 }

  nncTTFaultStatus    OBJECT-TYPE
                      SYNTAX TTFaultStatusType
                      MAX-ACCESS read-only
                      STATUS current
                      DESCRIPTION
                        "The fault status of a trouble ticket."
                      ::= { nncTTInfo 4 }


  nncTTOwner           OBJECT-TYPE
                      SYNTAX StringType
                      MAX-ACCESS read-only
                      STATUS current
                      DESCRIPTION
                        "The owner of this trouble ticket."
                      ::= { nncTTInfo 5 }


  nncExtNotifAlarm        NOTIFICATION-TYPE
                     OBJECTS         {
                       nncNodeInfo,
                       nncAlmInfo
                     }
                     STATUS  current
                     DESCRIPTION
                        "An SNMP trap to encapsulate a Newbridge alarm."
                     ::= { nncExtNotifAlarmType-v1Trap 1 }


  nncExtNotifHardwareTT       NOTIFICATION-TYPE
                     OBJECTS         {
                       nncNodeInfo,
                       nncTThardwareFaultType,
                       nncTTInfo
                     }
                     STATUS  current
                     DESCRIPTION
                        "An SNMP trap to encapsulate a Newbridge trouble ticket
                         with hardware fault type.
                        "
                     ::= { nncExtNotifTroubleTicketType-v1Trap 2 }


  nncExtNotifSoftwareTT       NOTIFICATION-TYPE
                     OBJECTS         {
                       nncNodeInfo,
                       nncTTsoftwareFaultType,
                       nncTTInfo
                     }
                     STATUS  current
                     DESCRIPTION
                        "An SNMP trap to encapsulate a Newbridge trouble ticket
                         with software fault type.
                        "
                     ::= { nncExtNotifTroubleTicketType-v1Trap 3 }


  nncExtNotifCommTT       NOTIFICATION-TYPE
                     OBJECTS         {
                       nncNodeInfo,
                       nncTTcommFaultType,
                       nncTTInfo
                     }
                     STATUS  current
                     DESCRIPTION
                        "An SNMP trap to encapsulate a Newbridge trouble ticket
                         with communication fault type.
                        "
                     ::= { nncExtNotifTroubleTicketType-v1Trap 4 }


  nncExtNotifUserTT       NOTIFICATION-TYPE
                     OBJECTS         {
                       nncNodeInfo,
                       nncTTuserFaultType,
                       nncTTInfo
                     }
                     STATUS  current
                     DESCRIPTION
                        "An SNMP trap to encapsulate a Newbridge trouble ticket
                         with user fault type.
                        "
                     ::= { nncExtNotifTroubleTicketType-v1Trap 5 }



  nncExtNotifCustomNodeTT       NOTIFICATION-TYPE
                     OBJECTS         {
                       nncNodeInfo,
                       nncTTcustomNodeFaultType,
                       nncTTInfo
                     }
                     STATUS  current
                     DESCRIPTION
                        "An SNMP trap to encapsulate a Newbridge trouble ticket
                         with custom node type.
                        "
                     ::= { nncExtNotifTroubleTicketType-v1Trap 6 }



  nncExtNotifLanNodeTT       NOTIFICATION-TYPE
                     OBJECTS         {
                       nncNodeInfo,
                       nncTTlanNodeFaultType,
                       nncTTInfo
                     }
                     STATUS  current
                     DESCRIPTION
                        "An SNMP trap to encapsulate a Newbridge trouble ticket
                         with LAN node fault type.
                        "
                     ::= { nncExtNotifTroubleTicketType-v1Trap 7 }


  nncExtNotifConnectExecTT       NOTIFICATION-TYPE
                     OBJECTS         {
                       nncNodeInfo,
                       nncTTconnectExecFaultType,
                       nncTTInfo
                     }
                     STATUS  current
                     DESCRIPTION
                        "An SNMP trap to encapsulate a Newbridge trouble ticket
                         with connect exec fault type.
                        "
                     ::= { nncExtNotifTroubleTicketType-v1Trap 8 }


  nncExtNotifTDaxNodeTT       NOTIFICATION-TYPE
                     OBJECTS         {
                       nncNodeInfo,
                       nncTTtDaxNodeFaultType,
                       nncTTInfo
                     }
                     STATUS  current
                     DESCRIPTION
                        "An SNMP trap to encapsulate a Newbridge trouble ticket
                         with TDAX node type.
                        "
                     ::= { nncExtNotifTroubleTicketType-v1Trap 9 }




  nncExtNotifAdminTT       NOTIFICATION-TYPE
                     OBJECTS         {
                       nncNodeInfo,
                       nncTTadminFaultType,
                       nncTTInfo
                     }
                     STATUS  current
                     DESCRIPTION
                        "An SNMP trap to encapsulate a Newbridge trouble ticket
                         with administrative fault type.
                        "
                     ::= { nncExtNotifTroubleTicketType-v1Trap 10 }


  nncExtNotifSsdhRingTT       NOTIFICATION-TYPE
                     OBJECTS         {
                       nncNodeInfo,
                       nncTTssdhRingFaultType,
                       nncTTInfo
                     }
                     STATUS  current
                     DESCRIPTION
                        "An SNMP trap to encapsulate a Newbridge trouble ticket
                         with SSDH Ring fault type.
                        "
                     ::= { nncExtNotifTroubleTicketType-v1Trap 11 }


  nncExtNotifExternalNodeTT       NOTIFICATION-TYPE
                     OBJECTS         {
                       nncNodeInfo,
                       nncTTextNodeFaultType,
                       nncTTInfo
                     }
                     STATUS  current
                     DESCRIPTION
                        "An SNMP trap to encapsulate a Newbridge trouble ticket
                         with External Node alarm type.
                        "
                     ::= { nncExtNotifTroubleTicketType-v1Trap 12 }



  nncExtNotifCongestionTT       NOTIFICATION-TYPE
                     OBJECTS         {
                       nncNodeInfo,
                       nncTTcongestionFaultType,
                       nncTTInfo
                     }
                     STATUS  current
                     DESCRIPTION
                        "An SNMP trap to encapsulate a Newbridge trouble ticket
                         with Congestion Problem fault type.
                        "
                     ::= { nncExtNotifTroubleTicketType-v1Trap 13 }


  nncExtNotifHeartBeat        NOTIFICATION-TYPE
                     OBJECTS         {
                       nncSysDescr,
                       nncSysUpTime
                     }
                     STATUS  current
                     DESCRIPTION
                        "An SNMP trap to encapsulate a Heartbeat Trap"
                     ::= { nncExtNotifHeartBeatType-v1Trap 1 }


   nncHeartBeatInfo   OBJECT-TYPE
                 SYNTAX  SEQUENCE OF NncHeartBeatInfo
                 MAX-ACCESS  not-accessible
                 STATUS  current
                 DESCRIPTION
                   "HeartBeat information used by HeartBeat trap types."
                 ::= { nncExtNotifObjects 5 }


  NncHeartBeatInfo        ::= SEQUENCE {
                     nncSysDescr       	    SysDescrType,
                     nncSysUpTime           TimeTicks
                   }


  nncSysDescr    	    OBJECT-TYPE
                      SYNTAX SysDescrType
                      MAX-ACCESS read-only
                      STATUS current
                      DESCRIPTION
                        "A textual description of the Newbridge network 
			management entity."
                      ::= { nncHeartBeatInfo 1 }


  nncSysUpTime   	    OBJECT-TYPE
                      SYNTAX TimeTicks
                      MAX-ACCESS read-only
                      STATUS current
                      DESCRIPTION
                        "The time (in tenths of a second) since the network
			management system was last re-initialized."
                      ::= { nncHeartBeatInfo 2 }


  nncTThardwareFaultType    OBJECT-TYPE
                      SYNTAX TThardwareFaultType
                      MAX-ACCESS read-only
                      STATUS current
                      DESCRIPTION
                        "The hardware fault reason of a trouble ticket.  "
                      ::= { nncTTFaultType 1 }


  nncTTsoftwareFaultType    OBJECT-TYPE
                      SYNTAX TTsoftwareFaultType
                      MAX-ACCESS read-only
                      STATUS current
                      DESCRIPTION
                        "The software fault reason of a trouble ticket.  "
                      ::= { nncTTFaultType 2 }


  nncTTcommFaultType    OBJECT-TYPE
                      SYNTAX TTcommFaultType
                      MAX-ACCESS read-only
                      STATUS current
                      DESCRIPTION
                        "The communication fault reason of a trouble ticket.  "
                      ::= { nncTTFaultType 3 }


  nncTTuserFaultType    OBJECT-TYPE
                      SYNTAX TTuserFaultType
                      MAX-ACCESS read-only
                      STATUS current
                      DESCRIPTION
                        "The user fault reason of a trouble ticket.  "
                      ::= { nncTTFaultType 4 }

  nncTTcustomNodeFaultType  OBJECT-TYPE
                      SYNTAX TTcustomNodeFaultType
                      MAX-ACCESS read-only
                      STATUS current
                      DESCRIPTION
                        "Custom node fault reason of a troble ticket."
                      ::= { nncTTFaultType 5 }



  nncTTlanNodeFaultType    OBJECT-TYPE
                      SYNTAX TTlanNodeFaultType
                      MAX-ACCESS read-only
                      STATUS current
                      DESCRIPTION
                        "The LAN node fault reason of a trouble ticket.  "
                      ::= { nncTTFaultType 6 }


  nncTTconnectExecFaultType    OBJECT-TYPE
                      SYNTAX TTconnectExecFaultType
                      MAX-ACCESS read-only
                      STATUS current
                      DESCRIPTION
                        "The connect exec fault reason of a trouble ticket.  "
                      ::= { nncTTFaultType 7 }

  nncTTtDaxNodeFaultType  OBJECT-TYPE
                      SYNTAX TTtDaxNodeFaultType
                      MAX-ACCESS read-only
                      STATUS current
                      DESCRIPTION
                        "TDAX Node fault reason of a trouble ticket."
                      ::= { nncTTFaultType 8 }


  nncTTdcsNodeFaultType    OBJECT-TYPE
                      SYNTAX TTdcsNodeFaultType
                      MAX-ACCESS read-only
                      STATUS current
                      DESCRIPTION
                        "DCS Manager fault reason of a trouble ticket."
                      ::= { nncTTFaultType 9 }


  nncTTadminFaultType    OBJECT-TYPE
                      SYNTAX TTadminFaultType
                      MAX-ACCESS read-only
                      STATUS current
                      DESCRIPTION
                        "The administrative fault reason of a trouble ticket.  "
                      ::= { nncTTFaultType 10 }

 nncTTssdhRingFaultType    OBJECT-TYPE
                      SYNTAX TTssdhRingFaultType
                      MAX-ACCESS read-only
                      STATUS current
                      DESCRIPTION
                        "UPSR ring prolem."
                      ::= { nncTTFaultType 11 }

  nncTTextNodeFaultType    OBJECT-TYPE
                      SYNTAX TTextNodeFaultType
                      MAX-ACCESS read-only
                      STATUS current
                      DESCRIPTION
                        "External alarm reason of a trouble ticket."
                      ::= { nncTTFaultType 12 }



 nncTTcongestionFaultType    OBJECT-TYPE
                      SYNTAX TTcongestionFaultType
                      MAX-ACCESS read-only
                      STATUS current
                      DESCRIPTION
                        "Congestion problem description of a trouble ticket."
                      ::= { nncTTFaultType 13 }


------------------------------------------------------------------------
-- Conformance Group Definitions
------------------------------------------------------------------------
nncExtNotifGroup OBJECT-GROUP
                OBJECTS         {
                   nncNodeInfo,
                   nncAlmInfo,
                   nncTTInfo,
                   nncTTFaultType
                }
                STATUS  current
                DESCRIPTION
                  "This group defines the Newbridge MIB extensions for
                   objects used to forward alarms and trouble tickets.
                  "
        ::= { nncExtNotifGroups 1 }

------------------------------------------------------------------------
-- Compliance Statements
------------------------------------------------------------------------
nncExtNotifCompliance MODULE-COMPLIANCE
                STATUS  current
                DESCRIPTION  "The compliance statement for SNMPv2 entities
                  residing on systems which implement the Newbridge MIB
                  extensions for notifications."
                MODULE -- compliance to the containing MIB module
        ::= { nncExtNotifCompliances 1 }


END

-------------------------------------------------------------------------------
--      Review Minutes
-------------------------------------------------------------------------------
--      MINUTES-BEGIN
--              REVIEW-DATE  "1997.02.07"
--              BODY  "
--
--
--      TO:     Satvinder Bawa*, Susan Griffin, Mike Holloway*,
--              Van Tan, Mark Tooker*, John Verbaas*
--              James Watt*, Chuong Ngo, Scott Thompson
--      CC:     Numbers Admin, NM Managers, Steven Quigley
--      FROM:   Connie Chang*
--
--      A meeting was held on 97.02.07 to review Notification.mib, the area
--      interface definition for the Alarm area in the system region.
--      Attendees are marked with * in the TO and CC lists above.
--
--      Outcome
--
--      It was the consensus of the review team that this file is
--      acceptable with the indicated modifications.
--
--      Actions:
--      A1 -    Connie Chang to update the file as indicated in D1 below.
--              To be completed by 97.02.12
--              Response:
--                 Notification.mib version 1.0 has been updated.
--
--                                              Status: CLOSED
--
--      A2 -    Connie Chang to add "warning" type comments to 7TN0205 and 46020
--              source code files, so that designers know that if any constants
--              are added in areas affecting this MIB, they will update the MIB
--              description accordingly.
--              To be completed by 97.02.12
--              Response:
--              This action has been added to the implementation plan outlined
--              in 07FI0212.
--                                              Status: CLOSED
--
--
--      A3 -    Connie Chang to determine the value of sending ttContactName
--              and ttContactPhNo, and the possibility of sending ttOwner
--              instead.
--              To be completed by 97.02.12
--              Response:
--                 ttContactName and ttContactPhNo have been replaced by ttOwner
--              as the contact name and the phone number entries are the same for the
--              entire network.
--                                              Status: CLOSED
--
--      A4 -    Connie Chang to investigate the use of object IDs instead of
--              enumeration for TT object differentiation.
--              To be completed by 97.02.07
--              Response:
--                 The use of object IDs will add to the length of the trap PDU.
--              If OIDs are used, then the total number of bytes in the trap PDU
--              will be more than the maximum TRAP length, 484 bytes.
--                                              Status: CLOSED
--
--      A5 -    Connie Chang to investigate breaking up trouble ticket fault
--              reasons into groups of reasons defined under different object
--              IDs.
--              To be completed by 97.02.12
--              Response:
--              The trouble ticket fault reasons have been broken down into groups
--              based on the trouble ticket fault source.  A single trap is
--              created to send out the trouble tickets with each fault source.
--              For example, a hardware fault trap is sent out for a hardware
--              fault trouble ticket with a hardware fault reason.
--
--                                              Status: CLOSED
--
--      A6 -    Connie Chang to discuss sending MIBII traps for selected TT
--              types with James Watt.
--              To be completed by 97.02.14
--              Response:
--              In order to send MIBII traps, we need to implement an interface
--              table so that an interface index can be used in the MIBII traps.
--              However, to implement an interface table down to the port level
--              will take more effort than this feature is planed for.  Thus,
--              no generic SNMP-defined types of traps are sent in this feature.
--
--                                              Status: CLOSED
--
--      Decisions:
--      D1 -    Notification.mib shall be updated as follows:
--              a) Create two traps: one for alarm information and the other
--                 for trouble ticket information.  These two traps share
--                 some common fields.
--              b) Change "nncExtensions 15" to "nncExtensions 999" until the
--                 extension number is assigned by Number Admin.
--              c) Change the file to conform SNMPv2.
--
--
--      "
--
--      END-MINUTES
