-- ################################################################################

--/* 
-- * $RCSfile: WAN-TRAP-MIB.mib,v $ - Wan blades enterprise MIB
-- *
-- * Copyright (c) 2000 by Optranet Networks Inc.
-- * 
-- * Revision control history
-- * ------------------------
-- * $Id: WAN-TRAP-MIB.mib,v 1.3 2005-09-22 22:19:49 scotth Exp $ $ProjectRevision: 1.85 $
-- *
-- * Extreme Networks modification history
-- * -------------------------------------
-- * $Log: not supported by cvs2svn $
-- * Revision 1.2.32.1  2005/09/15 04:10:33  scotth
-- * Reviewer      : Self
-- * Regression    : None
-- * PD none : cvs update -d -jv1130b11-br-rushmore7-6 -jv1130b11-br-rushmore7-7 exos
-- * Merge to branch-mckinley_v1140b1
-- *
-- * Revision 1.2.14.1  2005/09/09 00:58:31  ykhan
-- * Reviewer      : Balaji
-- * Regression    : none
-- * PD3-42847181  : DOS to unix conversion, Removed 11111111 from BITS default value, Fixes the TRAP mib to compile on HPOV
-- *
-- * Revision 1.2  2005/07/14 17:51:38  scotth
-- * Reviewer      : Self
-- * Regression    : None
-- * PD none : cvs update -d -jv1130b4-br-rushmore6-3 -jv1130b4-br-rushmore6-4 exos (v1130b8)
-- *
-- * Revision 1.1.2.1  2005/07/14 04:39:39  ykhan
-- * Reviewer      : Abhay
-- * Regression    : SC_050713_140715
-- * PD3-39730771: This file has been implemented by EW but not Exos. To keep mib in sync this file has to present in exos tree.
-- *
-- * Revision 1.1  2005/01/25 02:03:49  bsrinivasan
-- * Added the MIBs from the Titan tree
-- *
-- * Revision 1.1  2003/06/07 01:14:43  rnagarajan
-- * - Added new wantrap.mib from Extremeware 7.1
-- *
-- * Revision 1.3  2003/02/06 22:56:36  rtp-build
-- * PD none: merge 802.1x and SNMPv3 feature into trunk (v710b9)
-- *
-- * Revision 1.2.10.3  2003/02/04 17:41:10  dcarson
-- * PD none: never use dash-dash in an SNMP commit comment
-- *
-- * Revision 1.2.10.2  2003/02/04 16:20:13  dcarson
-- * PD none: promotion of branch-802-1x-snmpv3_v710b6 to _v710b8 (phase one; has compile errors)
-- *
-- * Revision 1.1.6.1  2003/01/15 03:53:44  rsharma
-- * PD2-116204701 : promote 802.1x ,netlogin & snmpv3 merge from v710b0 -> v710b6
-- *
-- * Revision 1.1.2.1  2002/12/03 16:46:56  agidwani
-- * PD2-109134118: SNMPv3 merge
-- *
-- * Revision 1.2  2002/03/21 20:59:13  dcarson
-- * PD 1-C8KSX: merge ABU_v700b4 into trunk
-- *
-- * Revision 1.1.6.1  2002/03/12 06:25:59  dcarson
-- * PD 1-BGKRG: merge branch-ABU_v700b3 to branch-ABU_v700b4
-- *
-- * Revision 1.1.4.1  2002/03/11 20:29:42  dwade
-- * conflict resolution for branch-ABU_v700b3
-- *
-- * Revision 1.1.2.2  2002/03/08 22:11:08  vtseng
-- * Lilac merge
-- *
-- * Revision 1.1.2.1  2002/02/21 16:45:46  dwade
-- * ABU files added for branch branch-ABU-v700
-- *
-- * Revision 1.1.3.1  2001/12/14 02:08:17  dwade
-- * Tree v618b1060_abu
-- *
-- * Revision 1.1.3.1  2001/06/05 19:48:53  rrose
-- * Tree optra
-- *
-- * Revision 1.1.1.1  2001/03/13 00:04:55  bmonsen
-- * Imported from MKS
-- *
-- * Revision 1.3  2000/10/26 20:27:30Z  victort
-- * Added NoMasterClockLost trap
-- * Revision 1.1  2000/09/10 08:30:00  victort
-- * Initial revision
-- *
-- */

--
-- WAN Traps
--

WAN-TRAP-MIB DEFINITIONS ::= BEGIN

        IMPORTS
        extremenetworks, extremeAgent   FROM EXTREME-BASE-MIB
		sysUpTime, sysDescr             FROM RFC1213-MIB
		dsx1LineIndex, dsx1IfIndex,
        dsx1LineStatus                  FROM RFC1406-MIB
		dsx3LineIndex, dsx3IfIndex,
        dsx3LineStatus                  FROM RFC1407-MIB
        TRAP-TYPE                       FROM RFC-1215
        OBJECT-TYPE                     FROM SNMPv2-SMI;
--
-- Traps for WAN Blade
--
	wanDsx1LineStatusChange TRAP-TYPE
		ENTERPRISE  extremenetworks
		VARIABLES { sysUpTime,
		            sysDescr,
		            dsx1LineIndex,
		            dsx1IfIndex,
                    dsx1LineStatus }
		DESCRIPTION
		"Signifies that the DS1 line status change for 
		the specified interface has been detected."
	::= 100
	
	wanDsx1LossOfMasterClock TRAP-TYPE
		ENTERPRISE  extremenetworks
		VARIABLES { sysUpTime,
		            sysDescr,
                    dsx1LineIndex,
		            dsx1IfIndex,
                    dsx1LineStatus }
		DESCRIPTION
		"Signifies that the wanDsx1LossOfMasterClock event for 
		the specified interface has been detected."
	::= 101
	
	wanDsx1NoLossOfMasterClock TRAP-TYPE
		ENTERPRISE  extremenetworks
		VARIABLES { sysUpTime,
		            sysDescr,
                    dsx1LineIndex,
		            dsx1IfIndex,
                    dsx1LineStatus }
		DESCRIPTION
		"Signifies that the wanDsx1NoLossOfMasterClock event for 
		the specified interface has been detected."
	::= 102
	
	wanDsx3LineStatusChange TRAP-TYPE
		ENTERPRISE  extremenetworks
		VARIABLES { sysUpTime,
		            sysDescr,
		            dsx3LineIndex,
		            dsx3IfIndex,
                    dsx3LineStatus }
		DESCRIPTION
		"Signifies that the T3 line status change for 
		the specified interface has been detected."
	::= 103
	
	wanDsx3LossOfMasterClock TRAP-TYPE
		ENTERPRISE  extremenetworks
		VARIABLES { sysUpTime,
		            sysDescr,
                    dsx3LineIndex,
		            dsx3IfIndex,
                    dsx3LineStatus }
		DESCRIPTION
		"Signifies that the wanDsx3LossOfMasterClock event for 
		the specified interface has been detected."
	::= 104
	
	wanDsx3NoLossOfMasterClock TRAP-TYPE
		ENTERPRISE  extremenetworks
		VARIABLES { sysUpTime,
		            sysDescr,
                    dsx3LineIndex,
		            dsx3IfIndex,
                    dsx3LineStatus }
		DESCRIPTION
		"Signifies that the wanDsx3NoLossOfMasterClock event for 
		the specified interface has been detected."
	::= 105
	
	
END
