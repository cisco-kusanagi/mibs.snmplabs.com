AISLCANALOG-MIB DEFINITIONS ::= BEGIN

IMPORTS
        MODULE-IDENTITY, OBJECT-TYPE, enterprises
                        FROM SNMPv2-SMI
        TruthValue, DisplayString
                        FROM SNMPv2-TC;

        PositiveInteger    ::= INTEGER (1..2147483647)
				NonNegativeInteger ::= INTEGER (0..2147483647)

        aii OBJECT IDENTIFIER ::= {enterprises 539}

aiSLCAnalog MODULE-IDENTITY
        LAST-UPDATED "0002181700Z"
        ORGANIZATION "Applied Innovation Inc."
        CONTACT-INFO "Engineering MIB Administrator
                      Postal: Applied Innovation Inc.
                              5800 Innovation Drive
                              Dublin, Ohio 43017-3271

                      Tel:    614-798-2000
                      Fax:    614-798-1770
                      Email:  snmp@aiinet.com"
        DESCRIPTION
                "MIB module for SLCs with analog input points."
        ::= {aii 28}

--=========================================================================

aiSLCAnalogInputTable OBJECT-TYPE
	SYNTAX		SEQUENCE OF AISLCAnalogInputEntry
	MAX-ACCESS	not-accessible
	STATUS		current
	DESCRIPTION
		"Table of analog inputs points indexed by point number.
		Includes description, configuration and status information."
	::= {aiSLCAnalog 1}

aiSLCAnalogInputEntry OBJECT-TYPE
	SYNTAX		AISLCAnalogInputEntry
	MAX-ACCESS	not-accessible
	STATUS		current
	DESCRIPTION	"Entry of aiSLCAnalogInputTable."
	INDEX		{aislcainPointNumber}
	::= {aiSLCAnalogInputTable 1}

AISLCAnalogInputEntry ::= SEQUENCE {
	aislcainPointNumber			PositiveInteger,
	aislcainScanningEnabled 		INTEGER,
	aislcainDescription			DisplayString,
	aislcainTrapEnable			INTEGER,
	aislcainNormalStateTrap			INTEGER,
	aislcainHighAlarmSeverity		INTEGER,
	aislcainHighAlarmStateText		DisplayString,
	aislcainLowAlarmSeverity		INTEGER,
	aislcainLowAlarmStateText		DisplayString,
	aislcainNormalStateText 		DisplayString,
	aislcainUserUnits			DisplayString,
	aislcainMinInputmA			DisplayString,
	aislcainMinInputuu			DisplayString,
	aislcainMaxInputmA			DisplayString,
	aislcainMaxInputuu			DisplayString,
	aislcainHighLimitScan   		INTEGER,
	aislcainHighAlarmThresholduu		DisplayString,
	aislcainHighAlarmThresholdIntervaluu DisplayString,
	aislcainHighAlarmMinPeriod		INTEGER,
	aislcainHighAlarmHysteresisuu		DisplayString,
	aislcainLowLimitScan   			INTEGER,
	aislcainLowAlarmThresholduu		DisplayString,
	aislcainLowAlarmThresholdIntervaluu DisplayString,
	aislcainLowAlarmMinPeriod		INTEGER,
	aislcainLowAlarmHysteresisuu		DisplayString,
	aislcainCurrentValueuu			DisplayString,
	aislcainCurrentValuemA			DisplayString,
	aislcainLastChangeTime			DisplayString,
	aislcaintl1AccessID			DisplayString,
	aislcaintl1Provisioned			TruthValue,
	aislcaintl1AccessIDType			INTEGER,
	aislcaintl1HighAlarmType		DisplayString,
	aislcaintl1HighAlarmMessage		DisplayString,
	aislcaintl1LowAlarmType			DisplayString,
	aislcaintl1LowAlarmMessage		DisplayString,
	aislcaintl1HighAlarmNotificationCode	DisplayString,
	aislcaintl1HighAlarmServiceAffecting	INTEGER,
	aislcaintl1HighAlarmConditionType	DisplayString,
	aislcaintl1HighAlarmConditionDesc	DisplayString,
	aislcaintl1LowAlarmNotificationCode	DisplayString,
	aislcaintl1LowAlarmServiceAffecting	INTEGER,
	aislcaintl1LowAlarmConditionType	DisplayString,
	aislcaintl1LowAlarmConditionDesc	DisplayString,
	aislcainAnalogStatus			INTEGER,
	aislcainCurrentStateText 		DisplayString,
	aislcainAnalogAlarmState 		INTEGER
}

aislcainPointNumber OBJECT-TYPE
	SYNTAX		PositiveInteger
	MAX-ACCESS	read-only
	STATUS		current
	DESCRIPTION	"Input point number to which this table row applies."
	::= {aiSLCAnalogInputEntry 1}

aislcainScanningEnabled OBJECT-TYPE
	SYNTAX		 INTEGER {enabled(1), disabled(2)}
	MAX-ACCESS read-write
	STATUS     current
	DESCRIPTION "Enable or disable scanning of the input."
	::= {aiSLCAnalogInputEntry 2}

aislcainDescription OBJECT-TYPE
	SYNTAX		DisplayString (SIZE (0..80))
	MAX-ACCESS	read-write
	STATUS		current
	DESCRIPTION	"Textual description of the point.
			Maximum length is 80 characters."
	::= {aiSLCAnalogInputEntry 3}

aislcainTrapEnable OBJECT-TYPE
	SYNTAX		INTEGER {enabled(1), disabled(2)}
	MAX-ACCESS	read-write
	STATUS		current
	DESCRIPTION	"Enable or disable alarm traps."
	::= {aiSLCAnalogInputEntry 4}

aislcainNormalStateTrap OBJECT-TYPE
	SYNTAX		INTEGER {enabled(1), disabled(2) }
	MAX-ACCESS	read-write
	STATUS		current
	DESCRIPTION "If enabled, transitions from an alarm state to the normal
			state will generate an SNMP trap or TL1 message."
	::= {aiSLCAnalogInputEntry 5}

aislcainHighAlarmSeverity OBJECT-TYPE
  SYNTAX          INTEGER {critical(1), major(2), minor(3), info(4), notReported(5) }
  MAX-ACCESS      read-write
  STATUS          current
  DESCRIPTION "Severity of the point's alarm state, or notReported(5)
               if the point does not generate an alarm."
  ::= {aiSLCAnalogInputEntry 6}

aislcainHighAlarmStateText OBJECT-TYPE
  SYNTAX          DisplayString (SIZE (0..80))
  MAX-ACCESS      read-write
  STATUS          current
  DESCRIPTION "Textual description of the point's alarm state.
               Maximum length is 80 characters."
  ::= {aiSLCAnalogInputEntry 7}

aislcainLowAlarmSeverity OBJECT-TYPE
  SYNTAX          INTEGER {critical(1), major(2), minor(3), info(4), notReported(5) }
  MAX-ACCESS      read-write
  STATUS          current
  DESCRIPTION "Severity of the point's alarm state, or notReported(5)
               if the point does not generate an alarm."
  ::= {aiSLCAnalogInputEntry 8}

aislcainLowAlarmStateText OBJECT-TYPE
  SYNTAX          DisplayString (SIZE (0..80))
  MAX-ACCESS      read-write
  STATUS          current
  DESCRIPTION "Textual description of the point's alarm state.
               Maximum length is 80 characters."
  ::= {aiSLCAnalogInputEntry 9}

aislcainNormalStateText OBJECT-TYPE
  SYNTAX          DisplayString (SIZE (0..80))
  MAX-ACCESS      read-write
  STATUS          current
  DESCRIPTION "Textual description of the point's normal state.
               Maximum length is 80 characters."
  ::= {aiSLCAnalogInputEntry 10}

aislcainUserUnits OBJECT-TYPE
	SYNTAX		DisplayString (SIZE (0..16))
	MAX-ACCESS	read-write
	STATUS		current
	DESCRIPTION	"The user-defined units for this input (e.g. degC, degF, etc.)."
	::= {aiSLCAnalogInputEntry 11}

aislcainMinInputmA OBJECT-TYPE
	SYNTAX		DisplayString (SIZE (0..8))
	MAX-ACCESS	read-write
	STATUS		current
	DESCRIPTION	"The current in mA corresponding to the minimum input in user-defined units."
	::= {aiSLCAnalogInputEntry 12}

aislcainMinInputuu OBJECT-TYPE
	SYNTAX		DisplayString (SIZE (0..8))
	MAX-ACCESS	read-write
	STATUS		current
	DESCRIPTION	"The minimum value in user-defined units corresponding to the minimum input in mA."
	::= {aiSLCAnalogInputEntry 13}

aislcainMaxInputmA OBJECT-TYPE
	SYNTAX		DisplayString (SIZE (0..8))
	MAX-ACCESS	read-write
	STATUS		current
	DESCRIPTION	"The current in mA corresponding to the maximum input in user-defined units."
	::= {aiSLCAnalogInputEntry 14}

aislcainMaxInputuu OBJECT-TYPE
	SYNTAX		DisplayString (SIZE (0..8))
	MAX-ACCESS	read-write
	STATUS		current
	DESCRIPTION	"The maximum value in user-defined units corresponding to the maximum input in mA."
	::= {aiSLCAnalogInputEntry 15}

aislcainHighLimitScan   OBJECT-TYPE
  SYNTAX          INTEGER {enabled(1), disabled(2) }
  MAX-ACCESS      read-write
  STATUS          current
  DESCRIPTION "If enabled, the high limit threshold will be checked when the input is scanned."
  ::= {aiSLCAnalogInputEntry 16}

aislcainHighAlarmThresholduu OBJECT-TYPE
	SYNTAX		DisplayString (SIZE (0..8))
	MAX-ACCESS	read-write
	STATUS		current
	DESCRIPTION	"The high alarm level in user-defined units."
	::= {aiSLCAnalogInputEntry 17}

aislcainHighAlarmThresholdIntervaluu OBJECT-TYPE
	SYNTAX		DisplayString (SIZE (0..8))
	MAX-ACCESS	read-write
	STATUS		current
	DESCRIPTION	"The high alarm level threshold interval in user-defined units.
	             When the high alarm is active, each time the input rises another
							 interval higher, a new alarm is sent."
	::= {aiSLCAnalogInputEntry 18}

aislcainHighAlarmMinPeriod OBJECT-TYPE
	SYNTAX		INTEGER(0..600)
	MAX-ACCESS	read-write
	STATUS		current
	DESCRIPTION	"The minimum number of seconds the input(s) should be energized when
			the input exceeds the high alarm threshold."
	::= {aiSLCAnalogInputEntry 19}

aislcainHighAlarmHysteresisuu OBJECT-TYPE
	SYNTAX		DisplayString (SIZE (0..8))
	MAX-ACCESS	read-write
	STATUS		current
	DESCRIPTION	"The amount by which the input must drop below the High Alarm Threshold
			before the High Alarm will be cleared."
	::= {aiSLCAnalogInputEntry 20}

aislcainLowLimitScan   OBJECT-TYPE
  SYNTAX          INTEGER {enabled(1), disabled(2) }
  MAX-ACCESS      read-write
  STATUS          current
  DESCRIPTION "If enabled, the low limit threshold will be checked when the input is scanned."
  ::= {aiSLCAnalogInputEntry 21}

aislcainLowAlarmThresholduu OBJECT-TYPE
	SYNTAX		DisplayString (SIZE (0..8))
	MAX-ACCESS	read-write
	STATUS		current
	DESCRIPTION	"The low alarm level in user-defined units."
	::= {aiSLCAnalogInputEntry 22}

aislcainLowAlarmThresholdIntervaluu OBJECT-TYPE
	SYNTAX		DisplayString (SIZE (0..8))
	MAX-ACCESS	read-write
	STATUS		current
	DESCRIPTION	"The low alarm level threshold interval in user-defined units.
	             When the low alarm is active, each time the input drops another
							 interval lower, a new alarm is sent."
	::= {aiSLCAnalogInputEntry 23}

aislcainLowAlarmMinPeriod OBJECT-TYPE
	SYNTAX		INTEGER(0..600)
	MAX-ACCESS	read-write
	STATUS		current
	DESCRIPTION	"The minimum number of seconds the input(s) should be energized when
			the input falls below the low alarm threshold."
	::= {aiSLCAnalogInputEntry 24}

aislcainLowAlarmHysteresisuu OBJECT-TYPE
	SYNTAX		DisplayString (SIZE (0..8))
	MAX-ACCESS	read-write
	STATUS		current
	DESCRIPTION	"The amount by which the input must rise above the Low Alarm Threshold
			before the Low Alarm will be cleared."
	::= {aiSLCAnalogInputEntry 25}

aislcainCurrentValueuu OBJECT-TYPE
	SYNTAX		DisplayString (SIZE (0..16))
	MAX-ACCESS	read-only
	STATUS		current
	DESCRIPTION	"The current input value in user-defined units."
	::= {aiSLCAnalogInputEntry 26}

aislcainCurrentValuemA OBJECT-TYPE
	SYNTAX		DisplayString (SIZE (0..8))
	MAX-ACCESS	read-only
	STATUS		current
	DESCRIPTION	"The current input value in mA."
	::= {aiSLCAnalogInputEntry 27}

aislcainLastChangeTime OBJECT-TYPE
	SYNTAX		DisplayString (SIZE (19..23))
	MAX-ACCESS	read-only
	STATUS		current
	DESCRIPTION	"Textural representation of the time of the most recent
			output change.  24-hour format YYYY-MM-DD HH:MM:SS."
	::= {aiSLCAnalogInputEntry 28}

aislcaintl1AccessID OBJECT-TYPE
	SYNTAX		DisplayString (SIZE (0..22))
	MAX-ACCESS	read-write
	STATUS		current
	DESCRIPTION	"Unique TL1 access identifier for this point.
			Maximum length is 22 characters."
	::= {aiSLCAnalogInputEntry 29}

aislcaintl1Provisioned OBJECT-TYPE
	SYNTAX		TruthValue
	MAX-ACCESS	read-write
	STATUS		current
	DESCRIPTION	"Enable TL1 management of this point."
	::= {aiSLCAnalogInputEntry 30}

aislcaintl1AccessIDType OBJECT-TYPE
	SYNTAX		INTEGER {equipment(1), environmental(2)}
	MAX-ACCESS	read-write
	STATUS		current
	DESCRIPTION	"Identifies the point as either an equipment(1) alarm condition
			or an environmental(2) alarm."
	::= {aiSLCAnalogInputEntry 31}


aislcaintl1HighAlarmType OBJECT-TYPE
	SYNTAX		DisplayString (SIZE (0..10))
	MAX-ACCESS	read-write
	STATUS		current
	DESCRIPTION	"String indicating the type of alarm, used only
			when aislcaintl1AccessIDType is environmental(2).
			Maximum length is 10 characters."
	::= {aiSLCAnalogInputEntry 32}

aislcaintl1HighAlarmMessage OBJECT-TYPE
	SYNTAX		DisplayString (SIZE (0..40))
	MAX-ACCESS	read-write
	STATUS		current
	DESCRIPTION	"Textual description of the alarm, used only when
			aislcaintl1AccessIDType is environmental(2).
			Maximum length is 40 characters."
	::= {aiSLCAnalogInputEntry 33}

aislcaintl1LowAlarmType OBJECT-TYPE
	SYNTAX		DisplayString (SIZE (0..10))
	MAX-ACCESS	read-write
	STATUS		current
	DESCRIPTION	"String indicating the type of alarm, used only
			when aislcaintl1AccessIDType is environmental(2).
			Maximum length is 10 characters."
	::= {aiSLCAnalogInputEntry 34}

aislcaintl1LowAlarmMessage OBJECT-TYPE
	SYNTAX		DisplayString (SIZE (0..40))
	MAX-ACCESS	read-write
	STATUS		current
	DESCRIPTION	"Textual description of the alarm, used only when
			aislcaintl1AccessIDType is environmental(2).
			Maximum length is 40 characters."
	::= {aiSLCAnalogInputEntry 35}

aislcaintl1HighAlarmNotificationCode OBJECT-TYPE
	SYNTAX		INTEGER {critical(1), major(2), minor(3)}
	MAX-ACCESS	read-write
	STATUS		current
	DESCRIPTION	"Severity of the point's alarm state."
	::= {aiSLCAnalogInputEntry 36}

aislcaintl1HighAlarmServiceAffecting OBJECT-TYPE
	SYNTAX		INTEGER {serviceAffecting(1), notServiceAffecting(2)}
	MAX-ACCESS	read-write
	STATUS		current
	DESCRIPTION	"Indicates whether or not the alarm affects the functioning
			of the equipment.  This is only meaningful when
			aislcaintl1AccessIDType is equipment(1)."
	::= {aiSLCAnalogInputEntry 37}

aislcaintl1HighAlarmConditionType OBJECT-TYPE
	SYNTAX		DisplayString (SIZE (0..20))
	MAX-ACCESS	read-write
	STATUS		current
	DESCRIPTION	"String indicating the type of alarm condition, used
			only when aislcaintl1AccessIDType is equipment(1).
			Maximum length is 20 characters."
	::= {aiSLCAnalogInputEntry 38}

aislcaintl1HighAlarmConditionDesc OBJECT-TYPE
	SYNTAX		DisplayString (SIZE (0..64))
	MAX-ACCESS	read-write
	STATUS		current
	DESCRIPTION	"Textual description of the alarm condition, used only
			when aislcaintl1AccessIDType is equipment(1).
			Maximum length is 64 characters."
	::= {aiSLCAnalogInputEntry 39}

aislcaintl1LowAlarmNotificationCode OBJECT-TYPE
	SYNTAX		INTEGER {critical(1), major(2), minor(3)}
	MAX-ACCESS	read-write
	STATUS		current
	DESCRIPTION	"Severity of the point's alarm state."
	::= {aiSLCAnalogInputEntry 40}

aislcaintl1LowAlarmServiceAffecting OBJECT-TYPE
	SYNTAX		INTEGER {serviceAffecting(1), notServiceAffecting(2)}
	MAX-ACCESS	read-write
	STATUS		current
	DESCRIPTION	"Indicates whether or not the alarm affects the functioning
			of the equipment.  This is only meaningful when
			aislcaintl1AccessIDType is equipment(1)."
	::= {aiSLCAnalogInputEntry 41}

aislcaintl1LowAlarmConditionType OBJECT-TYPE
	SYNTAX		DisplayString (SIZE (0..20))
	MAX-ACCESS	read-write
	STATUS		current
	DESCRIPTION	"String indicating the type of alarm condition, used
			only when aislcaintl1AccessIDType is equipment(1).
			Maximum length is 20 characters."
	::= {aiSLCAnalogInputEntry 42}

aislcaintl1LowAlarmConditionDesc OBJECT-TYPE
	SYNTAX		DisplayString (SIZE (0..64))
	MAX-ACCESS	read-write
	STATUS		current
	DESCRIPTION	"Textual description of the alarm condition, used only
			when aislcaintl1AccessIDType is equipment(1).
			Maximum length is 64 characters."
	::= {aiSLCAnalogInputEntry 43}

aislcainAnalogStatus OBJECT-TYPE
	SYNTAX	INTEGER {normal(1), highLimitExceeded(2), lowLimitExceeded(3), lossOfSignal(4), saturated(5)}
	MAX-ACCESS read-only
	STATUS  current
	DESCRIPTION "The current alarm status of the analog input."
	::= {aiSLCAnalogInputEntry 44}

aislcainCurrentStateText OBJECT-TYPE
	SYNTAX DisplayString (SIZE (0..80))
	MAX-ACCESS read-only
	STATUS     current
	DESCRIPTION "Textual description of the point's current state.
	             This is either aislcainNormalStateText or aislcainAlarmStateText."
  ::= {aiSLCAnalogInputEntry 45}

aislcainAnalogAlarmState OBJECT-TYPE
  SYNTAX          INTEGER {
                  critical(1),
                  major(2),
                  minor(3),
                  info(4),
                  normal(5)
                  }
  MAX-ACCESS      read-only
  STATUS          current
  DESCRIPTION     "The point's current alarm state, or normal(5)."
  ::= {aiSLCAnalogInputEntry 46}

-- |
-- | Traps
-- |
-- | We're not going to do these YET...
-- |    MAG, 5-18-01
-- |
-- | aiSLCAnalogHighTrap TRAP-TYPE
-- |   ENTERPRISE  aii
-- |   VARIABLES   { aislcainPointNumber }
-- |   DESCRIPTION "Blank for now."
-- |   ::= 63
-- | 
-- | aiSLCAnalogLowTrap TRAP-TYPE
-- |   ENTERPRISE  aii
-- |   VARIABLES   { aislcainPointNumber }
-- |   DESCRIPTION "Blank for now."
-- |   ::= 64
-- | 
-- | aiSLCAnalogNormalTrap TRAP-TYPE
-- |   ENTERPRISE  aii
-- |   VARIABLES   { aislcainPointNumber }
-- |   DESCRIPTION "Blank for now."
-- |   ::= 65
-- | 
END
