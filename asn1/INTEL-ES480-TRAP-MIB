INTEL-ES480-TRAP-MIB DEFINITIONS ::= BEGIN

        IMPORTS
        intel                 FROM INTEL-ES480-MIB
		sysUpTime, sysDescr, ifPhysAddress             FROM RFC1213-MIB
        TRAP-TYPE                       FROM RFC-1215;

          overheat TRAP-TYPE
              ENTERPRISE intel
              VARIABLES   { sysUpTime, sysDescr }
              DESCRIPTION
                          "A overheat trap indicates that the on board
                          tempature sensor has reported a overheat 
                          condition.  System will shutdown until unit has
                          sufficiently cooled such that operation may begin
                          again.  A cold start trap will be issued when
                          the unit has come back on line."
              ::= 1

          fanfailed TRAP-TYPE
              ENTERPRISE  intel
              VARIABLES   { sysUpTime, sysDescr }
              DESCRIPTION
                          "A fan failed trap indicates one or more of the
                          cooling fans inside the device has failed.  A
                          fanOK trap will be sent once the fan has attained
                          normal operation."
              ::= 2

          fanOK TRAP-TYPE
              ENTERPRISE  intel
              VARIABLES   { sysUpTime, sysDescr }
              DESCRIPTION
                          "A fan has transitioned out of a failure state and
                          is now operating correctly."
              ::= 3

          invalidLoginAttempt TRAP-TYPE
              ENTERPRISE  intel
              VARIABLES   { sysUpTime, sysDescr }
              DESCRIPTION
                "A user attempted to login to console or by telnet but was
                 refused access due to incorrect username or password"
              ::= 4

          powerSupplyFail TRAP-TYPE
              ENTERPRISE  intel
              VARIABLES   { sysUpTime, sysDescr }
              DESCRIPTION
                "One or more sources of power to this agent has failed.
                 Presumably a redundant power-supply has taken over."
              ::= 5

          powerSupplyGood TRAP-TYPE
              ENTERPRISE  intel
              VARIABLES   { sysUpTime, sysDescr }
              DESCRIPTION
                 "One or more previously bad sources of power to this agent 
                 has come back to life without causing an agent restart."
              ::= 6

END
