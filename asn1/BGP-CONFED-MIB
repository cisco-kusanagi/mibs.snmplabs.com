-- extracted from draft-richardson-bgp4-confed-mib-00.txt
-- at Sat Feb 24 06:04:17 2001

    BGP-CONFED-MIB DEFINITIONS ::= BEGIN


        IMPORTS
            MODULE-IDENTITY, OBJECT-TYPE, NOTIFICATION-TYPE,
            mib-2, 
                FROM SNMPv2-SMI
            MODULE-COMPLIANCE, OBJECT-GROUP, NOTIFICATION-GROUP
                FROM SNMPv2-CONF
	    TruthValue
		FROM SNMPv2-TC
	    bgp
		FROM BGP-MIB;

        bgpConfed MODULE-IDENTITY
            LAST-UPDATED "200102230000Z"
            ORGANIZATION "IETF IDR Working Group"
            CONTACT-INFO "E-mail:  idr@merit.net

			  Mathew Richardson (Author)
			  E-mail: mrr@nexthop.com
			  Shane Wright (Author)
			  E-mail: swright@nexthop.com
                          517 W. William Street
                          Ann Arbor, MI 48103-4943
                          Tel: +1 734 973-2200
                          Fax: +1 734 615-3241

                          Susan Hares  (Editor)
                          517 W. William Street
                          Ann Arbor, MI 48103-4943
                          Tel: +1 734 973-2200
                          Fax: +1 734 615-3241
                          E-mail: skh@nexthop.com"

            REVISION    "200102230000Z"
            DESCRIPTION
		    "Extension of the MIB module for BGP-4 to include
		     about BGP Confederations."
	    REFERENCE
		    "RFC 1965 - Autonomous System Confederations for BGP"
		    "RFC 1771 - Border Gateway Protocol version 4 (BGP-4)"
		
            ::= { bgp 12 }


        bgpConfederationId OBJECT-TYPE
            SYNTAX     INTEGER (0..65535)
            MAX-ACCESS read-only
            STATUS     current
            DESCRIPTION
                    "The local Confederation Identification Number.  A value
		     of zero (0) indicates the absence of this value."
	    REFERENCE
		    "RFC 1965 - Autonomous System Confederations for BGP"
            ::= { bgpConfed 1 }


        bgpPeerConfedTable OBJECT-TYPE
            SYNTAX     SEQUENCE OF BgpPeerConfedEntry
            MAX-ACCESS not-accessible
            STATUS     current
            DESCRIPTION
                    "BGP Peer Confederation Table.  This table contains
		     information on whether a given peer is in the same
		     Confederation as the router."
            ::= { bgpConfed 2 }


        bgpPeerConfedEntry OBJECT-TYPE
            SYNTAX     BgpPeerConfedEntry
            MAX-ACCESS not-accessible
            STATUS     current
            DESCRIPTION
		    "Information on whether a given peer is in the same
		     Confederation as the router."
            AUGMENTS	{ bgpPeerEntry }
            ::= { bgpPeerConfedTable 1 }


        BgpPeerConfedEntry ::= SEQUENCE {
		bgpPeerInConfederation
			TruthValue
                }


	bgpPeerInConfederation OBJECT-TYPE
	    SYNTAX	TruthValue
	    MAX-ACCESS	read-only
	    STATUS	current
	    DESCRIPTION
		    "This value indicates whether the given peer is in our
		     confederation or not."
	    ::= { bgpPeerConfedEntry 1 }

    END

-- 
-- 
--    Copyright (C) The Internet Society (1999).  All Rights Reserved.
-- 
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
-- 
--    The limited permissions granted above are perpetual and will not be
--    revoked by the Internet Society or its successors or assigns.
-- 
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
-- 
-- Expires August 2001
