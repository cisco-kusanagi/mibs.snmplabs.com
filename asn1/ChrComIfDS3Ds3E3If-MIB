ChrComIfDS3Ds3E3If-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfDS3				FROM  Chromatis-MIB
	ifIndex					FROM  RFC1213-MIB
	DS3LineType				FROM  DS3Types-MIB
	DS3ATMMapping				FROM  DS3Types-MIB
	DS3SendLoopbackCode			FROM  DS3Types-MIB
	DS3Loopback				FROM  DS3Types-MIB
	DS3ClockTiming				FROM  DS3Types-MIB
	DS3LineLength				FROM  DS3Types-MIB
	DS3LineCoding				FROM  DS3Types-MIB
	TruthValue				FROM  ChrTyp-MIB
	AlarmVector				FROM  DS3Types-MIB
	AlarmSeverity				FROM  DS3Types-MIB;

-- chrComIfDS3Ds3E3If Table

chrComIfDS3Ds3E3IfTable		OBJECT-TYPE
	SYNTAX		SEQUENCE OF ChrComIfDS3Ds3E3IfEntry
	MAX-ACCESS	not-accessible
	STATUS		current
	DESCRIPTION
	""
	::= { chrComIfDS3 1}

chrComIfDS3Ds3E3IfEntry		OBJECT-TYPE
	SYNTAX		ChrComIfDS3Ds3E3IfEntry
	MAX-ACCESS	not-accessible
	STATUS		current
	DESCRIPTION
	""
	INDEX  {  ifIndex }

--DEFAULT  get-function-async  MNIL_GetRoutine
--DEFAULT  set-function-async  MNIL_SetRoutine
--DEFAULT  next-function-async MNIL_NextRoutine
--DEFAULT  test-function-async MNIL_TestRoutine
--DEFAULT  cookie "Ds3E3If"
	::= { chrComIfDS3Ds3E3IfTable  1 }

ChrComIfDS3Ds3E3IfEntry  ::=
	SEQUENCE  {
	chrComIfDS3DS3LineType		DS3LineType,
	chrComIfDS3DS3ATMMapping		DS3ATMMapping,
	chrComIfDS3DS3SendLoopbackCode	DS3SendLoopbackCode,
	chrComIfDS3DS3Loopback		DS3Loopback,
	chrComIfDS3DS3ClockTiming		DS3ClockTiming,
	chrComIfDS3DS3LineLength		DS3LineLength,
	chrComIfDS3DS3LineCoding		DS3LineCoding,
	chrComIfDS3ForceAIS		TruthValue,
	chrComIfDS3ForceRAI		TruthValue,
	chrComIfDS3AlarmVector		AlarmVector,
	chrComIfDS3AlarmSeverity		AlarmSeverity
}

chrComIfDS3DS3LineType 	OBJECT-TYPE
	SYNTAX		DS3LineType
	MAX-ACCESS 	read-write
	STATUS 		current
	DESCRIPTION
	"Indicates signal type: DS3 or E3."
	::= { chrComIfDS3Ds3E3IfEntry  1 }

chrComIfDS3DS3ATMMapping 	OBJECT-TYPE
	SYNTAX		DS3ATMMapping
	MAX-ACCESS 	read-write
	STATUS 		current
	DESCRIPTION
	"Applicable only to DS3 C-bit Parity ATM application"
	::= { chrComIfDS3Ds3E3IfEntry  2 }

chrComIfDS3DS3SendLoopbackCode 	OBJECT-TYPE
	SYNTAX		DS3SendLoopbackCode
	MAX-ACCESS 	read-write
	STATUS 		current
	DESCRIPTION
	""
	::= { chrComIfDS3Ds3E3IfEntry  3 }

chrComIfDS3DS3Loopback 	OBJECT-TYPE
	SYNTAX		DS3Loopback
	MAX-ACCESS 	read-write
	STATUS 		current
	DESCRIPTION
	""
	::= { chrComIfDS3Ds3E3IfEntry  4 }

chrComIfDS3DS3ClockTiming 	OBJECT-TYPE
	SYNTAX		DS3ClockTiming
	MAX-ACCESS 	read-write
	STATUS 		current
	DESCRIPTION
	""
	::= { chrComIfDS3Ds3E3IfEntry  5 }

chrComIfDS3DS3LineLength 	OBJECT-TYPE
	SYNTAX		DS3LineLength
	MAX-ACCESS 	read-write
	STATUS 		current
	DESCRIPTION
	"NMS will display line length in feet 0 / 250 / (450) / 900"
	::= { chrComIfDS3Ds3E3IfEntry  6 }

chrComIfDS3DS3LineCoding 	OBJECT-TYPE
	SYNTAX		DS3LineCoding
	MAX-ACCESS 	read-write
	STATUS 		current
	DESCRIPTION
	""
	::= { chrComIfDS3Ds3E3IfEntry  7 }

chrComIfDS3ForceAIS 	OBJECT-TYPE
	SYNTAX		TruthValue
	MAX-ACCESS 	read-write
	STATUS 		current
	DESCRIPTION
	""
	::= { chrComIfDS3Ds3E3IfEntry  8 }

chrComIfDS3ForceRAI 	OBJECT-TYPE
	SYNTAX		TruthValue
	MAX-ACCESS 	read-write
	STATUS 		current
	DESCRIPTION
	""
	::= { chrComIfDS3Ds3E3IfEntry  9 }

chrComIfDS3AlarmVector 	OBJECT-TYPE
	SYNTAX		AlarmVector
	MAX-ACCESS 	read-only
	STATUS 		current
	DESCRIPTION
	"The alarms, which reside from bit 8 and on, are minor alarms, which dont cause to changing of operational status of higher layres and dont correlate other alarms in the vector."
	::= { chrComIfDS3Ds3E3IfEntry  10 }

chrComIfDS3AlarmSeverity 	OBJECT-TYPE
	SYNTAX		AlarmSeverity
	MAX-ACCESS 	read-only
	STATUS 		current
	DESCRIPTION
	""
	::= { chrComIfDS3Ds3E3IfEntry  11 }


END
