-------------------------------------------------------------------------------
-- file: ATMStatistics.mib 
--
-- description:
--      This file contains the SNMP definitions for the ATMStatistics area.
--
-- history:
-- $Log: 0.ATMStatistics.mib,v $
-- Revision 1.7.1.2  2000/12/28 13:42:42  cbrohier
-- 31A1634: etm developments merge in the Control Cards in 4.3
--
-- Revision 1.7.1.1.2.2  2000/11/16 09:24:42  eherviau
-- 31A1612: etm developments pre-merge in Control cards
--
-- Revision 1.7.1.1.1.3  2000/09/29 12:59:08  bsizun
-- P.324884: CLP0 Tx Cells counter not provided to the users
--
-- Revision 1.7.1.1.1.2  2000/07/27 17:22:42  bsizun
-- 31A1211: Added Vpa statistics
--
--      31A0632 / 96.01.29 / Wing-Leung Chan / Creation from V1.0 of 
--                                             MIBTemplate.mib
--      31A0632 / 96.02.12 / Wing-Leung Chan / changes per review on 96.01.31
--      31A0632 / 96.02.12 / M. Paquette     / remove first few lines as per
--                                             Wing-Leung's request     
--      08A0001 / 96.05.15 / M. Rehder       / Added validInterval counts and
--                                             VPL/VCL counter tables
--     P240963  / 98.07.16 / Randy Jones     / Changed DESCRIPTION
--                                             clause to reflect post
--                                             UPC counter formation
-- %%history-start%%
-- 1996.03.14 wchan 31A0632: Creation 
-- 1996.04.22 wchan 31A0632: Pickup TCs from new TC file and added 
--   NncExtCounter64 
-- 1996.04.25 wchan 31A0632: changed RowStatus permissions to read-write 
--   (SNMPv1 interoperability) 
-- 1998.04.19 bgemin 62A0032: xDSL 3.1 merge 
-- 1998.07.22 randyj P.00240963: Change DESCRIPTOR Clause of some objects to 
--   reflect post UPC collection. 
-- %%history-end%%
--
-- Copyright 1996 Newbridge Networks Corporation.  All Rights Reserved
-------------------------------------------------------------------------------
NNC-ATM-STATISTICS-MIB DEFINITIONS ::= BEGIN

  IMPORTS
    MODULE-IDENTITY, OBJECT-TYPE,
      Integer32, Counter64
      FROM SNMPv2-SMI
    RowStatus
      FROM SNMPv2-TC
    MODULE-COMPLIANCE, OBJECT-GROUP
      FROM SNMPv2-CONF
    ifIndex
      FROM IF-MIB
    nncExtensions, NncExtCounter64
      FROM NNCGNI0001-SMI
    atmVplVpi, atmVclVpi, atmVclVci
      FROM ATM-MIB
    NncExtIntvlStateType, NncExtAbsIntvlNumberType, NncExtRelIntvlNumberType
      FROM NNC-INTERVAL-STATISTICS-TC-MIB;
                        
  nncAtmStatistics  MODULE-IDENTITY        
    LAST-UPDATED    "9807210330Z"
    ORGANIZATION    "Newbridge Networks Corporation"
    CONTACT-INFO
                    "Newbridge Networks Corporation
                    Postal: 600 March Road
                    Kanata, Ontario
                    Canada K2K 2E6

                    Phone:  +1 613 591 3600
                    Fax:    +1 613 591 3680"
                
    DESCRIPTION "
      This module contains definitions for performance monitoring of the
      ATM layer and it's circuits.

      This MIB module contains the following tables:
        ATM VPL 15 Minute Current Table
        ATM VPL 15 Minute Interval Table
        ATM VPL 1 Hour Current Table
        ATM VPL 1 Hour Interval Table
        ATM VPL Stat Table
        ATM VPL Stat Counter Table

        ATM VCL 15 Minute Current Table
        ATM VCL 15 Minute Interval Table
        ATM VCL 1 Hour Current Table
        ATM VCL 1 Hour Interval Table
        ATM VCL Stat Table
        ATM VCL Stat Counter Table

        nncDepthOfHistoricalStrata

    These tables are heavily influenced by the definition of VPL/VCL
    described in rfc1695, and by the statistic table definitions described
    for Sonet in rfc1595. The number of intervals supported is dependent
    upon resource availibility on any given product, but should nominally
    be 32. To avoid building in massive amounts of storage, some products
    may adopt a bulk collection scheme. 

    Intervals:
    Statistics on the performance of VPL/VCLs are collected over a
	historical stratum of up to a maximum of M intervals. The value of M
	is a function of a product's storage capability.

	The intervals can be either 15 minutes or 1 hour and are aligned to
	the quarter or one hour, respectively, of a wall clock. The current
	interval spans back to the last 15 minute or 1 hour tick on the wall
	clock. Continuing along the timeline from that point is the most
	recently completed interval and has an index of 1. The previous
	interval has an index of 2 and so on. Note that the oldest interval
	may be incomplete since the statistic collection may have been
	enabled offset to the quarter or one hour tick.

		   t
		   0          -1i         -2i         -3i
	===========|===========|===========|===========|===========
	  current      N = 1       N = 2       N = 3       N = 4    ... N = M
	  interval

     
    Counters:
	The following is understood for each counter in this MIB:
	  - OAM cells are included in counts
	  - idle and unassigned cells are not counted
	  - valid cells are those that have passed HEC and have assigned VPI/VCI
	  - admitted cells have a connection
	  
     This module also contains definitions for performance monitoring of 
     Virtual Path Aggregation (VPA) - also known as VCC to VPC Traffic
     Aggregation - and implemented as Shaped Trunk Group.
     Only egress VPA statistics are provided.
      
     The following tables have been added :
        ATM VPA Short (15 minutes) Current Table
        ATM VPA Short (15 Minutes) Interval Table
        ATM VPA Long  (1 Hour) Current Table
        ATM VPA Long  (1 Hour) Interval Table
 
     Intervals:
     two 15-minute intervals are provided : current and previous
     two 1-hour intervals are provided : current and previous.
     
    "
      
  ::= { nncExtensions 29 }

  nncAtmStatisticsObjects OBJECT IDENTIFIER     ::= { nncAtmStatistics 1 }
  nncAtmStatisticsTraps OBJECT IDENTIFIER       ::= { nncAtmStatistics 2 }
  nncAtmStatisticsGroups OBJECT IDENTIFIER      ::= { nncAtmStatistics 3 }
  nncAtmStatisticsCompliances OBJECT IDENTIFIER ::= { nncAtmStatistics 4 }

--------------------------------------------------------------------------------
-- Virtual Path Links 15 Minute Current Statistics Table
--------------------------------------------------------------------------------

  nncVpl15MinCurrentTable       OBJECT-TYPE 
        SYNTAX                  SEQUENCE OF NncVpl15MinCurrentEntry 
        MAX-ACCESS              not-accessible
        STATUS                  current
        DESCRIPTION             "The nncVpl15MinCurrentTable contains
                                objects for monitoring the performance of a
                                VPL during the current 15 minute interval."
  ::= { nncAtmStatisticsObjects 1 }

  nncVpl15MinCurrentEntry       OBJECT-TYPE 
        SYNTAX                  NncVpl15MinCurrentEntry 
        MAX-ACCESS              not-accessible
        STATUS                  current
        DESCRIPTION             "An entry in the 15 minute current
                                statistics table. Each conceptual row
                                contains current statistics for a
                                particular VPL."
        INDEX                   { ifIndex, atmVplVpi }
  ::= { nncVpl15MinCurrentTable 1 }

  NncVpl15MinCurrentEntry ::=
    SEQUENCE {
      nncVpl15MinCurrentState                   NncExtIntvlStateType,
      nncVpl15MinCurrentAbsoluteIntervalNumber  NncExtAbsIntvlNumberType,
      nncVpl15MinCurrentClp0And1InCells         NncExtCounter64,
      nncVpl15MinCurrentClp0InCells             NncExtCounter64,
      nncVpl15MinCurrentDiscardClp0And1InCells  NncExtCounter64,
      nncVpl15MinCurrentDiscardClp0InCells      NncExtCounter64,
      nncVpl15MinCurrentTaggedInCells           NncExtCounter64,
      nncVpl15MinCurrentClp0And1OutCells        NncExtCounter64,
      nncVpl15MinCurrentClp0OutCells            NncExtCounter64
    }
  

  nncVpl15MinCurrentState       OBJECT-TYPE
        SYNTAX                  NncExtIntvlStateType
        MAX-ACCESS              read-only
        STATUS                  current
        DESCRIPTION             "The state of the current interval. The
                                object provides a status for those entries
                                which have been reset by the user, or have
                                been subject to a wall clock time change.
                                "
  ::= { nncVpl15MinCurrentEntry 1 }

  nncVpl15MinCurrentAbsoluteIntervalNumber      OBJECT-TYPE
        SYNTAX                  NncExtAbsIntvlNumberType
        MAX-ACCESS              read-only
        STATUS                  current
        DESCRIPTION             "The absolute interval number of this
                                interval."
  ::= { nncVpl15MinCurrentEntry 2 }

  nncVpl15MinCurrentClp0And1InCells     OBJECT-TYPE
        SYNTAX                  NncExtCounter64
        MAX-ACCESS              read-only
        STATUS                  current
        DESCRIPTION             "Number of valid cells admitted at ingress
                                on the VPL with CLP=0 or 1, including those
                                with header errors corrected. This counter
                                is formed after the UPC function."
  ::= { nncVpl15MinCurrentEntry 3 }

  nncVpl15MinCurrentClp0InCells OBJECT-TYPE
        SYNTAX                  NncExtCounter64
        MAX-ACCESS              read-only
        STATUS                  current
        DESCRIPTION             "Number of valid cells admitted at ingress
                                on the VPL with CLP=0, including those with
                                header errors corrected."
  ::= { nncVpl15MinCurrentEntry 4 }

  nncVpl15MinCurrentDiscardClp0And1InCells      OBJECT-TYPE
        SYNTAX                  NncExtCounter64
        MAX-ACCESS              read-only
        STATUS                  current
        DESCRIPTION             "Number of valid cells with CLP=1 discarded
                                at ingress by ingress traffic policing,
                                including those with header errors corrected."
  ::= { nncVpl15MinCurrentEntry 5 }

  nncVpl15MinCurrentDiscardClp0InCells  OBJECT-TYPE
        SYNTAX                  NncExtCounter64
        MAX-ACCESS              read-only
        STATUS                  current
        DESCRIPTION             "Number of valid cells with CLP=0 discarded
                                at ingress by ingress traffic policing,
                                including those with header errors corrected."
  ::= { nncVpl15MinCurrentEntry 6 }

  nncVpl15MinCurrentTaggedInCells       OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVpl15MinCurrentEntry 7 }

  nncVpl15MinCurrentClp0And1OutCells    OBJECT-TYPE
        SYNTAX                  NncExtCounter64
        MAX-ACCESS              read-only
        STATUS                  current
        DESCRIPTION             "Number of valid cells transmitted at egress
                                on the VPL with CLP=0 or 1."
  ::= { nncVpl15MinCurrentEntry 8 }

  nncVpl15MinCurrentClp0OutCells        OBJECT-TYPE
        SYNTAX                  NncExtCounter64
        MAX-ACCESS              read-only
        STATUS                  current
        DESCRIPTION             "Number of valid cells transmitted at egress
                                on the VPL with CLP=0."
  ::= { nncVpl15MinCurrentEntry 9 }




--------------------------------------------------------------------------------
-- Virtual Path Links 15 Minute Interval Statistics Table
--------------------------------------------------------------------------------

  nncVpl15MinIntervalTable      OBJECT-TYPE 
        SYNTAX                  SEQUENCE OF NncVpl15MinIntervalEntry 
        MAX-ACCESS              not-accessible
        STATUS                  current
        DESCRIPTION             "The nncVpl15MinIntervalTable contains
                                objects for monitoring the performance of a
                                virtual path link over a historical stratum
                                of M 15 minute intervals.
                                "
  ::= { nncAtmStatisticsObjects 2 }


  nncVpl15MinIntervalEntry      OBJECT-TYPE 
        SYNTAX                  NncVpl15MinIntervalEntry 
        MAX-ACCESS              not-accessible
        STATUS                  current
        DESCRIPTION             "An entry in the 15 minute interval
                                statistics table. Each conceptual row
                                contains statistics for a particular
                                VPL and interval."
  INDEX                         { ifIndex, atmVplVpi,
                                  nncVpl15MinIntervalNumber }
  ::= { nncVpl15MinIntervalTable 1 }

  NncVpl15MinIntervalEntry ::=
    SEQUENCE {
      nncVpl15MinIntervalNumber                 NncExtRelIntvlNumberType,
      nncVpl15MinIntervalState                  NncExtIntvlStateType,
      nncVpl15MinIntervalAbsoluteIntervalNumber NncExtAbsIntvlNumberType,
      nncVpl15MinIntervalClp0And1InCells        NncExtCounter64,
      nncVpl15MinIntervalClp0InCells            NncExtCounter64,
      nncVpl15MinIntervalDiscardClp0And1InCells NncExtCounter64,
      nncVpl15MinIntervalDiscardClp0InCells     NncExtCounter64,
      nncVpl15MinIntervalTaggedInCells          NncExtCounter64,
      nncVpl15MinIntervalClp0And1OutCells       NncExtCounter64,
      nncVpl15MinIntervalClp0OutCells           NncExtCounter64
    }
  

  nncVpl15MinIntervalNumber     OBJECT-TYPE
        SYNTAX                  NncExtRelIntvlNumberType
        MAX-ACCESS              not-accessible
        STATUS                  current
        DESCRIPTION             "The interval number (N) of the statistics in
                                this row."
  ::= { nncVpl15MinIntervalEntry 1 }

  nncVpl15MinIntervalState      OBJECT-TYPE
        SYNTAX                  NncExtIntvlStateType
        MAX-ACCESS              read-only
        STATUS                  current
        DESCRIPTION             "The state of the interval represented by
                                this row. The object provides a status for
                                those entries which have been reset by the
                                user, or have been subject to a wall clock
                                time change.
                                "
  ::= { nncVpl15MinIntervalEntry 2 }

  nncVpl15MinIntervalAbsoluteIntervalNumber     OBJECT-TYPE
        SYNTAX                  NncExtAbsIntvlNumberType
        MAX-ACCESS              read-only
        STATUS                  current
        DESCRIPTION             "The absolute interval number of this
                                interval."
  ::= { nncVpl15MinIntervalEntry 3 }

  nncVpl15MinIntervalClp0And1InCells    OBJECT-TYPE
        SYNTAX                  NncExtCounter64
        MAX-ACCESS              read-only
        STATUS                  current
        DESCRIPTION             "Number of valid cells admitted at ingress
                                on the VPL with CLP=0 or 1, including those
                                with header errors corrected. This counter
                                is formed after the UPC function."
  ::= { nncVpl15MinIntervalEntry 4 }

  nncVpl15MinIntervalClp0InCells        OBJECT-TYPE
        SYNTAX                  NncExtCounter64
        MAX-ACCESS              read-only
        STATUS                  current
        DESCRIPTION             "Number of valid cells admitted at ingress
                                on the VPL with CLP=0, including those with
                                header errors corrected."
  ::= { nncVpl15MinIntervalEntry 5 }

  nncVpl15MinIntervalDiscardClp0And1InCells     OBJECT-TYPE
        SYNTAX                  NncExtCounter64
        MAX-ACCESS              read-only
        STATUS                  current
        DESCRIPTION             "Number of valid cells with CLP=1 discarded
                                at ingress by ingress traffic policing,
                                including those with header errors corrected."
  ::= { nncVpl15MinIntervalEntry 6 }

  nncVpl15MinIntervalDiscardClp0InCells OBJECT-TYPE
        SYNTAX                  NncExtCounter64
        MAX-ACCESS              read-only
        STATUS                  current
        DESCRIPTION             "Number of valid cells with CLP=0 discarded
                                at ingress by ingress traffic policing,
                                including those with header errors corrected."
  ::= { nncVpl15MinIntervalEntry 7 }

  nncVpl15MinIntervalTaggedInCells      OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVpl15MinIntervalEntry 8 }

  nncVpl15MinIntervalClp0And1OutCells   OBJECT-TYPE
        SYNTAX                  NncExtCounter64
        MAX-ACCESS              read-only
        STATUS                  current
        DESCRIPTION             "Number of valid cells transmitted at egress
                                on the VPL with CLP=0 or 1."
  ::= { nncVpl15MinIntervalEntry 9 }

  nncVpl15MinIntervalClp0OutCells       OBJECT-TYPE
        SYNTAX                  NncExtCounter64
        MAX-ACCESS              read-only
        STATUS                  current
        DESCRIPTION             "Number of valid cells transmitted at egress
                                on the VPL with CLP=0."
  ::= { nncVpl15MinIntervalEntry 10 }




--------------------------------------------------------------------------------
-- Virtual Path Links 1 Hour Current Statistics Table
--------------------------------------------------------------------------------

  nncVpl1HourCurrentTable       OBJECT-TYPE 
        SYNTAX                  SEQUENCE OF NncVpl1HourCurrentEntry 
        MAX-ACCESS              not-accessible
        STATUS                  current
        DESCRIPTION             "The nncVpl1HourCurrentTable contains
                                objects for monitoring the performance of a
                                VPL during the current 1 hour interval.
                                "
  ::= { nncAtmStatisticsObjects 3 }


  nncVpl1HourCurrentEntry       OBJECT-TYPE 
        SYNTAX                  NncVpl1HourCurrentEntry 
        MAX-ACCESS              not-accessible
        STATUS                  current
        DESCRIPTION             "An entry in the 1 hour current statistics
                                table. Each conceptual row contains current
                                statistics for a particular VPL. 
                                
                                By default, 1 Hour statistics are not
                                gathered. In order to enable gathering of
                                these statistics, a row must be created.

                                The semantics of nncVpl1HourCurrentRowStatus
                                is the same as the definition of RowStatus
                                in rfc1443 with the following constraints.

                                1. Creation is done in one step, that is, by
                                   setting the nncVpl1HourCurrentRowStatus
                                   column to createAndGo. Setting the column
                                   to createAndWait will return wrongValue.
                                2. The VPI specified in the instance must
                                   be an endpoint that is currently used in
                                   a VPL otherwise the agent will return
                                   return inconsistentValue and no row is
                                   created.
                                3. If the maximum number of rows (an agent
                                   limitation) has been reached, 
                                   resourceUnavailable is returned and no
                                   row is created.
                                4. Creation of a current row will also enable
                                   the corresponding interval table whose
                                   rows will be created when intervals are
                                   completed.
                                5. Statistics collection is disabled by
                                   setting the column to destroy. This will
                                   also remove all corresponding rows in
                                   the interval table.
                                "
  INDEX                         { ifIndex, atmVplVpi }
  ::= { nncVpl1HourCurrentTable 1 }

  NncVpl1HourCurrentEntry ::=
    SEQUENCE {
      nncVpl1HourCurrentState                   NncExtIntvlStateType,
      nncVpl1HourCurrentAbsoluteIntervalNumber  NncExtAbsIntvlNumberType,
      nncVpl1HourCurrentClp0And1InCells         NncExtCounter64,
      nncVpl1HourCurrentClp0InCells             NncExtCounter64,
      nncVpl1HourCurrentDiscardClp0And1InCells  NncExtCounter64,
      nncVpl1HourCurrentDiscardClp0InCells      NncExtCounter64,
      nncVpl1HourCurrentTaggedInCells           NncExtCounter64,
      nncVpl1HourCurrentClp0And1OutCells        NncExtCounter64,
      nncVpl1HourCurrentClp0OutCells            NncExtCounter64,
      nncVpl1HourCurrentRowStatus               RowStatus
    }


  nncVpl1HourCurrentState       OBJECT-TYPE
        SYNTAX                  NncExtIntvlStateType
        MAX-ACCESS              read-only
        STATUS                  current
        DESCRIPTION             "The state of the current interval. The
                                object provides a status for those entries
                                which have been reset by the user, or have
                                been subject to a wall clock time change.
                                "
  ::= { nncVpl1HourCurrentEntry 1 }

  nncVpl1HourCurrentAbsoluteIntervalNumber      OBJECT-TYPE
        SYNTAX                  NncExtAbsIntvlNumberType
        MAX-ACCESS              read-only
        STATUS                  current
        DESCRIPTION             "The absolute interval number of this
                                interval."
  ::= { nncVpl1HourCurrentEntry 2 }

  nncVpl1HourCurrentClp0And1InCells     OBJECT-TYPE
        SYNTAX                  NncExtCounter64
        MAX-ACCESS              read-only
        STATUS                  current
        DESCRIPTION             "Number of valid cells admitted at ingress
                                on the VPL with CLP=0 or 1, including those
                                with header errors corrected. This counter
                                is formed after the UPC function."
  ::= { nncVpl1HourCurrentEntry 3 }

  nncVpl1HourCurrentClp0InCells OBJECT-TYPE
        SYNTAX                  NncExtCounter64
        MAX-ACCESS              read-only
        STATUS                  current
        DESCRIPTION             "Number of valid cells admitted at ingress
                                on the VPL with CLP=0, including those with
                                header errors corrected."
  ::= { nncVpl1HourCurrentEntry 4 }

  nncVpl1HourCurrentDiscardClp0And1InCells      OBJECT-TYPE
        SYNTAX                  NncExtCounter64
        MAX-ACCESS              read-only
        STATUS                  current
        DESCRIPTION             "Number of valid cells with CLP=1 discarded
                                at ingress by ingress traffic policing,
                                including those with header errors corrected."
  ::= { nncVpl1HourCurrentEntry 5 }

  nncVpl1HourCurrentDiscardClp0InCells  OBJECT-TYPE
        SYNTAX                  NncExtCounter64
        MAX-ACCESS              read-only
        STATUS                  current
        DESCRIPTION             "Number of valid cells with CLP=0 discarded
                                at ingress by ingress traffic policing,
                                including those with header errors corrected."
  ::= { nncVpl1HourCurrentEntry 6 }

  nncVpl1HourCurrentTaggedInCells       OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVpl1HourCurrentEntry 7 }

  nncVpl1HourCurrentClp0And1OutCells    OBJECT-TYPE
        SYNTAX                  NncExtCounter64
        MAX-ACCESS              read-only
        STATUS                  current
        DESCRIPTION             "Number of valid cells transmitted at egress
                                on the VPL with CLP=0 or 1."
  ::= { nncVpl1HourCurrentEntry 8 }

  nncVpl1HourCurrentClp0OutCells        OBJECT-TYPE
        SYNTAX                  NncExtCounter64
        MAX-ACCESS              read-only
        STATUS                  current
        DESCRIPTION             "Number of valid cells transmitted at egress
                                on the VPL with CLP=0."
  ::= { nncVpl1HourCurrentEntry 9 }

  nncVpl1HourCurrentRowStatus           OBJECT-TYPE
        SYNTAX                  RowStatus
        MAX-ACCESS              read-write
        STATUS                  current
        DESCRIPTION             "This object is used to create and delete 
                                rows in this table.
                                The following sets are invalid: createAndWait,
                                active, and notInService. Such sets will
                                return wrongValue.
                                "
  ::= { nncVpl1HourCurrentEntry 10 }



--------------------------------------------------------------------------------
-- Virtual Path Links 1 Hour Interval Statistics Table
--------------------------------------------------------------------------------

  nncVpl1HourIntervalTable      OBJECT-TYPE 
        SYNTAX                  SEQUENCE OF NncVpl1HourIntervalEntry 
        MAX-ACCESS              not-accessible
        STATUS                  current
        DESCRIPTION             "The nncVpl1HourIntervalTable contains
                                objects for monitoring the performance of a
                                virtual path link over a historical stratum
                                of M 1 hour intervals. 
                                "
  ::= { nncAtmStatisticsObjects 4 }


  nncVpl1HourIntervalEntry      OBJECT-TYPE 
        SYNTAX                  NncVpl1HourIntervalEntry 
        MAX-ACCESS              not-accessible
        STATUS                  current
        DESCRIPTION             "An entry in the 1 hour interval statistics
                                table. Each conceptual row contains
                                statistics for a particular VPL and interval. 
                                
                                These rows are automatically created if
                                there is a corresponding entry in the 1 hour
                                current table.
                                "
  INDEX                         { ifIndex, atmVplVpi,
                                  nncVpl1HourIntervalNumber }
  ::= { nncVpl1HourIntervalTable 1 }

  NncVpl1HourIntervalEntry ::=
    SEQUENCE {
      nncVpl1HourIntervalNumber                 NncExtRelIntvlNumberType,
      nncVpl1HourIntervalState                  NncExtIntvlStateType,
      nncVpl1HourIntervalAbsoluteIntervalNumber NncExtAbsIntvlNumberType,
      nncVpl1HourIntervalClp0And1InCells        NncExtCounter64,
      nncVpl1HourIntervalClp0InCells            NncExtCounter64,
      nncVpl1HourIntervalDiscardClp0And1InCells NncExtCounter64,
      nncVpl1HourIntervalDiscardClp0InCells     NncExtCounter64,
      nncVpl1HourIntervalTaggedInCells          NncExtCounter64,
      nncVpl1HourIntervalClp0And1OutCells       NncExtCounter64,
      nncVpl1HourIntervalClp0OutCells           NncExtCounter64
    }
  

  nncVpl1HourIntervalNumber     OBJECT-TYPE
        SYNTAX                  NncExtRelIntvlNumberType
        MAX-ACCESS              not-accessible
        STATUS                  current
        DESCRIPTION             "The interval number (N) of the statistics in
                                this row."
  ::= { nncVpl1HourIntervalEntry 1 }

  nncVpl1HourIntervalState      OBJECT-TYPE
        SYNTAX                  NncExtIntvlStateType
        MAX-ACCESS              read-only
        STATUS                  current
        DESCRIPTION             "The state of the interval represented by
                                this row. The object provides a status for
                                those entries which have been reset by the
                                user, or have been subject to a wall clock
                                time change.
                                "
  ::= { nncVpl1HourIntervalEntry 2 }

  nncVpl1HourIntervalAbsoluteIntervalNumber     OBJECT-TYPE
        SYNTAX                  NncExtAbsIntvlNumberType
        MAX-ACCESS              read-only
        STATUS                  current
        DESCRIPTION             "The absolute interval number of this
                                interval."
  ::= { nncVpl1HourIntervalEntry 3 }

  nncVpl1HourIntervalClp0And1InCells    OBJECT-TYPE
        SYNTAX                  NncExtCounter64
        MAX-ACCESS              read-only
        STATUS                  current
        DESCRIPTION             "Number of valid cells admitted at ingress
                                on the VPL with CLP=0 or 1, including those
                                with header errors corrected. This counter
                                is formed after the UPC function."
  ::= { nncVpl1HourIntervalEntry 4 }

  nncVpl1HourIntervalClp0InCells        OBJECT-TYPE
        SYNTAX                  NncExtCounter64
        MAX-ACCESS              read-only
        STATUS                  current
        DESCRIPTION             "Number of valid cells admitted at ingress
                                on the VPL with CLP=0, including those with
                                header errors corrected."
  ::= { nncVpl1HourIntervalEntry 5 }

  nncVpl1HourIntervalDiscardClp0And1InCells     OBJECT-TYPE
        SYNTAX                  NncExtCounter64
        MAX-ACCESS              read-only
        STATUS                  current
        DESCRIPTION             "Number of valid cells with CLP=1 discarded
                                at ingress by ingress traffic policing,
                                including those with header errors corrected."
  ::= { nncVpl1HourIntervalEntry 6 }

  nncVpl1HourIntervalDiscardClp0InCells OBJECT-TYPE
        SYNTAX                  NncExtCounter64
        MAX-ACCESS              read-only
        STATUS                  current
        DESCRIPTION             "Number of valid cells with CLP=0 discarded
                                at ingress by ingress traffic policing,
                                including those with header errors corrected."
  ::= { nncVpl1HourIntervalEntry 7 }

  nncVpl1HourIntervalTaggedInCells      OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVpl1HourIntervalEntry 8 }

  nncVpl1HourIntervalClp0And1OutCells   OBJECT-TYPE
        SYNTAX                  NncExtCounter64
        MAX-ACCESS              read-only
        STATUS                  current
        DESCRIPTION             "Number of valid cells transmitted at egress
                                on the VPL with CLP=0 or 1."
  ::= { nncVpl1HourIntervalEntry 9 }

  nncVpl1HourIntervalClp0OutCells       OBJECT-TYPE
        SYNTAX                  NncExtCounter64
        MAX-ACCESS              read-only
        STATUS                  current
        DESCRIPTION             "Number of valid cells transmitted at egress
                                on the VPL with CLP=0."
  ::= { nncVpl1HourIntervalEntry 10 }


--------------------------------------------------------------------------------
-- Virtual Path Links Statistics Table
--------------------------------------------------------------------------------

  nncVplStatTable       OBJECT-TYPE 
        SYNTAX                  SEQUENCE OF NncVplStatEntry 
        MAX-ACCESS              not-accessible
        STATUS                  current
        DESCRIPTION             "The nncVplStatTable contains objects
                                for monitoring the accumulated performance 
                                of a VPL since measurement started on the VPL."
  ::= { nncAtmStatisticsObjects 10 }


  nncVplStatEntry       OBJECT-TYPE 
        SYNTAX                  NncVplStatEntry 
        MAX-ACCESS              not-accessible
        STATUS                  current
        DESCRIPTION             "An entry in the Vpl Stat table.
                                Each conceptual row contains accumulated 
                                statistics for a particular VPL."
        INDEX                   { ifIndex, atmVplVpi }
  ::= { nncVplStatTable 1 }

  NncVplStatEntry ::=
    SEQUENCE {
      nncVplStatClp0And1InCells         NncExtCounter64,
      nncVplStatClp0InCells             NncExtCounter64,
      nncVplStatDiscardClp0And1InCells  NncExtCounter64,
      nncVplStatDiscardClp0InCells      NncExtCounter64,
      nncVplStatTaggedInCells           NncExtCounter64,
      nncVplStatClp0And1OutCells        NncExtCounter64,
      nncVplStatClp0OutCells            NncExtCounter64
    }
  
  nncVplStatClp0And1InCells     OBJECT-TYPE
        SYNTAX                  NncExtCounter64
        MAX-ACCESS              read-only
        STATUS                  current
        DESCRIPTION             "Number of valid cells admitted at ingress
                                on the VPL with CLP=0 or 1, including those
                                with header errors corrected. This counter
                                is formed after the UPC function."
  ::= { nncVplStatEntry 1 }

  nncVplStatClp0InCells OBJECT-TYPE
        SYNTAX                  NncExtCounter64
        MAX-ACCESS              read-only
        STATUS                  current
        DESCRIPTION             "Number of valid cells admitted at ingress
                                on the VPL with CLP=0, including those with
                                header errors corrected."
  ::= { nncVplStatEntry 2 }

  nncVplStatDiscardClp0And1InCells      OBJECT-TYPE
        SYNTAX                  NncExtCounter64
        MAX-ACCESS              read-only
        STATUS                  current
        DESCRIPTION             "Number of valid cells with CLP=1 discarded
                                at ingress by ingress traffic policing,
                                including those with header errors corrected."
  ::= { nncVplStatEntry 3 }

  nncVplStatDiscardClp0InCells  OBJECT-TYPE
        SYNTAX                  NncExtCounter64
        MAX-ACCESS              read-only
        STATUS                  current
        DESCRIPTION             "Number of valid cells with CLP=0 discarded
                                at ingress by ingress traffic policing,
                                including those with header errors corrected."
  ::= { nncVplStatEntry 4 }

  nncVplStatTaggedInCells       OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVplStatEntry 5 }

  nncVplStatClp0And1OutCells    OBJECT-TYPE
        SYNTAX                  NncExtCounter64
        MAX-ACCESS              read-only
        STATUS                  current
        DESCRIPTION             "Number of valid cells transmitted at egress
                                on the VPL with CLP=0 or 1."
  ::= { nncVplStatEntry 6 }

  nncVplStatClp0OutCells        OBJECT-TYPE
        SYNTAX                  NncExtCounter64
        MAX-ACCESS              read-only
        STATUS                  current
        DESCRIPTION             "Number of valid cells transmitted at egress
                                on the VPL with CLP=0."
  ::= { nncVplStatEntry 7 }


--------------------------------------------------------------------------------
-- Virtual Channel Links 15 Minute Current Statistics Table
--------------------------------------------------------------------------------

  nncVcl15MinCurrentTable       OBJECT-TYPE 
        SYNTAX                  SEQUENCE OF NncVcl15MinCurrentEntry 
        MAX-ACCESS              not-accessible
        STATUS                  current
        DESCRIPTION             "The nncVcl15MinCurrentTable contains
                                objects for monitoring the performance of a
                                VCL during the current 15 minute interval."
  ::= { nncAtmStatisticsObjects 5 }


  nncVcl15MinCurrentEntry       OBJECT-TYPE 
        SYNTAX                  NncVcl15MinCurrentEntry 
        MAX-ACCESS              not-accessible
        STATUS                  current
        DESCRIPTION             "An entry in the 15 minute current
                                statistics table. Each conceptual row
                                contains current statistics for a
                                particular VCL."
        INDEX                   { ifIndex, atmVclVpi, atmVclVci }
  ::= { nncVcl15MinCurrentTable 1 }

  NncVcl15MinCurrentEntry ::=
    SEQUENCE {
      nncVcl15MinCurrentState                   NncExtIntvlStateType,
      nncVcl15MinCurrentAbsoluteIntervalNumber  NncExtAbsIntvlNumberType,
      nncVcl15MinCurrentClp0And1InCells         NncExtCounter64,
      nncVcl15MinCurrentClp0InCells             NncExtCounter64,
      nncVcl15MinCurrentDiscardClp0And1InCells  NncExtCounter64,
      nncVcl15MinCurrentDiscardClp0InCells      NncExtCounter64,
      nncVcl15MinCurrentTaggedInCells           NncExtCounter64,
      nncVcl15MinCurrentClp0And1OutCells        NncExtCounter64,
      nncVcl15MinCurrentClp0OutCells            NncExtCounter64
    }
  

  nncVcl15MinCurrentState       OBJECT-TYPE
        SYNTAX                  NncExtIntvlStateType
        MAX-ACCESS              read-only
        STATUS                  current
        DESCRIPTION             "The state of the current interval. The
                                object provides a status for those entries
                                which have been reset by the user, or have
                                been subject to a wall clock time change.
                                "
  ::= { nncVcl15MinCurrentEntry 1 }

  nncVcl15MinCurrentAbsoluteIntervalNumber      OBJECT-TYPE
        SYNTAX                  NncExtAbsIntvlNumberType
        MAX-ACCESS              read-only
        STATUS                  current
        DESCRIPTION             "The absolute interval number of this
                                interval."
  ::= { nncVcl15MinCurrentEntry 2 }

  nncVcl15MinCurrentClp0And1InCells     OBJECT-TYPE
        SYNTAX                  NncExtCounter64
        MAX-ACCESS              read-only
        STATUS                  current
        DESCRIPTION             "Number of valid cells admitted at ingress
                                on the VCL with CLP=0 or 1, including those
                                with header errors corrected. This counter
                                is formed after the UPC function."
  ::= { nncVcl15MinCurrentEntry 3 }

  nncVcl15MinCurrentClp0InCells OBJECT-TYPE
        SYNTAX                  NncExtCounter64
        MAX-ACCESS              read-only
        STATUS                  current
        DESCRIPTION             "Number of valid cells admitted at ingress
                                on the VCL with CLP=0, including those with
                                header errors corrected."
  ::= { nncVcl15MinCurrentEntry 4 }

  nncVcl15MinCurrentDiscardClp0And1InCells      OBJECT-TYPE
        SYNTAX                  NncExtCounter64
        MAX-ACCESS              read-only
        STATUS                  current
        DESCRIPTION             "Number of valid cells with CLP=1 discarded
                                at ingress by ingress traffic policing,
                                including those with header errors corrected."
  ::= { nncVcl15MinCurrentEntry 5 }

  nncVcl15MinCurrentDiscardClp0InCells  OBJECT-TYPE
        SYNTAX                  NncExtCounter64
        MAX-ACCESS              read-only
        STATUS                  current
        DESCRIPTION             "Number of valid cells with CLP=0 discarded
                                at ingress by ingress traffic policing,
                                including those with header errors corrected."
  ::= { nncVcl15MinCurrentEntry 6 }

  nncVcl15MinCurrentTaggedInCells       OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVcl15MinCurrentEntry 7 }

  nncVcl15MinCurrentClp0And1OutCells    OBJECT-TYPE
        SYNTAX                  NncExtCounter64
        MAX-ACCESS              read-only
        STATUS                  current
        DESCRIPTION             "Number of valid cells transmitted at egress
                                on the VCL with CLP=0 or 1."
  ::= { nncVcl15MinCurrentEntry 8 }

  nncVcl15MinCurrentClp0OutCells        OBJECT-TYPE
        SYNTAX                  NncExtCounter64
        MAX-ACCESS              read-only
        STATUS                  current
        DESCRIPTION             "Number of valid cells transmitted at egress
                                on the VCL with CLP=0."
  ::= { nncVcl15MinCurrentEntry 9 }




--------------------------------------------------------------------------------
-- Virtual Channel Links 15 Minute Interval Statistics Table
--------------------------------------------------------------------------------

  nncVcl15MinIntervalTable      OBJECT-TYPE 
        SYNTAX                  SEQUENCE OF NncVcl15MinIntervalEntry 
        MAX-ACCESS              not-accessible
        STATUS                  current
        DESCRIPTION             "The nncVcl15MinIntervalTable contains
                                objects for monitoring the performance of a
                                virtual channel link over a historical stratum
                                of M 15 minute intervals.
                                "
  ::= { nncAtmStatisticsObjects 6 }


  nncVcl15MinIntervalEntry      OBJECT-TYPE 
        SYNTAX                  NncVcl15MinIntervalEntry 
        MAX-ACCESS              not-accessible
        STATUS                  current
        DESCRIPTION             "An entry in the 15 minute interval
                                statistics table. Each conceptual row
                                contains statistics for a particular
                                VCL and interval."
  INDEX                         { ifIndex, atmVclVpi, atmVclVci,
                                  nncVcl15MinIntervalNumber }
  ::= { nncVcl15MinIntervalTable 1 }

  NncVcl15MinIntervalEntry ::=
    SEQUENCE {
      nncVcl15MinIntervalNumber                 NncExtRelIntvlNumberType,
      nncVcl15MinIntervalState                  NncExtIntvlStateType,
      nncVcl15MinIntervalAbsoluteIntervalNumber NncExtAbsIntvlNumberType,
      nncVcl15MinIntervalClp0And1InCells        NncExtCounter64,
      nncVcl15MinIntervalClp0InCells            NncExtCounter64,
      nncVcl15MinIntervalDiscardClp0And1InCells NncExtCounter64,
      nncVcl15MinIntervalDiscardClp0InCells     NncExtCounter64,
      nncVcl15MinIntervalTaggedInCells          NncExtCounter64,
      nncVcl15MinIntervalClp0And1OutCells       NncExtCounter64,
      nncVcl15MinIntervalClp0OutCells           NncExtCounter64
    }
  

  nncVcl15MinIntervalNumber     OBJECT-TYPE
        SYNTAX                  NncExtRelIntvlNumberType
        MAX-ACCESS              not-accessible
        STATUS                  current
        DESCRIPTION             "The interval number (N) of the statistics in
                                this row."
  ::= { nncVcl15MinIntervalEntry 1 }

  nncVcl15MinIntervalState      OBJECT-TYPE
        SYNTAX                  NncExtIntvlStateType
        MAX-ACCESS              read-only
        STATUS                  current
        DESCRIPTION             "The state of the interval represented by
                                this row. The object provides a status for
                                those entries which have been reset by the
                                user, or have been subject to a wall clock
                                time change.
                                "
  ::= { nncVcl15MinIntervalEntry 2 }

  nncVcl15MinIntervalAbsoluteIntervalNumber     OBJECT-TYPE
        SYNTAX                  NncExtAbsIntvlNumberType
        MAX-ACCESS              read-only
        STATUS                  current
        DESCRIPTION             "The absolute interval number of this
                                interval."
  ::= { nncVcl15MinIntervalEntry 3 }

  nncVcl15MinIntervalClp0And1InCells    OBJECT-TYPE
        SYNTAX                  NncExtCounter64
        MAX-ACCESS              read-only
        STATUS                  current
        DESCRIPTION             "Number of valid cells admitted at ingress
                                on the VCL with CLP=0 or 1, including those
                                with header errors corrected. This counter
                                is formed after the UPC function."
  ::= { nncVcl15MinIntervalEntry 4 }

  nncVcl15MinIntervalClp0InCells        OBJECT-TYPE
        SYNTAX                  NncExtCounter64
        MAX-ACCESS              read-only
        STATUS                  current
        DESCRIPTION             "Number of valid cells admitted at ingress
                                on the VCL with CLP=0, including those with
                                header errors corrected."
  ::= { nncVcl15MinIntervalEntry 5 }

  nncVcl15MinIntervalDiscardClp0And1InCells     OBJECT-TYPE
        SYNTAX                  NncExtCounter64
        MAX-ACCESS              read-only
        STATUS                  current
        DESCRIPTION             "Number of valid cells with CLP=1 discarded
                                at ingress by ingress traffic policing,
                                including those with header errors corrected."
  ::= { nncVcl15MinIntervalEntry 6 }

  nncVcl15MinIntervalDiscardClp0InCells OBJECT-TYPE
        SYNTAX                  NncExtCounter64
        MAX-ACCESS              read-only
        STATUS                  current
        DESCRIPTION             "Number of valid cells with CLP=0 discarded
                                at ingress by ingress traffic policing,
                                including those with header errors corrected."
  ::= { nncVcl15MinIntervalEntry 7 }

  nncVcl15MinIntervalTaggedInCells      OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVcl15MinIntervalEntry 8 }

  nncVcl15MinIntervalClp0And1OutCells   OBJECT-TYPE
        SYNTAX                  NncExtCounter64
        MAX-ACCESS              read-only
        STATUS                  current
        DESCRIPTION             "Number of valid cells transmitted at egress
                                on the VCL with CLP=0 or 1."
  ::= { nncVcl15MinIntervalEntry 9 }

  nncVcl15MinIntervalClp0OutCells       OBJECT-TYPE
        SYNTAX                  NncExtCounter64
        MAX-ACCESS              read-only
        STATUS                  current
        DESCRIPTION             "Number of valid cells transmitted at egress
                                on the VCL with CLP=0."
  ::= { nncVcl15MinIntervalEntry 10 }




--------------------------------------------------------------------------------
-- Virtual Channel Links 1 Hour Current Statistics Table
--------------------------------------------------------------------------------

  nncVcl1HourCurrentTable       OBJECT-TYPE 
        SYNTAX                  SEQUENCE OF NncVcl1HourCurrentEntry 
        MAX-ACCESS              not-accessible
        STATUS                  current
        DESCRIPTION             "The nncVcl1HourCurrentTable contains
                                objects for monitoring the performance of a
                                VCL during the current 1 hour interval.
                                "
  ::= { nncAtmStatisticsObjects 7 }


  nncVcl1HourCurrentEntry       OBJECT-TYPE 
        SYNTAX                  NncVcl1HourCurrentEntry 
        MAX-ACCESS              not-accessible
        STATUS                  current
        DESCRIPTION             "An entry in the 1 hour current statistics
                                table. Each conceptual row contains current
                                statistics for a particular VCL. 
                                
                                By default, 1 Hour statistics are not
                                gathered. In order to enable gathering of
                                these statistics, a row must be created.

                                The semantics of nncVcl1HourCurrentRowStatus
                                is the same as the definition of RowStatus
                                in rfc1443 with the following constraints.

                                1. Creation is done in one step, that is, by
                                   setting the nncVcl1HourCurrentRowStatus
                                   column to createAndGo. Setting the column
                                   to createAndWait will return wrongValue.
                                2. The VCI specified in the instance must
                                   be an endpoint that is currently used in
                                   a VCL otherwise the agent will return
                                   return inconsistentValue and no row is
                                   created.
                                3. If the maximum number of rows (an agent
                                   limitation) has been reached, 
                                   resourceUnavailable is returned and no
                                   row is created.
                                4. Creation of a current row will also enable
                                   the corresponding interval table whose
                                   rows will be created when intervals are
                                   completed.
                                5. Statistics collection is disabled by
                                   setting the column to destroy. This will
                                   also remove all corresponding rows in
                                   the interval table.
                                "
  INDEX                         { ifIndex, atmVclVpi, atmVclVci }
  ::= { nncVcl1HourCurrentTable 1 }

  NncVcl1HourCurrentEntry ::=
    SEQUENCE {
      nncVcl1HourCurrentState                   NncExtIntvlStateType,
      nncVcl1HourCurrentAbsoluteIntervalNumber  NncExtAbsIntvlNumberType,
      nncVcl1HourCurrentClp0And1InCells         NncExtCounter64,
      nncVcl1HourCurrentClp0InCells             NncExtCounter64,
      nncVcl1HourCurrentDiscardClp0And1InCells  NncExtCounter64,
      nncVcl1HourCurrentDiscardClp0InCells      NncExtCounter64,
      nncVcl1HourCurrentTaggedInCells           NncExtCounter64,
      nncVcl1HourCurrentClp0And1OutCells        NncExtCounter64,
      nncVcl1HourCurrentClp0OutCells            NncExtCounter64,
      nncVcl1HourCurrentRowStatus               RowStatus
    }
  

  nncVcl1HourCurrentState       OBJECT-TYPE
        SYNTAX                  NncExtIntvlStateType
        MAX-ACCESS              read-only
        STATUS                  current
        DESCRIPTION             "The state of the current interval. The
                                object provides a status for those entries
                                which have been reset by the user, or have
                                been subject to a wall clock time change.
                                "
  ::= { nncVcl1HourCurrentEntry 1 }

  nncVcl1HourCurrentAbsoluteIntervalNumber      OBJECT-TYPE
        SYNTAX                  NncExtAbsIntvlNumberType
        MAX-ACCESS              read-only
        STATUS                  current
        DESCRIPTION             "The absolute interval number of this
                                interval."
  ::= { nncVcl1HourCurrentEntry 2 }

  nncVcl1HourCurrentClp0And1InCells     OBJECT-TYPE
        SYNTAX                  NncExtCounter64
        MAX-ACCESS              read-only
        STATUS                  current
        DESCRIPTION             "Number of valid cells admitted at ingress
                                on the VCL with CLP=0 or 1, including those
                                with header errors corrected. This counter
                                is formed after the UPC function."
  ::= { nncVcl1HourCurrentEntry 3 }

  nncVcl1HourCurrentClp0InCells OBJECT-TYPE
        SYNTAX                  NncExtCounter64
        MAX-ACCESS              read-only
        STATUS                  current
        DESCRIPTION             "Number of valid cells admitted at ingress
                                on the VCL with CLP=0, including those with
                                header errors corrected."
  ::= { nncVcl1HourCurrentEntry 4 }

  nncVcl1HourCurrentDiscardClp0And1InCells      OBJECT-TYPE
        SYNTAX                  NncExtCounter64
        MAX-ACCESS              read-only
        STATUS                  current
        DESCRIPTION             "Number of valid cells with CLP=1 discarded
                                at ingress by ingress traffic policing,
                                including those with header errors corrected."
  ::= { nncVcl1HourCurrentEntry 5 }

  nncVcl1HourCurrentDiscardClp0InCells  OBJECT-TYPE
        SYNTAX                  NncExtCounter64
        MAX-ACCESS              read-only
        STATUS                  current
        DESCRIPTION             "Number of valid cells with CLP=0 discarded
                                at ingress by ingress traffic policing,
                                including those with header errors corrected."
  ::= { nncVcl1HourCurrentEntry 6 }

  nncVcl1HourCurrentTaggedInCells       OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVcl1HourCurrentEntry 7 }

  nncVcl1HourCurrentClp0And1OutCells    OBJECT-TYPE
        SYNTAX                  NncExtCounter64
        MAX-ACCESS              read-only
        STATUS                  current
        DESCRIPTION             "Number of valid cells transmitted at egress
                                on the VCL with CLP=0 or 1."
  ::= { nncVcl1HourCurrentEntry 8 }

  nncVcl1HourCurrentClp0OutCells        OBJECT-TYPE
        SYNTAX                  NncExtCounter64
        MAX-ACCESS              read-only
        STATUS                  current
        DESCRIPTION             "Number of valid cells transmitted at egress
                                on the VCL with CLP=0."
  ::= { nncVcl1HourCurrentEntry 9 }

  nncVcl1HourCurrentRowStatus           OBJECT-TYPE
        SYNTAX                  RowStatus
        MAX-ACCESS              read-write
        STATUS                  current
        DESCRIPTION             "This object is used to create and delete 
                                rows in this table.
                                The following sets are invalid: createAndWait,
                                active, and notInService. Such sets will
                                return wrongValue.
                                "
  ::= { nncVcl1HourCurrentEntry 10 }



--------------------------------------------------------------------------------
-- Virtual Channel Links 1 Hour Interval Statistics Table
--------------------------------------------------------------------------------

  nncVcl1HourIntervalTable      OBJECT-TYPE 
        SYNTAX                  SEQUENCE OF NncVcl1HourIntervalEntry 
        MAX-ACCESS              not-accessible
        STATUS                  current
        DESCRIPTION             "The nncVcl1HourIntervalTable contains
                                objects for monitoring the performance of a
                                virtual Channel link over a historical stratum
                                of M 1 hour intervals. 
                                "
  ::= { nncAtmStatisticsObjects 8 }


  nncVcl1HourIntervalEntry      OBJECT-TYPE 
        SYNTAX                  NncVcl1HourIntervalEntry 
        MAX-ACCESS              not-accessible
        STATUS                  current
        DESCRIPTION             "An entry in the 1 hour interval statistics
                                table. Each conceptual row contains
                                statistics for a particular VCL and interval. 
                                
                                These rows are automatically created if
                                there is a corresponding entry in the 1 hour
                                current table.
                                "
  INDEX                         { ifIndex, atmVclVpi, atmVclVci,
                                  nncVcl1HourIntervalNumber }
  ::= { nncVcl1HourIntervalTable 1 }

  NncVcl1HourIntervalEntry ::=
    SEQUENCE {
      nncVcl1HourIntervalNumber                 NncExtRelIntvlNumberType,
      nncVcl1HourIntervalState                  NncExtIntvlStateType,
      nncVcl1HourIntervalAbsoluteIntervalNumber NncExtAbsIntvlNumberType,
      nncVcl1HourIntervalClp0And1InCells        NncExtCounter64,
      nncVcl1HourIntervalClp0InCells            NncExtCounter64,
      nncVcl1HourIntervalDiscardClp0And1InCells NncExtCounter64,
      nncVcl1HourIntervalDiscardClp0InCells     NncExtCounter64,
      nncVcl1HourIntervalTaggedInCells          NncExtCounter64,
      nncVcl1HourIntervalClp0And1OutCells       NncExtCounter64,
      nncVcl1HourIntervalClp0OutCells           NncExtCounter64
    }
  

  nncVcl1HourIntervalNumber     OBJECT-TYPE
        SYNTAX                  NncExtRelIntvlNumberType
        MAX-ACCESS              not-accessible
        STATUS                  current
        DESCRIPTION             "The interval number (N) of the statistics in
                                this row."
  ::= { nncVcl1HourIntervalEntry 1 }

  nncVcl1HourIntervalState      OBJECT-TYPE
        SYNTAX                  NncExtIntvlStateType
        MAX-ACCESS              read-only
        STATUS                  current
        DESCRIPTION             "The state of the interval represented by
                                this row. The object provides a status for
                                those entries which have been reset by the
                                user, or have been subject to a wall clock
                                time change.
                                "
  ::= { nncVcl1HourIntervalEntry 2 }

  nncVcl1HourIntervalAbsoluteIntervalNumber     OBJECT-TYPE
        SYNTAX                  NncExtAbsIntvlNumberType
        MAX-ACCESS              read-only
        STATUS                  current
        DESCRIPTION             "The absolute interval number of this
                                interval."
  ::= { nncVcl1HourIntervalEntry 3 }

  nncVcl1HourIntervalClp0And1InCells    OBJECT-TYPE
        SYNTAX                  NncExtCounter64
        MAX-ACCESS              read-only
        STATUS                  current
        DESCRIPTION             "Number of valid cells admitted at ingress
                                on the VCL with CLP=0 or 1, including those
                                with header errors corrected. This counter
                                is formed after the UPC function."
  ::= { nncVcl1HourIntervalEntry 4 }

  nncVcl1HourIntervalClp0InCells        OBJECT-TYPE
        SYNTAX                  NncExtCounter64
        MAX-ACCESS              read-only
        STATUS                  current
        DESCRIPTION             "Number of valid cells admitted at ingress
                                on the VCL with CLP=0, including those with
                                header errors corrected."
  ::= { nncVcl1HourIntervalEntry 5 }

  nncVcl1HourIntervalDiscardClp0And1InCells     OBJECT-TYPE
        SYNTAX                  NncExtCounter64
        MAX-ACCESS              read-only
        STATUS                  current
        DESCRIPTION             "Number of valid cells with CLP=1 discarded
                                at ingress by ingress traffic policing,
                                including those with header errors corrected."
  ::= { nncVcl1HourIntervalEntry 6 }

  nncVcl1HourIntervalDiscardClp0InCells OBJECT-TYPE
        SYNTAX                  NncExtCounter64
        MAX-ACCESS              read-only
        STATUS                  current
        DESCRIPTION             "Number of valid cells with CLP=0 discarded
                                at ingress by ingress traffic policing,
                                including those with header errors corrected."
  ::= { nncVcl1HourIntervalEntry 7 }

  nncVcl1HourIntervalTaggedInCells      OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVcl1HourIntervalEntry 8 }

  nncVcl1HourIntervalClp0And1OutCells   OBJECT-TYPE
        SYNTAX                  NncExtCounter64
        MAX-ACCESS              read-only
        STATUS                  current
        DESCRIPTION             "Number of valid cells transmitted at egress
                                on the VCL with CLP=0 or 1."
  ::= { nncVcl1HourIntervalEntry 9 }

  nncVcl1HourIntervalClp0OutCells       OBJECT-TYPE
        SYNTAX                  NncExtCounter64
        MAX-ACCESS              read-only
        STATUS                  current
        DESCRIPTION             "Number of valid cells transmitted at egress
                                on the VCL with CLP=0."
  ::= { nncVcl1HourIntervalEntry 10 }


--------------------------------------------------------------------------------
-- Virtual Channel Links Statistics Table
--------------------------------------------------------------------------------

  nncVclStatTable       OBJECT-TYPE 
        SYNTAX                  SEQUENCE OF NncVclStatEntry 
        MAX-ACCESS              not-accessible
        STATUS                  current
        DESCRIPTION             "The nncVclStatTable contains objects
                                for monitoring the accumulated performance 
                                of a VCL since measurement started on the VCL."
  ::= { nncAtmStatisticsObjects 11 }


  nncVclStatEntry       OBJECT-TYPE 
        SYNTAX                  NncVclStatEntry 
        MAX-ACCESS              not-accessible
        STATUS                  current
        DESCRIPTION             "An entry in the Stat table.
                                Each conceptual row contains accumulated 
                                statistics for a particular VCL."
        INDEX                   { ifIndex, atmVclVpi, atmVclVci }
  ::= { nncVclStatTable 1 }

  NncVclStatEntry ::=
    SEQUENCE {
      nncVclStatClp0And1InCells         NncExtCounter64,
      nncVclStatClp0InCells             NncExtCounter64,
      nncVclStatDiscardClp0And1InCells  NncExtCounter64,
      nncVclStatDiscardClp0InCells      NncExtCounter64,
      nncVclStatTaggedInCells           NncExtCounter64,
      nncVclStatClp0And1OutCells        NncExtCounter64,
      nncVclStatClp0OutCells            NncExtCounter64
    }
  
  nncVclStatClp0And1InCells     OBJECT-TYPE
        SYNTAX                  NncExtCounter64
        MAX-ACCESS              read-only
        STATUS                  current
        DESCRIPTION             "Number of valid cells admitted at ingress
                                on the VCL with CLP=0 or 1, including those
                                with header errors corrected. This counter
                                is formed after the UPC function."
  ::= { nncVclStatEntry 1 }

  nncVclStatClp0InCells OBJECT-TYPE
        SYNTAX                  NncExtCounter64
        MAX-ACCESS              read-only
        STATUS                  current
        DESCRIPTION             "Number of valid cells admitted at ingress
                                on the VCL with CLP=0, including those with
                                header errors corrected."
  ::= { nncVclStatEntry 2 }

  nncVclStatDiscardClp0And1InCells      OBJECT-TYPE
        SYNTAX                  NncExtCounter64
        MAX-ACCESS              read-only
        STATUS                  current
        DESCRIPTION             "Number of valid cells with CLP=1 discarded
                                at ingress by ingress traffic policing,
                                including those with header errors corrected."
  ::= { nncVclStatEntry 3 }

  nncVclStatDiscardClp0InCells  OBJECT-TYPE
        SYNTAX                  NncExtCounter64
        MAX-ACCESS              read-only
        STATUS                  current
        DESCRIPTION             "Number of valid cells with CLP=0 discarded
                                at ingress by ingress traffic policing,
                                including those with header errors corrected."
  ::= { nncVclStatEntry 4 }

  nncVclStatTaggedInCells       OBJECT-TYPE
        SYNTAX                  NncExtCounter64
        MAX-ACCESS              read-only
        STATUS                  current
        DESCRIPTION             "Number of valid cells admitted at ingress
                                with CLP=0, with CLP set to 1 by ingress
                                traffic policing, including those with header
                                errors corrected."
  ::= { nncVclStatEntry 5 }

  nncVclStatClp0And1OutCells    OBJECT-TYPE
        SYNTAX                  NncExtCounter64
        MAX-ACCESS              read-only
        STATUS                  current
        DESCRIPTION             "Number of valid cells transmitted at egress
                                on the VPL with CLP=0 or 1."
  ::= { nncVclStatEntry 6 }

  nncVclStatClp0OutCells        OBJECT-TYPE
        SYNTAX                  NncExtCounter64
        MAX-ACCESS              read-only
        STATUS                  current
        DESCRIPTION             "Number of valid cells transmitted at egress
                                on the VPL with CLP=0."
  ::= { nncVclStatEntry 7 }


--------------------------------------------------------------------------------
-- Virtual Path Links Stats Counter Table
--------------------------------------------------------------------------------

nncAtmVplStatCounterTable  OBJECT-TYPE
   SYNTAX SEQUENCE OF NncAtmVplStatCounterEntry
   MAX-ACCESS not-accessible
   STATUS current
   DESCRIPTION
       " This table supplies the maximum interval numbers for valid data for
         Atm Vpl End Points in the nncVpl15MinIntervalTable and
         nncVpl1HourIntervaltable."
   ::= { nncAtmStatisticsObjects 12 }

nncAtmVplStatCounterEntry  OBJECT-TYPE
   SYNTAX NncAtmVplStatCounterEntry
   MAX-ACCESS not-accessible
   STATUS current
   DESCRIPTION
       "  An Entry in nncAtmVplStatCounterTable. "
   INDEX { ifIndex, atmVplVpi, nncAtmVplStatCounterIndex }
   ::= { nncAtmVplStatCounterTable 1}

NncAtmVplStatCounterEntry ::= SEQUENCE {
       nncAtmVplStatCounterIndex       INTEGER,
       nncAtmVplStatCounterValue       INTEGER
       }

nncAtmVplStatCounterIndex  OBJECT-TYPE
   SYNTAX INTEGER {
       hourly(1),
       daily(2),
       monthly(3),
       interval(4)
       }
   MAX-ACCESS     read-only
   STATUS current
   DESCRIPTION
       "  This index specifies the type of interval available.
          1 = hourly
          2 = daily (not used)
          3 = monthly (not used)
          4 = 15 minute interval stats."
   ::= { nncAtmVplStatCounterEntry 1 }

nncAtmVplStatCounterValue  OBJECT-TYPE
   SYNTAX  INTEGER (0..'7fffffff'h)
   MAX-ACCESS     read-only
   STATUS current
   DESCRIPTION
       " This values represents the maximum interval number for valid data for
         Atm Vpl End Points. This number is based on the type of interval
         being reported."
   ::= { nncAtmVplStatCounterEntry 2 }


--------------------------------------------------------------------------------
-- Virtual Channel Links Counter Statistics Table
--------------------------------------------------------------------------------

nncAtmVclStatCounterTable  OBJECT-TYPE
   SYNTAX SEQUENCE OF NncAtmVclStatCounterEntry
   MAX-ACCESS not-accessible
   STATUS current
   DESCRIPTION
       " This table supplies the maximum interval numbers for valid data for
         Atm Vcl End Points in the nncVcl15MinIntervalTable and
         nncVcl1HourIntervaltable."
   ::= { nncAtmStatisticsObjects 13 }

nncAtmVclStatCounterEntry  OBJECT-TYPE
   SYNTAX NncAtmVclStatCounterEntry
   MAX-ACCESS not-accessible
   STATUS current
   DESCRIPTION
       "  An Entry in nncAtmVclStatCounterTable. "
   INDEX { ifIndex, atmVclVpi, atmVclVci, nncAtmVclStatCounterIndex }
   ::= { nncAtmVclStatCounterTable 1}

NncAtmVclStatCounterEntry ::= SEQUENCE {
       nncAtmVclStatCounterIndex       INTEGER,
       nncAtmVclStatCounterValue       INTEGER
       }

nncAtmVclStatCounterIndex  OBJECT-TYPE
   SYNTAX INTEGER {
       hourly(1),
       daily(2),
       monthly(3),
       interval(4)
       }
   MAX-ACCESS read-only
   STATUS current
   DESCRIPTION
       "  This index specifies the type of interval available.
          1 = hourly
          2 = daily (not used)
          3 = monthly (not used)
          4 = 15 minute interval stats."
   ::= { nncAtmVclStatCounterEntry 1}

nncAtmVclStatCounterValue  OBJECT-TYPE
   SYNTAX INTEGER (0..'7fffffff'h)
   MAX-ACCESS read-only
   STATUS current
   DESCRIPTION
       " This values represents the maximum interval number for valid data for
         Atm Vcl End Points. This number is based on the type of interval
         being reported."
   ::= { nncAtmVclStatCounterEntry 2}

--------------------------------------------------------------------------------
-- Virtual Path Aggregation Short Current Statistics Table
--------------------------------------------------------------------------------
 
  nncVpa15MinCurrentTable   OBJECT-TYPE 
        SYNTAX              SEQUENCE OF NncVpa15MinCurrentEntry 
        MAX-ACCESS          not-accessible
        STATUS              current
        DESCRIPTION         "The nncVpa15MinCurrentTable contains
                            objects for monitoring the performance of a
                            VPA during the current 15 minute interval."
  ::= { nncAtmStatisticsObjects 15 }
 
  nncVpa15MinCurrentEntry   OBJECT-TYPE 
        SYNTAX              NncVpa15MinCurrentEntry 
        MAX-ACCESS          not-accessible
        STATUS              current
        DESCRIPTION         "An entry in the 15 minute current
                            statistics table. Each conceptual row
                            contains current statistics for a
                            particular VPA"
        INDEX               { ifIndex , atmVplVpi}
  ::= { nncVpa15MinCurrentTable 1 }
 
  NncVpa15MinCurrentEntry ::=
    SEQUENCE {
      nncVpa15MinCurrentState                  NncExtIntvlStateType,
      nncVpa15MinCurrentAbsoluteIntervalNumber Integer32,
      nncVpa15MinCurrentClp0And1OutCells       Counter64,
      nncVpa15MinCurrentDiscardClp0And1Cells   Counter64,
      nncVpa15MinCurrentDiscardClp0Cells       Counter64
    }
  
  nncVpa15MinCurrentState       OBJECT-TYPE
        SYNTAX                  NncExtIntvlStateType
        MAX-ACCESS              read-only
        STATUS                  current
        DESCRIPTION             "The state of the current interval. The
                                object provides a status for those entries
                                which have been reset by the user, or have
                                been subject to a wall clock time change.
                                "
  ::= { nncVpa15MinCurrentEntry 1 }
 
  nncVpa15MinCurrentAbsoluteIntervalNumber      OBJECT-TYPE
        SYNTAX                  Integer32
        MAX-ACCESS              read-only
        STATUS                  current
        DESCRIPTION             "The absolute interval number of this
                                interval."
  ::= { nncVpa15MinCurrentEntry 2 }
 
  nncVpa15MinCurrentClp0And1OutCells     OBJECT-TYPE
        SYNTAX                  Counter64
        MAX-ACCESS              read-only
        STATUS                  current
        DESCRIPTION             "Total CLP0 and CLP1 cells transmitted on all
                                constituent VCs of a particular VPA"
  ::= { nncVpa15MinCurrentEntry 3 }
 
  nncVpa15MinCurrentDiscardClp0And1Cells      OBJECT-TYPE
        SYNTAX                  Counter64
        MAX-ACCESS              read-only
        STATUS                  current
        DESCRIPTION             "Total CLP0 and CLP1 cells discarded due to congestion
                                on all constituent VCs of a particular VPA"
  ::= { nncVpa15MinCurrentEntry 4 }
 
  nncVpa15MinCurrentDiscardClp0Cells  OBJECT-TYPE
        SYNTAX                  Counter64
        MAX-ACCESS              read-only
        STATUS                  current
        DESCRIPTION             "Total CLP0 cells discarded due to congestion
                                on all constituent VCs of a particular VPA"
  ::= { nncVpa15MinCurrentEntry 6 }
 
 
--------------------------------------------------------------------------------
-- Virtual Path Aggregation Short  Statistics Table
--------------------------------------------------------------------------------
 
  nncVpa15MinIntervalTable      OBJECT-TYPE 
        SYNTAX                  SEQUENCE OF NncVpa15MinIntervalEntry 
        MAX-ACCESS              not-accessible
        STATUS                  current
        DESCRIPTION             "The nncVpa15MinIntervalTable contains
                                objects for monitoring the performance of a
                                VPA during the  15 minute interval."
  ::= { nncAtmStatisticsObjects 16 }
 
  nncVpa15MinIntervalEntry      OBJECT-TYPE 
        SYNTAX                  NncVpa15MinIntervalEntry 
        MAX-ACCESS              not-accessible
        STATUS                  current
        DESCRIPTION             "An entry in the 15 minute current
                                statistics table. Each conceptual row
                                contains current statistics for a
                                particular VPA"
        INDEX                   { ifIndex , atmVplVpi, nncVpa15MinIntervalNumber }
  ::= { nncVpa15MinIntervalTable 1 }
 
  NncVpa15MinIntervalEntry ::=
    SEQUENCE {
      nncVpa15MinIntervalNumber                  Integer32,
      nncVpa15MinIntervalState                   NncExtIntvlStateType,
      nncVpa15MinIntervalAbsoluteIntervalNumber  Integer32,
      nncVpa15MinIntervalClp0And1OutCells        Counter64,
      nncVpa15MinIntervalDiscardClp0And1Cells    Counter64,
      nncVpa15MinIntervalDiscardClp0Cells        Counter64
    }
  
   nncVpa15MinIntervalNumber OBJECT-TYPE
    SYNTAX                   Integer32
    MAX-ACCESS               not-accessible
    STATUS                   current
    DESCRIPTION              "The interval number (N) of the statistics in
                             this row."
 ::= { nncVpa15MinIntervalEntry 1 }
 
  nncVpa15MinIntervalState   OBJECT-TYPE
        SYNTAX               NncExtIntvlStateType
        MAX-ACCESS           read-only
        STATUS               current
        DESCRIPTION          "The state of the current interval. The
                             object provides a status for those entries
                             which have been reset by the user, or have
                             been subject to a wall clock time change.
                                "
  ::= { nncVpa15MinIntervalEntry 2 }
 
  nncVpa15MinIntervalAbsoluteIntervalNumber OBJECT-TYPE
        SYNTAX               Integer32
        MAX-ACCESS           read-only
        STATUS               current
        DESCRIPTION          "The absolute interval number of this
                             interval."
  ::= { nncVpa15MinIntervalEntry 3 }
 
 
  nncVpa15MinIntervalClp0And1OutCells       OBJECT-TYPE
        SYNTAX               Counter64
        MAX-ACCESS           read-only
        STATUS               current
        DESCRIPTION          "Total CLP0 and CLP1 cells transmitted on all
                             constituent VCs of a particular VPA"
  ::= { nncVpa15MinIntervalEntry 4 }
 
  nncVpa15MinIntervalDiscardClp0And1Cells   OBJECT-TYPE
        SYNTAX               Counter64
        MAX-ACCESS           read-only
        STATUS               current
        DESCRIPTION          "Total CLP0 and CLP1 cells discarded due to congestion
                             on all constituent VCs of a particular VPA"
  ::= { nncVpa15MinIntervalEntry 5 }
 
  nncVpa15MinIntervalDiscardClp0Cells       OBJECT-TYPE
        SYNTAX               Counter64
        MAX-ACCESS           read-only
        STATUS               current
        DESCRIPTION          "Total CLP0 cells discarded due to congestion
                             on all constituent VCs of a particular VPA"
  ::= { nncVpa15MinIntervalEntry 6 }
 
--------------------------------------------------------------------------------
-- Virtual Path Aggregation Long Current Statistics Table
--------------------------------------------------------------------------------
 
  nncVpa1HourCurrentTable       OBJECT-TYPE 
        SYNTAX                  SEQUENCE OF NncVpa1HourCurrentEntry 
        MAX-ACCESS              not-accessible
        STATUS                  current
        DESCRIPTION             "The nncVpa1HourCurrentTable contains
                                objects for monitoring the performance of a
                                VPA during the current 1 hour interval."
  ::= { nncAtmStatisticsObjects 17 }
 
  nncVpa1HourCurrentEntry       OBJECT-TYPE 
        SYNTAX                  NncVpa1HourCurrentEntry 
        MAX-ACCESS              not-accessible
        STATUS                  current
        DESCRIPTION             "An entry in the 1 hour current
                                statistics table. Each conceptual row
                                contains current statistics for a
                                particular VPA"
        INDEX                   { ifIndex , atmVplVpi }
  ::= { nncVpa1HourCurrentTable 1 }
 
  NncVpa1HourCurrentEntry ::=
    SEQUENCE {
      nncVpa1HourCurrentState                  NncExtIntvlStateType,
      nncVpa1HourCurrentAbsoluteIntervalNumber Integer32,
      nncVpa1HourCurrentClp0And1OutCells       Counter64,
      nncVpa1HourCurrentDiscardClp0And1Cells   Counter64,
      nncVpa1HourCurrentDiscardClp0Cells       Counter64
    }
  
 
  nncVpa1HourCurrentState       OBJECT-TYPE
        SYNTAX                  NncExtIntvlStateType
        MAX-ACCESS              read-only
        STATUS                  current
        DESCRIPTION             "The state of the current interval. The
                                object provides a status for those entries
                                which have been reset by the user, or have
                                been subject to a wall clock time change.
                                "
  ::= { nncVpa1HourCurrentEntry 1 }
 
  nncVpa1HourCurrentAbsoluteIntervalNumber   OBJECT-TYPE
        SYNTAX                  Integer32
        MAX-ACCESS              read-only
        STATUS                  current
        DESCRIPTION             "The absolute interval number of this
                                interval."
  ::= { nncVpa1HourCurrentEntry 2 }
 
  nncVpa1HourCurrentClp0And1OutCells          OBJECT-TYPE
        SYNTAX                  Counter64
        MAX-ACCESS              read-only
        STATUS                  current
        DESCRIPTION             "Total CLP0 and CLP1 cells transmitted on all
                                constituent VCs of a particular VPA"
  ::= { nncVpa1HourCurrentEntry 3 }
 
  nncVpa1HourCurrentDiscardClp0And1Cells      OBJECT-TYPE
        SYNTAX                  Counter64
        MAX-ACCESS              read-only
        STATUS                  current
        DESCRIPTION             "Total CLP0 and CLP1 cells discarded due to congestion
                                on all constituent VCs of a particular VPA"
  ::= { nncVpa1HourCurrentEntry 4 }
 
  nncVpa1HourCurrentDiscardClp0Cells          OBJECT-TYPE
        SYNTAX                  Counter64
        MAX-ACCESS              read-only
        STATUS                  current
        DESCRIPTION             "Total CLP0 cells discarded due to congestion
                                on all constituent VCs of a particular VPA"
  ::= { nncVpa1HourCurrentEntry 5 }
 
 
--------------------------------------------------------------------------------
-- Virtual Path Aggregation Long  Statistics Table
--------------------------------------------------------------------------------
 
  nncVpa1HourIntervalTable      OBJECT-TYPE 
        SYNTAX                  SEQUENCE OF NncVpa1HourIntervalEntry 
        MAX-ACCESS              not-accessible
        STATUS                  current
        DESCRIPTION             "The nncVpa1HourIntervalTable contains
                                objects for monitoring the performance of a
                                VPA during the 1 hour interval."
  ::= { nncAtmStatisticsObjects 18 }
 
  nncVpa1HourIntervalEntry      OBJECT-TYPE 
        SYNTAX                  NncVpa1HourIntervalEntry 
        MAX-ACCESS              not-accessible
        STATUS                  current
        DESCRIPTION             "An entry in the 1hour current
                                statistics table. Each conceptual row
                                contains current statistics for a
                                particular VPA"
        INDEX                   { ifIndex , atmVplVpi, nncVpa1HourIntervalNumber}
  ::= { nncVpa1HourIntervalTable 1 }
 
  NncVpa1HourIntervalEntry ::=
    SEQUENCE {
      nncVpa1HourIntervalNumber                 Integer32,
      nncVpa1HourIntervalState                  NncExtIntvlStateType,
      nncVpa1HourIntervalAbsoluteIntervalNumber Integer32,
      nncVpa1HourIntervalClp0And1OutCells       Counter64,
      nncVpa1HourIntervalDiscardClp0And1Cells   Counter64,
      nncVpa1HourIntervalDiscardClp0Cells       Counter64
    }
  
   nncVpa1HourIntervalNumber    OBJECT-TYPE
    SYNTAX                      Integer32
    MAX-ACCESS                  not-accessible
    STATUS                      current
    DESCRIPTION                 "The interval number (N) of the statistics in
                                this row."
  ::= { nncVpa1HourIntervalEntry 1 }
 
  nncVpa1HourIntervalState      OBJECT-TYPE
        SYNTAX                  NncExtIntvlStateType
        MAX-ACCESS              read-only
        STATUS                  current
        DESCRIPTION             "The state of the current interval. The
                                object provides a status for those entries
                                which have been reset by the user, or have
                                been subject to a wall clock time change.
                                "
  ::= { nncVpa1HourIntervalEntry 2 }
 
  nncVpa1HourIntervalAbsoluteIntervalNumber    OBJECT-TYPE
        SYNTAX                  Integer32
        MAX-ACCESS              read-only
        STATUS                  current
        DESCRIPTION             "The absolute interval number of this
                                interval."
  ::= { nncVpa1HourIntervalEntry 3 }
 
 
  nncVpa1HourIntervalClp0And1OutCells          OBJECT-TYPE
        SYNTAX                  Counter64
        MAX-ACCESS              read-only
        STATUS                  current
        DESCRIPTION             "Total CLP0 and CLP1 cells transmitted on all
                                constituent VCs of a particular VPA"
  ::= { nncVpa1HourIntervalEntry 4 }
 
  nncVpa1HourIntervalDiscardClp0And1Cells      OBJECT-TYPE
        SYNTAX                  Counter64
        MAX-ACCESS              read-only
        STATUS                  current
        DESCRIPTION             "Total CLP0 and CLP1 cells discarded due to congestion
                                on all constituent VCs of a particular VPA"
  ::= { nncVpa1HourIntervalEntry 5 }
 
  nncVpa1HourIntervalDiscardClp0Cells          OBJECT-TYPE
        SYNTAX                  Counter64
        MAX-ACCESS              read-only
        STATUS                  current
        DESCRIPTION             "Total CLP0 cells discarded due to congestion
                                on all constituent VCs of a particular VPA"
  ::= { nncVpa1HourIntervalEntry 6 }
 
 
--------------------------------------------------------------------------------
-- Non-table objects
--------------------------------------------------------------------------------

  nncDepthOf15MinHistoricalStrata   OBJECT-TYPE 
        SYNTAX                      NncExtRelIntvlNumberType
        MAX-ACCESS                  read-only
        STATUS                      current
        DESCRIPTION                 "The depth of the historical strata of 
                                    15min interval tables in this module."
  ::= { nncAtmStatisticsObjects 9 }


  nncDepthOf1HourHistoricalStrata   OBJECT-TYPE 
        SYNTAX                      NncExtRelIntvlNumberType
        MAX-ACCESS                  read-only
        STATUS                      current
        DESCRIPTION                 "The depth of the historical strata of
                                    1 hour interval tables in this module."
  ::= { nncAtmStatisticsObjects 14 }

--------------------------------------------------------------------------------
-- Conformance Group Definitions
--------------------------------------------------------------------------------

        nncVpl15MinCurrentGroup         OBJECT-GROUP 
                OBJECTS {
                        nncVpl15MinCurrentAbsoluteIntervalNumber,
                        nncVpl15MinCurrentClp0And1InCells,
                        nncVpl15MinCurrentClp0InCells,
                        nncVpl15MinCurrentDiscardClp0And1InCells,
                        nncVpl15MinCurrentDiscardClp0InCells,
                        nncVpl15MinCurrentTaggedInCells,
                        nncVpl15MinCurrentClp0And1OutCells,
                        nncVpl15MinCurrentClp0OutCells
                }
                STATUS          current
                DESCRIPTION     "A collection of objects providing 15 Min
                                current statistics for a VPI endpoint"
        ::= { nncAtmStatisticsGroups 1 }

        nncVpl15MinIntervalGroup        OBJECT-GROUP 
                OBJECTS {
                        nncVpl15MinIntervalAbsoluteIntervalNumber,
                        nncVpl15MinIntervalClp0And1InCells,
                        nncVpl15MinIntervalClp0InCells,
                        nncVpl15MinIntervalDiscardClp0And1InCells,
                        nncVpl15MinIntervalDiscardClp0InCells,
                        nncVpl15MinIntervalTaggedInCells,
                        nncVpl15MinIntervalClp0And1OutCells,
                        nncVpl15MinIntervalClp0OutCells
                }
                STATUS          current
                DESCRIPTION     "A collection of objects providing 15 Min
                                interval statistics for a VPI endpoint"
        ::= { nncAtmStatisticsGroups 2 }

        nncVpl1HourCurrentGroup         OBJECT-GROUP 
                OBJECTS {
                        nncVpl1HourCurrentAbsoluteIntervalNumber,
                        nncVpl1HourCurrentClp0And1InCells,
                        nncVpl1HourCurrentClp0InCells,
                        nncVpl1HourCurrentDiscardClp0And1InCells,
                        nncVpl1HourCurrentDiscardClp0InCells,
                        nncVpl1HourCurrentTaggedInCells,
                        nncVpl1HourCurrentClp0And1OutCells,
                        nncVpl1HourCurrentClp0OutCells,
                        nncVpl1HourCurrentRowStatus
                }
                STATUS          current
                DESCRIPTION     "A collection of objects providing 1 Hour
                                current statistics for a VPI endpoint"
        ::= { nncAtmStatisticsGroups 3 }

        nncVpl1HourIntervalGroup        OBJECT-GROUP 
                OBJECTS {
                        nncVpl1HourIntervalAbsoluteIntervalNumber,
                        nncVpl1HourIntervalClp0And1InCells,
                        nncVpl1HourIntervalClp0InCells,
                        nncVpl1HourIntervalDiscardClp0And1InCells,
                        nncVpl1HourIntervalDiscardClp0InCells,
                        nncVpl1HourIntervalTaggedInCells,
                        nncVpl1HourIntervalClp0And1OutCells,
                        nncVpl1HourIntervalClp0OutCells
                }
                STATUS          current
                DESCRIPTION     "A collection of objects providing 1 Hour
                                interval statistics for a VPI endpoint"
        ::= { nncAtmStatisticsGroups 4 }

        nncVplStatGroup         OBJECT-GROUP 
                OBJECTS {
                        nncVplStatClp0And1InCells,
                        nncVplStatClp0InCells,
                        nncVplStatDiscardClp0And1InCells,
                        nncVplStatDiscardClp0InCells,
                        nncVplStatTaggedInCells,
                        nncVplStatClp0And1OutCells,
                        nncVplStatClp0OutCells
                }
                STATUS          current
                DESCRIPTION     "A collection of objects providing cumulative
                                 statistics for a VPI endpoint"
        ::= { nncAtmStatisticsGroups 9 }

        nncVcl15MinCurrentGroup         OBJECT-GROUP 
                OBJECTS {
                        nncVcl15MinCurrentState,
                        nncVcl15MinCurrentAbsoluteIntervalNumber,
                        nncVcl15MinCurrentClp0And1InCells,
                        nncVcl15MinCurrentClp0InCells,
                        nncVcl15MinCurrentDiscardClp0And1InCells,
                        nncVcl15MinCurrentDiscardClp0InCells,
                        nncVcl15MinCurrentTaggedInCells,
                        nncVcl15MinCurrentClp0And1OutCells,
                        nncVcl15MinCurrentClp0OutCells
                }
                STATUS          current
                DESCRIPTION     "A collection of objects providing 15 Min
                                current statistics for a VCI endpoint"
        ::= { nncAtmStatisticsGroups 5 }

        nncVcl15MinIntervalGroup        OBJECT-GROUP 
                OBJECTS {
                        nncVcl15MinIntervalAbsoluteIntervalNumber,
                        nncVcl15MinIntervalClp0And1InCells,
                        nncVcl15MinIntervalClp0InCells,
                        nncVcl15MinIntervalDiscardClp0And1InCells,
                        nncVcl15MinIntervalDiscardClp0InCells,
                        nncVcl15MinIntervalTaggedInCells,
                        nncVcl15MinIntervalClp0And1OutCells,
                        nncVcl15MinIntervalClp0OutCells
                }
                STATUS          current
                DESCRIPTION     "A collection of objects providing 15 Min
                                interval statistics for a VCI endpoint"
        ::= { nncAtmStatisticsGroups 6 }

        nncVcl1HourCurrentGroup         OBJECT-GROUP 
                OBJECTS {
                        nncVcl1HourCurrentState,
                        nncVcl1HourCurrentAbsoluteIntervalNumber,
                        nncVcl1HourCurrentClp0And1InCells,
                        nncVcl1HourCurrentClp0InCells,
                        nncVcl1HourCurrentDiscardClp0And1InCells,
                        nncVcl1HourCurrentDiscardClp0InCells,
                        nncVcl1HourCurrentTaggedInCells,
                        nncVcl1HourCurrentClp0And1OutCells,
                        nncVcl1HourCurrentClp0OutCells,
                        nncVcl1HourCurrentRowStatus
                }
                STATUS          current
                DESCRIPTION     "A collection of objects providing 1 Hour
                                current statistics for a VCI endpoint"
        ::= { nncAtmStatisticsGroups 7 }

        nncVcl1HourIntervalGroup        OBJECT-GROUP 
                OBJECTS {
                        nncVcl1HourIntervalAbsoluteIntervalNumber,
                        nncVcl1HourIntervalClp0And1InCells,
                        nncVcl1HourIntervalClp0InCells,
                        nncVcl1HourIntervalDiscardClp0And1InCells,
                        nncVcl1HourIntervalDiscardClp0InCells,
                        nncVcl1HourIntervalTaggedInCells,
                        nncVcl1HourIntervalClp0And1OutCells,
                        nncVcl1HourIntervalClp0OutCells
                }
                STATUS          current
                DESCRIPTION     "A collection of objects providing 1 Hour
                                interval statistics for a VCI endpoint"
        ::= { nncAtmStatisticsGroups 8 }

        nncVclStatGroup        OBJECT-GROUP 
                OBJECTS {
                        nncVclStatClp0And1InCells,
                        nncVclStatClp0InCells,
                        nncVclStatDiscardClp0And1InCells,
                        nncVclStatDiscardClp0InCells,
                        nncVclStatTaggedInCells,
                        nncVclStatClp0And1OutCells,
                        nncVclStatClp0OutCells
                }
                STATUS          current
                DESCRIPTION     "A collection of objects providing cumulative
                                 statistics for a VCI endpoint"
        ::= { nncAtmStatisticsGroups 10 }

        nncVplIntervalStateGroup        OBJECT-GROUP 
                OBJECTS {
                        nncVpl15MinCurrentState,
                        nncVpl15MinIntervalState,
                        nncVpl1HourCurrentState,
                        nncVpl1HourIntervalState
                }
                STATUS          current
                DESCRIPTION     "A collection of objects providing the state
                                 of intervals in the VPL current and interval
                                 tables."
        ::= { nncAtmStatisticsGroups 11 }

        nncVclIntervalStateGroup        OBJECT-GROUP 
                OBJECTS {
                        nncVcl15MinCurrentState,
                        nncVcl15MinIntervalState,
                        nncVcl1HourCurrentState,
                        nncVcl1HourIntervalState
                }
                STATUS          current
                DESCRIPTION     "A collection of objects providing the state
                                 of intervals in the VCL current and interval
                                 tables."
        ::= { nncAtmStatisticsGroups 12 }

        nncVplStatCounterGroup        OBJECT-GROUP 
                OBJECTS {
                        nncAtmVplStatCounterIndex,
                        nncAtmVplStatCounterValue
                }
                STATUS          current
                DESCRIPTION     "A collection of objects providing the count
                                 of valid intervals in the VPL interval tables."
        ::= { nncAtmStatisticsGroups 13 }

        nncVclStatCounterGroup        OBJECT-GROUP 
                OBJECTS {
                        nncAtmVclStatCounterIndex,
                        nncAtmVclStatCounterValue
                }
                STATUS          current
                DESCRIPTION     "A collection of objects providing the count
                                 of valid intervals in the VCL interval tables."
        ::= { nncAtmStatisticsGroups 14 }

        nncDepthOfHistoricalStrataGroup      OBJECT-GROUP 
                OBJECTS {
                        nncDepthOf15MinHistoricalStrata,
                        nncDepthOf1HourHistoricalStrata
                }
                STATUS          current
                DESCRIPTION     "A collection of objects providing the number
                                 of intervals supported in the interval 
                                 tables."
        ::= { nncAtmStatisticsGroups 15 }

        nncVpa15MinCurrentGroup         OBJECT-GROUP 
                OBJECTS {
                   nncVpa15MinCurrentState,
                   nncVpa15MinCurrentAbsoluteIntervalNumber,
                   nncVpa15MinCurrentClp0And1OutCells,
                   nncVpa15MinCurrentDiscardClp0And1Cells,
                   nncVpa15MinCurrentDiscardClp0Cells
                }
                STATUS          current
                DESCRIPTION     "A collection of objects providing 15 Min
                                current statistics for a VP Aggregation"
        ::= { nncAtmStatisticsGroups 16 }
 
        nncVpa15MinIntervalGroup         OBJECT-GROUP 
                OBJECTS {
                   nncVpa15MinIntervalNumber,
                   nncVpa15MinIntervalState,
                   nncVpa15MinIntervalAbsoluteIntervalNumber,
                   nncVpa15MinIntervalClp0And1OutCells,
                   nncVpa15MinIntervalDiscardClp0And1Cells,
                   nncVpa15MinIntervalDiscardClp0Cells
                }
                STATUS          current
                DESCRIPTION     "A collection of objects providing 15 Min
                                interval statistics for a VP Aggregation"
        ::= { nncAtmStatisticsGroups 17 }
 
        nncVpa1HourCurrentGroup         OBJECT-GROUP 
                OBJECTS {
                   nncVpa1HourCurrentState,
                   nncVpa1HourCurrentAbsoluteIntervalNumber,
                   nncVpa1HourCurrentClp0And1OutCells,
                   nncVpa1HourCurrentDiscardClp0And1Cells,
                   nncVpa1HourCurrentDiscardClp0Cells
                }
                STATUS          current
                DESCRIPTION     "A collection of objects providing 1 hour
                                current statistics for a VP Aggregation"
        ::= { nncAtmStatisticsGroups 18 }
 
        nncVpa1HourIntervalGroup         OBJECT-GROUP 
                OBJECTS {
                   nncVpa1HourIntervalNumber,
                   nncVpa1HourIntervalState,
                   nncVpa1HourIntervalAbsoluteIntervalNumber,
                   nncVpa1HourIntervalClp0And1OutCells,
                   nncVpa1HourIntervalDiscardClp0And1Cells,
                   nncVpa1HourIntervalDiscardClp0Cells
                }
                STATUS          current
                DESCRIPTION     "A collection of objects providing 1 hour
                                interval statistics for a VP Aggregation"
        ::= { nncAtmStatisticsGroups 19 }
 
--------------------------------------------------------------------------------
-- Compliance Statements (mandatory)
--------------------------------------------------------------------------------
        nncAtmStatisticsCompliance      MODULE-COMPLIANCE
                STATUS          current
                DESCRIPTION     "The compliance statement for Newbridge SNMP
                                entities which have Vpl/Vcl endpoints and VPA"
                MODULE
                        MANDATORY-GROUPS {
                                nncVpl15MinCurrentGroup,
                                nncVpl1HourCurrentGroup,
                                nncVcl15MinCurrentGroup,
                                nncVcl1HourCurrentGroup,
                                nncVplIntervalStateGroup,
                                nncVclIntervalStateGroup,
                                nncVpa15MinCurrentGroup,
                                nncVpa15MinIntervalGroup,
                                nncVpa1HourCurrentGroup,
                                nncVpa1HourIntervalGroup
                        }
        ::= { nncAtmStatisticsCompliances 1 } 

        nncAtmStatisticsServiceCompliance      MODULE-COMPLIANCE
                STATUS          current
                DESCRIPTION     "The compliance statement for Newbridge SNMP
                                 Service-level entities which report on
                                 Vpl/Vcl endpoints"
                MODULE
                        MANDATORY-GROUPS {
                                nncVpl15MinIntervalGroup,
                                nncVcl15MinIntervalGroup,
                                nncVplStatCounterGroup,
                                nncVclStatCounterGroup
                        }
        ::= { nncAtmStatisticsCompliances 2 } 

-------------------------------------------------------------------------------
--      Review Minutes 
-------------------------------------------------------------------------------
--      MINUTES-BEGIN
--              REVIEW-DATE  "1996.04.03"
--              BODY  "
--
--      
--      TO:     ATMnet_S/W_INFO, Frank Chen, Steve Fleury, Nelson Gillette
--      FROM:   Wing-Leung Chan*
--
--      A message was sent out on 1996.04.03 to electronically review
--      ATMStatistics.mib.
--
--      Outcome
--
--      It was the consensus of the review team that this file is 
--      acceptable with the indicated modifications
--
--      Comments:

--      From: James Watt (96/4/7)
--        Content/Usability
--        1) The module name should be NNC-ATM-STATISTICS-MIB (note the extra
--           hyphens) to match the rules in SQP0053,
-- 
--        2) I would move the block of comments before the
--           nncVpl15MinCurrentTable into the DESCRIPTION clause for the module
--           so they get retained even when some "mib munger" tool throws away
--           all of the comments
-- 
--        3) I would have IMPORTed atVplVpi from RFC 1695 and used it in the
--           INDEX clause to make the coupling between the tables more clear to
--           a "dumb" mechanical tool, just the way ifIndex was imported.  This
--           goes for all VPI indexed tables and for VCI tables too, although
--           you need atmVclVci, etc.
--        
--        4) The DESCRIPTION clause for nncVpl15MinCurrentEntry could really
--           use a case diagram to show how the counters add up (or don't add
--           up).
--        
--        5) In nncVpl15MinCurrentClp0And1InCells, does "admitted" mean
--           anything different than "received" ?  Also, does "...to the UPC
--           function.." exclude NPC ?  If not, perhaps using "traffic
--           policing" (as is done) later would be more general
--        
--        6) Do the cell counts include OAM cells ?
--        
--        7) What does "valid cells" mean  in each case ?
--        
--        8) I assume in all cases Idle and Unassigned cells are not counted ?
--        
--        9) In the description clauses the for the IntervalEntry's, there
--           should be a comment about the alignment of the intervals with a
--           reference back to the MODULE's description for more info.
--        
--        10) DOes nncDepthOfHistoricalStrata apply to 15min or 1h or both ?
--            To vcls or vpls or both ?  I can imagine when I would want
--            different values for vcls and vpls as there are a lot more of
--            one than the other...
--        
--        11) In the MODULE-COMPLIANCE invocation, you need to refer to the
--            Interval Groups
--        
--        Editorial
--        a) the IMPORTS clause could get formatted to match the V2 idiom
--           (e.g. see RFC1573),
--        b) the DESCRIPTION text should start under the R in DESCRIPTION
--        c) (a) and (b) make one wish we had a "pretty-printing" tool...
-- 
--      "
--
--      END-MINUTES
-------------------------------------------------------------------------------
--      MINUTES-BEGIN
--              REVIEW-DATE  "1996.01.31"
--              BODY  "
--
--      
--      TO:     Randy Jones*, Frank Chen*, Roger Bainbridge*, Peifang Zhou*
--              Nelson Gillette*, Andrew Paterson*, Sriram Darbha*,
--              Adam Milling*
--      CC:     Numbers Admin, Melanie Paquette, Suzanne Poulos
--      FROM:   Wing-Leung Chan*
--
--      A meeting was held on 1996.01.31 to review ATMStatistics.mib.
--      Attendees are marked with * in the TO and CC lists above.
--
--      Outcome
--
--      It was the consensus of the review team that this file is 
--      acceptable with the indicated modifications
--
--      Actions:
--      A1 -    Wing-Leung Chan to update the file as indicated in D1 below.  
--              Response:                       Status: completed
--
--      A2 -    Roger Bainbridge to fix 31FS0041. 
--              Response:                       Status: accepted
--
--      Decisions:
--      D1 -    ATMStatistics.mib shall be updated as follows:
--              a. delete lines 20-22
--              b. make current state type a textual convention
--              c. change NonExisting to NonExistent
--              d. add absolute interval number to each table entry type
--              e. change all occurrences of DiscardClp1 to DiscardClp0And1
--              f. create read objects that provide the depth of the
--                 historical strata
--              g. improve the description of the 1 hour current entries,
--                 including createAndGo and destroy settings
--              h. line 1094, add vpi index
--              i. create a conformance group per table
--              j. make current tables mandatory, interval tables optional
--
--      "
--
--      END-MINUTES
-------------------------------------------------------------------------------
--      MINUTES-BEGIN
--              REVIEW-DATE  "1996.05.14"
--              BODY  "
--
--      
--      TO:     Randy Jones*, Frank Chen*, Nelson Gillette*, Shafiq Pirbhai*,
--              Dave Fowler*
--      CC:     Numbers Admin, Melanie Paquette
--      FROM:   Mike Rehder*
--
--      A meeting was held on 1996.05.14 to review ATMStatistics.mib.
--      Attendees are marked with * in the TO and CC lists above.
--
--      Outcome
--
--      It was the consensus of the review team that this file is 
--      acceptable with the indicated modifications and an electronic re-review.
--
--      Actions:
--      A1 -    Mike Rehder to update the file as indicated in D1 below.  
--              Response:                        Status: closed
--      A2 -    Mike Rehder to talk to James Watt and find out what is the
--              "preferred" access for the intervalNumber field (no access
--              or read-only)
--              Response:                        Status: closed
--              The field will be not-accessible
--
--     Decisions:
--      D1 -    ATMStatistics.mib shall be updated as follows:
--              a. preserve object numbering for existing objects
--              b. add comments for VxL Stats Table to better explain the table
--              c. rename VxL Stats table - use "raw", "accumulator" or 
--                 something
--              d. page 19, line 113 - change path to channel
--              e. page 21, line 1361 and line 1521 - change "circuit" to 
--                 "channel"
--              f. page 23, line 1514 - change "available" to "maximum interval
--                 number for valid data" (quote is out of the new DS1 mib 
--                 draft)
--              g. change "sample" to "interval"
--              h. page 23, lines 1471-1475 - take out description of index
--              i. line 1502 - spelling of statistical
--              j. page 24, line 1590 - change depth object to be for 15min
--                 intervals and add an object for hourly data.
--      D2 -    change depthOfHistoricalStrata to apply to 15min interval 
--              and add a new depth object for hourly tables
--
--      comments by email
--      from James Watt (5/15/96)
--              1) In SNMPv2, if an object is an index term, i.e. it is
--                  mentioned in the INDEX clause, in general it _must_ be
--                  not-accessible (see RFC 1902 Section 7.7 first 3 of the 
--                  last 4 paragraphs).  SMICng will tell you this when you
--                  run it.
--              2) If it is simply free-running counters ,I would call it the
--                 VxlStatsTable...  It isn't totals, Accumulated doesn't add
--                  any value that I can see and Raw is just weird.
--              3) when Counters are "reset" and
--                  what their initial value is/may be defined by the SMI
--                  (e.g. see RFC 1902 7.1.6).
-- 
--      "
--      END-MINUTES
-------------------------------------------------------------------------------
--      MINUTES-BEGIN
--              REVIEW-DATE  "1998.07.21"
--              BODY  "
--
--      
--      TO:     Frank Chen*, Bill Schaller*, Richard Burke*
--      CC:     Numbers Admin,
--      FROM:   Randy Jones *
--
--      An electronic review  was held on 1998.07.20 to review ATMStatistics.mib.
--      Attendees are marked with * in the TO and CC lists above.
--       The changes correct the DESCRIPTION clause of several object
--      definitions to reflect the fact that counters are formed after
--      aplication of the UPC function. This work was performed to
--      address pts number 240963. Because the changes were minor, an
--      electronic review was deemed acceptable.
--
--      Outcome
--
--      It was the consensus of the review team that this file is 
--      acceptable without changes.
-- 
--      "
--      END-MINUTES
-------------------------------------------------------------------------------
--      MINUTES-BEGIN
--              REVIEW-DATE  "2000.07.18"
--              BODY  "
--
--      
--      TO:     George Yu*, Jack Sinclair*, Walter Prager*, 
--              Christopher Barrett*, Arash Hekmat*, Patrick Demellier*,
--      CC:     Numbers Admin, Philippe Lemetayer
--      FROM:   Bruno Sizun*
--
--      A meeting was held on 2000.07.18 to review ATMStatistics.mib.
--      Attendees are marked with * in the TO and CC lists above.
--
--      Outcome
--
--      It was the consensus of the review team that this file is 
--      acceptable with the indicated modifications
--
--      Actions:
--      A1 -    Bruno Sizun to update the file as indicated in D1 below.  
--              Response:                       Status: completed
--
--
--      Decisions:
--      D1 -    ATMStatistics.mib shall be updated as follows:
--              a. make the MIB nice (indentation, consistency)
--              b. add atmVplVpi index for Vpa tables
--
--      "
--
--      END-MINUTES
--
END -- DEFINITION OF NNC-ATM-STATISTICS-MIB
----------
