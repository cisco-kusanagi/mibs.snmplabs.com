--			Ascend mibipsec MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIPSEC-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfIpsec  OBJECT IDENTIFIER ::= { configuration 85}

	-- The mibmibProfIpsec table
	--
	-- This table contains parameters for the mibmibProfIpsec profile
	--

    mibmibProfIpsecTable	OBJECT-TYPE
	SYNTAX		SEQUENCE OF MibmibProfIpsecEntry
	ACCESS		not-accessible
	STATUS		mandatory
	DESCRIPTION	"A list of mibmibProfIpsec profile entries."
	::= { mibmibProfIpsec 1 }

    mibmibProfIpsecEntry	OBJECT-TYPE
	SYNTAX		MibmibProfIpsecEntry
	ACCESS		not-accessible
	STATUS		mandatory
	DESCRIPTION	"A mibmibProfIpsec entry containing objects that
			 maps to the parameters of mibmibProfIpsec profile."
	INDEX		{ mibProfIpsec-Name }
	::= { mibmibProfIpsecTable 1 }

    MibmibProfIpsecEntry ::=
	SEQUENCE {
	    mibProfIpsec-Name
		DisplayString,
	    mibProfIpsec-Active
		INTEGER,
	    mibProfIpsec-EncapMode
		INTEGER,
	    mibProfIpsec-TunnelAddress
		IpAddress,
	    mibProfIpsec-PfsMode
		INTEGER,
	    mibProfIpsec-SendAh-Active
		INTEGER,
	    mibProfIpsec-SendAh-Spi
		INTEGER,
	    mibProfIpsec-SendAh-AhType
		INTEGER,
	    mibProfIpsec-SendAh-Key
		DisplayString,
	    mibProfIpsec-SendAh-ReplayProtection
		INTEGER,
	    mibProfIpsec-RecvAh-Active
		INTEGER,
	    mibProfIpsec-RecvAh-Spi
		INTEGER,
	    mibProfIpsec-RecvAh-AhType
		INTEGER,
	    mibProfIpsec-RecvAh-Key
		DisplayString,
	    mibProfIpsec-RecvAh-ReplayProtection
		INTEGER,
	    mibProfIpsec-SendEsp-Active
		INTEGER,
	    mibProfIpsec-SendEsp-Spi
		INTEGER,
	    mibProfIpsec-SendEsp-Version
		INTEGER,
	    mibProfIpsec-SendEsp-EspType
		INTEGER,
	    mibProfIpsec-SendEsp-IvLen
		INTEGER,
	    mibProfIpsec-SendEsp-Key
		DisplayString,
	    mibProfIpsec-SendEsp-Key2
		DisplayString,
	    mibProfIpsec-SendEsp-Key3
		DisplayString,
	    mibProfIpsec-SendEsp-AuthType
		INTEGER,
	    mibProfIpsec-SendEsp-AuthKey
		DisplayString,
	    mibProfIpsec-SendEsp-ReplayProtection
		INTEGER,
	    mibProfIpsec-RecvEsp-Active
		INTEGER,
	    mibProfIpsec-RecvEsp-Spi
		INTEGER,
	    mibProfIpsec-RecvEsp-Version
		INTEGER,
	    mibProfIpsec-RecvEsp-EspType
		INTEGER,
	    mibProfIpsec-RecvEsp-IvLen
		INTEGER,
	    mibProfIpsec-RecvEsp-Key
		DisplayString,
	    mibProfIpsec-RecvEsp-Key2
		DisplayString,
	    mibProfIpsec-RecvEsp-Key3
		DisplayString,
	    mibProfIpsec-RecvEsp-AuthType
		INTEGER,
	    mibProfIpsec-RecvEsp-AuthKey
		DisplayString,
	    mibProfIpsec-RecvEsp-ReplayProtection
		INTEGER,
	    mibProfIpsec-SaLife-TimeLimit
		INTEGER,
	    mibProfIpsec-SaLife-SizeLimit
		INTEGER,
	    mibProfIpsec-SaLife-AnticipateRekey
		INTEGER,
	    mibProfIpsec-SaLife-LifeNegotiationFallback
		INTEGER,
	    mibProfIpsec-SaLife-IdleTimeout
		INTEGER,
	    mibProfIpsec-Next
		DisplayString,
	    mibProfIpsec-Action-o
		INTEGER
	}

    mibProfIpsec-Name	OBJECT-TYPE
	SYNTAX	DisplayString
	ACCESS	read-only
	STATUS	mandatory
	DESCRIPTION	"Name of this scheme"
	::= { mibmibProfIpsecEntry 1 }

    mibProfIpsec-Active	OBJECT-TYPE
	SYNTAX	INTEGER {
		    no (1),
		    yes (2)
		}
	ACCESS	read-write
	STATUS	mandatory
	DESCRIPTION	"Is this scheme in use?"
	::= { mibmibProfIpsecEntry 2 }

    mibProfIpsec-EncapMode	OBJECT-TYPE
	SYNTAX	INTEGER {
		    optimized (1),
		    transport (2),
		    tunnel (3)
		}
	ACCESS	read-write
	STATUS	mandatory
	DESCRIPTION	"Encapsulation mode."
	::= { mibmibProfIpsecEntry 3 }

    mibProfIpsec-TunnelAddress	OBJECT-TYPE
	SYNTAX	IpAddress
	ACCESS	read-write
	STATUS	mandatory
	DESCRIPTION	"Address of the machine at the tunnel end."
	::= { mibmibProfIpsecEntry 4 }

    mibProfIpsec-PfsMode	OBJECT-TYPE
	SYNTAX	INTEGER {
		    no (1),
		    keys (2),
		    keysAndId (3)
		}
	ACCESS	read-write
	STATUS	mandatory
	DESCRIPTION	"Perfect Forward Secrecy mode."
	::= { mibmibProfIpsecEntry 38 }

    mibProfIpsec-SendAh-Active	OBJECT-TYPE
	SYNTAX	INTEGER {
		    no (1),
		    yes (2)
		}
	ACCESS	read-write
	STATUS	mandatory
	DESCRIPTION	"Is this profile active? Yes/No."
	::= { mibmibProfIpsecEntry 5 }

    mibProfIpsec-SendAh-Spi	OBJECT-TYPE
	SYNTAX	INTEGER
	ACCESS	read-write
	STATUS	mandatory
	DESCRIPTION	"Security Parameters Index"
	::= { mibmibProfIpsecEntry 6 }

    mibProfIpsec-SendAh-AhType	OBJECT-TYPE
	SYNTAX	INTEGER {
		    none (1),
		    md5 (2),
		    sha1 (3),
		    md5Hmac (4),
		    sha1Hmac (5)
		}
	ACCESS	read-write
	STATUS	mandatory
	DESCRIPTION	"Which type of transform shall we use?"
	::= { mibmibProfIpsecEntry 7 }

    mibProfIpsec-SendAh-Key	OBJECT-TYPE
	SYNTAX	DisplayString
	ACCESS	read-write
	STATUS	mandatory
	DESCRIPTION	"Authentication Key for hashing."
	::= { mibmibProfIpsecEntry 8 }

    mibProfIpsec-SendAh-ReplayProtection	OBJECT-TYPE
	SYNTAX	INTEGER {
		    no (1),
		    yes (2)
		}
	ACCESS	read-write
	STATUS	mandatory
	DESCRIPTION	"Replay Protection enable/disable."
	::= { mibmibProfIpsecEntry 9 }

    mibProfIpsec-RecvAh-Active	OBJECT-TYPE
	SYNTAX	INTEGER {
		    no (1),
		    yes (2)
		}
	ACCESS	read-write
	STATUS	mandatory
	DESCRIPTION	"Is this profile active? Yes/No."
	::= { mibmibProfIpsecEntry 10 }

    mibProfIpsec-RecvAh-Spi	OBJECT-TYPE
	SYNTAX	INTEGER
	ACCESS	read-write
	STATUS	mandatory
	DESCRIPTION	"Security Parameters Index"
	::= { mibmibProfIpsecEntry 11 }

    mibProfIpsec-RecvAh-AhType	OBJECT-TYPE
	SYNTAX	INTEGER {
		    none (1),
		    md5 (2),
		    sha1 (3),
		    md5Hmac (4),
		    sha1Hmac (5)
		}
	ACCESS	read-write
	STATUS	mandatory
	DESCRIPTION	"Which type of transform shall we use?"
	::= { mibmibProfIpsecEntry 12 }

    mibProfIpsec-RecvAh-Key	OBJECT-TYPE
	SYNTAX	DisplayString
	ACCESS	read-write
	STATUS	mandatory
	DESCRIPTION	"Authentication Key for hashing."
	::= { mibmibProfIpsecEntry 13 }

    mibProfIpsec-RecvAh-ReplayProtection	OBJECT-TYPE
	SYNTAX	INTEGER {
		    no (1),
		    yes (2)
		}
	ACCESS	read-write
	STATUS	mandatory
	DESCRIPTION	"Replay Protection enable/disable."
	::= { mibmibProfIpsecEntry 14 }

    mibProfIpsec-SendEsp-Active	OBJECT-TYPE
	SYNTAX	INTEGER {
		    no (1),
		    yes (2)
		}
	ACCESS	read-write
	STATUS	mandatory
	DESCRIPTION	"Is this profile active? Yes/No."
	::= { mibmibProfIpsecEntry 15 }

    mibProfIpsec-SendEsp-Spi	OBJECT-TYPE
	SYNTAX	INTEGER
	ACCESS	read-write
	STATUS	mandatory
	DESCRIPTION	"Security Parameters Index"
	::= { mibmibProfIpsecEntry 16 }

    mibProfIpsec-SendEsp-Version	OBJECT-TYPE
	SYNTAX	INTEGER
	ACCESS	read-write
	STATUS	mandatory
	DESCRIPTION	"Version of ESP."
	::= { mibmibProfIpsecEntry 17 }

    mibProfIpsec-SendEsp-EspType	OBJECT-TYPE
	SYNTAX	INTEGER {
		    none (1),
		    desCbc (2),
		    n-3desCbc (3),
		    n-40desCbc (4)
		}
	ACCESS	read-write
	STATUS	mandatory
	DESCRIPTION	"The Type of ESP Transform."
	::= { mibmibProfIpsecEntry 18 }

    mibProfIpsec-SendEsp-IvLen	OBJECT-TYPE
	SYNTAX	INTEGER {
		    n-32 (2),
		    n-64 (3)
		}
	ACCESS	read-write
	STATUS	mandatory
	DESCRIPTION	"Length of Initialization Vector. Ignored for ESP V2 (always 64)."
	::= { mibmibProfIpsecEntry 19 }

    mibProfIpsec-SendEsp-Key	OBJECT-TYPE
	SYNTAX	DisplayString
	ACCESS	read-write
	STATUS	mandatory
	DESCRIPTION	"Authentication Key for ESP encryption."
	::= { mibmibProfIpsecEntry 20 }

    mibProfIpsec-SendEsp-Key2	OBJECT-TYPE
	SYNTAX	DisplayString
	ACCESS	read-write
	STATUS	mandatory
	DESCRIPTION	"Authentication Key for ESP encryption (only for 3DES-CBC)."
	::= { mibmibProfIpsecEntry 21 }

    mibProfIpsec-SendEsp-Key3	OBJECT-TYPE
	SYNTAX	DisplayString
	ACCESS	read-write
	STATUS	mandatory
	DESCRIPTION	"Authentication Key for ESP encryption (only for 3DES-CBC)."
	::= { mibmibProfIpsecEntry 22 }

    mibProfIpsec-SendEsp-AuthType	OBJECT-TYPE
	SYNTAX	INTEGER {
		    none (1),
		    md5 (2),
		    sha1 (3),
		    md5Hmac (4),
		    sha1Hmac (5)
		}
	ACCESS	read-write
	STATUS	mandatory
	DESCRIPTION	"Authentication Transform to be used. Valid only for ESP V2."
	::= { mibmibProfIpsecEntry 23 }

    mibProfIpsec-SendEsp-AuthKey	OBJECT-TYPE
	SYNTAX	DisplayString
	ACCESS	read-write
	STATUS	mandatory
	DESCRIPTION	"Authentication Key for hashing. Valid only for ESP V2."
	::= { mibmibProfIpsecEntry 24 }

    mibProfIpsec-SendEsp-ReplayProtection	OBJECT-TYPE
	SYNTAX	INTEGER {
		    no (1),
		    yes (2)
		}
	ACCESS	read-write
	STATUS	mandatory
	DESCRIPTION	"Replay Protection enable/disable. Automatically enabled for ESP V2"
	::= { mibmibProfIpsecEntry 25 }

    mibProfIpsec-RecvEsp-Active	OBJECT-TYPE
	SYNTAX	INTEGER {
		    no (1),
		    yes (2)
		}
	ACCESS	read-write
	STATUS	mandatory
	DESCRIPTION	"Is this profile active? Yes/No."
	::= { mibmibProfIpsecEntry 26 }

    mibProfIpsec-RecvEsp-Spi	OBJECT-TYPE
	SYNTAX	INTEGER
	ACCESS	read-write
	STATUS	mandatory
	DESCRIPTION	"Security Parameters Index"
	::= { mibmibProfIpsecEntry 27 }

    mibProfIpsec-RecvEsp-Version	OBJECT-TYPE
	SYNTAX	INTEGER
	ACCESS	read-write
	STATUS	mandatory
	DESCRIPTION	"Version of ESP."
	::= { mibmibProfIpsecEntry 28 }

    mibProfIpsec-RecvEsp-EspType	OBJECT-TYPE
	SYNTAX	INTEGER {
		    none (1),
		    desCbc (2),
		    n-3desCbc (3),
		    n-40desCbc (4)
		}
	ACCESS	read-write
	STATUS	mandatory
	DESCRIPTION	"The Type of ESP Transform."
	::= { mibmibProfIpsecEntry 29 }

    mibProfIpsec-RecvEsp-IvLen	OBJECT-TYPE
	SYNTAX	INTEGER {
		    n-32 (2),
		    n-64 (3)
		}
	ACCESS	read-write
	STATUS	mandatory
	DESCRIPTION	"Length of Initialization Vector. Ignored for ESP V2 (always 64)."
	::= { mibmibProfIpsecEntry 30 }

    mibProfIpsec-RecvEsp-Key	OBJECT-TYPE
	SYNTAX	DisplayString
	ACCESS	read-write
	STATUS	mandatory
	DESCRIPTION	"Authentication Key for ESP encryption."
	::= { mibmibProfIpsecEntry 31 }

    mibProfIpsec-RecvEsp-Key2	OBJECT-TYPE
	SYNTAX	DisplayString
	ACCESS	read-write
	STATUS	mandatory
	DESCRIPTION	"Authentication Key for ESP encryption (only for 3DES-CBC)."
	::= { mibmibProfIpsecEntry 32 }

    mibProfIpsec-RecvEsp-Key3	OBJECT-TYPE
	SYNTAX	DisplayString
	ACCESS	read-write
	STATUS	mandatory
	DESCRIPTION	"Authentication Key for ESP encryption (only for 3DES-CBC)."
	::= { mibmibProfIpsecEntry 33 }

    mibProfIpsec-RecvEsp-AuthType	OBJECT-TYPE
	SYNTAX	INTEGER {
		    none (1),
		    md5 (2),
		    sha1 (3),
		    md5Hmac (4),
		    sha1Hmac (5)
		}
	ACCESS	read-write
	STATUS	mandatory
	DESCRIPTION	"Authentication Transform to be used. Valid only for ESP V2."
	::= { mibmibProfIpsecEntry 34 }

    mibProfIpsec-RecvEsp-AuthKey	OBJECT-TYPE
	SYNTAX	DisplayString
	ACCESS	read-write
	STATUS	mandatory
	DESCRIPTION	"Authentication Key for hashing. Valid only for ESP V2."
	::= { mibmibProfIpsecEntry 35 }

    mibProfIpsec-RecvEsp-ReplayProtection	OBJECT-TYPE
	SYNTAX	INTEGER {
		    no (1),
		    yes (2)
		}
	ACCESS	read-write
	STATUS	mandatory
	DESCRIPTION	"Replay Protection enable/disable. Automatically enabled for ESP V2"
	::= { mibmibProfIpsecEntry 36 }

    mibProfIpsec-SaLife-TimeLimit	OBJECT-TYPE
	SYNTAX	INTEGER
	ACCESS	read-write
	STATUS	mandatory
	DESCRIPTION	"Lifetime of the SA in seconds. The SA will expire at the end of the lifetime. The value of 0 disables the timer."
	::= { mibmibProfIpsecEntry 39 }

    mibProfIpsec-SaLife-SizeLimit	OBJECT-TYPE
	SYNTAX	INTEGER
	ACCESS	read-write
	STATUS	mandatory
	DESCRIPTION	"Maximum number of kilobytes (KB) covered by the SA before it expires. The value of 0 disables the counter."
	::= { mibmibProfIpsecEntry 40 }

    mibProfIpsec-SaLife-AnticipateRekey	OBJECT-TYPE
	SYNTAX	INTEGER
	ACCESS	read-write
	STATUS	mandatory
	DESCRIPTION	"A percentage of lifetime or lifesize to trigger negotiation of a new SA before the old one expires (a.k.a. soft lifetime)."
	::= { mibmibProfIpsecEntry 41 }

    mibProfIpsec-SaLife-LifeNegotiationFallback	OBJECT-TYPE
	SYNTAX	INTEGER {
		    fail (1),
		    complete (2),
		    notification (3)
		}
	ACCESS	read-write
	STATUS	mandatory
	DESCRIPTION	"What to do when local policy requires a shorter life than what is proposed by SA initiator. Applies to IPSec SAs only."
	::= { mibmibProfIpsecEntry 42 }

    mibProfIpsec-SaLife-IdleTimeout	OBJECT-TYPE
	SYNTAX	INTEGER
	ACCESS	read-write
	STATUS	mandatory
	DESCRIPTION	"SA lifetime without traffic."
	::= { mibmibProfIpsecEntry 43 }

    mibProfIpsec-Next	OBJECT-TYPE
	SYNTAX	DisplayString
	ACCESS	read-write
	STATUS	mandatory
	DESCRIPTION	"The name of the next IPSec protection suite."
	::= { mibmibProfIpsecEntry 44 }

    mibProfIpsec-Action-o	OBJECT-TYPE
	SYNTAX	INTEGER {
		    noAction (1),
		    createProfile (2),
		    deleteProfile (3)
		}
	ACCESS	read-write
	STATUS	mandatory
	DESCRIPTION	""
	::= { mibmibProfIpsecEntry 37 }

END
