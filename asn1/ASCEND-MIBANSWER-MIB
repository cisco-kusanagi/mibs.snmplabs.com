--			Ascend mibanswer MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBANSWER-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibanswerProfile  OBJECT IDENTIFIER ::= { configuration 3}

	-- The mibanswerProfile table
	--
	-- This table contains parameters for the mibanswerProfile profile
	--

    mibanswerProfileTable	OBJECT-TYPE
	SYNTAX		SEQUENCE OF MibanswerProfileEntry
	ACCESS		not-accessible
	STATUS		mandatory
	DESCRIPTION	"A list of mibanswerProfile profile entries."
	::= { mibanswerProfile 1 }

    mibanswerProfileEntry	OBJECT-TYPE
	SYNTAX		MibanswerProfileEntry
	ACCESS		not-accessible
	STATUS		mandatory
	DESCRIPTION	"A mibanswerProfile entry containing objects that
			 maps to the parameters of mibanswerProfile profile."
	INDEX		{ answerProfile-Index-o }
	::= { mibanswerProfileTable 1 }

    MibanswerProfileEntry ::=
	SEQUENCE {
	    answerProfile-Index-o
		INTEGER,
	    answerProfile-UseAnswerForAllDefaults
		INTEGER,
	    answerProfile-Force56kbps
		INTEGER,
	    answerProfile-ProfilesRequired
		INTEGER,
	    answerProfile-ClidAuthMode
		INTEGER,
	    answerProfile-ClidSelection
		INTEGER,
	    answerProfile-CallbackClidPrefix
		DisplayString,
	    answerProfile-PppAnswer-Enabled
		INTEGER,
	    answerProfile-PppAnswer-ReceiveAuthMode
		INTEGER,
	    answerProfile-PppAnswer-BiDirectionalAuth
		INTEGER,
	    answerProfile-PppAnswer-SubstituteSendName
		DisplayString,
	    answerProfile-PppAnswer-DisconnectOnAuthTimeout
		INTEGER,
	    answerProfile-PppAnswer-BridgingGroup
		INTEGER,
	    answerProfile-PppAnswer-LinkCompression
		INTEGER,
	    answerProfile-PppAnswer-Mru
		INTEGER,
	    answerProfile-PppAnswer-Lqm
		INTEGER,
	    answerProfile-PppAnswer-LqmMinimumPeriod
		INTEGER,
	    answerProfile-PppAnswer-LqmMaximumPeriod
		INTEGER,
	    answerProfile-PppAnswer-CbcpEnabled
		INTEGER,
	    answerProfile-PppAnswer-IpxHeaderCompression
		INTEGER,
	    answerProfile-PppAnswer-Mtu
		INTEGER,
	    answerProfile-PppAnswer-AuthForAsyncFramedUsers
		INTEGER,
	    answerProfile-PppAnswer-MaxPapAuthRetry
		INTEGER,
	    answerProfile-PppAnswer-MaxPppConfigureRetry
		INTEGER,
	    answerProfile-PppAnswer-PppRestartTimer
		INTEGER,
	    answerProfile-PppAnswer-MaxPppRestartTimer
		INTEGER,
	    answerProfile-MpAnswer-Enabled
		INTEGER,
	    answerProfile-MpAnswer-MinimumChannels
		INTEGER,
	    answerProfile-MpAnswer-MaximumChannels
		INTEGER,
	    answerProfile-MpAnswer-BacpEnable
		INTEGER,
	    answerProfile-MppAnswer-Enabled
		INTEGER,
	    answerProfile-MppAnswer-DynamicAlgorithm
		INTEGER,
	    answerProfile-MppAnswer-BandwidthMonitorDirection
		INTEGER,
	    answerProfile-MppAnswer-IncrementChannelCount
		INTEGER,
	    answerProfile-MppAnswer-DecrementChannelCount
		INTEGER,
	    answerProfile-MppAnswer-SecondsHistory
		INTEGER,
	    answerProfile-MppAnswer-AddPersistence
		INTEGER,
	    answerProfile-MppAnswer-SubPersistence
		INTEGER,
	    answerProfile-MppAnswer-TargetUtilization
		INTEGER,
	    answerProfile-FrAnswer-Enabled
		INTEGER,
	    answerProfile-TcpClearAnswer-Enabled
		INTEGER,
	    answerProfile-AraAnswer-Enabled
		INTEGER,
	    answerProfile-V120Answer-Enabled
		INTEGER,
	    answerProfile-V120Answer-FrameLength
		INTEGER,
	    answerProfile-X25Answer-Enabled
		INTEGER,
	    answerProfile-X25Answer-X25Profile
		DisplayString,
	    answerProfile-X25Answer-X3Profile
		INTEGER,
	    answerProfile-X25Answer-MaxCalls
		INTEGER,
	    answerProfile-X25Answer-VcTimerEnable
		INTEGER,
	    answerProfile-X25Answer-AutoCallX121Address
		DisplayString,
	    answerProfile-X25Answer-ReverseCharge
		INTEGER,
	    answerProfile-X25Answer-X3CustomProf
		DisplayString,
	    answerProfile-EuAnswer-EurawEnabled
		INTEGER,
	    answerProfile-EuAnswer-EuuiEnabled
		INTEGER,
	    answerProfile-EuAnswer-DceAddr
		INTEGER,
	    answerProfile-EuAnswer-DteAddr
		INTEGER,
	    answerProfile-EuAnswer-Mru
		INTEGER,
	    answerProfile-IpAnswer-Enabled
		INTEGER,
	    answerProfile-IpAnswer-VjHeaderPrediction
		INTEGER,
	    answerProfile-IpAnswer-AssignAddress
		INTEGER,
	    answerProfile-IpAnswer-RoutingMetric
		INTEGER,
	    answerProfile-IpAnswer-PrivateRouteProfileRequired
		INTEGER,
	    answerProfile-IpAnswer-PoolForAsyncFramedUser
		INTEGER,
	    answerProfile-IpxAnswer-Enabled
		INTEGER,
	    answerProfile-IpxAnswer-PeerMode
		INTEGER,
	    answerProfile-SessionInfo-CallFilter
		DisplayString,
	    answerProfile-SessionInfo-DataFilter
		DisplayString,
	    answerProfile-SessionInfo-FilterPersistence
		INTEGER,
	    answerProfile-SessionInfo-FilterRequired
		INTEGER,
	    answerProfile-SessionInfo-IdleTimer
		INTEGER,
	    answerProfile-SessionInfo-TsIdleMode
		INTEGER,
	    answerProfile-SessionInfo-TsIdleTimer
		INTEGER,
	    answerProfile-SessionInfo-MaxCallDuration
		INTEGER,
	    answerProfile-X75Answer-Enabled
		INTEGER,
	    answerProfile-X75Answer-KFramesOutstanding
		INTEGER,
	    answerProfile-X75Answer-N2Retransmissions
		INTEGER,
	    answerProfile-X75Answer-T1RetranTimer
		INTEGER,
	    answerProfile-X75Answer-FrameLength
		INTEGER,
	    answerProfile-FramedOnly
		INTEGER,
	    answerProfile-HdlcNrmAnswer-Enabled
		INTEGER,
	    answerProfile-Visa2Answer-Enabled
		INTEGER,
	    answerProfile-AtmAnswer-SvcEnabled
		INTEGER,
	    answerProfile-PriorityAnswer-Enabled
		INTEGER,
	    answerProfile-PriorityAnswer-PacketClassification
		INTEGER,
	    answerProfile-PriorityAnswer-MaxRtpPacketDelay
		INTEGER,
	    answerProfile-PriorityAnswer-MinimumRtpPort
		INTEGER,
	    answerProfile-PriorityAnswer-MaximumRtpPort
		INTEGER,
	    answerProfile-PriorityAnswer-NoHighPrioPktDuration
		INTEGER,
	    answerProfile-Action-o
		INTEGER
	}

    answerProfile-Index-o	OBJECT-TYPE
	SYNTAX	INTEGER
	ACCESS	read-only
	STATUS	mandatory
	DESCRIPTION	""
	::= { mibanswerProfileEntry 1 }

    answerProfile-UseAnswerForAllDefaults	OBJECT-TYPE
	SYNTAX	INTEGER {
		    no (1),
		    yes (2)
		}
	ACCESS	read-write
	STATUS	mandatory
	DESCRIPTION	"When set to Yes, this profile will provide the default values for fields when building profiles. When set to No the factory profile will be used instead."
	::= { mibanswerProfileEntry 2 }

    answerProfile-Force56kbps	OBJECT-TYPE
	SYNTAX	INTEGER {
		    no (1),
		    yes (2)
		}
	ACCESS	read-write
	STATUS	mandatory
	DESCRIPTION	"If yes then inbound 64 kbps calls are connected at 56 kbps."
	::= { mibanswerProfileEntry 3 }

    answerProfile-ProfilesRequired	OBJECT-TYPE
	SYNTAX	INTEGER {
		    no (1),
		    yes (2)
		}
	ACCESS	read-write
	STATUS	mandatory
	DESCRIPTION	"Unused when incoming authentication is used. When authentication is not used a No value in this field indicates that we will create a temporary profile for a user on incoming calls. A Yes value indicates that we must find an existing profile (by matching the caller's IP address). This provided NO security."
	::= { mibanswerProfileEntry 4 }

    answerProfile-ClidAuthMode	OBJECT-TYPE
	SYNTAX	INTEGER {
		    ignore (1),
		    clidRequire (3),
		    clidPrefer (2),
		    clidFirst (7),
		    clidFallback (4),
		    dnisRequire (5),
		    dnisPref (6),
		    dnisFirst (8),
		    dnisFallback (9)
		}
	ACCESS	read-write
	STATUS	mandatory
	DESCRIPTION	"Specifies how calling line identification (CLID) will be used for incoming call authentication."
	::= { mibanswerProfileEntry 5 }

    answerProfile-ClidSelection	OBJECT-TYPE
	SYNTAX	INTEGER {
		    first (1),
		    securePrefer (2),
		    secureRequire (3),
		    userPrefer (4),
		    userRequire (5)
		}
	ACCESS	read-write
	STATUS	mandatory
	DESCRIPTION	"Selection of the CLID. An incoming call can optionally specify several CLIDs. A CLID provided by the PSTN (network provided) is considered secure. A CLID provided by the end user (user provided) is secure only if it has been validated by the PSTN (user provided, network verified and passed). Other forms of user CLIDs are considered unsecure."
	::= { mibanswerProfileEntry 73 }

    answerProfile-CallbackClidPrefix	OBJECT-TYPE
	SYNTAX	DisplayString
	ACCESS	read-write
	STATUS	mandatory
	DESCRIPTION	"Prefix to prepend to the dial number when callback is performed with the CLID number."
	::= { mibanswerProfileEntry 85 }

    answerProfile-PppAnswer-Enabled	OBJECT-TYPE
	SYNTAX	INTEGER {
		    no (1),
		    yes (2)
		}
	ACCESS	read-write
	STATUS	mandatory
	DESCRIPTION	"Set to Yes to enable incoming PPP calls. This includes the PPP variants, MP and MPP."
	::= { mibanswerProfileEntry 6 }

    answerProfile-PppAnswer-ReceiveAuthMode	OBJECT-TYPE
	SYNTAX	INTEGER {
		    noPppAuth (1),
		    papPppAuth (2),
		    chapPppAuth (3),
		    anyPppAuth (4),
		    desPapPppAuth (5),
		    tokenPapPppAuth (6),
		    tokenChapPppAuth (7),
		    cacheTokenPppAuth (8),
		    msChapPppAuth (9),
		    papPreferred (10)
		}
	ACCESS	read-write
	STATUS	mandatory
	DESCRIPTION	"The type of PPP authentication to use for incoming calls."
	::= { mibanswerProfileEntry 7 }

    answerProfile-PppAnswer-BiDirectionalAuth	OBJECT-TYPE
	SYNTAX	INTEGER {
		    none (1),
		    allowed (2),
		    required (3)
		}
	ACCESS	read-write
	STATUS	mandatory
	DESCRIPTION	"This parameter enables the authentication to be done in both directions. It can be used only with the CHAP, MS-CHAP or CACHE-TOKEN authentication."
	::= { mibanswerProfileEntry 79 }

    answerProfile-PppAnswer-SubstituteSendName	OBJECT-TYPE
	SYNTAX	DisplayString
	ACCESS	read-write
	STATUS	mandatory
	DESCRIPTION	"Name send to the far end, if different from the global system name."
	::= { mibanswerProfileEntry 80 }

    answerProfile-PppAnswer-DisconnectOnAuthTimeout	OBJECT-TYPE
	SYNTAX	INTEGER {
		    no (1),
		    yes (2)
		}
	ACCESS	read-write
	STATUS	mandatory
	DESCRIPTION	"???."
	::= { mibanswerProfileEntry 8 }

    answerProfile-PppAnswer-BridgingGroup	OBJECT-TYPE
	SYNTAX	INTEGER
	ACCESS	read-write
	STATUS	mandatory
	DESCRIPTION	"The default bridging group. Interfaces with the same bridging group can bridge to each other. Set to 0 to disable bridging."
	::= { mibanswerProfileEntry 9 }

    answerProfile-PppAnswer-LinkCompression	OBJECT-TYPE
	SYNTAX	INTEGER {
		    none (1),
		    stac (2),
		    stac9 (3),
		    msStac (4),
		    mppc (5)
		}
	ACCESS	read-write
	STATUS	mandatory
	DESCRIPTION	"The default type of link compression to use for PPP, MP, and MPP calls."
	::= { mibanswerProfileEntry 10 }

    answerProfile-PppAnswer-Mru	OBJECT-TYPE
	SYNTAX	INTEGER
	ACCESS	read-write
	STATUS	mandatory
	DESCRIPTION	"The Maximum Receive Unit, i.e. the largest frame we will accept."
	::= { mibanswerProfileEntry 11 }

    answerProfile-PppAnswer-Lqm	OBJECT-TYPE
	SYNTAX	INTEGER {
		    no (1),
		    yes (2)
		}
	ACCESS	read-write
	STATUS	mandatory
	DESCRIPTION	"Link Quality Monitoring. Set to Yes to enable the PPP LQM protocol."
	::= { mibanswerProfileEntry 12 }

    answerProfile-PppAnswer-LqmMinimumPeriod	OBJECT-TYPE
	SYNTAX	INTEGER
	ACCESS	read-write
	STATUS	mandatory
	DESCRIPTION	"The minimum period, in 1/100 of a second, that we will accept/send link quality monitoring packets."
	::= { mibanswerProfileEntry 13 }

    answerProfile-PppAnswer-LqmMaximumPeriod	OBJECT-TYPE
	SYNTAX	INTEGER
	ACCESS	read-write
	STATUS	mandatory
	DESCRIPTION	"The maximum period, in 1/100 of a second, that we will accept/send link quality monitoring packets."
	::= { mibanswerProfileEntry 14 }

    answerProfile-PppAnswer-CbcpEnabled	OBJECT-TYPE
	SYNTAX	INTEGER {
		    no (1),
		    yes (2)
		}
	ACCESS	read-write
	STATUS	mandatory
	DESCRIPTION	"Enable Microsoft Callback Control Protocol Negotiation."
	::= { mibanswerProfileEntry 70 }

    answerProfile-PppAnswer-IpxHeaderCompression	OBJECT-TYPE
	SYNTAX	INTEGER {
		    no (1),
		    yes (2)
		}
	ACCESS	read-write
	STATUS	mandatory
	DESCRIPTION	"Use IPX header compression if encapsulation supports it."
	::= { mibanswerProfileEntry 74 }

    answerProfile-PppAnswer-Mtu	OBJECT-TYPE
	SYNTAX	INTEGER
	ACCESS	read-write
	STATUS	mandatory
	DESCRIPTION	"The Maximum Transmit Unit, i.e. the largest frame we will send out."
	::= { mibanswerProfileEntry 75 }

    answerProfile-PppAnswer-AuthForAsyncFramedUsers	OBJECT-TYPE
	SYNTAX	INTEGER {
		    notRequired (1),
		    required (2)
		}
	ACCESS	read-write
	STATUS	mandatory
	DESCRIPTION	"Determines whether we need to authenticate async framed users."
	::= { mibanswerProfileEntry 81 }

    answerProfile-PppAnswer-MaxPapAuthRetry	OBJECT-TYPE
	SYNTAX	INTEGER
	ACCESS	read-write
	STATUS	mandatory
	DESCRIPTION	"Number of retries allowed, if PAP authentication fails."
	::= { mibanswerProfileEntry 82 }

    answerProfile-PppAnswer-MaxPppConfigureRetry	OBJECT-TYPE
	SYNTAX	INTEGER
	ACCESS	read-write
	STATUS	mandatory
	DESCRIPTION	"Number of retries allowed, if LCP/NCP fails"
	::= { mibanswerProfileEntry 92 }

    answerProfile-PppAnswer-PppRestartTimer	OBJECT-TYPE
	SYNTAX	INTEGER
	ACCESS	read-write
	STATUS	mandatory
	DESCRIPTION	"Initial LCP/NCP restart timer"
	::= { mibanswerProfileEntry 93 }

    answerProfile-PppAnswer-MaxPppRestartTimer	OBJECT-TYPE
	SYNTAX	INTEGER
	ACCESS	read-write
	STATUS	mandatory
	DESCRIPTION	"Maximum LCP/NCP restart timer"
	::= { mibanswerProfileEntry 94 }

    answerProfile-MpAnswer-Enabled	OBJECT-TYPE
	SYNTAX	INTEGER {
		    no (1),
		    yes (2)
		}
	ACCESS	read-write
	STATUS	mandatory
	DESCRIPTION	"Set to Yes to enable incoming MP calls. This includes the MP variant, MPP."
	::= { mibanswerProfileEntry 15 }

    answerProfile-MpAnswer-MinimumChannels	OBJECT-TYPE
	SYNTAX	INTEGER
	ACCESS	read-write
	STATUS	mandatory
	DESCRIPTION	"The default value for the minimum number of channels in a multi-channel call."
	::= { mibanswerProfileEntry 16 }

    answerProfile-MpAnswer-MaximumChannels	OBJECT-TYPE
	SYNTAX	INTEGER
	ACCESS	read-write
	STATUS	mandatory
	DESCRIPTION	"The default value for the maximum number of channels in a multi-channel call."
	::= { mibanswerProfileEntry 17 }

    answerProfile-MpAnswer-BacpEnable	OBJECT-TYPE
	SYNTAX	INTEGER {
		    no (1),
		    yes (2)
		}
	ACCESS	read-write
	STATUS	mandatory
	DESCRIPTION	"Enable Bandwidth Allocation Control Protocol (BACP)."
	::= { mibanswerProfileEntry 18 }

    answerProfile-MppAnswer-Enabled	OBJECT-TYPE
	SYNTAX	INTEGER {
		    no (1),
		    yes (2)
		}
	ACCESS	read-write
	STATUS	mandatory
	DESCRIPTION	"Set to Yes to enable incoming MPP calls."
	::= { mibanswerProfileEntry 19 }

    answerProfile-MppAnswer-DynamicAlgorithm	OBJECT-TYPE
	SYNTAX	INTEGER {
		    constant (1),
		    linear (2),
		    quadratic (3)
		}
	ACCESS	read-write
	STATUS	mandatory
	DESCRIPTION	"The algorithm to use to calculate the average link utilization. Bandwidth changes are performed on the average utilization, not current utilization."
	::= { mibanswerProfileEntry 20 }

    answerProfile-MppAnswer-BandwidthMonitorDirection	OBJECT-TYPE
	SYNTAX	INTEGER {
		    transmit (1),
		    transmitRecv (2),
		    none (3)
		}
	ACCESS	read-write
	STATUS	mandatory
	DESCRIPTION	"The direction to monitor link utilization. A unit can monitor transmit, transmit and receive, or turn off monitoring entirely."
	::= { mibanswerProfileEntry 21 }

    answerProfile-MppAnswer-IncrementChannelCount	OBJECT-TYPE
	SYNTAX	INTEGER
	ACCESS	read-write
	STATUS	mandatory
	DESCRIPTION	"Number of channels to increment as a block."
	::= { mibanswerProfileEntry 22 }

    answerProfile-MppAnswer-DecrementChannelCount	OBJECT-TYPE
	SYNTAX	INTEGER
	ACCESS	read-write
	STATUS	mandatory
	DESCRIPTION	"Number of channels to decrement as a block."
	::= { mibanswerProfileEntry 23 }

    answerProfile-MppAnswer-SecondsHistory	OBJECT-TYPE
	SYNTAX	INTEGER
	ACCESS	read-write
	STATUS	mandatory
	DESCRIPTION	"The number of seconds of history that link utilization is averaged over to make bandwidth changes."
	::= { mibanswerProfileEntry 24 }

    answerProfile-MppAnswer-AddPersistence	OBJECT-TYPE
	SYNTAX	INTEGER
	ACCESS	read-write
	STATUS	mandatory
	DESCRIPTION	"The number of seconds of that the average line utilization must exceed the target utilization before bandwidth will be added."
	::= { mibanswerProfileEntry 25 }

    answerProfile-MppAnswer-SubPersistence	OBJECT-TYPE
	SYNTAX	INTEGER
	ACCESS	read-write
	STATUS	mandatory
	DESCRIPTION	"The number of seconds of that the average line utilization must fall below the target utilization before bandwidth will be reduced. Bandwidth will not be reduced if the reduced bandwidth would exceed the target utilization."
	::= { mibanswerProfileEntry 26 }

    answerProfile-MppAnswer-TargetUtilization	OBJECT-TYPE
	SYNTAX	INTEGER
	ACCESS	read-write
	STATUS	mandatory
	DESCRIPTION	"The default value for the target utilization. Bandwidth changes occur when the average utilization exceeds or falls below this value."
	::= { mibanswerProfileEntry 27 }

    answerProfile-FrAnswer-Enabled	OBJECT-TYPE
	SYNTAX	INTEGER {
		    no (1),
		    yes (2)
		}
	ACCESS	read-write
	STATUS	mandatory
	DESCRIPTION	"Set to yes to enable incoming FR calls."
	::= { mibanswerProfileEntry 28 }

    answerProfile-TcpClearAnswer-Enabled	OBJECT-TYPE
	SYNTAX	INTEGER {
		    no (1),
		    yes (2)
		}
	ACCESS	read-write
	STATUS	mandatory
	DESCRIPTION	"If enabled, incoming calls that match a local profile with a call management type of tcp-raw will automatically be connected via a raw TCP pipe to the host named in the local profile. If disabled, logins that match a tcp-raw profile will be rejected."
	::= { mibanswerProfileEntry 29 }

    answerProfile-AraAnswer-Enabled	OBJECT-TYPE
	SYNTAX	INTEGER {
		    no (1),
		    yes (2)
		}
	ACCESS	read-write
	STATUS	mandatory
	DESCRIPTION	"Set to yes to enable incoming ARA calls."
	::= { mibanswerProfileEntry 30 }

    answerProfile-V120Answer-Enabled	OBJECT-TYPE
	SYNTAX	INTEGER {
		    no (1),
		    yes (2)
		}
	ACCESS	read-write
	STATUS	mandatory
	DESCRIPTION	"Set to yes to enable incoming V120 calls."
	::= { mibanswerProfileEntry 31 }

    answerProfile-V120Answer-FrameLength	OBJECT-TYPE
	SYNTAX	INTEGER
	ACCESS	read-write
	STATUS	mandatory
	DESCRIPTION	"The default frame length to use for incoming V.120 connections."
	::= { mibanswerProfileEntry 32 }

    answerProfile-X25Answer-Enabled	OBJECT-TYPE
	SYNTAX	INTEGER {
		    no (1),
		    yes (2)
		}
	ACCESS	read-write
	STATUS	mandatory
	DESCRIPTION	"If enabled, incoming calls that match a local profile with a call management type of x25 will be accepted."
	::= { mibanswerProfileEntry 33 }

    answerProfile-X25Answer-X25Profile	OBJECT-TYPE
	SYNTAX	DisplayString
	ACCESS	read-write
	STATUS	mandatory
	DESCRIPTION	"Name of the x25 profile that this profile is associated with."
	::= { mibanswerProfileEntry 34 }

    answerProfile-X25Answer-X3Profile	OBJECT-TYPE
	SYNTAX	INTEGER {
		    crtProfile (1),
		    infonetProfile (2),
		    defaultProfile (3),
		    scenProfile (4),
		    ccSspProfile (5),
		    ccTspProfile (6),
		    hardcopyProfile (7),
		    hdxProfile (8),
		    sharkProfile (9),
		    posProfile (12),
		    nullProfile (10),
		    customProfile (11)
		}
	ACCESS	read-write
	STATUS	mandatory
	DESCRIPTION	"X.3 profile parameter index"
	::= { mibanswerProfileEntry 35 }

    answerProfile-X25Answer-MaxCalls	OBJECT-TYPE
	SYNTAX	INTEGER
	ACCESS	read-write
	STATUS	mandatory
	DESCRIPTION	"Max number of unsuccessful calls"
	::= { mibanswerProfileEntry 36 }

    answerProfile-X25Answer-VcTimerEnable	OBJECT-TYPE
	SYNTAX	INTEGER {
		    no (1),
		    yes (2)
		}
	ACCESS	read-write
	STATUS	mandatory
	DESCRIPTION	"PAD VCE enable flag"
	::= { mibanswerProfileEntry 37 }

    answerProfile-X25Answer-AutoCallX121Address	OBJECT-TYPE
	SYNTAX	DisplayString
	ACCESS	read-only
	STATUS	mandatory
	DESCRIPTION	"X.121 address to auto-call upon session startup."
	::= { mibanswerProfileEntry 38 }

    answerProfile-X25Answer-ReverseCharge	OBJECT-TYPE
	SYNTAX	INTEGER {
		    no (1),
		    yes (2)
		}
	ACCESS	read-write
	STATUS	mandatory
	DESCRIPTION	"Reverse charge request"
	::= { mibanswerProfileEntry 39 }

    answerProfile-X25Answer-X3CustomProf	OBJECT-TYPE
	SYNTAX	DisplayString
	ACCESS	read-only
	STATUS	mandatory
	DESCRIPTION	"Custom profile enter a string for a custom X.3 profile if x3Prof says custom."
	::= { mibanswerProfileEntry 40 }

    answerProfile-EuAnswer-EurawEnabled	OBJECT-TYPE
	SYNTAX	INTEGER {
		    no (1),
		    yes (2)
		}
	ACCESS	read-write
	STATUS	mandatory
	DESCRIPTION	"Enable/disable the EUNET raw protocol."
	::= { mibanswerProfileEntry 45 }

    answerProfile-EuAnswer-EuuiEnabled	OBJECT-TYPE
	SYNTAX	INTEGER {
		    no (1),
		    yes (2)
		}
	ACCESS	read-write
	STATUS	mandatory
	DESCRIPTION	"Enable/disable the EUNET UI protocol."
	::= { mibanswerProfileEntry 46 }

    answerProfile-EuAnswer-DceAddr	OBJECT-TYPE
	SYNTAX	INTEGER
	ACCESS	read-write
	STATUS	mandatory
	DESCRIPTION	"The address of the DCE side of the link when the EUNET UI protocol is used."
	::= { mibanswerProfileEntry 47 }

    answerProfile-EuAnswer-DteAddr	OBJECT-TYPE
	SYNTAX	INTEGER
	ACCESS	read-write
	STATUS	mandatory
	DESCRIPTION	"The address of the DTE side of the link when the EUNET UI protocol is used."
	::= { mibanswerProfileEntry 48 }

    answerProfile-EuAnswer-Mru	OBJECT-TYPE
	SYNTAX	INTEGER
	ACCESS	read-write
	STATUS	mandatory
	DESCRIPTION	"The Maximum Receive Unit, i.e. the largest frame we will accept when the EUNET UI protocol is used."
	::= { mibanswerProfileEntry 49 }

    answerProfile-IpAnswer-Enabled	OBJECT-TYPE
	SYNTAX	INTEGER {
		    no (1),
		    yes (2)
		}
	ACCESS	read-write
	STATUS	mandatory
	DESCRIPTION	"Set to yes to enable IP routing on incoming calls using encapsulation protocols that support IP routing."
	::= { mibanswerProfileEntry 50 }

    answerProfile-IpAnswer-VjHeaderPrediction	OBJECT-TYPE
	SYNTAX	INTEGER {
		    no (1),
		    yes (2)
		}
	ACCESS	read-write
	STATUS	mandatory
	DESCRIPTION	"Set to yes to enable Van Jacobson IP header prediction to be negotiated on incoming calls using encapsulation protocols that support this feature."
	::= { mibanswerProfileEntry 51 }

    answerProfile-IpAnswer-AssignAddress	OBJECT-TYPE
	SYNTAX	INTEGER {
		    no (1),
		    yes (2)
		}
	ACCESS	read-write
	STATUS	mandatory
	DESCRIPTION	"Set to yes if this unit is configured with one or more pools of IP addresses that will be used as a source of addresses to assign to incoming callers."
	::= { mibanswerProfileEntry 52 }

    answerProfile-IpAnswer-RoutingMetric	OBJECT-TYPE
	SYNTAX	INTEGER
	ACCESS	read-write
	STATUS	mandatory
	DESCRIPTION	"The default metric assigned to routes created for incoming calls."
	::= { mibanswerProfileEntry 53 }

    answerProfile-IpAnswer-PrivateRouteProfileRequired	OBJECT-TYPE
	SYNTAX	INTEGER {
		    no (1),
		    yes (2)
		}
	ACCESS	read-write
	STATUS	mandatory
	DESCRIPTION	"Parameter to decide default action,if private route table not found. If set to yes, the call will be cleared if the private route profile cannot be found. If set to no, the call will be allowed to complete, even if the private route profile cannot be found."
	::= { mibanswerProfileEntry 76 }

    answerProfile-IpAnswer-PoolForAsyncFramedUser	OBJECT-TYPE
	SYNTAX	INTEGER
	ACCESS	read-write
	STATUS	mandatory
	DESCRIPTION	"Pool number to be used for dial-in asynchronous PPP framed users with out authentication."
	::= { mibanswerProfileEntry 83 }

    answerProfile-IpxAnswer-Enabled	OBJECT-TYPE
	SYNTAX	INTEGER {
		    no (1),
		    yes (2)
		}
	ACCESS	read-write
	STATUS	mandatory
	DESCRIPTION	"Set to Yes to enable incoming IPX calls."
	::= { mibanswerProfileEntry 54 }

    answerProfile-IpxAnswer-PeerMode	OBJECT-TYPE
	SYNTAX	INTEGER {
		    routerPeer (1),
		    dialinPeer (2)
		}
	ACCESS	read-write
	STATUS	mandatory
	DESCRIPTION	"Enable/disable full routing between peer or use the pool to assign a network number."
	::= { mibanswerProfileEntry 55 }

    answerProfile-SessionInfo-CallFilter	OBJECT-TYPE
	SYNTAX	DisplayString
	ACCESS	read-write
	STATUS	mandatory
	DESCRIPTION	"The name of the filter used to determine if a packet should cause the idle timer to be reset or, when the answer profile is used for connection profile defaults, if a call should be placed."
	::= { mibanswerProfileEntry 56 }

    answerProfile-SessionInfo-DataFilter	OBJECT-TYPE
	SYNTAX	DisplayString
	ACCESS	read-write
	STATUS	mandatory
	DESCRIPTION	"The name of the filter used to determine if packets should be forwarded or dropped."
	::= { mibanswerProfileEntry 57 }

    answerProfile-SessionInfo-FilterPersistence	OBJECT-TYPE
	SYNTAX	INTEGER {
		    no (1),
		    yes (2)
		}
	ACCESS	read-write
	STATUS	mandatory
	DESCRIPTION	"Determines if filters should persist between calls."
	::= { mibanswerProfileEntry 58 }

    answerProfile-SessionInfo-FilterRequired	OBJECT-TYPE
	SYNTAX	INTEGER {
		    no (1),
		    yes (2)
		}
	ACCESS	read-write
	STATUS	mandatory
	DESCRIPTION	"If No, the call will be allowed to come up even if the specified filter was not found either locally, in the cache or in RADIUS. If Yes, then the call will be cleared if the specified filter was not found either locally, in the cache or in RADIUS."
	::= { mibanswerProfileEntry 77 }

    answerProfile-SessionInfo-IdleTimer	OBJECT-TYPE
	SYNTAX	INTEGER
	ACCESS	read-write
	STATUS	mandatory
	DESCRIPTION	"The number of seconds of no activity before a call will be dropped. The value 0 disables the idle timer."
	::= { mibanswerProfileEntry 59 }

    answerProfile-SessionInfo-TsIdleMode	OBJECT-TYPE
	SYNTAX	INTEGER {
		    noIdle (1),
		    inputOnlyIdle (2),
		    inputOutputIdle (3)
		}
	ACCESS	read-write
	STATUS	mandatory
	DESCRIPTION	"The method used to determine when the terminal server idle session timer is reset."
	::= { mibanswerProfileEntry 60 }

    answerProfile-SessionInfo-TsIdleTimer	OBJECT-TYPE
	SYNTAX	INTEGER
	ACCESS	read-write
	STATUS	mandatory
	DESCRIPTION	"The number of seconds of no activity as defined by the idle mode before a session will be terminated."
	::= { mibanswerProfileEntry 61 }

    answerProfile-SessionInfo-MaxCallDuration	OBJECT-TYPE
	SYNTAX	INTEGER
	ACCESS	read-write
	STATUS	mandatory
	DESCRIPTION	"The number of minutes of connect time before a call will be dropped. The value 0 disables the connection timer."
	::= { mibanswerProfileEntry 62 }

    answerProfile-X75Answer-Enabled	OBJECT-TYPE
	SYNTAX	INTEGER {
		    no (1),
		    yes (2)
		}
	ACCESS	read-write
	STATUS	mandatory
	DESCRIPTION	"Set to yes to enable incoming X75 calls."
	::= { mibanswerProfileEntry 63 }

    answerProfile-X75Answer-KFramesOutstanding	OBJECT-TYPE
	SYNTAX	INTEGER
	ACCESS	read-write
	STATUS	mandatory
	DESCRIPTION	"Number of frames outstanding before we require an ack. Defaults to 7."
	::= { mibanswerProfileEntry 64 }

    answerProfile-X75Answer-N2Retransmissions	OBJECT-TYPE
	SYNTAX	INTEGER
	ACCESS	read-write
	STATUS	mandatory
	DESCRIPTION	"Number of retransmissions allowed. Defaults to 10."
	::= { mibanswerProfileEntry 65 }

    answerProfile-X75Answer-T1RetranTimer	OBJECT-TYPE
	SYNTAX	INTEGER
	ACCESS	read-write
	STATUS	mandatory
	DESCRIPTION	"Number of milliseconds between retransmissions. Defaults to 1000."
	::= { mibanswerProfileEntry 66 }

    answerProfile-X75Answer-FrameLength	OBJECT-TYPE
	SYNTAX	INTEGER
	ACCESS	read-write
	STATUS	mandatory
	DESCRIPTION	"Frame length to use for incoming X.75 connections. Defaults to 1024."
	::= { mibanswerProfileEntry 67 }

    answerProfile-FramedOnly	OBJECT-TYPE
	SYNTAX	INTEGER {
		    no (1),
		    yes (2)
		}
	ACCESS	read-write
	STATUS	mandatory
	DESCRIPTION	"A profile can be restricted to only doing the framed commands (ppp, mpp, slip, and quit) by setting this to YES"
	::= { mibanswerProfileEntry 68 }

    answerProfile-HdlcNrmAnswer-Enabled	OBJECT-TYPE
	SYNTAX	INTEGER {
		    no (1),
		    yes (2)
		}
	ACCESS	read-write
	STATUS	mandatory
	DESCRIPTION	"Set to yes to enable incoming HDLC-NRM calls."
	::= { mibanswerProfileEntry 71 }

    answerProfile-Visa2Answer-Enabled	OBJECT-TYPE
	SYNTAX	INTEGER {
		    no (1),
		    yes (2)
		}
	ACCESS	read-write
	STATUS	mandatory
	DESCRIPTION	"Set to yes to enable incoming VISA2 calls."
	::= { mibanswerProfileEntry 72 }

    answerProfile-AtmAnswer-SvcEnabled	OBJECT-TYPE
	SYNTAX	INTEGER {
		    no (1),
		    yes (2)
		}
	ACCESS	read-write
	STATUS	mandatory
	DESCRIPTION	"Set to yes to enable ATM SVC athentication on incoming calls."
	::= { mibanswerProfileEntry 78 }

    answerProfile-PriorityAnswer-Enabled	OBJECT-TYPE
	SYNTAX	INTEGER {
		    no (1),
		    yes (2)
		}
	ACCESS	read-write
	STATUS	mandatory
	DESCRIPTION	"Enable priority classification."
	::= { mibanswerProfileEntry 95 }

    answerProfile-PriorityAnswer-PacketClassification	OBJECT-TYPE
	SYNTAX	INTEGER {
		    qosTag (2),
		    udpPortRange (3)
		}
	ACCESS	read-write
	STATUS	mandatory
	DESCRIPTION	"Method used to classify PPP packets."
	::= { mibanswerProfileEntry 87 }

    answerProfile-PriorityAnswer-MaxRtpPacketDelay	OBJECT-TYPE
	SYNTAX	INTEGER
	ACCESS	read-write
	STATUS	mandatory
	DESCRIPTION	"Maximum delay for RTP packets in milli-seconds. Used for calculating the fragment size for the non-rtp traffic using the same link."
	::= { mibanswerProfileEntry 88 }

    answerProfile-PriorityAnswer-MinimumRtpPort	OBJECT-TYPE
	SYNTAX	INTEGER
	ACCESS	read-write
	STATUS	mandatory
	DESCRIPTION	"Minimum UDP port for prioritization"
	::= { mibanswerProfileEntry 89 }

    answerProfile-PriorityAnswer-MaximumRtpPort	OBJECT-TYPE
	SYNTAX	INTEGER
	ACCESS	read-write
	STATUS	mandatory
	DESCRIPTION	"Maximum UDP port for prioritization"
	::= { mibanswerProfileEntry 90 }

    answerProfile-PriorityAnswer-NoHighPrioPktDuration	OBJECT-TYPE
	SYNTAX	INTEGER
	ACCESS	read-write
	STATUS	mandatory
	DESCRIPTION	"The number of seconds of no high priority packets before disabling IP fragmentation of low priority packets. The value 0 disables checking duration of no high priority packet."
	::= { mibanswerProfileEntry 91 }

    answerProfile-Action-o	OBJECT-TYPE
	SYNTAX	INTEGER {
		    noAction (1),
		    createProfile (2),
		    deleteProfile (3)
		}
	ACCESS	read-write
	STATUS	mandatory
	DESCRIPTION	""
	::= { mibanswerProfileEntry 69 }

END
