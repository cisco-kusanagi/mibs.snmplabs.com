UMSHEALTH-MIB DEFINITIONS ::= BEGIN

IMPORTS
   OBJECT-TYPE
      FROM RFC-1212

   TRAP-TYPE
      FROM RFC-1215

   ibmpsgHealth,
   umservices, ibmpsg, ibmpsgEvent, win32, win32Event,
   Boolean, Uint8, Sint8, Uint16, Sint16, Uint32,
   Sint32, Uint64, Sint64, Real32, Real64, String, Datetime
      FROM UMS-MIB;


iBMPSGUMSComponentHealthTable OBJECT-TYPE
   SYNTAX         SEQUENCE OF IBMPSGUMSComponentHealthEntry
   ACCESS         not-accessible
   STATUS         mandatory
   DESCRIPTION    ""
   REFERENCE      "IBMPSG_UMSComponentHealth"
::= { ibmpsgHealth 3 }

iBMPSGUMSComponentHealthEntry OBJECT-TYPE
   SYNTAX         IBMPSGUMSComponentHealthEntry
   ACCESS         not-accessible
   STATUS         mandatory
   DESCRIPTION    ""
   INDEX          { iBMPSGUMSComponentHealthKeyIndex }
::= { iBMPSGUMSComponentHealthTable 1 }

IBMPSGUMSComponentHealthEntry ::= SEQUENCE
{
   iBMPSGUMSComponentHealthKeyIndex String,
   iBMPSGUMSComponentHealthCurrentState Uint16,
   iBMPSGUMSComponentHealthLastState Uint16,
   iBMPSGUMSComponentHealthDateTime Datetime,
   iBMPSGUMSComponentHealthLastUpdate Datetime,
   iBMPSGUMSComponentHealthDescription String,
   iBMPSGUMSComponentHealthEventCategory String,
   iBMPSGUMSComponentHealthResolution String,
   iBMPSGUMSComponentHealthSourceObjectPath String,
   iBMPSGUMSComponentHealthTargetObjectPath String,
   iBMPSGUMSComponentHealthStatus String
}

iBMPSGUMSComponentHealthKeyIndex OBJECT-TYPE
   SYNTAX         String
   ACCESS         read-only
   STATUS         mandatory
   DESCRIPTION    ""
   REFERENCE      "IBMPSG_UMSComponentHealth.KeyIndex"
::= { iBMPSGUMSComponentHealthEntry 1 }

iBMPSGUMSComponentHealthCurrentState OBJECT-TYPE
   SYNTAX         Uint16
   ACCESS         read-only
   STATUS         mandatory
   DESCRIPTION    ""
   REFERENCE      "IBMPSG_UMSComponentHealth.CurrentState"
::= { iBMPSGUMSComponentHealthEntry 2 }

iBMPSGUMSComponentHealthLastState OBJECT-TYPE
   SYNTAX         Uint16
   ACCESS         read-only
   STATUS         mandatory
   DESCRIPTION    ""
   REFERENCE      "IBMPSG_UMSComponentHealth.LastState"
::= { iBMPSGUMSComponentHealthEntry 3 }

iBMPSGUMSComponentHealthDateTime OBJECT-TYPE
   SYNTAX         Datetime
   ACCESS         read-write
   STATUS         mandatory
   DESCRIPTION    ""
   REFERENCE      "IBMPSG_UMSComponentHealth.DateTime"
::= { iBMPSGUMSComponentHealthEntry 4 }

iBMPSGUMSComponentHealthLastUpdate OBJECT-TYPE
   SYNTAX         Datetime
   ACCESS         read-write
   STATUS         mandatory
   DESCRIPTION    ""
   REFERENCE      "IBMPSG_UMSComponentHealth.LastUpdate"
::= { iBMPSGUMSComponentHealthEntry 5 }

iBMPSGUMSComponentHealthDescription OBJECT-TYPE
   SYNTAX         String
   ACCESS         read-write
   STATUS         mandatory
   DESCRIPTION    ""
   REFERENCE      "IBMPSG_UMSComponentHealth.Description"
::= { iBMPSGUMSComponentHealthEntry 6 }

iBMPSGUMSComponentHealthEventCategory OBJECT-TYPE
   SYNTAX         String
   ACCESS         read-write
   STATUS         mandatory
   DESCRIPTION    ""
   REFERENCE      "IBMPSG_UMSComponentHealth.EventCategory"
::= { iBMPSGUMSComponentHealthEntry 7 }

iBMPSGUMSComponentHealthResolution OBJECT-TYPE
   SYNTAX         String
   ACCESS         read-write
   STATUS         mandatory
   DESCRIPTION    ""
   REFERENCE      "IBMPSG_UMSComponentHealth.Resolution"
::= { iBMPSGUMSComponentHealthEntry 8 }

iBMPSGUMSComponentHealthSourceObjectPath OBJECT-TYPE
   SYNTAX         String
   ACCESS         read-write
   STATUS         mandatory
   DESCRIPTION    ""
   REFERENCE      "IBMPSG_UMSComponentHealth.SourceObjectPath"
::= { iBMPSGUMSComponentHealthEntry 9 }

iBMPSGUMSComponentHealthTargetObjectPath OBJECT-TYPE
   SYNTAX         String
   ACCESS         read-write
   STATUS         mandatory
   DESCRIPTION    ""
   REFERENCE      "IBMPSG_UMSComponentHealth.TargetObjectPath"
::= { iBMPSGUMSComponentHealthEntry 10 }

iBMPSGUMSComponentHealthStatus OBJECT-TYPE
   SYNTAX         String
   ACCESS         read-write
   STATUS         mandatory
   DESCRIPTION    ""
   REFERENCE      "IBMPSG_UMSComponentHealth.Status"
::= { iBMPSGUMSComponentHealthEntry 11 }

END
