--			Ascend mibbrite MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBBRITE-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibbRINetworkProfile  OBJECT IDENTIFIER ::= { configuration 63}

	-- The mibbRINetworkProfile table
	--
	-- This table contains parameters for the mibbRINetworkProfile profile
	--

    mibbRINetworkProfileTable	OBJECT-TYPE
	SYNTAX		SEQUENCE OF MibbRINetworkProfileEntry
	ACCESS		not-accessible
	STATUS		mandatory
	DESCRIPTION	"A list of mibbRINetworkProfile profile entries."
	::= { mibbRINetworkProfile 1 }

    mibbRINetworkProfileEntry	OBJECT-TYPE
	SYNTAX		MibbRINetworkProfileEntry
	ACCESS		not-accessible
	STATUS		mandatory
	DESCRIPTION	"A mibbRINetworkProfile entry containing objects that
			 maps to the parameters of mibbRINetworkProfile profile."
	INDEX		{ bRINetworkProfile-Shelf-o, bRINetworkProfile-Slot-o, bRINetworkProfile-Item-o }
	::= { mibbRINetworkProfileTable 1 }

    MibbRINetworkProfileEntry ::=
	SEQUENCE {
	    bRINetworkProfile-Shelf-o
		INTEGER,
	    bRINetworkProfile-Slot-o
		INTEGER,
	    bRINetworkProfile-Item-o
		INTEGER,
	    bRINetworkProfile-ProfileNumber
		INTEGER,
	    bRINetworkProfile-Name
		DisplayString,
	    bRINetworkProfile-PhysicalAddress-Shelf
		INTEGER,
	    bRINetworkProfile-PhysicalAddress-Slot
		INTEGER,
	    bRINetworkProfile-PhysicalAddress-ItemNumber
		INTEGER,
	    bRINetworkProfile-SwitchType
		INTEGER,
	    bRINetworkProfile-AnsVoiceCall
		INTEGER,
	    bRINetworkProfile-ConcatNailedLines
		INTEGER,
	    bRINetworkProfile-BriAnalogEncode
		INTEGER,
	    bRINetworkProfile-Action-o
		INTEGER
	}

    bRINetworkProfile-Shelf-o	OBJECT-TYPE
	SYNTAX	INTEGER
	ACCESS	read-only
	STATUS	mandatory
	DESCRIPTION	""
	::= { mibbRINetworkProfileEntry 1 }

    bRINetworkProfile-Slot-o	OBJECT-TYPE
	SYNTAX	INTEGER
	ACCESS	read-only
	STATUS	mandatory
	DESCRIPTION	""
	::= { mibbRINetworkProfileEntry 2 }

    bRINetworkProfile-Item-o	OBJECT-TYPE
	SYNTAX	INTEGER
	ACCESS	read-only
	STATUS	mandatory
	DESCRIPTION	""
	::= { mibbRINetworkProfileEntry 3 }

    bRINetworkProfile-ProfileNumber	OBJECT-TYPE
	SYNTAX	INTEGER
	ACCESS	read-write
	STATUS	mandatory
	DESCRIPTION	"If it is a stored profile, the number of the profile (1..MAX_NETWORK_PROFILES). If it is the current profile, the number of the stored profile from which it was loaded, or zero if it has never been loaded."
	::= { mibbRINetworkProfileEntry 4 }

    bRINetworkProfile-Name	OBJECT-TYPE
	SYNTAX	DisplayString
	ACCESS	read-write
	STATUS	mandatory
	DESCRIPTION	"The null terminated ascii string that the user gave to this particular profile."
	::= { mibbRINetworkProfileEntry 5 }

    bRINetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibbRINetworkProfileEntry 6 }

    bRINetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibbRINetworkProfileEntry 7 }

    bRINetworkProfile-PhysicalAddress-ItemNumber	OBJECT-TYPE
	SYNTAX	INTEGER
	ACCESS	read-write
	STATUS	mandatory
	DESCRIPTION	"A number that specifies an addressable entity within the context of shelf and slot."
	::= { mibbRINetworkProfileEntry 8 }

    bRINetworkProfile-SwitchType	OBJECT-TYPE
	SYNTAX	INTEGER {
		    attPri (1),
		    ntiPri (2),
		    globandPri (3),
		    japanPri (4),
		    vn3Pri (5),
		    onetr6Pri (6),
		    net5Pri (7),
		    danishPri (8),
		    australPri (9),
		    natIsdn2Pri (10),
		    taiwanPri (31),
		    isdxDpnss (11),
		    islxDpnss (12),
		    mercuryDpnss (13),
		    dass2 (14),
		    btSs7 (32),
		    unknownBri (15),
		    att5essBri (16),
		    dms100Nt1Bri (17),
		    nisdn1Bri (18),
		    vn2Bri (19),
		    btnr191Bri (20),
		    net3Bri (21),
		    ptpNet3Bri (22),
		    kddBri (23),
		    belgianBri (24),
		    australBri (25),
		    swissBri (26),
		    german1tr6Bri (27),
		    dutch1tr6Bri (28),
		    switchCas (29),
		    idslPtpBri (30)
		}
	ACCESS	read-write
	STATUS	mandatory
	DESCRIPTION	"The physical CO switch that the BRI's come from."
	::= { mibbRINetworkProfileEntry 9 }

    bRINetworkProfile-AnsVoiceCall	OBJECT-TYPE
	SYNTAX	INTEGER {
		    no (1),
		    yes (2)
		}
	ACCESS	read-write
	STATUS	mandatory
	DESCRIPTION	"When setting this field to no. the pipeline will not answer Voice call even if the call is destinated for us"
	::= { mibbRINetworkProfileEntry 10 }

    bRINetworkProfile-ConcatNailedLines	OBJECT-TYPE
	SYNTAX	INTEGER {
		    no (1),
		    yes (2)
		}
	ACCESS	read-write
	STATUS	mandatory
	DESCRIPTION	"When setting this field to no, BRI leased lines are concatenated, when yes, the B channels are concatenated (SUPER128)"
	::= { mibbRINetworkProfileEntry 11 }

    bRINetworkProfile-BriAnalogEncode	OBJECT-TYPE
	SYNTAX	INTEGER {
		    switchType (1),
		    muLaw (2),
		    aLaw (3)
		}
	ACCESS	read-write
	STATUS	mandatory
	DESCRIPTION	"Sets the encoding standard for digitized analog data to either u-Law or A-Law for BRI. The Defaults is to encode according to BRI switchType, this option is to override."
	::= { mibbRINetworkProfileEntry 12 }

    bRINetworkProfile-Action-o	OBJECT-TYPE
	SYNTAX	INTEGER {
		    noAction (1),
		    createProfile (2),
		    deleteProfile (3)
		}
	ACCESS	read-write
	STATUS	mandatory
	DESCRIPTION	""
	::= { mibbRINetworkProfileEntry 13 }


	-- The mibbRINetworkProfile__line_interface table
	--
	-- This table contains parameters for the mibbRINetworkProfile__line_interface profile
	--

    mibbRINetworkProfile-LineInterfaceTable	OBJECT-TYPE
	SYNTAX		SEQUENCE OF MibbRINetworkProfile-LineInterfaceEntry
	ACCESS		not-accessible
	STATUS		mandatory
	DESCRIPTION	"A list of mibbRINetworkProfile__line_interface profile entries."
	::= { mibbRINetworkProfile 2 }

    mibbRINetworkProfile-LineInterfaceEntry	OBJECT-TYPE
	SYNTAX		MibbRINetworkProfile-LineInterfaceEntry
	ACCESS		not-accessible
	STATUS		mandatory
	DESCRIPTION	"A mibbRINetworkProfile__line_interface entry containing objects that
			 maps to the parameters of mibbRINetworkProfile__line_interface profile."
	INDEX		{ bRINetworkProfile-LineInterface-Shelf-o, bRINetworkProfile-LineInterface-Slot-o, bRINetworkProfile-LineInterface-Item-o, bRINetworkProfile-LineInterface-Index-o }
	::= { mibbRINetworkProfile-LineInterfaceTable 1 }

    MibbRINetworkProfile-LineInterfaceEntry ::=
	SEQUENCE {
	    bRINetworkProfile-LineInterface-Shelf-o
		INTEGER,
	    bRINetworkProfile-LineInterface-Slot-o
		INTEGER,
	    bRINetworkProfile-LineInterface-Item-o
		INTEGER,
	    bRINetworkProfile-LineInterface-Index-o
		INTEGER,
	    bRINetworkProfile-LineInterface-Enabled
		INTEGER,
	    bRINetworkProfile-LineInterface-AnswerNumber1
		DisplayString,
	    bRINetworkProfile-LineInterface-AnswerNumber2
		DisplayString,
	    bRINetworkProfile-LineInterface-ClockSource
		INTEGER,
	    bRINetworkProfile-LineInterface-IdslBandwidth
		INTEGER,
	    bRINetworkProfile-LineInterface-Gr303Crv
		INTEGER,
	    bRINetworkProfile-LineInterface-Gr303InterfaceGroup
		INTEGER,
	    bRINetworkProfile-LineInterface-IgnoreLineup
		INTEGER
	}

    bRINetworkProfile-LineInterface-Shelf-o	OBJECT-TYPE
	SYNTAX	INTEGER
	ACCESS	read-only
	STATUS	mandatory
	DESCRIPTION	""
	::= { mibbRINetworkProfile-LineInterfaceEntry 1 }

    bRINetworkProfile-LineInterface-Slot-o	OBJECT-TYPE
	SYNTAX	INTEGER
	ACCESS	read-only
	STATUS	mandatory
	DESCRIPTION	""
	::= { mibbRINetworkProfile-LineInterfaceEntry 2 }

    bRINetworkProfile-LineInterface-Item-o	OBJECT-TYPE
	SYNTAX	INTEGER
	ACCESS	read-only
	STATUS	mandatory
	DESCRIPTION	""
	::= { mibbRINetworkProfile-LineInterfaceEntry 3 }

    bRINetworkProfile-LineInterface-Index-o	OBJECT-TYPE
	SYNTAX	INTEGER
	ACCESS	read-only
	STATUS	mandatory
	DESCRIPTION	""
	::= { mibbRINetworkProfile-LineInterfaceEntry 4 }

    bRINetworkProfile-LineInterface-Enabled	OBJECT-TYPE
	SYNTAX	INTEGER {
		    no (1),
		    yes (2)
		}
	ACCESS	read-write
	STATUS	mandatory
	DESCRIPTION	"Boolean that is TRUE if this interface is part of the set used for this network set, or FALSE otherwise."
	::= { mibbRINetworkProfile-LineInterfaceEntry 5 }

    bRINetworkProfile-LineInterface-AnswerNumber1	OBJECT-TYPE
	SYNTAX	DisplayString
	ACCESS	read-write
	STATUS	mandatory
	DESCRIPTION	"Phone numbers to match when routing by incoming phone number."
	::= { mibbRINetworkProfile-LineInterfaceEntry 6 }

    bRINetworkProfile-LineInterface-AnswerNumber2	OBJECT-TYPE
	SYNTAX	DisplayString
	ACCESS	read-write
	STATUS	mandatory
	DESCRIPTION	"Phone numbers to match when routing by incoming phone number."
	::= { mibbRINetworkProfile-LineInterfaceEntry 7 }

    bRINetworkProfile-LineInterface-ClockSource	OBJECT-TYPE
	SYNTAX	INTEGER {
		    eligible (1),
		    notEligible (2)
		}
	ACCESS	read-write
	STATUS	mandatory
	DESCRIPTION	"Boolean that is TRUE if this interface can be used as the netclock source."
	::= { mibbRINetworkProfile-LineInterfaceEntry 8 }

    bRINetworkProfile-LineInterface-IdslBandwidth	OBJECT-TYPE
	SYNTAX	INTEGER {
		    idsl128 (1),
		    idsl144 (2)
		}
	ACCESS	read-write
	STATUS	mandatory
	DESCRIPTION	"Configure IDSL subscriber bandwidth available."
	::= { mibbRINetworkProfile-LineInterfaceEntry 9 }

    bRINetworkProfile-LineInterface-Gr303Crv	OBJECT-TYPE
	SYNTAX	INTEGER
	ACCESS	read-write
	STATUS	mandatory
	DESCRIPTION	"GR-303 CRV associated with this line"
	::= { mibbRINetworkProfile-LineInterfaceEntry 10 }

    bRINetworkProfile-LineInterface-Gr303InterfaceGroup	OBJECT-TYPE
	SYNTAX	INTEGER
	ACCESS	read-write
	STATUS	mandatory
	DESCRIPTION	"GR-303 interface group associated with this line"
	::= { mibbRINetworkProfile-LineInterfaceEntry 11 }

    bRINetworkProfile-LineInterface-IgnoreLineup	OBJECT-TYPE
	SYNTAX	INTEGER {
		    systemDefined (1),
		    no (2),
		    yes (3)
		}
	ACCESS	read-write
	STATUS	mandatory
	DESCRIPTION	"Ignore line up value for this port."
	::= { mibbRINetworkProfile-LineInterfaceEntry 12 }


	-- The mibbRINetworkProfile__line_interface__channel_config table
	--
	-- This table contains parameters for the mibbRINetworkProfile__line_interface__channel_config profile
	--

    mibbRINetworkProfile-LineInterface-ChannelConfigTable	OBJECT-TYPE
	SYNTAX		SEQUENCE OF MibbRINetworkProfile-LineInterface-ChannelConfigEntry
	ACCESS		not-accessible
	STATUS		mandatory
	DESCRIPTION	"A list of mibbRINetworkProfile__line_interface__channel_config profile entries."
	::= { mibbRINetworkProfile 3 }

    mibbRINetworkProfile-LineInterface-ChannelConfigEntry	OBJECT-TYPE
	SYNTAX		MibbRINetworkProfile-LineInterface-ChannelConfigEntry
	ACCESS		not-accessible
	STATUS		mandatory
	DESCRIPTION	"A mibbRINetworkProfile__line_interface__channel_config entry containing objects that
			 maps to the parameters of mibbRINetworkProfile__line_interface__channel_config profile."
	INDEX		{ bRINetworkProfile-LineInterface-ChannelConfig-Shelf-o, bRINetworkProfile-LineInterface-ChannelConfig-Slot-o, bRINetworkProfile-LineInterface-ChannelConfig-Item-o, bRINetworkProfile-LineInterface-ChannelConfig-Index-o, bRINetworkProfile-LineInterface-ChannelConfig-Index1-o }
	::= { mibbRINetworkProfile-LineInterface-ChannelConfigTable 1 }

    MibbRINetworkProfile-LineInterface-ChannelConfigEntry ::=
	SEQUENCE {
	    bRINetworkProfile-LineInterface-ChannelConfig-Shelf-o
		INTEGER,
	    bRINetworkProfile-LineInterface-ChannelConfig-Slot-o
		INTEGER,
	    bRINetworkProfile-LineInterface-ChannelConfig-Item-o
		INTEGER,
	    bRINetworkProfile-LineInterface-ChannelConfig-Index-o
		INTEGER,
	    bRINetworkProfile-LineInterface-ChannelConfig-Index1-o
		INTEGER,
	    bRINetworkProfile-LineInterface-ChannelConfig-ChannelUsage
		INTEGER,
	    bRINetworkProfile-LineInterface-ChannelConfig-NailedGroup
		INTEGER
	}

    bRINetworkProfile-LineInterface-ChannelConfig-Shelf-o	OBJECT-TYPE
	SYNTAX	INTEGER
	ACCESS	read-only
	STATUS	mandatory
	DESCRIPTION	""
	::= { mibbRINetworkProfile-LineInterface-ChannelConfigEntry 1 }

    bRINetworkProfile-LineInterface-ChannelConfig-Slot-o	OBJECT-TYPE
	SYNTAX	INTEGER
	ACCESS	read-only
	STATUS	mandatory
	DESCRIPTION	""
	::= { mibbRINetworkProfile-LineInterface-ChannelConfigEntry 2 }

    bRINetworkProfile-LineInterface-ChannelConfig-Item-o	OBJECT-TYPE
	SYNTAX	INTEGER
	ACCESS	read-only
	STATUS	mandatory
	DESCRIPTION	""
	::= { mibbRINetworkProfile-LineInterface-ChannelConfigEntry 3 }

    bRINetworkProfile-LineInterface-ChannelConfig-Index-o	OBJECT-TYPE
	SYNTAX	INTEGER
	ACCESS	read-only
	STATUS	mandatory
	DESCRIPTION	""
	::= { mibbRINetworkProfile-LineInterface-ChannelConfigEntry 4 }

    bRINetworkProfile-LineInterface-ChannelConfig-Index1-o	OBJECT-TYPE
	SYNTAX	INTEGER
	ACCESS	read-only
	STATUS	mandatory
	DESCRIPTION	""
	::= { mibbRINetworkProfile-LineInterface-ChannelConfigEntry 5 }

    bRINetworkProfile-LineInterface-ChannelConfig-ChannelUsage	OBJECT-TYPE
	SYNTAX	INTEGER {
		    unusedChannel (1),
		    switchedChannel (2),
		    nailed64Channel (3),
		    dChannel (4),
		    nfasPrimaryDChannel (5),
		    nfasSecondaryDChannel (6),
		    semiPermChannel (7),
		    ss7SignalingChannel (8)
		}
	ACCESS	read-write
	STATUS	mandatory
	DESCRIPTION	"Usage of the b-channel."
	::= { mibbRINetworkProfile-LineInterface-ChannelConfigEntry 6 }

    bRINetworkProfile-LineInterface-ChannelConfig-NailedGroup	OBJECT-TYPE
	SYNTAX	INTEGER
	ACCESS	read-write
	STATUS	mandatory
	DESCRIPTION	"A number that identifies the set of channels that makes up a nailed group."
	::= { mibbRINetworkProfile-LineInterface-ChannelConfigEntry 7 }

END
