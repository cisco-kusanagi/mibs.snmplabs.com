-- *****************************************************************
-- ESC: Elastic Services Controller
--
-- Copyright (c) 2005-2006, 2017 by cisco Systems Inc.
-- All rights reserved.
--
-- *****************************************************************

CISCO-ESC-MIB DEFINITIONS ::= BEGIN

IMPORTS
    MODULE-IDENTITY,
    OBJECT-TYPE,
    NOTIFICATION-TYPE
        FROM SNMPv2-SMI
    MODULE-COMPLIANCE,
    NOTIFICATION-GROUP,
    OBJECT-GROUP
        FROM SNMPv2-CONF
    ciscoMgmt
        FROM CISCO-SMI;


ciscoEscMIB MODULE-IDENTITY
    LAST-UPDATED    "201705020000Z"
    ORGANIZATION    "Cisco Systems, Inc."
    CONTACT-INFO
            "Cisco Systems
            Customer Service

            Postal: 170 W Tasman Drive
            San Jose, CA  95134
            USA

            Tel: +1 800 553-NETS

            E-mail: miblib@cisco.com"
    DESCRIPTION
        "Objects relating to the Cisco Elastic Services Controller
        (ESC)"
    REVISION        "201703280000Z"
    DESCRIPTION
        "Latest version of this MIB module."
    ::= { ciscoMgmt 844 }


-- Textual Conventions definition will be defined before this line

escNotifs  OBJECT IDENTIFIER
    ::= { ciscoEscMIB 0 }

escMIBObjects  OBJECT IDENTIFIER
    ::= { ciscoEscMIB 1 }

ciscoEscMIBConform  OBJECT IDENTIFIER
    ::= { ciscoEscMIB 2 }

-- Objects relating to the VNF Manager

vnfm  OBJECT IDENTIFIER
    ::= { escMIBObjects 1 }


escStatusMessage OBJECT-TYPE
    SYNTAX          OCTET STRING
    MAX-ACCESS      read-only
    STATUS          current
    DESCRIPTION
        "ESC Status Message"
    ::= { vnfm 1 }

escStatusCode OBJECT-TYPE
    SYNTAX          OCTET STRING
    MAX-ACCESS      read-only
    STATUS          current
    DESCRIPTION
        "ESC Status Code"
    ::= { vnfm 2 }

-- Status Notification Type

escStatusNotif NOTIFICATION-TYPE
    OBJECTS         {
                        escStatusCode,
                        escStatusMessage
                    }
    STATUS          current
    DESCRIPTION
        "ESC Status Notification"
   ::= { escNotifs 1 }
ciscoEscMIBCompliances  OBJECT IDENTIFIER
    ::= { ciscoEscMIBConform 1 }

ciscoEscMIBGroups  OBJECT IDENTIFIER
    ::= { ciscoEscMIBConform 2 }


ciscoEscMIBCompliance MODULE-COMPLIANCE
    STATUS          current
    DESCRIPTION
        "This is a default module-compliance
        containing default object groups."
    MODULE          -- this module
    MANDATORY-GROUPS {
                        ciscoEscMIBObjectGroup,
                        ciscoEscMIBNotificationGroup
                    }
    ::= { ciscoEscMIBCompliances 1 }

-- Units of Conformance

ciscoEscMIBObjectGroup OBJECT-GROUP
    OBJECTS         {
                        escStatusCode,
                        escStatusMessage
                    }
    STATUS          current
    DESCRIPTION
        "The is a test group."
    ::= { ciscoEscMIBGroups 1 }

ciscoEscMIBNotificationGroup NOTIFICATION-GROUP
   NOTIFICATIONS    { escStatusNotif }
    STATUS          current
    DESCRIPTION
        "The is a test group."
    ::= { ciscoEscMIBGroups 2 }

END
