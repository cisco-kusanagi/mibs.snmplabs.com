BAS-TOPOLOGY-MIB DEFINITIONS ::= BEGIN

IMPORTS
    MODULE-IDENTITY, OBJECT-TYPE, Integer32, IpAddress  FROM SNMPv2-SMI
    IANAifType                                          FROM IANAifType-MIB
    InterfaceIndex, ifEntry                             FROM IF-MIB
    basTopology, BasChassisId, BasSlotId,
    BasInterfaceId, BasLogicalPortId, BasCardClass,
    BasIfClass, BasChassisType                          FROM BAS-MIB;

basTopologyMIB MODULE-IDENTITY
    LAST-UPDATED "9812010000Z"
    ORGANIZATION "Broadband Access Systems"
    CONTACT-INFO
        " Tech Support
          Broadband Access Systems
          201 Forest Street
          Marlboro, MA  01752
          U.S.A.
		  
          508-485-8200
          support@basystems.com"
    DESCRIPTION
        "The MIB module for defining Broadband Access System Cluster
         topology."
    ::= { basTopology 1 }

--*****************************************************************************
--* The BAS Chassis Topology Table
--*****************************************************************************

basChassisTopTable OBJECT-TYPE
    SYNTAX      SEQUENCE OF BasChassisTopEntry
    MAX-ACCESS  not-accessible
    STATUS      current
    DESCRIPTION
            "A table of chassis contained in a BAS cluster."
        ::= { basTopologyMIB 1 }

basChassisTopEntry OBJECT-TYPE
    SYNTAX      BasChassisTopEntry
    MAX-ACCESS  not-accessible
    STATUS      current
    DESCRIPTION
        ""
    INDEX { basChassisTopChassis, basChassisTopSlot,
            basChassisTopIf, basChassisTopLPort }
    ::= { basChassisTopTable 1 }

BasChassisTopEntry ::=
    SEQUENCE {
        basChassisTopChassis       BasChassisId,
        basChassisTopSlot          BasSlotId,
        basChassisTopIf            BasInterfaceId,
        basChassisTopLPort         BasLogicalPortId,
        basChassisTopChassisNumber Integer32,
        basChassisTopChassisType   BasChassisType,
        basChassisTopSlotInfo      OCTET STRING,
        basChassisTopStatus        INTEGER
    }

basChassisTopChassis OBJECT-TYPE
    SYNTAX      BasChassisId
    MAX-ACCESS  not-accessible
    STATUS      current
    DESCRIPTION
        "The chassis identifier of this chassis."
    ::= { basChassisTopEntry 1 }

basChassisTopSlot OBJECT-TYPE
    SYNTAX      BasSlotId
    MAX-ACCESS  not-accessible
    STATUS      current
    DESCRIPTION
        "The BAS slot ID of this card."
    ::= { basChassisTopEntry 2 }

basChassisTopIf OBJECT-TYPE
    SYNTAX      BasInterfaceId
    MAX-ACCESS  not-accessible
    STATUS      current
    DESCRIPTION
        "The BAS interface ID of this card."
    ::= { basChassisTopEntry 3 }

basChassisTopLPort OBJECT-TYPE
    SYNTAX      BasLogicalPortId
    MAX-ACCESS  not-accessible
    STATUS      current
    DESCRIPTION
        "The BAS logical port ID of this card."
    ::= { basChassisTopEntry 4 }

basChassisTopChassisNumber OBJECT-TYPE
    SYNTAX      Integer32
    MAX-ACCESS  read-only
    STATUS      current
    DESCRIPTION
        "The chassis number of this chassis."
    ::= { basChassisTopEntry 5 }

basChassisTopChassisType OBJECT-TYPE
    SYNTAX      BasChassisType
    MAX-ACCESS  read-only
    STATUS      current
    DESCRIPTION
        "The chassis type of this chassis."
    ::= { basChassisTopEntry 6 }

basChassisTopSlotInfo OBJECT-TYPE
    SYNTAX      OCTET STRING
    MAX-ACCESS  read-only
    STATUS      current
    DESCRIPTION
        "This object is used to identify the number of slots contained
        in a chassis, the type of card contained in populated slots, and
        if a populated slot contains at least one ICL link. The length
        of this OCTET STRING indicates the number of slots in the chassis.
        The encoding of each OCTET is defined below:

        bits 0-5  Card Type.
        bit 6	  If 1, slot contains at least one ICL link. If 0, slot
                  contains no ICL links.
        bit 7     Unused."
    ::= { basChassisTopEntry 7 }

basChassisTopStatus OBJECT-TYPE
    SYNTAX      INTEGER {
                        up(1),
                        down(2)
                }
    MAX-ACCESS  read-only
    STATUS      current
    DESCRIPTION
        "The current operational state of this chassis."
    ::= { basChassisTopEntry 8 }

--*****************************************************************************
--* The BAS Slot Topology Table
--*****************************************************************************

basSlotTopTable OBJECT-TYPE
    SYNTAX         SEQUENCE OF BasSlotTopEntry
    MAX-ACCESS     not-accessible
    STATUS         current
    DESCRIPTION
        "A table of slots contained in each chassis that make up
        a BAS cluster."
   ::= { basTopologyMIB 2 }

basSlotTopEntry OBJECT-TYPE
    SYNTAX         BasSlotTopEntry
    MAX-ACCESS     not-accessible
    STATUS         current
    DESCRIPTION
        ""
    INDEX          { basSlotTopChassis, basSlotTopSlot,
                     basSlotTopIf, basSlotTopLPort,
                     basSlotTopACChassis, basSlotTopACSlot,
                     basSlotTopACIf, basSlotTopACLPort }
    ::= {basSlotTopTable 1 }

BasSlotTopEntry ::= 
    SEQUENCE {
        basSlotTopChassis         BasChassisId,
        basSlotTopSlot            BasSlotId,
        basSlotTopIf              BasInterfaceId,
        basSlotTopLPort           BasLogicalPortId,
        basSlotTopACChassis       BasChassisId,
        basSlotTopACSlot          BasSlotId,
        basSlotTopACIf            BasInterfaceId,
        basSlotTopACLPort         BasLogicalPortId,
        basSlotTopNumberOfIfs     Integer32,
        basSlotTopIfInfo          OCTET STRING,
        basSlotTopCardType        BasCardClass,
        basSlotTopInterChassisIP  IpAddress,
        basSlotTopIntraChassisIP  IpAddress,
        basSlotTopStatus          INTEGER
    }

basSlotTopChassis OBJECT-TYPE
    SYNTAX      BasChassisId
    MAX-ACCESS  not-accessible
    STATUS      current
    DESCRIPTION
        "The BAS chassis ID of this card"
    ::= { basSlotTopEntry 1 }

basSlotTopSlot OBJECT-TYPE
    SYNTAX      BasSlotId
    MAX-ACCESS  not-accessible
    STATUS      current
    DESCRIPTION
        "The BAS slot ID of this card."
    ::= { basSlotTopEntry 2 }

basSlotTopIf OBJECT-TYPE
    SYNTAX      BasInterfaceId
    MAX-ACCESS  not-accessible
    STATUS      current
    DESCRIPTION
        "The BAS interface ID of this card."
    ::= { basSlotTopEntry 3 }

basSlotTopLPort OBJECT-TYPE
    SYNTAX      BasLogicalPortId
    MAX-ACCESS  not-accessible
    STATUS      current
    DESCRIPTION
        "The BAS logical port ID of this card."
    ::= { basSlotTopEntry 4 }

basSlotTopACChassis OBJECT-TYPE
    SYNTAX      BasChassisId
    MAX-ACCESS  not-accessible
    STATUS      current
    DESCRIPTION
        "The BAS chassis ID of the application card"
    ::= { basSlotTopEntry 5 }

basSlotTopACSlot OBJECT-TYPE
    SYNTAX      BasSlotId
    MAX-ACCESS  not-accessible
    STATUS      current
    DESCRIPTION
        "The BAS slot ID of the application card."
    ::= { basSlotTopEntry 6 }

basSlotTopACIf OBJECT-TYPE
    SYNTAX      BasInterfaceId
    MAX-ACCESS  not-accessible
    STATUS      current
    DESCRIPTION
        "The BAS interface ID of the application card."
    ::= { basSlotTopEntry 7 }

basSlotTopACLPort OBJECT-TYPE
    SYNTAX      BasLogicalPortId
    MAX-ACCESS  not-accessible
    STATUS      current
    DESCRIPTION
        "The BAS logical port ID of the application card."
    ::= { basSlotTopEntry 8 }

basSlotTopNumberOfIfs OBJECT-TYPE
    SYNTAX      Integer32
    MAX-ACCESS  read-only
    STATUS      current
    DESCRIPTION
        "The total number of physical interface on this slot."
    ::= { basSlotTopEntry 9 }

basSlotTopIfInfo OBJECT-TYPE
    SYNTAX      OCTET STRING
    MAX-ACCESS  read-only
    STATUS      current
    DESCRIPTION
        "This object is used to identify which interfaces in the slot are
        an ICL interface as well as the type of ICL the interface
        represents. This object also identifies each end of the ICL. The
        encoding of this object is defined below.

        Each interface is encoded as a 3-tuple. The 3-tuple is defined as
        follows, <Type of ICL, Local ifIndex, Remote ifIndex>, where 'Type
        of ICL' in one byte, 'Local ifIndex' is four bytes, and 'Remote
        ifIndex' is four bytes. There will be 'Number of Interfaces'
        3-tuples contained in this OCTET STRING.

        The values for each element which make up the 3-tuple can be as
        follows:

        'Type of ICL'    0 indicates this is not an ICL
                         1 indicates active ICL
                         2 indicates redundant ICL
        'Local ifIndex'  0 if 'Type of ICL' is 0
                         > 0 if 'Type of ICL' is not 0
        'Remote ifIndex' 0 if 'Type of ICL' is 0
                         > 0 if 'Type of ICL' is not 0"
    ::= { basSlotTopEntry 10 }

basSlotTopCardType OBJECT-TYPE
    SYNTAX      BasCardClass
    MAX-ACCESS  read-only
    STATUS      current
    DESCRIPTION
        "The BAS card class of this slot."
    ::= { basSlotTopEntry 11 }

basSlotTopInterChassisIP OBJECT-TYPE
    SYNTAX      IpAddress
    MAX-ACCESS  read-only
    STATUS      current
    DESCRIPTION
        "The IP address of the ."
    ::= { basSlotTopEntry 12 }

basSlotTopIntraChassisIP OBJECT-TYPE
    SYNTAX      IpAddress
    MAX-ACCESS  read-only
    STATUS      current
    DESCRIPTION
        "The IP address of the ."
    ::= { basSlotTopEntry 13 }

basSlotTopStatus OBJECT-TYPE
    SYNTAX      INTEGER {
                        up(1),
                        down(2)
                }
    MAX-ACCESS  read-only
    STATUS      current
    DESCRIPTION
        "The current operational state of this slot."
    ::= { basSlotTopEntry 14 }

--*****************************************************************************
--* The BAS Interface Topology Table
--*****************************************************************************

basIfTopTable OBJECT-TYPE
    SYNTAX      SEQUENCE OF BasIfTopEntry
    MAX-ACCESS  not-accessible
    STATUS      current
    DESCRIPTION
        "A table of interfaces on each slot contained in each chassis
        that make up a BAS cluster."
    ::= { basTopologyMIB 3 }

basIfTopEntry OBJECT-TYPE
    SYNTAX      BasIfTopEntry
    MAX-ACCESS  not-accessible
    STATUS      current
    DESCRIPTION
      ""
    AUGMENTS    { ifEntry }
    ::= {basIfTopTable 1 }

BasIfTopEntry ::= 
    SEQUENCE {
        basIfTopIfClass           BasIfClass,
        basIfTopIfType            IANAifType,
        basIfTopICLNeighbor       InterfaceIndex,
        basIfTopICLMode           INTEGER,
        basIfTopIfStatus          INTEGER
    }

basIfTopIfClass OBJECT-TYPE
    SYNTAX      BasIfClass
    MAX-ACCESS  read-only
    STATUS      current
    DESCRIPTION
        "The BAS defined class of this interface."
    ::= { basIfTopEntry 1 }

basIfTopIfType OBJECT-TYPE
    SYNTAX      IANAifType
    MAX-ACCESS  read-only
    STATUS      current
    DESCRIPTION
        "This is a mirror of ifType defined in the IF-MIB."
    ::= { basIfTopEntry 3 }

basIfTopICLNeighbor OBJECT-TYPE
    SYNTAX      InterfaceIndex
    MAX-ACCESS  read-only
    STATUS      current
    DESCRIPTION
        "If the value of basIfTopIfClass is icl(1), then this
        object will identify the ifIndex of the interface at the
        far side of the link. Otherwise, the value of this object
        is zero(0)."
    ::= { basIfTopEntry 4 }

basIfTopICLMode OBJECT-TYPE
    SYNTAX      INTEGER {
                        active(1),
                        redundant(2),
			other(3)
                }
    MAX-ACCESS  read-only
    STATUS      current
    DESCRIPTION
        "If the value of basIfTopIfClass is icl(1), then this
        object indicates whether this ICL is acting in an active(1)
        or redundant(2) mode."
    ::= { basIfTopEntry 5 }

basIfTopIfStatus OBJECT-TYPE
    SYNTAX      INTEGER {
                        up(1),
                        down(2)
                }
    MAX-ACCESS  read-only
    STATUS      current
    DESCRIPTION
        "The operational state of this interface."
    ::= { basIfTopEntry 6 }

--*****************************************************************************
--* The BAS Route Server Table
--*****************************************************************************

basRSTable OBJECT-TYPE
    SYNTAX      SEQUENCE OF BasRSEntry
    MAX-ACCESS  not-accessible
    STATUS      current
    DESCRIPTION
        "A table specifying a list of Route Servers in a BAS cluster."
    ::= { basTopologyMIB 4 }

basRSEntry OBJECT-TYPE
    SYNTAX      BasRSEntry
    MAX-ACCESS  not-accessible
    STATUS      current
    DESCRIPTION
        "Card specific Route Server information entry."
    INDEX { basRSMgrChassis, basRSMgrSlot, basRSMgrIf, basRSMgrLPort,
            basRSChassis, basRSSlot, basRSIf, basRSLPort }
    ::= { basRSTable 1 }

BasRSEntry ::=
    SEQUENCE {
        basRSMgrChassis         BasChassisId,
        basRSMgrSlot            BasSlotId,
        basRSMgrIf              BasInterfaceId,
        basRSMgrLPort           BasLogicalPortId,
        basRSChassis            BasChassisId,
        basRSSlot               BasSlotId,
        basRSIf                 BasInterfaceId,
        basRSLPort              BasLogicalPortId,
        basRSRole               INTEGER
    }

basRSMgrChassis OBJECT-TYPE
    SYNTAX      BasChassisId
    MAX-ACCESS  not-accessible
    STATUS      current
    DESCRIPTION
        "The BAS Chassis ID of this card."
    ::= { basRSEntry 1 }

basRSMgrSlot OBJECT-TYPE
    SYNTAX      BasSlotId
    MAX-ACCESS  not-accessible
    STATUS      current
    DESCRIPTION
        "The BAS Slot ID of this card."
    ::= { basRSEntry 2 }

basRSMgrIf OBJECT-TYPE
    SYNTAX      BasInterfaceId
    MAX-ACCESS  not-accessible
    STATUS      current
    DESCRIPTION
        "The BAS interface ID of this card."
    ::= { basRSEntry 3 }

basRSMgrLPort OBJECT-TYPE
    SYNTAX      BasLogicalPortId
    MAX-ACCESS  not-accessible
    STATUS      current
    DESCRIPTION
        "The BAS logical port ID of this card."
    ::= { basRSEntry 4 }

basRSChassis OBJECT-TYPE
    SYNTAX      BasChassisId
    MAX-ACCESS  read-only
    STATUS      current
    DESCRIPTION
        "The BAS Chassis ID of a Route Server known by this card."
    ::= { basRSEntry 5 }

basRSSlot OBJECT-TYPE
    SYNTAX      BasSlotId
    MAX-ACCESS  read-only
    STATUS      current
    DESCRIPTION
        "The BAS Slot ID of a Route Server known by this card."
    ::= { basRSEntry 6 }

basRSIf OBJECT-TYPE
    SYNTAX      BasInterfaceId
    MAX-ACCESS  read-only
    STATUS      current
    DESCRIPTION
        "The BAS interface ID of a Route Server known by this card."
    ::= { basRSEntry 7 }

basRSLPort OBJECT-TYPE
    SYNTAX      BasLogicalPortId
    MAX-ACCESS  read-only
    STATUS      current
    DESCRIPTION
        "The BAS logical port ID of a Route Server known by this card."
    ::= { basRSEntry 8 }

basRSRole OBJECT-TYPE
    SYNTAX      INTEGER {
                        primary(1),
                        secondary(2)
                }
    MAX-ACCESS  read-only
    STATUS      current
    DESCRIPTION
        "This object is used to indicate the role the Route Server
        plays within a BAS cluster."
    ::= { basRSEntry 9 }

END
