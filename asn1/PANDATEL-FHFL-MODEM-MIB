PANDATEL-FHFL-MODEM-MIB DEFINITIONS ::= BEGIN

 -- This is the private mib group section for the FH/FL modems.
 -- Because these modems must be installed in the PANDATEL modem rack
 -- the PANDATEL-MODEM-MIB also applies.

 -- Ver.1.06    Sep.13.1999

        IMPORTS
                enterprises
                        FROM RFC1155-SMI
                DisplayString
                        FROM RFC1213-MIB
                OBJECT-TYPE
                        FROM RFC-1212
                mdmSpecifics, device-id
                        FROM PANDATEL-MODEM-MIB;

-- ********************** THE MDM-FHFL SUBTREE ******************************

-- the specific identifier is identical to the modem type integer
-- of the FH/FL modem entries in the PANDATEL-MODEM-MIB mdmModemTable.

fhfl-modem      OBJECT IDENTIFIER ::= { device-id 101 }     -- chassis-mib

fhfl            OBJECT IDENTIFIER ::= { mdmSpecifics 101 }  -- this subtree

fhflModemTable OBJECT-TYPE
        SYNTAX  SEQUENCE OF FhflTableEntry
        ACCESS  not-accessible
        STATUS  mandatory
        DESCRIPTION
                "Table of all FH/FL modems in all racks."
        ::= { fhfl 1 }

fhflTableEntry OBJECT-TYPE
        SYNTAX  FhflTableEntry
        ACCESS  not-accessible
        STATUS  mandatory
        DESCRIPTION
                "The index of the table."
        INDEX   { mdmRack, mdmModem, mdmPosition }
        ::= { fhflModemTable 1 }

FhflTableEntry ::= SEQUENCE {
        mdmRack
                INTEGER,
        mdmModem
                INTEGER,
        mdmPosition
                INTEGER,
        mdmModemName
                DisplayString,
        mdmInterfaceEmulationMode
                INTEGER,
        mdmModemProperty
                INTEGER,
        mdmClockSystem
                INTEGER,
        mdmClockSource
                INTEGER,
        mdmDataRate
                INTEGER,
        mdmLocalCarrierDetect
                INTEGER
        }

mdmRack OBJECT-TYPE
        SYNTAX  INTEGER
        ACCESS  read-only
        STATUS  mandatory
        DESCRIPTION
                "The index of the rack where the modem is installed."
        ::= { fhflTableEntry 1 }

mdmModem OBJECT-TYPE
        SYNTAX  INTEGER
        ACCESS  read-only
        STATUS  mandatory
        DESCRIPTION
                "This variable displays the slot number where the
                 corresponding modem is installed in the rack."
        ::= { fhflTableEntry 2 }

mdmPosition OBJECT-TYPE
        SYNTAX  INTEGER {
                local       (1),
                remote      (2)
                }
        ACCESS  read-only
        STATUS  mandatory
        DESCRIPTION
                "This variable displays the location of the corresponding
                 modem: 'local' or 'remote'.
                 The modem which is plugged into a managed rack is 'local',
                 the counterpart is 'remote'."
        ::= { fhflTableEntry 3 }

mdmModemName OBJECT-TYPE
        SYNTAX  DisplayString
        ACCESS  read-only
        STATUS  mandatory
        DESCRIPTION
                "The verbal name of this modem."
        ::= { fhflTableEntry 5 }

mdmInterfaceEmulationMode OBJECT-TYPE
        SYNTAX  INTEGER {
                other       (1),
                dte         (2),
                dce         (3),
                te          (4),
                nt          (5),
                unknown     (99)
        }
        ACCESS  read-only
        STATUS  mandatory
        DESCRIPTION
                "Interface mode of the unit: 'dte', 'dce', 'te', or 'nt'."
        ::= { fhflTableEntry 6 }

mdmModemProperty OBJECT-TYPE
        SYNTAX  INTEGER {
                other                   (1),
                e1                      (2),
                t1                      (3),
                e2                      (4),
                t2                      (5),
                e1-t1                   (6),
                e2-t2                   (7),
                e3                      (8),
                t3                      (9),
                hssi                    (10),
                atm                     (11),
                eth10base-t-fullduplex  (12),
                eth10base-t-halfduplex  (13),
                unknown                 (99)
        }
        ACCESS  read-only
        STATUS  mandatory
        DESCRIPTION
                "The speed class of the unit: 'e1' or 't1'."
        ::= { fhflTableEntry 7 }

mdmClockSystem OBJECT-TYPE
        SYNTAX  INTEGER {
                other       (1),
                dual        (2),
                single      (3)
        }
        ACCESS  read-write
        STATUS  mandatory
        DESCRIPTION
                "The clock system of the link: 'single' or 'dual'. The remote
                 unit's configuration changes simultaneously."
        ::= { fhflTableEntry 23 }

mdmClockSource OBJECT-TYPE
        SYNTAX  INTEGER {
                other       (1),
                internal    (2),
                remote      (3),
                external    (4)
        }
        ACCESS  read-write
        STATUS  mandatory
        DESCRIPTION
                "The clock source of the link: 'internal', 'remote'
                 or 'external'."
        ::= { fhflTableEntry 24 }

mdmDataRate OBJECT-TYPE
        SYNTAX  INTEGER {
                other       (1)
        }
        ACCESS  read-write
        STATUS  mandatory
        DESCRIPTION
                "The data rate at the interface in bits per seconds. The
                 data rate at the remote counterpart changes simultaneously."
        ::= { fhflTableEntry 25 }

mdmLocalCarrierDetect OBJECT-TYPE
        SYNTAX  INTEGER {
                other                           (1),
                fo-link-and-remote-handshake    (2),
                fo-link                         (3)
        }
        ACCESS  read-write
        STATUS  mandatory
        DESCRIPTION
                "The data carrier detect mode at the interface: if set to
                 'fo-link-and-remote-handshake' the DCD signal (resp. I for
                 X.21, etc.) follows link status and remote RTS (resp. C for
                 X.21, etc.), if set to 'fo-link' the DCD signal follows link
                 status only."
        ::= { fhflTableEntry 60 }

END
