-- *************************************************************************
--
--  MIB:     ERI-ROOT-SMI
--
--  Purpose: This is the Eastern Research Root MIB that defines 
--           the Enterprise branches for the ERI products.
--
--  Contact: Eastern Research Inc. 1-800-337-4374  Email: support@erinc.com
--
--  Revised: May 06, 2002 - Nevio Poljak
--           Initial Release
--
-- *************************************************************************

ERI-ROOT-SMI DEFINITIONS ::= BEGIN

IMPORTS
	enterprises 
		FROM RFC1155-SMI;

-- *************************************************************************
-- The DNX enterprise OID will be { iso(1) org(3) dod(6) internet(1) private(4)
--                                  enterprises(1) eriEnterpriseRoot(644) 
--                                  eriProducts(2) dnx(4) 
--                                }
-- *************************************************************************

eriEnterpriseRoot  OBJECT IDENTIFIER ::= { enterprises 644 }

virProducts        OBJECT IDENTIFIER ::= { eriEnterpriseRoot 1 }
eriProducts        OBJECT IDENTIFIER ::= { eriEnterpriseRoot 2 }
eriMibs            OBJECT IDENTIFIER ::= { eriEnterpriseRoot 3 }

-- csu1               OBJECT IDENTIFIER ::= { eriProducts 1 }
-- csu2               OBJECT IDENTIFIER ::= { eriProducts 2 }
-- spanet             OBJECT IDENTIFIER ::= { eriProducts 3 }
-- dnx                OBJECT IDENTIFIER ::= { eriProducts 4 }
-- nat-1              OBJECT IDENTIFIER ::= { eriProducts 5 }
  	
END

-- *************************************************************************
--
--  MIB:     ERI-DNX-SMC-MIB
--
--  Purpose: This is the Eastern Research System Manager Card (SMC) 
--           MIB for the DNX product. This supports System-level
--           diagnostics and configuration via SNMP.
--
--  Contact: Eastern Research Inc. 1-800-337-4374  Email: support@erinc.com
--
-- *************************************************************************
