-- **********************************************
-- StorageTek Network System Group Enterprise MIB
-- **********************************************
--
-- Title:           NSC-MIB
-- Purpose:         This MIB defines the high-level object structure for
--                  NSC Enterprise MIBs.
-- Required MIBs:   None.
--
-- Last Update:     July 31, 1997     Steven Trapp <steven.trapp@network.com>


NSC-MIB DEFINITIONS ::= BEGIN

               IMPORTS
                       enterprises
                           FROM RFC1155-SMI;

               -- nsc is the top of the NSC tree and it resides under
               -- the enterprise node.  Its position under the enterprise
               -- node has been allocated and published and MUST NOT CHANGE.

               nsc		OBJECT IDENTIFIER ::= { enterprises 10 }


               -- There are two nodes under the nsc node. The nscMib node
               -- is used to represent published product and should only
               -- be added to; NEVER delete objects from it.  The
               -- nscExperimental node represents a copy of what is under
               -- the nscProduct node but is used for development of a
               -- MIB object.  The use of the nscExperimental node by
               -- customers should be forbidden since it's layout may
               -- change at any time.

               nscExperimental	OBJECT IDENTIFIER ::= { nsc 1 }

               nscMib		OBJECT IDENTIFIER ::= { nsc 2 }

               -- Under the nscMib (and nscExperimental when developing)
               -- consists a number of objects to describe individual
               -- products as well as generic NSC management.

               -- The nscProducts node contains a generic object (nscDevices)
               -- that can be used to locate the exact product being queried.
               -- There are also individual objects for a given product.
               -- MIB information for the specific product should be defined
               -- in a separate MIB and included with this MIB for a complete
               -- information base.

               nscProducts	OBJECT IDENTIFIER ::= { nscMib 1 }

               nscDevices	OBJECT IDENTIFIER ::= { nscProducts 1 }
               nscObj		   OBJECT IDENTIFIER ::= { nscDevices 1 }
               nscDevicesInstalled OBJECT IDENTIFIER ::= { nscDevices 2 }

               nsc6600		OBJECT IDENTIFIER ::= { nscProducts 2 }
               nscDx		OBJECT IDENTIFIER ::= { nscProducts 3 }
               nscHippiSwitch	OBJECT IDENTIFIER ::= { nscProducts 4 }
               nscHippiSonet	OBJECT IDENTIFIER ::= { nscProducts 5 }
               nscErs		OBJECT IDENTIFIER ::= { nscProducts 6 }
               nscPenril	OBJECT IDENTIFIER ::= { nscProducts 7 }
               nscServiceMultiplexer OBJECT IDENTIFIER ::= { nscProducts 8 }
               nscBorderGuard   OBJECT IDENTIFIER ::= { nscProducts 9 }
               nscSecurityRouter OBJECT IDENTIFIER ::= { nscProducts 10 }
               nscPrxy  OBJECT IDENTIFIER ::= { nscProducts 11}

               -- nscPrxyPS node contains MIB variables and trap definitions
               -- utilized by various Professional Services software products

               nscPrxyPS        OBJECT IDENTIFIER ::= { nscProducts 12 }
 
	       -- nscPrxyChan node contains MIB variables for channel interfaces
	       -- accessed through proxy.

               nscOsx           OBJECT IDENTIFIER ::= { nscProducts 13 }
 
               nscPrxyChan      OBJECT IDENTIFIER ::= { nscPrxy 1 }

               nscBG1000	OBJECT IDENTIFIER ::= { nscProducts 14 }
               nscBG1000NSR	OBJECT IDENTIFIER ::= { nscBG1000 2 }
               nscBG1000VPN	OBJECT IDENTIFIER ::= { nscBG1000 3 }
               nscBG1000IDS	OBJECT IDENTIFIER ::= { nscBG1000 4 }
               nscBG1000Sensor	OBJECT IDENTIFIER ::= { nscBG1000 5 }

               nscBG2000	OBJECT IDENTIFIER ::= { nscProducts 15 }
               nscBG2000NSR	OBJECT IDENTIFIER ::= { nscBG2000 2 }
               nscBG2000VPN	OBJECT IDENTIFIER ::= { nscBG2000 3 }
               nscBG2000IDS	OBJECT IDENTIFIER ::= { nscBG2000 4 }
               nscBG2000Sensor	OBJECT IDENTIFIER ::= { nscBG2000 5 }
              

               -- The nscManagement node provides a common method to control
               -- NSC products.  Objects which can not be successfully
               -- managed using a standard MIB but whose functions are common
               -- among more then one NSC product should be defined here.

               nscManagement	OBJECT IDENTIFIER ::= { nscMib 2 }

               nscSystem	OBJECT IDENTIFIER ::= { nscManagement 1 }

               nscTransmission	OBJECT IDENTIFIER ::= { nscManagement 2 }
	       nscHippi		OBJECT IDENTIFIER ::= { nscTransmission 1 }

               -- Protocols would include TCP, Appletalk, XNS, etc.
               nscProtocols	OBJECT IDENTIFIER ::= { nscManagement 3 }

	       nscIp		OBJECT IDENTIFIER ::= { nscProtocols 1}
	       nscDecnet	OBJECT IDENTIFIER ::= { nscProtocols 2}
	       nscAppletalk	OBJECT IDENTIFIER ::= { nscProtocols 3}
	       nscIpx		OBJECT IDENTIFIER ::= { nscProtocols 4}
	       nscXns		OBJECT IDENTIFIER ::= { nscProtocols 5}
	       nscBridging	OBJECT IDENTIFIER ::= { nscProtocols 6}
	       nscOsi		OBJECT IDENTIFIER ::= { nscProtocols 7}
	       nscVines		OBJECT IDENTIFIER ::= { nscProtocols 8}

               END
