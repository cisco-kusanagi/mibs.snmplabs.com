KALEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32, IpAddress
			FROM SNMPv2-SMI
		DisplayString, RowStatus
			FROM SNMPv2-TC
		kalExt
			FROM APENT-MIB;

--KALEXT MIB

    apKalExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  Keepalives"
      ::= { kalExt 1}


apKalTable OBJECT-TYPE
	SYNTAX          SEQUENCE OF APKalEntry
	MAX-ACCESS      not-accessible
	STATUS          current
	DESCRIPTION
		"A list of Keepalives"
	::= { kalExt 2 }

apKalEntry OBJECT-TYPE
	SYNTAX          APKalEntry
	MAX-ACCESS      not-accessible
	STATUS          current
	DESCRIPTION
		"A group of information uniquely identifying a Keepalive.  One entry 
         exists for each Keepalive"
	INDEX   { apKalName }
	::= { apKalTable 1 }

APKalEntry ::= SEQUENCE {
	apKalName			DisplayString,
	apKalStatus			RowStatus,
	apKalDescription    DisplayString,
	apKalEnable			INTEGER,
	apKalIPAddress		IpAddress,
	apKalPort			Integer32,
	apKalType			INTEGER,
	apKalFrequency		Integer32,
	apKalMaxFailure		Integer32,
	apKalRetryPeriod	Integer32,
	apKalUri			DisplayString,
	apKalMethod			INTEGER,
	apKalPersistence	INTEGER,
	apKalState          INTEGER,
	apKalHash           DisplayString,
	apKalFtpRecordName  DisplayString,
	apKalScriptName     DisplayString,
	apKalScriptArgs     DisplayString,
	apKalScriptLog      DisplayString
}


apKalName OBJECT-TYPE
	SYNTAX          DisplayString (SIZE(1..31))
	MAX-ACCESS      read-create
	STATUS          current
	DESCRIPTION     
			"The name of the Keepalive"
	::= {apKalEntry 1}

apKalStatus OBJECT-TYPE
	SYNTAX          RowStatus
	MAX-ACCESS      read-create
	STATUS          current
	DESCRIPTION      
		"Status entry for this row "
	::= {apKalEntry 2}

apKalDescription OBJECT-TYPE
	SYNTAX          DisplayString (SIZE(0..64))
	MAX-ACCESS      read-create
	STATUS          current
	DESCRIPTION     
			"The description of the Keepalive"
	::= {apKalEntry 3}

apKalEnable  OBJECT-TYPE
	SYNTAX  INTEGER {
					disable(0),
					enable(1)
 					}
	MAX-ACCESS      read-create
	STATUS 			current
	DESCRIPTION     
		"The state of the keepalive, either enable or disabled"
	DEFVAL { disable }
	::= {apKalEntry 4}

apKalIPAddress OBJECT-TYPE
	SYNTAX          IpAddress
	MAX-ACCESS      read-create
	STATUS  		current
	DESCRIPTION     
		"The IP Address the of the content providing service."
	--DEFAULT ap-display-name	IP Address
	--DEFAULT apjam-popup-ref apServicesGroupInst, Properties
	--DEFAULT apjam-wizard-field	1, normal
	::= {apKalEntry 5}

apKalPort OBJECT-TYPE
	SYNTAX          Integer32 (0..65535)
	MAX-ACCESS      read-create
	STATUS  		current
	DESCRIPTION     
		"The Keepalive IP Port to use"
	DEFVAL { 0 }
	::= {apKalEntry 6}

apKalType OBJECT-TYPE
	SYNTAX  INTEGER {
					icmp(1)                                         ,
					http(2)                            ,
					ftp(3)                           ,
					tcp(4)                           ,
					script(5)                              
					}
	MAX-ACCESS      read-create
	STATUS 			current
	DESCRIPTION     
		"The Keepalive detection method."
	DEFVAL { icmp }
	--DEFAULT ap-display-name	Keepalive Method
	--DEFAULT apjam-popup-ref apServicesGroupInst, Properties
	--DEFAULT apjam-wizard-field	2, normal
	::= {apKalEntry 7}

apKalFrequency OBJECT-TYPE
	SYNTAX          Integer32 (2..255)
	MAX-ACCESS      read-create
	STATUS  		current
	DESCRIPTION     
		"The Keepalive frequency of doing keepalive probes in units of seconds."
	DEFVAL { 5 }
	--DEFAULT ap-display-name	Keepalive Frequency
	--DEFAULT apjam-popup-ref apServicesGroupInst, Properties, Advanced
	::= {apKalEntry 8}

apKalMaxFailure OBJECT-TYPE
	SYNTAX          Integer32 (1..10)
	MAX-ACCESS      read-create
	STATUS  		current
	DESCRIPTION     
		"The Keepalive maximum number of failures before the service is 
		transitioned to failed state."
	DEFVAL { 3 }
	--DEFAULT ap-display-name	Keepalive Max Failures
	--DEFAULT apjam-popup-ref apServicesGroupInst, Properties, Advanced
	::= {apKalEntry 9}

apKalRetryPeriod OBJECT-TYPE
	SYNTAX          Integer32 (2..255)
	MAX-ACCESS      read-create
	STATUS  		current
	DESCRIPTION     
		"The Keepalive frequency of probes to the service after it has been
		transitioned to failed state."
	DEFVAL { 5 }
	--DEFAULT ap-display-name	Keepalive Retry Period
	--DEFAULT apjam-popup-ref apServicesGroupInst, Properties, Advanced
	::= {apKalEntry 10}

apKalUri OBJECT-TYPE
	SYNTAX          DisplayString (SIZE(0..64))
	MAX-ACCESS      read-create
	STATUS          current
	DESCRIPTION     
			"The URI which be checked during an HTTP keepalive."
	--DEFAULT ap-display-name	Keepalive HTTP Uri
	--DEFAULT apjam-popup-ref apServicesGroupInst, Properties
	--DEFAULT apjam-wizard-field	2, normal
	::= {apKalEntry 11}

apKalMethod  OBJECT-TYPE
	SYNTAX  INTEGER {
					head(1)                   ,
					get(2)                                 ,
					post(3)                                  
 					}
	MAX-ACCESS      read-create
	STATUS 			current
	DESCRIPTION     
		"The HTTP method used for the HTTP keepalive type.  The 
         methods operate in the following manner:
         HEAD -- HTTP HEAD generated.  200 response code required
         GET  -- HTTP GET generated.  MD5 Hash of entify body performed.
                 First successful GET (200 response code) becomes reference 
                 hash.  Deviation from rererence hash result, or non-200
                 response code, results in service state transition.
         POST -- Same as GET with substituation of POST method."
	DEFVAL { head }
	--DEFAULT ap-display-name	HTTP Keepalive Method
	--DEFAULT apjam-popup-ref apServicesGroupInst, Properties
	--DEFAULT apjam-wizard-field	2, normal
	::= {apKalEntry 12}

apKalPersistence  OBJECT-TYPE
	SYNTAX  INTEGER {
					non-persistent(0)                                              ,
					persistent(1)                                        
 					}
	MAX-ACCESS      read-create
	STATUS 			current
	DESCRIPTION     
		"This object controls whether the Keepalive will be attempted over
         a persistent connection.  Persistent connections are supported 
         through HTTP 1.1, and HTTP 1.0 with Connection-KeepAlive"
	DEFVAL { persistent }
	::= {apKalEntry 13}

apKalState  OBJECT-TYPE
	SYNTAX  INTEGER {
					suspended(1),
					down(2),
					alive(4),
					dying(5)
 					}
	MAX-ACCESS      read-only
	STATUS 			current
	DESCRIPTION     
		"The current keepalive state"
	DEFVAL { suspended }
	::= {apKalEntry 14}

apKalHash OBJECT-TYPE
	SYNTAX          DisplayString(SIZE(0..32))
	MAX-ACCESS      read-create
	STATUS  		current
	DESCRIPTION     
		"This object contains the MD5 hash which will be compared for
         HTTP keepalives which use the GET method."
	::= {apKalEntry 15}

apKalFtpRecordName OBJECT-TYPE
	SYNTAX          DisplayString(SIZE(0..32))
	MAX-ACCESS      read-create
	STATUS  		current
	DESCRIPTION     
		"This object contains the ftp-record used in conjunction with ftp
         keepalives"
	::= {apKalEntry 16}

apKalScriptName OBJECT-TYPE
	SYNTAX          DisplayString(SIZE(0..32))
	MAX-ACCESS      read-create
	STATUS  		current
	DESCRIPTION     
		"This name represents the script that will be used in conjunction with
        the keepalive type script.  The script will be played everytime the keepalive
        is issued."
	::= {apKalEntry 17}

apKalScriptArgs OBJECT-TYPE
	SYNTAX          DisplayString(SIZE(0..128))
	MAX-ACCESS      read-create
	STATUS  		current
	DESCRIPTION     
		"This name represents the script arguments that will be used in conjunction
        with the keepalive type script."
	::= {apKalEntry 18}

apKalScriptLog OBJECT-TYPE
	SYNTAX          DisplayString(SIZE(0..32))
	MAX-ACCESS      read-create
	STATUS  		current
	DESCRIPTION  
		"This name represents the script log that can be used to capture output
        from a keepalive script."   
	::= {apKalEntry 19}

END
