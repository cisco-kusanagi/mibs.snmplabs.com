Wellfleet-LOADER-MIB DEFINITIONS ::= BEGIN

-- Created by mdl2asn version 3.1
-- Creation date: Wed Aug 30 16:45:02 EDT 1995
-- Modified  4/23/98  cying      Added load mask for BAC PktGen.


    IMPORTS

      Counter
        FROM RFC1155-SMI
      OBJECT-TYPE
        FROM RFC-1212
      wfSoftwareConfig
        FROM Wellfleet-COMMON-MIB;


    wfProtocols OBJECT IDENTIFIER ::= { wfSoftwareConfig 1 }

    wfIPROTOLoad OBJECT-TYPE
        SYNTAX  Counter
        ACCESS  read-write
        STATUS  mandatory
        DESCRIPTION
                "Bit mask for loading the IP components on
                slots 1-14.  The MSBit represents slot 1, the next most
                significant bit represents slot 2, and so forth."
        ::= { wfProtocols 1 }

    wfDECNETLoad OBJECT-TYPE
        SYNTAX  Counter
        ACCESS  read-write
        STATUS  mandatory
        DESCRIPTION
                "Bit mask for loading the DECNet router on slots 1-14. The MSBit
                represents slot 1, the next most significant bit represents
                slot 2, and so forth."
        ::= { wfProtocols 2 }

    wfATLoad OBJECT-TYPE
        SYNTAX  Counter
        ACCESS  read-write
        STATUS  mandatory
        DESCRIPTION
                "Bit mask for loading the AppleTalk router on slots 1-14. The MSBit
                represents slot 1, the next most significant bit represents
                slot 2, and so forth."
        ::= { wfProtocols 3 }

    wfXNSLoad OBJECT-TYPE
        SYNTAX  Counter
        ACCESS  read-write
        STATUS  mandatory
        DESCRIPTION
                "Bit mask for loading the XNS router on slots 1-14. The MSBit
                represents slot 1, the next most significant bit represents
                slot 2, and so forth."
        ::= { wfProtocols 4 }

    wfIPXLoad OBJECT-TYPE
        SYNTAX  Counter
        ACCESS  read-write
        STATUS  mandatory
        DESCRIPTION
                "Bit mask for loading the IPX router on slots 1-14. The MSBit
                represents slot 1, the next most significant bit represents
                slot 2, and so forth."
        ::= { wfProtocols 5 }

    wfOSILoad OBJECT-TYPE
        SYNTAX  Counter
        ACCESS  read-write
        STATUS  mandatory
        DESCRIPTION
                "Bit mask for loading the ISO router on slots 1-14. The MSBit
                represents slot 1, the next most significant bit represents
                slot 2, and so forth."
        ::= { wfProtocols 6 }

    wfX25DTELoad OBJECT-TYPE
        SYNTAX  Counter
        ACCESS  read-write
        STATUS  mandatory
        DESCRIPTION
                "Bit mask for loading the X.25 DTE protocol on slots 1-14. The
                MSBit represents slot 1, the next most significant bit
                represents slot 2, and so forth."
        ::= { wfProtocols 7 }

    wfX25DCELoad OBJECT-TYPE
        SYNTAX  Counter
        ACCESS  read-write
        STATUS  mandatory
        DESCRIPTION
                "Bit mask for loading the X.25 DCE protocol on slots 1-14. The
                MSBit represents slot 1, the next most significant bit
                represents slot 2, and so forth."
        ::= { wfProtocols 8 }

    wfVINESLoad OBJECT-TYPE
        SYNTAX  Counter
        ACCESS  read-write
        STATUS  mandatory
        DESCRIPTION
                "Bit mask for loading the VINES router on slots 1-14. The MSBit
                represents slot 1, the next most significant bit represents
                slot 2, and so forth."
        ::= { wfProtocols 9 }

    wfFRLoad OBJECT-TYPE
        SYNTAX  Counter
        ACCESS  read-write
        STATUS  mandatory
        DESCRIPTION
                "Bit mask for loading the Frame Relay master on slots 1-14. The
                MSBit represents slot 1, and so forth."
        ::= { wfProtocols 10 }

    wfRARPLoad OBJECT-TYPE
        SYNTAX  Counter
        ACCESS  read-write
        STATUS  mandatory
        DESCRIPTION
                "Bit mask for loading Reverse ARP master on slots 1-14. The
                MSBit represents slot 1, and so forth."
        ::= { wfProtocols 11 }

    wfATMLoad OBJECT-TYPE
        SYNTAX  Counter
        ACCESS  read-write
        STATUS  mandatory
        DESCRIPTION
                "Bit mask for loading the ATM master on slots 1-14. The
                MSBit represents slot 1, and so forth."
        ::= { wfProtocols 12 }

    wfDLSLoad OBJECT-TYPE
        SYNTAX  Counter
        ACCESS  read-write
        STATUS  mandatory
        DESCRIPTION
                "Bit mask for loading the DLS master on slots 1-14. The
                MSBit represents slot 1, and so forth."
        ::= { wfProtocols 13 }

    wfLNMLoad OBJECT-TYPE
        SYNTAX  Counter
        ACCESS  read-write
        STATUS  mandatory
        DESCRIPTION
                "Bit mask for loading the LNM master on slots 1-14. The
                MSBit represents slot 1, and so forth."
        ::= { wfProtocols 14 }

    wfTelnetLoad OBJECT-TYPE
        SYNTAX  Counter
        ACCESS  read-write
        STATUS  mandatory
        DESCRIPTION
                "Bit mask for loading the Telnet protocol on slots 1-14. The
                MSBit represents slot 1, and so forth."
        ::= { wfProtocols 15 }

    wfTFTPLoad OBJECT-TYPE
        SYNTAX  Counter
        ACCESS  read-write
        STATUS  mandatory
        DESCRIPTION
                "Bit mask for loading the TFTP protocol on slots 1-14. The
                MSBit represents slot 1, and so forth."
        ::= { wfProtocols 16 }

    wfSNMPLoad OBJECT-TYPE
        SYNTAX  Counter
        ACCESS  read-write
        STATUS  mandatory
        DESCRIPTION
                "Bit mask for loading the SNMP protocol on slots 1-14. The
                MSBit represents slot 1, and so forth."
        ::= { wfProtocols 17 }

    wfTCPLoad OBJECT-TYPE
        SYNTAX  Counter
        ACCESS  read-write
        STATUS  mandatory
        DESCRIPTION
                "Bit mask for loading the TCP protocol on slots 1-14. The
                MSBit represents slot 1, and so forth."
        ::= { wfProtocols 18 }

    wfBGPLoad OBJECT-TYPE
        SYNTAX  Counter
        ACCESS  read-write
        STATUS  mandatory
        DESCRIPTION
                "Bit mask for loading the BGP protocol on slots 1-14. The
                MSBit represents slot 1, and so forth."
        ::= { wfProtocols 19 }

    wfEGPLoad OBJECT-TYPE
        SYNTAX  Counter
        ACCESS  read-write
        STATUS  mandatory
        DESCRIPTION
                "Bit mask for loading the EGP protocol on slots 1-14. The
                MSBit represents slot 1, and so forth."
        ::= { wfProtocols 20 }

    wfOSPFLoad OBJECT-TYPE
        SYNTAX  Counter
        ACCESS  read-write
        STATUS  mandatory
        DESCRIPTION
                "Bit mask for loading the OSPF protocol on slots 1-14. The
                MSBit represents slot 1, and so forth."
        ::= { wfProtocols 21 }

    wfWPROXYLoad OBJECT-TYPE
        SYNTAX  Counter
        ACCESS  read-write
        STATUS  mandatory
        DESCRIPTION
                "Bit mask for loading the WPROXY protocols on slots 1-14. The
                MSBit represents slot 1, and so forth."
        ::= { wfProtocols 22 }

    wfLLC2Load OBJECT-TYPE
        SYNTAX  Counter
        ACCESS  read-write
        STATUS  mandatory
        DESCRIPTION
                "Bit mask for loading the LLC2 master on slots 1-14. The
                MSBit represents slot 1, and so forth."
        ::= { wfProtocols 23 }

    wfSMDSLoad OBJECT-TYPE
        SYNTAX  Counter
        ACCESS  read-write
        STATUS  mandatory
        DESCRIPTION
                "Bit mask for loading the SMDS protocol on slots 1-14. The MSBit
                represents slot 1, and so forth."
        ::= { wfProtocols 24 }

    wfPPPLoad OBJECT-TYPE
        SYNTAX  Counter
        ACCESS  read-write
        STATUS  mandatory
        DESCRIPTION
                "Bit mask for loading PPP on slots 1-14. The MSBit
                represents slot 1, and so forth."
        ::= { wfProtocols 25 }

    wfPktCaptureLoad OBJECT-TYPE
        SYNTAX  Counter
        ACCESS  read-write
        STATUS  mandatory
        DESCRIPTION
                "Bit mask for loading Pcap on slots 1-14. The MSBit
                represents slot 1, and so forth."
        ::= { wfProtocols 26 }

    wfFRSWCNGCLoad OBJECT-TYPE
        SYNTAX  Counter
        ACCESS  read-write
        STATUS  mandatory
        DESCRIPTION
                "Bit mask for loading FrswCngc on slots 1-14. The MSBit
                represents slot 1, and so forth."
        ::= { wfProtocols 27 }

    wfSWPROXYLoad OBJECT-TYPE
        SYNTAX  Counter
        ACCESS  read-write
        STATUS  mandatory
        DESCRIPTION
                "Bit mask for loading Switch Proxy on slots 1-14. The MSBit
                represents slot 1, and so forth."
        ::= { wfProtocols 28 }

    wfFRSWLoad OBJECT-TYPE
        SYNTAX  Counter
        ACCESS  read-write
        STATUS  mandatory
        DESCRIPTION
                "Bit mask for loading FRSW on slots 1-14. The MSBit
                represents slot 1, and so forth."
        ::= { wfProtocols 29 }

    wfSWSMDSLoad OBJECT-TYPE
        SYNTAX  Counter
        ACCESS  read-write
        STATUS  mandatory
        DESCRIPTION
                "Bit mask for loading SWSMDS on slots 1-14. The MSBit
                represents slot 1, and so forth."
        ::= { wfProtocols 30 }

    wfNBASELoad OBJECT-TYPE
        SYNTAX  Counter
        ACCESS  read-write
        STATUS  mandatory
        DESCRIPTION
                "Bit mask for loading NBASE on slots 1-14. The MSBit
                represents slot 1, and so forth."
        ::= { wfProtocols 31 }

    wfSDLCLoad OBJECT-TYPE
        SYNTAX  Counter
        ACCESS  read-write
        STATUS  mandatory
        DESCRIPTION
                "Bit mask for loading SDLC on slots 1-14. The MSBit
                represents slot 1, and so forth."
        ::= { wfProtocols 32 }

    wfTNCLoad OBJECT-TYPE
        SYNTAX  Counter
        ACCESS  read-write
        STATUS  mandatory
        DESCRIPTION
                "Bit mask for loading Outbound Telnet on slots 1-14. The MSBit
                represents slot 1, and so forth."
        ::= { wfProtocols 33 }

    wfLAPBLoad OBJECT-TYPE
        SYNTAX  Counter
        ACCESS  read-write
        STATUS  mandatory
        DESCRIPTION
                "Bit mask for loading the LAPB protocol on slots 1-14. The
                MSBit represents slot 1, the next most significant bit
                represents slot 2, and so forth."
        ::= { wfProtocols 34 }

    wfDebugLoad OBJECT-TYPE
        SYNTAX  Counter
        ACCESS  read-write
        STATUS  mandatory
        DESCRIPTION
                "Bit mask for loading Debug on slots 1-14. The MSBit
                represents slot 1, and so forth."
        ::= { wfProtocols 35 }

    wfNBIPLoad OBJECT-TYPE
        SYNTAX  Counter
        ACCESS  read-write
        STATUS  mandatory
        DESCRIPTION
                "Bit mask for loading NBIP on slots 1-14. The MSBit
                represents slot 1, and so forth."
        ::= { wfProtocols 36 }

    wfATMCsLoad OBJECT-TYPE
        SYNTAX  Counter
        ACCESS  read-write
        STATUS  mandatory
        DESCRIPTION
                "Bit mask for loading ATM master on slots 1-14. The MSBit
                represents slot 1, and so forth."
        ::= { wfProtocols 37 }

    wfDvmrpLoad OBJECT-TYPE
        SYNTAX  Counter
        ACCESS  read-write
        STATUS  mandatory
        DESCRIPTION
                "Bit mask for loading DVMRP on slots 1-14. The MSBit
                represents slot 1, and so forth."
        ::= { wfProtocols 38 }

    wfIgmpLoad OBJECT-TYPE
        SYNTAX  Counter
        ACCESS  read-write
        STATUS  mandatory
        DESCRIPTION
                "Bit mask for loading IGMP on slots 1-14. The MSBit
                represents slot 1, and so forth."
        ::= { wfProtocols 39 }

    wfISDNLoad OBJECT-TYPE
        SYNTAX  Counter
        ACCESS  read-write
        STATUS  mandatory
        DESCRIPTION
                "Bit mask for loading ISDN on slots 1-14. The MSBit
                represents slot 1, and so forth."
        ::= { wfProtocols 40 }

    wfLMLoad OBJECT-TYPE
        SYNTAX  Counter
        ACCESS  read-write
        STATUS  mandatory
        DESCRIPTION
                "Bit mask for loading LM on slots 1-14. The MSBit
                represents slot 1, and so forth."
        ::= { wfProtocols 41 }

    wfPingLoad OBJECT-TYPE
        SYNTAX  Counter
        ACCESS  read-write
        STATUS  mandatory
        DESCRIPTION
                "Bit mask for loading PING on slots 1-14. The MSBit
                represents slot 1, and so forth."
        ::= { wfProtocols 42 }

    wfAPPNCpLoad OBJECT-TYPE
        SYNTAX  Counter
        ACCESS  read-write
        STATUS  mandatory
        DESCRIPTION
                "Bit mask for loading the APPN CP soloist on slots 1-14. The MSBit
                represents slot 1, and so forth."
        ::= { wfProtocols 43 }

    wfAPPNLsLoad OBJECT-TYPE
        SYNTAX  Counter
        ACCESS  read-write
        STATUS  mandatory
        DESCRIPTION
                "Bit mask for loading the APPN LS gates on slots 1-14. The MSBit
                represents slot 1, and so forth."
        ::= { wfProtocols 44 }

    wfWcpLoad OBJECT-TYPE
        SYNTAX  Counter
        ACCESS  read-write
        STATUS  mandatory
        DESCRIPTION
                "Bit mask for loading the WCP control gate on slots 1-14. The MSBit
                represents slot 1, and so forth."
        ::= { wfProtocols 45 }

    wfFTPLoad OBJECT-TYPE
        SYNTAX  Counter
        ACCESS  read-write
        STATUS  mandatory
        DESCRIPTION
                "Bit mask for loading the FTP protocol on slots 1-14. The
                MSBit represents slot 1, and so forth."
        ::= { wfProtocols 46 }

    wfARPLoad OBJECT-TYPE
        SYNTAX  Counter
        ACCESS  read-write
        STATUS  mandatory
        DESCRIPTION
                "Bit mask for loading ARP on slots 1-14. The MSBit
                represents slot 1, and so forth."
        ::= { wfProtocols 47 }

    wfSYSLLoad OBJECT-TYPE
        SYNTAX  Counter
        ACCESS  read-write
        STATUS  mandatory
        DESCRIPTION
                "Bit mask for loading SYSLOG on slots 1-14. The MSBit
                represents slot 1, and so forth."
        ::= { wfProtocols 48 }

    wfBGPRSLoad OBJECT-TYPE
        SYNTAX  Counter
        ACCESS  read-write
        STATUS  mandatory
        DESCRIPTION
                "Bit mask for loading BGP Route Server on slots 1-14. The MSBit
                represents slot 1, and so forth."
        ::= { wfProtocols 49 }

    wfATMLeLoad OBJECT-TYPE
        SYNTAX  Counter
        ACCESS  read-write
        STATUS  mandatory
        DESCRIPTION
                "Bit mask for loading ATM LE on slots 1-14. The MSBit
                represents slot 1, and so forth."
        ::= { wfProtocols 50 }

    wfCRMLoad OBJECT-TYPE
        SYNTAX  Counter
        ACCESS  read-write
        STATUS  mandatory
        DESCRIPTION
                "Bit mask for loading Circuit Resource Manager on slots 1-14. The
                MSBit represents slot 1, and so forth."
        ::= { wfProtocols 51 }

    wfIPEXLoad OBJECT-TYPE
        SYNTAX  Counter
        ACCESS  read-write
        STATUS  mandatory
        DESCRIPTION
                "Bit mask for loading IPEX on slots 1-14. The MSBit
                represents slot 1, and so forth."
        ::= { wfProtocols 52 }

    wfSt2Load OBJECT-TYPE
        SYNTAX  Counter
        ACCESS  read-write
        STATUS  mandatory
        DESCRIPTION
                "Bit mask for loading ST2 on slots 1-14. The MSBit
                represents slot 1, and so forth."
        ::= { wfProtocols 53 }

    wfNLSPLoad OBJECT-TYPE
        SYNTAX  Counter
        ACCESS  read-write
        STATUS  mandatory
        DESCRIPTION
                "Bit mask for loading NLSP on slots 1-14. The MSBit
                represents slot 1, and so forth."
        ::= { wfProtocols 54 }

    wfSTATSLoad OBJECT-TYPE
        SYNTAX  Counter
        ACCESS  read-write
        STATUS  mandatory
        DESCRIPTION
                "Bit mask for loading STATS on slots 1-14. The MSBit
                represents slot 1, and so forth."
        ::= { wfProtocols 55 }

    wfNPTLoad OBJECT-TYPE
        SYNTAX  Counter
        ACCESS  read-write
        STATUS  mandatory
        DESCRIPTION
                "Bit mask for loading STATS on slots 1-14. The MSBit
                represents slot 1, and so forth."
        ::= { wfProtocols 56 }

    wfRREDUNDLoad OBJECT-TYPE
        SYNTAX  Counter
        ACCESS  read-write
        STATUS  mandatory
        DESCRIPTION
                "Bit mask for loading RREDUND on slots 1-14. The MSBit
                represents slot 1, and so forth."
        ::= { wfProtocols 57 }

    wfATMSigLoad OBJECT-TYPE
        SYNTAX  Counter
        ACCESS  read-write
        STATUS  mandatory
        DESCRIPTION
                "Bit mask for loading ATM signaling on slots 1-14. The
                MSBit represents slot 1, the next most significant bit represents
                slot 2, and so forth."
        ::= { wfProtocols 58 }

    wfIPv6Load OBJECT-TYPE
        SYNTAX  Counter
        ACCESS  read-write
        STATUS  mandatory
        DESCRIPTION
                "Bit mask for loading IPv6 signaling on slots 1-14. The
                MSBit represents slot 1, the next most significant bit represents
                slot 2, and so forth."
        ::= { wfProtocols 59 }

    wfBOTLoad OBJECT-TYPE
        SYNTAX  Counter
        ACCESS  read-write
        STATUS  mandatory
        DESCRIPTION
             "Bit mask for loading BOT signaling on slots 1-14. The
             MSBit represents slot 1, the next most significant bit represents
             slot 2, and so forth."
        ::= { wfProtocols 60 }

    wfPimLoad OBJECT-TYPE
        SYNTAX  Counter
        ACCESS  read-write
        STATUS  mandatory
        DESCRIPTION
             "Bit mask for loading Protocol Independant Multicast (PIM)
             on slots 1-14. The MSBit represents slot 1, the next most
             significant bit represents slot 2, and so forth."
        ::= { wfProtocols 61 }

    wfLBCLoad OBJECT-TYPE
        SYNTAX  Counter
        ACCESS  read-write
        STATUS  mandatory
        DESCRIPTION
                "Bit mask for loading LBC on slots 1-14. The MSBit
                represents slot 1, and so forth."
        ::= { wfProtocols 62 }

    wfATMMcsLoad OBJECT-TYPE
        SYNTAX  Counter
        ACCESS  read-write
        STATUS  mandatory
        DESCRIPTION
                "Bit mask for loading ATM MCS on slots 1-14. The MSBit
                represents slot 1, and so forth."
        ::= { wfProtocols 63 }

    wfATMAsmLoad OBJECT-TYPE
        SYNTAX  Counter
        ACCESS  read-write
        STATUS  mandatory
        DESCRIPTION
                "Bit mask for loading ATM ASM on slots 1-14. The MSBit
                represents slot 1, and so forth."
        ::= { wfProtocols 64 }

    wfCPMLoad OBJECT-TYPE
        SYNTAX  Counter
        ACCESS  read-write
        STATUS  mandatory
        DESCRIPTION
                "Bit mask for loading ATM CPM on slots 1-14. The MSBit
                represents slot 1, and so forth."
        ::= { wfProtocols 65 }

    wfBAYSIGLoad OBJECT-TYPE
        SYNTAX  Counter
        ACCESS  read-write
        STATUS  mandatory
        DESCRIPTION
                "Bit mask for loading ATM Signalling (BAYSIG) on slots 1-14.
                The MSBit represents slot 1, and so forth."
        ::= { wfProtocols 66 }

    wfScmIpcLoad OBJECT-TYPE
        SYNTAX  Counter
        ACCESS  read-write
        STATUS  mandatory
        DESCRIPTION
                "Bit mask for loading SCM IPC on slots 1-14.
                The MSBit represents slot 1, and so forth."
        ::= { wfProtocols 67 }

        wfNTPLoad OBJECT-TYPE
        SYNTAX  Counter
        ACCESS  read-write
        STATUS  mandatory
        DESCRIPTION
                "Bit mask for loading NTP  signaling on slots 1-14. The
                MSBit represents slot 1, the next most significant bit
                represents slot 2, and so forth."
        ::= { wfProtocols 68 }

        wfRADIUSLoad OBJECT-TYPE
        SYNTAX  Counter
        ACCESS  read-write
        STATUS  mandatory
        DESCRIPTION
                "Bit mask for loading RADIUS on slots 1-14. The MSBit
                represents slot 1, and so forth."
        ::= { wfProtocols 69 }

        wfRCMDSLoad OBJECT-TYPE
        SYNTAX  Counter
        ACCESS  read-write
        STATUS  mandatory
        DESCRIPTION
                "Bit mask for loading RCMDS  signaling on slots 1-14. The
                MSBit represents slot 1, the next most significant bit
                represents slot 2, and so forth."
        ::= { wfProtocols 70 }

        wfDNSLoad OBJECT-TYPE
        SYNTAX  Counter
        ACCESS  read-write
        STATUS  mandatory
        DESCRIPTION
                "Bit mask for loading DNS  signaling on slots 1-14. The
                MSBit represents slot 1, the next most significant bit
                represents slot 2, and so forth."
        ::= { wfProtocols 71 }

        wfWepLoad OBJECT-TYPE
        SYNTAX  Counter
        ACCESS  read-write
        STATUS  mandatory
        DESCRIPTION
                "Bit mask for loading WEP encryption on slots 1-14. The
                MSBit represents slot 1, the next most significant bit
                represents slot 2, and so forth."
        ::= { wfProtocols 72 }

    wfRipv6Load OBJECT-TYPE
        SYNTAX  Counter
        ACCESS  read-write
        STATUS  mandatory
        DESCRIPTION
                "Bit mask for loading Ripv6 signaling on slots 1-14. The
                MSBit represents slot 1, the next most significant bit represents
                slot 2, and so forth."
        ::= { wfProtocols 73 }

    wfMOSPFLoad OBJECT-TYPE
        SYNTAX  Counter
        ACCESS  read-write
        STATUS  mandatory
        DESCRIPTION
                "Bit mask for loading the MOSPF components on
                slots 1-14.  The MSBit represents slot 1, the next most
                significant bit represents slot 2, and so forth."
        ::= { wfProtocols 74 }

    wfRSVPLoad OBJECT-TYPE
        SYNTAX  Counter
        ACCESS  read-write
        STATUS  mandatory
        DESCRIPTION
                "Bit mask for loading the RSVP components on
                slots 1-14.  The MSBit represents slot 1, the next most
                significant bit represents slot 2, and so forth."
        ::= { wfProtocols 75 }

    wfIpSwitchLoad OBJECT-TYPE
        SYNTAX  Counter
        ACCESS  read-write
        STATUS  mandatory
        DESCRIPTION
                "Bit mask for loading IpSwitch/AutoLearn on slots 1-14.
                The MSBit represents slot 1, and so forth."
        ::= { wfProtocols 76 }

    wfPortMtxLoad OBJECT-TYPE
        SYNTAX  Counter
        ACCESS  read-write
        STATUS  mandatory
        DESCRIPTION
                "Bit mask for loading Port Matrix, only one slot for FX.
              The MSBit represents slot 1, and so forth."
        ::= { wfProtocols 77 }

    wfConvStrLoad OBJECT-TYPE
        SYNTAX  Counter
        ACCESS  read-write
        STATUS  mandatory
        DESCRIPTION
                "Bit mask for loading Conversation Steer, only one slot for FX.
              The MSBit represents slot 1, and so forth."
        ::= { wfProtocols 78 }


    wfS5ChasLoad OBJECT-TYPE
        SYNTAX  Counter
        ACCESS  read-write
        STATUS  mandatory
        DESCRIPTION
                "Bit mask for loading S5  signaling on slots 1-14. The
                MSBit represents slot 1, the next most significant bit
                represents slot 2, and so forth."
        ::= { wfProtocols 79 }

    wfFRSVCLoad OBJECT-TYPE
        SYNTAX Counter
        ACCESS read-write
        STATUS mandatory
         DESCRIPTION
                "Bit mask for loading Frame Relay SVC software on slots 1-14.
               The MSBit represents slot 1, the next most significant bit
               represents slot 2, and so forth."
        ::= { wfProtocols 80 }

    wfAOTLoad OBJECT-TYPE
        SYNTAX  Counter
        ACCESS  read-write
        STATUS  mandatory
        DESCRIPTION
             "Bit mask for loading AOT signaling on slots 1-14. The
             MSBit represents slot 1, the next most significant bit represents
             slot 2, and so forth."
        ::= { wfProtocols 81 }

    wfNATLoad OBJECT-TYPE
        SYNTAX  Counter
        ACCESS  read-write
        STATUS  mandatory
        DESCRIPTION
             "Bit mask for loading NAT signaling on slots 1-14. The
             MSBit represents slot 1, the next most significant bit represents
             slot 2, and so forth."
        ::= { wfProtocols 82 }


    wfFRPTLoad OBJECT-TYPE
        SYNTAX Counter
        ACCESS read-write
        STATUS mandatory
         DESCRIPTION
                "Bit mask for loading Frame Relay PVC Passthru on slots 1-14.
                 The MSBit represents slot 1, the next most significant bit
                 represents slot 2, and so forth."
        ::= { wfProtocols 83 }

    wfHttpSrvLoad OBJECT-TYPE
        SYNTAX  Counter
        ACCESS  read-write
        STATUS  mandatory
        DESCRIPTION
                "Bit mask for loading the HTTP Server on slots 1-14. The
                 MSBit represents slot 1, the next most significant bit
                 represents slot 2, and so forth."
        ::= { wfProtocols 84 }

    wfStacLZSLoad OBJECT-TYPE
        SYNTAX  Counter
        ACCESS  read-write
        STATUS  mandatory
        DESCRIPTION
                "Bit mask for loading the Stac LZS control gate on slots 1-14.
                The MSBit represents slot 1, and so forth."
        ::= { wfProtocols 85 }

    wfASRLoad OBJECT-TYPE
         SYNTAX  Counter
         ACCESS  read-write
         STATUS  mandatory
         DESCRIPTION
                 "Bit mask for loading ASR signalling on slots 1-14. The
                  MSBit represents slot 1, the next most significant bit
                  represents slot 2, and so forth."
        ::= { wfProtocols 86 }

     wfNHRPLoad OBJECT-TYPE
          SYNTAX Counter
          ACCESS read-write
          STATUS mandatory
          DESCRIPTION
                  "Bit mask for loading NHRP on slots 1-14. The MSBit
                   represents slot 1, the next most significant bit
                   represents slot 2, and so forth."
        ::= { wfProtocols 87 }

     wfAHBLoad OBJECT-TYPE
          SYNTAX Counter
          ACCESS read-write
          STATUS mandatory
          DESCRIPTION
                  "Bit mask for loading AHB on slots 1-14. The MSBit
                   represents slot 1, the next most significant bit
                   represents slot 2, and so forth."
        ::= { wfProtocols 88 }

     wfL2TPLoad OBJECT-TYPE
        SYNTAX  Counter
        ACCESS  read-write
        STATUS  mandatory
        DESCRIPTION
                "Bit mask for loading L2TP on slots 1-14. The MSBit
                represents slot 1, and so forth."
        ::= { wfProtocols 89 }

    wfISDBLoad OBJECT-TYPE
        SYNTAX  Counter
        ACCESS  read-write
        STATUS  mandatory
        DESCRIPTION
                "Bit mask for loading ISDB on slots 1-14. The
                MSBit represents slot 1, the next most significant bit
                represents slot 2, and so forth."
        ::= { wfProtocols 90 }

     wfVCCTLoad OBJECT-TYPE
          SYNTAX Counter
          ACCESS read-write
          STATUS mandatory
          DESCRIPTION
                  "Bit mask for loading VCCT on slots 1-14. The MSBit
                   represents slot 1, the next most significant bit
                   represents slot 2, and so forth."
        ::= { wfProtocols 91 }

     wfMpsLoad OBJECT-TYPE
        SYNTAX  Counter
        ACCESS  read-write
        STATUS  mandatory
        DESCRIPTION
                "Bit mask for loading MPOA Server on slots 1-14. The
                MSBit represents slot 1, the next most significant bit
                represents slot 2, and so forth."
        ::= { wfProtocols 92 }

     wfTAG1QLoad OBJECT-TYPE
        SYNTAX  Counter
        ACCESS  read-write
        STATUS  mandatory
        DESCRIPTION
             "Bit mask for loading TAG1Q (802.1q) on slots 1-14. The
             MSBit represents slot 1, the next most significant bit
             represents slot 2, and so forth."
        ::= { wfProtocols 93 }

     wfMpcLoad OBJECT-TYPE
        SYNTAX  Counter
        ACCESS  read-write
        STATUS  mandatory
        DESCRIPTION
                "Bit mask for loading MPOA Client on slots 1-14. The
                MSBit represents slot 1, the next most significant bit
                represents slot 2, and so forth."
        ::= { wfProtocols 94 }

    wfDVSLoad OBJECT-TYPE
	SYNTAX  Counter
	ACCESS  read-write
	STATUS  mandatory
	DESCRIPTION
		"Bit mask for loading DVS on slots 1-14. The
                MSBit represents slot 1, the next most significant bit
                represents slot 2, and so forth."
        ::= { wfProtocols 95 }

    wfVRRPLoad OBJECT-TYPE
        SYNTAX  Counter
        ACCESS  read-write
        STATUS  mandatory
        DESCRIPTION
                "Bit mask for loading VRRP on slots 1-14. The MSBit
                represents slot 1, and so forth."
        ::= { wfProtocols 96 }

     wfDHCPLoad OBJECT-TYPE
          SYNTAX Counter
          ACCESS read-write
          STATUS mandatory
          DESCRIPTION
                  "Bit mask for loading DHCP on slots 1-14. The MSBit
                   represents slot 1, the next most significant bit
                   represents slot 2, and so forth."
        ::= { wfProtocols 97  }

    wfCAPILoad OBJECT-TYPE
        SYNTAX Counter
        ACCESS read-write
        STATUS mandatory
        DESCRIPTION
                "Bit mask for loading CAPI on slots 1-14.
                 The MSBit represents slot 1, the next most significant bit
                 represents slot 2, and so forth."
        ::= { wfProtocols 98 }

    wfIPSECLoad OBJECT-TYPE
        SYNTAX Counter
        ACCESS read-write
        STATUS mandatory
        DESCRIPTION
                "Bit mask for loading IPSec on slots 1-14.
                 The MSBit represents slot 1, the next most significant bit
                 represents slot 2, and so forth."
        ::= { wfProtocols 99 }

     wfMplsLdpLoad OBJECT-TYPE
        SYNTAX  Counter
        ACCESS  read-write
        STATUS  mandatory
        DESCRIPTION
             "Bit mask for loading MPLS LDP module on slots 1-14. The
             MSBit represents slot 1, the next most significant bit
             represents slot 2, and so forth."
        ::= { wfProtocols 100 }

     wfMplsMlmLoad OBJECT-TYPE
        SYNTAX  Counter
        ACCESS  read-write
        STATUS  mandatory
        DESCRIPTION
             "Bit mask for loading MPLS MLM module on slots 1-14. The
             MSBit represents slot 1, the next most significant bit
             represents slot 2, and so forth."
        ::= { wfProtocols 101 }

    wfBacPktGenLoad OBJECT-TYPE
        SYNTAX  Counter
        ACCESS  read-write
        STATUS  mandatory
        DESCRIPTION
               "Bit mask for loading Bac PktGen on slot 1-14.  The MSBit represents
		slot 1, the next most significant bit represents slot 2,
		and so forth."
       ::= { wfProtocols 102 }

    wfIISISLoad OBJECT-TYPE
        SYNTAX  Counter
        ACCESS  read-write
        STATUS  mandatory
        DESCRIPTION
                "Bit mask for loading IISIS on slots 1-14. The
                MSBit represents slot 1, the next most significant bit
                represents slot 2, and so forth."
        ::= { wfProtocols 103 }

    wfCopsCLoad OBJECT-TYPE
        SYNTAX  Counter
        ACCESS  read-write
        STATUS  mandatory
        DESCRIPTION
             "Bit mask for loading COPS Client on slots 1-14. The
             MSBit represents slot 1, the next most significant bit
             represents slot 2, and so forth."
        ::= { wfProtocols 104 }

    wfDiffServLoad OBJECT-TYPE
        SYNTAX  Counter
        ACCESS  read-write
        STATUS  mandatory
        DESCRIPTION
                "Bit mask for loading DiffServ on slots 1-14. The
                MSBit represents slot 1, the next most significant bit
                represents slot 2, and so forth."
        ::= { wfProtocols 105 }

     wfIKELoad OBJECT-TYPE
        SYNTAX  Counter
        ACCESS  read-write
        STATUS  mandatory
        DESCRIPTION
             "Bit mask for loading Internet Key Exchange(IKE) module on
              slots 1-14. The MSBit represents slot 1, the next most
              significant bit represents slot 2, and so forth."
        ::= { wfProtocols 106 }

    wfDsqmsProxyLoad OBJECT-TYPE
        SYNTAX  Counter
        ACCESS  read-write
        STATUS  mandatory
        DESCRIPTION
             "Bit mask for loading DSQMS Proxy on slots 1-14. The
             MSBit represents slot 1, the next most significant bit
             represents slot 2, and so forth."
        ::= { wfProtocols 107 }


    wfLinkModules       OBJECT IDENTIFIER ::= { wfSoftwareConfig 2 }

    wfENETIILoad OBJECT-TYPE
        SYNTAX  Counter
        ACCESS  read-write
        STATUS  mandatory
        DESCRIPTION
                "Bit mask for loading the Ethernet II driver on slots 1-14. The
                MSBit represents slot 1, the next most significant bit
                represents slot 2, and so forth."
        ::= { wfLinkModules 1 }

    wfQENETLoad OBJECT-TYPE
        SYNTAX  Counter
        ACCESS  read-write
        STATUS  mandatory
        DESCRIPTION
                "Bit mask for loading the Quad Ethernet driver on slots 1-14. The
                MSBit represents slot 1, the next most significant bit
                represents slot 2, and so forth."
        ::= { wfLinkModules 2 }

    wfFDDILoad OBJECT-TYPE
        SYNTAX  Counter
        ACCESS  read-write
        STATUS  mandatory
        DESCRIPTION
                "Bit mask for loading the FDDI driver on slots 1-14. The MSBit
                represents slot 1, the next most significant bit represents slot 2
                and so forth."
        ::= { wfLinkModules 3 }

    wfDSDELoad OBJECT-TYPE
        SYNTAX  Counter
        ACCESS  read-write
        STATUS  mandatory
        DESCRIPTION
                "Bit mask for loading the Dual Sync - Dual Enet driver on slots 1-14.
                The MSBit represents slot 1, the next most significant bit
                represents slot 2, and so forth."
        ::= { wfLinkModules 4 }

    wfDSDEIILoad OBJECT-TYPE
        SYNTAX  Counter
        ACCESS  read-write
        STATUS  mandatory
        DESCRIPTION
                "Bit mask for loading the Dual Sync - Dual Enet II driver on slots
                1-14.  The MSBit represents slot 1, the next most significant
                bit represents slot 2, and so forth."
        ::= { wfLinkModules 5 }

    wfQSYNCLoad OBJECT-TYPE
        SYNTAX  Counter
        ACCESS  read-write
        STATUS  mandatory
        DESCRIPTION
                "Bit mask for loading the Quad Sync driver on slots 1-14. The MSBit
                represents slot 1, the next most significant bit represents
                slot 2, and so forth."
        ::= { wfLinkModules 6 }

    wfDTLoad OBJECT-TYPE
        SYNTAX  Counter
        ACCESS  read-write
        STATUS  mandatory
        DESCRIPTION
                "Bit mask for loading the Dual Token driver on slots 1-14. The MSBit
                represents slot 1, the next most significant bit represents slot 2
                and so forth."
        ::= { wfLinkModules 7 }

    wfDSTLoad OBJECT-TYPE
        SYNTAX  Counter
        ACCESS  read-write
        STATUS  mandatory
        DESCRIPTION
                "Bit mask for loading the DST driver on slots 1-14. The MSBit
                represents slot 1, the next most significant bit represents slot 2
                and so forth."
        ::= { wfLinkModules 8 }

    wfT1IILoad OBJECT-TYPE
        SYNTAX  Counter
        ACCESS  read-write
        STATUS  mandatory
        DESCRIPTION
                "Bit mask for loading the T1 II driver on slots 1-14. The MSBit
                represents slot 1, the next most significant bit represents slot 2
                and so forth."
        ::= { wfLinkModules 9 }

    wfE1IILoad OBJECT-TYPE
        SYNTAX  Counter
        ACCESS  read-write
        STATUS  mandatory
        DESCRIPTION
                "Bit mask for loading the E1 II driver on slots 1-14. The MSBit
                represents slot 1, the next most significant bit represents slot 2
                and so forth."
        ::= { wfLinkModules 10 }

    wfHSSILoad OBJECT-TYPE
        SYNTAX  Counter
        ACCESS  read-write
        STATUS  mandatory
        DESCRIPTION
                "Bit mask for loading the HSSI driver on slots 1-14. The MSBit
                represents slot 1, the next most significant bit represents slot 2
                and so forth."
        ::= { wfLinkModules 11 }

    wfFNSDSELoad OBJECT-TYPE
        SYNTAX  Counter
        ACCESS  read-write
        STATUS  mandatory
        DESCRIPTION
                "Bit mask for loading the FNSDSE driver on slot 2 (FNES Only). The MSBit
                represents slot 1, the next most significant bit represents slot 2
                and so forth."
        ::= { wfLinkModules 12 }

    wfFNSDSDTLoad OBJECT-TYPE
        SYNTAX  Counter
        ACCESS  read-write
        STATUS  mandatory
        DESCRIPTION
                "Bit mask for loading the FNSDSDT driver on slot 2 (FNTS Only). The MSBit
                represents slot 1, the next most significant bit represents slot 2
                and so forth."
        ::= { wfLinkModules 13 }

    wfMCT1Load OBJECT-TYPE
        SYNTAX  Counter
        ACCESS  read-write
        STATUS  mandatory
        DESCRIPTION
                "Bit mask for loading the MCT1 driver on slots 1-14. The MSBit
                represents slot 1, the next most significant bit represents slot 2
                and so forth."
        ::= { wfLinkModules 14 }

    wfANLoad OBJECT-TYPE
        SYNTAX  Counter
        ACCESS  read-write
        STATUS  mandatory
        DESCRIPTION
                "Bit mask for loading the AN (AccessNode) driver. The MSBit represents slot 1,
                the next most significant bit represents slot 2 and so forth."
        ::= { wfLinkModules 15 }

    wfFNSDSETLoad OBJECT-TYPE
        SYNTAX  Counter
        ACCESS  read-write
        STATUS  mandatory
        DESCRIPTION
                "Bit mask for loading the FNSDSET (ie. Fibermux IN Special) driver on
                slot 2 (IN Only). The MSBit represents slot 1, the next most
                significant bit represents slot 2 and so forth."
        ::= { wfLinkModules 16 }

    wfMCT1E1Load OBJECT-TYPE
        SYNTAX  Counter
        ACCESS  read-write
        STATUS  mandatory
        DESCRIPTION
                "Bit mask for loading the MCT1/E1 driver on slots 1-14. The MSBit
                represents slot 1, the next most significant bit represents slot 2
                and so forth."
        ::= { wfLinkModules 17 }

    wfEFDDILoad OBJECT-TYPE
        SYNTAX  Counter
        ACCESS  read-write
        STATUS  mandatory
        DESCRIPTION
                "Bit mask for loading the EFDDI (ie. QENET/FDDI LANNET IN) module
                driver on slot 2 (IN Only)."
        ::= { wfLinkModules 18 }

    wfHLSLoad OBJECT-TYPE
        SYNTAX  Counter
        ACCESS  read-write
        STATUS  mandatory
        DESCRIPTION
                "Bit mask for loading the Hughes LAN Systems Module driver on
                slot 2 (IN Only)."
        ::= { wfLinkModules 19 }

    wfChipcomLoad OBJECT-TYPE
        SYNTAX  Counter
        ACCESS  read-write
        STATUS  mandatory
        DESCRIPTION
                "Bit mask for loading the Chipcom Module driver on
                slot 2 (IN Only)."
        ::= { wfLinkModules 20 }

    wfAtmcLoad OBJECT-TYPE
        SYNTAX  Counter
        ACCESS  read-write
        STATUS  mandatory
        DESCRIPTION
                "Bit mask for loading the ATMC driver on the ARE in slots 1-14.
                The MSBit represents slot 1, the next most significant bit
                represents slot 2 and so forth."
        ::= { wfLinkModules 21 }

    wfHDWANLMLoad OBJECT-TYPE
        SYNTAX  Counter
        ACCESS  read-write
        STATUS  mandatory
        DESCRIPTION
                "Bit mask for loading the hdwanlm module driver on
                slots 1-14"
        ::= { wfLinkModules 22 }

    wfDE100Load OBJECT-TYPE
        SYNTAX  Counter
        ACCESS  read-write
        STATUS  mandatory
        DESCRIPTION
                "Bit mask for loading the DE100 (dual ethernet 100 MB) driver on
                slots 1-14. The MSBit represents slot 1, the next most significant
                bit represents slot 2 and so forth."
        ::= { wfLinkModules 23 }

    wfAtmc5000Load OBJECT-TYPE
        SYNTAX  Counter
        ACCESS  read-write
        STATUS  mandatory
        DESCRIPTION
                "Bit mask for loading the ATMC 5000 AH driver on the ARE in slots 1-14.
                slots 1-14. The MSBit represents slot 1, the next most significant
                bit represents slot 2 and so forth."
        ::= { wfLinkModules 24 }

    wfArnLoad  OBJECT-TYPE
        SYNTAX  Counter
        ACCESS  read-write
        STATUS  mandatory
        DESCRIPTION
                "Bit mask for loading the ARN Common Module driver.  This is a
                 single slot system so only the MSBit is supported."
        ::= { wfLinkModules 25 }

    wfFntsLoad OBJECT-TYPE
        SYNTAX Counter
        ACCESS read-write
        STATUS mandatory
        DESCRIPTION
                "Bit mask for loading the Fnts Module driver on
                slot 2 (IN Only)."
        ::= { wfLinkModules 26 }

    wfSQE100Load OBJECT-TYPE
        SYNTAX  Counter
        ACCESS  read-write
        STATUS  mandatory
        DESCRIPTION
                "Bit mask for loading the 100MB Ethernet Module driver on
                slots 1-14. The MSBit represents slot 1, the next most
                significant bit represents slot 2 and so forth."
        ::= { wfLinkModules 27 }

    wfGigEnetLoad OBJECT-TYPE
        SYNTAX  Counter
        ACCESS  read-write
        STATUS  mandatory
        DESCRIPTION
                "Bit mask for loading the Gigabit Ethernet Module driver on
                slots 1-14. The MSBit represents slot 1, the next most
                significant bit represents slot 2 and so forth."
        ::= { wfLinkModules 28 }
    wfFBRLoad  OBJECT-TYPE
        SYNTAX  Counter
        ACCESS  read-write
        STATUS  mandatory
        DESCRIPTION
                "Bit mask for loading the FBR Common Module driver.  This is a
                 single slot system so only the MSBit is supported."
        ::= { wfLinkModules 29 }


    wfDrivers   OBJECT IDENTIFIER ::= { wfSoftwareConfig 3 }

    wfLANCELoad OBJECT-TYPE
        SYNTAX  Counter
        ACCESS  read-write
        STATUS  mandatory
        DESCRIPTION
                "Bit mask for loading the LANCE chip driver on slots 1-14. The MSBit
                represents slot 1, the next most significant bit represents slot 2
                and so forth."
        ::= { wfDrivers 1 }

    wfILACCLoad OBJECT-TYPE
        SYNTAX  Counter
        ACCESS  read-write
        STATUS  mandatory
        DESCRIPTION
                "Bit mask for loading the ILACC chip driver on slots 1-14. The MSBit
                represents slot 1, the next most significant bit represents slot 2
                and so forth."
        ::= { wfDrivers 2 }

    wfFSILoad OBJECT-TYPE
        SYNTAX  Counter
        ACCESS  read-write
        STATUS  mandatory
        DESCRIPTION
                "Bit mask for loading the FDDI System Interface (FSI) chip driver on
                slots 1-14. The MSBit represents slot 1, the next most significant
                bit represents slot 2 and so forth. This attribute shall be used to
                configure the FSI chip driver on the appropriate slots for FDDI only
                (see wfHSSIFSILoad for other usage)."
        ::= { wfDrivers 3 }

    wfTMS380Load OBJECT-TYPE
        SYNTAX  Counter
        ACCESS  read-write
        STATUS  mandatory
        DESCRIPTION
                "Bit mask for loading the TMS380 chip driver on slots 1-14. The MSBit
                represents slot 1, the next most significant bit represents slot 2
                and so forth."
        ::= { wfDrivers 4 }

    wfMK5025Load OBJECT-TYPE
        SYNTAX  Counter
        ACCESS  read-write
        STATUS  mandatory
        DESCRIPTION
                "Bit mask for loading the MK5025 chip driver on slots 1-14. The MSBit
                represents slot 1, the next most significant bit represents slot 2
                and so forth."
        ::= { wfDrivers 5 }

    wfDS2180Load OBJECT-TYPE
        SYNTAX  Counter
        ACCESS  read-write
        STATUS  mandatory
        DESCRIPTION
                "Bit mask for loading the DS2180 chip driver on slots 1-14. The MSBit
                represents slot 1, the next most significant bit represents slot 2
                and so forth."
        ::= { wfDrivers 6 }

    wfDS2181Load OBJECT-TYPE
        SYNTAX  Counter
        ACCESS  read-write
        STATUS  mandatory
        DESCRIPTION
                "Bit mask for loading the DS2181 chip driver on slots 1-14. The MSBit
                represents slot 1, the next most significant bit represents slot 2
                and so forth."
        ::= { wfDrivers 7 }

    wfDEFALoad OBJECT-TYPE
        SYNTAX  Counter
        ACCESS  read-write
        STATUS  mandatory
        DESCRIPTION
                "Bit mask for loading the AM99C10 chip driver on slots 1-14. The MSBit
                represents slot 1, the next most significant bit represents slot 2
                and so forth. The AM99C10 chip is Content Addressable Memory (CAM)
                and the driver to control it is represented by this attribute. The
                generic name of this attribute shall be the Hardware Filter Driver
                which will also provide control of the Dual Ethernet Filter
                Accelerator (DEFA) chip."
        ::= { wfDrivers 8 }

    wfAMZ8530Load OBJECT-TYPE
        SYNTAX  Counter
        ACCESS  read-write
        STATUS  mandatory
        DESCRIPTION
                "Bit mask for loading the AMZ8530 chip driver on slots 1-14. The
                MSBit represents slot 1, the next most significant bit represents
                slot 2, and so forth."
        ::= { wfDrivers 9 }

    wfHSSIFSILoad OBJECT-TYPE
        SYNTAX  Counter
        ACCESS  read-write
        STATUS  mandatory
        DESCRIPTION
                "Bit mask for loading the HSSI FSI chip driver on slots 1-14. The
                MSBit represents slot 1, the next most significant bit represents
                slot 2, and so forth."
        ::= { wfDrivers 10 }

    wfMUNICHT1Load OBJECT-TYPE
        SYNTAX  Counter
        ACCESS  read-write
        STATUS  mandatory
        DESCRIPTION
                "Bit mask for loading the MUNICH chip driver on slots 1-14. The
                MSBit represents slot 1, the next most significant bit represents
                slot 2, and so forth. The MUNICH chip is used on the MCT1 and
                MCE1 link modules"
        ::= { wfDrivers 11 }

    wfQsccSyncLoad OBJECT-TYPE
        SYNTAX  Counter
        ACCESS  read-write
        STATUS  mandatory
        DESCRIPTION
                "Bit mask for loading the Sync QUICC chip driver on slots 1-14. The
                MSBit represents slot 1, the next most significant bit represents
                slot 2, and so forth."
        ::= { wfDrivers 12 }

    wfQsccEnetLoad OBJECT-TYPE
        SYNTAX  Counter
        ACCESS  read-write
        STATUS  mandatory
        DESCRIPTION
                "Bit mask for loading the Ethernet QUICC chip driver on slots 1-14. The
                MSBit represents slot 1, the next most significant bit represents
                slot 2, and so forth."
        ::= { wfDrivers 13 }

    wfMunichLoad OBJECT-TYPE
        SYNTAX  Counter
        ACCESS  read-write
        STATUS  mandatory
        DESCRIPTION
                "Bit mask for loading the T1/E1 MUNICH chip driver on slots 1-14. The
                MSBit represents slot 1, the next most significant bit represents
                slot 2, and so forth. The MUNICH chip is used on the MCT1 and
                MCE1 link modules"
        ::= { wfDrivers 14 }

    wfHilanceLoad OBJECT-TYPE
        SYNTAX  Counter
        ACCESS  read-write
        STATUS  mandatory
        DESCRIPTION
                "Bit mask for loading the Hilance driver for the ASN on slots 1-14. The
                MSBit represents slot 1, the next most significant bit represents
                slot 2, and so forth."
        ::= { wfDrivers 15 }

    wfAtmAlcLoad OBJECT-TYPE
        SYNTAX  Counter
        ACCESS  read-write
        STATUS  mandatory
        DESCRIPTION
                "Bit mask for loading the ATM Link Module driver for the FRE-2 on slots
                1-14. The MSBit represents slot 1, the next most significant bit represents
                slot 2, and so forth."
        ::= { wfDrivers 16 }

    wfRptrLoad OBJECT-TYPE
        SYNTAX  Counter
        ACCESS  read-write
        STATUS  mandatory
        DESCRIPTION
                "Bit mask for loading the AN 802.3 driver on slot 1 - MSB represents slot 1
                - Only valid slot"
        ::= { wfDrivers 17 }

    wfIsacLoad OBJECT-TYPE
        SYNTAX  Counter
        ACCESS  read-write
        STATUS  mandatory
        DESCRIPTION
                "Bit mask for loading the ISAC D Channel chip driver on slots 1-14. The
                MSBit represents slot 1, the next most significant bit represents
                slot 2, and so forth."
        ::= { wfDrivers 18 }

    wfAtmizerLoad OBJECT-TYPE
        SYNTAX  Counter
        ACCESS  read-write
        STATUS  mandatory
        DESCRIPTION
                "Bit mask for loading the ATMizer driver for the ARE on slots 1-14. The
                MSBit represents slot 1, the next most significant bit represents slot 2,
                and so forth."
        ::= { wfDrivers 19 }

    wfNSC100MLoad OBJECT-TYPE
        SYNTAX  Counter
        ACCESS  read-write
        STATUS  mandatory
        DESCRIPTION
                "Bit mask for loading the National Semiconductor DP83810 driver on
                slots 1-14. The MSBit represents slot 1, the next most significant bit
                represents slot 2, and so forth."
        ::= { wfDrivers 20 }

    wfDCMMWLoad OBJECT-TYPE
        SYNTAX  Counter
        ACCESS  read-write
        STATUS  mandatory
        DESCRIPTION
                "Bit mask for loading the DCMMW on slot 1.
                The MSBit represents slot 1."
        ::= { wfDrivers 21 }

    wfHwCompLoad OBJECT-TYPE
        SYNTAX  Counter
        ACCESS  read-write
        STATUS  mandatory
        DESCRIPTION
                "Bit mask for loading the Hardware Compression driver on slots 1-14. The
                MSBit represents slot 1, the next most significant bit represents
                slot 2, and so forth."
        ::= { wfDrivers 22 }

    wfRAEsaLoad OBJECT-TYPE
        SYNTAX  Counter
        ACCESS  read-write
        STATUS  mandatory
        DESCRIPTION
                "Bit mask for loading RAESA on slots 1-14.
                The MSBit represents slot 1, and so forth."
       ::= { wfDrivers 23 }

    wfFntsAtmLoad OBJECT-TYPE
        SYNTAX Counter
        ACCESS read-write
        STATUS mandatory
         DESCRIPTION
                "Bit mask for loading the Fnts Atm driver for the FNTS on slots 1-14. The
                 MSBit represents slot 1, the next most significant bit represents
                slot 2, and so forth."
        ::= { wfDrivers 24 }

    wfRMONStatLoad OBJECT-TYPE
        SYNTAX  Counter
        ACCESS  read-write
        STATUS  mandatory
        DESCRIPTION
               "Bit mask for loading RMONSTAT on slot 1.
                The MSBit represents slot 1."

       ::= { wfDrivers 25 }

    wfSEEQ100MLoad OBJECT-TYPE
        SYNTAX  Counter
        ACCESS  read-write
        STATUS  mandatory
        DESCRIPTION
                "Bit mask for loading the SEEQ 100MB Ethernet driver on
                slots 1-14. The MSBit represents slot 1, the next most
                significant bit represents slot 2, and so forth."
        ::= { wfDrivers 26 }

    wfSeeqGigLoad OBJECT-TYPE
        SYNTAX  Counter
        ACCESS  read-write
        STATUS  mandatory
        DESCRIPTION
                "Bit mask for loading the SEEQ Gigabit Ethernet driver on
                slots 1-14. The MSBit represents slot 1, the next most
                significant bit represents slot 2, and so forth."
        ::= { wfDrivers 27 }
    wfPQ2EnetLoad OBJECT-TYPE
        SYNTAX  Counter
        ACCESS  read-write
        STATUS  mandatory
        DESCRIPTION
               "Bit mask for loading PQ2 Enet on slot 1.
                The MSBit represents slot 1."

       ::= { wfDrivers 28 }

    wfTdmManagerLoad OBJECT-TYPE
        SYNTAX  Counter
        ACCESS  read-write
        STATUS  mandatory
        DESCRIPTION
               "Bit mask for loading TDM Manager on slot 1.
                The MSBit represents slot 1."

       ::= { wfDrivers 29 }

    wfPQ2DsyncLoad OBJECT-TYPE
        SYNTAX  Counter
        ACCESS  read-write
        STATUS  mandatory
        DESCRIPTION
               "Bit mask for loading DSYNC PMC driver on slot 1.
                The MSBit represents slot 1."

       ::= { wfDrivers 30 }

    wfVoIPLoad OBJECT-TYPE
        SYNTAX  Counter
        ACCESS  read-write
        STATUS  mandatory
        DESCRIPTION
               "Bit mask for loading T1/E1 DUAL PMC driver on slot 1.
                The MSBit represents slot 1."

       ::= { wfDrivers 31 }



    wfQsccVoIPLoad OBJECT-TYPE
        SYNTAX  Counter
        ACCESS  read-write
        STATUS  mandatory
        DESCRIPTION
                "Bit mask for loading the VoIP QUICC chip driver on slots 1-14.
                 The MSBit represents slot 1, the next most significant bit 
                 represent s slot 2, and so forth."
        ::= { wfDrivers 32 }


    END  -- Wellfleet-LOADER-MIB
