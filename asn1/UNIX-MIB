UNIX-MIB DEFINITIONS ::= BEGIN

	IMPORTS
        	experimental
			FROM RFC1155-SMI
	        OBJECT-TYPE
			FROM RFC-1212;

-- Defined below is the main UNIX MIB tree

	host  	OBJECT IDENTIFIER ::= { experimental 999 }

--
--  conformance groups 
--

	machine	      OBJECT IDENTIFIER	::= { host 1}
	network	      OBJECT IDENTIFIER	::= { host 2}
	processor     OBJECT IDENTIFIER	::= { host 3}
	adapter	      OBJECT IDENTIFIER	::= { host 4}
	controller    OBJECT IDENTIFIER	::= { host 5}
	printer	      OBJECT IDENTIFIER	::= { host 6}
	disk	      OBJECT IDENTIFIER	::= { host 7}
	diskPartition OBJECT IDENTIFIER	::= { host 8}
	tape          OBJECT IDENTIFIER	::= { host 9}
	queue         OBJECT IDENTIFIER	::= { host 10}
	group         OBJECT IDENTIFIER	::= { host 11}
	user          OBJECT IDENTIFIER	::= { host 12}
	installedsw   OBJECT IDENTIFIER	::= { host 13}
	license       OBJECT IDENTIFIER	::= { host 14}
	filesystem    OBJECT IDENTIFIER	::= { host 15}
	mountinfo     OBJECT IDENTIFIER	::= { host 16}

--
-- The machine group
--

	machineOsType OBJECT-TYPE
		SYNTAX OCTET STRING
		ACCESS read-only
		STATUS mandatory
		DESCRIPTION
			"The operating system that the agent is running on"
	::= { machine 1 }

	machineName OBJECT-TYPE
		SYNTAX OCTET STRING
		ACCESS read-only
		STATUS mandatory
		DESCRIPTION
			"The name of the machine "
	::= { machine 2 }


	machineTime OBJECT-TYPE
		SYNTAX OCTET STRING
		ACCESS read-only
		STATUS mandatory
		DESCRIPTION
			"The time the machine was queried"
	::= { machine 3 }

	machineOsVersion OBJECT-TYPE
		SYNTAX OCTET STRING
		ACCESS read-only
		STATUS mandatory
		DESCRIPTION
			"The operating system version of the machine"
	::= { machine 4 }

	machineBootRoot OBJECT-TYPE
		SYNTAX OCTET STRING
		ACCESS read-only
		STATUS mandatory
		DESCRIPTION
			"The boot root of the machine"
	::= { machine 5 }

	machineBootTime OBJECT-TYPE
		SYNTAX OCTET STRING
		ACCESS read-only
		STATUS mandatory
		DESCRIPTION
			"The boot time of the machine"
	::= { machine 6 }

	machineHwModel OBJECT-TYPE
		SYNTAX OCTET STRING
		ACCESS read-only
		STATUS mandatory
		DESCRIPTION
			"The model name of the machine"
	::= { machine 7 }

	machineHwType OBJECT-TYPE
		SYNTAX OCTET STRING
		ACCESS read-only
		STATUS mandatory
		DESCRIPTION
			"The hardware type of the machine"
	::= { machine 8 }

	machineHwVersion OBJECT-TYPE
		SYNTAX OCTET STRING
		ACCESS read-only
		STATUS mandatory
		DESCRIPTION
			"The hardware version of the machine"
	::= { machine 9 }

	machineVendor OBJECT-TYPE
		SYNTAX OCTET STRING
		ACCESS read-only
		STATUS mandatory
		DESCRIPTION
			"The hardware vendor of the machine"
	::= { machine 10 }

	machineMemorySize OBJECT-TYPE
		SYNTAX INTEGER
		ACCESS read-only
		STATUS mandatory
		DESCRIPTION
			"The memory of the machine"
	::= { machine 10 }
--
-- The network table
--
	networkTable OBJECT-TYPE
		      SYNTAX SEQUENCE OF NetworkEntry
		      ACCESS not-accessible
		      STATUS mandatory
		      DESCRIPTION
			"This table describes the network"
	::= { host 2 }

	networkEntry OBJECT-TYPE
		SYNTAX NetworkEntry
		ACCESS not-accessible
		STATUS mandatory
		DESCRIPTION
			"An entry in the network table"
		INDEX { networkIndex }
	::= { networkTable 1 }

	NetworkEntry ::= SEQUENCE {
		networkIndex 
			INTEGER,     
		networkAddress
			OCTET STRING,
		networkNodeName 
			OCTET STRING,
		networkType    
			OCTET STRING
	}

	networkIndex OBJECT-TYPE
		SYNTAX OCTET STRING
		ACCESS read-only
		STATUS mandatory
		DESCRIPTION
			"The index "
	::= { networkEntry 1 }

	networkAddress OBJECT-TYPE
		SYNTAX OCTET STRING
		ACCESS read-only
		STATUS mandatory
		DESCRIPTION
			"The network address of the machine"
	::= { networkEntry 2 }

	networkNodeName OBJECT-TYPE
		SYNTAX OCTET STRING
		ACCESS read-only
		STATUS mandatory
		DESCRIPTION
			"The name of the machine as defined in the protocol"
	::= { networkEntry 3 }

	networkType OBJECT-TYPE
		SYNTAX OCTET STRING
		ACCESS read-only
		STATUS mandatory
		DESCRIPTION
			"The protocol of the network"
	::= { networkEntry 4 }

--
-- The processor table
--
	processorTable OBJECT-TYPE
		SYNTAX SEQUENCE OF ProcessorEntry
		ACCESS not-accessible
		STATUS mandatory
		DESCRIPTION
			"This table describes the processor"
	::= { host  3 }

	processorEntry OBJECT-TYPE
		SYNTAX ProcessorEntry
		ACCESS not-accessible
		STATUS mandatory
		DESCRIPTION
			"An entry in the processor table"
		INDEX { processorIndex }
	::= { processorTable 1 }

	ProcessorEntry ::= SEQUENCE {
		processorIndex 
			INTEGER,     
		processorNumber
			INTEGER,     
		processorActiveState
			INTEGER,
		processorPrimary
			INTEGER
	}

	processorIndex OBJECT-TYPE
		SYNTAX OCTET STRING
		ACCESS read-only
		STATUS mandatory
		DESCRIPTION
			"The index "
	::= { processorEntry 1 }

	processorActiveState OBJECT-TYPE
		SYNTAX INTEGER
		ACCESS read-only
		STATUS mandatory
		DESCRIPTION
			"The state of processor"
	::= { processorEntry 2 }

	processorPrimary OBJECT-TYPE
		SYNTAX OCTET STRING
		ACCESS read-only
		STATUS mandatory
		DESCRIPTION
			"whether the processor is primary"
	::= { processorEntry 3 }

--
-- The adapter table
--
	adapterTable OBJECT-TYPE
		SYNTAX SEQUENCE OF AdapterEntry
		ACCESS not-accessible
		STATUS mandatory
		DESCRIPTION
			"This table describes the adapters"
	::= { host 4 }

	adapterEntry OBJECT-TYPE
		SYNTAX AdapterEntry
		ACCESS not-accessible
		STATUS mandatory
		DESCRIPTION
			"An entry in the adapter table"
		INDEX { adapterIndex }
	::= { adapterTable 1 }

	AdapterEntry ::= SEQUENCE {
		adapterIndex 
			INTEGER,     
		adapterName
			INTEGER,     
		adapterUnitNumber
			INTEGER,
		adapterNexusNumber
			INTEGER,
		adapterRevLevel
			OCTET STRING
	}

	adapterIndex OBJECT-TYPE
		SYNTAX INTEGER
		ACCESS read-only
		STATUS mandatory
		DESCRIPTION
			"The index "
	::= { adapterEntry 1 }

	adapterName OBJECT-TYPE
		SYNTAX OCTET STRING
		ACCESS read-only
		STATUS mandatory
		DESCRIPTION
			"The name of the adapter"
	::= { adapterEntry 2 }

	adapterType OBJECT-TYPE
		SYNTAX OCTET STRING
		ACCESS read-only
		STATUS mandatory
		DESCRIPTION
			"The type of the adapter"
	::= { adapterEntry 3 }

	adapterUnitNumber OBJECT-TYPE
		SYNTAX INTEGER
		ACCESS read-only
		STATUS mandatory
		DESCRIPTION
			"The unit number of the adapter"
	::= { adapterEntry 4 }

	adapterNexusNumber OBJECT-TYPE
		SYNTAX INTEGER
		ACCESS read-only
		STATUS mandatory
		DESCRIPTION
			"The nexus number of the adapter"
	::= { adapterEntry 5 }

	adapterRevLevel OBJECT-TYPE
		SYNTAX OCTET STRING
		ACCESS read-only
		STATUS mandatory
		DESCRIPTION
			"The revision level of the adapter"
	::= { adapterEntry 5 }

--
-- The controller table
--
	controllerTable OBJECT-TYPE
		SYNTAX SEQUENCE OF ControllerEntry
		ACCESS not-accessible
		STATUS mandatory
		DESCRIPTION
			"This table describes the controller"
	::= { host 5 }

	controllerEntry OBJECT-TYPE
		SYNTAX ControllerEntry
		ACCESS not-accessible
		STATUS mandatory
		DESCRIPTION
			"An entry in the controller table"
		INDEX { controllerIndex }
	::= { controllerTable 1 }

	ControllerEntry ::= SEQUENCE {
		controllerIndex 
			INTEGER,     
		controllerName
			OCTET STRING,     
		controllerType 
			OCTET STRING,
		controllerUnitNumber 
			INTEGER
	}

	controllerIndex OBJECT-TYPE
		SYNTAX INTEGER
		ACCESS read-only
		STATUS mandatory
		DESCRIPTION
			"The index "
	::= { controllerEntry 1 }

	controllerName OBJECT-TYPE
		SYNTAX OCTET STRING
		ACCESS read-only
		STATUS mandatory
		DESCRIPTION
			"The name of the controller"
	::= { controllerEntry 2 }

	controllerType OBJECT-TYPE
		SYNTAX OCTET STRING
		ACCESS read-only
		STATUS mandatory
		DESCRIPTION
			"The type of the controller"
	::= { controllerEntry 3 }

	controllerUnitNumber OBJECT-TYPE
		SYNTAX INTEGER
		ACCESS read-only
		STATUS mandatory
		DESCRIPTION
			"The unit number of the controller"
	::= { controllerEntry 4 }

--
-- The printer table
--
	printerTable OBJECT-TYPE
		SYNTAX SEQUENCE OF PrinterEntry
		ACCESS not-accessible
		STATUS mandatory
		DESCRIPTION
			"This table describes the printer"
	::= { host 6 }

	printerEntry OBJECT-TYPE
		SYNTAX PrinterEntry
		ACCESS not-accessible
		STATUS mandatory
		DESCRIPTION
			"An entry in the printer table"
		INDEX { printerIndex }
	::= { printerTable 1 }

	PrinterEntry ::= SEQUENCE {
		printerIndex 
			INTEGER,     
		printerName
			OCTET STRING,     
		printerQueue
		       OCTET STRING,
		printerDeviceDriver
		       OCTET STRING,
		printerDeviceType
		       OCTET STRING,
		printerUnitNumber 
			INTEGER
	}

	printerIndex OBJECT-TYPE
		SYNTAX INTEGER
		ACCESS read-only
		STATUS mandatory
		DESCRIPTION
			"The index "
	::= { printerEntry 1 }

	printerName OBJECT-TYPE
		SYNTAX OCTET STRING
		ACCESS read-only
		STATUS mandatory
		DESCRIPTION
			"The name of the printer"
	::= { printerEntry 2 }

	printerQueue OBJECT-TYPE
		SYNTAX OCTET STRING
		ACCESS read-only
		STATUS mandatory
		DESCRIPTION
			"The queue of the printer"
	::= { printerEntry 3 }

	printerDeviceDriver OBJECT-TYPE
		SYNTAX OCTET STRING
		ACCESS read-only
		STATUS mandatory
		DESCRIPTION
			"The device driver of the printer"
	::= { printerEntry 4 }

	printerDeviceType OBJECT-TYPE
		SYNTAX OCTET STRING
		ACCESS read-only
		STATUS mandatory
		DESCRIPTION
			"The device type of the printer"
	::= { printerEntry 5 }

	printerUnitNumber OBJECT-TYPE
		SYNTAX INTEGER
		ACCESS read-only
		STATUS mandatory
		DESCRIPTION
			"The unit number of the printer"
	::= { printerEntry 6 }

--
-- The disk table
--
	diskTable OBJECT-TYPE
		SYNTAX SEQUENCE OF DiskEntry
		ACCESS not-accessible
		STATUS mandatory
		DESCRIPTION
			"This table describes the disks"
	::= { host 7 }

	diskEntry OBJECT-TYPE
		SYNTAX DiskEntry
		ACCESS not-accessible
		STATUS mandatory
		DESCRIPTION
			"An entry in the disk table"
		INDEX { diskIndex }
	::= { diskTable 1 }

	DiskEntry ::= SEQUENCE {
		diskIndex 
			INTEGER,     
		diskDeviceName
			OCTET STRING,     
		diskPrimaryHost
			OCTET STRING,     
		diskUnitNumber
			OCTET STRING,     
		diskDeviceType
			OCTET STRING,     
		diskDeviceDriver
			OCTET STRING,     
		diskPhysicalCapacity 
			INTEGER     
	}

	diskIndex OBJECT-TYPE
		SYNTAX INTEGER
		ACCESS read-only
		STATUS mandatory
		DESCRIPTION
			"The index "
	::= { diskEntry 1 }

	diskDeviceName OBJECT-TYPE
		SYNTAX OCTET STRING
		ACCESS read-only
		STATUS mandatory
		DESCRIPTION
			"The name of the disk"
	::= { diskEntry 2 }

	diskPrimaryHost OBJECT-TYPE
		SYNTAX OCTET STRING
		ACCESS read-only
		STATUS mandatory
		DESCRIPTION
			"The primary host of the disk"
	::= { diskEntry 3 }

	diskUnitNumber OBJECT-TYPE
		SYNTAX INTEGER
		ACCESS read-only
		STATUS mandatory
		DESCRIPTION
			"The unit number of the disk"
	::= { diskEntry 4 }

	diskDeviceDriver OBJECT-TYPE
		SYNTAX OCTET STRING
		ACCESS read-only
		STATUS mandatory
		DESCRIPTION
			"The device driver of the disk"
	::= { diskEntry 5 }

	diskDeviceType OBJECT-TYPE
		SYNTAX OCTET STRING
		ACCESS read-only
		STATUS mandatory
		DESCRIPTION
			"The device type of the disk"
	::= { diskEntry 6 }

	diskPhysicalCapacity OBJECT-TYPE
		SYNTAX INTEGER
		ACCESS read-only
		STATUS mandatory
		DESCRIPTION
			"The formatted capacity of the disk"
	::= { diskEntry 7 }

--
-- The disk partition table
--
	diskPartitionTable OBJECT-TYPE
		SYNTAX SEQUENCE OF DiskPartitionEntry
		ACCESS not-accessible
		STATUS mandatory
		DESCRIPTION
			"This table describes the disk partition"
	::= { host 8 }

	diskPartitionEntry OBJECT-TYPE
		SYNTAX DiskPartitionEntry
		ACCESS not-accessible
		STATUS mandatory
		DESCRIPTION
			"An entry in the disk table"
		INDEX { diskPartitionIndex }
	::= { diskPartitionTable 1 }

	DiskPartitionEntry ::= SEQUENCE {
		diskPartitonIndex 
			INTEGER,     
		diskPartitionName
			OCTET STRING,     
		diskPartitionPrimaryHost
			OCTET STRING,     
		diskPartitionUnitNumber
			INTEGER,     
		diskPartitionStartSector
			INTEGER,     
		diskPartitionEndSector
			INTEGER     
	}

	diskPartitionIndex OBJECT-TYPE
		SYNTAX INTEGER
		ACCESS read-only
		STATUS mandatory
		DESCRIPTION
			"The index "
	::= { diskPartitionEntry 1 }

	diskPartitionName OBJECT-TYPE
		SYNTAX OCTET STRING
		ACCESS read-only
		STATUS mandatory
		DESCRIPTION
			"The name of the disk partition"
	::= { diskPartitionEntry 2 }

	diskPartitionPrimaryHost OBJECT-TYPE
		SYNTAX OCTET STRING
		ACCESS read-only
		STATUS mandatory
		DESCRIPTION
			"The primary host of the disk partition"
	::= { diskPartitionEntry 3 }

	diskPartitionSize OBJECT-TYPE
		SYNTAX INTEGER
		ACCESS read-only
		STATUS mandatory
		DESCRIPTION
			"The size of the disk partition"
	::= { diskPartitionEntry 4 }

	diskPartitionDeviceName OBJECT-TYPE
		SYNTAX OCTET STRING
		ACCESS read-only
		STATUS mandatory
		DESCRIPTION
			"The device  of the disk partition"
	::= { diskPartitionEntry 5 }

	diskPartitionStartSector OBJECT-TYPE
		SYNTAX INTEGER
		ACCESS read-only
		STATUS mandatory
		DESCRIPTION
			"The start sector of the disk partition"
	::= { diskPartitionEntry 6 }

	diskPartitionEndSector OBJECT-TYPE
		SYNTAX INTEGER
		ACCESS read-only
		STATUS mandatory
		DESCRIPTION
			"The end sector of the diskPartition"
	::= { diskPartitionEntry 7 }

--
-- The tape table
--
	tapeTable OBJECT-TYPE
		SYNTAX SEQUENCE OF TapeEntry
		ACCESS not-accessible
		STATUS mandatory
		DESCRIPTION
			"This table describes the tapes"
	::= { host 9 }

	tapeEntry OBJECT-TYPE
		SYNTAX TapeEntry
		ACCESS not-accessible
		STATUS mandatory
		DESCRIPTION
			"An entry in the tape table"
		INDEX { tapeIndex }
	::= { tapeTable 1 }

	TapeEntry ::= SEQUENCE {
		tapeIndex
			INTEGER,
 		tapeDeviceName
			OCTET STRING,
		tapeUnitNumber
			INTEGER,
		tapeDeviceDriver
			OCTET STRING,
		tapeDeviceType
			OCTET STRING,
		tapeMountPoint
			OCTET STRING
	}

	tapeIndex OBJECT-TYPE
		SYNTAX OCTET STRING
		ACCESS read-only
		STATUS mandatory
		DESCRIPTION
			"The index"
	::= { tapeEntry 1 }

	tapeDeviceName OBJECT-TYPE
		SYNTAX OCTET STRING
		ACCESS read-only
		STATUS mandatory
		DESCRIPTION
			"The name of the tape"
	::= { tapeEntry 2 }

	tapeTapeUnitNumber	OBJECT-TYPE
		SYNTAX INTEGER
		ACCESS read-only
		STATUS mandatory
		DESCRIPTION
			"The unit number of the tape"
	::= { tapeEntry 4 }

	tapeDeviceDriver	OBJECT-TYPE
		SYNTAX OCTET STRING
		ACCESS read-only
		STATUS mandatory
		DESCRIPTION
			"The Device driver of the tape"
	::= { tapeEntry 5 }

	tapeDeviceType	OBJECT-TYPE
		SYNTAX OCTET STRING
		ACCESS read-only
		STATUS mandatory
		DESCRIPTION
			"The Device type of the tape"
	::= { tapeEntry 6 }

	tapeMountPoint 	OBJECT-TYPE
		SYNTAX OCTET STRING
		ACCESS read-only
		STATUS mandatory
		DESCRIPTION
			"The mount status of tape"
	::= { tapeEntry 7 }
--
-- The queue table
--
	queueTable OBJECT-TYPE
		SYNTAX SEQUENCE OF QueueEntry
		ACCESS not-accessible
		STATUS mandatory
		DESCRIPTION
			"This table describes the queue"
	::= { host 10 }

	queueEntry OBJECT-TYPE
		SYNTAX QueueEntry
		ACCESS not-accessible
		STATUS mandatory
		DESCRIPTION
			"An entry in the queue table"
		INDEX { queueIndex }
	::= { queueTable 1 }

	QueueEntry ::= SEQUENCE {
		queueIndex
			INTEGER,
		queueName
			OCTET STRING,
		queueType
			OCTET STRING,
		queueState
			OCTET STRING,
 		queueDestinationList
			OCTET STRING,
		queueCapacity
			INTEGER,
		queuePriority
			INTEGER,
		queueProtection
			OCTET STRING,
		queueUserComment
			OCTET STRING,
		queuePrintServer
			OCTET STRING
	}

	queueIndex OBJECT-TYPE
		SYNTAX INTEGER
		ACCESS read-only
		STATUS mandatory
		DESCRIPTION
			"The Index"
	::= { queueEntry 1 }

	queueName OBJECT-TYPE
		SYNTAX OCTET STRING
		ACCESS read-only
		STATUS mandatory
		DESCRIPTION
			"The Name of the queue"
	::= { queueEntry 2 }

	queueType OBJECT-TYPE
		SYNTAX OCTET STRING
		ACCESS read-only
		STATUS mandatory
		DESCRIPTION
			"The Type of the queue"
	::= { queueEntry 3 }

	queueState	OBJECT-TYPE
		SYNTAX INTEGER
		ACCESS read-only
		STATUS mandatory
		DESCRIPTION
			"The state of the queue - runnable, stopped, halted" 
	::= { queueEntry 4 }

	queueDestinationList	OBJECT-TYPE
		SYNTAX OCTET STRING
		ACCESS read-only
		STATUS mandatory
		DESCRIPTION
			"The Destination list of the queue "
	::= { queueEntry 5 }

	queueCapacity	OBJECT-TYPE
		SYNTAX OCTET STRING
		ACCESS read-only
		STATUS mandatory
		DESCRIPTION
			"The capacity of the queue"
	::= { queueEntry 6 }

	queuePriority	OBJECT-TYPE
		SYNTAX OCTET STRING
		ACCESS read-only
		STATUS mandatory
		DESCRIPTION
			"The Priority of the queue"
	::= { queueEntry 7 }

	queueProtection	OBJECT-TYPE
		SYNTAX INTEGER
		ACCESS read-only
		STATUS mandatory
		DESCRIPTION
			"The protection of the queue"
	::= { queueEntry 8 }

	queueUserComment	OBJECT-TYPE
		SYNTAX OCTET STRING
		ACCESS read-only
		STATUS mandatory
		DESCRIPTION
			"The user comment of the queue"
	::= { queueEntry 9 }

	queuePrintServer	OBJECT-TYPE
		SYNTAX OCTET STRING
		ACCESS read-only
		STATUS mandatory
		DESCRIPTION
			"The print server of the queue"
	::= { queueEntry 10 }


--
-- The group table
--
	groupTable OBJECT-TYPE
		SYNTAX SEQUENCE OF GroupEntry
		ACCESS not-accessible
		STATUS mandatory
		DESCRIPTION
			"This table describes the swGroup "
	::= { host 11 }

	groupEntry OBJECT-TYPE
		SYNTAX GroupEntry
		ACCESS not-accessible
		STATUS mandatory
		DESCRIPTION
			"An entry in the group table"
		INDEX { groupIndex }
	::= { groupTable 1 }

	GroupEntry ::= SEQUENCE {
		groupIndex
			INTEGER,
		groupId
			OCTET STRING,
		groupName
			OCTET STRING
	}

	groupIndex OBJECT-TYPE
		SYNTAX OCTET STRING
		ACCESS read-only
		STATUS mandatory
		DESCRIPTION
			"The index of the group"
	::= { groupEntry 1 }

	groupId	OBJECT-TYPE
		SYNTAX OCTET STRING
		ACCESS read-only
		STATUS mandatory
		DESCRIPTION
			"The Id of the group"
	::= { groupEntry 2 }

	groupName	OBJECT-TYPE
		SYNTAX OCTET STRING
		ACCESS read-only
		STATUS mandatory
		DESCRIPTION
			"The name of the group"
	::= { groupEntry 3 }

--
-- The User table
--
	
	userTable OBJECT-TYPE
		SYNTAX SEQUENCE OF UserEntry
		ACCESS not-accessible
		STATUS mandatory
		DESCRIPTION
			"This table describes the User"
	::= { host 12 }

	userEntry OBJECT-TYPE
		SYNTAX UserEntry
		ACCESS not-accessible
		STATUS mandatory
		DESCRIPTION
			"An entry in the user table"
		INDEX { userIndex }
	::= { userTable 1 }

	UserEntry ::= SEQUENCE {
		userIndex
			INTEGER,
		userOsType
			OCTET STRING,
		userName
			OCTET STRING,
		userId
			OCTET STRING,
 		userFullName
			OCTET STRING,
		userLoginShellCli
			OCTET STRING,
		userLoginDirectory
			OCTET STRING
	}


	userIndex OBJECT-TYPE
		SYNTAX INTEGER
		ACCESS read-only
		STATUS mandatory
		DESCRIPTION
			"The index"
	::= { userEntry 1 }

	userName OBJECT-TYPE
		SYNTAX OCTET STRING
		ACCESS read-only
		STATUS mandatory
		DESCRIPTION
			"The name of the user"
	::= { userEntry 2 }

	userId	OBJECT-TYPE
		SYNTAX OCTET STRING
		ACCESS read-only
		STATUS mandatory
		DESCRIPTION
			"The id of the user" 
	::= { userEntry 3 }

	userFullName OBJECT-TYPE
		SYNTAX OCTET STRING
		ACCESS read-only
		STATUS mandatory
		DESCRIPTION
			"The Full name list of the user "
	::= { userEntry 4 }

	userLoginShellCli OBJECT-TYPE
		SYNTAX OCTET STRING
		ACCESS read-only
		STATUS mandatory
		DESCRIPTION
			"The Login shell of the user"
	::= { userEntry 5 }

	userLoginDirectory	OBJECT-TYPE
		SYNTAX OCTET STRING
		ACCESS read-only
		STATUS mandatory
		DESCRIPTION
			"The login directory of the user"
	::= { userEntry 6 }

--
-- The installedSw table
--
	
	installedSwTable OBJECT-TYPE
		SYNTAX SEQUENCE OF InstalledSwEntry
		ACCESS not-accessible
		STATUS mandatory
		DESCRIPTION
			"This table describes the installedSw"
	::= { host 13 }

	installedSwEntry OBJECT-TYPE
		SYNTAX InstalledSwEntry
		ACCESS not-accessible
		STATUS mandatory
		DESCRIPTION
			"An entry in the installedSw table"
		INDEX { installedSwIndex }
	::= { installedSwTable 1 }

	InstalledSwEntry ::= SEQUENCE {
		installedSwIndex
			INTEGER,
		installedSwName
			OCTET STRING,
		installedSwVendorAuthor
			OCTET STRING,
		installedSwVersion
			OCTET STRING,
 		installedSwVendorPatches
			OCTET STRING,
		installedSwUserPatches
			OCTET STRING,
		installedSwLicInstalled
			OCTET STRING
	}


	installedSwIndex OBJECT-TYPE
		SYNTAX OCTET STRING
		ACCESS read-only
		STATUS mandatory
		DESCRIPTION
			"The index"
	::= { installedSwEntry 1 }

	installedSwName	OBJECT-TYPE
		SYNTAX OCTET STRING
		ACCESS read-only
		STATUS mandatory
		DESCRIPTION
			"The name of the installedSw"
	::= { installedSwEntry 2 }

	installedSwVendorAuthor	OBJECT-TYPE
		SYNTAX OCTET STRING
		ACCESS read-only
		STATUS mandatory
		DESCRIPTION
			"The vendor authorization of the installedSw"
	::= { installedSwEntry 3 }

	installedSwVersion	OBJECT-TYPE
		SYNTAX OCTET STRING
		ACCESS read-only
		STATUS mandatory
		DESCRIPTION
			"The version of the installedSw" 
	::= { installedSwEntry 4 }

	installedSwVendorPatches	OBJECT-TYPE
		SYNTAX OCTET STRING
		ACCESS read-only
		STATUS mandatory
		DESCRIPTION
			"The vendor patches list of the installedSw "
	::= { installedSwEntry 5 }

	installedSwUserPatches	OBJECT-TYPE
		SYNTAX OCTET STRING
		ACCESS read-only
		STATUS mandatory
		DESCRIPTION
			"The user patches of the installedSw"
	::= { installedSwEntry 6 }

	installedSwLicInstalled	OBJECT-TYPE
		SYNTAX OCTET STRING
		ACCESS read-only
		STATUS mandatory
		DESCRIPTION
			"The license of the installedSw"
	::= { installedSwEntry 7 }

--
-- The   license table
--
	
	licenseTable OBJECT-TYPE
		SYNTAX SEQUENCE OF LicenseEntry
		ACCESS not-accessible
		STATUS mandatory
		DESCRIPTION
			"This table describes the license"
	::= { host 14 }

	licenseEntry OBJECT-TYPE
		SYNTAX LicenseEntry
		ACCESS not-accessible
		STATUS mandatory
		DESCRIPTION
			"An entry in the license table"
		INDEX { licenseIndex }
	::= { licenseTable 1 }

	LicenseEntry ::= SEQUENCE {
		licenseIndex
			INTEGER,
		licensePoductName
			OCTET STRING,
		licenseVendorAuthor
			OCTET STRING,
		licenseExpirationDate
			OCTET STRING,
 		licenseVersion
			OCTET STRING,
		licenseCapacity
			OCTET STRING,
		licenseAuthorization
			OCTET STRING
	}

	licenseIndex	OBJECT-TYPE
		SYNTAX OCTET STRING
		ACCESS read-only
		STATUS mandatory
		DESCRIPTION
			"The index"
	::= { licenseEntry 1 }

	licenseProductName	OBJECT-TYPE
		SYNTAX OCTET STRING
		ACCESS read-only
		STATUS mandatory
		DESCRIPTION
			"The product name of the license"
	::= { licenseEntry 2 }

	licenseVendorAuthor	OBJECT-TYPE
		SYNTAX OCTET STRING
		ACCESS read-only
		STATUS mandatory
		DESCRIPTION
			"The vendor authorization of the license"
	::= { licenseEntry 3 }

	licenseExpirationDate	OBJECT-TYPE
		SYNTAX OCTET STRING
		ACCESS read-only
		STATUS mandatory
		DESCRIPTION
			"The Expiry date of the license" 
	::= { licenseEntry 4 }

	licenseVersion	OBJECT-TYPE
		SYNTAX OCTET STRING
		ACCESS read-only
		STATUS mandatory
		DESCRIPTION
			"The Version of the license "
	::= { licenseEntry 5 }

	licenseCapacity	OBJECT-TYPE
		SYNTAX OCTET STRING
		ACCESS read-only
		STATUS mandatory
		DESCRIPTION
			"The capacity of the license"
	::= { licenseEntry 6 }

	licenseAuthorization	OBJECT-TYPE
		SYNTAX OCTET STRING
		ACCESS read-only
		STATUS mandatory
		DESCRIPTION
			"The authorization of the license"
	::= { licenseEntry 7 }

--
-- The filesystem table
--
	
	filesystemTable	OBJECT-TYPE
		SYNTAX SEQUENCE OF FilesystemEntry
		ACCESS not-accessible
		STATUS mandatory
		DESCRIPTION
			"This table describes the filesystem"
	::= { host 15 }

	filesystemEntry OBJECT-TYPE
		SYNTAX FilesystemEntry
		ACCESS not-accessible
		STATUS mandatory
		DESCRIPTION
			"An entry in the filesystem table"
		INDEX { filesystemIndex }
	::= { filesystemTable 1 }

	FilesystemEntry ::= SEQUENCE {
		filesystemIndex
			INTEGER,
		filesystemOsType
			OCTET STRING,
		filesystemName
			OCTET STRING,
		filesystemHost
			OCTET STRING,
 		filesystemFreeCapacity
			INTEGER,
		filesystemFormattedCap
			INTEGER
	}

	filesystemIndex OBJECT-TYPE
		SYNTAX INTEGER
		ACCESS read-only
		STATUS mandatory
		DESCRIPTION
			"The Os type of the filesystem"
	::= { filesystemEntry 1 }

	filesystemName	OBJECT-TYPE
		SYNTAX OCTET STRING
		ACCESS read-only
		STATUS mandatory
		DESCRIPTION
			"The name of the filesystem"
	::= { filesystemEntry 2 }

	filesystemFreeCapacity	OBJECT-TYPE
		SYNTAX OCTET STRING
		ACCESS read-only
		STATUS mandatory
		DESCRIPTION
			"The free capatity of the filesystem "
	::= { filesystemEntry 3 }

	filesystemFormattedCap	OBJECT-TYPE
		SYNTAX INTEGER
		ACCESS read-only
		STATUS mandatory
		DESCRIPTION
			"The formatted capacity of the filesystem"
	::= { filesystemEntry 4 }


--
-- The mountInfo table
--
	
	mountInfoTable	OBJECT-TYPE
		SYNTAX SEQUENCE OF MountInfoEntry
		ACCESS not-accessible
		STATUS mandatory
		DESCRIPTION
			"This table describes the mountInfo"
	::= { host 16 }

	mountInfoEntry OBJECT-TYPE
		SYNTAX MountInfoEntry
		ACCESS not-accessible
		STATUS mandatory
		DESCRIPTION
			"An entry in the mountInfo table"
		INDEX { mountInfoIndex }
	::= { mountInfoTable 1 }

	MountInfoEntry ::= SEQUENCE {
		mountInfoIndex
			INTEGER,
		mountInfoFilesystemName
			OCTET STRING,
		mountInfoDeviceName
			OCTET STRING,
		mountInfoMountPoint
			OCTET STRING,
 		mountInfoMountType
			OCTET STRING,
		mountInfoRelVolNum
			INTEGER
	}

	mountInfoIndex	OBJECT-TYPE
		SYNTAX INTEGER
		ACCESS read-only
		STATUS mandatory
		DESCRIPTION
			"The file system name of the mountInfo"
	::= { mountInfoEntry 1 }

	mountInfoFileSystemName	OBJECT-TYPE
		SYNTAX OCTET STRING
		ACCESS read-only
		STATUS mandatory
		DESCRIPTION
			"The file system name of the mountInfo"
	::= { mountInfoEntry 2 }

	mountInfoDeviceName	OBJECT-TYPE
		SYNTAX OCTET STRING
		ACCESS read-only
		STATUS mandatory
		DESCRIPTION
			"The Device name of the mountInfo"
	::= { mountInfoEntry 3 }

	mountInfoMountPoint	OBJECT-TYPE
		SYNTAX OCTET STRING
		ACCESS read-only
		STATUS mandatory
		DESCRIPTION
			"The mount point of the mountInfo" 
	::= { mountInfoEntry 4 }

	mountInfoMountType	OBJECT-TYPE
		SYNTAX OCTET STRING
		ACCESS read-only
		STATUS mandatory
		DESCRIPTION
			"The Mount type list of the mountInfo "
	::= { mountInfoEntry 4 }

	mountInfoRelVolNum	OBJECT-TYPE
		SYNTAX INTEGER
		ACCESS read-only
		STATUS mandatory
		DESCRIPTION
			"The rel volume number of the mountInfo"
	::= { mountInfoEntry 6 }
END
