-- Digital Server Management MIB version V2.0 - svrmgt.mib
--
-- Description:
--  This MIB extension describes instrumentation in the
--  Digital extension agent itself, including the ability
--  to monitor for and detect thresholds on integer-valued
--  variables in any local SNMP MIB.  This MIB will also
--  be used to control management hardware and firmware that may 
--  optionally be present.

SVRMGT-MIB DEFINITIONS ::= BEGIN


IMPORTS
	TRAP-TYPE FROM RFC-1215
    mgmt, enterprises, NetworkAddress, IpAddress, Counter, Gauge, TimeTicks
        FROM RFC1155-SMI
    OBJECT-TYPE
        FROM RFC-1212
    DisplayString
        FROM RFC1213-MIB;


-- DEC-MIB { iso(1) org(3) dod(6) internet(1) private(4) enterprises(1) 36 }

dec OBJECT IDENTIFIER ::= { enterprises 36 }
ema OBJECT IDENTIFIER ::= { dec 2 }


-- textual conventions for types

Boolean ::= INTEGER {
                true(1) , 
                false(2) 
            }

--  Describes the possible SNMP error codes. Used when svrThrStatus == rowError.
SnmpErrors ::= INTEGER {
                noError(1) ,    --  Status = success
                tooBig(2) ,     --  Trying to reference an invalid oid, out of range problem ...
                readonly(3) ,   --  Trying to do an operation on a read-only attribute
                genericError(4) , 
                noSuchName(5) , --  Possibly an invalid oid.
                badValue(6)     --  Bad value on a SET operation
            }
Severity ::= INTEGER {
                high(1) , 
                medium(2) , 
                low(3) , 
                informational(4) 
            }

--  A way of logically grouping the thresholds
AlarmCategory ::= INTEGER {
                unknown(1) , 
                other(2) ,
                processorStatus(3) ,
                diskStatus(4) ,
                fanStatus(5) ,
                voltageStatus(6) ,
                powerSupplyStatus(7) ,
                temperatureStatus(8) ,
                memoryStatus(9) , 
                fileUsage(10) ,
                temperatureReading(11) ,
                cpuUsage(12) ,
                networkInboundErrors(13) ,
                networkOutboundErrors(14) ,
                networkInboundPackets(15) ,
                networkOutboundPackets(16) ,
                networkInboundDiscards(17) ,
                networkOutboundDiscards(18) ,
                networkInboundUnicastPackets(19) ,
                networkOutboundUnicastPackets(20) ,
                networkInboundNonUnicastPackets(21) ,
                networkOutboundNonUnicastPackets(22) ,
                networkInboundOctets(23) ,
                networkOutboundOctets(24) ,
                networkUnknownProtocol(25) ,
                voltageReading(26) ,
                clusterGroupStatus(27) ,
                secureBoxStatus(28) ,
                secureBoxBreakInCount(29)
            }

ResetRelationalOperators ::= INTEGER {
                greaterThan(1) , 
                greaterThanOrEqualTo(2) , 
                equalTo(3) , 
                lessThanOrEqualTo(4) , 
                lessThan(5) ,
                notEqualTo(6) 
            }

ThresholdOwner ::= INTEGER {
                unknown(1) ,
                other (2) ,
                serverWorks(3) ,
                serverWorksMinimalHealth(4) ,
                netView(5) ,
                openView(6) ,
                uniCenter(7) ,
                distributedMonitor(8) ,
                bmcPatrol(9) ,
                eminate(10) 
            }
                

--  Instrumentation of the server management agent, hardware & firmware.
mib-extensions-1                 OBJECT IDENTIFIER ::= { ema 18 }
svrSystem                        OBJECT IDENTIFIER ::= { mib-extensions-1 22 }
svrMgt                           OBJECT IDENTIFIER ::= { svrSystem 2 }


 -- groups in svrmgt

svrMgtMibInfo                   OBJECT IDENTIFIER ::= { svrMgt 1 }
svrAlarms                       OBJECT IDENTIFIER ::= { svrMgt 2 }
svrControl                      OBJECT IDENTIFIER ::= { svrMgt 3 }
svrTrap                         OBJECT IDENTIFIER ::= { svrMgt 4 }
svrMinimalHealth                OBJECT IDENTIFIER ::= { svrMgt 5 }

--  
--  svrMgtMibInfo
--  
--  Current state of this MIB module.
--  Mandatory.

svrMgtMibMajorRev OBJECT-TYPE
    SYNTAX  INTEGER
    ACCESS  read-only
    STATUS  mandatory
    DESCRIPTION
        "Major revision of this MIB.  Should equal 2."
    ::= { svrMgtMibInfo 1 }

svrMgtMibMinorRev OBJECT-TYPE
    SYNTAX  INTEGER
    ACCESS  read-only
    STATUS  mandatory
    DESCRIPTION
        "Minor revision of this mib. Should be 0."
    ::= { svrMgtMibInfo 2 }

--  
--  svrAlarms
--  
--  Group describing locally-generated alarms and their disposition.

svrAlarmNextThrIndex OBJECT-TYPE
    SYNTAX  INTEGER
    ACCESS  read-only
    STATUS  mandatory
    DESCRIPTION
        "Next available index for creating a svrThrEntry. If the value is -1
         then the maximum number of thresholds has been reached. This means 
         that a threshold record can not be created until a current threshold
         record is deleted. "
    ::= { svrAlarms 1 }

svrAlarmEnableTraps OBJECT-TYPE
    SYNTAX  Boolean
    ACCESS  not-accessible
    STATUS  obsolete
    DESCRIPTION
        "Starting with V2.0, this variable has been moved. Use the 
        svrControlEnableTraps for the same functionality."
    ::= { svrAlarms 2 }

svrThresholdTable OBJECT-TYPE
    SYNTAX SEQUENCE OF SvrThresholdEntry
    ACCESS not-accessible
    STATUS mandatory
    DESCRIPTION
        "Table of thresholds against which the agent should check
         for exceptions.
        
         This table describes conditions for setting and resetting alarms.
         
         Alarms may be set on absolute values - i.e. the current integer
         value of the sampled variable - or on delta values - i.e. the 
         difference between the current or last value.

         Alarms may be GreaterThan exception alarms, LessThan exception
         alarms, EqualsTo alarms etc.  See svrThrAlarmType for differences.

         Hysteresis is introduced by providing thresholds both for setting and
         resetting of the alarm state, thereby limiting the number of traps
         that will be sent on alarm triggering.

         Alarms may be created to persist across agent reboots, but this
         is not recommended for dynamic table variables.

         The triggering of an alarm will change a state variable in the
         conceptual row.  It may also trigger the sending of a trap, the
         local logging of an event, or the triggering of a locally-
         defined action. 
         
         "
    ::= { svrAlarms 3 }

svrThresholdEntry OBJECT-TYPE
    SYNTAX SvrThresholdEntry
    ACCESS not-accessible
    STATUS mandatory
    DESCRIPTION
        "One threshold alarm set on some particular integer-valued variable.
        
         An alarm entry is created by the management console.  It uses the 
         current value of svrAlarmNextThrIndex to name the instances of
         the row variables, and sets its svrThrStatus to underCreation.  
         When creating a theshold entry for the first time, issue a set
         request on svrThrStatus.

         The remaining row variables may be set in the same operation, or in
         subsequent operations.  Those not set will have retain their default
         values as described.  The following variable values MUST be set
         before enabling the alarm:

                svrThrStatus must be set to underCreation
                svrThrVariableName
                svrThrThresholdValue "

     INDEX    {
             svrThrIndex
             }
    ::= { svrThresholdTable 1 }

SvrThresholdEntry  ::=
    SEQUENCE {
        svrThrIndex
            INTEGER,
        svrThrStatus
            INTEGER,
        svrThrVariableName
            OBJECT IDENTIFIER,
        svrThrValueType
            INTEGER,
        svrThrAlarmType
            INTEGER,
        svrThrSampleInterval
            INTEGER,
        svrThrPersistent
            Boolean,
        svrThrThresholdValue
            INTEGER,
        svrThrResetValue
            INTEGER,
        svrThrLastValue
            INTEGER,
        svrThrAlarmState
            INTEGER,
        svrThrLogEvent
            Boolean,
        svrThrInvokeLocalHandler
            Boolean,
        svrThrLocalHandlerPath
            DisplayString,
        svrThrDescr
            DisplayString,
        svrThrErrorValue
            SnmpErrors,
        svrThrComparisonName
            OBJECT IDENTIFIER,
        svrThrComparisonValue
            DisplayString,
        svrThrSeverity
            Severity,
        svrThrTrapEnabler
            Boolean,
        svrThrLocalHandlerArguments1
            DisplayString,
        svrThrLocalHandlerArguments2
            DisplayString,
        svrThrLocalHandlerArguments3
            DisplayString,
        svrThrLocalHandlerArguments4
            DisplayString,
        svrThrTrapsSendingInterval
            INTEGER,
        svrThrManagerDefinedTrapData
            DisplayString,
        svrThrUserDefinedTrapData
            DisplayString,
        svrThrRetryCount
            INTEGER,
        svrThrResetType
            ResetRelationalOperators,
        svrThrAlarmCategory
            AlarmCategory,
        svrThrTrapOid
            OBJECT IDENTIFIER,
        svrThrCreatedBy
            ThresholdOwner,
        svrThrModifiable
            Boolean
             }

svrThrIndex OBJECT-TYPE
    SYNTAX  INTEGER
    ACCESS  read-only
    STATUS  mandatory
    DESCRIPTION
        "A locally-unique index value.  On creation, this should be set
        to the value of svrAlarmNextThrIndex."
    ::= { svrThresholdEntry 1 }

svrThrStatus OBJECT-TYPE
    SYNTAX  INTEGER {
                underCreation(1) , 
                rowInvalid(2) , 
                rowEnabled(3) , 
                rowDisabled(4) , 
                rowError(5) 
            }
    ACCESS  read-write
    STATUS  mandatory
    DESCRIPTION
        " This variable describes the status of the row.  When the row
        is created with the initial set, svrThrStatus must be set to
        underCreation.  When the management console has completed row
        setup, it should set this variable to rowEnabled.  Variables
        in the row may only be written if svrThrStatus is in the
        initial underCreation state or has been set to rowDisabled.

        To delete the row, set the status to rowInvalid. The agent will 
        physically delete the row and make that instance available to be used 
        again.

        Errors in variable polling and threshold checking that are determined
        by local implementation to be non-correctable will cause a row
        status change to rowError. Once the status is set to rowError by the 
        agent, the agent will not reset it. Instead, it is up to the management 
        console to reset the status based on information returned via 
        svrThrErrorValue or for other reasons.
        "

    ::= { svrThresholdEntry 2 }

svrThrVariableName OBJECT-TYPE
    SYNTAX  OBJECT IDENTIFIER
    ACCESS  read-write
    STATUS  mandatory
    DESCRIPTION
       "The OID of an integer-valued variable to be tested against this 
        threshold.  On row creation, this variable will equal the value 0.0,
        and must be set to the OID of an integer-valued variable before
        enabling the alarm. It's possible to get an error setting this due to
        invalid oid (may not support thresholding on this oid due to data type
        perhaps) or that we couldn't access the agent that supports this oid."
    ::= { svrThresholdEntry 3 }

svrThrValueType OBJECT-TYPE
    SYNTAX  INTEGER {
                absoluteValue(1) , 
                deltaValue(2) 
            }
    ACCESS  read-write
    STATUS  mandatory
    DESCRIPTION
        "Is this an absolute value or a delta value. The deltaValue is 
         calculated by taking the current value and subtracting svtThrLastValue. 
         The difference may be negative - allows for thresholding on negative 
         changes.Default on row creation is absoluteValue. "
    ::= { svrThresholdEntry 4 }

svrThrAlarmType OBJECT-TYPE
    SYNTAX  INTEGER {
                greaterThan(1) , 
                greaterThanOrEqualTo(2) , 
                equalTo(3) , 
                lessThanOrEqualTo(4) , 
                lessThan(5) 
            }
    ACCESS  read-write
    STATUS  mandatory
    DESCRIPTION
        "Is this a greater than, greater than or equal to, equal to, less than
         or equal to, or less than alarm? 
      
         Greater Than or Greater Than or Equal To thresholds for absolute 
         values occur when the sample value exceeds (or equals) the 
         svrThrThresholdValue and svrThrAlarmState was reset.  This will cause 
         the svrThrAlarmState to be set and, if svrAlarmEnableTraps is true, 
         a svrThrExceptTrap will be sent. SvrThrAlarmState will be reset when 
         the sample value falls below or equals svrThrResetValue. For delta
         values, the same holds true except the difference between the sample
         value and the svrThrLastValue is used for comparison with both the
         svrThrThresholdValue and the svrThrResetValue.

         Less Than or Less Than or Equal To thresholds for absolute 
         values occur when the sample value falls below (or equals) the 
         svrThrThresholdValue and svrThrAlarmState was reset.  This will cause 
         the svrThrAlarmState to be set and, if svrAlarmEnableTraps is true, 
         a svrThrExceptTrap will be sent. SvrThrAlarmState will be reset when 
         the sample value exceeds or equals svrThrResetValue. For delta
         values, the same holds true except the difference between the sample
         value and the svrThrLastValue is used for comparison with both the
         svrThrThresholdValue and the svrThrResetValue.

         Equal To thresholds for absolute values occur when the sample value 
         equals svrThrThresholdValue and svrThrAlarmState was reset.  This will
         cause the svrThrAlarmState to be set and, if svrAlarmEnableTraps is 
         true, a svrThrExceptTrap will be sent. SvrThrAlarmState will be reset 
         when the sample value does not equal svrThrResetValue. For delta
         values, the same holds true except the difference between the sample
         value and the svrThrLastValue is used for comparison with both the
         svrThrThresholdValue and the svrThrResetValue.

         NOTE - It is possible to have negative delta values since the differ-
         ence is computed as the current value minus the svrThrLastValue. 

         The default value on row creation is greaterThan.

         "
    ::= { svrThresholdEntry 5 }

svrThrSampleInterval OBJECT-TYPE
    SYNTAX  INTEGER
    ACCESS  read-write
    STATUS  mandatory
    DESCRIPTION
        "Interval in seconds between polls to check for threshold exceptions.
         Minimum Value is 1. The default value on row creation is 30 seconds."
    ::= { svrThresholdEntry 6 }

svrThrPersistent OBJECT-TYPE
    SYNTAX  Boolean
    ACCESS  read-write
    STATUS  mandatory
    DESCRIPTION
        "True if this threshold should persist across agent restarts.
         Default value on row creation is false."
    ::= { svrThresholdEntry 7 }

svrThrThresholdValue OBJECT-TYPE
    SYNTAX  INTEGER
    ACCESS  read-write
    STATUS  mandatory
    DESCRIPTION
        "This is the thresholding value which gets compared to the current or 
        delta value. Default value on row creation is 0."
    ::= { svrThresholdEntry 8 }

svrThrResetValue OBJECT-TYPE
    SYNTAX  INTEGER
    ACCESS  read-write
    STATUS  mandatory
    DESCRIPTION
        "This is the value that on all svrThrAlarmTypes except for equalTo, is 
        used to reset the threshold. Default value on row creation is 0"
    ::= { svrThresholdEntry 9 }

svrThrLastValue OBJECT-TYPE
    SYNTAX  INTEGER
    ACCESS  read-only
    STATUS  mandatory
    DESCRIPTION
        "Saved previous sample; needed to evaluate if alarm should be 
        triggered or to evaluate delta values for threshold checking."
    ::= { svrThresholdEntry 10 }

svrThrAlarmState OBJECT-TYPE
    SYNTAX  INTEGER {
                set(1) , 
                reset(2) 
            }
    ACCESS  read-only
    STATUS  mandatory
    DESCRIPTION
        "Whether this alarm is currently set or reset.  This variable
         is used by polling management applications to determine if
         a threshold exception state has been detected based on this
         alarm definition.
        
         It will initially have a value of reset when the alarm is 
         enabled. 
         
         For state change rules look at the definition for svrThrAlarmType.        
         In all cases, this value will reset on svrThrStatus change to
         rowDisabled or rowInvalid. The default value on row creation is 
         reset."
    ::= { svrThresholdEntry 11 }

svrThrLogEvent OBJECT-TYPE
    SYNTAX  Boolean
    ACCESS  read-write
    STATUS  mandatory
    DESCRIPTION
        "If yes, log to the system event log. Default value on row creation is 
         false."
    ::= { svrThresholdEntry 12 }

svrThrInvokeLocalHandler OBJECT-TYPE
    SYNTAX  Boolean
    ACCESS  read-write
    STATUS  mandatory
    DESCRIPTION
        "If true, invoke a local alarm handler, passing the concatenated local
         handler argument strings starting with argument 1.  
         Default value on row creation is false."
    ::= { svrThresholdEntry 13 }

svrThrLocalHandlerPath OBJECT-TYPE
    SYNTAX  DisplayString
    ACCESS  read-write
    STATUS  mandatory
    DESCRIPTION
        "Pathname of local alarm handler. This can be any pathname as long as
        it can be recognized by the particular operating system."
    ::= { svrThresholdEntry 14 }

svrThrDescr OBJECT-TYPE
    SYNTAX  DisplayString
    ACCESS  read-write
    STATUS  mandatory
    DESCRIPTION
        "This attribute is used to describe the type of threshold. This is set
        by the management console not by the agent. "
    ::= { svrThresholdEntry 15 }

svrThrErrorValue OBJECT-TYPE
    SYNTAX  SnmpErrors
    ACCESS  read-only
    STATUS  mandatory
    DESCRIPTION
        "This is the SNMP defined error status which caused the svrThrStatus 
        value to become equal to rowError. Only valid at that time. Default
        value on row creation is noError."
    ::= { svrThresholdEntry 16 }

svrThrComparisonName OBJECT-TYPE
    SYNTAX  OBJECT IDENTIFIER
    ACCESS  read-write
    STATUS  mandatory
    DESCRIPTION
        "An OID to a descriptor attribute which can be used with persistent to 
        verify that the svrThrVariableName instance is correct. On agent 
        restarts the value for this oid will be retrieved and compared to the
        svrThrComparisonValue. If not equal, then it's possible that the 
        oid instancing for svrThrVariableName is incorrect. 

        If this occurs, then the svrThrStatus will be set to rowError and the
        svrThrErrorValue will be set to badValue.

        This attribute is optional. The default value on row creation is 0.0. 
        Can be reset back to 0.0 if this attribute is not to be used."
    ::= { svrThresholdEntry 17 }

svrThrComparisonValue OBJECT-TYPE
    SYNTAX  DisplayString
    ACCESS  read-write
    STATUS  mandatory
    DESCRIPTION
        "Data value of svrThrComparisonName - used when persistent is set.  
        This value is compared to the current value on agent restarts.

        This attribute is optional. The default value on row creation is NULL."
    ::= { svrThresholdEntry 18 }

svrThrSeverity OBJECT-TYPE
    SYNTAX  Severity
    ACCESS  read-write
    STATUS  mandatory
    DESCRIPTION
        "Indicates the severity of the threshold. Default value on row creation
        is informational."
    ::= { svrThresholdEntry 19 }


svrThrTrapEnabler OBJECT-TYPE
    SYNTAX  Boolean
    ACCESS  read-write
    STATUS  mandatory
    DESCRIPTION
        "Determines if a trap should be sent out if the threshold event does 
        occur. If true, a trap will be sent out. If false, a trap will not be
        sent out. Default value on row creation is true."
    ::= { svrThresholdEntry 20 }

svrThrLocalHandlerArguments1 OBJECT-TYPE
    SYNTAX  DisplayString
    ACCESS  read-write
    STATUS  mandatory
    DESCRIPTION
        "This is the first part of the argument line if the 
        svrThrInvokeLocalHandler is used. This argument line is passed 
        directly to the application pointed to by the svrThrLocalHandlerPath.
        A parameter(s) could be substituted anywhere in the argument line with 
        an oid's value if there is a %oid% found within the string. The %oid% 
        will be replaced with the value of the oid at the time the event 
        occurred. For example if the svrSystemDesc value from the Digital Server
        System mib is required, then the argument list would have a replacement 
        statement like this: %.1.3.6.1.4.1.36.2.18.22.1.2.3.0%.

        If a value from a threshold record is requested, use %oid% where the 
        oid is .1.3.6.1.4.1.36.2.18.22.2.2.3.1.offset.instance. The offset is
        the oid offset (from 1 to 30) of the threshold entry variable. For 
        svrThrIndex, the offset is 1. The instance can be dropped if the 
        current threshold record (that which caused the event) is to be used.
        Otherwise, the instance of the requested threshold entry must be part
        of the %oid% statement.

        All the replaced values are inserted into the argument strings as 
        ascii/text strings. For an integer (counter, gauge, etc) value, if
        the value is negative, there will be a minus sign in front of the 
        value. For a positive number, there is no sign in front of the value.
        The integer value will be in ascii format - it is the responsibility
        of the application to convert the text into a decimal number. All octet
        strings, excluding display strings, will be inserted into the argument
        string as a text string in the format of 0xoctet value. For example
        if an octet string (hex based) of 8,23,6a,4e was retrieved using the 
        %oid% format, then the replaced value would be a text string looking
        like this - 0x8,0x23,0x6a,0x4e where the number are in ascii 
        (displayable) format separated by a comma. The 0x represents the 
        hexadecimal base while the number following that is the ascii 
        representation of the hexadecimal number. For display strings, there
        will be a pair of quotes around the string. 

        Use of the Handler Arguments must be done in ascending order. No 
        skipping of argument variables is allowed.

        NOTE - All oids must be preceded with a period(.) for proper system
        group recognition. Also all argument lists (concatenated starting with
        argument #1) are separated by a space. Default value on row creation 
        is null."
    ::= { svrThresholdEntry 21 }

svrThrLocalHandlerArguments2 OBJECT-TYPE
    SYNTAX  DisplayString
    ACCESS  read-write
    STATUS  mandatory
    DESCRIPTION
        "Same semantics as svrThrLocalHandlerArguments1."
    ::= { svrThresholdEntry 22 }

svrThrLocalHandlerArguments3 OBJECT-TYPE
    SYNTAX  DisplayString
    ACCESS  read-write
    STATUS  mandatory
    DESCRIPTION
        "Same semantics as svrThrLocalHandlerArguments1."
    ::= { svrThresholdEntry 23 }

svrThrLocalHandlerArguments4 OBJECT-TYPE
    SYNTAX  DisplayString
    ACCESS  read-write
    STATUS  mandatory
    DESCRIPTION
        "Same semantics as svrThrLocalHandlerArguments1."
    ::= { svrThresholdEntry 24 }

svrThrTrapsSendingInterval OBJECT-TYPE
    SYNTAX  INTEGER
    ACCESS  read-write
    STATUS  mandatory
    DESCRIPTION
        "Represents how often a trap should be sent if dealing with sending 
        multiple traps per event. The units is minutes. Default value on row
        creation is 0 minutes. When set to 0, only 1 trap will be sent out per
        event."
    ::= { svrThresholdEntry 25 }

svrThrManagerDefinedTrapData OBJECT-TYPE
    SYNTAX  DisplayString
    ACCESS  read-write
    STATUS  mandatory
    DESCRIPTION
        "This is a string provided by a management console to be sent out with 
        every trap. Default value on row creation is null."
    ::= { svrThresholdEntry 26 }

svrThrUserDefinedTrapData OBJECT-TYPE
    SYNTAX  DisplayString
    ACCESS  read-write
    STATUS  mandatory
    DESCRIPTION
        "This is a string provided by a user via a management console to be 
        sent out with every trap. Default value on row creation is null."
    ::= { svrThresholdEntry 27 }

svrThrRetryCount OBJECT-TYPE
    SYNTAX  INTEGER
    ACCESS  read-write
    STATUS  mandatory
    DESCRIPTION
        "Allows for a trap to be sent n number of sampling intervals after the 
        threshold event occurred rather than right after the event occurred. 
        This allows for cases when an event is just a momentary event and 
        should not be considered a problem until it has persisted over a number
        of sampling intervals. If the retry count is 0, then the trap will be
        sent out immediately after the event has occurred. Default value on row
        creation is 0."
    ::= { svrThresholdEntry 28 }

svrThrResetType OBJECT-TYPE
    SYNTAX  ResetRelationalOperators
    ACCESS  read-write
    STATUS  mandatory
    DESCRIPTION
        "Is this a greater than, greater than or equal to, equal to, less than 
        or equal to, or less than the reset value?
        This variable works just like the svrThrAlarmType. It is a relational 
        operator used to compare the oid's current value with the 
        svrThrResetValue to determine if the threshold's alarm state should be 
        reset. Default value on row creation is lessThanOrEqualTo."
    ::= { svrThresholdEntry 29 }

svrThrAlarmCategory OBJECT-TYPE
    SYNTAX  AlarmCategory
    ACCESS  read-write
    STATUS  mandatory
    DESCRIPTION
        "A management station provided variable to allow for 
        classification/grouping of thresholds."
    ::= { svrThresholdEntry 30 }

svrThrTrapOid OBJECT-TYPE
    SYNTAX  OBJECT IDENTIFIER
    ACCESS  read-write
    STATUS  mandatory
    DESCRIPTION
        "A fully defined OID of a svrmgt trap (other than reset and modify)
         that will be sent out when an event occurs. This OID will override 
         the usage of the svrThrSeverity value when choosing the appropriate
         trap. 

        NOTE - The svrmgt trap OID must be preceded with a period(.) for proper 
        system group recognition.

        This attribute is optional. The default value on row creation is 0.0." 
    ::= { svrThresholdEntry 31 }

svrThrCreatedBy OBJECT-TYPE
    SYNTAX  ThresholdOwner
    ACCESS  read-write
    STATUS  mandatory
    DESCRIPTION
        "Represents the creator of this threshold. This variable can be 
        modified only during threshold creation. The default value on row
        creation is the unknown value. "
    ::= { svrThresholdEntry 32 }

svrThrModifiable OBJECT-TYPE
    SYNTAX  Boolean
    ACCESS  read-write
    STATUS  mandatory
    DESCRIPTION
        "Determines whether modification of the threshold record is allowed 
        after creation. If false, modification is allowed only during row 
        creation. This variable can be modified only during threshold creation.
        The default value on row creation is true. "
    ::= { svrThresholdEntry 33 }

--  
--  svrControl
--  
--  Group of parameters to control local server behavior.  Instrumentation in 
--  server control hardware.
--  Mandatory

svrControlEnableTraps OBJECT-TYPE
    SYNTAX  Boolean
    ACCESS  read-write
    STATUS  mandatory
    DESCRIPTION
        "If true, the appropriate exception trap will be sent for each 
        triggered alarm. This value persists over agent restarts. Default 
        value is true."
    ::= { svrControl 1 }

svrControlEnableModifyTraps OBJECT-TYPE
    SYNTAX  Boolean
    ACCESS  read-write
    STATUS  mandatory
    DESCRIPTION
        "If true, a modify trap will be sent for each modification of the 
        threshold table when the threshold entry state is rowDisabled.
        This value persists over agent restarts. Default value is false."
    ::= { svrControl 2 }

svrControlEnableResetTraps OBJECT-TYPE
    SYNTAX  Boolean
    ACCESS  read-write
    STATUS  mandatory
    DESCRIPTION
        "If true, a reset trap will be sent each time any threshold event is 
        reset. If the alarm state goes from set to reset, a reset trap will be
        sent. This value persists over agent restarts. Default value is false."
    ::= { svrControl 3 }

svrControlModifyOID OBJECT-TYPE
    SYNTAX  OBJECT IDENTIFIER
    ACCESS  not-accessible
    STATUS  mandatory
    DESCRIPTION
        "This variable is used as a variable in the modification trap, 
        svrThrModifyTrap to represent the threshold variable which caused
        the modify trap to be sent. This variable can not be retrieved nor
        modified by the user."
    ::= { svrControl 4 }

--  
--  svrTrap
--  
--  Group describing the current configuration of the trap destination 
--  addresses.
--  Mandatory

svrTrapReconfigureEvent OBJECT-TYPE
    SYNTAX  INTEGER {
                enable(1) , 
                disable(2) 
            }
    ACCESS  write-only
    STATUS  mandatory
    DESCRIPTION
        "By setting this value to enable, trap destinations will be 
        reconfigured. On some operating systems like Windows/NT this will 
        cause the SNMP agent to restart."
    ::= { svrTrap 1 }

svrTrapCommunityNextIndex OBJECT-TYPE
    SYNTAX  INTEGER
    ACCESS  read-only
    STATUS  mandatory
    DESCRIPTION
        "Next available index for creating a svrTrapCommunityEntry. If the value
        is -1, then the maximum number of community names has been reached. This 
        means that a community record can not be created until another community
        name has been deleted."
    ::= { svrTrap 2 }

svrTrapCommunityTable OBJECT-TYPE
    SYNTAX SEQUENCE OF SvrTrapCommunityEntry
    ACCESS not-accessible
    STATUS mandatory
    DESCRIPTION
        "Table of svrTrapCommunityEntry (community names) for which each can
        have a list of IP addresses/TCPIP names/Netbios names/IPX addresses.
        These address/names are trap destinations. A trap is sent out per 
        community/address(name) pairing."
    ::= { svrTrap 6 }

svrTrapCommunityEntry OBJECT-TYPE
    SYNTAX SvrTrapCommunityEntry
    ACCESS not-accessible
    STATUS mandatory
    DESCRIPTION
        "In order to create a community entry, the svrTrapCommunityNextIndex 
        must be userd as the instance for that entry."
    INDEX    {
             svrTrapCommunityIndex
             }
    ::= { svrTrapCommunityTable 1 }

SvrTrapCommunityEntry  ::=
    SEQUENCE {
        svrTrapCommunityIndex
            INTEGER,
        svrTrapCommunityName
            DisplayString,
        svrTrapDestinationNextIndex
            INTEGER
             }

svrTrapCommunityIndex OBJECT-TYPE
    SYNTAX  INTEGER
    ACCESS  read-only
    STATUS  mandatory
    DESCRIPTION
        "A locally-unique index value. On creation, this should be set to the 
        value of svrTrapCommunityNextIndex."
    ::= { svrTrapCommunityEntry 1 }

svrTrapCommunityName OBJECT-TYPE
    SYNTAX  DisplayString
    ACCESS  read-write
    STATUS  mandatory
    DESCRIPTION
        "This is the community name that network addresses/names will be 
        associated with. When the trap is sent out, this community name is
        sent out with it. A common community name is public. To create a 
        community name entry, just issue a SET command for svrTrapCommunityName
        with an instance of svrTrapCommunityNextIndex. To delete the entry, 
        issue a SET command for that particular instance using an empty display
        string (length = 0). By deleting the community name entry, the underlying 
        destination entries for this community name instance will also be 
        deleted."
    ::= { svrTrapCommunityEntry 2 }

svrTrapDestinationNextIndex OBJECT-TYPE
    SYNTAX  INTEGER
    ACCESS  read-only
    STATUS  mandatory
    DESCRIPTION
        "Next available index for creating a svrTrapDestinationEntry. If the
        value is -1 then the maximum number of destination entries has been 
        reached. This means that a destination record can not be created
        until another has been deleted."
    ::= { svrTrapCommunityEntry 3 }

svrTrapDestinationTable OBJECT-TYPE
    SYNTAX SEQUENCE OF SvrTrapDestinationEntry
    ACCESS not-accessible
    STATUS mandatory
    DESCRIPTION
        "Table of IP addresses/TCPIP names/Netbios names/IPX addresses which
        are the trap destinations. A trap is sent out per community name/
        address(name) pairing."
    ::= { svrTrap 7 }

svrTrapDestinationEntry OBJECT-TYPE
    SYNTAX SvrTrapDestinationEntry
    ACCESS not-accessible
    STATUS mandatory
    DESCRIPTION
        "In order to create an address/name entry, the 
        svrTrapDestinationNextIndex must be used as the instance for that 
        entry."
    INDEX    {
             svrTrapCommunityIndex,
             svrTrapDestinationIndex
             }
    ::= { svrTrapDestinationTable 1 }

SvrTrapDestinationEntry  ::=
    SEQUENCE {
        svrTrapDestinationIndex
            INTEGER,
        svrTrapDestination
            DisplayString
             }

svrTrapDestinationIndex OBJECT-TYPE
    SYNTAX  INTEGER
    ACCESS  read-only
    STATUS  mandatory
    DESCRIPTION
        "A locally-unique index value. On creation, this must be set to the 
        value of svrTrapDestinationNextIndex."
    ::= { svrTrapDestinationEntry 1 }

svrTrapDestination OBJECT-TYPE
    SYNTAX  DisplayString
    ACCESS  read-write
    STATUS  mandatory
    DESCRIPTION
        "This is the destination that the trap will be sent. It can either an
        IP address, TCPIP name, Netbios name or IPX address. 
        To create a destination entry, just issue a SET command for 
        svrTrapDestination with an instance of svrTrapDestinationNextIndex.
        To delete the entry, issue a SET command for that particular instance
        using an empty display string (length = 0)."
    ::= { svrTrapDestinationEntry 2 }


--  
--  svrMinimalHealth
--  
--  Current state of the Minimal Health module.
--  Mandatory.

svrMinimalHealthMajorRev OBJECT-TYPE
    SYNTAX  INTEGER
    ACCESS  read-write
    STATUS  mandatory
    DESCRIPTION
        "Major revision of the Minimal Health module. Default is 0"
    ::= { svrMinimalHealth 1 }

svrMinimalHealthMinorRev OBJECT-TYPE
    SYNTAX  INTEGER
    ACCESS  read-write
    STATUS  mandatory
    DESCRIPTION
        "Minor revision of the Minimal Health module. Default is 0."
    ::= { svrMinimalHealth 2 }

svrMinimalHealthEnable OBJECT-TYPE
    SYNTAX  Boolean
    ACCESS  read-write
    STATUS  mandatory
    DESCRIPTION
        "If true, the minimal health module will be started. This value persists
         over agent restarts. Default value is true."
    ::= { svrMinimalHealth 3 }

svrMinimalHealthDesiredTemplateName OBJECT-TYPE
    SYNTAX  DisplayString
    ACCESS  read-write
    STATUS  mandatory
    DESCRIPTION
        "This is the desired template name for use by the minimal health agent."
    ::= { svrMinimalHealth 4 }

svrMinimalHealthDesiredTemplateRevision OBJECT-TYPE
    SYNTAX  DisplayString
    ACCESS  read-write
    STATUS  mandatory
    DESCRIPTION
        "This is the desired template revision for use by the minimal health agent."
    ::= { svrMinimalHealth 5 }

svrMinimalHealthDesiredTemplateRevisionDate OBJECT-TYPE
    SYNTAX  DisplayString
    ACCESS  read-write
    STATUS  mandatory
    DESCRIPTION
        "This is the desired template revision date for use by the minimal health 
        agent."
    ::= { svrMinimalHealth 6 }

svrMinimalHealthActualTemplateName OBJECT-TYPE
    SYNTAX  DisplayString
    ACCESS  read-write
    STATUS  mandatory
    DESCRIPTION
        "This is the actual template name for use by the minimal health agent."
    ::= { svrMinimalHealth 7 }

svrMinimalHealthActualTemplateRevision OBJECT-TYPE
    SYNTAX  DisplayString
    ACCESS  read-write
    STATUS  mandatory
    DESCRIPTION
        "This is the actual template revision for use by the minimal health agent."
    ::= { svrMinimalHealth 8 }

svrMinimalHealthActualTemplateRevisionDate OBJECT-TYPE
    SYNTAX  DisplayString
    ACCESS  read-write
    STATUS  mandatory
    DESCRIPTION
        "This is the actual template revision date for use by the minimal health 
        agent."
    ::= { svrMinimalHealth 9 }


--  
--    TRAP: svrThrModifyTrap
--  
svrThrModifyTrap TRAP-TYPE
    ENTERPRISE svrMgt
    VARIABLES { 
        svrThrVariableName,
        svrThrDescr,             
        svrControlModifyOID,
        svrThrManagerDefinedTrapData,
        svrThrUserDefinedTrapData,
        svrThrAlarmCategory,
        svrThrCreatedBy,
        svrThrSeverity }
    DESCRIPTION
        "This is a modification trap. The threshold OID whose value caused the 
        alarm is in svrControlModifyOID."
    ::= 99

--  
--    TRAP: svrThrResetTrap
--  
svrThrResetTrap TRAP-TYPE
    ENTERPRISE svrMgt
    VARIABLES { 
        svrThrVariableName,
        svrThrValueType,
        svrThrResetValue,
        svrThrLastValue,
        svrThrDescr,
        svrThrManagerDefinedTrapData,
        svrThrUserDefinedTrapData,
        svrThrAlarmCategory,
        svrThrCreatedBy,
        svrThrSeverity }
    DESCRIPTION
        "This is a reset trap. The value that cuased the alarm to be reset is 
        returned in svrThrLastValue."
    ::= 100



--  
--    TRAP: svrThrHighExceptTrap
--  
svrThrHighExceptTrap TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This is a high severity trap. The value that caused the alarm to occur 
        is returned in svrThrLastValue."
    ::= 101

--  
--    TRAP: svrThrMediumExceptTrap
--  
svrThrMediumExceptTrap TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This is a medium severity trap. The value that caused the alarm to 
        occur is returned in svrThrLastValue."
    ::= 102

--  
--    TRAP: svrThrLowExceptTrap
--  
svrThrLowExceptTrap TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This is a low severity trap. The value that caused the alarm to occur 
        is returned in svrThrLastValue."
    ::= 103

--  
--    TRAP: svrThrInformationalExceptTrap
--  
svrThrInformationalExceptTrap TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This is an Informational severity trap. The value that caused the 
        alarm to occur is returned in svrThrLastValue."
    ::= 104

--  
--    TRAP: svrThrDiskDown
--  
svrThrDiskDown TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the disk is not available for any use. The value 
        that caused the alarm to occur is returned in svrThrLastValue."
    ::= 105

--  
--    TRAP: svrThrDiskWarning
--  
svrThrDiskWarning TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that an unusual disk error condition has occured but
        that the device is still operational. The value that caused the alarm 
        to occur is returned in svrThrLastValue."
    ::= 106

--  
--    TRAP: svrThrDiskOk
--  
svrThrDiskOk TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the disk is up and running and that no unusual 
        error conditions are known. The value that caused the alarm to occur is 
        returned in svrThrLastValue."
    ::= 107

--  
--    TRAP: svrThrFileSystemUsage
--  
svrThrFileSystemUsage TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that file system usage has exceeded the user defined
         threshold.The value that caused the alarm to occur is returned in 
         svrThrLastValue."
    ::= 108

--  
--    TRAP: svrThrTemperatureOk
--  
svrThrTemperatureOk TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the temperature is within normal limits. The value
        that caused the alarm to occur is returned in svrThrLastValue."
    ::= 109

--  
--    TRAP: svrThrTemperatureCritical
--  
svrThrTemperatureCritical TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the temperature is in a critical state either low
        or high. The value that caused the alarm to occur is returned
        in svrThrLastValue."
    ::= 110

--  
--    TRAP: svrThrTemperatureWarning
--  
svrThrTemperatureWarning TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }

    DESCRIPTION
        "This indicates that the temperature is in a warning state either low or
         high. The value that caused the alarm to occur is returned in 
         svrThrLastValue."
    ::= 111

--  
--    TRAP: svrThrFanFailed
--  
svrThrFanFailed TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the fan has failed. The value that caused the alarm
        to occur is returned in svrThrLastValue."
    ::= 112

--  
--    TRAP: svrThrFanOk
--  
svrThrFanOk TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the fan is functioning well. The value that caused
        the alarm to occur is returned in svrThrLastValue."
    ::= 113

--  
--    TRAP: svrThrFanBackup
--  
svrThrFanBackup TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the fan is a backup fan. The value that caused the alarm
        to occur is returned in svrThrLastValue."
    ::= 114

--  
--    TRAP: svrThrVoltageOk
--  
svrThrVoltageOk TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the voltage is within normal limits. The value that
        caused the alarm to occur is returned in svrThrLastValue."
    ::= 115

--  
--    TRAP: svrThrVoltageCritical
--  
svrThrVoltageCritical TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the voltage is in a critical state, either low or
        high, but has not reached the shutdown threshold. The value that caused
        the alarm to occur is returned in svrThrLastValue."
    ::= 116

--  
--    TRAP: svrThrVoltageWarning
--  
svrThrVoltageWarning TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the voltage is in a warning state, either low or 
        high. The value that caused the alarm to occur is returned in svrThrLastValue."
    ::= 117

--  
--    TRAP: svrThrPowerSupplyFailed
--  
svrThrPowerSupplyFailed TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the power supply failed. The value that caused the 
        alarm to occur is returned in svrThrLastValue."
    ::= 118

--  
--    TRAP: svrThrPowerSupplyWarning
--  
svrThrPowerSupplyWarning TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the power supply is in a warning state but has 
        not yet failed. The value that caused the alarm to occur is returned in 
        svrThrLastValue."
    ::= 119

--  
--    TRAP: svrThrPowerSupplyOk
--  
svrThrPowerSupplyOk TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the power supply is functioning well. The value 
        that caused the alarm to occur is returned in svrThrLastValue."
    ::= 120

--  
--    TRAP: svrThrPowerSupplyBackup
--  
svrThrPowerSupplyBackup TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the power supply is in backup state. The value 
        that caused the alarm to occur is returned in svrThrLastValue."
    ::= 121

--  
--    TRAP: svrThrMemoryEltFailed
--  
svrThrMemoryEltFailed TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the memory element has failed. The value that
         caused the alarm to occur is returned in svrThrLastValue."
    ::= 122

--  
--    TRAP: svrThrMemoryEltWarning
--  
svrThrMemoryEltWarning TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the memory element is reporting errors. The value 
        that caused the alarm to occur is returned in svrThrLastValue."
    ::= 123

--  
--    TRAP: svrThrMemoryEltOk
--  
svrThrMemoryEltOk TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the memory element is functioning well. The value 
        that caused the alarm to occur is returned in svrThrLastValue."
    ::= 124

--  
--    TRAP: svrThrNetworkIfInErrors
--  
svrThrNetworkIfInErrors TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the network interface inbound errors have exceeded 
        the user defined threshold. The value that caused the alarm to occur is 
        returned in svrThrLastValue.
        "
    ::= 125

--  
--    TRAP: svrThrNetworkIfInOctets
--  
svrThrNetworkIfInOctets TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the network interface inbound octets have exceeded 
        the user defined threshold. The value that caused the alarm to occur is 
        returned in svrThrLastValue.
        "
    ::= 126

--  
--    TRAP: svrThrNetworkIfOutOctets
--  
svrThrNetworkIfOutOctets TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the network interface outbound octets have exceeded
        the user defined threshold. The value that caused the alarm to occur is 
        returned in svrThrLastValue."
    ::= 127

--  
--    TRAP: svrThrNetworkIfInPkts
--  
svrThrNetworkIfInPkts TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the network interface inbound packets have exceeded
        the user defined threshold. The value that caused the alarm to occur 
        is returned in svrThrLastValue."
    ::= 128

--  
--    TRAP: svrThrNetworkIfOutPkts
--  
svrThrNetworkIfOutPkts TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the network interface outbound packets have 
        exceeded the user defined threshold. The value that caused the alarm 
        to occur is returned in svrThrLastValue."
    ::= 129

--  
--    TRAP: svrThrNetworkIfOutErrors
--  
svrThrNetworkIfOutErrors TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the network interface outbound errors have exceeded
        the user defined threshold. The value that caused the alarm to occur 
        is returned in svrThrLastValue."
    ::= 130

--  
--    TRAP: svrThrNetworkIfInDiscards
--  
svrThrNetworkIfInDiscards TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the network interface inbound discards have 
        exceeded the user defined threshold. The value that caused the alarm to 
        occur is returned in svrThrLastValue."
    ::= 131

--  
--    TRAP: svrThrProcessorDown
--  
svrThrProcessorDown TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the processor is not available for any use. The 
        value that caused the alarm to occur is returned in svrThrLastValue."
    ::= 132

--  
--    TRAP: svrThrProcessorWarning
--  
svrThrProcessorWarning TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the processor has encountered an unusual error 
        condition but is still considered to be operational. The value that
        caused the alarm to occur is returned in svrThrLastValue."
    ::= 133

--  
--    TRAP: svrThrProcessorOk
--  
svrThrProcessorOk TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the processor is up and running and that no unusual
        error conditions are known. The value that caused the alarm to occur is 
        returned in svrThrLastValue."
    ::= 134

--  
--    TRAP: svrThrCpuUsage
--  
svrThrCpuUsage TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that CPU usage has exceeded the user defined threshold. 
        The value that caused the alarm to occur is returned in svrThrLastValue."
    ::= 135

--  
--    TRAP: svrThrClusterFailOverOwner
--  
svrThrClusterFailOverOwner TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the node has become the current owner of a cluster 
        resource. The value that caused the alarm to occur is returned in 
        svrThrLastValue."
    ::= 136

--  
--    TRAP: svrThrClusterFailOverNotOwner
--  
svrThrClusterFailOverNotOwner TRAP-TYPE
    ENTERPRISE svrMgt
    VARIABLES { 
        svrThrVariableName,
        svrThrValueType,
        svrThrThresholdValue,
        svrThrLastValue,
        svrThrDescr,
        svrThrManagerDefinedTrapData,
        svrThrUserDefinedTrapData,
        svrThrAlarmCategory,
        svrThrCreatedBy,
        svrThrSeverity }
    DESCRIPTION
        "This indicates that the node is not the current owner of a cluster 
        resource. The value that caused the alarm to occur is returned in 
        svrThrLastValue."
    ::= 137

END
