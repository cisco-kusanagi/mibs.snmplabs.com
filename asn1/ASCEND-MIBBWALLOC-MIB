--			Ascend mibbwalloc MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBBWALLOC-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibbandwidthAllocProfile  OBJECT IDENTIFIER ::= { configuration 29}
    mibbandwidthStatsProfile  OBJECT IDENTIFIER ::= { configuration 64}

	-- The mibbandwidthAllocProfile table
	--
	-- This table contains parameters for the mibbandwidthAllocProfile profile
	--

    mibbandwidthAllocProfileTable	OBJECT-TYPE
	SYNTAX		SEQUENCE OF MibbandwidthAllocProfileEntry
	ACCESS		not-accessible
	STATUS		mandatory
	DESCRIPTION	"A list of mibbandwidthAllocProfile profile entries."
	::= { mibbandwidthAllocProfile 1 }

    mibbandwidthAllocProfileEntry	OBJECT-TYPE
	SYNTAX		MibbandwidthAllocProfileEntry
	ACCESS		not-accessible
	STATUS		mandatory
	DESCRIPTION	"A mibbandwidthAllocProfile entry containing objects that
			 maps to the parameters of mibbandwidthAllocProfile profile."
	INDEX		{ bandwidthAllocProfile-Index-o }
	::= { mibbandwidthAllocProfileTable 1 }

    MibbandwidthAllocProfileEntry ::=
	SEQUENCE {
	    bandwidthAllocProfile-Index-o
		INTEGER,
	    bandwidthAllocProfile-Action-o
		INTEGER
	}

    bandwidthAllocProfile-Index-o	OBJECT-TYPE
	SYNTAX	INTEGER
	ACCESS	read-only
	STATUS	mandatory
	DESCRIPTION	""
	::= { mibbandwidthAllocProfileEntry 1 }

    bandwidthAllocProfile-Action-o	OBJECT-TYPE
	SYNTAX	INTEGER {
		    noAction (1),
		    createProfile (2),
		    deleteProfile (3)
		}
	ACCESS	read-write
	STATUS	mandatory
	DESCRIPTION	""
	::= { mibbandwidthAllocProfileEntry 2 }


	-- The mibbandwidthAllocProfile__traffic_shapers table
	--
	-- This table contains parameters for the mibbandwidthAllocProfile__traffic_shapers profile
	--

    mibbandwidthAllocProfile-TrafficShapersTable	OBJECT-TYPE
	SYNTAX		SEQUENCE OF MibbandwidthAllocProfile-TrafficShapersEntry
	ACCESS		not-accessible
	STATUS		mandatory
	DESCRIPTION	"A list of mibbandwidthAllocProfile__traffic_shapers profile entries."
	::= { mibbandwidthAllocProfile 2 }

    mibbandwidthAllocProfile-TrafficShapersEntry	OBJECT-TYPE
	SYNTAX		MibbandwidthAllocProfile-TrafficShapersEntry
	ACCESS		not-accessible
	STATUS		mandatory
	DESCRIPTION	"A mibbandwidthAllocProfile__traffic_shapers entry containing objects that
			 maps to the parameters of mibbandwidthAllocProfile__traffic_shapers profile."
	INDEX		{ bandwidthAllocProfile-TrafficShapers-Index-o, bandwidthAllocProfile-TrafficShapers-Index1-o }
	::= { mibbandwidthAllocProfile-TrafficShapersTable 1 }

    MibbandwidthAllocProfile-TrafficShapersEntry ::=
	SEQUENCE {
	    bandwidthAllocProfile-TrafficShapers-Index-o
		INTEGER,
	    bandwidthAllocProfile-TrafficShapers-Index1-o
		INTEGER,
	    bandwidthAllocProfile-TrafficShapers-Enabled
		INTEGER,
	    bandwidthAllocProfile-TrafficShapers-BitRate
		INTEGER,
	    bandwidthAllocProfile-TrafficShapers-PeakRate
		INTEGER,
	    bandwidthAllocProfile-TrafficShapers-MaxBurstSize
		INTEGER,
	    bandwidthAllocProfile-TrafficShapers-Aggregate
		INTEGER,
	    bandwidthAllocProfile-TrafficShapers-Priority
		INTEGER
	}

    bandwidthAllocProfile-TrafficShapers-Index-o	OBJECT-TYPE
	SYNTAX	INTEGER
	ACCESS	read-only
	STATUS	mandatory
	DESCRIPTION	""
	::= { mibbandwidthAllocProfile-TrafficShapersEntry 1 }

    bandwidthAllocProfile-TrafficShapers-Index1-o	OBJECT-TYPE
	SYNTAX	INTEGER
	ACCESS	read-only
	STATUS	mandatory
	DESCRIPTION	""
	::= { mibbandwidthAllocProfile-TrafficShapersEntry 2 }

    bandwidthAllocProfile-TrafficShapers-Enabled	OBJECT-TYPE
	SYNTAX	INTEGER {
		    no (1),
		    yes (2)
		}
	ACCESS	read-write
	STATUS	mandatory
	DESCRIPTION	"TRUE if the shaper is enabled, otherwise FALSE."
	::= { mibbandwidthAllocProfile-TrafficShapersEntry 3 }

    bandwidthAllocProfile-TrafficShapers-BitRate	OBJECT-TYPE
	SYNTAX	INTEGER
	ACCESS	read-write
	STATUS	mandatory
	DESCRIPTION	"What is the sustained rate in Kilobits per second that can be transmitted by the VC(s) when using this shaper. Limited by the framer mode and the interface type."
	::= { mibbandwidthAllocProfile-TrafficShapersEntry 4 }

    bandwidthAllocProfile-TrafficShapers-PeakRate	OBJECT-TYPE
	SYNTAX	INTEGER
	ACCESS	read-write
	STATUS	mandatory
	DESCRIPTION	"What is the peak rate in Kilobits per second that can be transmitted by the VC(s) when using this shaper. Limited by the framer mode and the interface type."
	::= { mibbandwidthAllocProfile-TrafficShapersEntry 5 }

    bandwidthAllocProfile-TrafficShapers-MaxBurstSize	OBJECT-TYPE
	SYNTAX	INTEGER
	ACCESS	read-write
	STATUS	mandatory
	DESCRIPTION	"What is the maximum burst size in cell that can be transmitted during the peak rate by the VC(s) when using this shaper."
	::= { mibbandwidthAllocProfile-TrafficShapersEntry 6 }

    bandwidthAllocProfile-TrafficShapers-Aggregate	OBJECT-TYPE
	SYNTAX	INTEGER {
		    no (1),
		    yes (2)
		}
	ACCESS	read-write
	STATUS	mandatory
	DESCRIPTION	"If FALSE each individual VC gets the bit rate that is assigned to this shaper. If TRUE the VCs share the bit rate that is assigned to this shaper equally."
	::= { mibbandwidthAllocProfile-TrafficShapersEntry 7 }

    bandwidthAllocProfile-TrafficShapers-Priority	OBJECT-TYPE
	SYNTAX	INTEGER
	ACCESS	read-write
	STATUS	mandatory
	DESCRIPTION	"A number that represent the prioriy of the shaper in respect to other shapers. 0 is the highest priority and 15 is the lowest."
	::= { mibbandwidthAllocProfile-TrafficShapersEntry 8 }


	-- The mibbandwidthAllocProfile__bandwidth_config table
	--
	-- This table contains parameters for the mibbandwidthAllocProfile__bandwidth_config profile
	--

    mibbandwidthAllocProfile-BandwidthConfigTable	OBJECT-TYPE
	SYNTAX		SEQUENCE OF MibbandwidthAllocProfile-BandwidthConfigEntry
	ACCESS		not-accessible
	STATUS		mandatory
	DESCRIPTION	"A list of mibbandwidthAllocProfile__bandwidth_config profile entries."
	::= { mibbandwidthAllocProfile 4 }

    mibbandwidthAllocProfile-BandwidthConfigEntry	OBJECT-TYPE
	SYNTAX		MibbandwidthAllocProfile-BandwidthConfigEntry
	ACCESS		not-accessible
	STATUS		mandatory
	DESCRIPTION	"A mibbandwidthAllocProfile__bandwidth_config entry containing objects that
			 maps to the parameters of mibbandwidthAllocProfile__bandwidth_config profile."
	INDEX		{ bandwidthAllocProfile-BandwidthConfig-Index-o, bandwidthAllocProfile-BandwidthConfig-Index1-o }
	::= { mibbandwidthAllocProfile-BandwidthConfigTable 1 }

    MibbandwidthAllocProfile-BandwidthConfigEntry ::=
	SEQUENCE {
	    bandwidthAllocProfile-BandwidthConfig-Index-o
		INTEGER,
	    bandwidthAllocProfile-BandwidthConfig-Index1-o
		INTEGER,
	    bandwidthAllocProfile-BandwidthConfig-AllowMaxUpStreamBandwidth
		INTEGER,
	    bandwidthAllocProfile-BandwidthConfig-AllowGuaranteedUpStreamBandwidth
		INTEGER
	}

    bandwidthAllocProfile-BandwidthConfig-Index-o	OBJECT-TYPE
	SYNTAX	INTEGER
	ACCESS	read-only
	STATUS	mandatory
	DESCRIPTION	""
	::= { mibbandwidthAllocProfile-BandwidthConfigEntry 1 }

    bandwidthAllocProfile-BandwidthConfig-Index1-o	OBJECT-TYPE
	SYNTAX	INTEGER
	ACCESS	read-only
	STATUS	mandatory
	DESCRIPTION	""
	::= { mibbandwidthAllocProfile-BandwidthConfigEntry 2 }

    bandwidthAllocProfile-BandwidthConfig-AllowMaxUpStreamBandwidth	OBJECT-TYPE
	SYNTAX	INTEGER
	ACCESS	read-write
	STATUS	mandatory
	DESCRIPTION	"Allowed maximum upstream bandwidth of the slot in Kbits/sec. The slot can send upstream traffic up to this limit but there is no guarantee that slot will be able to send this much traffic."
	::= { mibbandwidthAllocProfile-BandwidthConfigEntry 3 }

    bandwidthAllocProfile-BandwidthConfig-AllowGuaranteedUpStreamBandwidth	OBJECT-TYPE
	SYNTAX	INTEGER
	ACCESS	read-write
	STATUS	mandatory
	DESCRIPTION	"Allowed guaranteed upstream bandwidth of the slot in Kbits/sec. The slot can have real-time (guaranteed) traffic bandwidth up to this limit. The total of guaranteed up stream bandwidth from all slots can not be more than the maximum bandwidth of the system."
	::= { mibbandwidthAllocProfile-BandwidthConfigEntry 4 }


	-- The mibbandwidthAllocProfile__slot_vpi_vci_range table
	--
	-- This table contains parameters for the mibbandwidthAllocProfile__slot_vpi_vci_range profile
	--

    mibbandwidthAllocProfile-SlotVpiVciRangeTable	OBJECT-TYPE
	SYNTAX		SEQUENCE OF MibbandwidthAllocProfile-SlotVpiVciRangeEntry
	ACCESS		not-accessible
	STATUS		mandatory
	DESCRIPTION	"A list of mibbandwidthAllocProfile__slot_vpi_vci_range profile entries."
	::= { mibbandwidthAllocProfile 5 }

    mibbandwidthAllocProfile-SlotVpiVciRangeEntry	OBJECT-TYPE
	SYNTAX		MibbandwidthAllocProfile-SlotVpiVciRangeEntry
	ACCESS		not-accessible
	STATUS		mandatory
	DESCRIPTION	"A mibbandwidthAllocProfile__slot_vpi_vci_range entry containing objects that
			 maps to the parameters of mibbandwidthAllocProfile__slot_vpi_vci_range profile."
	INDEX		{ bandwidthAllocProfile-SlotVpiVciRange-Index-o, bandwidthAllocProfile-SlotVpiVciRange-Index1-o }
	::= { mibbandwidthAllocProfile-SlotVpiVciRangeTable 1 }

    MibbandwidthAllocProfile-SlotVpiVciRangeEntry ::=
	SEQUENCE {
	    bandwidthAllocProfile-SlotVpiVciRange-Index-o
		INTEGER,
	    bandwidthAllocProfile-SlotVpiVciRange-Index1-o
		INTEGER,
	    bandwidthAllocProfile-SlotVpiVciRange
		INTEGER
	}

    bandwidthAllocProfile-SlotVpiVciRange-Index-o	OBJECT-TYPE
	SYNTAX	INTEGER
	ACCESS	read-only
	STATUS	mandatory
	DESCRIPTION	""
	::= { mibbandwidthAllocProfile-SlotVpiVciRangeEntry 1 }

    bandwidthAllocProfile-SlotVpiVciRange-Index1-o	OBJECT-TYPE
	SYNTAX	INTEGER
	ACCESS	read-only
	STATUS	mandatory
	DESCRIPTION	""
	::= { mibbandwidthAllocProfile-SlotVpiVciRangeEntry 2 }

    bandwidthAllocProfile-SlotVpiVciRange	OBJECT-TYPE
	SYNTAX	INTEGER {
		    vpi01Vci321023 (6),
		    vpi03Vci32511 (1),
		    vpi07Vci32255 (2),
		    vpi015Vci32127 (3),
		    vpi031Vci3263 (4),
		    notApplicable (5)
		}
	ACCESS	read-write
	STATUS	mandatory
	DESCRIPTION	"The valid range of vpi and vci for the LIM(s). This range is shared by all ports of the LIM. The user should be very careful while changing this value because ALL CONNECTIONS INVOLVING ANY OF THE PORTS OF THIS LIM WILL BE DROPPED BY THE SYSTEM IN ORDER TO MAKE NEW RANGE EFFECTIVE."
	::= { mibbandwidthAllocProfile-SlotVpiVciRangeEntry 3 }


	-- The mibbandwidthStatsProfile table
	--
	-- This table contains parameters for the mibbandwidthStatsProfile profile
	--

    mibbandwidthStatsProfileTable	OBJECT-TYPE
	SYNTAX		SEQUENCE OF MibbandwidthStatsProfileEntry
	ACCESS		not-accessible
	STATUS		mandatory
	DESCRIPTION	"A list of mibbandwidthStatsProfile profile entries."
	::= { mibbandwidthStatsProfile 1 }

    mibbandwidthStatsProfileEntry	OBJECT-TYPE
	SYNTAX		MibbandwidthStatsProfileEntry
	ACCESS		not-accessible
	STATUS		mandatory
	DESCRIPTION	"A mibbandwidthStatsProfile entry containing objects that
			 maps to the parameters of mibbandwidthStatsProfile profile."
	INDEX		{ bandwidthStatsProfile-Index-o }
	::= { mibbandwidthStatsProfileTable 1 }

    MibbandwidthStatsProfileEntry ::=
	SEQUENCE {
	    bandwidthStatsProfile-Index-o
		INTEGER,
	    bandwidthStatsProfile-MaxUpstreamBandwidth
		INTEGER,
	    bandwidthStatsProfile-ActiveUpstreamBandwidthOnTrunks
		INTEGER,
	    bandwidthStatsProfile-StandbyUpstreamBandwidthOnTrunks
		INTEGER,
	    bandwidthStatsProfile-Action-o
		INTEGER
	}

    bandwidthStatsProfile-Index-o	OBJECT-TYPE
	SYNTAX	INTEGER
	ACCESS	read-only
	STATUS	mandatory
	DESCRIPTION	""
	::= { mibbandwidthStatsProfileEntry 1 }

    bandwidthStatsProfile-MaxUpstreamBandwidth	OBJECT-TYPE
	SYNTAX	INTEGER
	ACCESS	read-only
	STATUS	mandatory
	DESCRIPTION	"Maximum system upstream bandwidth in Kbits/sec."
	::= { mibbandwidthStatsProfileEntry 2 }

    bandwidthStatsProfile-ActiveUpstreamBandwidthOnTrunks	OBJECT-TYPE
	SYNTAX	INTEGER
	ACCESS	read-only
	STATUS	mandatory
	DESCRIPTION	"Currently available upstream bandwidth on active primary trunks in Kbits/sec. This value is adjusted with number of active primary trunks and their available upstream bandwidth."
	::= { mibbandwidthStatsProfileEntry 3 }

    bandwidthStatsProfile-StandbyUpstreamBandwidthOnTrunks	OBJECT-TYPE
	SYNTAX	INTEGER
	ACCESS	read-only
	STATUS	mandatory
	DESCRIPTION	"Currently available upstream bandwidth on active standby trunks in Kbits/sec. This value is adjusted with number of active standby trunks and their available upstream bandwidth."
	::= { mibbandwidthStatsProfileEntry 4 }

    bandwidthStatsProfile-Action-o	OBJECT-TYPE
	SYNTAX	INTEGER {
		    noAction (1),
		    createProfile (2),
		    deleteProfile (3)
		}
	ACCESS	read-write
	STATUS	mandatory
	DESCRIPTION	""
	::= { mibbandwidthStatsProfileEntry 5 }

END
