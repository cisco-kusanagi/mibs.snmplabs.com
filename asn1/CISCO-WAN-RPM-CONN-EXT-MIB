-- *****************************************************************
--
-- CISCO-WAN-RPM-CONN-EXT-MIB.my: 
-- CISCO RPM(Router Processor Module)Connection Extension MIB
--
-- June 1999, Siu-Man Leung
-- May 2002, Subra Hegde
--
-- Copyright (c) 1999,2002 by cisco Systems, Inc.
-- All rights reserved.
-- 
-- *****************************************************************

CISCO-WAN-RPM-CONN-EXT-MIB DEFINITIONS ::= BEGIN
IMPORTS
    MODULE-IDENTITY,
    OBJECT-TYPE,
    Unsigned32                             FROM SNMPv2-SMI
    TruthValue                             FROM SNMPv2-TC
    MODULE-COMPLIANCE, 
    OBJECT-GROUP                           FROM SNMPv2-CONF
    ciscoWan                               FROM CISCOWAN-SMI
    cwAtmChanCnfgEntry                     FROM CISCO-WAN-ATM-CONN-MIB;


ciscoWanRpmConnExtMIB    MODULE-IDENTITY
    LAST-UPDATED    "200205210000Z"
    ORGANIZATION    "Cisco Systems, Inc."
    CONTACT-INFO
        "    Cisco Systems
             Customer Service

             Postal: 170 W Tasman Drive
             San Jose, CA 95134
             USA

             Tel: +1 800 553-NETS

             E-mail: cs-wanatm@cisco.com"

    DESCRIPTION
        "This MIB together with the CISCO-WAN-ATM-CONN-MIB support
         provisioning of PVC endpoints and SPVCs on the MGX's Route
         Processor Module (RPM)."

        REVISION     "200205210000Z"
        DESCRIPTION  "Importing Unsigned32 from SNMPv2-SMI."

        REVISION "200203180000Z"
        DESCRIPTION 
            "Modified the range of cwrChanVirtualTemplate
             to be consistent with value supported in CLI.
             The Range has been modified from 0..25 to 0..200."

        REVISION "199909300000Z"
        DESCRIPTION 
            "Initial Version of this MIB Module."
    ::= { ciscoWan 9 }


cwRpmConnExtMIBObjects OBJECT IDENTIFIER ::= { ciscoWanRpmConnExtMIB 1 }

cwRpmConnExt OBJECT IDENTIFIER ::= { cwRpmConnExtMIBObjects 1 }

cwRpmChanExtTable    OBJECT-TYPE
    SYNTAX        SEQUENCE OF CwRpmChanExtEntry
    MAX-ACCESS    not-accessible
    STATUS        current
    DESCRIPTION
        "This table together with the 'cwAtmChanCnfgTable' support
         provisioning of PVC endpoints and SPVCs on an RPM.  This
         table contains objects that are specific to RPM.
         This table is an augmentation to the 'cwAtmChanCnfgTable'."
    ::= { cwRpmConnExt 1 }

 
cwRpmChanExtEntry    OBJECT-TYPE
    SYNTAX        CwRpmChanExtEntry
    MAX-ACCESS    not-accessible
    STATUS        current
    DESCRIPTION
        "Each entry contains RPM specific parameters for a
         connection endpoint on an RPM."
    AUGMENTS    { cwAtmChanCnfgEntry }
    ::= { cwRpmChanExtTable 1 }


CwRpmChanExtEntry ::= SEQUENCE {
    cwrChanSubInterface           Unsigned32,
    cwrChanVcd                    Unsigned32,

    cwrChanAalEncapType           INTEGER,
    cwrChanVirtualTemplate        Unsigned32,
    cwrChanInArpInterval          Unsigned32,

    cwrChanOamLoopbkTxInterval    Unsigned32,
    cwrChanOamManage              TruthValue,
    cwrChanOamRetryUpCount        Unsigned32,
    cwrChanOamRetryDownCount      Unsigned32,
    cwrChanOamRetryInterval       Unsigned32
    }
 
cwrChanSubInterface    OBJECT-TYPE
    SYNTAX        Unsigned32 (0..4294967295)
    MAX-ACCESS    read-create
    STATUS        current
    DESCRIPTION
        "The RPM's backplane sub-interface for which this channel
         is configured. Sub-interface 0 means the switch port."
    DEFVAL { 0 }
    ::= { cwRpmChanExtEntry 1 }

cwrChanVcd        OBJECT-TYPE
    SYNTAX        Unsigned32 (0..4095)
    MAX-ACCESS    read-only
    STATUS        current
    DESCRIPTION
        "Virtual Circuit Descriptor. A unique number which identifies
         a connection."
    ::= { cwRpmChanExtEntry 2 }

cwrChanAalEncapType    OBJECT-TYPE
    SYNTAX  INTEGER {
              aal5ciscoPPP(1),
              aal5muxAPOLLO(2),
              aal5muxAPPLETALK(3),
              aal5muxDECNET(4),
              aal5muxIP(5),
              aal5muxIPX(6),
              aal5muxPPP(7),
              aal5muxVINES(8),
              aal5muxXNS(9),
              aal5nlpid(10),
              aal5snap(11),
              ilmi(12),
              qsaal(13)
            }
    MAX-ACCESS    read-create
    STATUS        current
    DESCRIPTION
        "ATM adaptation layer (AAL) and Encapsulation type.

         aal5ciscoPPP     - For Cisco PPP over ATM.
                            'cwrChanVirtualTemplate' is required to be
                            set for this type.
         aal5muxAPOLLO    - For a multiplex (MUX) - type virtual
                            circuit using the Apollo protocol.
         aal5muxAPPLETALK - For a MUX-type virtual circuit using the
                            AppleTalk protocol.
         aal5muxDECNET    - For a MUX-type virtual circuit using the
                            DECnet protocol.
         aal5muxIP        - For a MUX-type virtual circuit using the
                            IP protocol.
         aal5muxIPX       - For a MUX-type virtual circuit using the
                            IPX protocol.
         aal5muxPPP       - For a MUX-type virtual circuit using the
                            PPP protocol.
                            'cwrChanVirtualTemplate' is required to be
                            set for this type.
         aal5muxVINES     - For a MUX-type virtual circuit using the
                            VINES protocol.
         aal5muxXNS       - For a MUX-type virtual circuit using the
                            XNS protocol.
         aal5nlpid        - Allows ATM interfaces to interoperate with
                            HSSI.
         aal5snap         - The only encapsulation supported for
                            Inverse ARP. Logical Link Control/
                            Subnetwork Access Protocol (LLC/SNAP)
                            precedes the protocol datagram.
         ilmi             - Used to set up communication with ILMI.
         qsaal            - A signalling type PVC used for setting up
                            or tearing down SVCs."
    DEFVAL { aal5snap }
    ::= { cwRpmChanExtEntry 3 }

cwrChanVirtualTemplate    OBJECT-TYPE
    SYNTAX        Unsigned32 (0..200)
    MAX-ACCESS    read-create
    STATUS        current
    DESCRIPTION
            "This object identifies the virtual template. 

            The non-zero value need to be specified for
            Cisco PPP or MUX-type PPP encapsulation 
            (i.e. cwrChanAalEncapType = aal5ciscoPPP or
            aal5muxPPP). 

            The value 0 signifies that Virtual Template
            is not applicable. "
    DEFVAL { 0 }
    ::= { cwRpmChanExtEntry 4 }

cwrChanInArpInterval    OBJECT-TYPE        
     SYNTAX        Unsigned32 (0..60)
    UNITS        "minutes"
    MAX-ACCESS    read-create
    STATUS        current
    DESCRIPTION
        "This specifies how often Inverse ARP datagrams will be sent
         on this channel.  0 will disable the InArp for this channel.
         This object is only supported for aal5snap encapsulation
         (i.e. cwrChanAalEncapType = aal5snap)."
    DEFVAL { 15 }
    ::= { cwRpmChanExtEntry 5 }

cwrChanOamLoopbkTxInterval OBJECT-TYPE
    SYNTAX        Unsigned32 (0..600)
    UNITS        "seconds"
    MAX-ACCESS    read-create
    STATUS        current
    DESCRIPTION
        "This specifies how often to generate an OAM F5 loopback cell
         from this channel.  0 will disable generation of OAM F5
         loopback cells."
    DEFVAL { 10 }
    ::= { cwRpmChanExtEntry 6 }

cwrChanOamManage    OBJECT-TYPE
    SYNTAX        TruthValue
    MAX-ACCESS    read-create
    STATUS        current
    DESCRIPTION
        "This enables/disables OAM management for this channel.
         If set to true(1), OAM management is enabled."
    DEFVAL { false }
    ::= { cwRpmChanExtEntry 7 }

cwrChanOamRetryUpCount    OBJECT-TYPE
    SYNTAX        Unsigned32 (1..600)
    MAX-ACCESS    read-create
    STATUS        current
    DESCRIPTION
        "Number of consecutive end-to-end F5 OAM loopback cell
         responses that must be received in order to change a PVC
         connection state to up.
         This object only applies if OAM management is enabled
         (i.e. cwrChanOAMManage = true)."
    DEFVAL { 3 }
    ::= { cwRpmChanExtEntry 8 } 

cwrChanOamRetryDownCount    OBJECT-TYPE
    SYNTAX        Unsigned32 (1..600)
    MAX-ACCESS    read-create
    STATUS        current
    DESCRIPTION
        "Number of consecutive end-to-end F5 OAM loopback cell
         responses that are not received in order to change a PVC
         connection state to down.
         This object only applies if OAM management is enabled
         (i.e. cwrChanOAMManage = true)."
    DEFVAL { 5 }
    ::= { cwRpmChanExtEntry 9 }

cwrChanOamRetryInterval    OBJECT-TYPE
    SYNTAX        Unsigned32 (1..1000)
    UNITS        "seconds"
    MAX-ACCESS    read-create
    STATUS        current
    DESCRIPTION
        "The frequency that end-to-end F5 OAM loopback cells are
         transmitted when a change in UP/DOWN state of a PVC is
         being verified.
         This object only applies if OAM management is enabled
         (i.e. cwrChanOAMManage = true)."
    DEFVAL { 1 }
    ::= { cwRpmChanExtEntry 10 }


-- conformance information

ciscoWanRpmConnExtMIBConformance
        OBJECT IDENTIFIER ::= { ciscoWanRpmConnExtMIB 2 }
ciscoWanRpmConnExtMIBCompliances
        OBJECT IDENTIFIER ::= { ciscoWanRpmConnExtMIBConformance 1 }
ciscoWanRpmConnExtMIBGroups
        OBJECT IDENTIFIER ::= { ciscoWanRpmConnExtMIBConformance 2 }


-- compliance statements

ciscoWanRpmConnExtMIBCompliance MODULE-COMPLIANCE
    STATUS    current
    DESCRIPTION
        "The compliance statement for the Cisco MGX RPM connection 
         management group."
    MODULE  -- this module
    MANDATORY-GROUPS { 
                   ciscoWanRpmConnExtMIBGroup
                 }

    ::= { ciscoWanRpmConnExtMIBCompliances 1 }

-- units of conformance


ciscoWanRpmConnExtMIBGroup    OBJECT-GROUP
    OBJECTS { 
        cwrChanSubInterface,
        cwrChanVcd,
        
        cwrChanAalEncapType,
        cwrChanVirtualTemplate,
        cwrChanInArpInterval,
    
        cwrChanOamLoopbkTxInterval,
        cwrChanOamManage,
        cwrChanOamRetryUpCount,
        cwrChanOamRetryDownCount,
        cwrChanOamRetryInterval
    }
    STATUS    current
    DESCRIPTION
        "Objects related to ATM connection in RPM module."
    ::= { ciscoWanRpmConnExtMIBGroups 1 }

END
