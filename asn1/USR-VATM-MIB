USR-VATM-MIB DEFINITIONS ::= BEGIN

IMPORTS
        OBJECT-TYPE
                FROM SNMPv2-SMI
        DisplayString
                 FROM SNMPv2-TC
   		ifIndex
	   		FROM IF-MIB
        usrVatmMib, UsrConfigStatus
                FROM USR-DEFINITIONS-MIB;


-- Textual conventions

-- VIPER ATM object type definitions

-- VIPER ATM Mib objects definitions

usrVatmMibObjects OBJECT IDENTIFIER ::= { usrVatmMib 1 }

--
-- The VATM Base Group.
--

usrVatmBaseGroup      OBJECT IDENTIFIER ::= { usrVatmMibObjects 1 }

usrVatmBaseCfgFileName OBJECT-TYPE
	    SYNTAX   DisplayString
        MAX-ACCESS   read-write
	    STATUS   current
	    DESCRIPTION		
		    "The name of a ConfigFile to read/write
			permanent database records. If the value of this
			object is an empty string, then the VATM process
			uses the default name `@file://Vatm.cfg'."
        ::= { usrVatmBaseGroup 1 }

usrVatmBaseCFMSaveStatus OBJECT-TYPE
        SYNTAX  UsrConfigStatus
        MAX-ACCESS  read-write
        STATUS  current
        DESCRIPTION
            "Setting the value of this object to `save'
            Causes the values of the VATM Group
            entries to be written out to the current VATM
            config file. While the new config file is being
            written, the VATM process will set the value
            of this flag set to `saving''. Any attempts to set
            the value while it is  not `normal' (i.e. the file
            is currently being written to the config file)
            while result in a badValue error being returned.
            Setting the value to `normal' will result in no
            action."
        ::= { usrVatmBaseGroup 2 }

usrVatmBaseDspVersion OBJECT-TYPE
	    SYNTAX   DisplayString
        MAX-ACCESS read-only
	    STATUS   current
	    DESCRIPTION		
		    "The version of the code loaded on the DSP."
        ::= { usrVatmBaseGroup 3 }

usrVatmLineGroup      OBJECT IDENTIFIER ::= { usrVatmMibObjects 2 }

usrVatmLineTable OBJECT-TYPE
        SYNTAX SEQUENCE OF UsrVatmLineTableEntry
        MAX-ACCESS not-accessible
        STATUS current
        DESCRIPTION
            "Table containing configuration and operational
            parameters for all VIPER ATM
            interfaces on this managed device."
        ::= { usrVatmLineGroup 1 }

usrVatmLineTableEntry OBJECT-TYPE
        SYNTAX UsrVatmLineTableEntry
        MAX-ACCESS not-accessible
        STATUS current
        DESCRIPTION
            "An entry in the VATM Line Table."
     	INDEX { ifIndex }
        ::= { usrVatmLineTable 1 }

UsrVatmLineTableEntry ::= SEQUENCE {
        usrVatmLineTblCellDelineation INTEGER,
        usrVatmLineTblIlmiVpi INTEGER,
		usrVatmLineTblIlmiVci INTEGER,
		usrVatmLineTblTxCells INTEGER,
		usrVatmLineTblTxIdleCells INTEGER, 
		usrVatmLineTblRxGoodCells INTEGER,
		usrVatmLineTblRxIdleCells INTEGER,
		usrVatmLineTblRxNoPktAvail INTEGER,
		usrVatmLineTblRxBadVpiVci INTEGER,
		usrVatmLineTblRxBadHec INTEGER,
		usrVatmLineTblMaxRxBadHec INTEGER,
		usrVatmLineTblRxQueueFull INTEGER,
		usrVatmLineTblUpSpeed INTEGER,
		usrVatmLineTblDownSpeed INTEGER,
		usrVatmLineTblUniVersion INTEGER,
        usrVatmLineTblIdleCellType INTEGER
		}

usrVatmLineTblCellDelineation OBJECT-TYPE
        SYNTAX INTEGER {
          notAcheived(1),
          acheived(2)
        }
        MAX-ACCESS read-only
        STATUS current
        DESCRIPTION
            "Indicates whether or not cell delineation
             has been acheived."
        ::= { usrVatmLineTableEntry 1 }

usrVatmLineTblIlmiVpi OBJECT-TYPE
     	SYNTAX    INTEGER  (0..4095)
        MAX-ACCESS read-write
        STATUS current
        DESCRIPTION
            "The VPI value that will be used by ILMI."
        DEFVAL { 0 }
	    --CONFIGURABLE
        ::= { usrVatmLineTableEntry 2 }

usrVatmLineTblIlmiVci OBJECT-TYPE
     	SYNTAX    INTEGER  (0..65535)
        MAX-ACCESS read-write
        STATUS current
        DESCRIPTION
            "The VCI value that will be used by ILMI."
        DEFVAL { 0 }
	    --CONFIGURABLE
        ::= { usrVatmLineTableEntry 3 }

usrVatmLineTblTxCells    OBJECT-TYPE
     	SYNTAX       INTEGER
     	MAX-ACCESS     read-only
     	STATUS         current
     	DESCRIPTION
      	"The number of cells transmitted."
     	::= { usrVatmLineTableEntry 4}

usrVatmLineTblTxIdleCells    OBJECT-TYPE
     	SYNTAX       INTEGER
     	MAX-ACCESS     read-only
     	STATUS         current
     	DESCRIPTION
      	"The number of idle cells transmitted."
     	::= { usrVatmLineTableEntry 5}

usrVatmLineTblRxGoodCells    OBJECT-TYPE
     	SYNTAX       INTEGER
     	MAX-ACCESS     read-only
     	STATUS         current
     	DESCRIPTION
      	"The number of good cells received."
     	::= { usrVatmLineTableEntry 6}

usrVatmLineTblRxIdleCells    OBJECT-TYPE
     	SYNTAX       INTEGER
     	MAX-ACCESS     read-only
     	STATUS         current
     	DESCRIPTION
      	"The number of idle cells received."
     	::= { usrVatmLineTableEntry 7}


usrVatmLineTblRxNoPktAvail    OBJECT-TYPE
     	SYNTAX       INTEGER
     	MAX-ACCESS     read-only
     	STATUS         current
     	DESCRIPTION
      	"The number of received cells dropped because no 
	  	packet buffer was available."
     	::= { usrVatmLineTableEntry 8}

usrVatmLineTblRxBadVpiVci    OBJECT-TYPE
     	SYNTAX       INTEGER
     	MAX-ACCESS     read-only
     	STATUS         current
     	DESCRIPTION
      	"The number of received cells dropped because 
	  	the VPI or VCI was not valid."
     	::= { usrVatmLineTableEntry 9}

usrVatmLineTblRxBadHec    OBJECT-TYPE
     	SYNTAX       INTEGER
     	MAX-ACCESS     read-only
     	STATUS         current
     	DESCRIPTION
      	"The number of received cells dropped because, oh 
	   	what the heck."
     	::= { usrVatmLineTableEntry 10}

usrVatmLineTblMaxRxBadHec OBJECT-TYPE
		SYNTAX   INTEGER
		MAX-ACCESS   read-write
		STATUS       current
		DESCRIPTION
			"The maximum allowed Bad Hec received per second before link
		     restarts. (Included for Lucent testing.)"
	   		--CONFIGURABLE
		::= { usrVatmLineTableEntry 11}

usrVatmLineTblRxQueueFull    OBJECT-TYPE
     	SYNTAX       INTEGER
     	MAX-ACCESS     read-only
     	STATUS         current
     	DESCRIPTION
      	"The number of received cells dropped because 
	  	the receive queue was full."
     	::= { usrVatmLineTableEntry 12}

usrVatmLineTblUpSpeed OBJECT-TYPE
     	SYNTAX       INTEGER
     	MAX-ACCESS     read-only
     	STATUS         current
     	DESCRIPTION
      	"The negotiated upstream speed."
     	::= { usrVatmLineTableEntry 13}

usrVatmLineTblDownSpeed OBJECT-TYPE
     	SYNTAX       INTEGER
     	MAX-ACCESS     read-only
     	STATUS         current
     	DESCRIPTION
      	"The negotiated downstream speed."
     	::= { usrVatmLineTableEntry 14}

usrVatmLineTblUniVersion OBJECT-TYPE
       SYNTAX      INTEGER {
	                        uni31 (1),
                            uni40 (2)
                           }
       MAX-ACCESS      read-write
       STATUS     		current 
       DESCRIPTION "This switch is to set ATM WAN interface UNI (user to network) version"
		DEFVAL { 1 }
	    --CONFIGURABLE
		::= { usrVatmLineTableEntry 15}

usrVatmLineTblIdleCellType OBJECT-TYPE
	   SYNTAX      INTEGER {
						   	normal (1),
						   	normalITU (2)
						   }
	   MAX-ACCESS      read-write
	   STATUS           current
	   DESCRIPTION "Selects unassigned or ITU Idle cell format "
	  	DEFVAL { 2 }
		-- CONFIGURABLE
		::= { usrVatmLineTableEntry 16}

-- The VC group

usrVatmVcGroup OBJECT IDENTIFIER ::= { usrVatmMibObjects 3 }

usrVatmVcTable OBJECT-TYPE
        SYNTAX SEQUENCE OF UsrVatmVcTableEntry
        MAX-ACCESS not-accessible
        STATUS current
        DESCRIPTION
            "Table containing configuration and operational
            parameters for all VIPER ATM
            interfaces on this managed device."
        ::= { usrVatmVcGroup 1 }

usrVatmVcTableEntry OBJECT-TYPE
        SYNTAX UsrVatmVcTableEntry
        MAX-ACCESS not-accessible
        STATUS current
        DESCRIPTION
            "An entry in the VATM Line Table."
     	INDEX  {ifIndex, usrVatmVcVpi, usrVatmVcVci }
        ::= { usrVatmVcTable 1 }


UsrVatmVcTableEntry ::= SEQUENCE {
		usrVatmVcVpi        			INTEGER,
		usrVatmVcVci        			INTEGER,
		usrVatmVcIndex        			INTEGER,
		usrVatmVcIfName        			OCTET STRING,
		usrVatmVcName        			OCTET STRING,
        usrVatmVcTxPkts 				INTEGER,
        usrVatmVcTxBytes 				INTEGER,
		usrVatmVcRxGoodPkts 			INTEGER,
        usrVatmVcRxBytes 				INTEGER,
		usrVatmVcRxPktBadCrc 			INTEGER,
		usrVatmVcRxPktTooBig 			INTEGER, 
		usrVatmVcRxReassemblyTimeout	INTEGER,
		usrVatmVcTxKbpsPerSec			INTEGER,
		usrVatmVcRxKbpsPerSec			INTEGER,
		usrVatmVcCounterResetFlag		INTEGER
        }

usrVatmVcVpi    OBJECT-TYPE
     SYNTAX    INTEGER  (0..4095)
     MAX-ACCESS     read-only
     STATUS         current
     DESCRIPTION
      "The VPI value of the VCL."
     ::= { usrVatmVcTableEntry 1}

usrVatmVcVci    OBJECT-TYPE
     SYNTAX    INTEGER  (0..65535)
     MAX-ACCESS     read-only
     STATUS         current
     DESCRIPTION
      "The VCI value of the VCL.
       The maximum VCI value cannot
       exceed the value allowable by the
       atmInterfaceMaxVciBits."
     ::= { usrVatmVcTableEntry 2}

usrVatmVcIndex    OBJECT-TYPE
     SYNTAX    INTEGER  (0..65535)
     MAX-ACCESS     read-only
     STATUS         current
     DESCRIPTION
      "The ifIndex of the interface
       carrying the VCL."
     ::= { usrVatmVcTableEntry 3}

usrVatmVcIfName    OBJECT-TYPE
     SYNTAX    OCTET STRING
     MAX-ACCESS     read-only
     STATUS         current
     DESCRIPTION
      "The value of the Name that
       identifies the interface over
	   which this VCL is operating."
     ::= { usrVatmVcTableEntry 4}

usrVatmVcName    OBJECT-TYPE
     SYNTAX    OCTET STRING
     MAX-ACCESS     read-only
     STATUS         current
     DESCRIPTION
      "The value of the friendly Name 
       associated with this VCL."
     ::= { usrVatmVcTableEntry 5}

usrVatmVcTxPkts    OBJECT-TYPE
     SYNTAX       INTEGER
     MAX-ACCESS     read-only
     STATUS         current
     DESCRIPTION
      "The number of transmitted packets."
     ::= { usrVatmVcTableEntry 6}

usrVatmVcTxBytes    OBJECT-TYPE
     SYNTAX       INTEGER
     MAX-ACCESS     read-only
     STATUS         current
     DESCRIPTION
      "The number of transmitted bytes."
     ::= { usrVatmVcTableEntry 7}

usrVatmVcRxGoodPkts    OBJECT-TYPE
     SYNTAX       INTEGER
     MAX-ACCESS     read-only
     STATUS         current
     DESCRIPTION
      "The number of valid received packets."
     ::= { usrVatmVcTableEntry 8}

usrVatmVcRxBytes    OBJECT-TYPE
     SYNTAX       INTEGER
     MAX-ACCESS     read-only
     STATUS         current
     DESCRIPTION
      "The number of received bytes."
     ::= { usrVatmVcTableEntry 9}


usrVatmVcRxPktBadCrc    OBJECT-TYPE
     SYNTAX       INTEGER
     MAX-ACCESS     read-only
     STATUS         current
     DESCRIPTION
      "The number of packets received with bad crc."
     ::= { usrVatmVcTableEntry 10}

usrVatmVcRxPktTooBig    OBJECT-TYPE
     SYNTAX       INTEGER
     MAX-ACCESS     read-only
     STATUS         current
     DESCRIPTION
      "The number of packets received that were too big."
     ::= { usrVatmVcTableEntry 11}

usrVatmVcRxReassemblyTimeout    OBJECT-TYPE
     SYNTAX       INTEGER
     MAX-ACCESS     read-only
     STATUS         current
     DESCRIPTION
      "The number of packets received with
	  reassembly timeout."
     ::= { usrVatmVcTableEntry 12}

usrVatmVcTxKbpsPerSec	OBJECT-TYPE
     SYNTAX       INTEGER
     MAX-ACCESS     read-only
     STATUS         current
     DESCRIPTION
      "Tx Kbps/sec for a particular VC"
     ::= { usrVatmVcTableEntry 13}

usrVatmVcRxKbpsPerSec	OBJECT-TYPE
     SYNTAX       INTEGER
     MAX-ACCESS     read-only
     STATUS         current
     DESCRIPTION
      "Rx Kbps/sec for a particular VC"
     ::= { usrVatmVcTableEntry 14}

usrVatmVcCounterResetFlag	OBJECT-TYPE
     SYNTAX       INTEGER
     MAX-ACCESS     read-write
     STATUS         current
     DESCRIPTION
      "Flag for reset vpi/vci statistics"
     ::= { usrVatmVcTableEntry 15}
END
