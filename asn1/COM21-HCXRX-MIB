-- 
--  Copyright 1996, Com21 Inc.  All Rights Reserved.
--
 
COM21-HCXRX-MIB DEFINITIONS ::= BEGIN
        IMPORTS MODULE-IDENTITY, OBJECT-TYPE, NOTIFICATION-TYPE, Integer32,
        IpAddress, Gauge32
        FROM SNMPv2-SMI
        DisplayString, MacAddress
        FROM SNMPv2-TC
        com21, com21Hcx
        FROM COM21-HCX-MIB
        com21Traps FROM COM21-HCX-MIB
		  hcxAlmSeverity, hcxEventLogTime
        FROM COM21-HCXALM-MIB;


        com21HcxRx MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"

                DESCRIPTION
                        "This is the Com21 ComController RX card MIB.
			 COM21 Part# 005-0025-00"
                ::= { com21Hcx 30 }

        com21HcxUpstrmPortGroup         OBJECT IDENTIFIER ::= {com21Hcx 31 }
        com21HcxUpstrmStatsGroup        OBJECT IDENTIFIER ::= {com21Hcx 32 }
        com21HcxUpstrmUnitGroup         OBJECT IDENTIFIER ::= {com21Hcx 33 }
        com21HcxVciStatsGroup           OBJECT IDENTIFIER ::= {com21Hcx 34 }
        com21HcxRpmIPortGroup           OBJECT IDENTIFIER ::= {com21Hcx 35 }
        com21HcxRpmStatsGroup           OBJECT IDENTIFIER ::= {com21Hcx 36 }
        com21HcxRfAnalysisGroup         OBJECT IDENTIFIER ::= {com21Hcx 37 }

        UpstrmFreqKhz    ::= INTEGER (5000..40000)
        PrimServiceState ::= INTEGER { is(1), oos(2) }
	RfAnalysisdBmv   ::= INTEGER (-58..-5)


        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the 
	-- SNMP interface and the MIB II Interfaces Group for both the 
	-- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        --   com21HcxUpstrmUnitGroup    - this group provides for monitor and
        --                                control of a single RF RX card. As
        --                                noted above, all control of the port
        --                                state shall be performed through this
        --                                card level group.
        --
        --   com21HcxUpstrmPortGroup    - this group represents a single
        --                                upstream RF port on the RF RX card.
        --                                Note that the RX card contains only
        --                                one port. Therefore the control of
        --                                port state is presently at the card
        --                                level. If a multiport card is
        --                                produced in the future, this group
        --                                shall be expanded.
        --
        --   com21HcxUpstrmStatsGroup   - this group holds statistical data
        --                                related to the overall upstream
        --                                RF link.
        --
        --   com21HcxVciStatsGroup      - this group holds statistical data
        --                                related to individual VCs in the
        --                                system. The statistical data shall
        --                                be collected in differing physical
	--
	--   com21HcxRpmIPortGroup	- this group holds the config and
	--				  state information related to a
	--				  specific RPM I-Port.
	--
	--   com21HcxRpmStatsGroup      - this group holds the statistical
	--				  data related to a single RPM I-Port.
	--
	--   com21HcxRfAnalysisGroup	- this group provides an operator
	--				  with the ability to define RF
	--				  analysis.
        --
        -- -- -- -- -- -- -- -- -- -- -- -- -- -- -- -- -- -- -- -- -- -- -- --
        -- -- -- -- -- -- -- -- -- -- -- -- -- -- -- -- -- -- -- -- -- -- -- --
 
 
  
        -- -- -- -- -- -- -- -- -- -- -- -- -- -- -- -- -- -- -- -- -- -- -- --
        -- -- -- -- -- -- -- -- -- -- -- -- -- -- -- -- -- -- -- -- -- -- -- --
        --
        -- com21HcxUpstrmUnitGroup
        --
        -- defines the attributes related to the management of the 
        -- ComController RF Receiver Unit.
        --
        -- -- -- -- -- -- -- -- -- -- -- -- -- -- -- -- -- -- -- -- -- -- -- --
        -- -- -- -- -- -- -- -- -- -- -- -- -- -- -- -- -- -- -- -- -- -- -- --

        com21HcxUpstrmUnitTable OBJECT-TYPE
                SYNTAX  SEQUENCE OF HcxUpstrmUnitEntry
                MAX-ACCESS  not-accessible
                STATUS  current
                DESCRIPTION "."
                ::= { com21HcxUpstrmUnitGroup 1 }
 
        com21HcxUpstrmUnitEntry OBJECT-TYPE
                SYNTAX  HcxUpstrmUnitEntry
                MAX-ACCESS  not-accessible
                STATUS  current
                DESCRIPTION "."
                INDEX { hcxUpstreamShelfId, hcxUpstreamSlotId }
                ::= { com21HcxUpstrmUnitTable 1 }

	HcxUpstrmUnitEntry ::= SEQUENCE {
		hcxUpstreamShelfId		INTEGER,
		hcxUpstreamSlotId		Integer32,
                hcxUpstreamHardwareVersion      DisplayString,
                hcxUpstreamBootVersion          DisplayString,
		hcxUpstreamUnitPrimServState	PrimServiceState,
		hcxUpstreamUnitSecServState	DisplayString,
		hcxUpstreamUnitConfigState	INTEGER,
		hcxUpstreamUnitRestartAction	INTEGER,
		hcxUpstreamGroupId		INTEGER,
		hcxAcquisitionEnable		INTEGER,
        	hcxUpDiagTestAction 		INTEGER,
        	hcxUpDiagTestResult		INTEGER,
		hcxUpTestStatusLed		INTEGER,
		hcxUpFaultStatusLed		INTEGER,
                hcxUpstreamSerialNumber         DisplayString }

        hcxUpstreamShelfId OBJECT-TYPE
                SYNTAX INTEGER (1..2)
                MAX-ACCESS read-only
                STATUS current
                DESCRIPTION "
                        contains upstream shelf id."
                ::= { com21HcxUpstrmUnitEntry 1 }

        hcxUpstreamSlotId OBJECT-TYPE
                SYNTAX Integer32
                MAX-ACCESS read-only
                STATUS current
                DESCRIPTION "
                        contains upstream unit id. This is the slot number."
                ::= { com21HcxUpstrmUnitEntry 2 }

        hcxUpstreamHardwareVersion OBJECT-TYPE
                SYNTAX DisplayString (SIZE (16))
                MAX-ACCESS read-only   
                STATUS current
                DESCRIPTION "  
                        contains the hardware version of the RX card. Will
			be empty if card not present."
                ::= { com21HcxUpstrmUnitEntry 3 }
 
        hcxUpstreamBootVersion OBJECT-TYPE
                SYNTAX DisplayString (SIZE (16))
                MAX-ACCESS read-only
                STATUS current
                DESCRIPTION "
                        contains the version of the RX card boot ROM. This
			will be an empty string if card is missing."
                ::= { com21HcxUpstrmUnitEntry 4 }
 
        hcxUpstreamUnitPrimServState OBJECT-TYPE
                SYNTAX PrimServiceState
                MAX-ACCESS read-only
                STATUS current
                DESCRIPTION "
                        contains primary service state of the Upstream 
			Unit."
                ::= { com21HcxUpstrmUnitEntry 5 }

        hcxUpstreamUnitPrimStateChange NOTIFICATION-TYPE
                OBJECTS { hcxAlmSeverity, hcxEventLogTime,
                            hcxUpstreamShelfId, hcxUpstreamSlotId,
			    hcxUpstreamUnitPrimServState }
                STATUS current
                DESCRIPTION "
			Generated whenever a the hcxUpstreamUnitPrimServState
			changes in value. This an event with no clear 
			condition. Only severity is WARNING."
                ::= { com21Traps 30 }
 
        hcxUpstreamUnitSecServState OBJECT-TYPE
                SYNTAX DisplayString (SIZE (16))
                MAX-ACCESS read-only
                STATUS current
                DESCRIPTION "
                        contains a string defining the secondary service states
			of the Upstream Unit. The substrings supported by 
			the Upstream Unit shall be: TEST - in test, as set 
			by hcxUpstreamUnitConfigState, MT - offline, again set 
			by hcxUpstreamUnitConfigState, FAULT - hardware 
			failure, UNEQ - unequipped."
                ::= { com21HcxUpstrmUnitEntry 6 }

        hcxUpstreamUnitSecStateChange NOTIFICATION-TYPE
                OBJECTS { hcxAlmSeverity, hcxEventLogTime,
                            hcxUpstreamShelfId, hcxUpstreamSlotId,
                            hcxUpstreamUnitSecServState }
                STATUS current
                DESCRIPTION "
			Generated whenever a the hcxUpstreamUnitSecServState
			changes in value. This an event with no clear 
			condition. Only severity is WARNING."
                ::= { com21Traps 31 }
  
        hcxUpstreamUnitConfigState OBJECT-TYPE
                SYNTAX INTEGER {
                                offline(2000),
                                online(2001),
                                test(2002) }
                MAX-ACCESS read-write
                STATUS current
                DESCRIPTION "
                        The Upstream Unit State is an active-value. 
			Offline will disable the RF and all other cell 
			forwarding. 
			Online enables RF and performs all traffic and
			scheduling functions.
			Test will also place the card offline but shall 
			allow a diagnostic test.
			Maintenance keeps RF alive but RX performs no
			scheduling. Note that RX card will not enter
			the maintenance state if there are any
			authorized ComPorts. It is the responsibility of
			the CC to hop any ComPorts prior to entering this
			state.
			Offline is default."
                ::= { com21HcxUpstrmUnitEntry 7 }

	hcxUpstreamUnitRestartAction OBJECT-TYPE
                SYNTAX INTEGER {
                                nil(1),
                                restart(2) }
                MAX-ACCESS read-write
                STATUS current
                DESCRIPTION "
			The RX Unit Restart Action is an active-value.
			The setting of this attribute to restart(2) causes
			the RX card to reset and download a new image."
                ::= { com21HcxUpstrmUnitEntry 8 }
		
        hcxUpstreamGroupId OBJECT-TYPE
                SYNTAX INTEGER (1..12)
                MAX-ACCESS read-write
                STATUS current
                DESCRIPTION "
              		The Upstream group id defines the receiver
                        group to which this RF Receiver belongs. The 
                        shall ensure that the group contains a single RF
                        Receiver card operating as an ComPort acquirer.
			Default is group 1."
                ::= { com21HcxUpstrmUnitEntry 9 }

        hcxAcquisitionEnable OBJECT-TYPE
                SYNTAX INTEGER { true (1), false (2) }
                MAX-ACCESS read-write
                STATUS current
                DESCRIPTION "
                        Used to select an RF Receiver for acquisition.
                        The ComController shall ensure that only one RX
                        card in a receiver group is selected for
                        acquisition."
                ::= { com21HcxUpstrmUnitEntry 10 }

        hcxUpDiagTestAction OBJECT-TYPE
                SYNTAX INTEGER { nil(1), execute(2) }
                MAX-ACCESS read-write
                STATUS current
                DESCRIPTION "
                        This attribute is used to invoke the internal
                        RX diagnostic test. In order to activate this
			test, the card must be placed in the test state."
                ::= { com21HcxUpstrmUnitEntry 11 }

        hcxUpDiagTestComplete NOTIFICATION-TYPE
                OBJECTS { hcxAlmSeverity, hcxEventLogTime,
                            hcxUpstreamShelfId, hcxUpstreamSlotId,
                            hcxUpDiagTestResult }
                STATUS current
                DESCRIPTION "
                        This notification is generated whenever the RX
                        internal diagnostic tests are completed. This an event
                        with no clear condition. Only severity is WARNING."
                ::= { com21Traps 32 }

        hcxUpDiagTestResult OBJECT-TYPE
                SYNTAX INTEGER { 
				inprogress(1),
				success(2), 
				failure(3),
				invalidState(4) }
                MAX-ACCESS read-only
                STATUS current
                DESCRIPTION "
                        This attribute contains the result of the last RX
                        diagnostic test."
                ::= { com21HcxUpstrmUnitEntry 12 }

	hcxUpTestStatusLed OBJECT-TYPE
                SYNTAX INTEGER { on (1), off (2) }
                MAX-ACCESS read-only
                STATUS current
                DESCRIPTION "
                        The RX Test Status LED is a read-only attribute 
			which describes the condition of the RX
                        Test Status light emitting diode located on
                        the RX board. A value of on(1) indicates that a
                        service effecting test is in progress and that 
			the LED is illuminated. off if no card present."
                ::= { com21HcxUpstrmUnitEntry 13 }

        hcxUpTestStatusLedChange NOTIFICATION-TYPE
                OBJECTS { hcxAlmSeverity, hcxEventLogTime,
                            hcxUpstreamShelfId, hcxUpstreamSlotId,
                            hcxUpTestStatusLed }
                STATUS current
                DESCRIPTION "
                        generated whenever there is a change in test LED
                        status. This an event with no clear condition.
                        Only severity is WARNING."
                ::= { com21Traps 33  }

        hcxUpFaultStatusLed OBJECT-TYPE 
                SYNTAX INTEGER { on (1), off (2) } 
                MAX-ACCESS read-only 
                STATUS current 
                DESCRIPTION " 
                        The RX Fault Status LED is a read-only attribute 
                        which describes the condition of the RX
                        Fault Status light emitting diode located on
                        the RX board. A value of on(1) indicates that an
                        fault condition has been detected (for which a
			trap will have been issued) and the LED is 
			illuminated. off if no card present."
                ::= { com21HcxUpstrmUnitEntry 14 } 
 
        hcxUpFaultStatusLedChange NOTIFICATION-TYPE
                OBJECTS { hcxAlmSeverity, hcxEventLogTime, 
                            hcxUpstreamShelfId, hcxUpstreamSlotId,
                            hcxUpFaultStatusLed } 
                STATUS current
                DESCRIPTION " 
                        generated whenever there is a change in the Fault
			LED status. This an event with no clear condition. 
                        Only severity is WARNING." 
                ::= { com21Traps 34 }

        hcxUpOperationFailure NOTIFICATION-TYPE
                OBJECTS { hcxAlmSeverity, hcxEventLogTime,
                            hcxUpstreamShelfId, hcxUpstreamSlotId }
                STATUS current
                DESCRIPTION "
                        This notification is generated by the CC whenever 
			an RX card fails to respond correctly to a
			request. This failure could indicate either a
			resource problem or software failure. Note that
			if an RX card failures to respond completely to
			a CC request, then a hcxInsertChange trap shall
			be generated. This an event with no clear condition. 
			Only severity is WARNING."
                ::= { com21Traps 35 }

        hcxUpstreamSerialNumber OBJECT-TYPE
                SYNTAX DisplayString (SIZE (16))
                MAX-ACCESS read-only
                STATUS current
                DESCRIPTION "
                        contains the serial number of the RX card. This
			will be an empty string if card is missing."
                ::= { com21HcxUpstrmUnitEntry 15 }

 

	-- -- -- -- -- -- -- -- -- -- -- -- -- -- -- -- -- -- -- -- -- -- -- --
	-- -- -- -- -- -- -- -- -- -- -- -- -- -- -- -- -- -- -- -- -- -- -- --
	--
	-- com21HcxUpstrmPortGroup
	--
	-- defines the attributes related to the management of a Upstream
	-- port. At the moment of writing there are assumed to be up to 12
	-- active ports, with one port per card.
	--
	-- -- -- -- -- -- -- -- -- -- -- -- -- -- -- -- -- -- -- -- -- -- -- --
	-- -- -- -- -- -- -- -- -- -- -- -- -- -- -- -- -- -- -- -- -- -- -- --

	com21HcxUpstrmPortTable OBJECT-TYPE
		SYNTAX  SEQUENCE OF HcxUpstrmPortEntry
	        MAX-ACCESS  not-accessible
	        STATUS  current
	        DESCRIPTION "."
	        ::= { com21HcxUpstrmPortGroup 1 }

        com21HcxUpstrmPortEntry OBJECT-TYPE 
                SYNTAX  HcxUpstrmPortEntry
                MAX-ACCESS  not-accessible 
                STATUS  current
                DESCRIPTION "."
		INDEX { hcxUpstrmPortShelfId, hcxUpstrmPortSlotId, hcxUpstreamPortId }
                ::= { com21HcxUpstrmPortTable 1 }

	HcxUpstrmPortEntry ::= SEQUENCE {
		hcxUpstrmPortShelfId	   INTEGER,
		hcxUpstrmPortSlotId	   Integer32,
		hcxUpstreamPortId	   Integer32,
		hcxRecvFrequency	   UpstrmFreqKhz,
		hcxRecvPower		   INTEGER,
		hcxUpstrmAggrStuCbrRate    Integer32,
		hcxUpstrmAggrStuMinRate    Integer32,
		hcxUpstrmAggrStuMaxRate    Integer32,
		hcxUpstrmFreqHopping	   INTEGER,
		hcxUpstrmAltFreqA	   INTEGER,
		hcxUpstrmAltFreqB	   INTEGER,
		hcxUpstrmActiveFreq	   UpstrmFreqKhz,
		hcxUpstrmRpmControl	   INTEGER,
		hcxUpstrmRpmPrimServState  PrimServiceState,
		hcxUpstrmRpmSecServState   DisplayString,
		hcxUpstrmRpmConnType	   INTEGER,
	        hcxUpstrmAggrStuVoiceRate  Integer32}
		
        hcxUpstrmPortShelfId OBJECT-TYPE
                SYNTAX INTEGER (1..2)
                MAX-ACCESS read-only
                STATUS current
                DESCRIPTION "
                        contains upstream shelf id containing the RX card."
                ::= { com21HcxUpstrmPortEntry 1 }

        hcxUpstrmPortSlotId OBJECT-TYPE
                SYNTAX Integer32
                MAX-ACCESS read-only
                STATUS current
                DESCRIPTION "
                        contains upstream slot id containing the port.
			Presently there is one port per card."
                ::= { com21HcxUpstrmPortEntry 2 }

	hcxUpstreamPortId OBJECT-TYPE
                SYNTAX Integer32
                MAX-ACCESS read-only
                STATUS current
                DESCRIPTION "
                        Contains the id for the upstream port. Presently
			should be one only."
                ::= { com21HcxUpstrmPortEntry 3 }

	hcxRecvFrequency OBJECT-TYPE
		SYNTAX UpstrmFreqKhz
		MAX-ACCESS read-write
		STATUS current
		DESCRIPTION "
                        Contains the receive frequency of the RF board in 
                        KHz. Note that any change to this frequency shall
                        result in temporary loss of service for the ComPorts
                        as the RX needs to issue a frquency change message 
                        to each ComPort in turn. Also note that the CC shall 
                        check for frequency overlap with other RX cards within
                        the group - the RX channels can be no closer than 
                        1.8Mhz. With the advent of frequency hopping this
                        attribute defines the primary frequency. Minimum step
                        size is 50. i.e. 50000hz. Default is 0."
		::= { com21HcxUpstrmPortEntry 4 }

        hcxRecvPower OBJECT-TYPE
                SYNTAX INTEGER (-15..15)
                MAX-ACCESS read-write
                STATUS current
                DESCRIPTION "
                        Contains the receiver power level in dBmv. Default 
			is 0."
                ::= { com21HcxUpstrmPortEntry 5 }

	hcxUpstrmAggrStuCbrRate OBJECT-TYPE
                SYNTAX Integer32
                MAX-ACCESS read-only
                STATUS current
                DESCRIPTION "
                        This attribute defines the aggregate of all ComPort
                        upstream CBR rates on the RX port. Defined in Kbps."
                ::= { com21HcxUpstrmPortEntry 6 }

        hcxUpstrmAggrStuMinRate OBJECT-TYPE 
                SYNTAX Integer32
                MAX-ACCESS read-only 
                STATUS current 
                DESCRIPTION " 
                        This attribute defines the aggregate of all ComPort
			upstream Minimum rates on the RX port. Defined in 
			Kbps." 
                ::= { com21HcxUpstrmPortEntry 7 }

        hcxUpstrmAggrStuMaxRate OBJECT-TYPE  
                SYNTAX Integer32
                MAX-ACCESS read-only  
                STATUS current  
                DESCRIPTION "  
                        This attribute defines the aggregate of all ComPort
                        upstream Maximum rates on the RX port. Defined in
			Kbps." 
                ::= { com21HcxUpstrmPortEntry 8 }

        hcxRxFreqHop NOTIFICATION-TYPE
                OBJECTS { hcxAlmSeverity, hcxEventLogTime,
			    hcxUpstrmPortShelfId, hcxUpstrmPortSlotId,
                            hcxUpstreamPortId, hcxUpstrmActiveFreq }
                STATUS current
                DESCRIPTION "
			This trap is generated when an RX port frequency
			is hopped due to errors. The hcxUpstrmActiveFreq
			varbind indicates the new frequency. Severity is 
			WARNING."
                ::= { com21Traps 82 }

        hcxUpstrmFreqHopping OBJECT-TYPE
                SYNTAX INTEGER { on (1), off (2) }
                MAX-ACCESS read-write
                STATUS current
                DESCRIPTION "
                        This attribute controls whether an RX port is
                        protected by automatic frequency hopping.
                        If this attribute is transitioned from on -> off
                        then the RX port shall return to the primary
                        frequency. This method can be used to force an
                        RX port to a specific frequency if a hop away
                        from the primary freq had previously occurred.
                        Default will be on."
                ::= { com21HcxUpstrmPortEntry 9 }

        hcxUpstrmAltFreqA OBJECT-TYPE
                SYNTAX INTEGER (0..40000)
                MAX-ACCESS read-write
                STATUS current
                DESCRIPTION "
                        Contains the first alternate frequency for this RX
                        port. This need NOT be unique. i.e. other RX ports
                        within the receiver group can also share the same
                        alternate frequencies.
                        Valid values are 0 or 5000-40000KHz. 0 indicates
                        no alternate frequency. If this frequency was being 
                        used by the receiver port and is set to 0 then the 
                        port shall revert back to the primary frequency. 
                        Minimum step size is 50. i.e. 50000hz. Default is 0."
                ::= { com21HcxUpstrmPortEntry 10 }

        hcxUpstrmAltFreqB OBJECT-TYPE
                SYNTAX INTEGER (0..40000)
                MAX-ACCESS read-write
                STATUS current
                DESCRIPTION "
                        Contains the second alternate frequency for this RX
                        port. Same restrictions and defaults as for 
			hcxUpstrmAltFreqA."
                ::= { com21HcxUpstrmPortEntry 11 }
 
        hcxUpstrmActiveFreq OBJECT-TYPE
                SYNTAX UpstrmFreqKhz
                MAX-ACCESS read-only
                STATUS current
                DESCRIPTION "
                        Contains the presently active frequency. i.e.
			primary, alternate A or alternate B. Upon initial
			deployment of the system this frequency will always
			match the primary frequency. Upon reboot, the RX port
			shall always return to this frequency."
                ::= { com21HcxUpstrmPortEntry 12 }

        hcxUpstrmRpmControl OBJECT-TYPE
                SYNTAX INTEGER { 
				notSupported(1), 
				enable4Port(2), 
				enable8Port(3) }
                MAX-ACCESS read-write
                STATUS current
                DESCRIPTION "
                        Defines RPM control. This attribute is only
			applicable in the case of an RXM card. For the
			RX card this attribute will be read-only with a
			value of notSupported. If the RPM is present then
			the control shall be validated against the
			physical configuration. If an attempt is made
			to place the RPM in 8 port mode but it is
			physically configured for 4 port, then an
			error response shall be return. Default for RxM
			is enable8Port. Option notSupported is unavailable
			for RxM."
                ::= { com21HcxUpstrmPortEntry 13 }

        hcxRpmInvalidPhyConfig NOTIFICATION-TYPE
                OBJECTS { hcxAlmSeverity, hcxEventLogTime,
                            hcxUpstrmPortShelfId, hcxUpstrmPortSlotId,
                            hcxUpstreamPortId }
                STATUS current
                DESCRIPTION "
                        this trap is generated whenever the actual RPM
			configuration does not match that defined by the
			hcxUpstrmRpmControl attribute above. Default
			severity is MINOR."
                ::= { com21Traps 87 }

        hcxRpmInvalidConfClear NOTIFICATION-TYPE
                OBJECTS { hcxAlmSeverity, hcxEventLogTime,
                            hcxUpstrmPortShelfId, hcxUpstrmPortSlotId,
                            hcxUpstreamPortId }
                STATUS current
                DESCRIPTION "
                        this trap is generated once the actual and
			configured RPM configuration match. Severity 
			is CLEARED."
                ::= { com21Traps 88 }

        hcxRpmTimingFault NOTIFICATION-TYPE
                OBJECTS { hcxAlmSeverity, hcxEventLogTime,
                            hcxUpstrmPortShelfId, hcxUpstrmPortSlotId,
                            hcxUpstreamPortId }
                STATUS current
                DESCRIPTION "
                        this trap is generated whenever an RPM timing 
			problem is detected. Default severity is MINOR."
                ::= { com21Traps 89 }

        hcxRpmTimingFaultClear NOTIFICATION-TYPE
                OBJECTS { hcxAlmSeverity, hcxEventLogTime,
                            hcxUpstrmPortShelfId, hcxUpstrmPortSlotId,
                            hcxUpstreamPortId }
                STATUS current
                DESCRIPTION "
                        this trap is generated once a previously detected
			RPM timing problem is cleared. Severity is CLEARED."
                ::= { com21Traps 130 }

        hcxRpmLinkError NOTIFICATION-TYPE 
                OBJECTS { hcxAlmSeverity, hcxEventLogTime, 
                            hcxUpstrmPortShelfId, hcxUpstrmPortSlotId,
                            hcxUpstreamPortId } 
                STATUS current
                DESCRIPTION " 
                        this trap is generated whenever the link between
			the RPM and RxM is detected as down or in error.
			Default severity is MINOR."
                ::= { com21Traps 131 }
 
        hcxRpmLinkErrClear NOTIFICATION-TYPE
                OBJECTS { hcxAlmSeverity, hcxEventLogTime, 
                            hcxUpstrmPortShelfId, hcxUpstrmPortSlotId,
                            hcxUpstreamPortId } 
                STATUS current
                DESCRIPTION " 
                        this trap is generated once a previously reported
			RPM link error is cleared. Severity is CLEARED." 
                ::= { com21Traps 132 }

        hcxUpstrmRpmPrimServState OBJECT-TYPE
                SYNTAX PrimServiceState
                MAX-ACCESS read-only
                STATUS current
                DESCRIPTION "
                        contains primary service state of the RPM."
                ::= { com21HcxUpstrmPortEntry 14 }

        hcxUpstrmRpmPrimStateChange NOTIFICATION-TYPE
                OBJECTS { hcxAlmSeverity, hcxEventLogTime,
                            hcxUpstrmPortShelfId, hcxUpstrmPortSlotId,
                            hcxUpstreamPortId, hcxUpstrmRpmPrimServState }
                STATUS current
                DESCRIPTION "
                        Generated whenever a the hcxUpstrmRpmPrimServState
                        changes in value. This an event with no clear
                        condition. Only severity is WARNING."
                ::= { com21Traps 133 }

        hcxUpstrmRpmSecServState OBJECT-TYPE
                SYNTAX DisplayString (SIZE(16))
                MAX-ACCESS read-only  
                STATUS current
                DESCRIPTION "  
                        contains a string defining the secondary service states
                        of the RPM. The substrings supported by the RPM shall 
			be: UNEQ - not present, CONF - invalid configuration,
			LINK - link fault, TIME - timing fault."
                ::= { com21HcxUpstrmPortEntry 15 }
 
        hcxUpstrmRpmConnType OBJECT-TYPE
                SYNTAX INTEGER { unconnected(1), master(2), slave(3) }
                MAX-ACCESS read-only
                STATUS current
                DESCRIPTION "
                        contains management connection type to the RPM
			device. Note that if the RxM is in slave mode,
			then the state information defined by the 
			attributes above shall not be applicable."
                ::= { com21HcxUpstrmPortEntry 16 }

        hcxUpstrmAggrStuVoiceRate OBJECT-TYPE
                SYNTAX Integer32
                MAX-ACCESS read-only
                STATUS current
                DESCRIPTION "
                        This attribute defines the aggregate of all ComPort
                        upstream voice rates on the RX port. Defined in Kbps."
                ::= { com21HcxUpstrmPortEntry 17 }

  

	-- -- -- -- -- -- -- -- -- -- -- -- -- -- -- -- -- -- -- -- -- -- -- --
	-- -- -- -- -- -- -- -- -- -- -- -- -- -- -- -- -- -- -- -- -- -- -- --
	--
	-- com21HcxUpstrmStatsGroup
	--
	-- defines the attributes related to the statistical analysis of an
	-- Upstream port. This statistical infomation covers physical and ATM
	-- layer statistics.
	-- When the data is retrieved by a management device the appropriate 
	-- RF Receiver card is queried. 
	--
	-- -- -- -- -- -- -- -- -- -- -- -- -- -- -- -- -- -- -- -- -- -- -- --
	-- -- -- -- -- -- -- -- -- -- -- -- -- -- -- -- -- -- -- -- -- -- -- --

        com21HcxUpstrmStatsTable OBJECT-TYPE
                SYNTAX  SEQUENCE OF HcxUpstrmStatsEntry
                MAX-ACCESS  not-accessible
                STATUS  current
                DESCRIPTION "."
                ::= { com21HcxUpstrmStatsGroup 1 }
 
        com21HcxUpstrmStatsEntry OBJECT-TYPE
                SYNTAX  HcxUpstrmStatsEntry
                MAX-ACCESS  not-accessible
                STATUS  current
                DESCRIPTION "."
                INDEX { hcxStatsUpstreamShelfId, hcxStatsUpstreamSlotId, hcxStatsUpstreamPortId }
                ::= { com21HcxUpstrmStatsTable 1 }

        HcxUpstrmStatsEntry ::= SEQUENCE {
                hcxStatsUpstreamShelfId        	INTEGER,
                hcxStatsUpstreamSlotId        	Integer32,
                hcxStatsUpstreamPortId        	Integer32,
		hcxPortCurrMinRxCells		Gauge32,
		hcxPortCurrMinRxNullCells	Gauge32,
		hcxPortCurrMinUncorrFecHecCells	Gauge32,
		hcxPortCurrMinCorrectedFec	Gauge32,
		hcxPortCurrMinOverSubPeriods	Gauge32,
		hcxPortPrevMinRxCells		Gauge32,
		hcxPortPrevMinRxNullCells	Gauge32,
		hcxPortPrevMinUncorrFecHecCells	Gauge32,
		hcxPortPrevMinCorrectedFec	Gauge32,
		hcxPortPrevMinOverSubPeriods	Gauge32,
		hcxPortUpstreamUtil		INTEGER,
		hcxPortCurrMeanNoise		Integer32,
		hcxPortPrevMeanNoise        	Integer32,
		hcxPortCorrFecRatioThres        INTEGER,
                hcxPortCellErrRatioThres        INTEGER,
		hcxPortRatioThresPeriod		INTEGER,
		hcxPortMinErrRatioCells		INTEGER,
        	hcxPortCnrThres			INTEGER,
		hcxPortCurrMinNoise		Integer32,
		hcxPortCurrMaxNoise		Integer32,
		hcxPortPrevMinNoise		Integer32,
		hcxPortPrevMaxNoise		Integer32,
		hcxPortRealTimeMeanNoise	Integer32,
                hcxPortRealTimeMinNoise         Integer32,
                hcxPortRealTimeMaxNoise         Integer32,
		hcxPortClearStats		INTEGER }
                 
        hcxStatsUpstreamShelfId OBJECT-TYPE
                SYNTAX INTEGER (1..2)
                MAX-ACCESS read-only
                STATUS current
                DESCRIPTION "
                        Contains the id for the shelf in which the associated
			RX card is located."
                ::= { com21HcxUpstrmStatsEntry 1 }
 
        hcxStatsUpstreamSlotId OBJECT-TYPE
                SYNTAX Integer32
                MAX-ACCESS read-only
                STATUS current
                DESCRIPTION "
                        Contains the id for the upstream slot."
                ::= { com21HcxUpstrmStatsEntry 2 }
 
        hcxStatsUpstreamPortId OBJECT-TYPE
                SYNTAX Integer32
                MAX-ACCESS read-only
                STATUS current
                DESCRIPTION "
                        Contains the id for the upstream port. Between 1 and 12"
                ::= { com21HcxUpstrmStatsEntry 3 }
 
	hcxPortCurrMinRxCells OBJECT-TYPE
		SYNTAX Gauge32
		MAX-ACCESS read-only
                STATUS current
                DESCRIPTION " 
                        Represents the number of cells received in the current
                        15 minute period."
                ::= { com21HcxUpstrmStatsEntry 4 }

	hcxPortCurrMinRxNullCells OBJECT-TYPE
		SYNTAX Gauge32
		MAX-ACCESS read-only
                STATUS current
                DESCRIPTION " 
                        Represents the number of null cells received in the 
			current 15 minute period."
                ::= { com21HcxUpstrmStatsEntry 5 }

	hcxPortCurrMinUncorrFecHecCells OBJECT-TYPE
		SYNTAX Gauge32
		MAX-ACCESS read-only
                STATUS current
                DESCRIPTION " 
                        Represents the number of received cells with either
			uncorrectable FEC or HEC errors in current 15 minute 
			period."
                ::= { com21HcxUpstrmStatsEntry 6 }

        -- -- -- -- -- -- -- -- -- -- -- -- -- -- -- -- -- -- -- -- -- -- -- --
        -- -- -- 1 Attribute Deprecated
        -- -- -- -- -- -- -- -- -- -- -- -- -- -- -- -- -- -- -- -- -- -- -- --


        hcxPortCurrMinCorrectedFec OBJECT-TYPE
                SYNTAX Gauge32
                MAX-ACCESS read-only
                STATUS current
                DESCRIPTION "
                        Represents the number of corrected FEC errors
                        in the current 15 minute period."
                ::= { com21HcxUpstrmStatsEntry 8 }

	hcxPortCurrMinOverSubPeriods OBJECT-TYPE
                SYNTAX Gauge32
                MAX-ACCESS read-only
                STATUS current
                DESCRIPTION "
                        Represents the number of 512 cell slot scheduling 
			periods that were actively oversubscribed in the 
			current 15 minute period."
                ::= { com21HcxUpstrmStatsEntry 9 }

	hcxPortPrevMinRxCells OBJECT-TYPE
		SYNTAX Gauge32
		MAX-ACCESS read-only
                STATUS current
                DESCRIPTION " 
                        Represents the number of cells received in the previous
                        15 minute period."
                ::= { com21HcxUpstrmStatsEntry 10 }

	hcxPortPrevMinRxNullCells OBJECT-TYPE
		SYNTAX Gauge32
		MAX-ACCESS read-only
                STATUS current
                DESCRIPTION " 
                        Represents the number of cells received in the previous
                        15 minute period."
                ::= { com21HcxUpstrmStatsEntry 11 }

	hcxPortPrevMinUncorrFecHecCells OBJECT-TYPE
		SYNTAX Gauge32
		MAX-ACCESS read-only
                STATUS current
                DESCRIPTION " 
                        Represents the number of received cells with either
                        uncorrectable FEC or HEC errors in the previous 15 
			minute period."
                ::= { com21HcxUpstrmStatsEntry 12 }

        -- -- -- -- -- -- -- -- -- -- -- -- -- -- -- -- -- -- -- -- -- -- -- --
        -- -- -- 1 Attribute Deprecated
        -- -- -- -- -- -- -- -- -- -- -- -- -- -- -- -- -- -- -- -- -- -- -- --

        hcxPortPrevMinCorrectedFec OBJECT-TYPE 
                SYNTAX Gauge32 
                MAX-ACCESS read-only 
                STATUS current 
                DESCRIPTION "
                        Represents the number of corrected FEC errors 
                        in the previous 15 minute period." 
                ::= { com21HcxUpstrmStatsEntry 14 } 

        hcxPortPrevMinOverSubPeriods OBJECT-TYPE 
                SYNTAX Gauge32 
                MAX-ACCESS read-only 
                STATUS current
                DESCRIPTION "  
                        Represents the number of 512 cell slot scheduling 
                        periods that were actively oversubscribed in the 
                        previous 15 minute period."
                ::= { com21HcxUpstrmStatsEntry 15 } 
 
	hcxPortUpstreamUtil OBJECT-TYPE
		SYNTAX INTEGER (0..100)	-- 0% -to- 100%
		MAX-ACCESS read-only
		STATUS current
		DESCRIPTION "
			Represents the percentage of utilization on all slots 
			of the upstream channel."
		::= { com21HcxUpstrmStatsEntry 16 }

        hcxPortCurrMeanNoise OBJECT-TYPE
                SYNTAX Integer32
                MAX-ACCESS read-only
                STATUS current
                DESCRIPTION "
                        This attribute defines the mean noise level in
                        dBmv sampled by the RX card in the current 15
                        minute period."
                ::= { com21HcxUpstrmStatsEntry 17 }
 
        hcxPortPrevMeanNoise OBJECT-TYPE
                SYNTAX Integer32
                MAX-ACCESS read-only
                STATUS current
                DESCRIPTION "
                        This attribute defines the mean noise level in
                        dBmv sampled by the RX card in the previous 15
                        minute period."
                ::= { com21HcxUpstrmStatsEntry 18 }

        hcxPortCorrFecRatioThres OBJECT-TYPE            
                SYNTAX INTEGER (0..100) -- 0% -to- 100%
                MAX-ACCESS read-write
		STATUS current
                DESCRIPTION "
			This attribute defines a threshold point at
                        which a hop of the receive channel frequency shall 
                        take place. The threshold is defined as the 
			percentage of corrected FEC errored cells to good 
			cells. The RX card shall calculate this percentage
                        over a one second period, and the threshold must
                        be crossed for the period defined by the 
                        hcxPortRatioThresPeriod attribute before a trap 
                        is generated. In addition the cells received 
                        within the second must be greater than that defined 
                        by hcxPortMinErrRatioCells. A value of 0 disables 
			the threshold. Default is 20.
			If this RX port is connected to an RPM then this
			threshold is not valid."
                ::= { com21HcxUpstrmStatsEntry 19 }

        hcxCorrFecRatioThres NOTIFICATION-TYPE
                OBJECTS { hcxAlmSeverity, hcxEventLogTime,
			    hcxStatsUpstreamShelfId, hcxStatsUpstreamSlotId,
                            hcxStatsUpstreamPortId, hcxPortCorrFecRatioThres }
                STATUS current
                DESCRIPTION "
                        Severity is WARNING."
                ::= { com21Traps 80 }
 
        hcxPortCellErrRatioThres OBJECT-TYPE            
                SYNTAX INTEGER (0..100) -- 0% -to- 100%
                MAX-ACCESS read-write
                STATUS current
                DESCRIPTION "  
                        This attribute defines a threshold point at
                        which a hop of the receive channel frequency shall 
                        take place. The threshold is defined as the 
                        percentage of FEC/HEC errored cells to good 
                        cells. The RX card shall calculate this percentage
                        over a one second period, and the threshold must 
                        be crossed for the period defined by the 
			hcxPortRatioThresPeriod attribute before a trap
			is generated. In addition the cells received 
			within one second must be greater than that defined 
			by hcxPortMinErrRatioCells. A value of 0 disables 
			the threshold. Default is 10.
                        If this RX port is connected to an RPM then this
                        threshold is not valid."
                ::= { com21HcxUpstrmStatsEntry 20 }

        hcxCellErrRatioThres NOTIFICATION-TYPE
                OBJECTS { hcxAlmSeverity, hcxEventLogTime,
			    hcxStatsUpstreamShelfId, hcxStatsUpstreamSlotId,
                            hcxStatsUpstreamPortId, hcxPortCellErrRatioThres }
                STATUS current
                DESCRIPTION " 
                        Severity is WARNING." 
                ::= { com21Traps 81 }

        hcxPortRatioThresPeriod OBJECT-TYPE
                SYNTAX INTEGER (0..900)
                MAX-ACCESS read-write
                STATUS current
                DESCRIPTION "
                        This attribute defines the integration period for
			the error ratio thresholds. This attribute defines
			the number of seconds over which the threshold
			is contiguously exceeded before a trap is generated.
			0 disables the thresholds. Default is 5."
                ::= { com21HcxUpstrmStatsEntry 21 } 

	hcxPortMinErrRatioCells OBJECT-TYPE
                SYNTAX INTEGER (10..2500)
                MAX-ACCESS read-write
                STATUS current
                DESCRIPTION "
                        This attribute defines the minimum number of cells
			that should be received per second in order to
			allow the Error and Corrected Cell Thresholds to
			cause a frequency hop. Default is 50."
                ::= { com21HcxUpstrmStatsEntry 22 }

        hcxPortCnrThres OBJECT-TYPE
                SYNTAX INTEGER (7..16)
                MAX-ACCESS read-write
                STATUS current
                DESCRIPTION "
                        Defines the average carrier to noise level, in dB, 
			at which a frequency hop should occur. Note that the 
			data error thresholds define above take precedence -
			this CNR threshold applies only if the data rate
			is less than the hcxPortMinErrRatioCells. Default
			11dB.
                        If this RX port is connected to an RPM then this
                        threshold is not valid."
                ::= { com21HcxUpstrmStatsEntry 23 }

        hcxCnrThres NOTIFICATION-TYPE
                OBJECTS { hcxAlmSeverity, hcxEventLogTime,
                            hcxStatsUpstreamShelfId, hcxStatsUpstreamSlotId,
                            hcxStatsUpstreamPortId, hcxPortCnrThres }
                STATUS current
                DESCRIPTION "
                        Tbd. Severity is WARNING."
                ::= { com21Traps 83 }

        hcxPortCurrMinNoise OBJECT-TYPE
                SYNTAX Integer32
                MAX-ACCESS read-only
                STATUS current
                DESCRIPTION "
                        defines the minimum noise level in dBmv sampled 
			by the RX card in the current 15 minute period."
                ::= { com21HcxUpstrmStatsEntry 24 }

        hcxPortCurrMaxNoise OBJECT-TYPE
                SYNTAX Integer32
                MAX-ACCESS read-only
                STATUS current
                DESCRIPTION "
                        defines the maximum noise level in dBmv sampled 
                        by the RX card in the current 15 minute period."
                ::= { com21HcxUpstrmStatsEntry 25 }

        hcxPortPrevMinNoise OBJECT-TYPE
                SYNTAX Integer32
                MAX-ACCESS read-only 
                STATUS current 
                DESCRIPTION "
                        defines the minimum noise level in dBmv sampled  
                        by the RX card in the previous 15 minute period." 
                ::= { com21HcxUpstrmStatsEntry 26 }

        hcxPortPrevMaxNoise OBJECT-TYPE
                SYNTAX Integer32
                MAX-ACCESS read-only 
                STATUS current 
                DESCRIPTION "
                        defines the maximum noise level in dBmv sampled  
                        by the RX card in the previous 15 minute period." 
                ::= { com21HcxUpstrmStatsEntry 27 }

        hcxPortRealTimeMeanNoise OBJECT-TYPE
                SYNTAX Integer32
                MAX-ACCESS read-only
                STATUS current
                DESCRIPTION "
                        This attribute provides a realtime mean noise level 
			in dBmv. It is updated every approx 5 seconds and
			provides a snap shot of the noise conditions on this
			receiver port."
                ::= { com21HcxUpstrmStatsEntry 28 }

        hcxPortRealTimeMinNoise OBJECT-TYPE
                SYNTAX Integer32
                MAX-ACCESS read-only
                STATUS current
                DESCRIPTION "
                ::= { com21HcxUpstrmStatsEntry 29 }
                        This attribute provides a realtime min noise level 
			in dBmv. The attribute is updated every approx 5
			seconds and provides the minimum noise level
			during that period."
                ::= { com21HcxUpstrmStatsEntry 29 } 

        hcxPortRealTimeMaxNoise OBJECT-TYPE
                SYNTAX Integer32
                MAX-ACCESS read-only
                STATUS current
                DESCRIPTION "
                        This attribute provides a realtime max noise level 
			in dBmv. The attribute is updated every approx 5
                        seconds and provides the maximum noise level 
                        during that period."
                ::= { com21HcxUpstrmStatsEntry 30 }

        hcxPortClearStats OBJECT-TYPE
                SYNTAX INTEGER { nil(1), clear(2) }
                MAX-ACCESS read-write
                STATUS current
                DESCRIPTION "
                        This attribute is used to clear all RX
                        statistics counters in this group. This operation
                        is only possible if the hcxStatsControl attribute
                        is set to wrapCurr."
                ::= { com21HcxUpstrmStatsEntry 31 }
 


        -- -- -- -- -- -- -- -- -- -- -- -- -- -- -- -- -- -- -- -- -- -- -- --
        -- -- -- -- -- -- -- -- -- -- -- -- -- -- -- -- -- -- -- -- -- -- -- --
        --
        -- com21HcxVciStatsGroup
        -- 
        -- defines the attributes related to the statistics monitoring of a
	-- single ComController<->ComPort VPI/VCI. This group is based very 
	-- closely on the ATM 2.1 ILMI atmfAtmStatsTable. Any future adoption 
	-- of a differing standarized ATM MIB would most likely replace this 
	-- group.
	-- Note we are assuming a max of 2044 x 4 of these records. This
	-- represents approx. 750kbytes of memory.
	-- The agent is responsible for construction of a single file containing
	-- the previous stats when the 15minute period is completed. This single
	-- file is retrieved by the NMAPS. Assuming that the NMAPS is interested
	-- only in the ethernet VCI info then this file will be 
	-- 2044 x 6counters x 4bytes = approx 50kbytes.
	-- This data shall be collected from the various RF Receiver cards
	-- and compiled into a single statistics file to be read by NMAPS.
        --
        -- -- -- -- -- -- -- -- -- -- -- -- -- -- -- -- -- -- -- -- -- -- -- --
        -- -- -- -- -- -- -- -- -- -- -- -- -- -- -- -- -- -- -- -- -- -- -- --

        com21HcxVciStatsTable OBJECT-TYPE
                SYNTAX  SEQUENCE OF HcxVciStatsEntry
                MAX-ACCESS  not-accessible
                STATUS  current
                DESCRIPTION "."
                ::= { com21HcxVciStatsGroup 1 }
 
        com21HcxVciStatsEntry OBJECT-TYPE
                SYNTAX  HcxVciStatsEntry
                MAX-ACCESS  not-accessible
                STATUS  current
                DESCRIPTION "."
                INDEX { hcxStuStatsMacAddr }
                ::= { com21HcxVciStatsTable 1 }
 
        HcxVciStatsEntry ::= SEQUENCE {
                hcxStuStatsMacAddr		MacAddress,
		hcxStatsCurrMinRxCells		Gauge32,
		hcxStatsCurrMinRxNullCells	Gauge32,
		hcxStatsCurrMinUncorFecHec	Gauge32,
		hcxStatsCurrMinUncorFecThres	Integer32,
		hcxStatsCurrMinCorrectedFec	Gauge32,
		hcxStatsCurrMinCorFecThres	Integer32,
                hcxStatsPrevMinRxCells          Gauge32,
		hcxStatsPrevMinRxNullCells	Gauge32,
		hcxStatsPrevMinUncorFecHec	Gauge32,
		hcxStatsPrevMinCorrectedFec	Gauge32,
		hcxStatsCurrMinMeanSignal       Integer32,
		hcxStatsPrevMinMeanSignal       Integer32,
		hcxStatsClearStats		INTEGER }
		
        hcxStuStatsMacAddr OBJECT-TYPE
                SYNTAX MacAddress
                MAX-ACCESS read-only
                STATUS current
                DESCRIPTION "
                        Contains IEEE 802 medium access control address
                        of the ComPort device."
                ::= { com21HcxVciStatsEntry 1 }

        hcxStatsCurrMinRxCells OBJECT-TYPE
                SYNTAX Gauge32
                MAX-ACCESS read-only
                STATUS current
                DESCRIPTION "
                        Represents the number of cells successfully received in 
			the current 15 minute period."
                ::= { com21HcxVciStatsEntry 2 }
 
        hcxStatsCurrMinRxNullCells OBJECT-TYPE
                SYNTAX Gauge32
                MAX-ACCESS read-only
                STATUS current
                DESCRIPTION "
                        Represents the number of null cells received in 
			the current 15 minute period."
                ::= { com21HcxVciStatsEntry 3 }
 
        -- -- -- -- -- -- -- -- -- -- -- -- -- -- -- -- -- -- -- -- -- -- -- --
        -- -- -- 2 Attribute Deprecated
        -- -- -- -- -- -- -- -- -- -- -- -- -- -- -- -- -- -- -- -- -- -- -- --

	hcxStatsCurrMinUncorFecHec OBJECT-TYPE
                SYNTAX Gauge32
                MAX-ACCESS read-only
                STATUS current
                DESCRIPTION "  
                        Represents the number of bad cells - HEC/Uncorrectable
			FEC/ Collisions - reported in cell slots allocated to
			this ComPort/VCI in the current 15 minute period."
                ::= { com21HcxVciStatsEntry 6 }
 
        hcxStatsCurrMinUncorFecThres OBJECT-TYPE
                SYNTAX Integer32
                MAX-ACCESS read-write
                STATUS current
                DESCRIPTION "
                        Represents the number of HEC/Uncorrectable FEC error 
			cells received in the present 15minute period that 
			shall cause a threshold trap to be generated. Default 
			is 0 - threshold disabled."
                ::= { com21HcxVciStatsEntry 7 }

        hcxUncorFecHecMinThres NOTIFICATION-TYPE 
                OBJECTS { hcxAlmSeverity, hcxEventLogTime,
                            hcxStuStatsMacAddr, hcxStatsCurrMinUncorFecThres,
                            hcxStatsCurrMinUncorFecHec }
                STATUS current
                DESCRIPTION "
                        Severity is WARNING."
                ::= { com21Traps 37 }
  
        hcxStatsCurrMinCorrectedFec OBJECT-TYPE
                SYNTAX Gauge32
                MAX-ACCESS read-only
                STATUS current
                DESCRIPTION " 
                        Represents the number of corrected FEC errors
                        for this ComPort/VCI in the current 15 minute period."
                ::= { com21HcxVciStatsEntry 8 }
 
        hcxStatsCurrMinCorFecThres OBJECT-TYPE
                SYNTAX Integer32
                MAX-ACCESS read-write
                STATUS current
                DESCRIPTION "
                        Represents the number of corrected FEC errors in the
                        present 15minute period that shall cause a threshold
                        trap to be generated. Default is 0 - threshold
                        disabled."
                ::= { com21HcxVciStatsEntry 9 }
 
        hcxCorrectedFecMinThres NOTIFICATION-TYPE
                OBJECTS { hcxAlmSeverity, hcxEventLogTime,
                            hcxStuStatsMacAddr, hcxStatsCurrMinCorFecThres,
                            hcxStatsCurrMinCorrectedFec }
                STATUS current
                DESCRIPTION "
                        Severity is WARNING."
                ::= { com21Traps 38 }

        hcxStatsPrevMinRxCells OBJECT-TYPE
                SYNTAX Gauge32
                MAX-ACCESS read-only
                STATUS current
                DESCRIPTION "
                        Represents the number of cells successfully received in
                        the previous 15 minute period."
                ::= { com21HcxVciStatsEntry 10 }
 
        hcxStatsPrevMinRxNullCells OBJECT-TYPE
                SYNTAX Gauge32
                MAX-ACCESS read-only
                STATUS current
                DESCRIPTION "
                        Represents the number of null cells received in
                        the previous 15 minute period."
                ::= { com21HcxVciStatsEntry 11 }
 
        -- -- -- -- -- -- -- -- -- -- -- -- -- -- -- -- -- -- -- -- -- -- -- --
        -- -- -- 1 Attribute Deprecated
        -- -- -- -- -- -- -- -- -- -- -- -- -- -- -- -- -- -- -- -- -- -- -- --

        hcxStatsPrevMinUncorFecHec OBJECT-TYPE 
                SYNTAX Gauge32 
                MAX-ACCESS read-only 
                STATUS current 
                DESCRIPTION "   
                        Represents the number of bad cells - HEC/Uncorrectable
			FEC/Collisions - reported in cell slots allocated to
                        this ComPort/VCI in the previous 15 minute period."
                ::= { com21HcxVciStatsEntry 13 } 

        hcxStatsPrevMinCorrectedFec OBJECT-TYPE
                SYNTAX Gauge32 
                MAX-ACCESS read-only 
                STATUS current
                DESCRIPTION "  
                        Represents the number of corrected FEC errors
                        for this ComPort/VCI in the previous 15 minute period."
                ::= { com21HcxVciStatsEntry 14 }

	hcxStatsCurrMinMeanSignal OBJECT-TYPE
                SYNTAX Integer32
                MAX-ACCESS read-only
                STATUS current
                DESCRIPTION "
                        This attribute contains the mean signal strength value
			in dBmv sampled for this ComPort in the current 15 
			minute period."
                ::= { com21HcxVciStatsEntry 15 }

        hcxStatsPrevMinMeanSignal OBJECT-TYPE
                SYNTAX Integer32
                MAX-ACCESS read-only 
                STATUS current 
                DESCRIPTION " 
                        This attribute contains the mean signal strength value
			in dBmv sampled for this ComPort in the previous 15 
			minute period."
                ::= { com21HcxVciStatsEntry 16 } 

        hcxStatsClearStats OBJECT-TYPE
                SYNTAX INTEGER { nil(1), clear(2) }
                MAX-ACCESS read-write
                STATUS current
                DESCRIPTION "
                        This attribute is used to clear all RX ComPort
                        statistics counters in this group. This operation
                        is only possible if the hcxStatsControl attribute
                        is set to wrapCurr."
                ::= { com21HcxVciStatsEntry 17 }
 


        -- -- -- -- -- -- -- -- -- -- -- -- -- -- -- -- -- -- -- -- -- -- -- --
        -- -- -- -- -- -- -- -- -- -- -- -- -- -- -- -- -- -- -- -- -- -- -- --
        --
        -- com21HcxRpmIPortGroup
        --
        -- defines the attributes related to the management of a single
        -- RPM I-port. Maximum of 8 per upstream port.
        --
        -- -- -- -- -- -- -- -- -- -- -- -- -- -- -- -- -- -- -- -- -- -- -- --
        -- -- -- -- -- -- -- -- -- -- -- -- -- -- -- -- -- -- -- -- -- -- -- --
 
        com21HcxRpmIPortTable OBJECT-TYPE
                SYNTAX  SEQUENCE OF HcxRpmIPortEntry
                MAX-ACCESS  not-accessible
                STATUS  current
                DESCRIPTION "."
                ::= { com21HcxRpmIPortGroup 1 }
 
        com21HcxRpmIPortEntry OBJECT-TYPE
                SYNTAX  HcxRpmIPortEntry
                MAX-ACCESS  not-accessible
                STATUS  current
                DESCRIPTION "."
                INDEX { hcxRpmIPortShelfId, hcxRpmIPortSlotId, hcxRpmRxPortId, hcxRpmIPortId }
                ::= { com21HcxRpmIPortTable 1 }
 
        HcxRpmIPortEntry ::= SEQUENCE {
                hcxRpmIPortShelfId        INTEGER,
                hcxRpmIPortSlotId         Integer32,
                hcxRpmRxPortId            Integer32,
                hcxRpmIPortId             INTEGER,
                hcxRpmIPortRecvPower      INTEGER,
		hcxRpmIPortConfigState	  INTEGER,
		hcxRpmIPortContSchedType  INTEGER }
                 
        hcxRpmIPortShelfId OBJECT-TYPE
                SYNTAX INTEGER (1..2)
                MAX-ACCESS read-only
                STATUS current
                DESCRIPTION "
                        contains upstream shelf id containing the RX card."
                ::= { com21HcxRpmIPortEntry 1 }
 
        hcxRpmIPortSlotId OBJECT-TYPE
                SYNTAX Integer32
                MAX-ACCESS read-only
                STATUS current
                DESCRIPTION "
                        contains upstream slot id containing the port.
                        Presently there is one port per card."
                ::= { com21HcxRpmIPortEntry 2 }
 
        hcxRpmRxPortId OBJECT-TYPE
                SYNTAX Integer32
                MAX-ACCESS read-only
                STATUS current
                DESCRIPTION "
                        Contains the id for the upstream port. Presently
                        should be one only."
                ::= { com21HcxRpmIPortEntry 3 }
 
        hcxRpmIPortId OBJECT-TYPE
                SYNTAX INTEGER (1..8)
                MAX-ACCESS read-only
                STATUS current
                DESCRIPTION "
                        Contains the id for the RPM I-port."
                ::= { com21HcxRpmIPortEntry 4 }
 
        hcxRpmIPortRecvPower OBJECT-TYPE
                SYNTAX INTEGER (-15..15)
                MAX-ACCESS read-write
                STATUS current
                DESCRIPTION "
                        Contains the receiver power level in dBmv. Default
                        is 0."
                ::= { com21HcxRpmIPortEntry 5 }
 
        hcxRpmIPortConfigState OBJECT-TYPE
                SYNTAX INTEGER { disable (1), enable (2) }
                MAX-ACCESS read-write
                STATUS current
                DESCRIPTION "
                        Used to activate or deactivate the I-Port. For
			test purposes, one port can be enabled and all
			others disabled. This will cause the I-Port to
			be permanently closed. i.e. traffic passing.
			Default disable. Note that setting an I-Port to
			the disabled state will have the effect of 
			clearing the statistics for the I-Port."
                ::= { com21HcxRpmIPortEntry 6 }

        hcxRpmIPortContSchedType OBJECT-TYPE      
                SYNTAX INTEGER { 
				roundRobinOperation (1), 
				simultaneousOperation (2) }
                MAX-ACCESS read-write
                STATUS current
                DESCRIPTION "
                        Used to control the type of contention slot
			scheduling utilized by this I-Port. The
			roundRobinOperation indicates that this I-Port
			shall have a individual contention opportunity
			- i.e. no other I-Ports active - allocated on
			a round-robin basis. The simultaneousOperation
			indicates that this I-Port shall be included
			with a group of I-Ports given the same,
			simultaneous contention opportunities. Default 
			is roundRobinOperation."
                ::= { com21HcxRpmIPortEntry 7 }
 
 

        -- -- -- -- -- -- -- -- -- -- -- -- -- -- -- -- -- -- -- -- -- -- -- --
        -- -- -- -- -- -- -- -- -- -- -- -- -- -- -- -- -- -- -- -- -- -- -- --
        --
        -- com21HcxRpmStatsGroup
        -- 
        -- this group contains the per I-Port statistics. 
        -- 
        -- -- -- -- -- -- -- -- -- -- -- -- -- -- -- -- -- -- -- -- -- -- -- --
        -- -- -- -- -- -- -- -- -- -- -- -- -- -- -- -- -- -- -- -- -- -- -- --

        com21HcxRpmStatsTable OBJECT-TYPE
                SYNTAX  SEQUENCE OF HcxRpmStatsEntry
                MAX-ACCESS  not-accessible
                STATUS  current
                DESCRIPTION "."
                ::= { com21HcxRpmStatsGroup 1 }

        com21HcxRpmStatsEntry OBJECT-TYPE
                SYNTAX  HcxRpmStatsEntry
                MAX-ACCESS  not-accessible
                STATUS  current
                DESCRIPTION "."
                INDEX { hcxStatsRpmShelfId, hcxStatsRpmSlotId, hcxStatsRxPortId, hcxStatsRpmIPortId }
                ::= { com21HcxRpmStatsTable 1 }

        HcxRpmStatsEntry ::= SEQUENCE {
                hcxStatsRpmShelfId             INTEGER,
                hcxStatsRpmSlotId              Integer32,
                hcxStatsRxPortId               Integer32,
                hcxStatsRpmIPortId             INTEGER,
                hcxRpmCurrMinRxCells           Gauge32,
                hcxRpmCurrMinRxNullCells       Gauge32,
                hcxRpmCurrMinUncorFecHecCells  Gauge32,
                hcxRpmCurrMinCorrectedFec      Gauge32,
                hcxRpmCurrMeanNoise            Integer32,
                hcxRpmCurrMinNoise             Integer32,
                hcxRpmCurrMaxNoise             Integer32,
                hcxRpmRealTimeMeanNoise        Integer32,
                hcxRpmRealTimeMinNoise         Integer32,
                hcxRpmRealTimeMaxNoise         Integer32,
                hcxRpmPrevMinRxCells           Gauge32,
                hcxRpmPrevMinRxNullCells       Gauge32,
                hcxRpmPrevMinUncorFecHecCells  Gauge32,
                hcxRpmPrevMinCorrectedFec      Gauge32,
                hcxRpmPrevMeanNoise            Integer32,
                hcxRpmPrevMinNoise             Integer32,
                hcxRpmPrevMaxNoise             Integer32,
		hcxRpmCorrFecRatioThres	       INTEGER,
        	hcxRpmCellErrRatioThres	       INTEGER,
		hcxRpmRatioThresPeriod	       INTEGER,
	        hcxRpmMinErrRatioCells 	       INTEGER,
 		hcxRpmCnrThres		       INTEGER,
		hcxRpmClearStats	       INTEGER }

        hcxStatsRpmShelfId OBJECT-TYPE
                SYNTAX INTEGER (1..2)
                MAX-ACCESS read-only
                STATUS current
                DESCRIPTION "
                        Contains the id for the shelf in which the associated
                        RX card is located."
                ::= { com21HcxRpmStatsEntry 1 }
 
        hcxStatsRpmSlotId OBJECT-TYPE
                SYNTAX Integer32
                MAX-ACCESS read-only
                STATUS current
                DESCRIPTION "
                        Contains the id for the upstream slot."
                ::= { com21HcxRpmStatsEntry 2 }
 
        hcxStatsRxPortId OBJECT-TYPE
                SYNTAX Integer32
                MAX-ACCESS read-only
                STATUS current
                DESCRIPTION "
                        Contains the id for the upstream port."
                ::= { com21HcxRpmStatsEntry 3 }

        hcxStatsRpmIPortId OBJECT-TYPE
                SYNTAX INTEGER  (1..8)
                MAX-ACCESS read-only
                STATUS current
                DESCRIPTION "  
                        Contains the id for the RPM I-Port."
                ::= { com21HcxRpmStatsEntry 4 }
 
        hcxRpmCurrMinRxCells OBJECT-TYPE
                SYNTAX Gauge32
                MAX-ACCESS read-only
                STATUS current
                DESCRIPTION "
                        Represents the number of cells received via the I-Port
			in the current 15 minute period."
                ::= { com21HcxRpmStatsEntry 5 }
 
        hcxRpmCurrMinRxNullCells OBJECT-TYPE
                SYNTAX Gauge32
                MAX-ACCESS read-only
                STATUS current
                DESCRIPTION "
                        Represents the number of null cells received via the
			RPM I-Port in the current 15 minute period."
                ::= { com21HcxRpmStatsEntry 6 }
 
        hcxRpmCurrMinUncorFecHecCells OBJECT-TYPE
                SYNTAX Gauge32
                MAX-ACCESS read-only
                STATUS current
                DESCRIPTION "
                        Represents the number of received cells with either
			uncorrectable FEC or HEC errors received via the 
			I-Port in the current 15 minute period."
                ::= { com21HcxRpmStatsEntry 7 }

        hcxRpmCurrMinCorrectedFec OBJECT-TYPE
                SYNTAX Gauge32
                MAX-ACCESS read-only
                STATUS current
                DESCRIPTION "
                        Represents the number of corrected FEC errors
                        received via the I-Port in the current 15 minute
			period."
                ::= { com21HcxRpmStatsEntry 8 }
 
        hcxRpmCurrMeanNoise OBJECT-TYPE
                SYNTAX Integer32
                MAX-ACCESS read-only
                STATUS current
                DESCRIPTION "
                        This attribute defines the mean noise value,
                        in dBmv, sampled on the I-Port in the current 15
                        minute period."
                ::= { com21HcxRpmStatsEntry 9 }

        hcxRpmCurrMinNoise OBJECT-TYPE
                SYNTAX Integer32
                MAX-ACCESS read-only
                STATUS current
                DESCRIPTION "
                        Defines the minimum noise level, in dBmv, sampled
                        on the I-Port in the current 15 minute period."
                ::= { com21HcxRpmStatsEntry 10 }
 
        hcxRpmCurrMaxNoise OBJECT-TYPE
                SYNTAX Integer32
                MAX-ACCESS read-only
                STATUS current
                DESCRIPTION "
                        Defines the maximum noise level, in dBmv, sampled
                        on the I-Port in the current 15 minute period."
                ::= { com21HcxRpmStatsEntry 11 }

        hcxRpmRealTimeMeanNoise OBJECT-TYPE
                SYNTAX Integer32
                MAX-ACCESS read-only
                STATUS current
                DESCRIPTION "
                        This attribute provides a realtime mean noise level
                        in dBmv sampled on the I-Port. It is updated every 
			approx 5 seconds and provides a snap shot of the noise 
			conditions on this I-Port."
                ::= { com21HcxRpmStatsEntry 12 }
 
        hcxRpmRealTimeMinNoise OBJECT-TYPE
                SYNTAX Integer32
                MAX-ACCESS read-only
                STATUS current
                DESCRIPTION "
                        This attribute provides a realtime min noise level 
			in dBmv sampled on the I-Port. The attribute is updated
			every approx 5 seconds and provides the minimum noise 
			level during that period."
                ::= { com21HcxRpmStatsEntry 13 }
 
        hcxRpmRealTimeMaxNoise OBJECT-TYPE
                SYNTAX Integer32
                MAX-ACCESS read-only
                STATUS current
                DESCRIPTION "
                        This attribute provides a realtime max noise level 
			in dBmv sampled on the I-Port. The attribute is updated
                        every approx 5 seconds and provides the maximum noise 
                        level during that period."
                ::= { com21HcxRpmStatsEntry 14 }
 
        hcxRpmPrevMinRxCells OBJECT-TYPE
                SYNTAX Gauge32
                MAX-ACCESS read-only
                STATUS current
                DESCRIPTION "
                        Represents the number of cells received via the
			RPM I-Port in the previous 15 minute period."
                ::= { com21HcxRpmStatsEntry 15 }
 
        hcxRpmPrevMinRxNullCells OBJECT-TYPE
                SYNTAX Gauge32
                MAX-ACCESS read-only
                STATUS current
                DESCRIPTION "
                        Represents the number of null cells received via
			the I-Port in the previous 15 minute period."
                ::= { com21HcxRpmStatsEntry 16 }
 
        hcxRpmPrevMinUncorFecHecCells OBJECT-TYPE
                SYNTAX Gauge32
                MAX-ACCESS read-only
                STATUS current
                DESCRIPTION "
                        Represents the number of cells with uncorrectable
			FEC or HEC errors received via the I-Port in the 
			previous 15 minute period."
                ::= { com21HcxRpmStatsEntry 17 }
 
        hcxRpmPrevMinCorrectedFec OBJECT-TYPE
                SYNTAX Gauge32
                MAX-ACCESS read-only
                STATUS current
                DESCRIPTION "
                        Represents the number of corrected FEC errors
                        in the previous 15 minute period."
                ::= { com21HcxRpmStatsEntry 18 }
 
        hcxRpmPrevMeanNoise OBJECT-TYPE
                SYNTAX Integer32
                MAX-ACCESS read-only
                STATUS current
                DESCRIPTION "
                        This attribute defines the mean noise value,
                        in dBmv, sampled on the I-Port in the previous 15
                        minute period."
                ::= { com21HcxRpmStatsEntry 19 }
 
        hcxRpmPrevMinNoise OBJECT-TYPE
                SYNTAX Integer32
                MAX-ACCESS read-only
                STATUS current
                DESCRIPTION "
                        Defines the minimum noise level, in dBmv, sampled
                        on the I-Port in the previous 15 minute period."
                ::= { com21HcxRpmStatsEntry 20 }
 
        hcxRpmPrevMaxNoise OBJECT-TYPE
                SYNTAX Integer32
                MAX-ACCESS read-only
                STATUS current
                DESCRIPTION "
                        Defines the maximum noise level, in dBmv, sampled
                        on the I-Port in the previous 15 minute period."
                ::= { com21HcxRpmStatsEntry 21 }
 
        hcxRpmCorrFecRatioThres OBJECT-TYPE            
                SYNTAX INTEGER (0..100) -- 0% -to- 100%
                MAX-ACCESS read-write
                STATUS current
                DESCRIPTION "
                        This attribute defines a threshold point at
                        which a hop of the receive channel frequency shall
                        take place. The threshold is defined as the 
                        percentage of corrected FEC errored cells to good
                        cells. The RX card shall calculate this percentage
                        over a one second period, and the threshold must
                        be crossed for the period defined by the 
                        hcxRpmRatioThresPeriod attribute before a trap
                        is generated. In addition the cells received 
                        within the second must be greater than that defined
                        by hcxRpmMinErrRatioCells. A value of 0 disables
                        the threshold. Default is 20."
                ::= { com21HcxRpmStatsEntry 22 }
 
        hcxRpmFecRatioThres NOTIFICATION-TYPE
                OBJECTS { hcxAlmSeverity, hcxEventLogTime,
                            hcxStatsRpmShelfId, hcxStatsRpmSlotId,
                            hcxStatsRxPortId, hcxStatsRpmIPortId,
			    hcxRpmCorrFecRatioThres }
                STATUS current
                DESCRIPTION "
                        Severity is WARNING."
                ::= { com21Traps 84 }
 
        hcxRpmCellErrRatioThres OBJECT-TYPE            
                SYNTAX INTEGER (0..100) -- 0% -to- 100%
                MAX-ACCESS read-write
                STATUS current
                DESCRIPTION "  
                        This attribute defines a threshold point at
                        which a hop of the receive channel frequency shall
                        take place. The threshold is defined as the 
                        percentage of FEC/HEC errored cells to good 
                        cells. The RX card shall calculate this percentage
                        over a one second period, and the threshold must
                        be crossed for the period defined by the 
                        hcxRpmRatioThresPeriod attribute before a trap
                        is generated. In addition the cells received 
                        within one second must be greater than that defined
                        by hcxRpmMinErrRatioCells. A value of 0 disables
                        the threshold. Default is 10."
                ::= { com21HcxRpmStatsEntry 23 }

        hcxRpmCellErrRatioThresTrap NOTIFICATION-TYPE
                OBJECTS { hcxAlmSeverity, hcxEventLogTime,
                            hcxStatsRpmShelfId, hcxStatsRpmSlotId,
                            hcxStatsRxPortId, hcxStatsRpmIPortId,
			    hcxRpmCellErrRatioThres }
                STATUS current
                DESCRIPTION "
                        Severity is WARNING."
                ::= { com21Traps 85 }

        hcxRpmRatioThresPeriod OBJECT-TYPE
                SYNTAX INTEGER (0..900)
                MAX-ACCESS read-write
                STATUS current
                DESCRIPTION "
                        This attribute defines the integration period for
                        the error ratio thresholds. This attribute defines
                        the number of seconds over which the threshold
                        is contiguously exceeded before a trap is generated.
                        0 disables the thresholds. Default is 5."
                ::= { com21HcxRpmStatsEntry 24 }
 
        hcxRpmMinErrRatioCells OBJECT-TYPE
                SYNTAX INTEGER (10..2500)
                MAX-ACCESS read-write
                STATUS current
                DESCRIPTION "
                        This attribute defines the minimum number of cells
                        that should be received per second in order to
                        allow the Error and Corrected Cell Thresholds to
                        cause a frequency hop. Default is 50."
                ::= { com21HcxRpmStatsEntry 25 }
 
        hcxRpmCnrThres OBJECT-TYPE
                SYNTAX INTEGER (7..16)
                MAX-ACCESS read-write
                STATUS current
                DESCRIPTION "
                        Defines the average noise level, in dBmv, at which
                        a frequency hop should occur. Note that the data
                        error thresholds define above take precedence -
                        this CNR threshold applies only if the data rate
                        is less than the hcxRpmMinErrRatioCells. Default
                        11dBmv."
                ::= { com21HcxRpmStatsEntry 26 }
 
        hcxRpmCnrThresTrap NOTIFICATION-TYPE
                OBJECTS { hcxAlmSeverity, hcxEventLogTime,
                            hcxStatsRpmShelfId, hcxStatsRpmSlotId,
                            hcxStatsRxPortId, hcxStatsRpmIPortId,
                            hcxRpmCnrThres }
                STATUS current
                DESCRIPTION "
                        Tbd. Severity is WARNING."
                ::= { com21Traps 86 }

	hcxRpmClearStats OBJECT-TYPE
                SYNTAX INTEGER { nil(1), clear(2) }
                MAX-ACCESS read-write
                STATUS current
                DESCRIPTION "
                        This attribute is used to clear all RPM
                        statistics counters in this group. This operation
                        is only possible if the hcxStatsControl attribute
                        is set to wrapCurr."
                ::= { com21HcxRpmStatsEntry 27 }



        -- -- -- -- -- -- -- -- -- -- -- -- -- -- -- -- -- -- -- -- -- -- -- --
        -- -- -- -- -- -- -- -- -- -- -- -- -- -- -- -- -- -- -- -- -- -- -- --
        --
        -- com21HcxRfAnalysisGroup
        --
        -- this group provides the operator with the ability to analyse the
	-- real-time qualities of RF noise on the receiver channel. The 
	-- operator is given the option of defining three noise sample 
	-- "buckets" and the number of samples with the parameters of the 
	-- "bucket" is sampled on a real-time basis.
        --
        -- -- -- -- -- -- -- -- -- -- -- -- -- -- -- -- -- -- -- -- -- -- -- --
        -- -- -- -- -- -- -- -- -- -- -- -- -- -- -- -- -- -- -- -- -- -- -- --
 
        com21HcxRfAnalysisTable OBJECT-TYPE
                SYNTAX  SEQUENCE OF HcxRfAnalysisEntry
                MAX-ACCESS  not-accessible
                STATUS  current
                DESCRIPTION "."
                ::= { com21HcxRfAnalysisGroup 1 }

        com21HcxRfAnalysisEntry OBJECT-TYPE       
                SYNTAX  HcxRfAnalysisEntry
                MAX-ACCESS  not-accessible
                STATUS  current
                DESCRIPTION "."
                INDEX { hcxRfAnalysisShelfId, hcxRfAnalysisSlotId, hcxRfAnalysisPortId, hcxRfAnalysisRpmPortId }
                ::= { com21HcxRfAnalysisTable 1 }
 
        HcxRfAnalysisEntry ::= SEQUENCE {
                hcxRfAnalysisShelfId            INTEGER,
                hcxRfAnalysisSlotId             Integer32,
                hcxRfAnalysisPortId             Integer32,
                hcxRfAnalysisRpmPortId          INTEGER,
                hcxRfAnalysisControl		INTEGER,
		hcxRfAnalysisPoint1		INTEGER,
		hcxRfAnalysisPoint2		INTEGER,
		hcxRfAnalysisPoint3		INTEGER,
		hcxRfAnalysisPoint4		INTEGER,
        	hcxRfAnalysisBin1Count		Gauge32,
		hcxRfAnalysisBin2Count          Gauge32,
        	hcxRfAnalysisBin3Count		Gauge32,
		hcxRfAnalysisClearCount		INTEGER }
		
 
        hcxRfAnalysisShelfId OBJECT-TYPE
                SYNTAX INTEGER (1..2)
                MAX-ACCESS read-only
                STATUS current
                DESCRIPTION "
                        contains upstream shelf id."
                ::= { com21HcxRfAnalysisEntry 1 }

        hcxRfAnalysisSlotId OBJECT-TYPE
                SYNTAX Integer32
                MAX-ACCESS read-only
                STATUS current
                DESCRIPTION "
                        contains upstream slot id."
                ::= { com21HcxRfAnalysisEntry 2 }

        hcxRfAnalysisPortId OBJECT-TYPE
                SYNTAX Integer32
                MAX-ACCESS read-only
                STATUS current
                DESCRIPTION "
                        contains upstream port id. Presently only one port
			is supported."
                ::= { com21HcxRfAnalysisEntry 3 }

        hcxRfAnalysisRpmPortId OBJECT-TYPE
                SYNTAX INTEGER (1..8)
                MAX-ACCESS read-only
                STATUS current
                DESCRIPTION "
                        contains any RPM I-Port id. Note an RX card or RXM
                        card operating without an RPM expects 1 for this
                        attribute."
                ::= { com21HcxRfAnalysisEntry 4 }

	hcxRfAnalysisControl OBJECT-TYPE
                SYNTAX INTEGER { disable (1), enable (2) }
                MAX-ACCESS read-write
                STATUS current
                DESCRIPTION "
                        Used to activate or deactivate the RF analysis
			for a port or I-Port. Default disable."
                ::= { com21HcxRfAnalysisEntry 5 }

        hcxRfAnalysisPoint1 OBJECT-TYPE
                SYNTAX RfAnalysisdBmv
                MAX-ACCESS read-write 
                STATUS current 
                DESCRIPTION "  
                        This attribute is used to define the first, and
			lowest, noise level point. Default is -58dBmv."
                ::= { com21HcxRfAnalysisEntry 6 }

        hcxRfAnalysisPoint2 OBJECT-TYPE
                SYNTAX RfAnalysisdBmv
                MAX-ACCESS read-write 
                STATUS current 
                DESCRIPTION "  
                        This attribute is used to define the second noise
			level point. This value must be greater than
			hcxRfAnalysisPoint1. Default is -15dBmv."
                ::= { com21HcxRfAnalysisEntry 7 }

        hcxRfAnalysisPoint3 OBJECT-TYPE
                SYNTAX RfAnalysisdBmv
                MAX-ACCESS read-write
                STATUS current
                DESCRIPTION "
                        This attribute is used to define the third noise
                        level point. This value must be greater than
                        hcxRfAnalysisPoint2. Default is -10dBmv."
                ::= { com21HcxRfAnalysisEntry 8 }

        hcxRfAnalysisPoint4 OBJECT-TYPE
                SYNTAX RfAnalysisdBmv
                MAX-ACCESS read-write
                STATUS current
                DESCRIPTION "
                        This attribute is used to define the final noise
                        level point. This value must be greater than
                        hcxRfAnalysisPoint3. Default is -5dBmv."
                ::= { com21HcxRfAnalysisEntry 9 }

        hcxRfAnalysisBin1Count OBJECT-TYPE 
                SYNTAX Gauge32
                MAX-ACCESS read-only
                STATUS current  
                DESCRIPTION "
                        This attribute respresents the number of noise
			samples with levels between hcxRfAnalysisPoint1
			and hcxRfAnalysisPoint2."
                ::= { com21HcxRfAnalysisEntry 10 } 

        hcxRfAnalysisBin2Count OBJECT-TYPE
                SYNTAX Gauge32
                MAX-ACCESS read-only
                STATUS current   
                DESCRIPTION "  
                        This attribute respresents the number of noise
                        samples with levels between hcxRfAnalysisPoint2
			and hcxRfAnalysisPoint3."
                ::= { com21HcxRfAnalysisEntry 11 }
 
        hcxRfAnalysisBin3Count OBJECT-TYPE  
                SYNTAX Gauge32
                MAX-ACCESS read-only
                STATUS current
                DESCRIPTION "
                        This attribute respresents the number of noise
                        samples with levels between hcxRfAnalysisPoint3
			and hcxRfAnalysisPoint4."
                ::= { com21HcxRfAnalysisEntry 12 }
 
        hcxRfAnalysisClearCount OBJECT-TYPE  
                SYNTAX INTEGER { nil(1), clear(2) }
                MAX-ACCESS read-write
                STATUS current
                DESCRIPTION "
                        This attribute is used to clear the three RF
			analysis counts."
                ::= { com21HcxRfAnalysisEntry 13 }
 
 

END
