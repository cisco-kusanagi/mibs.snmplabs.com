-- $Id: it-decnet-mib.mib,v 1.1 2000/07/25 14:21:27 sse Exp $
            ITOUCH-DECNET-MIB DEFINITIONS ::= BEGIN

                    IMPORTS
                            Counter
                                    FROM RFC1155-SMI
                            PhivAddr
                                    FROM RFC1289-phivMIB
                            iTouch, DateTime
                                    FROM ITOUCH-MIB
                            OBJECT-TYPE
                                    FROM RFC-1212;

            xDecnet         OBJECT IDENTIFIER ::= { iTouch 14 }

            -- iTouch DECnet groups

            xRcp            OBJECT IDENTIFIER ::= { xDecnet 1 }
            xPhiv           OBJECT IDENTIFIER ::= { xDecnet 2 }

            -- Phase IV subgroups

            xPhivRoute      OBJECT IDENTIFIER ::= { xPhiv 1 }
            xPhivCircuit    OBJECT IDENTIFIER ::= { xPhiv 2 }
            xPhivImport     OBJECT IDENTIFIER ::= { xPhiv 3 }
            xPhivImportArea OBJECT IDENTIFIER ::= { xPhiv 4 }
            xPhivExport     OBJECT IDENTIFIER ::= { xPhiv 5 }
            xPhivExportArea OBJECT IDENTIFIER ::= { xPhiv 6 }
            xPhivFilter     OBJECT IDENTIFIER ::= { xPhiv 7 }
            xPhivTraffic    OBJECT IDENTIFIER ::= { xPhiv 8 }




            -- This is a MIB module for all iTouch Communications DECnet
            -- implementations.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the Remote Console group

            -- Implementation of this group is mandatory for all iTouch
            -- systems that implement DECnet remote console (RCP)

            rcpRemoteAddress OBJECT-TYPE
                SYNTAX OCTET STRING (SIZE (0..6))
                ACCESS read-only
                STATUS mandatory
                DESCRIPTION
                    "If a remote console session exists, the Ethernet 
                    address of the remote partner, otherwise zero 
                    length."
                ::= { xRcp 1 }


            -- the Phase IV group

            -- Implementation of this group is mandatory for all iTouch
            -- systems that implement DECnet Phase IV routing

            -- the Phase IV Route subgroup

            phivPathSelection OBJECT-TYPE
                SYNTAX INTEGER { roundRobin(1), samePath(2) }
                ACCESS read-write
                STATUS mandatory
                DESCRIPTION
                    "The algorithm used to balance traffic between equal 
                    next hop paths.  'roundRobin' selects the next hop 
                    using a round robin algorithm for each hop.  
                    'samePath' selects the next hop guaranteeing that 
                    all packets with the same source/destination pair 
                    will always use the same next hop."
                DEFVAL { roundRobin }
                ::= { xPhivRoute 1 }

            phivMaxPaths OBJECT-TYPE
                SYNTAX INTEGER (1..255)
                ACCESS read-write
                STATUS mandatory
                DESCRIPTION
                    "The maximum number of equal cost next hops that the 
                    router can remember and successfully load balance 
                    between."
                DEFVAL { 1 }
                ::= { xPhivRoute 2 }

            phivStatus OBJECT-TYPE
                SYNTAX INTEGER { active(1), disabled(2),
                                 noAddressSpecified(3),
                                 noInterfacesEnabled(4),
                                 badCost(5) }
                ACCESS read-only
                STATUS mandatory
                DESCRIPTION
                    "The status of the DECnet routing software."
                ::= { xPhivRoute 3 }


            -- the Phase IV Circuit subgroup

            phivCircuitTable OBJECT-TYPE
                SYNTAX SEQUENCE OF PhivCircuitEntry
                ACCESS not-accessible
                STATUS mandatory
                DESCRIPTION
                    "A list of DECnet circuit entries."
                ::= { xPhivCircuit 1 }

            phivCircuitEntry OBJECT-TYPE
                SYNTAX PhivCircuitEntry
                ACCESS not-accessible
                STATUS mandatory
                DESCRIPTION
                    "Parameter values for a DECnet circuit."
                INDEX { xPhivCircuitIndex }
                ::= { phivCircuitTable 1 }

            PhivCircuitEntry ::=
                SEQUENCE {
                    xPhivCircuitIndex
                        INTEGER,
                    phivCircuitRoutingTimer
                        INTEGER,
                    phivCircuitOperCost
                        INTEGER,
                    phivCircuitErrors
                        Counter,
                    phivCircuitLastError
                        INTEGER,
                    phivCircuitLastErrorTime
                        DateTime,
                    phivCircuitLastErrorData
                        OCTET STRING,
                    phivCircuitProtocolPriority
                        INTEGER,
                    phivCircuitRoutingPriority
                        INTEGER
                }

            xPhivCircuitIndex OBJECT-TYPE
                SYNTAX INTEGER
                ACCESS read-only
                STATUS mandatory
                DESCRIPTION
                    "Identification of a circuit entry.  Same as an 
                    interface index (ifIndex)."
                ::= { phivCircuitEntry 1 }

            phivCircuitRoutingTimer OBJECT-TYPE
                SYNTAX INTEGER (1..65535)
                ACCESS read-write
                STATUS mandatory
                DESCRIPTION
                    "The maximum time in seconds allowed between Routing 
                    updates on the circuit. Different values for LANs 
                    vs. WANs."
                DEFVAL { 40 }
                ::= { phivCircuitEntry 2 }

            phivCircuitOperCost OBJECT-TYPE
                SYNTAX INTEGER
                ACCESS read-only
                STATUS mandatory
                DESCRIPTION
                    "The actual cost associated with the circuit."
                ::= { phivCircuitEntry 3 }

            phivCircuitErrors OBJECT-TYPE
                SYNTAX Counter
                ACCESS read-only
                STATUS mandatory
                DESCRIPTION
                    "The number of routed DECnet packets received in 
                    error on this circuit."
                ::= { phivCircuitEntry 4 }

            phivCircuitLastError OBJECT-TYPE
                SYNTAX INTEGER { noError(1),
                                 addressOutOfRange(2),
                                 ageExceeded(3),
                                 destinationUnreachable(4),
                                 packetFormatError(5),
                                 packetOversized(6),
                                 partialRoutingUpdate(7),
                                 verificationReject(8) }
                ACCESS read-only
                STATUS mandatory
                DESCRIPTION
                    "The error of the last routed DECnet packet received 
                    in error on this circuit."
                ::= { phivCircuitEntry 5 }

            phivCircuitLastErrorTime OBJECT-TYPE
                SYNTAX DateTime
                ACCESS read-only
                STATUS mandatory
                DESCRIPTION
                    "The date and time that the last routed DECnet 
                    packet was received in error on this circuit."
                ::= { phivCircuitEntry 6 }

            phivCircuitLastErrorData OBJECT-TYPE
                SYNTAX OCTET STRING (SIZE (22))
                ACCESS read-only
                STATUS mandatory
                DESCRIPTION
                    "The first 22 bytes of the last routed DECnet packet 
                    received in error on this circuit."
                ::= { phivCircuitEntry 7 }

            phivCircuitProtocolPriority OBJECT-TYPE
                SYNTAX INTEGER { low(1), medium(3), high(5) }
                ACCESS read-write
                STATUS mandatory
                DESCRIPTION
                    "The priority at which all DECnet routed packets 
                    will be placed on the WAN output queue."
                DEFVAL { medium }
                ::= { phivCircuitEntry 8 }

            phivCircuitRoutingPriority OBJECT-TYPE
                SYNTAX INTEGER (0..127)
                ACCESS read-write
                STATUS mandatory
                DESCRIPTION
                    "Router's priority to be designated router on this 
                    circuit."
                DEFVAL { 64 }
                ::= { phivCircuitEntry 9 }


            -- the Phase IV Import Filter subgroup

            phivCircuitImportTable OBJECT-TYPE
                SYNTAX SEQUENCE OF PhivCircuitImportEntry
                ACCESS not-accessible
                STATUS mandatory
                DESCRIPTION
                    "A list of circuit import filter entries."
                ::= { xPhivImport 1 }

            phivCircuitImportEntry OBJECT-TYPE
                SYNTAX PhivCircuitImportEntry
                ACCESS not-accessible
                STATUS mandatory
                DESCRIPTION
                    "Parameter values for an import filter."
                INDEX { phivCircuitImportIf, phivCircuitImportAddr,
                        phivCircuitImportMask }
                ::= { phivCircuitImportTable 1 }

            PhivCircuitImportEntry ::=
                SEQUENCE {
                    phivCircuitImportIf
                        INTEGER,
                    phivCircuitImportAddr
                        PhivAddr,
                    phivCircuitImportMask
                        PhivAddr,
                    phivCircuitImportAction
                        INTEGER,
                    phivCircuitImportStatus
                        INTEGER
                }

            phivCircuitImportIf OBJECT-TYPE
                SYNTAX INTEGER
                ACCESS read-only
                STATUS mandatory
                DESCRIPTION
                    "The interface associated with the import routing 
                    filter."
                ::= { phivCircuitImportEntry 1 }

            phivCircuitImportAddr OBJECT-TYPE
                SYNTAX PhivAddr
                ACCESS read-only
                STATUS mandatory
                DESCRIPTION
                    "The address (node or area) to match against learned 
                    route entries to decide whether to import the entry 
                    to the routing database."
                ::= { phivCircuitImportEntry 2 }

            phivCircuitImportMask OBJECT-TYPE
                SYNTAX PhivAddr
                ACCESS read-only
                STATUS mandatory
                DESCRIPTION
                    "The mask which is ANDed with the address field as 
                    well as the route entries address to determine 
                    whether the address matches the route entry."
                ::= { phivCircuitImportEntry 3 }

            phivCircuitImportAction OBJECT-TYPE
                SYNTAX INTEGER { discard(1), accept(2) }
                ACCESS read-write
                STATUS mandatory
                DESCRIPTION
                    "The action to take if the address field along with 
                    the mask field matches the route entry."
                DEFVAL { accept }
                ::= { phivCircuitImportEntry 4 }

            phivCircuitImportStatus OBJECT-TYPE
                SYNTAX INTEGER { invalid(1), valid(2) }
                ACCESS read-write
                STATUS mandatory
                DESCRIPTION
                    "Setting to 'invalid' removes this import filter 
                    from the table. Setting to 'valid' has no effect."
                DEFVAL { valid }
                ::= { phivCircuitImportEntry 5 }


            -- the Phase IV Import Area Filters subgroup

            phivCircuitImportAreaTable OBJECT-TYPE
                SYNTAX SEQUENCE OF PhivCircuitImportAreaEntry
                ACCESS not-accessible
                STATUS mandatory
                DESCRIPTION
                    "A list of circuit import area filter entries."
                ::= { xPhivImportArea 1 }

            phivCircuitImportAreaEntry OBJECT-TYPE
                SYNTAX PhivCircuitImportAreaEntry
                ACCESS not-accessible
                STATUS mandatory
                DESCRIPTION
                    "Parameter values for an import area filter."
                INDEX { phivCircuitImportAreaIf,
                        phivCircuitImportAreaAddr,
                        phivCircuitImportAreaMask }
                ::= { phivCircuitImportAreaTable 1 }

            PhivCircuitImportAreaEntry ::=
                SEQUENCE {
                    phivCircuitImportAreaIf
                        INTEGER,
                    phivCircuitImportAreaAddr
                        PhivAddr,
                    phivCircuitImportAreaMask
                        PhivAddr,
                    phivCircuitImportAreaAction
                        INTEGER,
                    phivCircuitImportAreaStatus
                        INTEGER
                }

            phivCircuitImportAreaIf OBJECT-TYPE
                SYNTAX INTEGER
                ACCESS read-only
                STATUS mandatory
                DESCRIPTION
                    "The interface associated with the import area 
                    routing filter."
                ::= { phivCircuitImportAreaEntry 1 }

            phivCircuitImportAreaAddr OBJECT-TYPE
                SYNTAX PhivAddr
                ACCESS read-only
                STATUS mandatory
                DESCRIPTION
                    "The address (node or area) to match against learned 
                    route entries to decide whether to import the entry 
                    to the routing database."
                ::= { phivCircuitImportAreaEntry 2 }

            phivCircuitImportAreaMask OBJECT-TYPE
                SYNTAX PhivAddr
                ACCESS read-only
                STATUS mandatory
                DESCRIPTION
                    "The mask which is ANDed with the address field as 
                    well as the route entries address to determine 
                    whether the address matches the route entry."
                ::= { phivCircuitImportAreaEntry 3 }

            phivCircuitImportAreaAction OBJECT-TYPE
                SYNTAX INTEGER { discard(1), accept(2) }
                ACCESS read-write
                STATUS mandatory
                DESCRIPTION
                    "The action to take if the address field along with 
                    the mask field matches the route entry."
                DEFVAL { accept }
                ::= { phivCircuitImportAreaEntry 4 }

            phivCircuitImportAreaStatus OBJECT-TYPE
                SYNTAX INTEGER { invalid(1), valid(2) }
                ACCESS read-write
                STATUS mandatory
                DESCRIPTION
                    "Setting to 'invalid' removes this import area 
                    filter from the table.  Setting to 'valid' has no 
                    effect."
                DEFVAL { valid }
                ::= { phivCircuitImportAreaEntry 5 }


            -- the Phase IV Export Filters subgroup

            phivCircuitExportTable OBJECT-TYPE
                SYNTAX SEQUENCE OF PhivCircuitExportEntry
                ACCESS not-accessible
                STATUS mandatory
                DESCRIPTION
                    "A list of circuit export filter entries."
                ::= { xPhivExport 1 }

            phivCircuitExportEntry OBJECT-TYPE
                SYNTAX PhivCircuitExportEntry
                ACCESS not-accessible
                STATUS mandatory
                DESCRIPTION
                    "Parameter values for an export filter."
                INDEX { phivCircuitExportIf, phivCircuitExportAddr,
                        phivCircuitExportMask }
                ::= { phivCircuitExportTable 1 }

            PhivCircuitExportEntry ::=
                SEQUENCE {
                    phivCircuitExportIf
                        INTEGER,
                    phivCircuitExportAddr
                        PhivAddr,
                    phivCircuitExportMask
                        PhivAddr,
                    phivCircuitExportAction
                        INTEGER,
                    phivCircuitExportStatus
                        INTEGER
                }

            phivCircuitExportIf OBJECT-TYPE
                SYNTAX INTEGER
                ACCESS read-only
                STATUS mandatory
                DESCRIPTION
                    "The interface associated with the export routing 
                    filter."
                ::= { phivCircuitExportEntry 1 }

            phivCircuitExportAddr OBJECT-TYPE
                SYNTAX PhivAddr
                ACCESS read-only
                STATUS mandatory
                DESCRIPTION
                    "The address (node or area) to match against learned 
                    route entries to decide whether to export the entry 
                    to the routing database."
                ::= { phivCircuitExportEntry 2 }

            phivCircuitExportMask OBJECT-TYPE
                SYNTAX PhivAddr
                ACCESS read-only
                STATUS mandatory
                DESCRIPTION
                    "The mask which is ANDed with the address field as 
                    well as the route entries address to determine 
                    whether the address matches the route entry."
                ::= { phivCircuitExportEntry 3 }

            phivCircuitExportAction OBJECT-TYPE
                SYNTAX INTEGER { hide(1), advertise(2) }
                ACCESS read-write
                STATUS mandatory
                DESCRIPTION
                    "The action to take if the address field along with 
                    the mask field matches the route entry."
                DEFVAL { advertise }
                ::= { phivCircuitExportEntry 4 }

            phivCircuitExportStatus OBJECT-TYPE
                SYNTAX INTEGER { invalid(1), valid(2) }
                ACCESS read-write
                STATUS mandatory
                DESCRIPTION
                    "Setting to 'invalid' removes this export filter 
                    from the table.  Setting to 'valid' has no effect."
                DEFVAL { valid }
                ::= { phivCircuitExportEntry 5 }


            -- the Phase IV Export Area Filters subgroup

            phivCircuitExportAreaTable OBJECT-TYPE
                SYNTAX SEQUENCE OF PhivCircuitExportAreaEntry
                ACCESS not-accessible
                STATUS mandatory
                DESCRIPTION
                    "A list of circuit export area filter entries."
                ::= { xPhivExportArea 1 }

            phivCircuitExportAreaEntry OBJECT-TYPE
                SYNTAX PhivCircuitExportAreaEntry
                ACCESS not-accessible
                STATUS mandatory
                DESCRIPTION
                    "Parameter values for an export area filter."
                INDEX { phivCircuitExportAreaIf,
                        phivCircuitExportAreaAddr,
                        phivCircuitExportAreaMask }
                ::= { phivCircuitExportAreaTable 1 }

            PhivCircuitExportAreaEntry ::=
                SEQUENCE {
                    phivCircuitExportAreaIf
                        INTEGER,
                    phivCircuitExportAreaAddr
                        PhivAddr,
                    phivCircuitExportAreaMask
                        PhivAddr,
                    phivCircuitExportAreaAction
                        INTEGER,
                    phivCircuitExportAreaStatus
                        INTEGER
                }

            phivCircuitExportAreaIf OBJECT-TYPE
                SYNTAX INTEGER
                ACCESS read-only
                STATUS mandatory
                DESCRIPTION
                    "The interface associated with the export area 
                    routing filter."
                ::= { phivCircuitExportAreaEntry 1 }

            phivCircuitExportAreaAddr OBJECT-TYPE
                SYNTAX PhivAddr
                ACCESS read-only
                STATUS mandatory
                DESCRIPTION
                    "The address (node or area) to match against learned 
                    route entries to decide whether to export the entry 
                    to the routing database."
                ::= { phivCircuitExportAreaEntry 2 }

            phivCircuitExportAreaMask OBJECT-TYPE
                SYNTAX PhivAddr
                ACCESS read-only
                STATUS mandatory
                DESCRIPTION
                    "The mask which is ANDed with the address field as 
                    well as the route entries address to determine 
                    whether the address matches the route entry."
                ::= { phivCircuitExportAreaEntry 3 }

            phivCircuitExportAreaAction OBJECT-TYPE
                SYNTAX INTEGER { hide(1), advertise(2) }
                ACCESS read-write
                STATUS mandatory
                DESCRIPTION
                    "The action to take if the address field along with 
                    the mask field matches the route entry."
                DEFVAL { advertise }
                ::= { phivCircuitExportAreaEntry 4 }

            phivCircuitExportAreaStatus OBJECT-TYPE
                SYNTAX INTEGER { invalid(1), valid(2) }
                ACCESS read-write
                STATUS mandatory
                DESCRIPTION
                    "Setting to 'invalid' removes this export area 
                    filter from the table.  Setting to 'valid' has no 
                    effect."
                DEFVAL { valid }
                ::= { phivCircuitExportAreaEntry 5 }


            -- the Phase IV Filters subgroup

            phivCircuitFilterTable OBJECT-TYPE
                SYNTAX SEQUENCE OF PhivCircuitFilterEntry
                ACCESS not-accessible
                STATUS mandatory
                DESCRIPTION
                    "A list of circuit filter entries."
                ::= { xPhivFilter 1 }

            phivCircuitFilterEntry OBJECT-TYPE
                SYNTAX PhivCircuitFilterEntry
                ACCESS not-accessible
                STATUS mandatory
                DESCRIPTION
                    "Parameter values for a filter."
                INDEX { phivCircuitFilterIf,
                        phivCircuitFilterDstAddr,
                        phivCircuitFilterDstMask,
                        phivCircuitFilterSrcAddr,
                        phivCircuitFilterSrcMask }
                ::= { phivCircuitFilterTable 1 }

            PhivCircuitFilterEntry ::=
                SEQUENCE {
                    phivCircuitFilterIf
                        INTEGER,
                    phivCircuitFilterDstAddr
                        PhivAddr,
                    phivCircuitFilterDstMask
                        PhivAddr,
                    phivCircuitFilterSrcAddr
                        PhivAddr,
                    phivCircuitFilterSrcMask
                        PhivAddr,
                    phivCircuitFilterAction
                        INTEGER,
                    phivCircuitFilterStatus
                        INTEGER
                }

            phivCircuitFilterIf OBJECT-TYPE
                SYNTAX INTEGER
                ACCESS read-only
                STATUS mandatory
                DESCRIPTION
                    "The interface associated with the filter entry."
                ::= { phivCircuitFilterEntry 1 }

            phivCircuitFilterDstAddr OBJECT-TYPE
                SYNTAX PhivAddr
                ACCESS read-only
                STATUS mandatory
                DESCRIPTION
                    "The address (node or area) to match against the 
                    destination address of the packet to decide whether 
                    to forward the packet."
                ::= { phivCircuitFilterEntry 2 }

            phivCircuitFilterDstMask OBJECT-TYPE
                SYNTAX PhivAddr
                ACCESS read-only
                STATUS mandatory
                DESCRIPTION
                    "The mask which is ANDed with the destination 
                    address field and the packet's destination address 
                    to determine whether the address matches the 
                    packet's address."
                ::= { phivCircuitFilterEntry 3 }

            phivCircuitFilterSrcAddr OBJECT-TYPE
                SYNTAX PhivAddr
                ACCESS read-only
                STATUS mandatory
                DESCRIPTION
                    "The address (node or area) to match against the 
                    source address of the packet to decide whether to 
                    forward the packet."
                ::= { phivCircuitFilterEntry 4 }

            phivCircuitFilterSrcMask OBJECT-TYPE
                SYNTAX PhivAddr
                ACCESS read-only
                STATUS mandatory
                DESCRIPTION
                    "The mask which is ANDed with the source address 
                    field and the packet's source address to determine 
                    whether the address matches the packet's address."
                ::= { phivCircuitFilterEntry 5 }

            phivCircuitFilterAction OBJECT-TYPE
                SYNTAX INTEGER { discard(1), forward(2) }
                ACCESS read-write
                STATUS mandatory
                DESCRIPTION
                    "The action to take if the address fields along with 
                    the mask fields match the packet."
                DEFVAL { forward }
                ::= { phivCircuitFilterEntry 6 }

            phivCircuitFilterStatus OBJECT-TYPE
                SYNTAX INTEGER { invalid(1), valid(2) }
                ACCESS read-write
                STATUS mandatory
                DESCRIPTION
                    "Setting to 'invalid' removes this Filter filter 
                    from the table.  Setting to 'valid' has no effect."
                DEFVAL { valid }
                ::= { phivCircuitFilterEntry 7 }


            -- the Phase IV Traffic subgroup

            phivTrafficSort OBJECT-TYPE
                SYNTAX INTEGER { ready(1), execute(2) }
                ACCESS read-write
                STATUS mandatory
                DESCRIPTION
                    "Setting to 'execute' causes the most recent traffic 
                    information to be sorted into the phivTrafficTable. 
                    The sorting precedence is: decreasing percentage, 
                    increasing destination address, increasing source 
                    address, and increasing interface number.  Setting 
                    to 'ready' has no effect."
                ::= { xPhivTraffic 1 }

            phivTrafficTable OBJECT-TYPE
                SYNTAX SEQUENCE OF PhivTrafficEntry
                ACCESS not-accessible
                STATUS mandatory
                DESCRIPTION
                    "A list of traffic entries, sorted in the order 
                    specified by phivTrafficSort."
                ::= { xPhivTraffic 2 }

            phivTrafficEntry OBJECT-TYPE
                SYNTAX PhivTrafficEntry
                ACCESS not-accessible
                STATUS mandatory
                DESCRIPTION
                    "A traffic entry."
                INDEX { phivTrafficIndex }
                ::= { phivTrafficTable 1 }

            PhivTrafficEntry ::=
                SEQUENCE {
                    phivTrafficIndex
                        INTEGER,
                    phivTrafficPercent
                        INTEGER,
                    phivTrafficDst
                        PhivAddr,
                    phivTrafficSrc
                        PhivAddr,
                    phivTrafficIf
                        INTEGER
                }

            phivTrafficIndex OBJECT-TYPE
                SYNTAX INTEGER
                ACCESS read-only
                STATUS mandatory
                DESCRIPTION
                    "Identification of this traffic entry."
                ::= { phivTrafficEntry 1 }

            phivTrafficPercent OBJECT-TYPE
                SYNTAX INTEGER (0..1000)
                ACCESS read-only
                STATUS mandatory
                DESCRIPTION
                    "The percentage of total traffic that this traffic 
                    entry represents, in tenths of a percent."
                ::= { phivTrafficEntry 2 }

            phivTrafficDst OBJECT-TYPE
                SYNTAX PhivAddr
                ACCESS read-only
                STATUS mandatory
                DESCRIPTION
                    "The destination to which the traffic entry 
                    applies."
                ::= { phivTrafficEntry 3 }

            phivTrafficSrc OBJECT-TYPE
                SYNTAX PhivAddr
                ACCESS read-only
                STATUS mandatory
                DESCRIPTION
                    "The source to which the traffic entry applies."
                ::= { phivTrafficEntry 4 }

            phivTrafficIf OBJECT-TYPE
                SYNTAX INTEGER
                ACCESS read-only
                STATUS mandatory
                DESCRIPTION
                    "The inbound interface to which the traffic entry 
                    applies.  This value is the same as IfIndex."
                ::= { phivTrafficEntry 5 }

END
