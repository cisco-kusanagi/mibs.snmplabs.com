CXPCM-MIB DEFINITIONS ::= BEGIN

IMPORTS
   Counter        FROM RFC1155-SMI
   OBJECT-TYPE    FROM RFC-1212
   cxPCM,SapIndex FROM CXProduct-SMI;

-- Propietary Data Types
ChannelIndex      ::=   INTEGER (1..31)


--  Pulse Coded Modulation Configuration Table
-- The table describes:
-- status available for monitoring the current state of the service
-- access point.
-- statistics available for monitoring any service access point.
-- This Service Access Point is considered the PCM access point 
-- to the voice application. Hence, this MIB is only used in
-- voice applications.


pcmSapTable          OBJECT-TYPE
      SYNTAX   SEQUENCE OF PcmSapEntry
      ACCESS   not-accessible
      STATUS   mandatory
      DESCRIPTION
"A table containing configuration, controls, status and statistics 
information about each PCM module layer service access point."
      ::= { cxPCM 40 }


pcmSapEntry          OBJECT-TYPE
      SYNTAX   PcmSapEntry
      ACCESS   not-accessible
      STATUS   mandatory
      DESCRIPTION
"The parameters for a specific service access point."
      INDEX { pcmSapLinkNumber,
              pcmSapChannelNumber }
      ::= { pcmSapTable 1 }


PcmSapEntry   ::=
      SEQUENCE {
-- Parameters
         pcmSapLinkNumber     SapIndex,
         pcmSapChannelNumber  ChannelIndex,
-- Status
         pcmSapChannelState   INTEGER,
-- Statistics
         pcmSapRxPacket       Counter,
         pcmSapTxPacket       Counter,
         pcmSapTxDesync       Counter,
         pcmSapTxNotReady     Counter,
         pcmSapRxBusy         Counter,
         pcmSapTxUnderrun     Counter
         }


pcmSapLinkNumber      OBJECT-TYPE
      SYNTAX   SapIndex
      ACCESS   read-only
      STATUS   mandatory
      DESCRIPTION
"Indicates the link number associated with this SAP.

Range of Values: 1-2 for DI600 (port)

Default Value: none"
      ::= { pcmSapEntry 1 }


pcmSapChannelNumber   OBJECT-TYPE
      SYNTAX   ChannelIndex
      ACCESS   read-only
      STATUS   mandatory
      DESCRIPTION
"Indicates the B channel associated with this SAP.

Range of Values: 1-24 for T1
                 1-31 for E1
Default Value: none"
      ::= { pcmSapEntry 2 }


pcmSapChannelState   OBJECT-TYPE
      SYNTAX   INTEGER {
                  down  (1),
                  up    (2)
            }
      ACCESS   read-only
      STATUS   mandatory
      DESCRIPTION
"Indicates the current state of a voice configured  
B channel associated to this SAP.

Options:
down (1): A voice call is not established on this B channel.

unbound (2): A voice call is established on this B channel.

Default Value: none"
::= { pcmSapEntry 40 }


pcmSapRxPacket       OBJECT-TYPE
      SYNTAX   Counter
      ACCESS   read-only
      STATUS   mandatory
      DESCRIPTION
"Indicates the total number of error-free PCM voice packets 
received by the link since statistics were last reset.

Range of Values: 0-4, 294, 967, 295

Default Value: none"
      ::= { pcmSapEntry 60 }


pcmSapTxPacket       OBJECT-TYPE
      SYNTAX   Counter
      ACCESS   read-only
      STATUS   mandatory
      DESCRIPTION
"Indicates the total number of PCM voice packets successfully 
transmitted by the link since statistics were last reset. 

Range of Values: 0-4, 294, 967, 295

Default Value: none"
      ::= { pcmSapEntry 61 }


pcmSapTxDesync       OBJECT-TYPE
      SYNTAX   Counter
      ACCESS   read-only
      STATUS   mandatory
      DESCRIPTION
"Indicates the number of silence PCM voice packets sent 
when the voice application has no packet to send.

Range of Values: 0-4, 294, 967, 295

Default Value: none"
      ::= { pcmSapEntry 62 }


pcmSapTxNotReady     OBJECT-TYPE
      SYNTAX   Counter
      ACCESS   read-only
      STATUS   mandatory
      DESCRIPTION
"Indicates the number of reinitialization of this B channel 
due to a transmitter malfunction.

Range of Values: 0-4, 294, 967, 295

Default Value: none"
      ::= { pcmSapEntry 63 }


pcmSapRxBusy         OBJECT-TYPE
      SYNTAX   Counter
      ACCESS   read-only
      STATUS   mandatory
      DESCRIPTION
"Indicates the number of times that the receiver FIFO
has been full.

Range of Values: 0-4, 294, 967, 295

Default Value: none"
      ::= { pcmSapEntry 64 }


pcmSapTxUnderrun     OBJECT-TYPE
      SYNTAX   Counter
      ACCESS   read-only
      STATUS   mandatory
      DESCRIPTION
"Indicates the number of times that the transmitter FIFO
has been full.

Range of Values: 0-4, 294, 967, 295

Default Value: none"
      ::= { pcmSapEntry 65 }


--  Pulse Coded Modulation Debugging Table
-- The table describes:
-- controls available to manipulate a service access point
-- statistics.
-- The Service Access Points here is considered as the access 
-- point of the voice application. Hence, this MIB is only used
-- in voice applications.


pcmDebugTable        OBJECT-TYPE
      SYNTAX   SEQUENCE OF PcmDebugEntry
      ACCESS   not-accessible
      STATUS   mandatory
      DESCRIPTION
"A table containing controls about each PCM module 
layer service access point."
      ::= { cxPCM 60 }


pcmDebugEntry        OBJECT-TYPE
      SYNTAX   PcmDebugEntry
      ACCESS   not-accessible
      STATUS   mandatory
      DESCRIPTION
"The parameters for a specific service access point."
      INDEX { pcmDebugLinkNumber }
      ::= { pcmDebugTable 1 }


PcmDebugEntry   ::=
      SEQUENCE {
-- Parameters
         pcmDebugLinkNumber   SapIndex,
-- Controls
         pcmDebugLoopInfo     INTEGER
         }


pcmDebugLinkNumber      OBJECT-TYPE
      SYNTAX   SapIndex
      ACCESS   read-only
      STATUS   mandatory
      DESCRIPTION
"Indicates the link number associated with this SAP.

Range of Values: 1-2 for DI600 (port)

Default Value: none"
      ::= { pcmDebugEntry 1 }


pcmDebugLoopInfo    OBJECT-TYPE
      SYNTAX    INTEGER 
      ACCESS    write-only
      STATUS    mandatory
      DESCRIPTION
"This object displays the statistics relative to this PCM 
control block. When pcmSapDebugInfo is set to 1, it does
nothing, 2 displays the link information concerning the 
looping informations and timings while 3 clears these 
statistics."
      ::= { pcmDebugEntry 80 }

END
