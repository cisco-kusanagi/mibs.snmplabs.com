Wellfleet-IPPOLICY-MIB DEFINITIONS ::= BEGIN

-- Created by mdl2asn version 3.1
-- Creation date: Wed Aug 30 16:43:28 EDT 1995


    IMPORTS

      IpAddress
        FROM RFC1155-SMI
      OBJECT-TYPE
        FROM RFC-1212
      DisplayString
        FROM RFC1213-MIB
      wfIpPolicyGroup
        FROM Wellfleet-COMMON-MIB;


    wfIpRipAcceptTable OBJECT-TYPE
        SYNTAX	SEQUENCE OF WfIpRipAcceptEntry
        ACCESS	not-accessible
        STATUS	mandatory
        DESCRIPTION
                "The Table of Rip Accept Policy Rules"
        ::= { wfIpPolicyGroup 1 }

    wfIpRipAcceptEntry OBJECT-TYPE
        SYNTAX	WfIpRipAcceptEntry
        ACCESS	not-accessible
        STATUS	mandatory
        DESCRIPTION
                "An entry in the Rip Accept Rule Table"
        INDEX	{ wfIpRipAcceptIndex }
        ::= { wfIpRipAcceptTable 1 }

    WfIpRipAcceptEntry ::= SEQUENCE {
    	    wfIpRipAcceptDelete
    		INTEGER,
    	    wfIpRipAcceptDisable
    		INTEGER,
    	    wfIpRipAcceptIndex
    		INTEGER,
    	    wfIpRipAcceptName
    		DisplayString,
    	    wfIpRipAcceptNetworks
    		OCTET STRING,
    	    wfIpRipAcceptAction
    		INTEGER,
    	    wfIpRipAcceptPreference
    		INTEGER,
    	    wfIpRipAcceptPrecedence
    		INTEGER,
    	    wfIpRipAcceptInject
    		OCTET STRING,
    	    wfIpRipAcceptGateway
    		OCTET STRING,
    	    wfIpRipAcceptInterface
    		OCTET STRING,
    	    wfIpRipAcceptApplyMask
    		IpAddress
        }

    wfIpRipAcceptDelete OBJECT-TYPE
        SYNTAX	INTEGER {
    		    create(1),
    		    delete(2)
    		}
        ACCESS	read-write
        STATUS	mandatory
        DESCRIPTION
                "Create/Delete parameter."
        DEFVAL	{ create }
        ::= { wfIpRipAcceptEntry 1 }

    wfIpRipAcceptDisable OBJECT-TYPE
        SYNTAX	INTEGER {
    		    enabled(1),
    		    disabled(2)
    		}
        ACCESS	read-write
        STATUS	mandatory
        DESCRIPTION
                "Enable/Disable parameter."
        DEFVAL	{ enabled }
        ::= { wfIpRipAcceptEntry 2 }

    wfIpRipAcceptIndex OBJECT-TYPE
        SYNTAX	INTEGER
        ACCESS	read-only
        STATUS	mandatory
        DESCRIPTION
                "Rule index number"
        ::= { wfIpRipAcceptEntry 3 }

    wfIpRipAcceptName OBJECT-TYPE
        SYNTAX	DisplayString
        ACCESS	read-write
        STATUS	mandatory
        DESCRIPTION
                "Rule name - user specified name for this rule"
        ::= { wfIpRipAcceptEntry 4 }

    wfIpRipAcceptNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpRipAcceptEntry 5 }

    wfIpRipAcceptAction OBJECT-TYPE
        SYNTAX	INTEGER {
    		    accept(1),
    		    ignore(3)
    		}
        ACCESS	read-write
        STATUS	mandatory
        DESCRIPTION
                "action. 'accept' means that the route should be
                considered for inclusion in the routing table.  'ignore'
                means don't consider the route"
        DEFVAL	{ accept }
        ::= { wfIpRipAcceptEntry 6 }

    wfIpRipAcceptPreference OBJECT-TYPE
        SYNTAX	INTEGER(0..16)
        ACCESS	read-write
        STATUS	mandatory
        DESCRIPTION
                "preference. This is a metric to be used to compare
                the route to other routes to the same destination.  A
                value of 16 is 'most preferred'.  This parameter only has
                meaning if the action is 'accept'."
        DEFVAL	{ 1 }
        ::= { wfIpRipAcceptEntry 7 }

    wfIpRipAcceptPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpRipAcceptEntry 8 }

    wfIpRipAcceptInject OBJECT-TYPE
        SYNTAX	OCTET STRING
        ACCESS	read-only
        STATUS	mandatory
        DESCRIPTION
                "network injection list. this octet string should only be
                non-null if the action is 'accept' and if it is desired to
                insert networks into the routing table that differ from
                the actual advertised network.  For instance, if a number of
                networks in a certain range are learned, an aggregate
                advertisement could be inserted instead of the individual
                networks.

                If non-null, The octet string contains one or more 2-tuples
                of this form:

                 first 4 octets: network number
                 next 4 octets: network mask

                Upon receiving a route that matches this filter, all networks
                in this list will be considered for inclusion in the routing
                table.  If the list is null, the actual received network is
                considered.

                An encoding of 255.255.255.255/255.255.255.255 means 'match the
                actual received network.'  This allows insertion of an
                aggregate or default along with the actual network.

                Currently, this is only used for routes received via BGP."
        ::= { wfIpRipAcceptEntry 9 }

    wfIpRipAcceptGateway OBJECT-TYPE
        SYNTAX	OCTET STRING
        ACCESS	read-write
        STATUS	mandatory
        DESCRIPTION
                "RIP gateway list. This octet string contains the addresses
                of one or more routers that could send RIP updates to this
                router.  If a router address is included in this list,
                this filter applies to RIP advertisements from that router.

                If non-null, The octet string contains one or more 4-octet
                IP addresses.  If null, this filter applies to RIP updates
                from any router."
        ::= { wfIpRipAcceptEntry 10 }

    wfIpRipAcceptInterface OBJECT-TYPE
        SYNTAX	OCTET STRING
        ACCESS	read-write
        STATUS	mandatory
        DESCRIPTION
                "RIP interface list. This octet string contains the
                addresses of one or more interfaces on this router.  If an
                interface address is included in this list, this filter
                applies to RIP advertisements received on that interface.

                If non-null, The octet string contains one or more 4-octet
                IP addresses.  If null, this filter applies to RIP updates
                received on any interface."
        ::= { wfIpRipAcceptEntry 11 }

    wfIpRipAcceptApplyMask OBJECT-TYPE
        SYNTAX	IpAddress
        ACCESS	read-write
        STATUS	mandatory
        DESCRIPTION
                "Injection Mask: If the 'action' is accept and the
                actual received network will be considered, this is an
                optional IP address mask that will be applied to the network
                number from the RIP update.  This is used to override the
                interface's subnet mask in the presence of networks with
                variable length subnet masks."
        ::= { wfIpRipAcceptEntry 12 }

    wfIpRipAnnounceTable OBJECT-TYPE
        SYNTAX	SEQUENCE OF WfIpRipAnnounceEntry
        ACCESS	not-accessible
        STATUS	mandatory
        DESCRIPTION
                "The Table of Rip Announce Route Policy Rules"
        ::= { wfIpPolicyGroup 2 }

    wfIpRipAnnounceEntry OBJECT-TYPE
        SYNTAX	WfIpRipAnnounceEntry
        ACCESS	not-accessible
        STATUS	mandatory
        DESCRIPTION
                "An entry in the Rip Announce Rule Table"
        INDEX	{ wfIpRipAnnounceIndex }
        ::= { wfIpRipAnnounceTable 1 }

    WfIpRipAnnounceEntry ::= SEQUENCE {
    	    wfIpRipAnnounceDelete
    		INTEGER,
    	    wfIpRipAnnounceDisable
    		INTEGER,
    	    wfIpRipAnnounceIndex
    		INTEGER,
    	    wfIpRipAnnounceName
    		DisplayString,
    	    wfIpRipAnnounceNetworks
    		OCTET STRING,
    	    wfIpRipAnnounceAction
    		INTEGER,
    	    wfIpRipAnnouncePrecedence
    		INTEGER,
    	    wfIpRipAnnounceRouteSource
    		INTEGER,
    	    wfIpRipAnnounceExtRouteSource
    		INTEGER,
    	    wfIpRipAnnounceAdvertise
    		OCTET STRING,
    	    wfIpRipAnnounceRipGateway
    		OCTET STRING,
    	    wfIpRipAnnounceRipInterface
    		OCTET STRING,
    	    wfIpRipAnnounceOspfRouterId
    		OCTET STRING,
    	    wfIpRipAnnounceOspfType
    		INTEGER,
    	    wfIpRipAnnounceOspfTag
    		OCTET STRING,
    	    wfIpRipAnnounceEgpPeer
    		OCTET STRING,
    	    wfIpRipAnnounceEgpPeerAs
    		OCTET STRING,
    	    wfIpRipAnnounceEgpGateway
    		OCTET STRING,
    	    wfIpRipAnnounceBgpPeer
    		OCTET STRING,
    	    wfIpRipAnnounceBgpPeerAs
    		OCTET STRING,
    	    wfIpRipAnnounceBgpNextHop
    		OCTET STRING,
    	    wfIpRipAnnounceInterface
    		OCTET STRING,
    	    wfIpRipAnnounceRipMetric
    		INTEGER
        }

    wfIpRipAnnounceDelete OBJECT-TYPE
        SYNTAX	INTEGER {
    		    create(1),
    		    delete(2)
    		}
        ACCESS	read-write
        STATUS	mandatory
        DESCRIPTION
                "Create/Delete parameter."
        DEFVAL	{ create }
        ::= { wfIpRipAnnounceEntry 1 }

    wfIpRipAnnounceDisable OBJECT-TYPE
        SYNTAX	INTEGER {
    		    enabled(1),
    		    disabled(2)
    		}
        ACCESS	read-write
        STATUS	mandatory
        DESCRIPTION
                "Enable/Disable parameter."
        DEFVAL	{ enabled }
        ::= { wfIpRipAnnounceEntry 2 }

    wfIpRipAnnounceIndex OBJECT-TYPE
        SYNTAX	INTEGER
        ACCESS	read-only
        STATUS	mandatory
        DESCRIPTION
                "Rule index number"
        ::= { wfIpRipAnnounceEntry 3 }

    wfIpRipAnnounceName OBJECT-TYPE
        SYNTAX	DisplayString
        ACCESS	read-write
        STATUS	mandatory
        DESCRIPTION
                "Rule name - user specified name for this rule"
        ::= { wfIpRipAnnounceEntry 4 }

    wfIpRipAnnounceNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpRipAnnounceEntry 5 }

    wfIpRipAnnounceAction OBJECT-TYPE
        SYNTAX	INTEGER {
    		    announce(2),
    		    ignore(3)
    		}
        ACCESS	read-write
        STATUS	mandatory
        DESCRIPTION
                "action. 'announce' means that the route should be
                advertised.  'ignore' means don't advertise the route."
        DEFVAL	{ announce }
        ::= { wfIpRipAnnounceEntry 6 }

    wfIpRipAnnouncePrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpRipAnnounceEntry 7 }

    wfIpRipAnnounceRouteSource OBJECT-TYPE
        SYNTAX	INTEGER 
        ACCESS	read-write
        STATUS	mandatory
        DESCRIPTION
                "route source. This parameter can contain one or more
                route source identifiers.  If the route source is in this
                bit map, then a route from that source that meets the other
                criteria of this filter will match the filter.

                bit 0                                bit 31
                +---------------------------------------+
                |                                       |
                +---------------------------------------+

                bit31  DIRECT
                bit30  STATIC
                bit29  RIP
                bit28  OSPF
                bit27  EGP
                bit26  BGP
                "
        DEFVAL	{ 63 }
        ::= { wfIpRipAnnounceEntry 8 }

    wfIpRipAnnounceExtRouteSource OBJECT-TYPE
        SYNTAX	INTEGER
        ACCESS	read-write
        STATUS	mandatory
        DESCRIPTION
                "external route source. This parameter can contain one
                or more external route source identifiers.  If the external
                route source is in this bit map, then a route from that
                external source that meets the other criteria of this
                filter will match the filter.

                bit 0                                bit 31
                +---------------------------------------+
                |                                       |
                +---------------------------------------+

                bit31  DIRECT
                bit30  STATIC
                bit29  RIP
                bit28  OSPF
                bit27  EGP
                bit26  BGP
                "
        DEFVAL	{ 63 }
        ::= { wfIpRipAnnounceEntry 9 }

    wfIpRipAnnounceAdvertise OBJECT-TYPE
        SYNTAX	OCTET STRING
        ACCESS	read-write
        STATUS	mandatory
        DESCRIPTION
                "network advertisement list. this octet string should
                only be non-null if the action is 'announce' and if it is
                desired to advertise networks that differ from the actual
                network in the routing table.  For instance, if a number of
                networks in a certain range are in the table, an aggregate
                could be advertised instead of the individual networks.

                If non-null, The octet string contains one or more 2-tuples
                of this form:

                 first 4 octets: network number
                 next 4 octets: network mask

                Upon receiving a route that matches this filter, all networks
                in this list will be advertised.  If the list is null, the
                actual network is advertised.

                An encoding of 255.255.255.255/255.255.255.255 means 'match
                the actual network.'  This allows advertisement of an aggregate
                or default along with the actual network."
        ::= { wfIpRipAnnounceEntry 10 }

    wfIpRipAnnounceRipGateway OBJECT-TYPE
        SYNTAX	OCTET STRING
        ACCESS	read-write
        STATUS	mandatory
        DESCRIPTION
                "from RIP' gateway list. Only applicable for RIP sourced
                routes and if RIP is included as a route source.  This octet
                string contains the addresses of one or more routers that could
                send RIP updates to this router.  If a router address is
                included in this list, this filter applies to RIP
                advertisements from that router.

                If non-null, The octet string contains one or more 4-octet
                IP addresses.  If null, this filter applies to RIP updates
                from any router."
        ::= { wfIpRipAnnounceEntry 11 }

    wfIpRipAnnounceRipInterface OBJECT-TYPE
        SYNTAX	OCTET STRING
        ACCESS	read-write
        STATUS	mandatory
        DESCRIPTION
                "from RIP' interface list. Only applicable for RIP
                sourced routes and if RIP is included as a route source.
                This octet string contains the addresses of one or more
                interfaces on this router.  If an interface address is
                included in this list, this filter applies to RIP
                advertisements received on that interface.

                If non-null, The octet string contains one or more 4-octet
                IP addresses.  If null, this filter applies to RIP updates
                received on any interface."
        ::= { wfIpRipAnnounceEntry 12 }

    wfIpRipAnnounceOspfRouterId OBJECT-TYPE
        SYNTAX	OCTET STRING
        ACCESS	read-write
        STATUS	mandatory
        DESCRIPTION
                "from OSPF' Router ID list. Only applicable for OSPF sourced
                routes and if OSPF is included as a route source.  This octet
                string contains the router IDs of one or more OSPF routers.
                If a router ID is included in this list, this filter applies
                to OSPF advertisements authored by that router.

                If non-null, The octet string contains one or more 4-octet
                IP addresses.  If null, this filter applies to OSPF updates
                from any router."
        ::= { wfIpRipAnnounceEntry 13 }

    wfIpRipAnnounceOspfType OBJECT-TYPE
        SYNTAX	INTEGER {
    		    type1(1),
    		    type2(2),
    		    external(3),
    		    internal(4),
    		    any(7)
    		}
        ACCESS	read-write
        STATUS	mandatory
        DESCRIPTION
                "from OSPF' route type. Only applicable for OSPF sourced
                routes and if OSPF is included as a route source.  This
                parameter describes which types of OSPF routes match this
                filter.  'any' means match any route type.  'internal'
                means 'match any non-ASE'.  'external' means 'match any
                ASE'.  'type1' means 'match any external type 1'.  'type2'
                means 'match any external type 2"
        DEFVAL	{ any }
        ::= { wfIpRipAnnounceEntry 14 }

    wfIpRipAnnounceOspfTag OBJECT-TYPE
        SYNTAX	OCTET STRING
        ACCESS	read-write
        STATUS	mandatory
        DESCRIPTION
                "from OSPF' ASE tag list. Only applicable for OSPF sourced
                ASE routes and if OSPF is included as a route source.  This
                octet string contains tag values that could be present in an
                OSPF ASE advertisement.  If a tag value is included in this
                list, this filter applies to OSPF ASE advertisements that
                contain this tag value.

                If non-null, The octet string contains one or more 4-octet
                tag values.  If null, this filter applies to OSPF ASEs with
                any tag value."
        ::= { wfIpRipAnnounceEntry 15 }

    wfIpRipAnnounceEgpPeer OBJECT-TYPE
        SYNTAX	OCTET STRING
        ACCESS	read-write
        STATUS	mandatory
        DESCRIPTION
                "from EGP' Peer list. Only applicable for EGP sourced
                routes and if EGP is included as a route source.  This octet
                string contains the IP address of one or more EGP peers.
                If an EGP peer is included in this list, this filter applies
                to EGP advertisements authored by that router.

                If non-null, The octet string contains one or more 4-octet
                IP addresses.  If null, this filter applies to EGP
                advertisements from any router."
        ::= { wfIpRipAnnounceEntry 16 }

    wfIpRipAnnounceEgpPeerAs OBJECT-TYPE
        SYNTAX	OCTET STRING
        ACCESS	read-write
        STATUS	mandatory
        DESCRIPTION
                "from EGP' Peer AS list. Only applicable for EGP sourced
                routes and if EGP is included as a route source.  This octet
                string contains Autonomous System Numbers.  If an AS number
                is included in this list, this filter applies to EGP
                advertisements received from EBP peers in that AS.

                If non-null, The octet string contains one or more 2-octet
                AS numbers.  If null, this filter applies to EGP advertisements
                from peers in any AS."
        ::= { wfIpRipAnnounceEntry 17 }

    wfIpRipAnnounceEgpGateway OBJECT-TYPE
        SYNTAX	OCTET STRING
        ACCESS	read-write
        STATUS	mandatory
        DESCRIPTION
                "from EGP' Gateway list. Only applicable for EGP sourced
                routes and if EGP is included as a route source.  This octet
                string contains the IP address of one or more EGP gateways.
                If an EGP gateway is included in this list, this filter applies
                to EGP advertisements that use this gateway as the next hop.

                If non-null, The octet string contains one or more 4-octet
                IP addresses.  If null, this filter applies to EGP
                advertisements with any gateway address."
        ::= { wfIpRipAnnounceEntry 18 }

    wfIpRipAnnounceBgpPeer OBJECT-TYPE
        SYNTAX	OCTET STRING
        ACCESS	read-write
        STATUS	mandatory
        DESCRIPTION
                "from BGP' Peer list. Only applicable for BGP sourced
                routes and if BGP is included as a route source.  This octet
                string contains the IP address of one or more BGP peers.
                If a BGP peer is included in this list, this filter applies
                to BGP advertisements authored by that router.

                If non-null, The octet string contains one or more 4-octet
                IP addresses.  If null, this filter applies to BGP
                advertisements from any router."
        ::= { wfIpRipAnnounceEntry 19 }

    wfIpRipAnnounceBgpPeerAs OBJECT-TYPE
        SYNTAX	OCTET STRING
        ACCESS	read-write
        STATUS	mandatory
        DESCRIPTION
                "from BGP' AS list. Only applicable for BGP sourced
                routes and if BGP is included as a route source.  This octet
                string contains Autonomous System Numbers.  If an AS number
                is included in this list, this filter applies to BGP
                advertisements received from BGP peers in that AS.

                If non-null, The octet string contains one or more 2-octet
                AS numbers.  If null, this filter applies to BGP advertisements
                from peers in any AS."
        ::= { wfIpRipAnnounceEntry 20 }

    wfIpRipAnnounceBgpNextHop OBJECT-TYPE
        SYNTAX	OCTET STRING
        ACCESS	read-write
        STATUS	mandatory
        DESCRIPTION
                "from BGP' NextHop list. Only applicable for BGP sourced
                routes and if BGP is included as a route source.  This octet
                string contains IP addresses.  If an IP address
                is included in this list, this filter applies to BGP
                advertisements whose NEXT_HOP attribute matches this
                IP address.

                If non-null, The octet string contains one or more 4-octet
                IP addresses.  If null, this filter applies to BGP
                advertisements with any NEXT_HOP attribute."
        ::= { wfIpRipAnnounceEntry 21 }

    wfIpRipAnnounceInterface OBJECT-TYPE
        SYNTAX	OCTET STRING
        ACCESS	read-write
        STATUS	mandatory
        DESCRIPTION
                "RIP outbound interface list. This is a list of outgoing RIP
                interfaces.  If an interface appears in this list, the filter
                applies to RIP advertisements sent via that interface.

                If non-null, The octet string contains one or more 4-octet IP
                addresses.  If null, this filter applies to any outbound
                RIP interface."
        ::= { wfIpRipAnnounceEntry 22 }

    wfIpRipAnnounceRipMetric OBJECT-TYPE
        SYNTAX	INTEGER(0..15)
        ACCESS	read-write
        STATUS	mandatory
        DESCRIPTION
                "RIP metric. Only valid if the action is 'propagate'.
                This is an optional export metric to use when advertising
                a route that matches this filter.  If zero, the routing table
                metric calculated for RIP plus the interface cost is used."
        ::= { wfIpRipAnnounceEntry 23 }

    wfIpOspfAcceptTable OBJECT-TYPE
        SYNTAX	SEQUENCE OF WfIpOspfAcceptEntry
        ACCESS	not-accessible
        STATUS	mandatory
        DESCRIPTION
                "The Table of OSPF Accept Route Filter Rules"
        ::= { wfIpPolicyGroup 3 }

    wfIpOspfAcceptEntry OBJECT-TYPE
        SYNTAX	WfIpOspfAcceptEntry
        ACCESS	not-accessible
        STATUS	mandatory
        DESCRIPTION
                "An entry in the OSPF Accept Route Policy Table"
        INDEX	{ wfIpOspfAcceptIndex }
        ::= { wfIpOspfAcceptTable 1 }

    WfIpOspfAcceptEntry ::= SEQUENCE {
    	    wfIpOspfAcceptDelete
    		INTEGER,
    	    wfIpOspfAcceptDisable
    		INTEGER,
    	    wfIpOspfAcceptIndex
    		INTEGER,
    	    wfIpOspfAcceptName
    		DisplayString,
    	    wfIpOspfAcceptNetworks
    		OCTET STRING,
    	    wfIpOspfAcceptAction
    		INTEGER,
    	    wfIpOspfAcceptPreference
    		INTEGER,
    	    wfIpOspfAcceptPrecedence
    		INTEGER,
    	    wfIpOspfAcceptInject
    		OCTET STRING,
    	    wfIpOspfAcceptType
    		INTEGER,
    	    wfIpOspfAcceptTag
    		OCTET STRING
        }

    wfIpOspfAcceptDelete OBJECT-TYPE
        SYNTAX	INTEGER {
    		    create(1),
    		    delete(2)
    		}
        ACCESS	read-write
        STATUS	mandatory
        DESCRIPTION
                "Create/Delete parameter."
        DEFVAL	{ create }
        ::= { wfIpOspfAcceptEntry 1 }

    wfIpOspfAcceptDisable OBJECT-TYPE
        SYNTAX	INTEGER {
    		    enabled(1),
    		    disabled(2)
    		}
        ACCESS	read-write
        STATUS	mandatory
        DESCRIPTION
                "Enable/Disable parameter."
        DEFVAL	{ enabled }
        ::= { wfIpOspfAcceptEntry 2 }

    wfIpOspfAcceptIndex OBJECT-TYPE
        SYNTAX	INTEGER
        ACCESS	read-only
        STATUS	mandatory
        DESCRIPTION
                "Rule index number"
        ::= { wfIpOspfAcceptEntry 3 }

    wfIpOspfAcceptName OBJECT-TYPE
        SYNTAX	DisplayString
        ACCESS	read-write
        STATUS	mandatory
        DESCRIPTION
                "Rule name - user specified name for this rule"
        ::= { wfIpOspfAcceptEntry 4 }

    wfIpOspfAcceptNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpOspfAcceptEntry 5 }

    wfIpOspfAcceptAction OBJECT-TYPE
        SYNTAX	INTEGER {
    		    accept(1),
    		    ignore(3)
    		}
        ACCESS	read-write
        STATUS	mandatory
        DESCRIPTION
                "action. 'accept' means that the route should be
                considered for inclusion in the routing table.  'ignore'
                means don't consider the route"
        DEFVAL	{ accept }
        ::= { wfIpOspfAcceptEntry 6 }

    wfIpOspfAcceptPreference OBJECT-TYPE
        SYNTAX	INTEGER(0..16)
        ACCESS	read-write
        STATUS	mandatory
        DESCRIPTION
                "preference. This is a metric to be used to compare
                the route to other routes to the same destination.  A
                value of 16 is 'most preferred'.  This parameter only has
                meaning if the action is 'accept'."
        DEFVAL	{ 1 }
        ::= { wfIpOspfAcceptEntry 7 }

    wfIpOspfAcceptPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpOspfAcceptEntry 8 }

    wfIpOspfAcceptInject OBJECT-TYPE
        SYNTAX	OCTET STRING
        ACCESS	read-only
        STATUS	mandatory
        DESCRIPTION
                "network injection list. this octet string should only be
                non-null if the action is 'accept' and if it is desired to
                insert networks into the routing table that differ from
                the actual advertised network.  For instance, if a number of
                networks in a certain range are learned, an aggregate
                advertisement could be inserted instead of the individual
                networks.

                If non-null, The octet string contains one or more 2-tuples
                of this form:

                 first 4 octets: network number
                 next 4 octets: network mask

                Upon receiving a route that matches this filter, all networks
                in this list will be considered for inclusion in the routing
                table.  If the list is null, the actual received network is
                considered.

                An encoding of 255.255.255.255/255.255.255.255 means 'match the
                actual received network.'  This allows insertion of an
                aggregate or default along with the actual network.

                Currently, this is only used for routes received via BGP."
        ::= { wfIpOspfAcceptEntry 9 }

    wfIpOspfAcceptType OBJECT-TYPE
        SYNTAX	INTEGER {
    		    type1(1),
    		    type2(2),
    		    any(3)
    		}
        ACCESS	read-write
        STATUS	mandatory
        DESCRIPTION
                "OSPF ASE type. This parameter describes which
                types of OSPF ASE routes match this filter.
                'any' means 'match either ASE type 1 or 2'.
                'type1' means 'match any external type 1'.
                'type2' means 'match any external type 2"
        DEFVAL	{ any }
        ::= { wfIpOspfAcceptEntry 10 }

    wfIpOspfAcceptTag OBJECT-TYPE
        SYNTAX	OCTET STRING
        ACCESS	read-write
        STATUS	mandatory
        DESCRIPTION
                "OSPF ASE tag list. This octet string contains tag
                values that could be present in an OSPF ASE
                advertisement.  If a tag value is included in this
                list, this filter applies to OSPF ASE advertisements that
                contain this tag value.

                If non-null, The octet string contains one or more 4-octet
                tag values.  If null, this filter applies to OSPF ASEs with
                any tag value."
        ::= { wfIpOspfAcceptEntry 11 }

    wfIpOspfAnnounceTable OBJECT-TYPE
        SYNTAX	SEQUENCE OF WfIpOspfAnnounceEntry
        ACCESS	not-accessible
        STATUS	mandatory
        DESCRIPTION
                "The Table of OSPF Announce Route Policy Rules"
        ::= { wfIpPolicyGroup 4 }

    wfIpOspfAnnounceEntry OBJECT-TYPE
        SYNTAX	WfIpOspfAnnounceEntry
        ACCESS	not-accessible
        STATUS	mandatory
        DESCRIPTION
                "An entry in the OSPF Announce Route Filter Table"
        INDEX	{ wfIpOspfAnnounceIndex }
        ::= { wfIpOspfAnnounceTable 1 }

    WfIpOspfAnnounceEntry ::= SEQUENCE {
    	    wfIpOspfAnnounceDelete
    		INTEGER,
    	    wfIpOspfAnnounceDisable
    		INTEGER,
    	    wfIpOspfAnnounceIndex
    		INTEGER,
    	    wfIpOspfAnnounceName
    		DisplayString,
    	    wfIpOspfAnnounceNetworks
    		OCTET STRING,
    	    wfIpOspfAnnounceAction
    		INTEGER,
    	    wfIpOspfAnnouncePrecedence
    		INTEGER,
    	    wfIpOspfAnnounceRouteSource
    		INTEGER,
    	    wfIpOspfAnnounceExtRouteSource
    		INTEGER,
    	    wfIpOspfAnnounceAdvertise
    		OCTET STRING,
    	    wfIpOspfAnnounceRipGateway
    		OCTET STRING,
    	    wfIpOspfAnnounceRipInterface
    		OCTET STRING,
    	    wfIpOspfAnnounceOspfRouterId
    		OCTET STRING,
    	    wfIpOspfAnnounceOspfType
    		INTEGER,
    	    wfIpOspfAnnounceOspfTag
    		OCTET STRING,
    	    wfIpOspfAnnounceEgpPeer
    		OCTET STRING,
    	    wfIpOspfAnnounceEgpPeerAs
    		OCTET STRING,
    	    wfIpOspfAnnounceEgpGateway
    		OCTET STRING,
    	    wfIpOspfAnnounceBgpPeer
    		OCTET STRING,
    	    wfIpOspfAnnounceBgpPeerAs
    		OCTET STRING,
    	    wfIpOspfAnnounceBgpNextHop
    		OCTET STRING,
    	    wfIpOspfAnnounceType
    		INTEGER,
    	    wfIpOspfAnnounceTag
    		INTEGER,
    	    wfIpOspfAnnounceAutoTag
    		INTEGER,
    	    wfIpOspfAnnounceMetric
    		INTEGER,
    	    wfIpOspfAnnounceNssaPropagate
    		INTEGER
        }

    wfIpOspfAnnounceDelete OBJECT-TYPE
        SYNTAX	INTEGER {
    		    create(1),
    		    delete(2)
    		}
        ACCESS	read-write
        STATUS	mandatory
        DESCRIPTION
                "Create/Delete parameter."
        DEFVAL	{ create }
        ::= { wfIpOspfAnnounceEntry 1 }

    wfIpOspfAnnounceDisable OBJECT-TYPE
        SYNTAX	INTEGER {
    		    enabled(1),
    		    disabled(2)
    		}
        ACCESS	read-write
        STATUS	mandatory
        DESCRIPTION
                "Enable/Disable parameter."
        DEFVAL	{ enabled }
        ::= { wfIpOspfAnnounceEntry 2 }

    wfIpOspfAnnounceIndex OBJECT-TYPE
        SYNTAX	INTEGER
        ACCESS	read-only
        STATUS	mandatory
        DESCRIPTION
                "Rule index number"
        ::= { wfIpOspfAnnounceEntry 3 }

    wfIpOspfAnnounceName OBJECT-TYPE
        SYNTAX	DisplayString
        ACCESS	read-write
        STATUS	mandatory
        DESCRIPTION
                "Rule name - user specified name for this rule"
        ::= { wfIpOspfAnnounceEntry 4 }

    wfIpOspfAnnounceNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpOspfAnnounceEntry 5 }

    wfIpOspfAnnounceAction OBJECT-TYPE
        SYNTAX	INTEGER {
    		    announce(2),
    		    ignore(3)
    		}
        ACCESS	read-write
        STATUS	mandatory
        DESCRIPTION
                "action. 'announce' means that the route should be
                advertised.  'ignore' means don't advertise the route."
        DEFVAL	{ announce }
        ::= { wfIpOspfAnnounceEntry 6 }

    wfIpOspfAnnouncePrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpOspfAnnounceEntry 7 }

    wfIpOspfAnnounceRouteSource OBJECT-TYPE
        SYNTAX	INTEGER
        ACCESS	read-write
        STATUS	mandatory
        DESCRIPTION
                "route source. This parameter can contain one or more
                route source identifiers.  If the route source is in this
                bit map, then a route from that source that meets the other
                criteria of this filter will match the filter.

                bit 0                                bit 31
                +---------------------------------------+
                |                                       |
                +---------------------------------------+

                bit31  DIRECT
                bit30  STATIC
                bit29  RIP
                bit27  EGP
                bit26  BGP
                "
        DEFVAL	{ 63 }
        ::= { wfIpOspfAnnounceEntry 8 }

    wfIpOspfAnnounceExtRouteSource OBJECT-TYPE
       SYNTAX	INTEGER {
    		    any(63)
    		}
        ACCESS	read-only
        STATUS	mandatory
        DESCRIPTION
                "external route source. This parameter can contain one
                or more external route source identifiers.  If the external
                route source is in this bit map, then a route from that
                external source that meets the other criteria of this
                filter will match the filter.  Not valid for OSPF announce rules."
        DEFVAL	{ any }
        ::= { wfIpOspfAnnounceEntry 9 }

    wfIpOspfAnnounceAdvertise OBJECT-TYPE
        SYNTAX	OCTET STRING
        ACCESS	read-write
        STATUS	mandatory
        DESCRIPTION
                "network advertisement list. this octet string should
                only be non-null if the action is 'announce' and if it is
                desired to advertise networks that differ from the actual
                network in the routing table.  For instance, if a number of
                networks in a certain range are in the table, an aggregate
                could be advertised instead of the individual networks.

                If non-null, The octet string contains one or more 2-tuples
                of this form:

                 first 4 octets: network number
                 next 4 octets: network mask

                Upon receiving a route that matches this filter, all networks
                in this list will be advertised.  If the list is null, the
                actual network is advertised.

                An encoding of 255.255.255.255/255.255.255.255 means 'match
                the actual network.'  This allows advertisement of an aggregate
                or default along with the actual network."
        ::= { wfIpOspfAnnounceEntry 10 }

    wfIpOspfAnnounceRipGateway OBJECT-TYPE
        SYNTAX	OCTET STRING
        ACCESS	read-write
        STATUS	mandatory
        DESCRIPTION
                "from RIP' gateway list. Only applicable for RIP sourced
                routes and if RIP is included as a route source.  This octet
                string contains the addresses of one or more routers that could
                send RIP updates to this router.  If a router address is
                included in this list, this filter applies to RIP
                advertisements from that router.

                If non-null, The octet string contains one or more 4-octet
                IP addresses.  If null, this filter applies to RIP updates
                from any router."
        ::= { wfIpOspfAnnounceEntry 11 }

    wfIpOspfAnnounceRipInterface OBJECT-TYPE
        SYNTAX	OCTET STRING
        ACCESS	read-write
        STATUS	mandatory
        DESCRIPTION
                "from RIP' interface list. Only applicable for RIP
                sourced routes and if RIP is included as a route source.
                This octet string contains the addresses of one or more
                interfaces on this router.  If an interface address is
                included in this list, this filter applies to RIP
                advertisements received on that interface.

                If non-null, The octet string contains one or more 4-octet
                IP addresses.  If null, this filter applies to RIP updates
                received on any interface."
        ::= { wfIpOspfAnnounceEntry 12 }

    wfIpOspfAnnounceOspfRouterId OBJECT-TYPE
        SYNTAX	OCTET STRING
        ACCESS	read-write
        STATUS	mandatory
        DESCRIPTION
                "from OSPF' Router ID list. Only applicable for OSPF sourced
                routes and if OSPF is included as a route source.  This octet
                string contains the router IDs of one or more OSPF routers.
                If a router ID is included in this list, this filter applies
                to OSPF advertisements authored by that router.

                If non-null, The octet string contains one or more 4-octet
                IP addresses.  If null, this filter applies to OSPF updates
                from any router."
        ::= { wfIpOspfAnnounceEntry 13 }

    wfIpOspfAnnounceOspfType OBJECT-TYPE
        SYNTAX	INTEGER {
    		    type1(1),
    		    type2(2),
    		    external(3),
    		    internal(4),
    		    any(7)
    		}
        ACCESS	read-write
        STATUS	mandatory
        DESCRIPTION
                "from OSPF' route type. Only applicable for OSPF sourced
                routes and if OSPF is included as a route source.  This
                parameter describes which types of OSPF routes match this
                filter.  'any' means match any route type.  'internal'
                means 'match any non-ASE'.  'external' means 'match any
                ASE'.  'type1' means 'match any external type 1'.  'type2'
                means 'match any external type 2"
        DEFVAL	{ any }
        ::= { wfIpOspfAnnounceEntry 14 }

    wfIpOspfAnnounceOspfTag OBJECT-TYPE
        SYNTAX	OCTET STRING
        ACCESS	read-write
        STATUS	mandatory
        DESCRIPTION
                "from OSPF' ASE tag list. Only applicable for OSPF sourced
                ASE routes and if OSPF is included as a route source.  This
                octet string contains tag values that could be present in an
                OSPF ASE advertisement.  If a tag value is included in this
                list, this filter applies to OSPF ASE advertisements that
                contain this tag value.

                If non-null, The octet string contains one or more 4-octet
                tag values.  If null, this filter applies to OSPF ASEs with
                any tag value."
        ::= { wfIpOspfAnnounceEntry 15 }

    wfIpOspfAnnounceEgpPeer OBJECT-TYPE
        SYNTAX	OCTET STRING
        ACCESS	read-write
        STATUS	mandatory
        DESCRIPTION
                "from EGP' Peer list. Only applicable for EGP sourced
                routes and if EGP is included as a route source.  This octet
                string contains the IP address of one or more EGP peers.
                If an EGP peer is included in this list, this filter applies
                to EGP advertisements authored by that router.

                If non-null, The octet string contains one or more 4-octet
                IP addresses.  If null, this filter applies to EGP
                advertisements from any router."
        ::= { wfIpOspfAnnounceEntry 16 }

    wfIpOspfAnnounceEgpPeerAs OBJECT-TYPE
        SYNTAX	OCTET STRING
        ACCESS	read-write
        STATUS	mandatory
        DESCRIPTION
                "from EGP' Peer AS list. Only applicable for EGP sourced
                routes and if EGP is included as a route source.  This octet
                string contains Autonomous System Numbers.  If an AS number
                is included in this list, this filter applies to EGP
                advertisements received from EBP peers in that AS.

                If non-null, The octet string contains one or more 2-octet
                AS numbers.  If null, this filter applies to EGP advertisements
                from peers in any AS."
        ::= { wfIpOspfAnnounceEntry 17 }

    wfIpOspfAnnounceEgpGateway OBJECT-TYPE
        SYNTAX	OCTET STRING
        ACCESS	read-write
        STATUS	mandatory
        DESCRIPTION
                "from EGP' Gateway list. Only applicable for EGP sourced
                routes and if EGP is included as a route source.  This octet
                string contains the IP address of one or more EGP gateways.
                If an EGP gateway is included in this list, this filter applies
                to EGP advertisements that use this gateway as the next hop.

                If non-null, The octet string contains one or more 4-octet
                IP addresses.  If null, this filter applies to EGP
                advertisements with any gateway address."
        ::= { wfIpOspfAnnounceEntry 18 }

    wfIpOspfAnnounceBgpPeer OBJECT-TYPE
        SYNTAX	OCTET STRING
        ACCESS	read-write
        STATUS	mandatory
        DESCRIPTION
                "from BGP' Peer list. Only applicable for BGP sourced
                routes and if BGP is included as a route source.  This octet
                string contains the IP address of one or more BGP peers.
                If a BGP peer is included in this list, this filter applies
                to BGP advertisements authored by that router.

                If non-null, The octet string contains one or more 4-octet
                IP addresses.  If null, this filter applies to BGP
                advertisements from any router."
        ::= { wfIpOspfAnnounceEntry 19 }

    wfIpOspfAnnounceBgpPeerAs OBJECT-TYPE
        SYNTAX	OCTET STRING
        ACCESS	read-write
        STATUS	mandatory
        DESCRIPTION
                "from BGP' AS list. Only applicable for BGP sourced
                routes and if BGP is included as a route source.  This octet
                string contains Autonomous System Numbers.  If an AS number
                is included in this list, this filter applies to BGP
                advertisements received from BGP peers in that AS.

                If non-null, The octet string contains one or more 2-octet
                AS numbers.  If null, this filter applies to BGP advertisements
                from peers in any AS."
        ::= { wfIpOspfAnnounceEntry 20 }

    wfIpOspfAnnounceBgpNextHop OBJECT-TYPE
        SYNTAX	OCTET STRING
        ACCESS	read-write
        STATUS	mandatory
        DESCRIPTION
                "from BGP' NextHop list. Only applicable for BGP sourced
                routes and if BGP is included as a route source.  This octet
                string contains IP addresses.  If an IP address
                is included in this list, this filter applies to BGP
                advertisements whose NEXT_HOP attribute matches this
                IP address.

                If non-null, The octet string contains one or more 4-octet
                IP addresses.  If null, this filter applies to BGP
                advertisements with any NEXT_HOP attribute."
        ::= { wfIpOspfAnnounceEntry 21 }

    wfIpOspfAnnounceType OBJECT-TYPE
        SYNTAX	INTEGER {
    		    type1(1),
    		    type2(2)
    		}
        ACCESS	read-write
        STATUS	mandatory
        DESCRIPTION
                "OSPF ASE type. The ASE type to use for routes that
                match this filter.  This is only applicable if the
                action is 'accept'.  A zero value means to use the
                default ASE type for the route source."
        ::= { wfIpOspfAnnounceEntry 22 }

    wfIpOspfAnnounceTag OBJECT-TYPE
        SYNTAX	INTEGER
        ACCESS	read-write
        STATUS	mandatory
        DESCRIPTION
                "OSPF ASE tag. The ASE tag value to use for routes
                that match this filter.  This is only applicable if the
                action is 'accept' and autotag is set to 'disable'."
        ::= { wfIpOspfAnnounceEntry 23 }

    wfIpOspfAnnounceAutoTag OBJECT-TYPE
        SYNTAX	INTEGER {
    		    enabled(1),
    		    disabled(2),
    		    wf(3)
    		}
        ACCESS	read-write
        STATUS	mandatory
        DESCRIPTION
                "BGP/OSPF automatic tag generation: Only applicable
                if action is 'announce'.  if set to 'disabled',
                the value in wfIpOspfAnnounceTag will be used for a tag.
                If set to 'enabled', a tag will be generated according
                to the criteria in RFC 1403 (or any RFC that supercedes
                it)."
        DEFVAL	{ disabled }
        ::= { wfIpOspfAnnounceEntry 24 }

    wfIpOspfAnnounceMetric OBJECT-TYPE
        SYNTAX	INTEGER
        ACCESS	read-write
        STATUS	mandatory
        DESCRIPTION
                "The optional metric to apply to this route.
                Zero means : use the route's actual cost. Only
                valid for propagate."
        ::= { wfIpOspfAnnounceEntry 25 }

    wfIpOspfAnnounceNssaPropagate OBJECT-TYPE
        SYNTAX	 INTEGER {
		enabled(1),
		disabled(2)
	}
	ACCESS	 read-write
        STATUS	mandatory
        DESCRIPTION
		"Indicates whether or not the P-bit will be set in the Type-7 
		LSA of this route. If P-bit is set, the Type-7 LSA is 
		translated into a Type-5 LSA and the Type-5 LSA is flooded 
		into all non-stub areas. Otherwise, the Type-7 LSA is not 
		translated. This field only applies to the Type-7 LSA
		originated by an NSSA internal AS boundary router"
	 DEFVAL	 { disabled }
	 ::= { wfIpOspfAnnounceEntry 26 }

    wfIpEgpAcceptTable OBJECT-TYPE
        SYNTAX	SEQUENCE OF WfIpEgpAcceptEntry
        ACCESS	not-accessible
        STATUS	mandatory
        DESCRIPTION
                "The Table of EGP Accept Policy Rules"
        ::= { wfIpPolicyGroup 5 }

    wfIpEgpAcceptEntry OBJECT-TYPE
        SYNTAX	WfIpEgpAcceptEntry
        ACCESS	not-accessible
        STATUS	mandatory
        DESCRIPTION
                "An entry in the Egp Accept Rule Table"
        INDEX	{ wfIpEgpAcceptIndex }
        ::= { wfIpEgpAcceptTable 1 }

    WfIpEgpAcceptEntry ::= SEQUENCE {
    	    wfIpEgpAcceptDelete
    		INTEGER,
    	    wfIpEgpAcceptDisable
    		INTEGER,
    	    wfIpEgpAcceptIndex
    		INTEGER,
    	    wfIpEgpAcceptName
    		DisplayString,
    	    wfIpEgpAcceptNetworks
    		OCTET STRING,
    	    wfIpEgpAcceptAction
    		INTEGER,
    	    wfIpEgpAcceptPreference
    		INTEGER,
    	    wfIpEgpAcceptPrecedence
    		INTEGER,
    	    wfIpEgpAcceptInject
    		OCTET STRING,
    	    wfIpEgpAcceptPeer
    		OCTET STRING,
    	    wfIpEgpAcceptAs
    		OCTET STRING,
    	    wfIpEgpAcceptGateway
    		OCTET STRING
        }

    wfIpEgpAcceptDelete OBJECT-TYPE
        SYNTAX	INTEGER {
    		    create(1),
    		    delete(2)
    		}
        ACCESS	read-write
        STATUS	mandatory
        DESCRIPTION
                "Create/Delete parameter."
        DEFVAL	{ create }
        ::= { wfIpEgpAcceptEntry 1 }

    wfIpEgpAcceptDisable OBJECT-TYPE
        SYNTAX	INTEGER {
    		    enabled(1),
    		    disabled(2)
    		}
        ACCESS	read-write
        STATUS	mandatory
        DESCRIPTION
                "Enable/Disable parameter."
        DEFVAL	{ enabled }
        ::= { wfIpEgpAcceptEntry 2 }

    wfIpEgpAcceptIndex OBJECT-TYPE
        SYNTAX	INTEGER
        ACCESS	read-only
        STATUS	mandatory
        DESCRIPTION
                "Rule index number"
        ::= { wfIpEgpAcceptEntry 3 }

    wfIpEgpAcceptName OBJECT-TYPE
        SYNTAX	DisplayString
        ACCESS	read-write
        STATUS	mandatory
        DESCRIPTION
                "Rule name - user specified name for this rule"
        ::= { wfIpEgpAcceptEntry 4 }

    wfIpEgpAcceptNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpEgpAcceptEntry 5 }

    wfIpEgpAcceptAction OBJECT-TYPE
        SYNTAX	INTEGER {
    		    accept(1),
    		    ignore(3)
    		}
        ACCESS	read-write
        STATUS	mandatory
        DESCRIPTION
                "action. 'accept' means that the route should be
                considered for inclusion in the routing table.  'ignore'
                means don't consider the route"
        DEFVAL	{ accept }
        ::= { wfIpEgpAcceptEntry 6 }

    wfIpEgpAcceptPreference OBJECT-TYPE
        SYNTAX	INTEGER(0..16)
        ACCESS	read-write
        STATUS	mandatory
        DESCRIPTION
                "preference. This is a metric to be used to compare
                the route to other routes to the same destination.  A
                value of 16 is 'most preferred'.  This parameter only has
                meaning if the action is 'accept'."
        DEFVAL	{ 1 }
        ::= { wfIpEgpAcceptEntry 7 }

    wfIpEgpAcceptPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpEgpAcceptEntry 8 }

    wfIpEgpAcceptInject OBJECT-TYPE
        SYNTAX	OCTET STRING
        ACCESS	read-only
        STATUS	mandatory
        DESCRIPTION
                "network injection list. this octet string should only be
                non-null if the action is 'accept' and if it is desired to
                insert networks into the routing table that differ from
                the actual advertised network.  For instance, if a number of
                networks in a certain range are learned, an aggregate
                advertisement could be inserted instead of the individual
                networks.

                If non-null, The octet string contains one or more 2-tuples
                of this form:

                 first 4 octets: network number
                 next 4 octets: network mask

                Upon receiving a route that matches this filter, all networks
                in this list will be considered for inclusion in the routing
                table.  If the list is null, the actual received network is
                considered.

                An encoding of 255.255.255.255/255.255.255.255 means 'match the
                actual received network.'  This allows insertion of an
                aggregate or default along with the actual network.

                Currently, this is only used for routes received via BGP."
        ::= { wfIpEgpAcceptEntry 9 }

    wfIpEgpAcceptPeer OBJECT-TYPE
        SYNTAX	OCTET STRING
        ACCESS	read-write
        STATUS	mandatory
        DESCRIPTION
                "EGP Peer list. This octet string contains the
                IP addresses of one or more EGP peers.  If a peer
                address appears in this list, this filter applies
                to EGP advertisements from that peer.

                If non-null, The octet string contains one or more 4-octet
                IP addresses.  If null, this filter applies to EGP
                advertisements from any EGP peer."
        ::= { wfIpEgpAcceptEntry 10 }

    wfIpEgpAcceptAs OBJECT-TYPE
        SYNTAX	OCTET STRING
        ACCESS	read-write
        STATUS	mandatory
        DESCRIPTION
                "EGP Peer AS list. This octet string contains
                Autonomous System numbers.  If an AS appears in this
                list, this filter applies to EGP advertisements from
                peers in that AS.

                If non-null, The octet string contains one or more 2-octet
                AS numbers.  If null, this filter applies to EGP
                advertisements from peers in any AS."
        ::= { wfIpEgpAcceptEntry 11 }

    wfIpEgpAcceptGateway OBJECT-TYPE
        SYNTAX	OCTET STRING
        ACCESS	read-write
        STATUS	mandatory
        DESCRIPTION
                "EGP gateway list. This octet string contains the
                IP address of one or more EGP gateways.  If an EGP
                gateway is included in this list, this filter applies
                to EGP advertisements that use this gateway as the next hop.

                If non-null, The octet string contains one or more 4-octet
                IP addresses.  If null, this filter applies to EGP
                advertisements with any gateway address."
        ::= { wfIpEgpAcceptEntry 12 }

    wfIpEgpAnnounceTable OBJECT-TYPE
        SYNTAX	SEQUENCE OF WfIpEgpAnnounceEntry
        ACCESS	not-accessible
        STATUS	mandatory
        DESCRIPTION
                "The Table of Egp Announce Route Policy Rules"
        ::= { wfIpPolicyGroup 6 }

    wfIpEgpAnnounceEntry OBJECT-TYPE
        SYNTAX	WfIpEgpAnnounceEntry
        ACCESS	not-accessible
        STATUS	mandatory
        DESCRIPTION
                "An entry in the Egp Announce Rule Table"
        INDEX	{ wfIpEgpAnnounceIndex }
        ::= { wfIpEgpAnnounceTable 1 }

    WfIpEgpAnnounceEntry ::= SEQUENCE {
    	    wfIpEgpAnnounceDelete
    		INTEGER,
    	    wfIpEgpAnnounceDisable
    		INTEGER,
    	    wfIpEgpAnnounceIndex
    		INTEGER,
    	    wfIpEgpAnnounceName
    		DisplayString,
    	    wfIpEgpAnnounceNetworks
    		OCTET STRING,
    	    wfIpEgpAnnounceAction
    		INTEGER,
    	    wfIpEgpAnnouncePrecedence
    		INTEGER,
    	    wfIpEgpAnnounceRouteSource
    		INTEGER,
    	    wfIpEgpAnnounceExtRouteSource
    		INTEGER,
    	    wfIpEgpAnnounceAdvertise
    		OCTET STRING,
    	    wfIpEgpAnnounceRipGateway
    		OCTET STRING,
    	    wfIpEgpAnnounceRipInterface
    		OCTET STRING,
    	    wfIpEgpAnnounceOspfRouterId
    		OCTET STRING,
    	    wfIpEgpAnnounceOspfType
    		INTEGER,
    	    wfIpEgpAnnounceOspfTag
    		OCTET STRING,
    	    wfIpEgpAnnounceEgpPeer
    		OCTET STRING,
    	    wfIpEgpAnnounceEgpPeerAs
    		OCTET STRING,
    	    wfIpEgpAnnounceEgpGateway
    		OCTET STRING,
    	    wfIpEgpAnnounceBgpPeer
    		OCTET STRING,
    	    wfIpEgpAnnounceBgpPeerAs
    		OCTET STRING,
    	    wfIpEgpAnnounceBgpNextHop
    		OCTET STRING,
    	    wfIpEgpAnnouncePeer
    		OCTET STRING,
    	    wfIpEgpAnnounceInterface
    		OCTET STRING,
    	    wfIpEgpAnnounceMetric
    		INTEGER
        }

    wfIpEgpAnnounceDelete OBJECT-TYPE
        SYNTAX	INTEGER {
    		    create(1),
    		    delete(2)
    		}
        ACCESS	read-write
        STATUS	mandatory
        DESCRIPTION
                "Create/Delete parameter."
        DEFVAL	{ create }
        ::= { wfIpEgpAnnounceEntry 1 }

    wfIpEgpAnnounceDisable OBJECT-TYPE
        SYNTAX	INTEGER {
    		    enabled(1),
    		    disabled(2)
    		}
        ACCESS	read-write
        STATUS	mandatory
        DESCRIPTION
                "Enable/Disable parameter."
        DEFVAL	{ enabled }
        ::= { wfIpEgpAnnounceEntry 2 }

    wfIpEgpAnnounceIndex OBJECT-TYPE
        SYNTAX	INTEGER
        ACCESS	read-only
        STATUS	mandatory
        DESCRIPTION
                "Rule index number"
        ::= { wfIpEgpAnnounceEntry 3 }

    wfIpEgpAnnounceName OBJECT-TYPE
        SYNTAX	DisplayString
        ACCESS	read-write
        STATUS	mandatory
        DESCRIPTION
                "Rule name - user specified name for this rule"
        ::= { wfIpEgpAnnounceEntry 4 }

    wfIpEgpAnnounceNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpEgpAnnounceEntry 5 }

    wfIpEgpAnnounceAction OBJECT-TYPE
        SYNTAX	INTEGER {
    		    announce(2),
    		    ignore(3)
    		}
        ACCESS	read-write
        STATUS	mandatory
        DESCRIPTION
                "action. 'announce' means that the route should be
                advertised.  'ignore' means don't advertise the route."
        DEFVAL	{ announce }
        ::= { wfIpEgpAnnounceEntry 6 }

    wfIpEgpAnnouncePrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpEgpAnnounceEntry 7 }

    wfIpEgpAnnounceRouteSource OBJECT-TYPE
        SYNTAX	INTEGER
        ACCESS	read-write
        STATUS	mandatory
        DESCRIPTION
                "route source. This parameter can contain one or more
                route source identifiers.  If the route source is in this
                bit map, then a route from that source that meets the other
                criteria of this filter will match the filter.

                bit 0                                bit 31
                +---------------------------------------+
                |                                       |
                +---------------------------------------+

                bit31  DIRECT
                bit30  STATIC
                bit29  RIP
                bit28  OSPF
                bit27  EGP
                bit26  BGP
                "
        DEFVAL	{ 63 }
        ::= { wfIpEgpAnnounceEntry 8 }

    wfIpEgpAnnounceExtRouteSource OBJECT-TYPE
        SYNTAX	INTEGER
        ACCESS	read-write
        STATUS	mandatory
        DESCRIPTION
                "external route source. This parameter can contain one
                or more external route source identifiers.  If the external
                route source is in this bit map, then a route from that
                external source that meets the other criteria of this
                filter will match the filter.

                bit 0                                bit 31
                +---------------------------------------+
                |                                       |
                +---------------------------------------+

                bit31  DIRECT
                bit30  STATIC
                bit29  RIP
                bit28  OSPF
                bit27  EGP
                bit26  BGP
                "
        DEFVAL	{ 63 }
        ::= { wfIpEgpAnnounceEntry 9 }

    wfIpEgpAnnounceAdvertise OBJECT-TYPE
        SYNTAX	OCTET STRING
        ACCESS	read-write
        STATUS	mandatory
        DESCRIPTION
                "network advertisement list. this octet string should
                only be non-null if the action is 'announce' and if it is
                desired to advertise networks that differ from the actual
                network in the routing table.  For instance, if a number of
                networks in a certain range are in the table, an aggregate
                could be advertised instead of the individual networks.

                If non-null, The octet string contains one or more 2-tuples
                of this form:

                 first 4 octets: network number
                 next 4 octets: network mask

                Upon receiving a route that matches this filter, all networks
                in this list will be advertised.  If the list is null, the
                actual network is advertised.

                An encoding of 255.255.255.255/255.255.255.255 means 'match
                the actual network.'  This allows advertisement of an aggregate
                or default along with the actual network."
        ::= { wfIpEgpAnnounceEntry 10 }

    wfIpEgpAnnounceRipGateway OBJECT-TYPE
        SYNTAX	OCTET STRING
        ACCESS	read-write
        STATUS	mandatory
        DESCRIPTION
                "from RIP' gateway list. Only applicable for RIP sourced
                routes and if RIP is included as a route source.  This octet
                string contains the addresses of one or more routers that could
                send RIP updates to this router.  If a router address is
                included in this list, this filter applies to RIP
                advertisements from that router.

                If non-null, The octet string contains one or more 4-octet
                IP addresses.  If null, this filter applies to RIP updates
                from any router."
        ::= { wfIpEgpAnnounceEntry 11 }

    wfIpEgpAnnounceRipInterface OBJECT-TYPE
        SYNTAX	OCTET STRING
        ACCESS	read-write
        STATUS	mandatory
        DESCRIPTION
                "from RIP' interface list. Only applicable for RIP
                sourced routes and if RIP is included as a route source.
                This octet string contains the addresses of one or more
                interfaces on this router.  If an interface address is
                included in this list, this filter applies to RIP
                advertisements received on that interface.

                If non-null, The octet string contains one or more 4-octet
                IP addresses.  If null, this filter applies to RIP updates
                received on any interface."
        ::= { wfIpEgpAnnounceEntry 12 }

    wfIpEgpAnnounceOspfRouterId OBJECT-TYPE
        SYNTAX	OCTET STRING
        ACCESS	read-write
        STATUS	mandatory
        DESCRIPTION
                "from OSPF' Router ID list. Only applicable for OSPF sourced
                routes and if OSPF is included as a route source.  This octet
                string contains the router IDs of one or more OSPF routers.
                If a router ID is included in this list, this filter applies
                to OSPF advertisements authored by that router.

                If non-null, The octet string contains one or more 4-octet
                IP addresses.  If null, this filter applies to OSPF updates
                from any router."
        ::= { wfIpEgpAnnounceEntry 13 }

    wfIpEgpAnnounceOspfType OBJECT-TYPE
        SYNTAX	INTEGER {
    		    type1(1),
    		    type2(2),
    		    external(3),
    		    internal(4),
    		    any(7)
    		}
        ACCESS	read-write
        STATUS	mandatory
        DESCRIPTION
                "from OSPF' route type. Only applicable for OSPF sourced
                routes and if OSPF is included as a route source.  This
                parameter describes which types of OSPF routes match this
                filter.  'any' means match any route type.  'internal'
                means 'match any non-ASE'.  'external' means 'match any
                ASE'.  'type1' means 'match any external type 1'.  'type2'
                means 'match any external type 2"
        DEFVAL	{ any }
        ::= { wfIpEgpAnnounceEntry 14 }

    wfIpEgpAnnounceOspfTag OBJECT-TYPE
        SYNTAX	OCTET STRING
        ACCESS	read-write
        STATUS	mandatory
        DESCRIPTION
                "from OSPF' ASE tag list. Only applicable for OSPF sourced
                ASE routes and if OSPF is included as a route source.  This
                octet string contains tag values that could be present in an
                OSPF ASE advertisement.  If a tag value is included in this
                list, this filter applies to OSPF ASE advertisements that
                contain this tag value.

                If non-null, The octet string contains one or more 4-octet
                tag values.  If null, this filter applies to OSPF ASEs with
                any tag value."
        ::= { wfIpEgpAnnounceEntry 15 }

    wfIpEgpAnnounceEgpPeer OBJECT-TYPE
        SYNTAX	OCTET STRING
        ACCESS	read-write
        STATUS	mandatory
        DESCRIPTION
                "from EGP' Peer list. Only applicable for EGP sourced
                routes and if EGP is included as a route source.  This octet
                string contains the IP address of one or more EGP peers.
                If an EGP peer is included in this list, this filter applies
                to EGP advertisements authored by that router.

                If non-null, The octet string contains one or more 4-octet
                IP addresses.  If null, this filter applies to EGP
                advertisements from any router."
        ::= { wfIpEgpAnnounceEntry 16 }

    wfIpEgpAnnounceEgpPeerAs OBJECT-TYPE
        SYNTAX	OCTET STRING
        ACCESS	read-write
        STATUS	mandatory
        DESCRIPTION
                "from EGP' Peer AS list. Only applicable for EGP sourced
                routes and if EGP is included as a route source.  This octet
                string contains Autonomous System Numbers.  If an AS number
                is included in this list, this filter applies to EGP
                advertisements received from EBP peers in that AS.

                If non-null, The octet string contains one or more 2-octet
                AS numbers.  If null, this filter applies to EGP advertisements
                from peers in any AS."
        ::= { wfIpEgpAnnounceEntry 17 }

    wfIpEgpAnnounceEgpGateway OBJECT-TYPE
        SYNTAX	OCTET STRING
        ACCESS	read-write
        STATUS	mandatory
        DESCRIPTION
                "from EGP' Gateway list. Only applicable for EGP sourced
                routes and if EGP is included as a route source.  This octet
                string contains the IP address of one or more EGP gateways.
                If an EGP gateway is included in this list, this filter applies
                to EGP advertisements that use this gateway as the next hop.

                If non-null, The octet string contains one or more 4-octet
                IP addresses.  If null, this filter applies to EGP
                advertisements with any gateway address."
        ::= { wfIpEgpAnnounceEntry 18 }

    wfIpEgpAnnounceBgpPeer OBJECT-TYPE
        SYNTAX	OCTET STRING
        ACCESS	read-write
        STATUS	mandatory
        DESCRIPTION
                "from BGP' Peer list. Only applicable for BGP sourced
                routes and if BGP is included as a route source.  This octet
                string contains the IP address of one or more BGP peers.
                If a BGP peer is included in this list, this filter applies
                to BGP advertisements authored by that router.

                If non-null, The octet string contains one or more 4-octet
                IP addresses.  If null, this filter applies to BGP
                advertisements from any router."
        ::= { wfIpEgpAnnounceEntry 19 }

    wfIpEgpAnnounceBgpPeerAs OBJECT-TYPE
        SYNTAX	OCTET STRING
        ACCESS	read-write
        STATUS	mandatory
        DESCRIPTION
                "from BGP' AS list. Only applicable for BGP sourced
                routes and if BGP is included as a route source.  This octet
                string contains Autonomous System Numbers.  If an AS number
                is included in this list, this filter applies to BGP
                advertisements received from BGP peers in that AS.

                If non-null, The octet string contains one or more 2-octet
                AS numbers.  If null, this filter applies to BGP advertisements
                from peers in any AS."
        ::= { wfIpEgpAnnounceEntry 20 }

    wfIpEgpAnnounceBgpNextHop OBJECT-TYPE
        SYNTAX	OCTET STRING
        ACCESS	read-write
        STATUS	mandatory
        DESCRIPTION
                "from BGP' NextHop list. Only applicable for BGP sourced
                routes and if BGP is included as a route source.  This octet
                string contains IP addresses.  If an IP address
                is included in this list, this filter applies to BGP
                advertisements whose NEXT_HOP attribute matches this
                IP address.

                If non-null, The octet string contains one or more 4-octet
                IP addresses.  If null, this filter applies to BGP
                advertisements with any NEXT_HOP attribute."
        ::= { wfIpEgpAnnounceEntry 21 }

    wfIpEgpAnnouncePeer OBJECT-TYPE
        SYNTAX	OCTET STRING
        ACCESS	read-write
        STATUS	mandatory
        DESCRIPTION
                "EGP outbound peer list. This is a list of IP addresses
                of EGP peers.  If a peer appears in this list, the filter
                applies to EGP advertisements sent to that peer.

                If non-null, The octet string contains one or more 4-octet IP
                addresses.  If null, this filter applies to any EGP peer."
        ::= { wfIpEgpAnnounceEntry 22 }

    wfIpEgpAnnounceInterface OBJECT-TYPE
        SYNTAX	OCTET STRING
        ACCESS	read-write
        STATUS	mandatory
        DESCRIPTION
                "EGP outbound interface list. This is a list of outgoing
                interfaces.  If an interface appears in this list, the filter
                applies to EGP advertisements sent via that interface.

                If non-null, The octet string contains one or more 4-octet IP
                addresses.  If null, this filter applies to any outbound
                interface."
        ::= { wfIpEgpAnnounceEntry 23 }

    wfIpEgpAnnounceMetric OBJECT-TYPE
        SYNTAX	INTEGER(0..255)
        ACCESS	read-write
        STATUS	mandatory
        DESCRIPTION
                "EGP metric. Only valid if the action is 'propagate'.
                This is an optional export metric to use when advertising
                a route that matches this filter.  If zero, the routing table
                metric calculated for EGP is used."
        ::= { wfIpEgpAnnounceEntry 24 }

    wfIpBgp3AcceptTable OBJECT-TYPE
        SYNTAX	SEQUENCE OF WfIpBgp3AcceptEntry
        ACCESS	not-accessible
        STATUS	mandatory
        DESCRIPTION
                "The table of BGP-3 Accept Route Policy Rules"
        ::= { wfIpPolicyGroup 7 }

    wfIpBgp3AcceptEntry OBJECT-TYPE
        SYNTAX	WfIpBgp3AcceptEntry
        ACCESS	not-accessible
        STATUS	mandatory
        DESCRIPTION
                "An entry in the BGP-3 Accept Rule Table"
        INDEX	{ wfIpBgp3AcceptIndex }
        ::= { wfIpBgp3AcceptTable 1 }

    WfIpBgp3AcceptEntry ::= SEQUENCE {
    	    wfIpBgp3AcceptDelete
    		INTEGER,
    	    wfIpBgp3AcceptDisable
    		INTEGER,
    	    wfIpBgp3AcceptIndex
    		INTEGER,
    	    wfIpBgp3AcceptName
    		DisplayString,
    	    wfIpBgp3AcceptNetworks
    		OCTET STRING,
    	    wfIpBgp3AcceptAction
    		INTEGER,
    	    wfIpBgp3AcceptPreference
    		INTEGER,
    	    wfIpBgp3AcceptPrecedence
    		INTEGER,
    	    wfIpBgp3AcceptInject
    		OCTET STRING,
    	    wfIpBgp3AcceptPeerAs
    		OCTET STRING,
    	    wfIpBgp3AcceptPeerAddress
    		OCTET STRING,
    	    wfIpBgp3AcceptOrigAs
    		OCTET STRING,
    	    wfIpBgp3AcceptRouteOrigin
    		INTEGER,
    	    wfIpBgp3AcceptBgp3Preference
    		INTEGER,
    	    wfIpBgp3AcceptAsWeightClass
    		INTEGER,
	    wfIpBgp3AcceptCommunityMatch
		OCTET STRING
        }

    wfIpBgp3AcceptDelete OBJECT-TYPE
        SYNTAX	INTEGER {
    		    create(1),
    		    delete(2)
    		}
        ACCESS	read-write
        STATUS	mandatory
        DESCRIPTION
                "Create/Delete parameter."
        DEFVAL	{ create }
        ::= { wfIpBgp3AcceptEntry 1 }

    wfIpBgp3AcceptDisable OBJECT-TYPE
        SYNTAX	INTEGER {
    		    enabled(1),
    		    disabled(2)
    		}
        ACCESS	read-write
        STATUS	mandatory
        DESCRIPTION
                "Enable/Disable parameter."
        DEFVAL	{ enabled }
        ::= { wfIpBgp3AcceptEntry 2 }

    wfIpBgp3AcceptIndex OBJECT-TYPE
        SYNTAX	INTEGER
        ACCESS	read-only
        STATUS	mandatory
        DESCRIPTION
                "Rule index number"
        ::= { wfIpBgp3AcceptEntry 3 }

    wfIpBgp3AcceptName OBJECT-TYPE
        SYNTAX	DisplayString
        ACCESS	read-write
        STATUS	mandatory
        DESCRIPTION
                "Rule name - user specified name for this rule"
        ::= { wfIpBgp3AcceptEntry 4 }

    wfIpBgp3AcceptNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpBgp3AcceptEntry 5 }

    wfIpBgp3AcceptAction OBJECT-TYPE
        SYNTAX	INTEGER {
    		    accept(1),
    		    ignore(3)
    		}
        ACCESS	read-write
        STATUS	mandatory
        DESCRIPTION
                "action. 'accept' means that the route should be
                considered for inclusion in the routing table.  'ignore'
                means don't consider the route"
        DEFVAL	{ ignore }
        ::= { wfIpBgp3AcceptEntry 6 }

    wfIpBgp3AcceptPreference OBJECT-TYPE
        SYNTAX	INTEGER(0..16)
        ACCESS	read-write
        STATUS	mandatory
        DESCRIPTION
                "preference. This is a metric to be used to compare
                the route to other routes to the same destination.  A
                value of 16 is 'most preferred'.  This parameter only has
                meaning if the action is 'accept'."
        DEFVAL	{ 1 }
        ::= { wfIpBgp3AcceptEntry 7 }

    wfIpBgp3AcceptPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpBgp3AcceptEntry 8 }

    wfIpBgp3AcceptInject OBJECT-TYPE
        SYNTAX	OCTET STRING
        ACCESS	read-write
        STATUS	mandatory
        DESCRIPTION
                "network injection list. this octet string should only be
                non-null if the action is 'accept' and if it is desired to
                insert networks into the routing table that differ from
                the actual advertised network.  For instance, if a number of
                networks in a certain range are learned, an aggregate
                advertisement could be inserted instead of the individual
                networks.

                If non-null, The octet string contains one or more 2-tuples
                of this form:

                 first 4 octets: network number
                 next 4 octets: network mask

                Upon receiving a route that matches this filter, all networks
                in this list will be considered for inclusion in the routing
                table.  If the list is null, the actual received network is
                considered.

                An encoding of 255.255.255.255/255.255.255.255 means 'match the
                actual received network.'  This allows insertion of an
                aggregate or default along with the actual network.

                Currently, this is only used for routes received via BGP."
        ::= { wfIpBgp3AcceptEntry 9 }

    wfIpBgp3AcceptPeerAs OBJECT-TYPE
        SYNTAX	OCTET STRING
        ACCESS	read-write
        STATUS	mandatory
        DESCRIPTION
                "BGP-3 Peer AS list. This octet string contains
                Autonomous System numbers.  If an AS appears in this
                list, this filter applies to BGP advertisements from
                peers in that AS.

                If non-null, The octet string contains one or more 2-octet
                AS numbers.  If null, this filter applies to BGP
                advertisements from peers in any AS."
        ::= { wfIpBgp3AcceptEntry 10 }

    wfIpBgp3AcceptPeerAddress OBJECT-TYPE
        SYNTAX	OCTET STRING
        ACCESS	read-write
        STATUS	mandatory
        DESCRIPTION
                "BGP-3 Peer list. This octet string contains the
                IP addresses of one or more BGP peers.  If a peer
                address appears in this list, this filter applies
                to BGP advertisements from that peer.

                If non-null, The octet string contains one or more 4-octet
                IP addresses.  If null, this filter applies to BGP
                advertisements from any BGP peer."
        ::= { wfIpBgp3AcceptEntry 11 }

    wfIpBgp3AcceptOrigAs OBJECT-TYPE
        SYNTAX	OCTET STRING
        ACCESS	read-write
        STATUS	mandatory
        DESCRIPTION
                "BGP-3 Originating AS list. This octet string contains
                Autonomous System numbers.  If an AS appears in this
                list, this filter applies to BGP advertisements that have
                the AS as their originating AS.

                If non-null, The octet string contains one or more 2-octet
                AS numbers.  If null, this filter applies to BGP
                advertisements with any originating AS."
        ::= { wfIpBgp3AcceptEntry 12 }

    wfIpBgp3AcceptRouteOrigin OBJECT-TYPE
        SYNTAX	INTEGER {
    		    igp(1),
    		    egp(2),
    		    igporegp(3),
    		    incomplete(4),
    		    incompleteorigp(5),
    		    incompleteoregp(6),
    		    any(7)
    		}
        ACCESS	read-write
        STATUS	mandatory
        DESCRIPTION
                "BGP-3 ORIGIN path attribute. This is a bit map of the
                three possible origin types: IGP, EGP, and Incomplete.
                If the bit for a particular origin type is on, this filter
                applies to all advertisements with that ORIGIN path
                attribute."
        DEFVAL	{ any }
        ::= { wfIpBgp3AcceptEntry 13 }

    wfIpBgp3AcceptBgp3Preference OBJECT-TYPE
        SYNTAX	INTEGER(1..16)
        ACCESS	read-write
        STATUS	mandatory
        DESCRIPTION
                "BGP-3 preference. For routes that match this filter,
                this value is used for comparison against other BGP-3
                routes.  A larger value is more preferred.  Only valid
                if 'action' is 'accept'."
        DEFVAL	{ 1 }
        ::= { wfIpBgp3AcceptEntry 14 }

    wfIpBgp3AcceptAsWeightClass OBJECT-TYPE
        SYNTAX	INTEGER {
    		    class1(1),
    		    class2(2),
    		    class3(3),
    		    class4(4),
    		    class5(5),
    		    class6(6),
    		    class7(7),
    		    class8(8)
    		}
        ACCESS	read-write
        STATUS	mandatory
        DESCRIPTION
                "BGP AS Weight Class. For routes that match this filter,
                this value indicates which weight values should be used
                when calculating the AS path weight (see the AS weights
                table).  Only valid if 'action' is 'accept'."
        DEFVAL	{ class1 }
        ::= { wfIpBgp3AcceptEntry 15 }

    wfIpBgp3AcceptCommunityMatch OBJECT-TYPE
        SYNTAX  OCTET STRING
        ACCESS  read-write
        STATUS  mandatory
        DESCRIPTION
                "BGP Community list. This list identifies which
		attributes will match this rule. The octet string is
		a list of communities. Each community is 4 bytes long.
		If the 2 MS bytes are 0, the match is performed on
		the lower 16 bits.
 
                 A null string means 'match any attribute'."
        ::= { wfIpBgp3AcceptEntry 16 }
 
    wfIpBgp3AnnounceTable OBJECT-TYPE
        SYNTAX	SEQUENCE OF WfIpBgp3AnnounceEntry
        ACCESS	not-accessible
        STATUS	mandatory
        DESCRIPTION
                "The table of BGP-3 Announce Policy Rules"
        ::= { wfIpPolicyGroup 8 }

    wfIpBgp3AnnounceEntry OBJECT-TYPE
        SYNTAX	WfIpBgp3AnnounceEntry
        ACCESS	not-accessible
        STATUS	mandatory
        DESCRIPTION
                "An entry in the BGP-3 Announce Rule Table"
        INDEX	{ wfIpBgp3AnnounceIndex }
        ::= { wfIpBgp3AnnounceTable 1 }

    WfIpBgp3AnnounceEntry ::= SEQUENCE {
    	    wfIpBgp3AnnounceDelete
    		INTEGER,
    	    wfIpBgp3AnnounceDisable
    		INTEGER,
    	    wfIpBgp3AnnounceIndex
    		INTEGER,
    	    wfIpBgp3AnnounceName
    		DisplayString,
    	    wfIpBgp3AnnounceNetworks
    		OCTET STRING,
    	    wfIpBgp3AnnounceAction
    		INTEGER,
    	    wfIpBgp3AnnouncePrecedence
    		INTEGER,
    	    wfIpBgp3AnnounceRouteSource
    		INTEGER,
    	    wfIpBgp3AnnounceExtRouteSource
    		INTEGER,
    	    wfIpBgp3AnnounceAdvertise
    		OCTET STRING,
    	    wfIpBgp3AnnounceRipGateway
    		OCTET STRING,
    	    wfIpBgp3AnnounceRipInterface
    		OCTET STRING,
    	    wfIpBgp3AnnounceOspfRouterId
    		OCTET STRING,
    	    wfIpBgp3AnnounceOspfType
    		INTEGER,
    	    wfIpBgp3AnnounceOspfTag
    		OCTET STRING,
    	    wfIpBgp3AnnounceEgpPeer
    		OCTET STRING,
    	    wfIpBgp3AnnounceEgpPeerAs
    		OCTET STRING,
    	    wfIpBgp3AnnounceEgpGateway
    		OCTET STRING,
    	    wfIpBgp3AnnounceBgpPeer
    		OCTET STRING,
    	    wfIpBgp3AnnounceBgpPeerAs
    		OCTET STRING,
    	    wfIpBgp3AnnounceBgpNextHop
    		OCTET STRING,
    	    wfIpBgp3AnnouncePeerAs
    		OCTET STRING,
    	    wfIpBgp3AnnouncePeer
    		OCTET STRING,
    	    wfIpBgp3AnnounceUseMetric
    		INTEGER,
    	    wfIpBgp3AnnounceInterAsMetric
    		INTEGER,
    	    wfIpBgp3AnnounceOrigin
    		INTEGER,
    	    wfIpBgp3AnnounceAsPath
    		OCTET STRING,
    	    wfIpBgp3AnnounceNextHop
    		IpAddress,
	    wfIpBgp3AnnounceCommunity
		OCTET STRING,
	    wfIpBgp3AnnounceCommunityAction
		INTEGER,
	    wfIpBgp3AnnounceCommunityMatch
		OCTET STRING  
        }
    
    wfIpBgp3AnnounceDelete OBJECT-TYPE
        SYNTAX	INTEGER {
    		    create(1),
    		    delete(2)
    		}
        ACCESS	read-write
        STATUS	mandatory
        DESCRIPTION
                "Create/Delete parameter."
        DEFVAL	{ create }
        ::= { wfIpBgp3AnnounceEntry 1 }

    wfIpBgp3AnnounceDisable OBJECT-TYPE
        SYNTAX	INTEGER {
    		    enabled(1),
    		    disabled(2)
    		}
        ACCESS	read-write
        STATUS	mandatory
        DESCRIPTION
                "Enable/Disable parameter."
        DEFVAL	{ enabled }
        ::= { wfIpBgp3AnnounceEntry 2 }

    wfIpBgp3AnnounceIndex OBJECT-TYPE
        SYNTAX	INTEGER
        ACCESS	read-only
        STATUS	mandatory
        DESCRIPTION
                "Rule index number"
        ::= { wfIpBgp3AnnounceEntry 3 }

    wfIpBgp3AnnounceName OBJECT-TYPE
        SYNTAX	DisplayString
        ACCESS	read-write
        STATUS	mandatory
        DESCRIPTION
                "Rule name - user specified name for this rule"
        ::= { wfIpBgp3AnnounceEntry 4 }

    wfIpBgp3AnnounceNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpBgp3AnnounceEntry 5 }

    wfIpBgp3AnnounceAction OBJECT-TYPE
        SYNTAX	INTEGER {
    		    announce(2),
    		    ignore(3)
    		}
        ACCESS	read-write
        STATUS	mandatory
        DESCRIPTION
                "action. 'announce' means that the route should be
                advertised.  'ignore' means don't advertise the route."
        DEFVAL	{ ignore }
        ::= { wfIpBgp3AnnounceEntry 6 }

    wfIpBgp3AnnouncePrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpBgp3AnnounceEntry 7 }

    wfIpBgp3AnnounceRouteSource OBJECT-TYPE
        SYNTAX	INTEGER
        ACCESS	read-write
        STATUS	mandatory
        DESCRIPTION
                "route source. This parameter can contain one or more
                route source identifiers.  If the route source is in this
                bit map, then a route from that source that meets the other
                criteria of this filter will match the filter.

		bit 0                                bit 31
                +---------------------------------------+
                |                                       |
                +---------------------------------------+

                bit31  DIRECT
                bit30  STATIC
                bit29  RIP
                bit28  OSPF
                bit27  EGP
                bit26  BGP
                "
        DEFVAL	{ 63 }
        ::= { wfIpBgp3AnnounceEntry 8 }

    wfIpBgp3AnnounceExtRouteSource OBJECT-TYPE
        SYNTAX	INTEGER
        ACCESS	read-write
        STATUS	mandatory
        DESCRIPTION
                "external route source. This parameter can contain one
                or more external route source identifiers.  If the external
                route source is in this bit map, then a route from that
                external source that meets the other criteria of this
                filter will match the filter.

                bit 0                                bit 31
                +---------------------------------------+
                |                                       |
                +---------------------------------------+

                bit31  DIRECT
                bit30  STATIC
                bit29  RIP
                bit28  OSPF
                bit27  EGP
                bit26  BGP
                "
        DEFVAL	{ 63 }
        ::= { wfIpBgp3AnnounceEntry 9 }

    wfIpBgp3AnnounceAdvertise OBJECT-TYPE
        SYNTAX	OCTET STRING
        ACCESS	read-write
        STATUS	mandatory
        DESCRIPTION
                "network advertisement list. this octet string should
                only be non-null if the action is 'announce' and if it is
                desired to advertise networks that differ from the actual
                network in the routing table.  For instance, if a number of
                networks in a certain range are in the table, an aggregate
                could be advertised instead of the individual networks.

                If non-null, The octet string contains one or more 2-tuples
                of this form:

                 first 4 octets: network number
                 next 4 octets: network mask

                Upon receiving a route that matches this filter, all networks
                in this list will be advertised.  If the list is null, the
                actual network is advertised.

                An encoding of 255.255.255.255/255.255.255.255 means 'match
                the actual network.'  This allows advertisement of an aggregate
                or default along with the actual network."
        ::= { wfIpBgp3AnnounceEntry 10 }

    wfIpBgp3AnnounceRipGateway OBJECT-TYPE
        SYNTAX	OCTET STRING
        ACCESS	read-write
        STATUS	mandatory
        DESCRIPTION
                "from RIP' gateway list. Only applicable for RIP sourced
                routes and if RIP is included as a route source.  This octet
                string contains the addresses of one or more routers that could
                send RIP updates to this router.  If a router address is
                included in this list, this filter applies to RIP
                advertisements from that router.

                If non-null, The octet string contains one or more 4-octet
                IP addresses.  If null, this filter applies to RIP updates
                from any router."
        ::= { wfIpBgp3AnnounceEntry 11 }

    wfIpBgp3AnnounceRipInterface OBJECT-TYPE
        SYNTAX	OCTET STRING
        ACCESS	read-write
        STATUS	mandatory
        DESCRIPTION
                "from RIP' interface list. Only applicable for RIP
                sourced routes and if RIP is included as a route source.
                This octet string contains the addresses of one or more
                interfaces on this router.  If an interface address is
                included in this list, this filter applies to RIP
                advertisements received on that interface.

                If non-null, The octet string contains one or more 4-octet
                IP addresses.  If null, this filter applies to RIP updates
                received on any interface."
        ::= { wfIpBgp3AnnounceEntry 12 }

    wfIpBgp3AnnounceOspfRouterId OBJECT-TYPE
        SYNTAX	OCTET STRING
        ACCESS	read-write
        STATUS	mandatory
        DESCRIPTION
                "from OSPF' Router ID list. Only applicable for OSPF sourced
                routes and if OSPF is included as a route source.  This octet
                string contains the router IDs of one or more OSPF routers.
                If a router ID is included in this list, this filter applies
                to OSPF advertisements authored by that router.

                If non-null, The octet string contains one or more 4-octet
                IP addresses.  If null, this filter applies to OSPF updates
                from any router."
        ::= { wfIpBgp3AnnounceEntry 13 }

    wfIpBgp3AnnounceOspfType OBJECT-TYPE
        SYNTAX	INTEGER {
    		    type1(1),
    		    type2(2),
    		    external(3),
    		    internal(4),
    		    any(7)
    		}
        ACCESS	read-write
        STATUS	mandatory
        DESCRIPTION
                "from OSPF' route type. Only applicable for OSPF sourced
                routes and if OSPF is included as a route source.  This
                parameter describes which types of OSPF routes match this
                filter.  'any' means match any route type.  'internal'
                means 'match any non-ASE'.  'external' means 'match any
                ASE'.  'type1' means 'match any external type 1'.  'type2'
                means 'match any external type 2"
        DEFVAL	{ any }
        ::= { wfIpBgp3AnnounceEntry 14 }

    wfIpBgp3AnnounceOspfTag OBJECT-TYPE
        SYNTAX	OCTET STRING
        ACCESS	read-write
        STATUS	mandatory
        DESCRIPTION
                "from OSPF' ASE tag list. Only applicable for OSPF sourced
                ASE routes and if OSPF is included as a route source.  This
                octet string contains tag values that could be present in an
                OSPF ASE advertisement.  If a tag value is included in this
                list, this filter applies to OSPF ASE advertisements that
                contain this tag value.

                If non-null, The octet string contains one or more 4-octet
                tag values.  If null, this filter applies to OSPF ASEs with
                any tag value."
        ::= { wfIpBgp3AnnounceEntry 15 }

    wfIpBgp3AnnounceEgpPeer OBJECT-TYPE
        SYNTAX	OCTET STRING
        ACCESS	read-write
        STATUS	mandatory
        DESCRIPTION
                "from EGP' Peer list. Only applicable for EGP sourced
                routes and if EGP is included as a route source.  This octet
                string contains the IP address of one or more EGP peers.
                If an EGP peer is included in this list, this filter applies
                to EGP advertisements authored by that router.

                If non-null, The octet string contains one or more 4-octet
                IP addresses.  If null, this filter applies to EGP
                advertisements from any router."
        ::= { wfIpBgp3AnnounceEntry 16 }

    wfIpBgp3AnnounceEgpPeerAs OBJECT-TYPE
        SYNTAX	OCTET STRING
        ACCESS	read-write
        STATUS	mandatory
        DESCRIPTION
                "from EGP' Peer AS list. Only applicable for EGP sourced
                routes and if EGP is included as a route source.  This octet
                string contains Autonomous System Numbers.  If an AS number
                is included in this list, this filter applies to EGP
                advertisements received from EBP peers in that AS.

                If non-null, The octet string contains one or more 2-octet
                AS numbers.  If null, this filter applies to EGP advertisements
                from peers in any AS."
        ::= { wfIpBgp3AnnounceEntry 17 }

    wfIpBgp3AnnounceEgpGateway OBJECT-TYPE
        SYNTAX	OCTET STRING
        ACCESS	read-write
        STATUS	mandatory
        DESCRIPTION
                "from EGP' Gateway list. Only applicable for EGP sourced
                routes and if EGP is included as a route source.  This octet
                string contains the IP address of one or more EGP gateways.
                If an EGP gateway is included in this list, this filter applies
                to EGP advertisements that use this gateway as the next hop.

                If non-null, The octet string contains one or more 4-octet
                IP addresses.  If null, this filter applies to EGP
                advertisements with any gateway address."
        ::= { wfIpBgp3AnnounceEntry 18 }

    wfIpBgp3AnnounceBgpPeer OBJECT-TYPE
        SYNTAX	OCTET STRING
        ACCESS	read-write
        STATUS	mandatory
        DESCRIPTION
                "from BGP' Peer list. Only applicable for BGP sourced
                routes and if BGP is included as a route source.  This octet
                string contains the IP address of one or more BGP peers.
                If a BGP peer is included in this list, this filter applies
                to BGP advertisements authored by that router.

                If non-null, The octet string contains one or more 4-octet
                IP addresses.  If null, this filter applies to BGP
                advertisements from any router."
        ::= { wfIpBgp3AnnounceEntry 19 }

    wfIpBgp3AnnounceBgpPeerAs OBJECT-TYPE
        SYNTAX	OCTET STRING
        ACCESS	read-write
        STATUS	mandatory
        DESCRIPTION
                "from BGP' AS list. Only applicable for BGP sourced
                routes and if BGP is included as a route source.  This octet
                string contains Autonomous System Numbers.  If an AS number
                is included in this list, this filter applies to BGP
                advertisements received from BGP peers in that AS.

                If non-null, The octet string contains one or more 2-octet
                AS numbers.  If null, this filter applies to BGP advertisements
                from peers in any AS."
        ::= { wfIpBgp3AnnounceEntry 20 }

    wfIpBgp3AnnounceBgpNextHop OBJECT-TYPE
        SYNTAX	OCTET STRING
        ACCESS	read-write
        STATUS	mandatory
        DESCRIPTION
                "from BGP' NextHop list. Only applicable for BGP sourced
                routes and if BGP is included as a route source.  This octet
                string contains IP addresses.  If an IP address
                is included in this list, this filter applies to BGP
                advertisements whose NEXT_HOP attribute matches this
                IP address.

                If non-null, The octet string contains one or more 4-octet
                IP addresses.  If null, this filter applies to BGP
                advertisements with any NEXT_HOP attribute."
        ::= { wfIpBgp3AnnounceEntry 21 }

    wfIpBgp3AnnouncePeerAs OBJECT-TYPE
        SYNTAX	OCTET STRING
        ACCESS	read-write
        STATUS	mandatory
        DESCRIPTION
                "BGP-3 Outbound Peer AS list. This octet string
                contains Autonomous System Numbers.  If an AS number
                is included in this list, this filter applies to BGP
                advertisements being sent to BGP peers in that AS.

                If non-null, The octet string contains one or more 2-octet
                AS numbers.  If null, this filter applies to BGP advertisements
                going to peers in any AS."
        ::= { wfIpBgp3AnnounceEntry 22 }

    wfIpBgp3AnnouncePeer OBJECT-TYPE
        SYNTAX	OCTET STRING
        ACCESS	read-write
        STATUS	mandatory
        DESCRIPTION
                "BGP-3 Outbound Peer list. This octet string contains the
                IP address of one or more BGP peers.  If a BGP peer is
                included in this list, this filter applies to BGP
                advertisements being sent to that peer.

                If non-null, The octet string contains one or more 4-octet
                IP addresses.  If null, this filter applies to BGP
                advertisements being sent to any peer."
        ::= { wfIpBgp3AnnounceEntry 23 }

    wfIpBgp3AnnounceUseMetric OBJECT-TYPE
        SYNTAX	INTEGER {
    		    none(1),
    		    specified(2),
    		    originating(3)
    		}
        ACCESS	read-write
        STATUS	mandatory
        DESCRIPTION
                "Inter-AS Metric Selector. This parameter indicates
                whether or not an INTER_AS_METRIC will be advertised
                for a network matching this filter and, if advertised,
                what value to use.  'none' indicates that no metric will
                be advertised.  'specified' indicates that the value in
                wfIpBgp3AnnounceInterAsMetric will be used.  'originating'
                indicates that the metric from the originating
                protocol will be used.  Only valid if 'action' is
                'announce'."
        DEFVAL	{ none }
        ::= { wfIpBgp3AnnounceEntry 24 }

    wfIpBgp3AnnounceInterAsMetric OBJECT-TYPE
        SYNTAX	INTEGER(0..65535)
        ACCESS	read-write
        STATUS	mandatory
        DESCRIPTION
                "Specific Inter-AS Metric. If wfIpBgp3AnnounceUseMetric
                is set to 'specified', this is the value that will be used
                for the INTER_AS_METRIC.  Only valid if 'action' is
                'announce"
        ::= { wfIpBgp3AnnounceEntry 25 }

    wfIpBgp3AnnounceOrigin OBJECT-TYPE
        SYNTAX	INTEGER {
    		    igp(1),
    		    egp(2),
    		    incomplete(3),
		    none(4)
    		}
        ACCESS	read-write
        STATUS	mandatory
        DESCRIPTION
                "ORIGIN attribute override. If non-null, the ORIGIN
                attribute of a route matching this filter will be replaced
                with the indicated value.  Only valid if 'action' is
                'announce'."
	DEFVAL	{ none }
        ::= { wfIpBgp3AnnounceEntry 26 }

    wfIpBgp3AnnounceAsPath OBJECT-TYPE
        SYNTAX	OCTET STRING
        ACCESS	read-write
        STATUS	mandatory
        DESCRIPTION
                "AS-path override. If non-null, the AS_PATH attribute
                of a route matching this filter will be replaced with
                the indicated AS path.  Each element of the AS path is
                2-octet AS number.  Only valid if 'action' is
                'announce'."
        ::= { wfIpBgp3AnnounceEntry 27 }

    wfIpBgp3AnnounceNextHop OBJECT-TYPE
        SYNTAX	IpAddress
        ACCESS	read-write
        STATUS	mandatory
        DESCRIPTION
                "Announce Next Hop. If action is ANNOUNCE and this
                instance is non-zero, then overwrite Next Hop with
                specified value."
        ::= { wfIpBgp3AnnounceEntry 28 }

    wfIpBgp3AnnounceCommunity OBJECT-TYPE
        SYNTAX  OCTET STRING
        ACCESS  read-write
        STATUS  mandatory
        DESCRIPTION
                "BGP Community list. This identifies which
                 communities will be associated with this rule.
                 If non-null, the octet string contains one or
                 more 4-octet BGP Community numbers."
        ::= { wfIpBgp3AnnounceEntry 29 }
 
    wfIpBgp3AnnounceCommunityAction OBJECT-TYPE
        SYNTAX  INTEGER {
			as-is(1),
			remove(2),
			append(3),
			replace(4)
			}
        ACCESS  read-write
        STATUS  mandatory
        DESCRIPTION
		"Action 'as-is' means that existing BGP Community
		attribute is unchanged. 'remove' - all BGP
		Communities are removed from an update.
		'append' - existing BGP Communities are appended with
		the list of communities defined in wfIpBgp3AnnounceCommunity.
		'replace' - existing BGP Communities are are replaced
		with those defined in wfIpBgp3AnnounceCommunity."
        ::= { wfIpBgp3AnnounceEntry 30}
 
    wfIpBgp3AnnounceCommunityMatch OBJECT-TYPE
        SYNTAX  OCTET STRING
        ACCESS  read-write
        STATUS  mandatory
        DESCRIPTION
                "BGP Community list. This list identifies which
		attributes will match this rule. The octet string is
		a list of communities. Each community is 4 bytes long.
		If the 2 MS bytes are 0, the match is performed on
		the lower 16 bits. Only applicable to BGP-learnt routes.
 
                 A null string means 'match any attribute'."
        ::= { wfIpBgp3AnnounceEntry 31 }

    wfIpBgp4AcceptTable OBJECT-TYPE
        SYNTAX	SEQUENCE OF WfIpBgp4AcceptEntry
        ACCESS	not-accessible
        STATUS	mandatory
        DESCRIPTION
                "The table of BGP-4 Accept Route Policy Rules"
        ::= { wfIpPolicyGroup 9 }

    wfIpBgp4AcceptEntry OBJECT-TYPE
        SYNTAX	WfIpBgp4AcceptEntry
        ACCESS	not-accessible
        STATUS	mandatory
        DESCRIPTION
                "An entry in the BGP-4 Accept Rule Table"
        INDEX	{ wfIpBgp4AcceptIndex }
        ::= { wfIpBgp4AcceptTable 1 }

    WfIpBgp4AcceptEntry ::= SEQUENCE {
    	    wfIpBgp4AcceptDelete
    		INTEGER,
    	    wfIpBgp4AcceptDisable
    		INTEGER,
    	    wfIpBgp4AcceptIndex
    		INTEGER,
    	    wfIpBgp4AcceptName
    		DisplayString,
    	    wfIpBgp4AcceptNetworks
    		OCTET STRING,
    	    wfIpBgp4AcceptAction
    		INTEGER,
    	    wfIpBgp4AcceptPreference
    		INTEGER,
    	    wfIpBgp4AcceptPrecedence
    		INTEGER,
    	    wfIpBgp4AcceptInject
    		OCTET STRING,
    	    wfIpBgp4AcceptPeerAs
    		OCTET STRING,
    	    wfIpBgp4AcceptPeerAddress
    		OCTET STRING,
    	    wfIpBgp4AcceptOrigAs
    		OCTET STRING,
    	    wfIpBgp4AcceptRouteOrigin
    		INTEGER,
    	    wfIpBgp4AcceptAggrAs
    		OCTET STRING,
    	    wfIpBgp4AcceptAggrRouter
    		OCTET STRING,
    	    wfIpBgp4AcceptLocalPref
    		INTEGER,
    	    wfIpBgp4AcceptBgp4Preference
    		INTEGER,
    	    wfIpBgp4AcceptAsWeightClass
    		INTEGER,
    	    wfIpBgp4AcceptAsPatternMatch
    		DisplayString,
	    wfIpBgp4AcceptCommunityMatch
		OCTET STRING,
	    wfIpBgp4AcceptUseMultiExitDisc
		INTEGER,
            wfIpBgp4AcceptMultiExitDisc
		INTEGER, 
	    wfIpBgp4AcceptAsPrepend
                OCTET STRING,
            wfIpBgp4AcceptCommunity
                OCTET STRING,
            wfIpBgp4AcceptCommunityAction
                INTEGER,
            wfIpBgp4AcceptRFDampeningEnable
                INTEGER,
            wfIpBgp4AcceptRFDampeningTemplate
                INTEGER
        }

    wfIpBgp4AcceptDelete OBJECT-TYPE
        SYNTAX	INTEGER {
    		    create(1),
    		    delete(2)
    		}
        ACCESS	read-write
        STATUS	mandatory
        DESCRIPTION
                "Create/Delete parameter."
        DEFVAL	{ create }
        ::= { wfIpBgp4AcceptEntry 1 }

    wfIpBgp4AcceptDisable OBJECT-TYPE
        SYNTAX	INTEGER {
    		    enabled(1),
    		    disabled(2)
    		}
        ACCESS	read-write
        STATUS	mandatory
        DESCRIPTION
                "Enable/Disable parameter."
        DEFVAL	{ enabled }
        ::= { wfIpBgp4AcceptEntry 2 }

    wfIpBgp4AcceptIndex OBJECT-TYPE
        SYNTAX	INTEGER
        ACCESS	read-only
        STATUS	mandatory
        DESCRIPTION
                "Rule index number"
        ::= { wfIpBgp4AcceptEntry 3 }

    wfIpBgp4AcceptName OBJECT-TYPE
        SYNTAX	DisplayString
        ACCESS	read-write
        STATUS	mandatory
        DESCRIPTION
                "Rule name - user specified name for this rule"
        ::= { wfIpBgp4AcceptEntry 4 }

    wfIpBgp4AcceptNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpBgp4AcceptEntry 5 }

    wfIpBgp4AcceptAction OBJECT-TYPE
        SYNTAX	INTEGER {
    		    accept(1),
    		    ignore(3)
    		}
        ACCESS	read-write
        STATUS	mandatory
        DESCRIPTION
                "action. 'accept' means that the route should be
                considered for inclusion in the routing table.  'ignore'
                means don't consider the route"
        DEFVAL	{ ignore }
        ::= { wfIpBgp4AcceptEntry 6 }

    wfIpBgp4AcceptPreference OBJECT-TYPE
        SYNTAX	INTEGER(0..16)
        ACCESS	read-write
        STATUS	mandatory
        DESCRIPTION
                "preference. This is a metric to be used to compare
                the route to other routes to the same destination.  A
                value of 16 is 'most preferred'.  This parameter only has
                meaning if the action is 'accept'."
        DEFVAL	{ 1 }
        ::= { wfIpBgp4AcceptEntry 7 }

    wfIpBgp4AcceptPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpBgp4AcceptEntry 8 }

    wfIpBgp4AcceptInject OBJECT-TYPE
        SYNTAX	OCTET STRING
        ACCESS	read-write
        STATUS	mandatory
        DESCRIPTION
                "network injection list. this octet string should only be
                non-null if the action is 'accept' and if it is desired to
                insert networks into the routing table that differ from
                the actual advertised network.  For instance, if a number of
                networks in a certain range are learned, an aggregate
                advertisement could be inserted instead of the individual
                networks.

                If non-null, The octet string contains one or more 2-tuples
                of this form:

                 first 4 octets: network number
                 next 4 octets: network mask

                Upon receiving a route that matches this filter, all networks
                in this list will be considered for inclusion in the routing
                table.  If the list is null, the actual received network is
                considered.

                An encoding of 255.255.255.255/255.255.255.255 means 'match the
                actual received network.'  This allows insertion of an
                aggregate or default along with the actual network.

                Currently, this is only used for routes received via BGP."
        ::= { wfIpBgp4AcceptEntry 9 }

    wfIpBgp4AcceptPeerAs OBJECT-TYPE
        SYNTAX	OCTET STRING
        ACCESS	read-write
        STATUS	mandatory
        DESCRIPTION
                "BGP-4 Peer AS list. This octet string contains
                Autonomous System numbers.  If an AS appears in this
                list, this filter applies to BGP advertisements from
                peers in that AS.

                If non-null, The octet string contains one or more 2-octet
                AS numbers.  If null, this filter applies to BGP
                advertisements from peers in any AS."
        ::= { wfIpBgp4AcceptEntry 10 }

    wfIpBgp4AcceptPeerAddress OBJECT-TYPE
        SYNTAX	OCTET STRING
        ACCESS	read-write
        STATUS	mandatory
        DESCRIPTION
                "BGP-4 Peer list. This octet string contains the
                IP addresses of one or more BGP peers.  If a peer
                address appears in this list, this filter applies
                to BGP advertisements from that peer.

                If non-null, The octet string contains one or more 4-octet
                IP addresses.  If null, this filter applies to BGP
                advertisements from any BGP peer."
        ::= { wfIpBgp4AcceptEntry 11 }

    wfIpBgp4AcceptOrigAs OBJECT-TYPE
        SYNTAX	OCTET STRING
        ACCESS	read-write
        STATUS	mandatory
        DESCRIPTION
                "BGP-4 Originating AS list. This octet string contains
                Autonomous System numbers.  If an AS appears in this
                list, this filter applies to BGP advertisements that have
                the AS as their originating AS.

                If non-null, The octet string contains one or more 2-octet
                AS numbers.  If null, this filter applies to BGP
                advertisements with any originating AS."
        ::= { wfIpBgp4AcceptEntry 12 }

    wfIpBgp4AcceptRouteOrigin OBJECT-TYPE
        SYNTAX	INTEGER {
    		    igp(1),
    		    egp(2),
    		    igporegp(3),
    		    incomplete(4),
    		    incompleteorigp(5),
    		    incompleteoregp(6),
    		    any(7)
    		}
        ACCESS	read-write
        STATUS	mandatory
        DESCRIPTION
                "BGP-4 ORIGIN path attribute. This is a bit map of the
                three possible origin types: IGP, EGP, and Incomplete.
                If the bit for a particular origin type is on, this filter
                applies to all advertisements with that ORIGIN path
                attribute."
        DEFVAL	{ any }
        ::= { wfIpBgp4AcceptEntry 13 }

    wfIpBgp4AcceptAggrAs OBJECT-TYPE
        SYNTAX	OCTET STRING
        ACCESS	read-write
        STATUS	mandatory
        DESCRIPTION
                "BGP-4 Aggregator AS list. This octet string contains
                Autonomous System numbers.  If an AS appears in this
                list, this filter applies to BGP advertisements that contain
                the AS number in their AGGREGATOR path attribute.

                If non-null, The octet string contains one or more 2-octet
                AS numbers.  If null, this filter applies to BGP
                advertisements with any AS number in the AGGREGATOR
                path attribute."
        ::= { wfIpBgp4AcceptEntry 14 }

    wfIpBgp4AcceptAggrRouter OBJECT-TYPE
        SYNTAX	OCTET STRING
        ACCESS	read-write
        STATUS	mandatory
        DESCRIPTION
                "BGP-4 Aggregator Router list. This octet string contains
                the IP addresses of one or more BGP routers.  If a router
                address appears in this list, this filter applies to BGP
                advertisements that contain the address in their AGGREGATOR
                path attribute.

                If non-null, The octet string contains one or more 4-octet
                IP addresses.  If null, this filter applies to BGP
                advertisements with any router address in the AGGREGATOR
                path attribute."
        ::= { wfIpBgp4AcceptEntry 15 }

    wfIpBgp4AcceptLocalPref OBJECT-TYPE
        SYNTAX	INTEGER
        ACCESS	read-write
        STATUS	mandatory
        DESCRIPTION
                "BGP-4 Local Preference override. If non-null,
                any route matching this filter takes is assigned a
                local preference of the indicated value.  This is used
                to override the calculated value for EBGP routes or
                the LOCAL_PREF path attribute for IBGP routes."
        ::= { wfIpBgp4AcceptEntry 16 }

    wfIpBgp4AcceptBgp4Preference OBJECT-TYPE
        SYNTAX	INTEGER(1..16)
        ACCESS	read-write
        STATUS	mandatory
        DESCRIPTION
                "BGP-4 preference. For routes that match this filter,
                this value is used for comparison against other BGP-4
                routes.  A larger value is more preferred.  Only valid
                if 'action' is 'accept'."
        DEFVAL	{ 1 }
        ::= { wfIpBgp4AcceptEntry 17 }

    wfIpBgp4AcceptAsWeightClass OBJECT-TYPE
        SYNTAX	INTEGER {
    		    class1(1),
    		    class2(2),
    		    class3(3),
    		    class4(4),
    		    class5(5),
    		    class6(6),
    		    class7(7),
    		    class8(8)
    		}
        ACCESS	read-write
        STATUS	mandatory
        DESCRIPTION
                "BGP AS Weight Class. For routes that match this filter,
                this value indicates which weight values should be used
                when calculating the AS path weight (see the AS weights
                table).  Only valid if 'action' is 'accept'."
        DEFVAL	{ class1 }
        ::= { wfIpBgp4AcceptEntry 18 }

    wfIpBgp4AcceptAsPatternMatch OBJECT-TYPE
        SYNTAX	DisplayString
        ACCESS	read-write
        STATUS	mandatory
        DESCRIPTION
                "BGP AS_PATH Pattern Match string. This filter applies to BGP
                AS_PATH attribute and only routes which as_path matches
                the pattern string will be accepted. A pattern string can be
                any regular expression; this parameter is ignored if the string
                is malformed or not set."
        ::= { wfIpBgp4AcceptEntry 19 }

    wfIpBgp4AcceptCommunityMatch OBJECT-TYPE
        SYNTAX  OCTET STRING
        ACCESS  read-write
        STATUS  mandatory
        DESCRIPTION
                "BGP Community list. This list identifies which
		attributes will match this rule. The octet string is
		a list of communities. Each community is 4 bytes long.
		If the 2 MS bytes are 0, the match is performed on
		the lower 16 bits.
 
                 A null string means 'match any attribute'."
        ::= { wfIpBgp4AcceptEntry 20 }
    wfIpBgp4AcceptUseMultiExitDisc OBJECT-TYPE
	SYNTAX        INTEGER {
		passthru(1),
		override(2),
		generate(3),
		delete(4)   
		}
	ACCESS        read-write
	STATUS        mandatory
	DESCRIPTION
		"Multi-Exit Discriminator Selector. This parameter
		indicates whether or not a MULTI_EXIT_DISC will be
		accepted for a network matching this filter and, if
		accepted, what value to use.  'pass' indicates that the
		value will be advertised as received.  'override' indicates 
		that the value in wfIpBgp4AnnounceMultiExitDisc will be used.
		'generate' indicates that the value in 
		wfIpBgp4AnnounceMultiExitDisc will be used if a MED attr.
	        is not present in the BGP-4 update message.
	        'delete' indicates that the metric will be removed
	        if present in the attribute list.  Only valid if
	        'action' is 'accept'."
	DEFVAL        { passthru }
	::= { wfIpBgp4AcceptEntry 21 }

    wfIpBgp4AcceptMultiExitDisc OBJECT-TYPE
	SYNTAX        INTEGER(-1..2147483647)
	ACCESS        read-write
	STATUS        mandatory
	DESCRIPTION
	        "Specific Multi-Exit Discriminator. If
	        wfIpBgp4AcceptUseMultiExitDisc is set to 'override' or 
	        'Generate' and there is MED present,
	        this is the value that will be used for the
	        MULTI_EXIT_DISC.  Only valid if 'action' is 'accept'."
	DEFVAL  { -1 }
	::= { wfIpBgp4AcceptEntry 22 }

    wfIpBgp4AcceptAsPrepend OBJECT-TYPE
	SYNTAX  OCTET STRING
        ACCESS  read-write
        STATUS  mandatory
        DESCRIPTION
		"AS Prepend. This octet string contains AS numbers to
		 be added as a SEQUENCE to AS Path."
	::= { wfIpBgp4AcceptEntry 23 }

    wfIpBgp4AcceptCommunity OBJECT-TYPE
        SYNTAX  OCTET STRING
        ACCESS  read-write
        STATUS  mandatory
        DESCRIPTION
                "BGP Community list. This identifies which
                 communities will be associated with this rule.
                 If non-null, the octet string contains one or
                 more 4-octet BGP Community numbers."
        ::= { wfIpBgp4AcceptEntry 24 }

    wfIpBgp4AcceptCommunityAction OBJECT-TYPE
        SYNTAX  INTEGER {
                        as-is(1),
                        remove(2),
                        append(3),
                        replace(4)
                        }
        ACCESS  read-write
        STATUS  mandatory
        DESCRIPTION
                "Action 'as-is' means that existing BGP Community
                attribute is unchanged. 'remove' - all BGP
                Communities are removed from an update.
                'append' - existing BGP Communities are appended with
                the list of communities defined in wfIpBgp4AcceptCommunity.
                'replace' - existing BGP Communities are are replaced
                with those defined in wfIpBgp4AcceptCommunity."
        DEFVAL  { as-is }
        ::= { wfIpBgp4AcceptEntry 25 }

    wfIpBgp4AcceptRFDampeningEnable OBJECT-TYPE
        SYNTAX  INTEGER {
                    enabled(1),
                    disabled(2)
                }
        ACCESS  read-write
        STATUS  mandatory
        DESCRIPTION
                "Enables or disables Route Flap Dampening. Route flap dampeni
ng applies only to EBGP learnt routes."
        DEFVAL  { disabled }
        ::= { wfIpBgp4AcceptEntry 26 }

    wfIpBgp4AcceptRFDampeningTemplate OBJECT-TYPE
        SYNTAX  INTEGER
        ACCESS  read-write
        STATUS  mandatory
        DESCRIPTION
                "If Route Flap Dampening enabled, it will use this value
                 to index into the wfBgpRouteFlapTemplate table. The default
                 value of 1, points to the Default Template"
        DEFVAL  { 1 }
        ::= { wfIpBgp4AcceptEntry 27 }


    wfIpBgp4AnnounceTable OBJECT-TYPE
        SYNTAX	SEQUENCE OF WfIpBgp4AnnounceEntry
        ACCESS	not-accessible
        STATUS	mandatory
        DESCRIPTION
                "The table of BGP-4 Announce Policy Rules"
        ::= { wfIpPolicyGroup 10 }

    wfIpBgp4AnnounceEntry OBJECT-TYPE
        SYNTAX	WfIpBgp4AnnounceEntry
        ACCESS	not-accessible
        STATUS	mandatory
        DESCRIPTION
                "An entry in the BGP-4 Announce Rule Table"
        INDEX	{ wfIpBgp4AnnounceIndex }
        ::= { wfIpBgp4AnnounceTable 1 }

    WfIpBgp4AnnounceEntry ::= SEQUENCE {
    	    wfIpBgp4AnnounceDelete
    		INTEGER,
    	    wfIpBgp4AnnounceDisable
    		INTEGER,
    	    wfIpBgp4AnnounceIndex
    		INTEGER,
    	    wfIpBgp4AnnounceName
    		DisplayString,
    	    wfIpBgp4AnnounceNetworks
    		OCTET STRING,
    	    wfIpBgp4AnnounceAction
    		INTEGER,
    	    wfIpBgp4AnnouncePrecedence
    		INTEGER,
    	    wfIpBgp4AnnounceRouteSource
    		INTEGER,
    	    wfIpBgp4AnnounceExtRouteSource
    		INTEGER,
    	    wfIpBgp4AnnounceAdvertise
    		OCTET STRING,
    	    wfIpBgp4AnnounceRipGateway
    		OCTET STRING,
    	    wfIpBgp4AnnounceRipInterface
    		OCTET STRING,
    	    wfIpBgp4AnnounceOspfRouterId
    		OCTET STRING,
    	    wfIpBgp4AnnounceOspfType
    		INTEGER,
    	    wfIpBgp4AnnounceOspfTag
    		OCTET STRING,
    	    wfIpBgp4AnnounceEgpPeer
    		OCTET STRING,
    	    wfIpBgp4AnnounceEgpPeerAs
    		OCTET STRING,
    	    wfIpBgp4AnnounceEgpGateway
    		OCTET STRING,
    	    wfIpBgp4AnnounceBgpPeer
    		OCTET STRING,
    	    wfIpBgp4AnnounceBgpPeerAs
    		OCTET STRING,
    	    wfIpBgp4AnnounceBgpNextHop
    		OCTET STRING,
    	    wfIpBgp4AnnouncePeerAs
    		OCTET STRING,
    	    wfIpBgp4AnnouncePeer
    		OCTET STRING,
    	    wfIpBgp4AnnounceUseMultiExitDisc
    		INTEGER,
    	    wfIpBgp4AnnounceMultiExitDisc
    		INTEGER,
    	    wfIpBgp4AnnounceOrigin
    		INTEGER,
    	    wfIpBgp4AnnounceAsPath
    		OCTET STRING,
    	    wfIpBgp4AnnounceLocalPrefOverride
    		INTEGER,
    	    wfIpBgp4AnnounceLocalPref
    		INTEGER,
    	    wfIpBgp4AnnounceNextHop
    		IpAddress,
    	    wfIpBgp4AnnounceAtomic
    		INTEGER,
    	    wfIpBgp4AnnounceAsPatternMatch
    		DisplayString,
	    wfIpBgp4AnnounceCommunity
		OCTET STRING,
	    wfIpBgp4AnnounceCommunityAction
		INTEGER,
	    wfIpBgp4AnnounceCommunityMatch
		OCTET STRING,
	    wfIpBgp4AnnounceAsPrepend
		OCTET STRING
        }

    wfIpBgp4AnnounceDelete OBJECT-TYPE
        SYNTAX	INTEGER {
    		    create(1),
    		    delete(2)
    		}
        ACCESS	read-write
        STATUS	mandatory
        DESCRIPTION
                "Create/Delete parameter."
        DEFVAL	{ create }
        ::= { wfIpBgp4AnnounceEntry 1 }

    wfIpBgp4AnnounceDisable OBJECT-TYPE
        SYNTAX	INTEGER {
    		    enabled(1),
    		    disabled(2)
    		}
        ACCESS	read-write
        STATUS	mandatory
        DESCRIPTION
                "Enable/Disable parameter."
        DEFVAL	{ enabled }
        ::= { wfIpBgp4AnnounceEntry 2 }

    wfIpBgp4AnnounceIndex OBJECT-TYPE
        SYNTAX	INTEGER
        ACCESS	read-only
        STATUS	mandatory
        DESCRIPTION
                "Rule index number"
        ::= { wfIpBgp4AnnounceEntry 3 }

    wfIpBgp4AnnounceName OBJECT-TYPE
        SYNTAX	DisplayString
        ACCESS	read-write
        STATUS	mandatory
        DESCRIPTION
                "Rule name - user specified name for this rule"
        ::= { wfIpBgp4AnnounceEntry 4 }

    wfIpBgp4AnnounceNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpBgp4AnnounceEntry 5 }

    wfIpBgp4AnnounceAction OBJECT-TYPE
        SYNTAX	INTEGER {
    		    announce(2),
    		    ignore(3)
    		}
        ACCESS	read-write
        STATUS	mandatory
        DESCRIPTION
                "action. 'announce' means that the route should be
                advertised.  'ignore' means don't advertise the route."
        DEFVAL	{ ignore }
        ::= { wfIpBgp4AnnounceEntry 6 }

    wfIpBgp4AnnouncePrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpBgp4AnnounceEntry 7 }

    wfIpBgp4AnnounceRouteSource OBJECT-TYPE
        SYNTAX	INTEGER
        ACCESS	read-write
        STATUS	mandatory
        DESCRIPTION
                "route source. This parameter can contain one or more
                route source identifiers.  If the route source is in this
                bit map, then a route from that source that meets the other
                criteria of this filter will match the filter.

                bit 0                                bit 31
                +---------------------------------------+
                |                                       |
                +---------------------------------------+

                bit31  DIRECT
                bit30  STATIC
                bit29  RIP
                bit28  OSPF
                bit27  EGP
                bit26  BGP
                "
        DEFVAL	{ 63 }
        ::= { wfIpBgp4AnnounceEntry 8 }

    wfIpBgp4AnnounceExtRouteSource OBJECT-TYPE
        SYNTAX	INTEGER
        ACCESS	read-write
        STATUS	mandatory
        DESCRIPTION
                "external route source. This parameter can contain one
                or more external route source identifiers.  If the external
                route source is in this bit map, then a route from that
                external source that meets the other criteria of this
                filter will match the filter.

                bit 0                                bit 31
                +---------------------------------------+
                |                                       |
                +---------------------------------------+

                bit31  DIRECT
                bit30  STATIC
                bit29  RIP
                bit28  OSPF
                bit27  EGP
                bit26  BGP
                "
        DEFVAL	{ 63 }
        ::= { wfIpBgp4AnnounceEntry 9 }

    wfIpBgp4AnnounceAdvertise OBJECT-TYPE
        SYNTAX	OCTET STRING
        ACCESS	read-write
        STATUS	mandatory
        DESCRIPTION
                "network advertisement list. this octet string should
                only be non-null if the action is 'announce' and if it is
                desired to advertise networks that differ from the actual
                network in the routing table.  For instance, if a number of
                networks in a certain range are in the table, an aggregate
                could be advertised instead of the individual networks.

                If non-null, The octet string contains one or more 2-tuples
                of this form:

                 first 4 octets: network number
                 next 4 octets: network mask

                Upon receiving a route that matches this filter, all networks
                in this list will be advertised.  If the list is null, the
                actual network is advertised.

                An encoding of 255.255.255.255/255.255.255.255 means 'match
                the actual network.'  This allows advertisement of an aggregate
                or default along with the actual network."
        ::= { wfIpBgp4AnnounceEntry 10 }

    wfIpBgp4AnnounceRipGateway OBJECT-TYPE
        SYNTAX	OCTET STRING
        ACCESS	read-write
        STATUS	mandatory
        DESCRIPTION
                "from RIP' gateway list. Only applicable for RIP sourced
                routes and if RIP is included as a route source.  This octet
                string contains the addresses of one or more routers that could
                send RIP updates to this router.  If a router address is
                included in this list, this filter applies to RIP
                advertisements from that router.

                If non-null, The octet string contains one or more 4-octet
                IP addresses.  If null, this filter applies to RIP updates
                from any router."
        ::= { wfIpBgp4AnnounceEntry 11 }

    wfIpBgp4AnnounceRipInterface OBJECT-TYPE
        SYNTAX	OCTET STRING
        ACCESS	read-write
        STATUS	mandatory
        DESCRIPTION
                "from RIP' interface list. Only applicable for RIP
                sourced routes and if RIP is included as a route source.
                This octet string contains the addresses of one or more
                interfaces on this router.  If an interface address is
                included in this list, this filter applies to RIP
                advertisements received on that interface.

                If non-null, The octet string contains one or more 4-octet
                IP addresses.  If null, this filter applies to RIP updates
                received on any interface."
        ::= { wfIpBgp4AnnounceEntry 12 }

    wfIpBgp4AnnounceOspfRouterId OBJECT-TYPE
        SYNTAX	OCTET STRING
        ACCESS	read-write
        STATUS	mandatory
        DESCRIPTION
                "from OSPF' Router ID list. Only applicable for OSPF sourced
                routes and if OSPF is included as a route source.  This octet
                string contains the router IDs of one or more OSPF routers.
                If a router ID is included in this list, this filter applies
                to OSPF advertisements authored by that router.

                If non-null, The octet string contains one or more 4-octet
                IP addresses.  If null, this filter applies to OSPF updates
                from any router."
        ::= { wfIpBgp4AnnounceEntry 13 }

    wfIpBgp4AnnounceOspfType OBJECT-TYPE
        SYNTAX	INTEGER {
    		    type1(1),
    		    type2(2),
    		    external(3),
    		    internal(4),
    		    any(7)
    		}
        ACCESS	read-write
        STATUS	mandatory
        DESCRIPTION
                "from OSPF' route type. Only applicable for OSPF sourced
                routes and if OSPF is included as a route source.  This
                parameter describes which types of OSPF routes match this
                filter.  'any' means match any route type.  'internal'
                means 'match any non-ASE'.  'external' means 'match any
                ASE'.  'type1' means 'match any external type 1'.  'type2'
                means 'match any external type 2"
        DEFVAL	{ any }
        ::= { wfIpBgp4AnnounceEntry 14 }

    wfIpBgp4AnnounceOspfTag OBJECT-TYPE
        SYNTAX	OCTET STRING
        ACCESS	read-write
        STATUS	mandatory
        DESCRIPTION
                "from OSPF' ASE tag list. Only applicable for OSPF sourced
                ASE routes and if OSPF is included as a route source.  This
                octet string contains tag values that could be present in an
                OSPF ASE advertisement.  If a tag value is included in this
                list, this filter applies to OSPF ASE advertisements that
                contain this tag value.

                If non-null, The octet string contains one or more 4-octet
                tag values.  If null, this filter applies to OSPF ASEs with
                any tag value."
        ::= { wfIpBgp4AnnounceEntry 15 }

    wfIpBgp4AnnounceEgpPeer OBJECT-TYPE
        SYNTAX	OCTET STRING
        ACCESS	read-write
        STATUS	mandatory
        DESCRIPTION
                "from EGP' Peer list. Only applicable for EGP sourced
                routes and if EGP is included as a route source.  This octet
                string contains the IP address of one or more EGP peers.
                If an EGP peer is included in this list, this filter applies
                to EGP advertisements authored by that router.

                If non-null, The octet string contains one or more 4-octet
                IP addresses.  If null, this filter applies to EGP
                advertisements from any router."
        ::= { wfIpBgp4AnnounceEntry 16 }

    wfIpBgp4AnnounceEgpPeerAs OBJECT-TYPE
        SYNTAX	OCTET STRING
        ACCESS	read-write
        STATUS	mandatory
        DESCRIPTION
                "from EGP' Peer AS list. Only applicable for EGP sourced
                routes and if EGP is included as a route source.  This octet
                string contains Autonomous System Numbers.  If an AS number
                is included in this list, this filter applies to EGP
                advertisements received from EBP peers in that AS.

                If non-null, The octet string contains one or more 2-octet
                AS numbers.  If null, this filter applies to EGP advertisements
                from peers in any AS."
        ::= { wfIpBgp4AnnounceEntry 17 }

    wfIpBgp4AnnounceEgpGateway OBJECT-TYPE
        SYNTAX	OCTET STRING
        ACCESS	read-write
        STATUS	mandatory
        DESCRIPTION
                "from EGP' Gateway list. Only applicable for EGP sourced
                routes and if EGP is included as a route source.  This octet
                string contains the IP address of one or more EGP gateways.
                If an EGP gateway is included in this list, this filter applies
                to EGP advertisements that use this gateway as the next hop.

                If non-null, The octet string contains one or more 4-octet
                IP addresses.  If null, this filter applies to EGP
                advertisements with any gateway address."
        ::= { wfIpBgp4AnnounceEntry 18 }

    wfIpBgp4AnnounceBgpPeer OBJECT-TYPE
        SYNTAX	OCTET STRING
        ACCESS	read-write
        STATUS	mandatory
        DESCRIPTION
                "from BGP' Peer list. Only applicable for BGP sourced
                routes and if BGP is included as a route source.  This octet
                string contains the IP address of one or more BGP peers.
                If a BGP peer is included in this list, this filter applies
                to BGP advertisements authored by that router.

                If non-null, The octet string contains one or more 4-octet
                IP addresses.  If null, this filter applies to BGP
                advertisements from any router."
        ::= { wfIpBgp4AnnounceEntry 19 }

    wfIpBgp4AnnounceBgpPeerAs OBJECT-TYPE
        SYNTAX	OCTET STRING
        ACCESS	read-write
        STATUS	mandatory
        DESCRIPTION
                "from BGP' AS list. Only applicable for BGP sourced
                routes and if BGP is included as a route source.  This octet
                string contains Autonomous System Numbers.  If an AS number
                is included in this list, this filter applies to BGP
                advertisements received from BGP peers in that AS.

                If non-null, The octet string contains one or more 2-octet
                AS numbers.  If null, this filter applies to BGP advertisements
                from peers in any AS."
        ::= { wfIpBgp4AnnounceEntry 20 }

    wfIpBgp4AnnounceBgpNextHop OBJECT-TYPE
        SYNTAX	OCTET STRING
        ACCESS	read-write
        STATUS	mandatory
        DESCRIPTION
                "from BGP' NextHop list. Only applicable for BGP sourced
                routes and if BGP is included as a route source.  This octet
                string contains IP addresses.  If an IP address
                is included in this list, this filter applies to BGP
                advertisements whose NEXT_HOP attribute matches this
                IP address.

                If non-null, The octet string contains one or more 4-octet
                IP addresses.  If null, this filter applies to BGP
                advertisements with any NEXT_HOP attribute."
        ::= { wfIpBgp4AnnounceEntry 21 }

    wfIpBgp4AnnouncePeerAs OBJECT-TYPE
        SYNTAX	OCTET STRING
        ACCESS	read-write
        STATUS	mandatory
        DESCRIPTION
                "BGP-4 Outbound Peer AS list. This octet string
                contains Autonomous System Numbers.  If an AS number
                is included in this list, this filter applies to BGP
                advertisements being sent to BGP peers in that AS.

                If non-null, The octet string contains one or more 2-octet
                AS numbers.  If null, this filter applies to BGP advertisements
                going to peers in any AS."
        ::= { wfIpBgp4AnnounceEntry 22 }

    wfIpBgp4AnnouncePeer OBJECT-TYPE
        SYNTAX	OCTET STRING
        ACCESS	read-write
        STATUS	mandatory
        DESCRIPTION
                "BGP-4 Outbound Peer list. This octet string contains the
                IP address of one or more BGP peers.  If a BGP peer is
                included in this list, this filter applies to BGP
                advertisements being sent to that peer.

                If non-null, The octet string contains one or more 4-octet
                IP addresses.  If null, this filter applies to BGP
                advertisements being sent to any peer."
        ::= { wfIpBgp4AnnounceEntry 23 }

    wfIpBgp4AnnounceUseMultiExitDisc OBJECT-TYPE
        SYNTAX	INTEGER {
    		    none(1),
    		    specified(2),
    		    originating(3)
    		}
        ACCESS	read-write
        STATUS	mandatory
        DESCRIPTION
                "Multi-Exit Discriminator Selector. This parameter
                indicates whether or not a MULTI_EXIT_DISC will be
                advertised for a network matching this filter and, if
                advertised, what value to use.  'none' indicates that no
                value will be advertised.  'specified' indicates that
                the value in wfIpBgp4AnnounceMultiExitDisc will be used.
                'originating' indicates that the metric from the
                originating protocol will be used.  Only valid if
                'action' is 'announce'."
        DEFVAL	{ none }
        ::= { wfIpBgp4AnnounceEntry 24 }

    wfIpBgp4AnnounceMultiExitDisc OBJECT-TYPE
        SYNTAX	INTEGER(0..65535)
        ACCESS	read-write
        STATUS	mandatory
        DESCRIPTION
                "Specific Multi-Exit Discriminator. If
                wfIpBgp4AnnounceUseMultiExitDisc is set to 'specified',
                this is the value that will be used for the
                MULTI_EXIT_DISC.  Only valid if 'action' is 'announce'."
        ::= { wfIpBgp4AnnounceEntry 25 }

    wfIpBgp4AnnounceOrigin OBJECT-TYPE
        SYNTAX	INTEGER {
    		    igp(1),
    		    egp(2),
    		    incomplete(3),
		    none(4)	
    		}
        ACCESS	read-write
        STATUS	mandatory
        DESCRIPTION
                "ORIGIN attribute override. If non-null, the ORIGIN
                attribute of a route matching this filter will be replaced
                with the indicated value.  Only valid if 'action' is
                'announce'."
	 DEFVAL	{ none }
        ::= { wfIpBgp4AnnounceEntry 26 }

    wfIpBgp4AnnounceAsPath OBJECT-TYPE
        SYNTAX	OCTET STRING
        ACCESS	read-write
        STATUS	mandatory
        DESCRIPTION
                "AS-path override. If non-null, the AS_PATH attribute
                of a route matching this filter will be replaced with
                the indicated AS path.  A BGP-4 AS_PATH is composed of AS
                path segments.  Each AS path segment is represented by a
                triple: <path segment type, path segment length, path
                segment value>.

                The path segment type is a 1-octet long field with the
                following values defined:

                1: AS_SET: an unordered set of ASes a route in the UPDATE
                   message has traversed.

                2: AS_SEQUENCE: an ordered set of ASes a route in the
                   UPDATE message has traversed.

                The path segment length is a 1-octet long field containing
                the number of ASes in the path segment value field.

                The path segment value field contains one or more AS numbers,
                each encoded as a 2-octet long field.

                Only valid if 'action' is 'announce'."
        ::= { wfIpBgp4AnnounceEntry 27 }

    wfIpBgp4AnnounceLocalPrefOverride OBJECT-TYPE
        SYNTAX	INTEGER {
    		    false(1),
    		    true(2)
    		}
        ACCESS	read-write
        STATUS	mandatory
        DESCRIPTION
                "local pref override. Only valid when advertise
                to an IBGP peer.  If this is false, the route
                weight value will be used to calculate the LOCAL_PREF
                path attribute.  If this is true, the value in
                wfIpBgp4AnnounceLocalPref will be used instead."
        DEFVAL	{ false }
        ::= { wfIpBgp4AnnounceEntry 28 }

    wfIpBgp4AnnounceLocalPref OBJECT-TYPE
        SYNTAX	INTEGER
        ACCESS	read-write
        STATUS	mandatory
        DESCRIPTION
                "local pref override value. Only valid when advertise
                to an IBGP peer. and if wfIpBgp4AnnounceLocalPrefOverride
                is set to IP_BGP4_ANNOUNCE_LOCAL_PREF_OVERRIDE_TRUE.
                If this case, this value is used as the LOCAL_PREF path
                attribute."
        ::= { wfIpBgp4AnnounceEntry 29 }

    wfIpBgp4AnnounceNextHop OBJECT-TYPE
        SYNTAX	IpAddress
        ACCESS	read-write
        STATUS	mandatory
        DESCRIPTION
                "Announce Next Hop. If action is ANNOUNCE and this
                instance is non-zero, then overwrite Next Hop with
                specified value."
        ::= { wfIpBgp4AnnounceEntry 30 }

    wfIpBgp4AnnounceAtomic OBJECT-TYPE
        SYNTAX	INTEGER {
    		    default(1),
    		    force(2),
    		    ignore(3)
    		}
        ACCESS	read-write
        STATUS	mandatory
        DESCRIPTION
                "Announce Atomic aggregation"
        DEFVAL	{ default }
        ::= { wfIpBgp4AnnounceEntry 31 }

    wfIpBgp4AnnounceAsPatternMatch OBJECT-TYPE
        SYNTAX	DisplayString
        ACCESS	read-write
        STATUS	mandatory
        DESCRIPTION
                "BGP AS_PATH Pattern Match string. This filter applies to BGP
                AS_PATH attribute and only routes which as_path matches
                the pattern string will be announced. A pattern string can be
                any regular expression; this parameter is ignored if the string
                is malformed or not set."
        ::= { wfIpBgp4AnnounceEntry 32 }

    wfIpBgp4AnnounceCommunity OBJECT-TYPE
        SYNTAX  OCTET STRING
        ACCESS  read-write
        STATUS  mandatory
        DESCRIPTION
                "BGP Community list. This identifies which
                 communities will be associated with this rule.
                 If non-null, the octet string contains one or
                 more 4-octet BGP Community numbers."
        ::= { wfIpBgp4AnnounceEntry 33 }
 
    wfIpBgp4AnnounceCommunityAction OBJECT-TYPE
        SYNTAX  INTEGER {
			as-is(1),
			remove(2),
			append(3),
			replace(4)
			}
        ACCESS  read-write
        STATUS  mandatory
        DESCRIPTION
		"Action 'as-is' means that existing BGP Community
		attribute is unchanged. 'remove' - all BGP
		Communities are removed from an update.
		'append' - existing BGP Communities are appended with
		the list of communities defined in wfIpBgp4AnnounceCommunity.
		'replace' - existing BGP Communities are are replaced
		with those defined in wfIpBgp4AnnounceCommunity."
        DEFVAL  { as-is }
        ::= { wfIpBgp4AnnounceEntry 34 }
 
    wfIpBgp4AnnounceCommunityMatch OBJECT-TYPE
        SYNTAX  OCTET STRING
        ACCESS  read-write
        STATUS  mandatory
        DESCRIPTION
                "BGP Community list. This list identifies which
		attributes will match this rule. The octet string is
		a list of communities. Each community is 4 bytes long.
		If the 2 MS bytes are 0, the match is performed on
		the lower 16 bits. Only applicable to BGP-learnt routes.
 
                 A null string means 'match any attribute'."
        ::= { wfIpBgp4AnnounceEntry 35 }

    wfIpBgp4AnnounceAsPrepend OBJECT-TYPE
        SYNTAX  OCTET STRING
        ACCESS  read-write
        STATUS  mandatory
        DESCRIPTION
		"AS numbers list.This octet string contains AS numbers to
                 be added as a SEQUENCE to AS Path."
        ::= { wfIpBgp4AnnounceEntry 36 }


 
    wfIpIgmpGroupPolicyTable OBJECT-TYPE
        SYNTAX	SEQUENCE OF WfIpIgmpGroupPolicyEntry
        ACCESS	not-accessible
        STATUS	mandatory
        DESCRIPTION
                "The Table of IGMP Group Policy Rules"
        ::= { wfIpPolicyGroup 11 }

    wfIpIgmpGroupPolicyEntry OBJECT-TYPE
        SYNTAX	WfIpIgmpGroupPolicyEntry
        ACCESS	not-accessible
        STATUS	mandatory
        DESCRIPTION
                "An entry in the IGMP Group Policy Table."
        INDEX	{ wfIpIgmpGroupPolicyIndex }
        ::= { wfIpIgmpGroupPolicyTable 1 }

    WfIpIgmpGroupPolicyEntry ::= SEQUENCE {
    	    wfIpIgmpGroupPolicyDelete
    		INTEGER,
    	    wfIpIgmpGroupPolicyDisable
    		INTEGER,
    	    wfIpIgmpGroupPolicyIndex
    		INTEGER,
    	    wfIpIgmpGroupPolicyName
    		DisplayString,
    	    wfIpIgmpGroupPolicySources
    		OCTET STRING,
    	    wfIpIgmpGroupPolicyAction
    		INTEGER,
    	    wfIpIgmpGroupPolicyPreference
    		INTEGER,
    	    wfIpIgmpGroupPolicyPrecedence
    		INTEGER,
    	    wfIpIgmpGroupPolicyInject
    		OCTET STRING,
    	    wfIpIgmpGroupPolicyGroups
    		OCTET STRING,
    	    wfIpIgmpGroupPolicyCircuits
    		OCTET STRING,
    	    wfIpIgmpGroupPolicySenders
    		OCTET STRING
        }

    wfIpIgmpGroupPolicyDelete OBJECT-TYPE
        SYNTAX	INTEGER {
    		    create(1),
    		    delete(2)
    		}
        ACCESS	read-write
        STATUS	mandatory
        DESCRIPTION
                "Create/Delete parameter."
        DEFVAL	{ create }
        ::= { wfIpIgmpGroupPolicyEntry 1 }

    wfIpIgmpGroupPolicyDisable OBJECT-TYPE
        SYNTAX	INTEGER {
    		    enabled(1),
    		    disabled(2)
    		}
        ACCESS	read-write
        STATUS	mandatory
        DESCRIPTION
                "Enable/Disable parameter."
        DEFVAL	{ enabled }
        ::= { wfIpIgmpGroupPolicyEntry 2 }

    wfIpIgmpGroupPolicyIndex OBJECT-TYPE
        SYNTAX	INTEGER
        ACCESS	read-only
        STATUS	mandatory
        DESCRIPTION
                "Rule index number"
        ::= { wfIpIgmpGroupPolicyEntry 3 }

    wfIpIgmpGroupPolicyName OBJECT-TYPE
        SYNTAX	DisplayString
        ACCESS	read-write
        STATUS	mandatory
        DESCRIPTION
                "Rule name - user specified name for this rule"
        ::= { wfIpIgmpGroupPolicyEntry 4 }

    wfIpIgmpGroupPolicySources OBJECT-TYPE
        SYNTAX	OCTET STRING
        ACCESS	read-write
        STATUS	mandatory
        DESCRIPTION
                "Source identification list. This identifies which
                sources will match this rule.  If non-null, The octet
                string contains one or more 3-tuples of this form:

                 first octet:  exact (1) or range (2)
                 next 4 octets: source address
                 next 4 octets: source mask

                An entry with an 'exact' tag means to only match the
                specific source (number & mask).  An
                entry with a 'range' tag means to match any source
                that falls in the range indicated by the source
                and mask.

                A null string also means 'match any source'."
        ::= { wfIpIgmpGroupPolicyEntry 5 }

    wfIpIgmpGroupPolicyAction OBJECT-TYPE
        SYNTAX	INTEGER {
    		    accept(1),
    		    ignore(3)
    		}
        ACCESS	read-write
        STATUS	mandatory
        DESCRIPTION
                "action. 'accept' means that the group join should be
                accepted.  'ignore' means to ignore the group join"
        DEFVAL	{ ignore }
        ::= { wfIpIgmpGroupPolicyEntry 6 }

    wfIpIgmpGroupPolicyPreference OBJECT-TYPE
        SYNTAX	INTEGER(0..16)
        ACCESS	read-only
        STATUS	mandatory
        DESCRIPTION
                "not used. this is here only because of a common
		 internal data structure"
        ::= { wfIpIgmpGroupPolicyEntry 7 }

    wfIpIgmpGroupPolicyPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins).

		Note that the policy match is not 'most specific'
		so the precedence has to be used to select from
		multiple matches."
        ::= { wfIpIgmpGroupPolicyEntry 8 }

    wfIpIgmpGroupPolicyInject OBJECT-TYPE
        SYNTAX	OCTET STRING
        ACCESS	read-only
        STATUS	mandatory
        DESCRIPTION
                "not used. this is here only because of a common
		 internal data structure"
        ::= { wfIpIgmpGroupPolicyEntry 9 }

    wfIpIgmpGroupPolicyGroups OBJECT-TYPE
        SYNTAX	OCTET STRING
        ACCESS	read-write
        STATUS	mandatory
        DESCRIPTION
                "Group list. This identifies which
                groups will match this rule.  If non-null, The octet
                string contains one or more 2-tuples of this form:

                 next 4 octets: group number
                 next 4 octets: group mask

                A null string also means 'match any group'."
        ::= { wfIpIgmpGroupPolicyEntry 10 }

    wfIpIgmpGroupPolicyCircuits OBJECT-TYPE
        SYNTAX	OCTET STRING
        ACCESS	read-write
        STATUS	mandatory
        DESCRIPTION
                "Circuit identification list. This identifies which
                circuits will match this rule.  If non-null, The octet
                string contains one or more 2-octet, each representing
                a circuit.

                A null string also means 'match any circuit'."
        ::= { wfIpIgmpGroupPolicyEntry 11 }

    wfIpIgmpGroupPolicySenders OBJECT-TYPE
        SYNTAX	OCTET STRING
        ACCESS	read-write
        STATUS	mandatory
        DESCRIPTION
                "Sender identification list. This identifies which
                senders will match this rule.  If non-null, The octet
                string contains one or more 2-tuples of this form:

                 first 4 octets: sender address
                 next 4 octets:  sender mask

                A null string also means 'match any sender'."
        ::= { wfIpIgmpGroupPolicyEntry 12 }


    wfMTMStaticFwdTable OBJECT-TYPE
        SYNTAX	SEQUENCE OF WfMTMStaticFwdEntry
        ACCESS	not-accessible
        STATUS	obsolete
        DESCRIPTION
                "The Table of static forwarding entries"
        ::= { wfIpPolicyGroup 12 }

    wfMTMStaticFwdEntry OBJECT-TYPE
        SYNTAX	WfMTMStaticFwdEntry
        ACCESS	not-accessible
        STATUS	obsolete
        DESCRIPTION
                "An entry in the static forwarding Table"
        INDEX	{ wfMTMStaticFwdIndex }
        ::= { wfMTMStaticFwdTable 1 }

    WfMTMStaticFwdEntry ::= SEQUENCE {
    	    wfMTMStaticFwdDelete
    		INTEGER,
    	    wfMTMStaticFwdDisable
    		INTEGER,
    	    wfMTMStaticFwdIndex
    		INTEGER,
    	    wfMTMStaticFwdName
    		DisplayString,
    	    wfMTMStaticFwdGroups
    		OCTET STRING,
    	    wfMTMStaticFwdAction
    		INTEGER,
    	    wfMTMStaticFwdPreference
    		INTEGER,
    	    wfMTMStaticFwdPrecedence
    		INTEGER,
    	    wfMTMStaticFwdInject
    		OCTET STRING,
    	    wfMTMStaticFwdSources
    		OCTET STRING,
    	    wfMTMStaticFwdInCircuits
    		OCTET STRING,
    	    wfMTMStaticFwdOutCircuits
    		OCTET STRING,
            wfMTMStaticFwdMode
                INTEGER
               
        }

    wfMTMStaticFwdDelete OBJECT-TYPE
        SYNTAX	INTEGER {
    		    create(1),
    		    delete(2)
    		}
        ACCESS	read-write
        STATUS	obsolete
        DESCRIPTION
                "Create/Delete parameter."
        DEFVAL	{ create }
        ::= { wfMTMStaticFwdEntry 1 }

    wfMTMStaticFwdDisable OBJECT-TYPE
        SYNTAX	INTEGER {
    		    enabled(1),
    		    disabled(2)
    		}
        ACCESS	read-write
        STATUS	obsolete
        DESCRIPTION
                "Enable/Disable parameter."
        DEFVAL	{ enabled }
        ::= { wfMTMStaticFwdEntry 2 }

    wfMTMStaticFwdIndex OBJECT-TYPE
        SYNTAX	INTEGER
        ACCESS	read-only
        STATUS	obsolete
        DESCRIPTION
                "Rule index number"
        ::= { wfMTMStaticFwdEntry 3 }

    wfMTMStaticFwdName OBJECT-TYPE
        SYNTAX	DisplayString
        ACCESS	read-write
        STATUS	obsolete
        DESCRIPTION
                "Rule name - user specified name for this rule"
        ::= { wfMTMStaticFwdEntry 4 }

    wfMTMStaticFwdGroups OBJECT-TYPE
        SYNTAX	OCTET STRING
        ACCESS	read-write
        STATUS	obsolete
        DESCRIPTION
                "Group list. This identifies which
                groups will match this rule.  If non-null, The octet
                string contains one or more 2-tuples of this form:

                 next 4 octets: group number
                 next 4 octets: group mask

                A null string also means 'match any group'."
        ::= { wfMTMStaticFwdEntry 5 }

    wfMTMStaticFwdAction OBJECT-TYPE
        SYNTAX	INTEGER
        ACCESS	read-only
        STATUS	obsolete
        DESCRIPTION
                "not used. this is here only because of a common
		 internal data structure"
        ::= { wfMTMStaticFwdEntry 6 }

    wfMTMStaticFwdPreference OBJECT-TYPE
        SYNTAX	INTEGER(0..16)
        ACCESS	read-write
        STATUS	obsolete
        DESCRIPTION
                "If not 0, indicates this policy overwrites multicast protocols
                 otherwise it can be overwritten by multicast protocols.

		 If it overwrites protocols, then forwarding decision is made
                 purely according to the policy; if it can be
                 overwritten by protocols, then protocols have to be
                 consulted to make the decision.

                 For example, s policy 'overwritten_by_procotol' can be
                 used in the following situation:

                 Before a multicast protocol comes up on an incoming
                 circuit, forwarding decision is made according to
                 the policy. After the protocol comes up, the
                 protocol will make the decision"
        DEFVAL	{ 1 }
        ::= { wfMTMStaticFwdEntry 7 }

    wfMTMStaticFwdPrecedence OBJECT-TYPE
        SYNTAX	INTEGER
        ACCESS	read-write
        STATUS	obsolete
        DESCRIPTION
                "precedence. This is a metric to be used to compare
                this policy rule to other rules that a given route may
                match.  A rule with a higher precedence value will be
                chosen over one with a smaller value.  In the case of
                a tie, the rule index is used (larger wins).

		Note that the policy match is not most specific
		so the precedence has to be used to select from
		multiple matches."
        ::= { wfMTMStaticFwdEntry 8 }

    wfMTMStaticFwdInject OBJECT-TYPE
        SYNTAX	OCTET STRING
        ACCESS	read-only
        STATUS	obsolete
        DESCRIPTION
                "not used. this is here only because of a common
		 internal data structure"
        ::= { wfMTMStaticFwdEntry 9 }

    wfMTMStaticFwdSources OBJECT-TYPE
        SYNTAX	OCTET STRING
        ACCESS	read-write
        STATUS	obsolete
        DESCRIPTION
                "Source identification list. This identifies which
                sources will match this rule.  If non-null, The octet
                string contains one or more 2-tuples of this form:

                 next 4 octets: source address
                 next 4 octets: source mask

                A null string also means 'match any source'."
        ::= { wfMTMStaticFwdEntry 10 }

    wfMTMStaticFwdInCircuits OBJECT-TYPE
        SYNTAX	OCTET STRING
        ACCESS	read-write
        STATUS	obsolete
        DESCRIPTION
                "Inbound ircuit ist. This is not a selection
                 criteria. If non-null, The octet string contains one
                 or more 2-octet, each representing a circuit on which
                 mulicast packets whose (s, g) matche this rule
                 will be accepted.

                A null string means those packets should not be accepted
                at all"
        ::= { wfMTMStaticFwdEntry 11 }


    wfMTMStaticFwdOutCircuits OBJECT-TYPE
        SYNTAX	OCTET STRING
        ACCESS	read-write
        STATUS	obsolete
        DESCRIPTION
                "Outbound circuit list. This is not a selection
                 criteria. If non-null, The octet string contains one
                 or more 2-tuple, each representing a circuit out of
                 which mulicast packets whose (s, g) matche this rule
                 will be forwarded.

                 Each tuple is in the following format:

                 first 2-octet: circuit number 
                 following 2 octets: ttl threshold

                A null string means those packets should not be
                forwarded at all."

        ::= { wfMTMStaticFwdEntry 12 }

     wfMTMStaticFwdMode OBJECT-TYPE
        SYNTAX	INTEGER {
    		  static (2),
    		  statictodynamic(3),
		  dynamictostatic(4)
		}
        ACCESS	read-write
        STATUS	obsolete
        DESCRIPTION
                  "
                  static   static entries overrides multicast protocol 
                            decisions
                  statictodynamic Accept the multicast packet from a 
                                   specified non-multicast and static 
                                   configured interface and forward it 
                                   on to outbound interfaces running 
                                   multicast protocols  as per multicast 
                                   protocol rules 
                  dynamictostatic accept the multicast packet from an
                                   interface running multicast protocol
                                   and forward it on to static  configured 
                                   non-multicast out bound interfaces  "
        DEFVAL	{ static }
        ::= { wfMTMStaticFwdEntry 13 }

    wfIpMospfAcceptTable OBJECT-TYPE
        SYNTAX	SEQUENCE OF WfIpMospfAcceptEntry
        ACCESS	not-accessible
        STATUS	mandatory
        DESCRIPTION
                "The Table of Rip Accept Policy Rules"
        ::= { wfIpPolicyGroup 13 }

    wfIpMospfAcceptEntry OBJECT-TYPE
        SYNTAX	WfIpMospfAcceptEntry
        ACCESS	not-accessible
        STATUS	mandatory
        DESCRIPTION
                "An entry in the Rip Accept Rule Table"
        INDEX	{ wfIpMospfAcceptIndex }
        ::= { wfIpMospfAcceptTable 1 }

    WfIpMospfAcceptEntry ::= SEQUENCE {
    	    wfIpMospfAcceptDelete
    		INTEGER,
    	    wfIpMospfAcceptDisable
    		INTEGER,
    	    wfIpMospfAcceptIndex
    		INTEGER,
    	    wfIpMospfAcceptName
    		DisplayString,
    	    wfIpMospfAcceptNetworks
    		OCTET STRING,
    	    wfIpMospfAcceptAction
    		INTEGER,
    	    wfIpMospfAcceptPreference
    		INTEGER,
    	    wfIpMospfAcceptPrecedence
    		INTEGER,
    	    wfIpMospfAcceptInject
    		OCTET STRING,
    	    wfIpMospfAcceptGateway
    		OCTET STRING,
    	    wfIpMospfAcceptInterface
    		OCTET STRING,
    	    wfIpMospfAcceptApplyMask
    		IpAddress
        }

    wfIpMospfAcceptDelete OBJECT-TYPE
        SYNTAX	INTEGER {
    		    create(1),
    		    delete(2)
    		}
        ACCESS	read-write
        STATUS	mandatory
        DESCRIPTION
                "Create/Delete parameter."
        DEFVAL	{ create }
        ::= { wfIpMospfAcceptEntry 1 }

    wfIpMospfAcceptDisable OBJECT-TYPE
        SYNTAX	INTEGER {
    		    enabled(1),
    		    disabled(2)
    		}
        ACCESS	read-write
        STATUS	mandatory
        DESCRIPTION
                "Enable/Disable parameter."
        DEFVAL	{ enabled }
        ::= { wfIpMospfAcceptEntry 2 }

    wfIpMospfAcceptIndex OBJECT-TYPE
        SYNTAX	INTEGER
        ACCESS	read-only
        STATUS	mandatory
        DESCRIPTION
                "Rule index number"
        ::= { wfIpMospfAcceptEntry 3 }

    wfIpMospfAcceptName OBJECT-TYPE
        SYNTAX	DisplayString
        ACCESS	read-write
        STATUS	mandatory
        DESCRIPTION
                "Rule name - user specified name for this rule"
        ::= { wfIpMospfAcceptEntry 4 }

    wfIpMospfAcceptNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpMospfAcceptEntry 5 }

    wfIpMospfAcceptAction OBJECT-TYPE
        SYNTAX	INTEGER {
    		    accept(1),
    		    ignore(3)
    		}
        ACCESS	read-write
        STATUS	mandatory
        DESCRIPTION
                "action. 'accept' means that the route should be
                considered for inclusion in the routing table.  'ignore'
                means don't consider the route"
        DEFVAL	{ accept }
        ::= { wfIpMospfAcceptEntry 6 }

    wfIpMospfAcceptPreference OBJECT-TYPE
        SYNTAX	INTEGER(0..16)
        ACCESS	read-write
        STATUS	mandatory
        DESCRIPTION
                "preference. This is a metric to be used to compare
                the route to other routes to the same destination.  A
                value of 16 is 'most preferred'.  This parameter only has
                meaning if the action is 'accept'."
        DEFVAL	{ 1 }
        ::= { wfIpMospfAcceptEntry 7 }

    wfIpMospfAcceptPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpMospfAcceptEntry 8 }

    wfIpMospfAcceptInject OBJECT-TYPE
        SYNTAX	OCTET STRING
        ACCESS	read-only
        STATUS	mandatory
        DESCRIPTION
                "network injection list. this octet string should only be
                non-null if the action is 'accept' and if it is desired to
                insert networks into the routing table that differ from
                the actual advertised network.  For instance, if a number of
                networks in a certain range are learned, an aggregate
                advertisement could be inserted instead of the individual
                networks.

                If non-null, The octet string contains one or more 2-tuples
                of this form:

                 first 4 octets: network number
                 next 4 octets: network mask

                Upon receiving a route that matches this filter, all networks
                in this list will be considered for inclusion in the routing
                table.  If the list is null, the actual received network is
                considered.

                An encoding of 255.255.255.255/255.255.255.255 means 'match the
                actual received network.'  This allows insertion of an
                aggregate or default along with the actual network.

                Currently, this is only used for routes received via BGP."
        ::= { wfIpMospfAcceptEntry 9 }

    wfIpMospfAcceptGateway OBJECT-TYPE
        SYNTAX	OCTET STRING
        ACCESS	read-write
        STATUS	mandatory
        DESCRIPTION
                "RIP gateway list. This octet string contains the addresses
                of one or more routers that could send RIP updates to this
                router.  If a router address is included in this list,
                this filter applies to RIP advertisements from that router.

                If non-null, The octet string contains one or more 4-octet
                IP addresses.  If null, this filter applies to RIP updates
                from any router."
        ::= { wfIpMospfAcceptEntry 10 }

    wfIpMospfAcceptInterface OBJECT-TYPE
        SYNTAX	OCTET STRING
        ACCESS	read-write
        STATUS	mandatory
        DESCRIPTION
                "RIP interface list. This octet string contains the
                addresses of one or more interfaces on this router.  If an
                interface address is included in this list, this filter
                applies to RIP advertisements received on that interface.

                If non-null, The octet string contains one or more 4-octet
                IP addresses.  If null, this filter applies to RIP updates
                received on any interface."
        ::= { wfIpMospfAcceptEntry 11 }

    wfIpMospfAcceptApplyMask OBJECT-TYPE
        SYNTAX	IpAddress
        ACCESS	read-write
        STATUS	mandatory
        DESCRIPTION
                "Injection Mask: If the 'action' is accept and the
                actual received network will be considered, this is an
                optional IP address mask that will be applied to the network
                number from the RIP update.  This is used to override the
                interface's subnet mask in the presence of networks with
                variable length subnet masks."
        ::= { wfIpMospfAcceptEntry 12 }


    wfIpMospfAnnounceTable OBJECT-TYPE
        SYNTAX	SEQUENCE OF WfIpMospfAnnounceEntry
        ACCESS	not-accessible
        STATUS	mandatory
        DESCRIPTION
                "The Table of Mospf Announce Route Policy Rules.
                 The rules in this table are how the mospf learns
                 routes from DVMRP routing pool."
        ::= { wfIpPolicyGroup 14 }

    wfIpMospfAnnounceEntry OBJECT-TYPE
        SYNTAX	WfIpMospfAnnounceEntry
        ACCESS	not-accessible
        STATUS	mandatory
        DESCRIPTION
                "An entry in the MOSPF Announce Rule Table"
        INDEX	{ wfIpMospfAnnounceIndex }
        ::= { wfIpMospfAnnounceTable 1 }

    WfIpMospfAnnounceEntry ::= SEQUENCE {
    	    wfIpMospfAnnounceDelete
    		INTEGER,
    	    wfIpMospfAnnounceDisable
    		INTEGER,
    	    wfIpMospfAnnounceIndex
    		INTEGER,
    	    wfIpMospfAnnounceName
    		DisplayString,
    	    wfIpMospfAnnounceNetworks
    		OCTET STRING,
    	    wfIpMospfAnnounceAction
    		INTEGER,
    	    wfIpMospfAnnouncePrecedence
    		INTEGER,
    	    wfIpMospfAnnounceRouteSource
    		INTEGER,
    	    wfIpMospfAnnounceExtRouteSource
    		INTEGER,
    	    wfIpMospfAnnounceAdvertise
    		OCTET STRING,
    	    wfIpMospfAnnounceRipGateway
    		OCTET STRING,
    	    wfIpMospfAnnounceRipInterface
    		OCTET STRING,
    	    wfIpMospfAnnounceOspfRouterId
    		OCTET STRING,
    	    wfIpMospfAnnounceOspfType
    		INTEGER,
    	    wfIpMospfAnnounceOspfTag
    		OCTET STRING,
    	    wfIpMospfAnnounceEgpPeer
    		OCTET STRING,
    	    wfIpMospfAnnounceEgpPeerAs
    		OCTET STRING,
    	    wfIpMospfAnnounceEgpGateway
    		OCTET STRING,
    	    wfIpMospfAnnounceBgpPeer
    		OCTET STRING,
    	    wfIpMospfAnnounceBgpPeerAs
    		OCTET STRING,
    	    wfIpMospfAnnounceBgpNextHop
    		OCTET STRING
        }

    wfIpMospfAnnounceDelete OBJECT-TYPE
        SYNTAX	INTEGER {
    		    create(1),
    		    delete(2)
    		}
        ACCESS	read-write
        STATUS	mandatory
        DESCRIPTION
                "Create/Delete parameter."
        DEFVAL	{ create }
        ::= { wfIpMospfAnnounceEntry 1 }

    wfIpMospfAnnounceDisable OBJECT-TYPE
        SYNTAX	INTEGER {
    		    enabled(1),
    		    disabled(2)
    		}
        ACCESS	read-write
        STATUS	mandatory
        DESCRIPTION
                "Enable/Disable parameter."
        DEFVAL	{ enabled }
        ::= { wfIpMospfAnnounceEntry 2 }

    wfIpMospfAnnounceIndex OBJECT-TYPE
        SYNTAX	INTEGER
        ACCESS	read-only
        STATUS	mandatory
        DESCRIPTION
                "Rule index number"
        ::= { wfIpMospfAnnounceEntry 3 }

    wfIpMospfAnnounceName OBJECT-TYPE
        SYNTAX	DisplayString
        ACCESS	read-write
        STATUS	mandatory
        DESCRIPTION
                "Rule name - user specified name for this rule"
        ::= { wfIpMospfAnnounceEntry 4 }

    wfIpMospfAnnounceNetworks OBJECT-TYPE
        SYNTAX	OCTET STRING
        ACCESS	read-write
        STATUS	mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpMospfAnnounceEntry 5 }

    wfIpMospfAnnounceAction OBJECT-TYPE
        SYNTAX	INTEGER {
    		    announce(2),
    		    ignore(3)
    		}
        ACCESS	read-write
        STATUS	mandatory
        DESCRIPTION
                "action. 'announce' means that the route should be
                advertised.  'ignore' means don't advertise the route."
        DEFVAL	{ announce }
        ::= { wfIpMospfAnnounceEntry 6 }

    wfIpMospfAnnouncePrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfIpMospfAnnounceEntry 7 }

    wfIpMospfAnnounceRouteSource OBJECT-TYPE
        SYNTAX	INTEGER
        ACCESS	read-only
        STATUS	mandatory
        DESCRIPTION
                "not used. this is here only because of a common
		 internal data structure"
        ::= { wfIpMospfAnnounceEntry 8 }

    wfIpMospfAnnounceExtRouteSource OBJECT-TYPE
        SYNTAX	INTEGER
        ACCESS	read-only
        STATUS	mandatory
        DESCRIPTION
                "not used. this is here only because of a common
		 internal data structure"
        ::= { wfIpMospfAnnounceEntry 9 }

    wfIpMospfAnnounceAdvertise OBJECT-TYPE
        SYNTAX	OCTET STRING
        ACCESS	read-write
        STATUS	mandatory
        DESCRIPTION
                "network advertisement list. this octet string should
                only be non-null if the action is 'announce' and if it is
                desired to advertise networks that differ from the actual
                network in the routing table.  For instance, if a number of
                networks in a certain range are in the table, an aggregate
                could be advertised instead of the individual networks.

                If non-null, The octet string contains one or more 2-tuples
                of this form:

                 first 4 octets: network number
                 next 4 octets: network mask

                Upon receiving a route that matches this filter, all networks
                in this list will be advertised.  If the list is null, the
                actual network is advertised.

                An encoding of 255.255.255.255/255.255.255.255 means 'match
                the actual network.'  This allows advertisement of an aggregate
                or default along with the actual network."
        ::= { wfIpMospfAnnounceEntry 10 }

    wfIpMospfAnnounceRipGateway OBJECT-TYPE
        SYNTAX	OCTET STRING
        ACCESS	read-only
        STATUS	mandatory
        DESCRIPTION
                "not used. this is here only because of a common
		 internal data structure"
        ::= { wfIpMospfAnnounceEntry 11 }

    wfIpMospfAnnounceRipInterface OBJECT-TYPE
        SYNTAX	OCTET STRING
        ACCESS	read-only
        STATUS	mandatory
        DESCRIPTION
                "not used. this is here only because of a common
		 internal data structure"
        ::= { wfIpMospfAnnounceEntry 12 }

    wfIpMospfAnnounceOspfRouterId OBJECT-TYPE
        SYNTAX	OCTET STRING
        ACCESS	read-only
        STATUS	mandatory
        DESCRIPTION
                "not used. this is here only because of a common
		 internal data structure"
        ::= { wfIpMospfAnnounceEntry 13 }

    wfIpMospfAnnounceOspfType OBJECT-TYPE
        SYNTAX	INTEGER {
    		    type1(1),
    		    type2(2),
    		    external(3),
    		    internal(4),
    		    any(7)
    		}
        ACCESS	read-only
        STATUS	mandatory
        DESCRIPTION
                "not used. this is here only because of a common
		 internal data structure"
        DEFVAL	{ any }
        ::= { wfIpMospfAnnounceEntry 14 }

    wfIpMospfAnnounceOspfTag OBJECT-TYPE
        SYNTAX	OCTET STRING
        ACCESS	read-only
        STATUS	mandatory
        DESCRIPTION
                "not used. this is here only because of a common
		 internal data structure"
        ::= { wfIpMospfAnnounceEntry 15 }

    wfIpMospfAnnounceEgpPeer OBJECT-TYPE
        SYNTAX	OCTET STRING
        ACCESS	read-only
        STATUS	mandatory
        DESCRIPTION
                "not used. this is here only because of a common
		 internal data structure"
        ::= { wfIpMospfAnnounceEntry 16 }

    wfIpMospfAnnounceEgpPeerAs OBJECT-TYPE
        SYNTAX	OCTET STRING
        ACCESS	read-only
        STATUS	mandatory
        DESCRIPTION
                "not used. this is here only because of a common
		 internal data structure"
        ::= { wfIpMospfAnnounceEntry 17 }

    wfIpMospfAnnounceEgpGateway OBJECT-TYPE
        SYNTAX	OCTET STRING
        ACCESS	read-only
        STATUS	mandatory
        DESCRIPTION
                "not used. this is here only because of a common
		 internal data structure"
        ::= { wfIpMospfAnnounceEntry 18 }

    wfIpMospfAnnounceBgpPeer OBJECT-TYPE
        SYNTAX	OCTET STRING
        ACCESS	read-only
        STATUS	mandatory
        DESCRIPTION
                "not used. this is here only because of a common
		 internal data structure"
        ::= { wfIpMospfAnnounceEntry 19 }

    wfIpMospfAnnounceBgpPeerAs OBJECT-TYPE
        SYNTAX	OCTET STRING
        ACCESS	read-only
        STATUS	mandatory
        DESCRIPTION
                "not used. this is here only because of a common
		 internal data structure"
        ::= { wfIpMospfAnnounceEntry 20 }

    wfIpMospfAnnounceBgpNextHop OBJECT-TYPE
        SYNTAX	OCTET STRING
        ACCESS	read-only
        STATUS	mandatory
        DESCRIPTION
                "not used. this is here only because of a common
		 internal data structure"
        ::= { wfIpMospfAnnounceEntry 21 }

    wfIpDvmrpAcceptTable OBJECT-TYPE
        SYNTAX  SEQUENCE OF WfIpDvmrpAcceptEntry
        ACCESS  not-accessible
        STATUS  mandatory
        DESCRIPTION
                "The Table of Rip Accept Policy Rules"
        ::= { wfIpPolicyGroup 15 }

    wfIpDvmrpAcceptEntry OBJECT-TYPE
        SYNTAX  WfIpDvmrpAcceptEntry
        ACCESS  not-accessible
        STATUS  mandatory
        DESCRIPTION
                "An entry in the Dvmrp Accept Rule Table"
        INDEX  { wfIpDvmrpAcceptIndex }
        ::= { wfIpDvmrpAcceptTable 1 }

    WfIpDvmrpAcceptEntry ::= SEQUENCE {
          wfIpDvmrpAcceptDelete
              INTEGER,
          wfIpDvmrpAcceptDisable
              INTEGER,
          wfIpDvmrpAcceptIndex
              INTEGER,
          wfIpDvmrpAcceptName
              DisplayString,
          wfIpDvmrpAcceptNetworks
              OCTET STRING,
          wfIpDvmrpAcceptAction
              INTEGER,
          wfIpDvmrpAcceptPreference
              INTEGER,
          wfIpDvmrpAcceptPrecedence
              INTEGER,
          wfIpDvmrpAcceptInject
              OCTET STRING,
          wfIpDvmrpAcceptGateway
              OCTET STRING,
          wfIpDvmrpAcceptInterface
              OCTET STRING,
          wfIpDvmrpAcceptApplyMask
              IpAddress,
          wfIpDvmrpAcceptTunnels
              OCTET STRING,
          wfIpDvmrpAcceptInjectMetric
              INTEGER
        }

    wfIpDvmrpAcceptDelete OBJECT-TYPE
        SYNTAX  INTEGER {
            create(1),
            delete(2)
        }
        ACCESS  read-write
        STATUS  mandatory
        DESCRIPTION
                "Create/Delete parameter."
        DEFVAL  { create }
        ::= { wfIpDvmrpAcceptEntry 1 }

    wfIpDvmrpAcceptDisable OBJECT-TYPE
        SYNTAX  INTEGER {
            enabled(1),
            disabled(2)
        }
        ACCESS  read-write
        STATUS  mandatory
        DESCRIPTION
                "Enable/Disable parameter."
        DEFVAL  { enabled }
        ::= { wfIpDvmrpAcceptEntry 2 }

    wfIpDvmrpAcceptIndex OBJECT-TYPE
        SYNTAX  INTEGER
        ACCESS  read-only
        STATUS  mandatory
        DESCRIPTION
                "Rule index number"
        ::= { wfIpDvmrpAcceptEntry 3 }

    wfIpDvmrpAcceptName OBJECT-TYPE
        SYNTAX  DisplayString
        ACCESS  read-write
        STATUS  mandatory
        DESCRIPTION
                "Rule name - user specified name for this rule"
        ::= { wfIpDvmrpAcceptEntry 4 }

    wfIpDvmrpAcceptNetworks OBJECT-TYPE
        SYNTAX  OCTET STRING
        ACCESS  read-write
        STATUS  mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpDvmrpAcceptEntry 5 }

    wfIpDvmrpAcceptAction OBJECT-TYPE
        SYNTAX  INTEGER {
            accept(1),
            ignore(3)
        }
        ACCESS  read-write
        STATUS  mandatory
        DESCRIPTION
                "action. 'accept' means that the route should be
                considered for inclusion in the routing table.  'ignore'
                means don't consider the route"
        DEFVAL  { accept }
        ::= { wfIpDvmrpAcceptEntry 6 }

    wfIpDvmrpAcceptPreference OBJECT-TYPE
        SYNTAX  INTEGER(0..16)
        ACCESS  read-only
        STATUS  mandatory
        DESCRIPTION
                "not used. This is here only for common internal data 
                structures."
        DEFVAL {10}
        ::= { wfIpDvmrpAcceptEntry 7 }

    wfIpDvmrpAcceptPrecedence OBJECT-TYPE
        SYNTAX  INTEGER
        ACCESS  read-write
        STATUS  mandatory
        DESCRIPTION
                "precedence. This is a metric to be used to compare
                this policy rule to other rules that a given route may
                match.  A rule with a higher precedence value will be
                chosen over one with a smaller value.  In the case of
                a tie, the rule index is used (larger wins)."
        ::= { wfIpDvmrpAcceptEntry 8 }

    wfIpDvmrpAcceptInject OBJECT-TYPE
        SYNTAX  OCTET STRING
        ACCESS  read-write
        STATUS  mandatory
        DESCRIPTION
                "Network injection list. this octet string should only be
                non-null if the action is 'accept' and if it is desired to
                insert networks into the routing table that differ from
                the actual advertised network.  For instance, if a number of
                networks in a certain range are learned, an aggregate
                advertisement could be inserted instead of the individual
                networks.

                If non-null, The octet string contains one 2-tuples of 
                this form:

                first 4 octets: network number
                next 4 octets: network mask

                Upon receiving a route that matches this filter, the network
                in this list will be considered for inclusion in the routing
                table.  If the list is null, the actual received network is
                considered."
        ::= { wfIpDvmrpAcceptEntry 9 }

    wfIpDvmrpAcceptGateway OBJECT-TYPE
        SYNTAX  OCTET STRING
        ACCESS  read-write
        STATUS  mandatory
        DESCRIPTION
                "DVMRP gateway list. This octet string contains the addresses
                of one or more routers that could send DVMRP updates to this
                router.  If a router address is included in this list,
                this filter applies to DVMRP advertisements from that router.

                If non-null, The octet string contains one or more 4-octet
                IP addresses.  If null, this filter applies to DVMRP updates
                from any router."
        ::= { wfIpDvmrpAcceptEntry 10 }

    wfIpDvmrpAcceptInterface OBJECT-TYPE
        SYNTAX  OCTET STRING
        ACCESS  read-write
        STATUS  mandatory
        DESCRIPTION
                  "Dvmrp interface list. This is a list of DVMRP
                  interfaces.  If a interface appears in this list, the filter
                  applies to DVMRP advertisements received on this interface.

                  If non-null, The octet string contains 4-octet IP address.
                  If null, this filter applies to DVMRP updates received on any
                  DVMRP interface. "
        ::= { wfIpDvmrpAcceptEntry 11 }

    wfIpDvmrpAcceptApplyMask OBJECT-TYPE
        SYNTAX  IpAddress
        ACCESS  read-only
        STATUS  mandatory
        DESCRIPTION
                "Not used in this release
                Injection Mask: If the 'action' is accept and the
                actual received network will be considered, this is an
                optional IP address mask that will be applied to the network
                number from the DVMRP update.  This is used to override the
                interface's subnet mask in the presence of networks with
                variable length subnet masks."
        ::= { wfIpDvmrpAcceptEntry 12 }

    wfIpDvmrpAcceptTunnels OBJECT-TYPE
        SYNTAX  OCTET STRING
        ACCESS  read-write
        STATUS  mandatory
        DESCRIPTION
                "Dvmrp tunnel list. This is a list of DVMRP tunnels. If
                an tunnel interface appears in this listless filter
                applies to DVMRP advertisements sent via that tunnel.
                Each tunnel takes 8 octets, the first 4 of which are for
                local IP address, and the last 4 are for remote IP address

                If non-null, The octet string contains one or more 8-octet IP
                addresses. If the first 8-octet contains all f, this filter
                does not applies to any tunnel. If null, this filter applies
                to any DVMRP tunnel. "
        ::= { wfIpDvmrpAcceptEntry 13}

    wfIpDvmrpAcceptInjectMetric OBJECT-TYPE
        SYNTAX  INTEGER (1..31)
        ACCESS  read-write
        STATUS  mandatory
        DESCRIPTION
                "Inject Route Metric. This value represents the cost of the
                 aggregated route which associates with wfIpDvmrpAcceptInject
                 mib injects into DVMRP routing table.
                 The default value is set to 1."

        DEFVAL  { 1 }
        ::= { wfIpDvmrpAcceptEntry 14 }


    wfIpDvmrpAnnounceTable OBJECT-TYPE
        SYNTAX  SEQUENCE OF WfIpDvmrpAnnounceEntry
        ACCESS  not-accessible
        STATUS  mandatory
        DESCRIPTION
                "The Table of Dvmrp Announce Route Policy Rules"
        ::= { wfIpPolicyGroup 16 }

    wfIpDvmrpAnnounceEntry OBJECT-TYPE
        SYNTAX  WfIpDvmrpAnnounceEntry
        ACCESS  not-accessible
        STATUS  mandatory
        DESCRIPTION
                "An entry in the Dvmrp Announce Rule Table"
        INDEX  { wfIpDvmrpAnnounceIndex }
        ::= { wfIpDvmrpAnnounceTable 1 }

    WfIpDvmrpAnnounceEntry ::= SEQUENCE {
          wfIpDvmrpAnnounceDelete
              INTEGER,
          wfIpDvmrpAnnounceDisable
              INTEGER,
          wfIpDvmrpAnnounceIndex
              INTEGER,
          wfIpDvmrpAnnounceName
              DisplayString,
          wfIpDvmrpAnnounceNetworks
              OCTET STRING,
          wfIpDvmrpAnnounceAction
              INTEGER,
          wfIpDvmrpAnnouncePrecedence
              INTEGER,
          wfIpDvmrpAnnounceRouteSource
              INTEGER,
          wfIpDvmrpAnnounceExtRouteSource
              INTEGER,
          wfIpDvmrpAnnounceAdvertise
              OCTET STRING,
          wfIpDvmrpAnnounceRipGateway
              OCTET STRING,
          wfIpDvmrpAnnounceRipInterface
              OCTET STRING,
          wfIpDvmrpAnnounceOspfRouterId
              OCTET STRING,
          wfIpDvmrpAnnounceOspfType
              INTEGER,
          wfIpDvmrpAnnounceOspfTag
              OCTET STRING,
          wfIpDvmrpAnnounceEgpPeer
              OCTET STRING,
          wfIpDvmrpAnnounceEgpPeerAs
              OCTET STRING,
          wfIpDvmrpAnnounceEgpGateway
              OCTET STRING,
          wfIpDvmrpAnnounceBgpPeer
              OCTET STRING,
          wfIpDvmrpAnnounceBgpPeerAs
              OCTET STRING,
          wfIpDvmrpAnnounceBgpNextHop
              OCTET STRING,
          wfIpDvmrpAnnounceCircuits
              OCTET STRING,
          wfIpDvmrpAnnounceTunnels
              OCTET STRING,
          wfIpDvmrpAnnounceMetric
              INTEGER,
          wfIpDvmrpAnnounceInterface
              OCTET STRING
        }

    wfIpDvmrpAnnounceDelete OBJECT-TYPE
        SYNTAX  INTEGER {
            create(1),
            delete(2)
        }
        ACCESS  read-write
        STATUS  mandatory
        DESCRIPTION
                "Create/Delete parameter."
        DEFVAL  { create }
        ::= { wfIpDvmrpAnnounceEntry 1 }

    wfIpDvmrpAnnounceDisable OBJECT-TYPE
        SYNTAX  INTEGER {
            enabled(1),
            disabled(2)
        }
        ACCESS  read-write
        STATUS  mandatory
        DESCRIPTION
                "Enable/Disable parameter."
        DEFVAL  { enabled }
        ::= { wfIpDvmrpAnnounceEntry 2 }

    wfIpDvmrpAnnounceIndex OBJECT-TYPE
        SYNTAX  INTEGER
        ACCESS  read-only
        STATUS  mandatory
        DESCRIPTION
                "Rule index number"
        ::= { wfIpDvmrpAnnounceEntry 3 }

    wfIpDvmrpAnnounceName OBJECT-TYPE
        SYNTAX  DisplayString
        ACCESS  read-write
        STATUS  mandatory
        DESCRIPTION
                "Rule name - user specified name for this rule"
        ::= { wfIpDvmrpAnnounceEntry 4 }

    wfIpDvmrpAnnounceNetworks OBJECT-TYPE
        SYNTAX  OCTET STRING
        ACCESS  read-write
        STATUS  mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpDvmrpAnnounceEntry 5 }

    wfIpDvmrpAnnounceAction OBJECT-TYPE
        SYNTAX  INTEGER {
            announce(2),
            ignore(3)
        }
        ACCESS  read-write
        STATUS  mandatory
        DESCRIPTION
                "action. 'announce' means that the route should be
                advertised.  'ignore' means don't advertise the route."
        DEFVAL  { announce }
        ::= { wfIpDvmrpAnnounceEntry 6 }

    wfIpDvmrpAnnouncePrecedence OBJECT-TYPE
        SYNTAX  INTEGER
        ACCESS  read-write
        STATUS  mandatory
        DESCRIPTION
                "precedence. This is a metric to be used to compare
                this policy rule to other rules that a given route may
                match.  A rule with a higher precedence value will be
                chosen over one with a smaller value.  In the case of
                a tie, the rule index is used (larger wins)."
        ::= { wfIpDvmrpAnnounceEntry 7 }

    wfIpDvmrpAnnounceRouteSource OBJECT-TYPE
        SYNTAX  INTEGER
        ACCESS  read-only
        STATUS  mandatory
        DESCRIPTION
                "not used. this is here only because of a common
     internal data structure"
        ::= { wfIpDvmrpAnnounceEntry 8 }

    wfIpDvmrpAnnounceExtRouteSource OBJECT-TYPE
        SYNTAX  INTEGER
        ACCESS  read-only
        STATUS  mandatory
        DESCRIPTION
                "not used. this is here only because of a common
     internal data structure"
        ::= { wfIpDvmrpAnnounceEntry 9 }

    wfIpDvmrpAnnounceAdvertise OBJECT-TYPE
        SYNTAX  OCTET STRING
        ACCESS  read-write
        STATUS  mandatory
        DESCRIPTION
                "Network advertisement list. this octet string should
                only be non-null if the action is 'announce' and if it is
                desired to advertise networks that differ from the actual
                network in the routing table.  For instance, if a number of
                networks in a certain range are in the table, an aggregate
                could be advertised instead of the individual networks.

                If non-null, The octet string contains one 2-tuples
                of this form:

                first 4 octets: network number
                next 4 octets: network mask

                Upon receiving a route that matches this filter, the network
                in this list will be advertised.  If the list is null, the
                actual network is advertised."

        ::= { wfIpDvmrpAnnounceEntry 10 }

    wfIpDvmrpAnnounceRipGateway OBJECT-TYPE
        SYNTAX  OCTET STRING
        ACCESS  read-only
        STATUS  mandatory
        DESCRIPTION
                "not used. this is here only because of a common
     internal data structure"
        ::= { wfIpDvmrpAnnounceEntry 11 }

    wfIpDvmrpAnnounceRipInterface OBJECT-TYPE
        SYNTAX  OCTET STRING
        ACCESS  read-only
        STATUS  mandatory
        DESCRIPTION
                "Not used. Only here because of common internal data
                structures."
        ::= { wfIpDvmrpAnnounceEntry 12 }

    wfIpDvmrpAnnounceOspfRouterId OBJECT-TYPE
        SYNTAX  OCTET STRING
        ACCESS  read-only
        STATUS  mandatory
        DESCRIPTION
                "not used. this is here only because of a common
     internal data structure"
        ::= { wfIpDvmrpAnnounceEntry 13 }

    wfIpDvmrpAnnounceOspfType OBJECT-TYPE
        SYNTAX  INTEGER {
            type1(1),
            type2(2),
            external(3),
            internal(4),
            any(7)
        }
        ACCESS  read-only
        STATUS  mandatory
        DESCRIPTION
                "not used. this is here only because of a common
     internal data structure"
        ::= { wfIpDvmrpAnnounceEntry 14 }

    wfIpDvmrpAnnounceOspfTag OBJECT-TYPE
        SYNTAX  OCTET STRING
        ACCESS  read-only
        STATUS  mandatory
        DESCRIPTION
                "not used. this is here only because of a common
     internal data structure"
        ::= { wfIpDvmrpAnnounceEntry 15 }

    wfIpDvmrpAnnounceEgpPeer OBJECT-TYPE
        SYNTAX  OCTET STRING
        ACCESS  read-only
        STATUS  mandatory
        DESCRIPTION
                "not used. this is here only because of a common
     internal data structure"
        ::= { wfIpDvmrpAnnounceEntry 16 }

    wfIpDvmrpAnnounceEgpPeerAs OBJECT-TYPE
        SYNTAX  OCTET STRING
        ACCESS  read-only
        STATUS  mandatory
        DESCRIPTION
                "not used. this is here only because of a common
     internal data structure"
        ::= { wfIpDvmrpAnnounceEntry 17 }

    wfIpDvmrpAnnounceEgpGateway OBJECT-TYPE
        SYNTAX  OCTET STRING
        ACCESS  read-only
        STATUS  mandatory
        DESCRIPTION
                "not used. this is here only because of a common
     internal data structure"
        ::= { wfIpDvmrpAnnounceEntry 18 }

    wfIpDvmrpAnnounceBgpPeer OBJECT-TYPE
        SYNTAX  OCTET STRING
        ACCESS  read-only
        STATUS  mandatory
        DESCRIPTION
                "not used. this is here only because of a common
     internal data structure"
        ::= { wfIpDvmrpAnnounceEntry 19 }

    wfIpDvmrpAnnounceBgpPeerAs OBJECT-TYPE
        SYNTAX  OCTET STRING
        ACCESS  read-only
        STATUS  mandatory
        DESCRIPTION
                "not used. this is here only because of a common
     internal data structure"
        ::= { wfIpDvmrpAnnounceEntry 20 }

    wfIpDvmrpAnnounceBgpNextHop OBJECT-TYPE
        SYNTAX  OCTET STRING
        ACCESS  read-only
        STATUS  mandatory
        DESCRIPTION
                "not used. this is here only because of a common
     internal data structure"
        ::= { wfIpDvmrpAnnounceEntry 21 }

    wfIpDvmrpAnnounceCircuits OBJECT-TYPE
        SYNTAX  OCTET STRING
        ACCESS  read-write
        STATUS  obsolete 
        DESCRIPTION
                "Dvmrp circuit list. This is a list of DVMRP
                circuits.  If a circuit appears in this list, the filter
                applies to DVMRP advertisements sent via that circuit.

                If non-null, The octet string contains one or more 2-octet 
                circuit number.  If the first 2-octet contains all f, this 
                filter does not applies to any circuits. If null, this 
                filter applies to any outbound
                DVMRP circuit. "
        ::= { wfIpDvmrpAnnounceEntry 22 }

    wfIpDvmrpAnnounceTunnels OBJECT-TYPE
        SYNTAX  OCTET STRING
        ACCESS  read-write
        STATUS  mandatory
        DESCRIPTION
                "Dvmrp tunnel list. This is a list of DVMRP
                tunnels. If an tunnel interface appears in this list,the filter
                applies to DVMRP advertisements sent via that tunnel.
                Each tunnel takes 8 octets, the first 4 of which are for 
                local IP address, and the last 4 are for remote IP address

                If non-null, The octet string contains one or more 8-octet IP
                addresses. If the first 8-octet contains all f, this filter
                does not applies to any tunnel. If null, this filter applies 
                to any DVMRP tunnel. "
        ::= { wfIpDvmrpAnnounceEntry 23 }

    wfIpDvmrpAnnounceMetric OBJECT-TYPE
        SYNTAX  INTEGER (0..31)
        ACCESS  read-write
        STATUS  mandatory
        DESCRIPTION
                "Route Metric. This value is announced as the metric for the
                routes specified in the network identification list.

                If non-null, then the routes for the specified networks in the
                network identification list are advertised with this metric
                even it differs from the metric in the routing table. If null,
                then the metrics in the routing table are advertised."
        ::= { wfIpDvmrpAnnounceEntry 24 }

    wfIpDvmrpAnnounceInterface OBJECT-TYPE
        SYNTAX  OCTET STRING
        ACCESS  read-write
        STATUS  mandatory
        DESCRIPTION
                "Dvmrp interface list. This is a list of DVMRP
                interfaces.  If a interface appears in this list, the filter
                applies to DVMRP advertisements sent via that interface.

                If non-null, The octet string contains 4-octet IP address.
                If null, this filter applies to any outbound DVMRP interface. "
        ::= { wfIpDvmrpAnnounceEntry 25 }

   wfIpDvmrpInjectRtTable OBJECT-TYPE
        SYNTAX  SEQUENCE OF WfIpDvmrpInjectRtEntry
        ACCESS  not-accessible
        STATUS  mandatory
        DESCRIPTION
                "The Table of Dvmrp Inject Unicast routes Policy Rules"
        ::= { wfIpPolicyGroup 17 }

    wfIpDvmrpInjectRtEntry OBJECT-TYPE
        SYNTAX  WfIpDvmrpInjectRtEntry
        ACCESS  not-accessible
        STATUS  mandatory
        DESCRIPTION
                "An entry in the Dvmrp Inject Route Rule Table"
        INDEX   { wfIpDvmrpInjectRtIndex }
        ::= { wfIpDvmrpInjectRtTable 1 }

    WfIpDvmrpInjectRtEntry ::= SEQUENCE {
            wfIpDvmrpInjectRtDelete
                INTEGER,
            wfIpDvmrpInjectRtDisable
                INTEGER,
            wfIpDvmrpInjectRtIndex
                INTEGER,
            wfIpDvmrpInjectRtName
                DisplayString,
            wfIpDvmrpInjectRtNetworks
                OCTET STRING,
            wfIpDvmrpInjectRtAction
                INTEGER,
            wfIpDvmrpInjectRtPreference
                INTEGER,
            wfIpDvmrpInjectRtPrecedence
                INTEGER,
            wfIpDvmrpInjectRtInject
                OCTET STRING,
            wfIpDvmrpInjectRtInInterface
                OCTET STRING,
            wfIpDvmrpInjectRtType
                INTEGER,
            wfIpDvmrpInjectRtMetric
                INTEGER
        }

    wfIpDvmrpInjectRtDelete OBJECT-TYPE
        SYNTAX  INTEGER {
                    create(1),
                    delete(2)
                }
        ACCESS  read-write
        STATUS  mandatory
        DESCRIPTION
                "Create/Delete parameter."
        DEFVAL  { create }
        ::= { wfIpDvmrpInjectRtEntry 1 }

    wfIpDvmrpInjectRtDisable OBJECT-TYPE
        SYNTAX  INTEGER {
                    enabled(1),
                    disabled(2)
                }
        ACCESS  read-write
        STATUS  mandatory
        DESCRIPTION
                "Enable/Disable parameter."
        DEFVAL  { enabled }
        ::= { wfIpDvmrpInjectRtEntry 2 }

    wfIpDvmrpInjectRtIndex OBJECT-TYPE
        SYNTAX  INTEGER
        ACCESS  read-only
        STATUS  mandatory
        DESCRIPTION
                "Rule index number"
        ::= { wfIpDvmrpInjectRtEntry 3 }

    wfIpDvmrpInjectRtName OBJECT-TYPE
        SYNTAX  DisplayString
        ACCESS  read-write
        STATUS  mandatory
        DESCRIPTION
                "Rule name - user specified name for this rule"
        ::= { wfIpDvmrpInjectRtEntry 4 }

    wfIpDvmrpInjectRtNetworks OBJECT-TYPE
        SYNTAX  OCTET STRING
        ACCESS  read-write
        STATUS  mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                A null string also means 'match any route'."

        ::= { wfIpDvmrpInjectRtEntry 5 }

    wfIpDvmrpInjectRtAction OBJECT-TYPE
        SYNTAX  INTEGER {
                    accept(1),
                    ignore(3)
                }
        ACCESS  read-write
        STATUS  mandatory
        DESCRIPTION
                "action. 'accept' means that the route should be
                imported from RTM to  the DVMRP routing table.  'ignore'
                means don't consider the route"
        DEFVAL  { accept }
        ::= { wfIpDvmrpInjectRtEntry 6 }

    wfIpDvmrpInjectRtPreference OBJECT-TYPE
        SYNTAX  INTEGER(0..16)
        ACCESS  read-write
        STATUS  mandatory
        DESCRIPTION
                "preference. This is a metric to be used to compare
                the preference path between inject route or the existing
                route in DVMRP routing table. If the injecting unicast
                route is prefered, then the value need to be set higher than
                the preference of the existing route.
                The routes learned from DVMRP network always has preference
                set to 1.
                This parameter only has meaning if the action is 'accept'."
        DEFVAL  { 0 }
        ::= { wfIpDvmrpInjectRtEntry 7 }

    wfIpDvmrpInjectRtPrecedence OBJECT-TYPE
        SYNTAX  INTEGER
        ACCESS  read-write
        STATUS  mandatory
        DESCRIPTION
                "precedence. This is a metric to be used to compare
                this policy rule to other rules that a given route may
                match.  A rule with a higher precedence value will be
                chosen over one with a smaller value.  In the case of
                a tie, the rule index is used (larger wins).

                Note that the policy match is not most specific
                so the precedence has to be used to select from
                multiple matches."
        ::= { wfIpDvmrpInjectRtEntry 8 }

    wfIpDvmrpInjectRtInject OBJECT-TYPE
        SYNTAX  OCTET STRING
        ACCESS  read-write
        STATUS  mandatory
        DESCRIPTION
                "network injection list. this octet string should only be
                non-null if the action is 'accept' and if it is desired to
                insert networks into the routing table that differ from
                the actual advertised network.  For instance, if a number of
                networks in a certain range are learned, an aggregate
                advertisement could be inserted instead of the individual
                networks.

                If non-null, The octet string contains one 2-tuples of 
                this form:

                first 4 octets: network number
                next  4 octets: network mask

                Upon receiving a route that matches this filter, the network
                in this list will be considered for inclusion in the routing
                table.  If the list is null, the actual received network is
                considered."
        ::= { wfIpDvmrpInjectRtEntry 9 }

    wfIpDvmrpInjectRtInInterface OBJECT-TYPE
        SYNTAX  OCTET STRING
        ACCESS  read-write
        STATUS  mandatory
        DESCRIPTION
                "Injected unicast routes inbound circuit list.
                This octet string contains one or more 4-octet IP addresses.
                If an interface address is included in this list, the unicast
                routes received on that interface match this rule will be
                accepted.

                If null, this filter applies to unicast routes received on
                any interface."
        ::= { wfIpDvmrpInjectRtEntry 10 }

      wfIpDvmrpInjectRtType OBJECT-TYPE

          SYNTAX  INTEGER {
                      best-route(2),
                      ospf(4),
                      both(6)
                  }
          ACCESS  read-write
          STATUS  mandatory
          DESCRIPTION
                  "Select the injected route type from RTM."
          DEFVAL  { best-route }
          ::= { wfIpDvmrpInjectRtEntry 11 }

     wfIpDvmrpInjectRtMetric OBJECT-TYPE
        SYNTAX  INTEGER (1..31)
        ACCESS  read-write
        STATUS  mandatory
        DESCRIPTION
                "Route Metric. This value represents the cost of the external
                 routes which are OSPF or unicast best route  to be injected
                 into DVMRP routing table. The default value is set to 1."

        DEFVAL  { 1 }
        ::= { wfIpDvmrpInjectRtEntry 12 }


     wfIpIisisAcceptTable OBJECT-TYPE
        SYNTAX  SEQUENCE OF WfIpIisisAcceptEntry
        ACCESS  not-accessible
        STATUS  mandatory
        DESCRIPTION
                "The Table of Integrated IS-IS Accept Route Filter Rules"
        ::= { wfIpPolicyGroup 18}

    wfIpIisisAcceptEntry OBJECT-TYPE
        SYNTAX  WfIpIisisAcceptEntry
        ACCESS  not-accessible
        STATUS  mandatory
        DESCRIPTION
                "An entry in the Integrated IS-IS Accept Route Policy Table"
        INDEX   { wfIpIisisAcceptIndex }
        ::= { wfIpIisisAcceptTable 1 }

    WfIpIisisAcceptEntry ::= SEQUENCE {
            wfIpIisisAcceptDelete
                INTEGER,
            wfIpIisisAcceptDisable
                INTEGER,
            wfIpIisisAcceptIndex
                INTEGER,
            wfIpIisisAcceptName
                DisplayString,
            wfIpIisisAcceptNetworks
                OCTET STRING,
            wfIpIisisAcceptAction
                INTEGER,
            wfIpIisisAcceptPreference
                INTEGER,
            wfIpIisisAcceptPrecedence
                INTEGER,
            wfIpIisisAcceptInject
                OCTET STRING,
            wfIpIisisAcceptType
                INTEGER
        }

    wfIpIisisAcceptDelete OBJECT-TYPE
        SYNTAX  INTEGER {
                    create(1),
                    delete(2)
                }
        ACCESS  read-write
        STATUS  mandatory
        DESCRIPTION
                "Create/Delete parameter."
        DEFVAL  { create }
        ::= { wfIpIisisAcceptEntry 1 }

    wfIpIisisAcceptDisable OBJECT-TYPE
        SYNTAX  INTEGER {
                    enabled(1),
                    disabled(2)
                }
        ACCESS  read-write
        STATUS  mandatory
        DESCRIPTION
                "Enable/Disable parameter."
        DEFVAL  { enabled }
        ::= { wfIpIisisAcceptEntry 2 }

    wfIpIisisAcceptIndex OBJECT-TYPE
        SYNTAX  INTEGER
        ACCESS  read-only
        STATUS  mandatory
        DESCRIPTION
                "Rule index number"
        ::= { wfIpIisisAcceptEntry 3 }

    wfIpIisisAcceptName OBJECT-TYPE
        SYNTAX  DisplayString
        ACCESS  read-write
        STATUS  mandatory
        DESCRIPTION
                "Rule name - user specified name for this rule"
        ::= { wfIpIisisAcceptEntry 4 }

    wfIpIisisAcceptNetworks OBJECT-TYPE
        SYNTAX  OCTET STRING
        ACCESS  read-write
        STATUS  mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                A null string also means 'match any route'."
        ::= { wfIpIisisAcceptEntry 5 }

    wfIpIisisAcceptAction OBJECT-TYPE
        SYNTAX  INTEGER {
                    accept(1),
                    ignore(3)
                }
        ACCESS  read-write
        STATUS  mandatory
        DESCRIPTION
                "action. 'accept' means that the route should be
                considered for inclusion in the routing table.  'ignore'
                means don't consider the route"
        DEFVAL  { accept }
        ::= { wfIpIisisAcceptEntry 6 }


    wfIpIisisAcceptPreference OBJECT-TYPE
        SYNTAX  INTEGER(0..16)
        ACCESS  read-write
        STATUS  mandatory
        DESCRIPTION
                "preference. This is a metric to be used to compare
                the route to other routes to the same destination.  A
                value of 16 is 'most preferred'.  This parameter only has
                meaning if the action is 'accept'."
        DEFVAL  { 1 }
        ::= { wfIpIisisAcceptEntry 7 }


    wfIpIisisAcceptPrecedence OBJECT-TYPE
        SYNTAX  INTEGER
        ACCESS  read-write
        STATUS  mandatory
        DESCRIPTION
                "precedence. This is a metric to be used to compare
                this policy rule to other rules that a given route may
                match.  A rule with a higher precedence value will be
                chosen over one with a smaller value.  In the case of
                a tie, the rule index is used (larger wins)."
        ::= { wfIpIisisAcceptEntry 8 }


    wfIpIisisAcceptInject OBJECT-TYPE
        SYNTAX  OCTET STRING
        ACCESS  read-only
        STATUS  mandatory
        DESCRIPTION
                "network injection list. this octet string should only be
                non-null if the action is 'accept' and if it is desired to
                insert networks into the routing table that differ from
                the actual advertised network.  For instance, if a number of
                networks in a certain range are learned, an aggregate
                advertisement could be inserted instead of the individual
                networks.

                If non-null, The octet string contains one or more 2-tuples
                of this form:

                 first 4 octets: network number
                 next 4 octets: network mask

                Upon receiving a route that matches this filter, all networks
                in this list will be considered for inclusion in the routing
                table.  If the list is null, the actual received network is
                considered.

                An encoding of 255.255.255.255/255.255.255.255 means 'match the
                actual received network.'  This allows insertion of an
                aggregate or default along with the actual network.

                Currently, this is only used for routes received via BGP."
        ::= { wfIpIisisAcceptEntry 9 }


    wfIpIisisAcceptType OBJECT-TYPE
        SYNTAX  INTEGER {
                    internal(1),
                    external(2),
                    any(3)
                }
        ACCESS  read-write
        STATUS  mandatory
        DESCRIPTION
                "Integrated IS-IS external metric type. This
                 parameter describes which types of Integrated IS-IS routes
                 match this filter.
                'any' means 'match either internal or external'. "
        DEFVAL  { any }
        ::= { wfIpIisisAcceptEntry 10 }


    wfIpIisisAnnounceTable OBJECT-TYPE
        SYNTAX  SEQUENCE OF WfIpIisisAnnounceEntry
        ACCESS  not-accessible
        STATUS  mandatory
        DESCRIPTION
                "The Table of Integrated IS-IS Announce Route Policy Rules"
        ::= { wfIpPolicyGroup 19 }

    wfIpIisisAnnounceEntry OBJECT-TYPE
        SYNTAX  WfIpIisisAnnounceEntry
        ACCESS  not-accessible
        STATUS  mandatory
        DESCRIPTION
                "An entry in the  Announce Route Filter Table"
        INDEX   { wfIpIisisAnnounceIndex }
        ::= { wfIpIisisAnnounceTable 1 }

    WfIpIisisAnnounceEntry ::= SEQUENCE {
            wfIpIisisAnnounceDelete
                INTEGER,
            wfIpIisisAnnounceDisable
                INTEGER,
            wfIpIisisAnnounceIndex
                INTEGER,
            wfIpIisisAnnounceName
                DisplayString,
            wfIpIisisAnnounceNetworks
                OCTET STRING,
            wfIpIisisAnnounceAction
                INTEGER,
            wfIpIisisAnnouncePrecedence
                INTEGER,
            wfIpIisisAnnounceRouteSource
                INTEGER,
            wfIpIisisAnnounceExtRouteSource
                INTEGER,
            wfIpIisisAnnounceAdvertise
                OCTET STRING,
            wfIpIisisAnnounceRipGateway
                OCTET STRING,
            wfIpIisisAnnounceRipInterface
                OCTET STRING,
            wfIpIisisAnnounceIisisRouterId
                OCTET STRING,
            wfIpIisisAnnounceIisisType
                INTEGER,
            wfIpIisisAnnounceIisisTag
                OCTET STRING,
            wfIpIisisAnnounceEgpPeer
                OCTET STRING,
            wfIpIisisAnnounceEgpPeerAs
                OCTET STRING,
            wfIpIisisAnnounceEgpGateway
                OCTET STRING,
            wfIpIisisAnnounceBgpPeer
                OCTET STRING,
            wfIpIisisAnnounceBgpPeerAs
                OCTET STRING,
            wfIpIisisAnnounceBgpNextHop
                OCTET STRING,
            wfIpIisisAnnounceType
                INTEGER,
            wfIpIisisAnnounceTag
                INTEGER,
            wfIpIisisAnnounceAutoTag
                INTEGER,
            wfIpIisisAnnounceMetric
                INTEGER
       }


    wfIpIisisAnnounceDelete OBJECT-TYPE
        SYNTAX  INTEGER {
                    create(1),
                    delete(2)
                }
        ACCESS  read-write
        STATUS  mandatory
        DESCRIPTION
                "Create/Delete parameter."
        DEFVAL  { create }
        ::= { wfIpIisisAnnounceEntry 1 }


    wfIpIisisAnnounceDisable OBJECT-TYPE
        SYNTAX  INTEGER {
                    enabled(1),
                    disabled(2)
                }
        ACCESS  read-write
        STATUS  mandatory
        DESCRIPTION
                "Enable/Disable parameter."
        DEFVAL  { enabled }
        ::= { wfIpIisisAnnounceEntry 2 }


    wfIpIisisAnnounceIndex OBJECT-TYPE
        SYNTAX  INTEGER
        ACCESS  read-only
        STATUS  mandatory
        DESCRIPTION
                "Rule index number"
        ::= { wfIpIisisAnnounceEntry 3 }


    wfIpIisisAnnounceName OBJECT-TYPE
        SYNTAX  DisplayString
        ACCESS  read-write
        STATUS  mandatory
        DESCRIPTION
                "Rule name - user specified name for this rule"
        ::= { wfIpIisisAnnounceEntry 4 }


    wfIpIisisAnnounceNetworks OBJECT-TYPE
        SYNTAX  OCTET STRING
        ACCESS  read-write
        STATUS  mandatory
        DESCRIPTION
                "Network identification list. This identifies which
                networks will match this rule.  If non-null, The octet
                string contains one or more 3-tuples of this form:

                 first octet:  exact (1) or range (2)
                 next 4 octets: network number
                 next 4 octets: network mask

                An entry with an 'exact' tag means to only match the
                specific network advertisement (number & mask).  An
                entry with a 'range' tag means to match any network
                number that falls in the range indicated by the number
                and mask.

                An 'exact' encoding of 0.0.0.0/0.0.0.0 means 'match the
                default route.  A 'range' encoding of 0.0.0.0/0.0.0.0 means
                'match any route'.

                 A null string also means 'match any route'."
        ::= { wfIpIisisAnnounceEntry 5 }


    wfIpIisisAnnounceAction OBJECT-TYPE
        SYNTAX  INTEGER {
                    announce(2),
                    ignore(3)
                }
        ACCESS  read-write
        STATUS  mandatory
        DESCRIPTION
                "action. 'announce' means that the route should be
                advertised.  'ignore' means don't advertise the route."
        DEFVAL  { ignore }
        ::= { wfIpIisisAnnounceEntry 6 }


    wfIpIisisAnnouncePrecedence OBJECT-TYPE
        SYNTAX  INTEGER
        ACCESS  read-write
        STATUS  mandatory
        DESCRIPTION
                "precedence. This is a metric to be used to compare
                this policy rule to other rules that a given route may
                match.  A rule with a higher precedence value will be
                chosen over one with a smaller value.  In the case of
                a tie, the rule index is used (larger wins)."
        ::= { wfIpIisisAnnounceEntry 7 }


    wfIpIisisAnnounceRouteSource OBJECT-TYPE
        SYNTAX  INTEGER
        ACCESS  read-write
        STATUS  mandatory
        DESCRIPTION
                "route source. This parameter can contain one or more
                  route source identifiers.  If the route source is in this
                bit map, then a route from that source that meets the other
                criteria of this filter will match the filter. In the first
                phase of Integrated IS-IS only direct and static are being
                considered

                bit 0                                bit 31
                +---------------------------------------+
                |                                       |
                +---------------------------------------+

                bit31  DIRECT
                bit30  STATIC
                bit29  RIP
		bit28  OSPF
                bit27  EGP
                bit26  BGP
                "
        DEFVAL  { 63 }
        ::= { wfIpIisisAnnounceEntry 8 }


    wfIpIisisAnnounceExtRouteSource OBJECT-TYPE
        SYNTAX  INTEGER
        ACCESS  read-only
        STATUS  mandatory
        DESCRIPTION
                " NOT USED for Integrated IS-IS
                external route source. This parameter can contain one
                or more external route source identifiers.  If the external
                route source is in this bit map, then a route from that
                external source that meets the other criteria of this
                filter will match the filter.  Not valid for OSPF announce rules
                ."
        DEFVAL  { 63 }
        ::= { wfIpIisisAnnounceEntry 9 }

    wfIpIisisAnnounceAdvertise OBJECT-TYPE
        SYNTAX  OCTET STRING
        ACCESS  read-write
        STATUS  mandatory
        DESCRIPTION
                "network advertisement list. this octet string should
                only be non-null if the action is 'announce' and if it is
                desired to advertise networks that differ from the actual
                network in the routing table.  For instance, if a number of
                networks in a certain range are in the table, an aggregate
                could be advertised instead of the individual networks.

                If non-null, The octet string contains one or more 2-tuples
                of this form:

                 first 4 octets: network number
                 next 4 octets: network mask

                Upon receiving a route that matches this filter, all networks
                in this list will be advertised.  If the list is null, the
                actual network is advertised.

                An encoding of 255.255.255.255/255.255.255.255 means 'match
                the actual network.'  This allows advertisement of an aggregate
                or default along with the actual network."
        ::= { wfIpIisisAnnounceEntry 10 }


    wfIpIisisAnnounceRipGateway OBJECT-TYPE
        SYNTAX  OCTET STRING
        ACCESS  read-write
        STATUS  mandatory
        DESCRIPTION
                " Not applicable for first phase of Integrated IS_IS
                from RIP' gateway list. Only applicable for RIP sourced
                routes and if RIP is included as a route source.  This octet
                string contains the addresses of one or more routers that could
                send RIP updates to this router.  If a router address is
                included in this list, this filter applies to RIP
                advertisements from that router.

                If non-null, The octet string contains one or more 4-octet
                IP addresses.  If null, this filter applies to RIP updates
                from any router."
        ::= { wfIpIisisAnnounceEntry 11 }

    wfIpIisisAnnounceRipInterface OBJECT-TYPE
        SYNTAX  OCTET STRING
        ACCESS  read-write
        STATUS  mandatory
        DESCRIPTION
                " Not applicable for first phase of Integrated IS_IS
                from RIP' interface list. Only applicable for RIP
                sourced routes and if RIP is included as a route source.
                This octet string contains the addresses of one or more
                interfaces on this router.  If an interface address is
                included in this list, this filter applies to RIP
                advertisements received on that interface.

                If non-null, The octet string contains one or more 4-octet
                IP addresses.  If null, this filter applies to RIP updates
                received on any interface."
        ::= { wfIpIisisAnnounceEntry 12 }

    wfIpIisisAnnounceIisisRouterId OBJECT-TYPE
        SYNTAX  OCTET STRING
        ACCESS  read-write
        STATUS  mandatory
        DESCRIPTION
                " Not applicable for first phase of Integrated IS_IS
                from OSPF' Router ID list. Only applicable for OSPF sourced
                routes and if OSPF is included as a route source.  This octet
                string contains the router IDs of one or more OSPF routers.
                If a router ID is included in this list, this filter applies
                to OSPF advertisements authored by that router.

                If non-null, The octet string contains one or more 4-octet
                IP addresses.  If null, this filter applies to OSPF updates
                from any router."
        ::= { wfIpIisisAnnounceEntry 13 }

    wfIpIisisAnnounceIisisType OBJECT-TYPE
        SYNTAX  INTEGER {
                    type1(1),
                    type2(2),
                    external(3),
                    internal(4),
                    any(7)
                }
        ACCESS  read-write
        STATUS  mandatory
        DESCRIPTION
                " Not applicable for first phase of Integrated IS_IS
                from OSPF' route type. Only applicable for OSPF sourced
                routes and if OSPF is included as a route source.  This
                parameter describes which types of OSPF routes match this
                filter.  'any' means match any route type.  'internal'
                means 'match any non-ASE'.  'external' means 'match any
                ASE'.  'type1' means 'match any external type 1'.  'type2'
                means 'match any external type 2"
        DEFVAL  { any }
        ::= { wfIpIisisAnnounceEntry 14 }

    wfIpIisisAnnounceIisisTag OBJECT-TYPE
        SYNTAX  OCTET STRING
        ACCESS  read-write
        STATUS  mandatory
        DESCRIPTION
                " Not applicable for first phase of Integrated IS_IS
                from OSPF' ASE tag list. Only applicable for OSPF sourced
                ASE routes and if OSPF is included as a route source.  This
                octet string contains tag values that could be present in an
                OSPF ASE advertisement.  If a tag value is included in this
                list, this filter applies to OSPF ASE advertisements that
                contain this tag value.

                If non-null, The octet string contains one or more 4-octet
                tag values.  If null, this filter applies to OSPF ASEs with
                any tag value."
        ::= { wfIpIisisAnnounceEntry 15 }

    wfIpIisisAnnounceEgpPeer OBJECT-TYPE
        SYNTAX  OCTET STRING
        ACCESS  read-write
        STATUS  mandatory
        DESCRIPTION
                " Not applicable for first phase of Integrated IS_IS
                from EGP' Peer list. Only applicable for EGP sourced
                routes and if EGP is included as a route source.  This octet
                string contains the IP address of one or more EGP peers.
                If an EGP peer is included in this list, this filter applies
                to EGP advertisements authored by that router.

                If non-null, The octet string contains one or more 4-octet
                IP addresses.  If null, this filter applies to EGP
                advertisements from any router."
        ::= { wfIpIisisAnnounceEntry 16 }

    wfIpIisisAnnounceEgpPeerAs OBJECT-TYPE
        SYNTAX  OCTET STRING
        ACCESS  read-write
        STATUS  mandatory
        DESCRIPTION
                " Not applicable for first phase of Integrated IS_IS
                from EGP' Peer AS list. Only applicable for EGP sourced
                routes and if EGP is included as a route source.  This octet
                string contains Autonomous System Numbers.  If an AS number
                is included in this list, this filter applies to EGP
                advertisements received from EBP peers in that AS.

                If non-null, The octet string contains one or more 2-octet
                AS numbers.  If null, this filter applies to EGP advertisements
                from peers in any AS."
        ::= { wfIpIisisAnnounceEntry 17 }

    wfIpIisisAnnounceEgpGateway OBJECT-TYPE
        SYNTAX  OCTET STRING
        ACCESS  read-write
        STATUS  mandatory
        DESCRIPTION
                " Not applicable for first phase of Integrated IS_IS
                from EGP' Gateway list. Only applicable for EGP sourced
                routes and if EGP is included as a route source.  This octet
                string contains the IP address of one or more EGP gateways.
                If an EGP gateway is included in this list, this filter applies
                to EGP advertisements that use this gateway as the next hop.

                If non-null, The octet string contains one or more 4-octet
                IP addresses.  If null, this filter applies to EGP
                advertisements with any gateway address."
        ::= { wfIpIisisAnnounceEntry 18 }

    wfIpIisisAnnounceBgpPeer OBJECT-TYPE
        SYNTAX  OCTET STRING
        ACCESS  read-write
        STATUS  mandatory
        DESCRIPTION
                " Not applicable for first phase of Integrated IS_IS
                from BGP' Peer list. Only applicable for BGP sourced
                routes and if BGP is included as a route source.  This octet
                string contains the IP address of one or more BGP peers.
                If a BGP peer is included in this list, this filter applies
                to BGP advertisements authored by that router.

                If non-null, The octet string contains one or more 4-octet
                IP addresses.  If null, this filter applies to BGP
                advertisements from any router."
        ::= { wfIpIisisAnnounceEntry 19 }

    wfIpIisisAnnounceBgpPeerAs OBJECT-TYPE
        SYNTAX  OCTET STRING
        ACCESS  read-write
        STATUS  mandatory
        DESCRIPTION
                " Not applicable for first phase of Integrated IS_IS
                from BGP' AS list. Only applicable for BGP sourced
                routes and if BGP is included as a route source.  This octet
                string contains Autonomous System Numbers.  If an AS number
                is included in this list, this filter applies to BGP
                advertisements received from BGP peers in that AS.
                If non-null, The octet string contains one or more 2-octet
                AS numbers.  If null, this filter applies to BGP advertisements
                from peers in any AS."
        ::= { wfIpIisisAnnounceEntry 20 }

    wfIpIisisAnnounceBgpNextHop OBJECT-TYPE
        SYNTAX  OCTET STRING
        ACCESS  read-write
        STATUS  mandatory
        DESCRIPTION
                " Not applicable for first phase of Integrated IS_IS
                from BGP' NextHop list. Only applicable for BGP sourced
                routes and if BGP is included as a route source.  This octet
                string contains IP addresses.  If an IP address
                is included in this list, this filter applies to BGP
                advertisements whose NEXT_HOP attribute matches this
                IP address.

                If non-null, The octet string contains one or more 4-octet
                IP addresses.  If null, this filter applies to BGP
                advertisements with any NEXT_HOP attribute."
        ::= { wfIpIisisAnnounceEntry 21 }

    wfIpIisisAnnounceType OBJECT-TYPE
        SYNTAX  INTEGER {
                    internal(1),
                    external(2)
                }
        ACCESS  read-write
        STATUS  mandatory
        DESCRIPTION
                "OSPF ASE type. The ASE type to use for routes that
                match this filter.  This is only applicable if the
                action is 'accept'.  A zero value means to use the
                default ASE type for the route source."
        ::= { wfIpIisisAnnounceEntry 22 }

    wfIpIisisAnnounceTag OBJECT-TYPE
         SYNTAX  INTEGER
        ACCESS  read-write
        STATUS  mandatory
        DESCRIPTION
                "Not applicable for Integrated IS-IS
                 OSPF ASE tag. The ASE tag value to use for routes
                that match this filter.  This is only applicable if the
                action is 'accept' and autotag is set to 'disable'."
        ::= { wfIpIisisAnnounceEntry 23 }

    wfIpIisisAnnounceAutoTag OBJECT-TYPE
        SYNTAX  INTEGER {
                    enabled(1),
                    disabled(2),
                    wf(3)
                }
        ACCESS  read-write
        STATUS  mandatory
        DESCRIPTION
                "Not applicable for Integrated IS-IS
                 BGP/OSPF automatic tag generation: Only applicable
                if action is 'announce'.  if set to 'disabled',
                the value in wfIpIisisAnnounceTag will be used for a tag.
                If set to 'enabled', a tag will be generated according
                to the criteria in RFC 1403 (or any RFC that supercedes
                it)."
        DEFVAL  { disabled }
        ::= { wfIpIisisAnnounceEntry 24 }

    wfIpIisisAnnounceMetric OBJECT-TYPE
        SYNTAX  INTEGER
        ACCESS  read-write
        STATUS  mandatory
        DESCRIPTION
                "The optional metric to apply to this route.
                Zero means : use the route's actual cost. Only
                valid for propagate."
        ::= { wfIpIisisAnnounceEntry 25 }

    wfMTMStaticForwardTable OBJECT-TYPE
        SYNTAX	SEQUENCE OF WfMTMStaticForwardEntry
        ACCESS	not-accessible
        STATUS	mandatory
        DESCRIPTION
                "The Table of static forwarding entries"
        ::= { wfIpPolicyGroup 20 }

    wfMTMStaticForwardEntry OBJECT-TYPE
        SYNTAX	WfMTMStaticForwardEntry
        ACCESS	not-accessible
        STATUS	mandatory
        DESCRIPTION
                "An entry in the static forwarding Table"
        INDEX	{ wfMTMStaticForwardIndex }
        ::= { wfMTMStaticForwardTable 1 }

    WfMTMStaticForwardEntry ::= SEQUENCE {
    	    wfMTMStaticForwardDelete
    		INTEGER,
    	    wfMTMStaticForwardDisable
    		INTEGER,
    	    wfMTMStaticForwardIndex
    		INTEGER,
    	    wfMTMStaticForwardName
    		DisplayString,
    	    wfMTMStaticForwardGroups
    		OCTET STRING,
    	    wfMTMStaticForwardAction
    		INTEGER,
    	    wfMTMStaticForwardPreference
    		INTEGER,
    	    wfMTMStaticForwardPrecedence
    		INTEGER,
    	    wfMTMStaticForwardInject
    		OCTET STRING,
    	    wfMTMStaticForwardSources
    		OCTET STRING,
    	    wfMTMStaticForwardInCircuits
    		OCTET STRING,
    	    wfMTMStaticForwardOutCircuits
    		OCTET STRING,
            wfMTMStaticForwardMode
                INTEGER
               
        }

    wfMTMStaticForwardDelete OBJECT-TYPE
        SYNTAX	INTEGER {
    		    create(1),
    		    delete(2)
    		}
        ACCESS	read-write
        STATUS	mandatory
        DESCRIPTION
                "Create/Delete parameter."
        DEFVAL	{ create }
        ::= { wfMTMStaticForwardEntry 1 }

    wfMTMStaticForwardDisable OBJECT-TYPE
        SYNTAX	INTEGER {
    		    enabled(1),
    		    disabled(2)
    		}
        ACCESS	read-write
        STATUS	mandatory
        DESCRIPTION
                "Enable/Disable parameter."
        DEFVAL	{ enabled }
        ::= { wfMTMStaticForwardEntry 2 }

    wfMTMStaticForwardIndex OBJECT-TYPE
        SYNTAX	INTEGER
        ACCESS	read-only
        STATUS	mandatory
        DESCRIPTION
                "Rule index number"
        ::= { wfMTMStaticForwardEntry 3 }

    wfMTMStaticForwardName OBJECT-TYPE
        SYNTAX	DisplayString
        ACCESS	read-write
        STATUS	mandatory
        DESCRIPTION
                "Rule name - user specified name for this rule"
        ::= { wfMTMStaticForwardEntry 4 }

    wfMTMStaticForwardGroups OBJECT-TYPE
        SYNTAX	OCTET STRING
        ACCESS	read-write
        STATUS	mandatory
        DESCRIPTION
                "Group list. This identifies which
                groups will match this rule.  If non-null, The octet
                string contains one or more 2-tuples of this form:
                 First octet : 0x1(exact)  or 0x2 (range)
                 next 4 octets: group number
                 next 4 octets: group mask

                A null string also means 'match any group'."
        ::= { wfMTMStaticForwardEntry 5 }

    wfMTMStaticForwardAction OBJECT-TYPE
        SYNTAX	INTEGER
        ACCESS	read-only
        STATUS	mandatory
        DESCRIPTION
                "not used. this is here only because of a common
		 internal data structure"
        ::= { wfMTMStaticForwardEntry 6 }

    wfMTMStaticForwardPreference OBJECT-TYPE
        SYNTAX	INTEGER(0..16)
        ACCESS	read-write
        STATUS  mandatory	
        DESCRIPTION
                " note: Not used .This is here only for common internal 
                  data structures"
        DEFVAL	{ 1 }
        ::= { wfMTMStaticForwardEntry 7 }

    wfMTMStaticForwardPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins).

		Note that the policy match is not most specific
		so the precedence has to be used to select from
		multiple matches."
        ::= { wfMTMStaticForwardEntry 8 }

    wfMTMStaticForwardInject OBJECT-TYPE
        SYNTAX	OCTET STRING
        ACCESS	read-only
        STATUS	mandatory
        DESCRIPTION
                "not used. this is here only because of a common
		 internal data structure"
        ::= { wfMTMStaticForwardEntry 9 }

    wfMTMStaticForwardSources OBJECT-TYPE
        SYNTAX	OCTET STRING
        ACCESS	read-write
        STATUS	mandatory
        DESCRIPTION
                "Source identification list. This identifies which
                sources will match this rule.  If non-null, The octet
                string contains one or more 2-tuples of this form:

                 next 4 octets: source address
                 next 4 octets: source mask

                A null string also means 'match any source'."
        ::= { wfMTMStaticForwardEntry 10 }

    wfMTMStaticForwardInCircuits OBJECT-TYPE
        SYNTAX	OCTET STRING
        ACCESS	read-write
        STATUS	mandatory
        DESCRIPTION
                "Inbound ircuit ist. This is not a selection
                 criteria. If non-null, The octet string contains one
                 or more 2-octet, each representing a circuit on which
                 mulicast packets whose (s, g) matche this rule
                 will be accepted.

                A null string means those packets should not be accepted
                at all"
        ::= { wfMTMStaticForwardEntry 11 }


    wfMTMStaticForwardOutCircuits OBJECT-TYPE
        SYNTAX	OCTET STRING
        ACCESS	read-write
        STATUS	mandatory
        DESCRIPTION
                "Outbound circuit list. This is not a selection
                 criteria. If non-null, The octet string contains one
                 or more 2-tuple, each representing a circuit out of
                 which mulicast packets whose (s, g) matche this rule
                 will be forwarded.

                 Each tuple is in the following format:

                 first 2-octet: circuit number 
                 following 2 octets: ttl threshold

                A null string means those packets should not be
                forwarded at all."

        ::= { wfMTMStaticForwardEntry 12 }

     wfMTMStaticForwardMode OBJECT-TYPE
        SYNTAX	INTEGER {
    		  static (2),
    		  statictodynamic(3),
		  dynamictostatic(4)
		}
        ACCESS	read-write
        STATUS	mandatory
        DESCRIPTION
                  "
                  static   static entries overrides multicast protocol 
                            decisions
                  statictodynamic Accept the multicast packet from a 
                                   specified non-multicast and static 
                                   configured interface and forward it 
                                   on to outbound interfaces running 
                                   multicast protocols  as per multicast 
                                   protocol rules 
                  dynamictostatic accept the multicast packet from an
                                   interface running multicast protocol
                                   and forward it on to static  configured 
                                   non-multicast out bound interfaces  "
        DEFVAL	{ static }
        ::= { wfMTMStaticForwardEntry 13 }

     END  -- Wellfleet-IPPOLICY-MIB
