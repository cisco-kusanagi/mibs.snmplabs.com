-- 
--  Copyright 1996, Com21 Inc.  All Rights Reserved.
--
 
COM21-HCXTOP-MIB DEFINITIONS ::= BEGIN
        IMPORTS MODULE-IDENTITY, OBJECT-TYPE, NOTIFICATION-TYPE, Integer32,
        IpAddress, Gauge32, TimeTicks
        FROM SNMPv2-SMI
        DisplayString, MacAddress
        FROM SNMPv2-TC
        com21, com21Hcx, com21Traps, com21Reg
        FROM COM21-HCX-MIB
		  hcxAlmSeverity, hcxEventLogTime
        FROM COM21-HCXALM-MIB;

        com21HcxCtrl MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"

                DESCRIPTION
                        "This is the Com21 ComController Unit Control MIB 
			   module. It provides for overall, high-level 
			   control of the ComController and comUNITY system. 
			   COM21 Part# 005-0025-00"
                ::= { com21Hcx 1 }

        com21HcxControlGroup            OBJECT IDENTIFIER ::= {com21Hcx  2}
	com21HcxAcqCnfgGroup		OBJECT IDENTIFIER ::= {com21Hcx  3}
	com21HcxAlmOverGroup		OBJECT IDENTIFIER ::= {com21Hcx  4}
	com21HcxStuOverGroup		OBJECT IDENTIFIER ::= {com21Hcx  5}
        com21HcxTrapRcvrGroup           OBJECT IDENTIFIER ::= {com21Hcx  6}
        com21HcxShelfGroup              OBJECT IDENTIFIER ::= {com21Hcx  7}
        com21HcxSlotGroup               OBJECT IDENTIFIER ::= {com21Hcx  8}
        com21HcxImageListGroup          OBJECT IDENTIFIER ::= {com21Hcx  9}
        com21HcxServTypeGroup           OBJECT IDENTIFIER ::= {com21Hcx 10}
	com21HcxArpFiltTrapGroup	OBJECT IDENTIFIER ::= {com21Hcx 12}
	com21HcxStuDefaultGroup		OBJECT IDENTIFIER ::= {com21Hcx 13}
	com21HcxDbControlGroup		OBJECT IDENTIFIER ::= {com21Hcx 14}
	com21HcxBootControlGroup	OBJECT IDENTIFIER ::= {com21Hcx 18}

	com21HcxPhase30			OBJECT IDENTIFIER ::= {com21Reg  1}
	com21HcxCompact			OBJECT IDENTIFIER ::= {com21Reg  2}

	UpstrmFreqKhz    ::= INTEGER (5000..40000)
        StuGain          ::= INTEGER (18..58)
        EpochTime        ::= INTEGER (0..2147483647)
        PrimServiceState ::= INTEGER { is(1), oos(2) }
	Com21RowStatus   ::= INTEGER { active(1), create(2), destroy(3),
				       deactive(4) }

        HcxCardType      ::= INTEGER { rx(1), tx(2), ethDual10bT(3), 
				       ethQuad10bT(4), eth100bT(5), tele(6), 
				       cc(7), oc3(8), atm25(9), empty(10),
				       txRf(11), txDig(12), eth10bT8k(13),
				       intConn(14), rxm(15), atmlSw(16),
				       compactSw(17) }


        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the 
	-- SNMP interface and the MIB II Interfaces Group for both the 
	-- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        -- The com21HcxCtrl MIB contains the following groups :
        --
        --   com21HcxControlGroup       - this group supports the overall
        --                                control of the ComController as a 
	--				  whole.
        --
	--   com21HcxAcqCnfgGroup       - this group provides for configuration
	--				  of the ComPort parameters passed 
	--				  during acquisition.
	--
	--   com21HcxAlmOverGroup	- this group contains an overview of
	--				  the alarm state and alarm config
	--				  of the ComController.
	--
	--   com21HcxStuOverGroup	- this group provides an overview of
	--				  of the ComPort connectivity.
	--
        --   com21HcxTrapRcvrGroup      - this group provides each management
        --                                entry with the ability to control the
        --                                reception of ComController and 
	--				  ComPort traps.
        --
	--   com21HcxShelfGroup		- this group specifies the shelf
	--				  type, the number of slots and
	--				  any other specific information.
	--
        --   com21HcxSlotGroup          - this group provides a table with a
        --                                single entry for each physical card
        --                                slot in the ComController system. 
	--				  The user may use this group to 
	--				  preconfigure the ComController.
        --
        --   com21HcxImageListGroup     - table of stored ComController and 
	--				  ComPort images.
        --
        -- -- -- -- -- -- -- -- -- -- -- -- -- -- -- -- -- -- -- -- -- -- -- --
        -- -- -- -- -- -- -- -- -- -- -- -- -- -- -- -- -- -- -- -- -- -- -- --

        -- -- -- -- -- -- -- -- -- -- -- -- -- -- -- -- -- -- -- -- -- -- -- --
        -- -- -- -- -- -- -- -- -- -- -- -- -- -- -- -- -- -- -- -- -- -- -- --
        --
        -- com21HcxControlGroup
        --
        -- defines the attributes related to the management of overall 
        -- ComController functionality. 
        --
        -- -- -- -- -- -- -- -- -- -- -- -- -- -- -- -- -- -- -- -- -- -- -- --
        -- -- -- -- -- -- -- -- -- -- -- -- -- -- -- -- -- -- -- -- -- -- -- --
  
	hcxMacAddress OBJECT-TYPE
	        SYNTAX MacAddress
		MAX-ACCESS read-only
		STATUS current
		DESCRIPTION "
			Contains IEEE 802 medium access control address of the 
			ComController device."
		::= { com21HcxControlGroup 1 }

        hcxEncryptionEnable OBJECT-TYPE
                SYNTAX INTEGER { true (1), false (2) }
                MAX-ACCESS read-write
                STATUS current
                DESCRIPTION "
                        Used to enable or disable encryption on a system 
			basis. Default is true."
                ::= { com21HcxControlGroup 2 }
 
	hcxPartNumber OBJECT-TYPE
		SYNTAX DisplayString (SIZE(32))
		MAX-ACCESS read-only
		STATUS current
		DESCRIPTION "
			The ComController Part Number is a display string ."
		::= { com21HcxControlGroup 3 }

	hcxEpochTime OBJECT-TYPE
		SYNTAX EpochTime 
		MAX-ACCESS read-write
		STATUS current
		DESCRIPTION "
			The Epoch Time is a 31 bit signed positive integer
			containing the number of seconds since 1970."
		::= { com21HcxControlGroup 4 }

	hcxUserText OBJECT-TYPE
		SYNTAX DisplayString (SIZE(32))
		MAX-ACCESS read-write
		STATUS current
		DESCRIPTION "
			The User Text is a non-volatile string which is set
			by the management system with an arbitrary value. This
			value does not have to be unique. It's purpose is solely
			to assist the carrier personnel with identifying the
			ComController device."
		::= { com21HcxControlGroup 5 }

	hcxSerialNumber OBJECT-TYPE
		SYNTAX DisplayString (SIZE(32))
		MAX-ACCESS read-only
		STATUS current
		DESCRIPTION "
			The Serial Number is a 32 character number used
			by COM21 to uniquely identify the device."
		::= { com21HcxControlGroup 6 }

	hcxIpAddress OBJECT-TYPE
                SYNTAX IpAddress
        	MAX-ACCESS read-only
        	STATUS current
        	DESCRIPTION "
			IP address of the ComController SNMP Agent."
        	::= { com21HcxControlGroup 7 }

	hcxIpMask OBJECT-TYPE
                SYNTAX IpAddress
        	MAX-ACCESS read-write
        	STATUS current
        	DESCRIPTION "
			IP mask of the ComController SNMP Agent."
        	::= { com21HcxControlGroup 27 }

	hcxGatewayAddress OBJECT-TYPE
                SYNTAX IpAddress
        	MAX-ACCESS read-write
        	STATUS current
        	DESCRIPTION "
			IP address of any IP Gateway. Default is 0.0.0.0."
        	::= { com21HcxControlGroup 8 }

	hcxRestartAction OBJECT-TYPE
		SYNTAX INTEGER {
				nil(1),
				warmStart(2),
				coldStart(3) }
		MAX-ACCESS read-write
		STATUS current
		DESCRIPTION "
			The Restart Action is an active-value. The setting
			of this value to warmStart(2) causes the 
			ComController to restart utilizing the present 
			active software load. The setting of this value to 
			coldStart(3) causes the ComController to restart, 
			refreshing the current active firmware images and 
			the active configuration file from the NMAPS. This 
			completion of the reboot shall be indicated by the 
			standard SNMP warmStart or coldStart trap."
		::= { com21HcxControlGroup 9 }

        hcxRestartNotify NOTIFICATION-TYPE       
                OBJECTS { hcxAlmSeverity, hcxEventLogTime }
                STATUS current
                DESCRIPTION "
                        this trap is generated upon HCX initialization
                        after a restart. This trap indicates to a management
			system that the HCX SNMP Agent, and the system
			generally, is ready.  Only severity is WARNING."
                ::= { com21Traps 59 }
 
	hcxMajorAlarmStatusLed OBJECT-TYPE
		SYNTAX INTEGER { on (1), off (2) }
		MAX-ACCESS read-only
		STATUS current
		DESCRIPTION "
			The Major Alarm Status LED is a read-only 
			variable which describes the condition of the
			ComController Major Alarm Status light emitting 
			diode located on the CC board. A value of on(1) 
			indicates that a Major alarm exists and that the 
			LED is illuminated. A value of off(2) indicates 
			that no major alarm condition is detected."
		::= { com21HcxControlGroup 10 }

        hcxMajorStatusLedChange NOTIFICATION-TYPE
                OBJECTS { hcxAlmSeverity, hcxEventLogTime,
		            hcxMajorAlarmStatusLed }
                STATUS current
                DESCRIPTION "
			generated whenever there is a change in major alarm 
			LED status. This an event with no clear condition. 
			Only severity is WARNING."
                ::= { com21Traps 40 }

        hcxMinorAlarmStatusLed OBJECT-TYPE
                SYNTAX INTEGER { on (1), off (2) }
                MAX-ACCESS read-only
                STATUS current
                DESCRIPTION "
                        The Minor Alarm Status LED is a read-only 
                        variable which describes the condition of the 
                        ComController Minor Alarm Status light emitting 
			diode located on the CC board. A value of on(1) 
			indicates that a Minor alarm exists and that the 
			LED is illuminated. A value of off(2) indicates 
			that no minor alarm condition is detected."
                ::= { com21HcxControlGroup 11 }
 
        hcxMinorStatusLedChange NOTIFICATION-TYPE
                OBJECTS { hcxAlmSeverity, hcxEventLogTime,
		            hcxMinorAlarmStatusLed }
                STATUS current
                DESCRIPTION "
			generated whenever there is a change in minor alarm 
                        LED status. This an event with no clear condition. 
			Only severity is WARNING."
                ::= { com21Traps 41 }

        hcxAutoLoadBalancing OBJECT-TYPE
                SYNTAX INTEGER { on (1), off (2) }
                MAX-ACCESS read-write
                STATUS current
                DESCRIPTION "
                        This attribute controls whether the ComController
                        shall perform automatic load balancing after an
			RX resource is added (or restored to the system). 
			Default is on."
                ::= { com21HcxControlGroup 12 }

        hcxAutoFreqHopping OBJECT-TYPE 
                SYNTAX INTEGER { on (1), off (2) } 
                MAX-ACCESS read-write
                STATUS current
                DESCRIPTION " 
                        This attribute controls whether the ComController
			shall perform automatic frequency hopping. Note that
			the auto frequency hopping can also be controlled
			on a specific RX port basis. Turning this attribute 
			off will override the individual ComPort 
			configurations. Default will be on."
                ::= { com21HcxControlGroup 13 }
 
	hcxKeyRenewalPeriod OBJECT-TYPE
                SYNTAX INTEGER (0..8784)
                MAX-ACCESS read-write
                STATUS current
                DESCRIPTION "
                        Contains the period at which encryption keys should
			be renewed. This attribute is expressed in hours.
			i.e. value of 48 indicates a 48hour renewal frequency.
			Default is 24. 0 disables renewal."
                ::= { com21HcxControlGroup 14 }

        -- -- -- -- -- -- -- -- -- -- -- -- -- -- -- -- -- -- -- -- -- -- -- --
        -- -- -- 1 Attribute Deprecated
        -- -- -- -- -- -- -- -- -- -- -- -- -- -- -- -- -- -- -- -- -- -- -- --


	hcxHcxSwRelease OBJECT-TYPE
                SYNTAX DisplayString (SIZE(32))
                MAX-ACCESS read-only
                STATUS current
                DESCRIPTION "
                        This attribute details the current, active CC software 
			revision. Format is a.b.c.ddd."
                ::= { com21HcxControlGroup 16 }

        hcxHcxAlternateSwRel OBJECT-TYPE
                SYNTAX DisplayString (SIZE(32))
                MAX-ACCESS read-write
                STATUS current
                DESCRIPTION "
                        This attribute details the alternate software 
			revision. It is written after cold boot by the CC 
			and later can be written by the user. If this value 
			is written by the user - note that the release need
                        not necessarily change - then the CC shall
                        retrieve a new set of alternate images from the boot 
			server. Format is a.b.c.ddd."
                ::= { com21HcxControlGroup 31 }

        hcxHcxImageControl OBJECT-TYPE
                SYNTAX DisplayString (SIZE(32))
                MAX-ACCESS read-write
                STATUS current
                DESCRIPTION "
                        This attribute is used to activate a given revision
			of software images. The CC shall automatically 
			reboot if this field is changed by the user and
			the version input is valid. Format is a.b.c.ddd."
                ::= { com21HcxControlGroup 32 }

        -- -- -- -- -- -- -- -- -- -- -- -- -- -- -- -- -- -- -- -- -- -- -- --
        -- -- -- 1 Attribute Deprecated
        -- -- -- -- -- -- -- -- -- -- -- -- -- -- -- -- -- -- -- -- -- -- -- --


	hcxImageTransfer OBJECT-TYPE
                SYNTAX DisplayString (SIZE(32))
                MAX-ACCESS read-write
                STATUS current
                DESCRIPTION "
			This attribute is used tell the CC to download an 
			individual ComController software image from the boot 
			server (NMAPS) to PCMCIA disk.  Images transfered as 
			a result of this command are not loaded to the 
			corresponding card - to do this, the uploaded image 
			must be made to be the primary image and the card must 
			be rebooted. The images are specified via 
			<image type> <revision>, where the revision is of the 
			a.b.c.ddd format and the image type is one of the 
			following:

				rx       - RX card
				rxm      - RXM card
				tx       - TX card
				cc       - CC card
				10bt     - 10bT card
				100bt    - 100bT card
				oc3      - OC3 card
				atm      - ATM switch
				comp     - compact HCX image
				stu3com  - 3COM modem image(s)
				stu      - COM21 ComPort images

			The CC will check the validity of the revision number
			against the hcxHcxSwRelease and hcxHcxAlternateSwRel
			values."
                ::= { com21HcxControlGroup 34 }

        hcxHcxSwDnldResult OBJECT-TYPE
                SYNTAX INTEGER { 
				inprogress(1),
				success(2), 
				serverNoResponse(3),
				imageNotFound(4),
				versionMismatch(5),
				serverConnectionLost(6),
				uninitiated(7) }
                MAX-ACCESS read-only
                STATUS current
                DESCRIPTION "
                        This attribute contains the result of the last
                        ComController software image download from the 
			boot server."
                ::= { com21HcxControlGroup 18 }
 
        hcxHcxSwDnldComplete NOTIFICATION-TYPE
                OBJECTS { hcxAlmSeverity, hcxEventLogTime,
                            hcxHcxSwDnldResult }
                STATUS current
                DESCRIPTION "
                        This notification is generated whenever the CC
                        completes the ComController software image download. 
			This an event with no clear condition. Only severity 
			is WARNING."
                ::= { com21Traps 42 }

        -- -- -- -- -- -- -- -- -- -- -- -- -- -- -- -- -- -- -- -- -- -- -- --
        -- -- -- 2 Attribute Deprecated
        -- -- -- -- -- -- -- -- -- -- -- -- -- -- -- -- -- -- -- -- -- -- -- --


       -- 	DEPRECATED TRAP
       --
       --        hcxStuSwDnldComplete NOTIFICATION-TYPE
       --         OBJECTS { hcxAlmSeverity, hcxEventLogTime,
       --                     hcxStuSwDnldResult }
       --         STATUS current
       --         DESCRIPTION "
       --                 This notification is generated whenever the CC
       --                 completes the ComPort software revision image
       --		download. This an event with no clear condition. 
       --			Only severity is WARNING."
       --         ::= { com21Traps 43 }
       --	
 
        hcxCnfgBackupAction OBJECT-TYPE
                SYNTAX INTEGER {
                                nil(1),
                                backupToSaved(2),
				revertToSaved(3) }
                MAX-ACCESS read-write
                STATUS current
                DESCRIPTION "
			This attribute is provided to allow a user to
                        trigger a backup of ComController configuration 
			data on to the boot server. backupToSaved is
			used to create a user controlled backup on NMAPS.
			revertToSaved is used retrieve a saved database
			from NMAPS."
                ::= { com21HcxControlGroup 21 }

        hcxCnfgBackupComplete NOTIFICATION-TYPE
                OBJECTS { hcxAlmSeverity, hcxEventLogTime,
                            hcxCnfgBackupResult }
                STATUS current
                DESCRIPTION "
                        This notification is generated whenever the CC
                        completes the configuration data backup. This an event 
                        with no clear condition. Only severity is WARNING."
                ::= { com21Traps 44 }

        hcxCnfgBackupResult OBJECT-TYPE
                SYNTAX INTEGER { 
				inprogress(1),
				success(2), 
                                serverNoResponse(3),
				writeFailed(4),
				uninitiated(5) }
                MAX-ACCESS read-only
                STATUS current
                DESCRIPTION "
                        This attribute contains the result of the last
                        configuration data backup operation."
                ::= { com21HcxControlGroup 22 }

	hcxPhyConfigType OBJECT-TYPE
                SYNTAX INTEGER { 
				singleShelf(1), 
				fullConfig(2), 
				compactShelf(3) }
		MAX-ACCESS read-only
		STATUS current
                DESCRIPTION "
                        This attribute details the physical configuration
			type of the ComController."
                ::= { com21HcxControlGroup 23 }
 
        hcxNumOfShelves OBJECT-TYPE
                SYNTAX INTEGER (1..2)
		MAX-ACCESS read-only 
                STATUS current 
                DESCRIPTION " 
                        This attribute specifies the number of shelves
			in the system. Presently one or two."
                ::= { com21HcxControlGroup 24 }

	hcxBootpServer OBJECT-TYPE
                SYNTAX DisplayString (SIZE(32))
                MAX-ACCESS read-only
                STATUS current
                DESCRIPTION "
                        This attribute contains bootp server hostname."
                ::= { com21HcxControlGroup 25 }
 
        hcxBootpFailed NOTIFICATION-TYPE
                OBJECTS { hcxAlmSeverity, hcxEventLogTime,
                            hcxBootpResult }
                STATUS current
                DESCRIPTION "
                        This notification is generated whenever the CC
                        fails to successfully complete a bootp operation.
                        Only severity is WARNING."
                ::= { com21Traps 45 }

        hcxBootpResult OBJECT-TYPE
                SYNTAX INTEGER {
                                inprogress(1),
                                success(2),
                                serverNoResponse(3),
                                serverUnknown(4),
				imageNotFound(5),
				versionMismatch(6),
                                serverConnectionLost(7) }
                MAX-ACCESS read-only
                STATUS current
                DESCRIPTION "
                        This attribute contains the result of the last
                        bootp operation."
                ::= { com21HcxControlGroup 26 }
 
        hcxPowerFailDetected NOTIFICATION-TYPE
                OBJECTS { hcxAlmSeverity, hcxEventLogTime, hcxShelfId }
                STATUS current
                DESCRIPTION "
                        This notification is generated whenever a power
                        failure condition is detected. Default severity
                        is MAJOR."
                ::= { com21Traps 46 }
 
        hcxPowerFailClear NOTIFICATION-TYPE 
                OBJECTS { hcxAlmSeverity, hcxEventLogTime, hcxShelfId }
                STATUS current
                DESCRIPTION " 
                        This notification is generated whenever a power
                        failure condition is removed. Severity is
                        CLEARED." 
                ::= { com21Traps 47 }

        hcxFanFailDetected NOTIFICATION-TYPE 
                OBJECTS { hcxAlmSeverity, hcxEventLogTime, hcxShelfId }
                STATUS current
                DESCRIPTION " 
                        This notification is generated whenever a fan
                        failure condition is detected. Default severity 
                        is MAJOR." 
                ::= { com21Traps 48 }
  
        hcxFanFailClear NOTIFICATION-TYPE  
                OBJECTS { hcxAlmSeverity, hcxEventLogTime, hcxShelfId } 
                STATUS current
                DESCRIPTION "  
                        This notification is generated whenever a fan
                        failure condition is removed. Severity is 
                        CLEARED."  
                ::= { com21Traps 49 }

        hcxFreqHopPause OBJECT-TYPE
                SYNTAX INTEGER (0..300)
                MAX-ACCESS read-write
                STATUS current
                DESCRIPTION "
                        This attribute defines the number of seconds
                        between a failed frequency hopping operation
                        and a subsequent attempt. If a given upstream
                        frequency is found to be in an error state, then
                        the HCX will cycle through the configured
                        alternates. If all these alternates are also
                        found to be in a degraded state, then the HCX
                        shall pause for the number of seconds defined
                        by this attribute before attempting another hop.
                        Default 30secs."
                ::= { com21HcxControlGroup 28 }

        hcxMaxDnstrmCBRAlloc OBJECT-TYPE
                SYNTAX INTEGER (0..100)
                MAX-ACCESS read-write
                STATUS current
                DESCRIPTION "
                        This attribute defines the maximum percentage
			of downstream bandwidth that can be allocated
			to CBR traffic. This control mechanism will
			denied service to acquiring ComPorts if the
			addition of the configured CBR bandwidth 
			would exceed the defined percentage. Note
			that this is a limit. i.e. if this attribute
			is set to 50%, then UP TO half the bandwidth
			can be CBR. It does not mean that half WILL
			be CBR. 100%, the default, means in effect 
			there is no control."
                ::= { com21HcxControlGroup 29 }

        hcxMaxUpstrmCBRAlloc OBJECT-TYPE 
                SYNTAX INTEGER (0..100)  
                MAX-ACCESS read-write  
                STATUS current
                DESCRIPTION "  
                        This attribute defines the maximum percentage   
                        of upstream bandwidth that can be allocated
                        to CBR traffic. Default 100."
                ::= { com21HcxControlGroup 30 }

        hcxStatsControl OBJECT-TYPE
                SYNTAX INTEGER { previousCounts(1), wrapCurr(2) }
                MAX-ACCESS read-write
                STATUS current
                DESCRIPTION "
                        This attribute controls the statistics collection
			mechanism. If previousCounts is selected then the
			current stats shall be copied into the previous
			stats counts every 15minutes. If wrapCurr is
			selected, then there shall be no copying in to
			previous counts and the current counters shall
			wrap. If NMAPS is utilized then previousCounts
			MUST be selected. Default previousCounts."
                ::= { com21HcxControlGroup 33 }

	hcxTrapFormat OBJECT-TYPE 
                SYNTAX INTEGER { snmpv1 (1), snmpv2 (2) }
		MAX-ACCESS read-write 
                STATUS current 
                DESCRIPTION "  
                        specifies the format of the traps generated by the
			Common Controller. Default is snmpv1."
                ::= { com21HcxControlGroup 35 }

        hcxSyncClkConfigure OBJECT-TYPE
                SYNTAX INTEGER { internalClk (1), networkClk (2) }
                MAX-ACCESS read-write
                STATUS current
                DESCRIPTION "
                        specifies the clock used for synchronization.
                        if networkClk is selected, one of the
                        OC3 card should be selected as the primary
                        source. Optionally secondary source can
                        also be selected. The behaviour is as follows:
 
                        If no Oc3 card exists
                                ClockSelect is internalClk
                        if priOc3Card is Online
                                ClockSelect is priNetworkClk
                        if secOc3Card is Online and priOc3Card is Offline
                                ClockSelect is secNetworkClk
 
                        Default is internalClk."
                ::= { com21HcxControlGroup 36 }
 
 
        hcxSyncClkSelect OBJECT-TYPE
                SYNTAX INTEGER { internalClk (1),
                                 priNetworkClk (2),
                                 secNetworkClk (3) }
                MAX-ACCESS read-only
                STATUS current
                DESCRIPTION "
                        specifies the clock selected for
                        synchronization.
                        Default is internalClk."
                ::= { com21HcxControlGroup 37 }
 
        hcxSyncClkChange NOTIFICATION-TYPE
                OBJECTS { hcxAlmSeverity, hcxEventLogTime,
                          hcxSyncClkSelect }
                STATUS current
                DESCRIPTION "
                        This notification is generated whenever
                        there is a change in Clock
                        used for Synchronization "
                ::= { com21Traps 181 }




        -- -- -- -- -- -- -- -- -- -- -- -- -- -- -- -- -- -- -- -- -- -- -- --
        -- -- -- -- -- -- -- -- -- -- -- -- -- -- -- -- -- -- -- -- -- -- -- --
        --
        -- com21HcxAcqCnfgGroup
        --
        -- defines the attributes related to the acquisition of ComPorts. It
	-- is anticipated that these values should be set only by COM21 
	-- personnel.
        --
        -- -- -- -- -- -- -- -- -- -- -- -- -- -- -- -- -- -- -- -- -- -- -- --
        -- -- -- -- -- -- -- -- -- -- -- -- -- -- -- -- -- -- -- -- -- -- -- --

	hcxAcquisitionFreq OBJECT-TYPE
                SYNTAX UpstrmFreqKhz
                MAX-ACCESS read-write
                STATUS deprecated
                DESCRIPTION "
                        No longer supported."
                ::= { com21HcxAcqCnfgGroup 1 }

        hcxAcqMinPower OBJECT-TYPE
                SYNTAX StuGain
                MAX-ACCESS read-write
                STATUS current
                DESCRIPTION "
                        Contains the minimum power setting to be used by
			the ComPort when hunting for upstream channel. This 
			data is used in the INVITE_CONFIG message. 
			Default 18."
                ::= { com21HcxAcqCnfgGroup 6 }

        hcxAcqMaxPower OBJECT-TYPE
                SYNTAX StuGain
                MAX-ACCESS read-write
                STATUS current
                DESCRIPTION "
                        Contains the maximum power setting to be used by
			the ComPort when hunting for upstream channel. This 
			data is used in the INVITE_CONFIG message. Default
			58."
                ::= { com21HcxAcqCnfgGroup 7 }
 
         hcxAcqPowerStepSize OBJECT-TYPE
                SYNTAX INTEGER (1..20)
                MAX-ACCESS read-write
                STATUS current
                DESCRIPTION "
                        Contains the power step size to be used by the
                        ComPort when hunting for upstream channel. This data 
			is used in the INVITE_CONFIG message. Default 1."
                ::= { com21HcxAcqCnfgGroup 8 }

        hcxAltAcqFreq OBJECT-TYPE
                SYNTAX INTEGER (0..40000)
                MAX-ACCESS read-write
                STATUS deprecated
                DESCRIPTION "
                        No longer supported."
                ::= { com21HcxAcqCnfgGroup 9 }

        hcxActiveAcqFreq OBJECT-TYPE
                SYNTAX UpstrmFreqKhz
                MAX-ACCESS read-only
                STATUS deprecated
                DESCRIPTION "
                        No longer supported."
                ::= { com21HcxAcqCnfgGroup 10 }

 
        -- -- -- -- -- -- -- -- -- -- -- -- -- -- -- -- -- -- -- -- -- -- -- --
        -- -- -- -- -- -- -- -- -- -- -- -- -- -- -- -- -- -- -- -- -- -- -- --
        --
        -- com21HcxAlmOverGroup
        --
        -- defines the attributes providing an overview of the alarm
	-- status and configuration of the ComController system.
        --
        -- -- -- -- -- -- -- -- -- -- -- -- -- -- -- -- -- -- -- -- -- -- -- --
        -- -- -- -- -- -- -- -- -- -- -- -- -- -- -- -- -- -- -- -- -- -- -- --

	hcxNoCurrAlarms OBJECT-TYPE
                SYNTAX INTEGER (0..255)
                MAX-ACCESS read-only
                STATUS current
                DESCRIPTION "
 			Contains the number of active ComController alarms."
                ::= { com21HcxAlmOverGroup 1 }

	hcxEventLogSize OBJECT-TYPE
                SYNTAX INTEGER (10..1000)
                MAX-ACCESS read-write
                STATUS current
                DESCRIPTION "
 			Contains the maximum number of events to be stored
			in the log. Default is 200. Upper limit will be
			controlled by the available memory. Set to 1000 for
			now."
                ::= { com21HcxAlmOverGroup 2 }



        -- -- -- -- -- -- -- -- -- -- -- -- -- -- -- -- -- -- -- -- -- -- -- --
        -- -- -- -- -- -- -- -- -- -- -- -- -- -- -- -- -- -- -- -- -- -- -- --
        --
        -- com21HcxStuOverGroup
        --
        -- defines the attributes providing an overview of the ComPorts
	-- in the system.
        --
        -- -- -- -- -- -- -- -- -- -- -- -- -- -- -- -- -- -- -- -- -- -- -- --
        -- -- -- -- -- -- -- -- -- -- -- -- -- -- -- -- -- -- -- -- -- -- -- --

	hcxNumConfiguredStus OBJECT-TYPE
		SYNTAX INTEGER (0..2048)
		MAX-ACCESS read-only
		STATUS current
		DESCRIPTION "
			This value contains the number of configured ComPorts 
			for this ComController."
		::= { com21HcxStuOverGroup 1 }

	hcxNumAcquiredStus OBJECT-TYPE
		SYNTAX INTEGER (0..2048)
		MAX-ACCESS read-only
		STATUS current
		DESCRIPTION "
			This value contains the number of acquired ComPorts 
			for this ComController."
		::= { com21HcxStuOverGroup 2 }

	hcxLastStuTopolgyChng OBJECT-TYPE
                SYNTAX EpochTime
                MAX-ACCESS read-only
                STATUS current
                DESCRIPTION "
                        Contains the last time (epoch) that a change
			occurred in the ComPort topology."
                ::= { com21HcxStuOverGroup 3 }

        stuTopologyChange NOTIFICATION-TYPE
                OBJECTS { hcxAlmSeverity, hcxEventLogTime,
		            hcxNumAcquiredStus }
                STATUS current
                DESCRIPTION "
			This trap is sent at a maximum rate of once every 
			5seconds or when 100 ComPort acquisition/deacquisitions
			have occured, which ever is first. This an event 
                        with no clear condition. Only severity is WARNING."
                ::= { com21Traps 50 }

	hcxNumEnabledStus OBJECT-TYPE
		SYNTAX INTEGER (0..2048)
		MAX-ACCESS read-only
		STATUS current
		DESCRIPTION "
			This value contains the number of enabled and active
			ComPorts on this ComController. Note that we assume all 
			ComPort support ethernet if."
		::= { com21HcxStuOverGroup 4 }

        hcxStuAggrUpStrmCbrRate OBJECT-TYPE
                SYNTAX Integer32
                MAX-ACCESS read-only
                STATUS current
                DESCRIPTION "
                        This attribute defines the aggregate of all ComPort
                        upstream CBR rates in the ComController. This includes
			both acquired and unacquired ComPorts. Defined in Kbps."
                ::= { com21HcxStuOverGroup 5 }
 
        hcxStuAggrUpStrmMinRate OBJECT-TYPE
                SYNTAX Integer32
                MAX-ACCESS read-only
                STATUS current
                DESCRIPTION "
                        This attribute defines the aggregate of all ComPort
                        upstream minimum PCR rates in the ComController. This
			includes both acquired and unacquired ComPorts.
			Defined in Kbps."
                ::= { com21HcxStuOverGroup 6 }
 
        hcxStuAggrUpStrmMaxRate OBJECT-TYPE
                SYNTAX Integer32
                MAX-ACCESS read-only
                STATUS current
                DESCRIPTION "
                        This attribute defines the aggregate of all ComPort
                        upstream maximum rates in the ComController. This
			includes both acquired and unacquired ComPorts.
			Defined in Kbps."
                ::= { com21HcxStuOverGroup 7 }


        hcxStuResourceExhausted NOTIFICATION-TYPE
                OBJECTS { hcxAlmSeverity, hcxEventLogTime }
                STATUS current
                DESCRIPTION "
                        generated whenever an ComPort must be denied 
			acquisition due to a lack of CC resources. This
			includes an exhaustion of SIDs, leck of database
			capacity, etc. Only severity is WARNING."
                ::= { com21Traps 51 }

        hcxStuAltDownFreq OBJECT-TYPE
                SYNTAX INTEGER (88000..800000)
                MAX-ACCESS read-write
                STATUS current
                DESCRIPTION "
                        This attribute defines an alternate ComController
                        downstream frequency. This attribute would be
                        utilized if an unrecognized ComPort is acquired and
                        the hcxStuAltDownFreqEnable is set to enable.
                        Minimum step size is 200. i.e. 200000hz.
                        Default is 0, indicating no alternate frequency."
                ::= { com21HcxStuOverGroup 9 }
 

	hcxStuAcqTrapEnable OBJECT-TYPE
                SYNTAX INTEGER { 
				topoChgTrapOnly (1), 
				acqTrapOnly (2),
				bothTopoAndAcqTrap (3) }
                MAX-ACCESS read-write
                STATUS current
                DESCRIPTION "
                        Indicates whether the topology change trap mechanism
			should be used, or a trap per STU acq, or both. Note
			that NMAPS is dependant upon the topology change
			mechanism, so should be disabled only when NMAPS is
			not in use. Also be aware that a high number of traps
			will occur if the per acq trap is selected. Default 
			is topoChgTrapOnly."
                ::= { com21HcxStuOverGroup 11 }

        hcxStuRpcEnable OBJECT-TYPE
                SYNTAX INTEGER { true (1), false (2) }
                MAX-ACCESS read-write
                STATUS current
                DESCRIPTION "
                        Controls whether the system offers an RPC based
			interface for statistics and ComPort status.
                        Default is true."
                ::= { com21HcxStuOverGroup 12 }

        hcxStuAutoDiscEnable OBJECT-TYPE
                SYNTAX INTEGER { true (1), false (2) }
                MAX-ACCESS read-write
                STATUS current
                DESCRIPTION "
                        Controls whether the system performs auto
			discover of telephone return ComPorts.
                        Default is true."
                ::= { com21HcxStuOverGroup 13 }

        hcxStuAutoDiscIpAddr OBJECT-TYPE
                SYNTAX IpAddress
                MAX-ACCESS read-write
                STATUS current
                DESCRIPTION "
                        The IP address of the return path interface of a
                        PC that will enable autodiscovery of a ComPORT
                        operating in Telephone Return mode. A PC must be
                        present with this address on an established return
                        path connection to allow telephone return
                        autodiscovery to take place."
                ::= { com21HcxStuOverGroup 14 }

	hcxStuAutoGainAdjust OBJECT-TYPE
                SYNTAX INTEGER { disable (1), enable (2) }
                MAX-ACCESS read-write
                STATUS current
                DESCRIPTION "
			This attribute is used to control the automatic
			adjustment of ComPort gain after acquisition.
			Default is disable."
                ::= { com21HcxStuOverGroup 15 }

        hcxStuAltDownFreqEnable OBJECT-TYPE
                SYNTAX INTEGER { disable (1), enable (2) }
                MAX-ACCESS read-write
                STATUS current
                DESCRIPTION "
                        This attribute is used to control the automatic
                        setting of an alternate downstream frequency. If
                        enabled, the hcxStuAltDownFreq shall be set in any
                        unconfigured ComPort acquired by an HCX. Note that
                        this feature CANNOT be enabled if hcxStuDefaultAuth
                        is set to true or hcxStuAltDownFreq is set to 0.
                        Default is disabled."
                ::= { com21HcxStuOverGroup 16 }
 
        hcxStuPcMacAddress OBJECT-TYPE
                SYNTAX MacAddress
                MAX-ACCESS read-write
                STATUS current
                DESCRIPTION "
                        This attribute is used to set the mac address of the PC.
                        Setting this attribute starts a search for the mac
                        address of the ComPort that is connected to this PC."
                ::= { com21HcxStuOverGroup 17 }
 
        hcxStuPcToStuMacAddressResult OBJECT-TYPE
                SYNTAX INTEGER {
                                inprogress(1),
                                success(2),
                                failure(3) }
                MAX-ACCESS read-only
                STATUS current
                DESCRIPTION "
                        This attribute contains the result of the last
                        PC to ComPort mac address search.
                        It changes to 'inprogress' when hcxStuPcMacAddress
                        is set. When the search completes this attribute
                        will display either 'success' or 'failure'."
                ::= { com21HcxStuOverGroup 18 }
 
        hcxStuOverMacAddress OBJECT-TYPE
                SYNTAX MacAddress
                MAX-ACCESS read-only
                STATUS current
                DESCRIPTION "
                        This attribute displays the mac address of the
                        ComPort that is connected to the PC with mac address
                        hcxStuPcMacAddress. The value is valid only if
                        hcxStuPcToStuMacAddressResult displays success."
                ::= { com21HcxStuOverGroup 19 }

	hcxStuGlobalSwImage OBJECT-TYPE
                SYNTAX DisplayString (SIZE(16))
                MAX-ACCESS read-write
                STATUS current
                DESCRIPTION "
			This attribute provides an easy way to change the
			configured software image for all configured ComPorts
			without having to modify hcxStuConfSwImage of
			individual ComPorts.
			When this attribute is written to by the user, the
			hcxStuConfSwImage attribute for all configured
			ComPorts will be automatically modified to reflect
			this value. However, this is only a one-time action.
			The user is free to modify the hcxStuConfSwImage
			attribute of individual ComPorts to other values.
			Since this attribute only affects configured ComPorts,
			it does not interfere with hcxStuDefCom21SwImage or
			hcxStuDef3ComSwImage from com21HcxStuDefaultGroup.
			Default is 0.0.0.0. Also, it will reset back to 0.0.0.0
			upon a ComController reboot."
                ::= { com21HcxStuOverGroup 20 }



        -- -- -- -- -- -- -- -- -- -- -- -- -- -- -- -- -- -- -- -- -- -- -- --
        -- -- -- -- -- -- -- -- -- -- -- -- -- -- -- -- -- -- -- -- -- -- -- --
        --
        -- com21HcxStuDefaultGroup
        --
        -- This group allows a user to define a default QoS, image and VLAN
        -- in order to permit previously unconfigured ComPort to be
        -- automatically acquired and enable connectivity. This feature
        -- presently support two-way ComPorts ONLY.
        --
        -- -- -- -- -- -- -- -- -- -- -- -- -- -- -- -- -- -- -- -- -- -- -- --
        -- -- -- -- -- -- -- -- -- -- -- -- -- -- -- -- -- -- -- -- -- -- -- --


	hcxStuDefaultAuth OBJECT-TYPE
                SYNTAX INTEGER { true (1), false (2) }
                MAX-ACCESS read-write    
                STATUS current
                DESCRIPTION "  
                        Indicates whether the default authorization of
			a previously unconfigured and unauthorized ComPort
			should be permitted. If true, then all other
			attributes in this group must be set. Note that
                        this feature CANNOT be enabled if
                        hcxStuAltDownFreqEnable is set to true. Default false."
                ::= { com21HcxStuDefaultGroup 1 }
 
	hcxStuDefaultServType OBJECT-TYPE
                SYNTAX INTEGER (0..16)
                MAX-ACCESS read-write
                STATUS current
                DESCRIPTION "
                        Contains the default QoS group for an acquired
			but unconfigured/unauthorized ComPort. Once
			configured, then the appropriate service type
			defined for the particular ComPort shall be used.
                        0 indicates no default QoS group to be used. 
			Default 0."
                ::= { com21HcxStuDefaultGroup 2 }

        hcxStuDefaultVlan OBJECT-TYPE
                SYNTAX INTEGER (0..64)
                MAX-ACCESS read-write
                STATUS current
                DESCRIPTION " 
                        Contains the default VLAN id for an acquired but
                        unconfigured/unauthorized ComPort. Once configured, 
			then the appropriate VLAN id defined for the 
			particular ComPort shall be used. 0 indicates no 
			default VLAN id to be used. Default 0."
                ::= { com21HcxStuDefaultGroup 3 }

        hcxStuDefCom21SwImage OBJECT-TYPE 
                SYNTAX DisplayString (SIZE(16))
                MAX-ACCESS read-write    
                STATUS current
                DESCRIPTION "  
                        Contains the default software image for an acquired 
			but unconfigured/unauthorized ComPort. Once configured, 
                        then the appropriate software image defined for the 
                        particular ComPort shall be used. Null string
                        indicates no default software image to be used. 
			Default null string."
                ::= { com21HcxStuDefaultGroup 4 }

        hcxStuDef3ComSwImage OBJECT-TYPE 
                SYNTAX DisplayString (SIZE(16))
                MAX-ACCESS read-write    
                STATUS current
                DESCRIPTION "  
                        Contains the default software image for an acquired 
			but unconfigured/unauthorized 3COM modem. Once 
			configured, then the appropriate software image 
			defined for the particular 3COM modem shall be used. 
			Null string indicates no default software image to 
			be used. Default null string."
                ::= { com21HcxStuDefaultGroup 5 }



        -- -- -- -- -- -- -- -- -- -- -- -- -- -- -- -- -- -- -- -- -- -- -- --
        -- -- -- -- -- -- -- -- -- -- -- -- -- -- -- -- -- -- -- -- -- -- -- --
        --
        -- com21HcxArpFiltTrapGroup
        --
        -- defines the attributes related to the reporting of ARP filter
        -- traps.
        --
        -- -- -- -- -- -- -- -- -- -- -- -- -- -- -- -- -- -- -- -- -- -- -- --
        -- -- -- -- -- -- -- -- -- -- -- -- -- -- -- -- -- -- -- -- -- -- -- --

        hcxArpServerTrapEnable OBJECT-TYPE
                SYNTAX INTEGER { true (1), false (2) }
                MAX-ACCESS read-write
                STATUS current
                DESCRIPTION "
                        specifies if traps should be generated when user
                        impersonation of ComController server IP addresses is
                        detected. Default false."
                ::= { com21HcxArpFiltTrapGroup 1 }

        hcxArpUserTrapEnable OBJECT-TYPE              
                SYNTAX INTEGER { true (1), false (2) }
                MAX-ACCESS read-write
                STATUS current
                DESCRIPTION "
                        controls if traps should be generated when user
                        specifies an incorrect IP address in an ARP
                        message. Default false."
                ::= { com21HcxArpFiltTrapGroup 2 }
 
 

	-- -- -- -- -- -- -- -- -- -- -- -- -- -- -- -- -- -- -- -- -- -- -- --
	-- -- -- -- -- -- -- -- -- -- -- -- -- -- -- -- -- -- -- -- -- -- -- --
	--
	-- com21HcxTrapRcvrGroup
	--
	-- defines the attributes related to the trap receiver. This group
	-- provides for the control of trap messages to a management interface.
	-- Initially the ComController shall support only a single trap based 
	-- interface to the NMAPS. The CUI shall not receive traps.
	--
	-- -- -- -- -- -- -- -- -- -- -- -- -- -- -- -- -- -- -- -- -- -- -- --
	-- -- -- -- -- -- -- -- -- -- -- -- -- -- -- -- -- -- -- -- -- -- -- --

	hcxTrapReceiverTable OBJECT-TYPE
        SYNTAX  SEQUENCE OF HcxTrapReceiverEntry
        MAX-ACCESS  not-accessible
        STATUS  current
        DESCRIPTION
                "Table containing list of NMAPS or other management systems
		 that are to receive traps generated by this NMM. There 
		 must be an entry for each connected NMAPS."
        ::= { com21HcxTrapRcvrGroup 1 }

	hcxTrapReceiverEntry OBJECT-TYPE
        SYNTAX  HcxTrapReceiverEntry
        MAX-ACCESS  not-accessible
        STATUS  current
        DESCRIPTION
                "A destination address and community string to a particular
                trap server, along with a trap filter and entry aging
                capability."
        INDEX   { hcxTrapRcvrNetAddress }
        ::= { hcxTrapReceiverTable 1 }

	HcxTrapReceiverEntry ::= SEQUENCE {
        	hcxTrapRcvrStatus	INTEGER,
        	hcxTrapRcvrNetAddress	IpAddress,
        	hcxTrapRcvrComm		OCTET STRING,
        	hcxTrapRcvrAgeTime	TimeTicks }

	hcxTrapRcvrStatus OBJECT-TYPE 
        SYNTAX  INTEGER  {
                valid (1),              -- a valid address
                invalid (2),            -- an invalid address, stop forwarding
                delete (3) }            -- delete this entry from the table
        MAX-ACCESS  read-create
        STATUS  current
        DESCRIPTION
                "Setting this object to the value invalid(2) has the effect
                of invalidating the corresponding entry in the
                hcxTrapReceiverTable. That is, it effectively disassociates
                the address identified with the entry by removing the entry
                from the table. On a read the value of valid(1) should be
                returned if the entry contains a valid record, or invalid(2)
                should be returned if the entry contains an invalid record.
                Default is valid."
        ::= { hcxTrapReceiverEntry 1 }

	hcxTrapRcvrNetAddress OBJECT-TYPE
        SYNTAX  IpAddress
        MAX-ACCESS  read-only
        STATUS  current
        DESCRIPTION
                "IP address for trap server that is to receive the trap."
        ::= { hcxTrapReceiverEntry  2 }
 
	hcxTrapRcvrComm OBJECT-TYPE
        SYNTAX  OCTET STRING (SIZE(0..16))
        MAX-ACCESS  read-only
        STATUS  current
        DESCRIPTION
                "Community string used for traps sent to this trap receiver.
		 Note that this string is writable only by the CC CUI."
        ::= { hcxTrapReceiverEntry  3 }
 
	hcxTrapRcvrAgeTime OBJECT-TYPE
        SYNTAX  TimeTicks
        MAX-ACCESS  read-write
        STATUS  current
        DESCRIPTION
                "This is the time interval used to age entries out of the trap
                receiver table.  The default value if not specified will be 0,
                or infinite, never to be aged out. At least initially, there
		will be no transient management devices in the comUNITY system.
		Therefore this attibute will always be set to 0."
        ::= { hcxTrapReceiverEntry  4 }



        -- -- -- -- -- -- -- -- -- -- -- -- -- -- -- -- -- -- -- -- -- -- -- --
        -- -- -- -- -- -- -- -- -- -- -- -- -- -- -- -- -- -- -- -- -- -- -- --
        --
        -- com21HcxShelfGroup
        --
        -- defines a shelf in the ComController shelf. One instance for each 
	-- shelf.
        --
        -- -- -- -- -- -- -- -- -- -- -- -- -- -- -- -- -- -- -- -- -- -- -- --
        -- -- -- -- -- -- -- -- -- -- -- -- -- -- -- -- -- -- -- -- -- -- -- --
 
        com21HcxShelfTable OBJECT-TYPE
                SYNTAX  SEQUENCE OF HcxShelfEntry
                MAX-ACCESS  not-accessible
                STATUS  current
                DESCRIPTION   
                        "TBD."
                ::= { com21HcxShelfGroup 1 }
 
        com21HcxShelfEntry OBJECT-TYPE
                SYNTAX  HcxShelfEntry
                MAX-ACCESS  not-accessible 
                STATUS  current
                DESCRIPTION "."
                INDEX { hcxShelfId }
                ::= { com21HcxShelfTable 1 }
 
        HcxShelfEntry ::= SEQUENCE {
                hcxShelfId              INTEGER,
                hcxShelfNoSlots		Integer32}
 
        hcxShelfId OBJECT-TYPE
                SYNTAX INTEGER (1..2)
                MAX-ACCESS read-only
                STATUS current
                DESCRIPTION "
                        contains ComController shelf id."
                ::= { com21HcxShelfEntry 1 }
 
        hcxShelfNoSlots OBJECT-TYPE
                SYNTAX Integer32
                MAX-ACCESS read-only
                STATUS current
                DESCRIPTION "
                        contains number of slots in this shelf."
                ::= { com21HcxShelfEntry 2 }
 


        -- -- -- -- -- -- -- -- -- -- -- -- -- -- -- -- -- -- -- -- -- -- -- --
        -- -- -- -- -- -- -- -- -- -- -- -- -- -- -- -- -- -- -- -- -- -- -- --
        --
        -- com21HcxSlotGroup
        --
        -- defines a slot in the ComController shelf. One instance for each 
	-- slot.
	--
        -- -- -- -- -- -- -- -- -- -- -- -- -- -- -- -- -- -- -- -- -- -- -- --
        -- -- -- -- -- -- -- -- -- -- -- -- -- -- -- -- -- -- -- -- -- -- -- --
 
        com21HcxSlotTable OBJECT-TYPE
                SYNTAX  SEQUENCE OF HcxSlotEntry
                MAX-ACCESS  not-accessible
                STATUS  current
                DESCRIPTION   
                        "TBD."
                ::= { com21HcxSlotGroup 1 }  

        com21HcxSlotEntry OBJECT-TYPE
                SYNTAX  HcxSlotEntry
                MAX-ACCESS  not-accessible 
                STATUS  current
                DESCRIPTION "."
                INDEX { hcxShelfNo, hcxSlotId }
                ::= { com21HcxSlotTable 1 }

        HcxSlotEntry ::= SEQUENCE {
		hcxShelfNo		INTEGER,
		hcxSlotId		INTEGER,
		hcxSlotSupportedTypes	INTEGER,
		hcxSlotConfigCardType	HcxCardType,
		hcxSlotInsertCardType	HcxCardType }

        hcxShelfNo OBJECT-TYPE
                SYNTAX INTEGER (1..2)
                MAX-ACCESS read-only
                STATUS current
                DESCRIPTION "
                        contains ComController shelf id."
                ::= { com21HcxSlotEntry 1 }

        hcxSlotId OBJECT-TYPE
                SYNTAX INTEGER (1..11)
                MAX-ACCESS read-only
                STATUS current
                DESCRIPTION "
                        contains ComController slot id."
                ::= { com21HcxSlotEntry 2 }

        hcxSlotSupportedTypes OBJECT-TYPE
                SYNTAX INTEGER {
			rx(1),
			tx(2),
			cc(3),
			com21Exp(4),
			txDig(5),
			intConn(6),
			rxIntConn(7),
			noCard(8),
			rxCom21Exp(9) }
                MAX-ACCESS read-only
                STATUS current
                DESCRIPTION "
                        contains card types supported for this slot. com21Exp
                        specifies 10baseT or 100baseT or oc3.
                        intConn is the interconnect card used on the
                        expansion shelf (Shelf2).

                        rxIntConn is used to indicate a slot that can be
                        used for an RX, 100bT or 10bT card in the single shelf
                        configuration or for the interconnect card when an
                        expansion shelf is present.

			rx indicates either RX or RXM cards.

                        On the expansion shelf there is support of up to
                        8 rx cards.

                        rxCom21Exp defines RX, oc3, 10bT or 100bT card for
			slots 3 and 4. For all other slots it defines 
			Rx, 10bT or 100bT cards (This implies that 
			oc3 card is supported only in slots 2,3 and 4).
			Note that there is a maximum of 5x10bT/100bT and 
			12xRX in the system.
			maximum number of oc3 cards supported is 2
			

                        Release 2.3 software shall support the following slot
                        designations. 

			if hcxPhyConfigType = singleShelf:

			  Shelf 1
			    Slot 1  - cc
			    Slot 2  - com21Exp
			    Slot 3  - rxCom21Exp
			    Slot 4  - rxCom21Exp
			    Slot 5  - rxIntConn
			    Slot 6  - rxCom21Exp
			    Slot 7  - rxCom21Exp
			    Slot 8  - rx
			    Slot 9  - rx
		   	    Slot 10 - txDig
			    Slot 11 - tx

			if hcxPhyConfigType = fullShelf:

			  Shelf 1		Shelf2
			    Slot 1  - cc	  Slot 1  - intConn
			    Slot 2  - com21Exp	  Slot 2  - rx
			    Slot 3  - rxCom21Exp  Slot 3  - rx
			    Slot 4  - rxCom21Exp  Slot 4  - rx
			    Slot 5  - rxIntConn   Slot 5  - rx
			    Slot 6  - rxCom21Exp  Slot 6  - rx
			    Slot 7  - rxCom21Exp  Slot 7  - rx
			    Slot 8  - rx	  Slot 8  - rx
			    Slot 9  - rx	  Slot 9  - rx
		   	    Slot 10 - txDig	  Slot 10 - noCard
			    Slot 11 - tx	  Slot 11 - noCard

			if hcxPhyConfigType = compactShelf:

			  Shelf 1
			    Slot 1  - cc
			    Slot 2  - com21Exp
			    Slot 3  - rxCom21Exp
			    Slot 4  - rx
			    Slot 5  - txDig
			    Slot 6  - tx"
                ::= { com21HcxSlotEntry 3 }

        hcxSlotConfigCardType OBJECT-TYPE
                SYNTAX HcxCardType
                MAX-ACCESS read-write
                STATUS current
                DESCRIPTION "
                        contains card type configured for this slot. This
			attribute will be checked against the set of 
			supported card types and rejected if not present.
			Note that the cardtype of ethDual10bT can be used
                        to specify either the 4k or 8k CAM versions of the
                        10bT card. Note that a 10bT or 100bT or oc3 card 
			CANNOT be unconfigured if an STU on an associated 
			VLAN is acquired."
                ::= { com21HcxSlotEntry 4 }

        hcxSlotInsertCardType OBJECT-TYPE
                SYNTAX HcxCardType
                MAX-ACCESS read-only
                STATUS current
                DESCRIPTION "
                        contains card type inserted in the ComController slot. 
			A value of empty shall be stored if there is no
			card."
                ::= { com21HcxSlotEntry 5 }

        hcxInsertChange NOTIFICATION-TYPE
                OBJECTS { hcxAlmSeverity, hcxEventLogTime,
                            hcxSlotInsertCardType, hcxShelfNo, hcxSlotId }
                STATUS current
                DESCRIPTION "
			generated whenever a card is inserted for the
			first time, or during restart of the ComController.
			Only severity is WARNING."
                ::= { com21Traps 52 }

        hcxCardRemoved NOTIFICATION-TYPE
                OBJECTS { hcxAlmSeverity, hcxEventLogTime, hcxShelfNo, 
		            hcxSlotId }
                STATUS current
                DESCRIPTION "
                        generated whenever an inserted and correctly
			configured card is removed. Default severity is MAJOR."
                ::= { com21Traps 120 }

        hcxCardRemClear NOTIFICATION-TYPE 
                OBJECTS { hcxAlmSeverity, hcxEventLogTime, hcxShelfNo, 
                            hcxSlotId }
                STATUS current
                DESCRIPTION " 
                        generated whenever a card is reinserted in a slot
			or when a slot is configured to empty or when a
			slot is reassigned, and that slot has a previously 
			generated hcxCardRemoved trap. If the inserted card 
			is of the incorrect type, then a subsequent 
			hcxMismatchDetect trap will be generated. Severity 
			is CLEARED."
                ::= { com21Traps 121 }

        hcxMismatchDetect NOTIFICATION-TYPE
                OBJECTS { hcxAlmSeverity, hcxEventLogTime,
                            hcxSlotInsertCardType, hcxShelfNo, hcxSlotId }
                STATUS current
                DESCRIPTION "
			generated when the inserted card does not match
			the configured card type. Default severity is MAJOR."
                ::= { com21Traps 53 }

        hcxMismatchClear NOTIFICATION-TYPE
                OBJECTS { hcxAlmSeverity, hcxEventLogTime,
                            hcxSlotInsertCardType, hcxShelfNo, hcxSlotId }
                STATUS current
                DESCRIPTION "
			this mismatch clear is submitted when an incorrect
			card is removed from a slot. Severity is CLEARED."
                ::= { com21Traps 54 }

	hcxCardNoRespond NOTIFICATION-TYPE
                OBJECTS { hcxAlmSeverity, hcxEventLogTime,
                            hcxSlotInsertCardType, hcxShelfNo, hcxSlotId }
                STATUS current
                DESCRIPTION "
                        generated when an inserted card fails to respond to
			a CC generated message. This an event with no clear 
			condition. Only severity is WARNING."
                ::= { com21Traps 55 }

	hcxCardPollFail NOTIFICATION-TYPE
                OBJECTS { hcxAlmSeverity, hcxEventLogTime,
                            hcxSlotInsertCardType, hcxShelfNo, hcxSlotId }
                STATUS current
                DESCRIPTION "
                        generated when an inserted card fails to respond to
                        a CC polling. Default severity is MAJOR."
                ::= { com21Traps 56 }

        hcxCardPollFailClear NOTIFICATION-TYPE 
                OBJECTS { hcxAlmSeverity, hcxEventLogTime, 
                            hcxSlotInsertCardType, hcxShelfNo, hcxSlotId } 
                STATUS current
                DESCRIPTION " 
                        generated when a card successfully responses to
                        CC polling after a previous failure. Only severity 
			is CLEARED." 
                ::= { com21Traps 57 }

        hcxCardDnldFailNoImage NOTIFICATION-TYPE 
                OBJECTS { hcxAlmSeverity, hcxEventLogTime, 
                            hcxSlotInsertCardType, hcxShelfNo, hcxSlotId } 
                STATUS current
                DESCRIPTION " 
                        generated when a card cannot be download due to a
			lack of the correct image. Only severity is WARNING."
                ::= { com21Traps 58 }

 

        -- -- -- -- -- -- -- -- -- -- -- -- -- -- -- -- -- -- -- -- -- -- -- --
        -- -- -- -- -- -- -- -- -- -- -- -- -- -- -- -- -- -- -- -- -- -- -- --
        --
        -- com21HcxImageListGroup
        --
        -- defines all the images loaded on to the Common Controller.
	-- This list includes both ComPort and ComController card images. The 
	-- NMAPS shall add an Image List entry and the ComController shall 
	-- respond by downloading the specified image via FTP.
        --
        -- -- -- -- -- -- -- -- -- -- -- -- -- -- -- -- -- -- -- -- -- -- -- --
        -- -- -- -- -- -- -- -- -- -- -- -- -- -- -- -- -- -- -- -- -- -- -- --

        com21HcxImageListTable OBJECT-TYPE
                SYNTAX  SEQUENCE OF HcxImageListEntry
                MAX-ACCESS  not-accessible
                STATUS  current
                DESCRIPTION
                        "table of all ComController and ComPort images loaded 
			 on the CC."
                ::= { com21HcxImageListGroup 1 }
 
        com21HcxImageListEntry OBJECT-TYPE
                SYNTAX  HcxImageListEntry
                MAX-ACCESS  not-accessible
                STATUS  current
                DESCRIPTION "."
                INDEX { hcxImageId }
                ::= { com21HcxImageListTable 1 }
 
        HcxImageListEntry ::= SEQUENCE {
		hcxImageId		INTEGER,
                hcxImageType            INTEGER,
		hcxImageFilename	DisplayString,
                hcxSwRevision	        DisplayString,
                hcxHwRevision           DisplayString,
                hcxFwRevision           DisplayString,
		hcxImageState		INTEGER }

        hcxImageId OBJECT-TYPE
                SYNTAX INTEGER (1..4294967295)
                MAX-ACCESS read-only
                STATUS current
                DESCRIPTION "
                        contains image list reference."
                ::= { com21HcxImageListEntry 1 }

        hcxImageType OBJECT-TYPE
                SYNTAX INTEGER {
				hcxCC (1),
				hcxTx (2),
				hcxRx (3),
				hcxEth10baseT (4),
				hcxEth100baseT (5),
				hcxTele (6),
				stu (7),
				stu3com (8),
				hcxRxm (9),
				atmlSwitch (10),
				compCfg (11),
				compSwitch (12),
				hcxOc3 (13)  }
                MAX-ACCESS read-only
                STATUS current
                DESCRIPTION "
                        contains image type."
                ::= { com21HcxImageListEntry 2 }

        hcxImageState OBJECT-TYPE
                SYNTAX INTEGER { active(1), alternate(2) }
                MAX-ACCESS read-only
                STATUS current
                DESCRIPTION "
                        this attribute specifies the state of an image.
			An image is either part of the active set of
			ComController and ComPort images, or is a part
			of the alternate set."
                ::= { com21HcxImageListEntry 7 }

        hcxImageFilename OBJECT-TYPE
                SYNTAX DisplayString (SIZE(64))
                MAX-ACCESS read-only
                STATUS current
                DESCRIPTION "
                        contains image filename. This shall be used to 
			retrieve the image from the boot server."
                ::= { com21HcxImageListEntry 3 }

        hcxSwRevision OBJECT-TYPE
                SYNTAX DisplayString (SIZE(32))
                MAX-ACCESS read-only
                STATUS current
                DESCRIPTION "
                        contains image software revision."
                ::= { com21HcxImageListEntry 4 }

        hcxHwRevision OBJECT-TYPE
                SYNTAX DisplayString (SIZE(32))
                MAX-ACCESS read-only
                STATUS current
                DESCRIPTION "
                        contains hardware revision supported by this image.
			Note that in the future, we may define a range of 
			hardware revisions supported."
                ::= { com21HcxImageListEntry 5 }

        hcxFwRevision OBJECT-TYPE
                SYNTAX DisplayString (SIZE(32))
                MAX-ACCESS read-only
                STATUS current
                DESCRIPTION "
                        contains firmware boot revision supported by this
			image. Note that in the future, we may define a 
			range of hardware revisions supported."
                ::= { com21HcxImageListEntry 6 }



        -- -- -- -- -- -- -- -- -- -- -- -- -- -- -- -- -- -- -- -- -- -- -- --
        -- -- -- -- -- -- -- -- -- -- -- -- -- -- -- -- -- -- -- -- -- -- -- --
        --
        -- com21HcxDbControlGroup
        --
        -- used to manage the database revisions.
        --
        -- -- -- -- -- -- -- -- -- -- -- -- -- -- -- -- -- -- -- -- -- -- -- --
        -- -- -- -- -- -- -- -- -- -- -- -- -- -- -- -- -- -- -- -- -- -- -- --
 
        hcxDbAction OBJECT-TYPE
                SYNTAX INTEGER {
				nil(1),
				saveDb(2),
				deleteSavedDb(3),
				deletePeriodicDb(4),
				revertToPeriodicDb(5),
				revertToSavedDb(6) }
                MAX-ACCESS read-write
                STATUS current 
                DESCRIPTION "  
                        This attribute is used to control various database
			actions. saveDb causes the present active database
			to be saved to disk. This will overwrite any previously
			saved database. revertToPeriodicDb causes the
			periodically saved database to become the active
			database. revertToSavedDb causes the user saved
			database to become the active database. deleteSavedDb
			and deletePeriodicDb simply delete the current
			saved and periodic database respectively. In the case
			of these last two options, the CC shall reboot."
                ::= { com21HcxDbControlGroup 1 }

        hcxDbActionResult OBJECT-TYPE
                SYNTAX INTEGER {
                                inprogress(1),
                                success(2),
                                diskFailure(3),
                                noDatabaseFound(4),
                                invalidDatabase(5) }
                MAX-ACCESS read-only
                STATUS current
                DESCRIPTION "
                        This attribute contains the result of the last
                        hcxDbAction."
                ::= { com21HcxDbControlGroup 2 }

        hcxDbActionComplete NOTIFICATION-TYPE
                OBJECTS { hcxAlmSeverity, hcxEventLogTime,
                            hcxDbActionResult }
                STATUS current
                DESCRIPTION "
                        this notification is generated whenever the CC
                        completes the database action. This an event with
                        no clear condition. Only severity is WARNING."
                ::= { com21Traps 19 }
 
        hcxDbBackupPeriod OBJECT-TYPE
                SYNTAX INTEGER  (0..24)
                MAX-ACCESS read-write 
                STATUS current  
                DESCRIPTION "   
                        the period, in hours, at which the database will 
			be automatically saved on the disk. 0 will
			disable the auto backup. Default 24." 
                ::= { com21HcxDbControlGroup 3 }

 

        -- -- -- -- -- -- -- -- -- -- -- -- -- -- -- -- -- -- -- -- -- -- -- --
        -- -- -- -- -- -- -- -- -- -- -- -- -- -- -- -- -- -- -- -- -- -- -- --
        --
        -- com21HcxServTypeGroup
        --
        -- defines all Service Types. These define the various categories
        -- of upstream and downstream bandwidth service available to a
	-- user.
        --
        -- -- -- -- -- -- -- -- -- -- -- -- -- -- -- -- -- -- -- -- -- -- -- --
        -- -- -- -- -- -- -- -- -- -- -- -- -- -- -- -- -- -- -- -- -- -- -- --
 
        com21HcxServTypeTable OBJECT-TYPE
                SYNTAX  SEQUENCE OF HcxServTypeEntry
                MAX-ACCESS  not-accessible
                STATUS  current
                DESCRIPTION
                        "TBD."
                ::= { com21HcxServTypeGroup 1 }
 
        com21HcxServTypeEntry OBJECT-TYPE
                SYNTAX  HcxServTypeEntry
                MAX-ACCESS  not-accessible
                STATUS  current
                DESCRIPTION "."
                INDEX { hcxServiceTypeId }
                ::= { com21HcxServTypeTable 1 }
 
        HcxServTypeEntry ::= SEQUENCE {
                hcxServiceTypeId	Integer32,
                hcxServTypeDesc         DisplayString,
                hcxDnStrmType           INTEGER,
                hcxDnStrmRate           INTEGER,
		hcxUpStrmType           INTEGER,
                hcxUpStrmMinRate	INTEGER,
		hcxUpStrmMaxRate        INTEGER,
		hcxServTypeDelete	INTEGER }
 
        hcxServiceTypeId OBJECT-TYPE
                SYNTAX Integer32
                MAX-ACCESS read-only
                STATUS current
                DESCRIPTION "
                        contains service type id."
                ::= { com21HcxServTypeEntry 1 }

        hcxServTypeDesc OBJECT-TYPE 
                SYNTAX DisplayString (SIZE (32))
                MAX-ACCESS read-write
                STATUS current 
                DESCRIPTION "  
                        contains service type description string. This
                        string must be unique."
                ::= { com21HcxServTypeEntry 2 } 

	hcxDnStrmType OBJECT-TYPE
                SYNTAX INTEGER { cbr (1), ondemand (2) }
                MAX-ACCESS read-write
                STATUS current
                DESCRIPTION "
                        defines CBR or ondemand (UBR) traffic in the
			downstream direction. Default is ondemand."
                ::= { com21HcxServTypeEntry 3 }

	hcxDnStrmRate OBJECT-TYPE
                SYNTAX INTEGER (0..11560000)
                MAX-ACCESS read-write
                STATUS current
                DESCRIPTION "
                        peak bits per second in the downstream direction. 
			Policing/shaping of this attribute is the 
			responsibility of the appropriate Ethernet
                        card. Setting this value to 0 will have the
                        effect of stopping downstream traffic."
                ::= { com21HcxServTypeEntry 4 }

        hcxUpStrmType OBJECT-TYPE
                SYNTAX INTEGER { cbr (1), ondemand (2) }
                MAX-ACCESS read-write
                STATUS current
                DESCRIPTION "
                        defines CBR or ondemand in the upstream direction. 
			This attribute controls the type of minimum
			cell traffic. Default is ondemand."
                ::= { com21HcxServTypeEntry 5 }
 
        hcxUpStrmMinRate OBJECT-TYPE
                SYNTAX INTEGER (0..1650000)
                MAX-ACCESS read-write
                STATUS current
                DESCRIPTION "
                        bits per second in the upstream direction. 
                        Policing/shaping of this attribute is the 
                        responsibility of the appropriate RX card."
                ::= { com21HcxServTypeEntry 6 }
 
        hcxUpStrmMaxRate OBJECT-TYPE
                SYNTAX INTEGER (0..1650000)
                MAX-ACCESS read-write
                STATUS current
                DESCRIPTION "
                        peak bits per second in the upstream direction. 
			This is a best-effort rate. Policing/shaping 
			of this attribute is the responsibility of the 
			appropriate RX card."
                ::= { com21HcxServTypeEntry 7 }
 
	hcxServTypeDelete OBJECT-TYPE 
                SYNTAX INTEGER { nil (1), execute (2) }
                MAX-ACCESS read-create
                STATUS current
                DESCRIPTION "
                        The ComController Service Type Delete is an
                        active-value. The setting of this value to execute(2)
                        causes the multicast list entry to be deleted."
                ::= { com21HcxServTypeEntry 8 }



        -- -- -- -- -- -- -- -- -- -- -- -- -- -- -- -- -- -- -- -- -- -- -- --
        -- -- -- -- -- -- -- -- -- -- -- -- -- -- -- -- -- -- -- -- -- -- -- --
        --
        -- com21HcxBootControlGroup
        --
        -- tbd
        --
        -- -- -- -- -- -- -- -- -- -- -- -- -- -- -- -- -- -- -- -- -- -- -- --
        -- -- -- -- -- -- -- -- -- -- -- -- -- -- -- -- -- -- -- -- -- -- -- --
 
        hcxFileTransProt OBJECT-TYPE
                SYNTAX INTEGER { ftp (1), tftp (2) }
                MAX-ACCESS read-write
                STATUS current
                DESCRIPTION "
                        specifies the type of protocol used for file
                        transfer. i.e. for config_db and images. This
                        information is stored in NVRAM. Note that a
                        upon boot, if there is no valid CC image, an
                        TFTP will be attempted regardless of the setting
                        of this attribute. Default is ftp."
                ::= { com21HcxBootControlGroup 1 }
 
        hcxFileServerCntrl OBJECT-TYPE
                SYNTAX INTEGER { bootp (1), mibSpecified (2) }
                MAX-ACCESS read-only
                STATUS current
                DESCRIPTION "
                        specifies how the file server address is
                        obtained. This parameter is controlled by CC
                        Boot shell line. Can elect to use bootp or allow
                        the operator to explicitly specify. Note that if
                        this attribute is set to mibSpecified then no
                        bootp should be generated by the boot or runtime
                        code. This information is stored in NVRAM. Default
                        is bootp."
                ::= { com21HcxBootControlGroup 2 }
 
        hcxImageServerIpAddr OBJECT-TYPE
                SYNTAX IpAddress
                MAX-ACCESS read-write
                STATUS current
                DESCRIPTION "
                        IP address of the image file server. This attribute
                        is writeable only if hcxFileServerCntrl is set to
                        mibSpecified. Otherwise it is a read-only attribute
                        detailing the IP address returned by bootp. This
                        attribute is held in NVRAM. Default is 0.0.0.0."
                ::= { com21HcxBootControlGroup 3 }
 
        hcxImageServerPath OBJECT-TYPE
                SYNTAX DisplayString (SIZE(32))
                MAX-ACCESS read-write
                STATUS current
                DESCRIPTION "
                        specifies path to the image files. This attribute
                        is writeable only  if hcxFileServerCntrl is set to
                        mibSpecified. Otherwise it is a read-only attribute
                        detailing the path returned by bootp. This attribute 
			is held in NVRAM. Default is null string."
                ::= { com21HcxBootControlGroup 4 }

         hcxImageServerLogin OBJECT-TYPE
                SYNTAX DisplayString (SIZE(16))
                MAX-ACCESS read-write
                STATUS current
                DESCRIPTION "
                        specifies a login to the image server. This attribute
                        is only applicable if hcxFileServerCntrl is set to
                        mibSpecified and hcxFileTransProt is set to ftp. This
                        attribute is held in NVRAM. Default is ftp."
                ::= { com21HcxBootControlGroup 5 }

         hcxImageServerPassword OBJECT-TYPE
                SYNTAX DisplayString (SIZE(16))
                MAX-ACCESS read-write
                STATUS current
                DESCRIPTION "
                        specifies a password to the image server. This
                        attribute is only applicable if hcxFileServerCntrl
                        is set to mibSpecified and hcxFileTransProt is set
                        to ftp. This attribute is held in NVRAM. Default is
                        anonymous."
                ::= { com21HcxBootControlGroup 6 }

         hcxDatabaseServerIpAddr OBJECT-TYPE
                SYNTAX IpAddress
                MAX-ACCESS read-write
                STATUS current
                DESCRIPTION "
                        IP address of the server on which to save and
                        retrieve the config database. This attribute is
                        only applicable if hcxFileServerCntrl is set to
                        mibSpecified. Default is 0.0.0.0."
                ::= { com21HcxBootControlGroup 7 }

        hcxDatabaseServerPath OBJECT-TYPE
                SYNTAX DisplayString (SIZE(32))
                MAX-ACCESS read-write
                STATUS current
                DESCRIPTION "
                        specifies path and the name of the config
                        database file. This attribute is only applicable
                        if hcxFileServerCntrl is set to mibSpecified.
                        Default is null string."
                ::= { com21HcxBootControlGroup 8 }

         hcxDatabaseServerLogin OBJECT-TYPE
                SYNTAX DisplayString (SIZE(16))
                MAX-ACCESS read-write
                STATUS current
                DESCRIPTION "
                        specifies a login to the Database server. This
                        attribute is only applicable if hcxFileServerCntrl
                        is set to mibSpecified and hcxFileTransProt is set
                        to ftp. Default is ftp."
                ::= { com21HcxBootControlGroup 9 }

         hcxDatabaseServerPassword OBJECT-TYPE
                SYNTAX DisplayString (SIZE(16))
                MAX-ACCESS read-write
                STATUS current
                DESCRIPTION "
                        specifies a password to the Database server. This
                        attribute is only applicable if hcxFileServerCntrl
                        is set to mibSpecified and hcxFileTransProt is set
                        to ftp. Default is anonymous."
                ::= { com21HcxBootControlGroup 10 }


 
END
