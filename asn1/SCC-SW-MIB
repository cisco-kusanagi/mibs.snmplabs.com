-- ******************************************************************
--           Secure Computing Corporation Enterprise MIB
-- ******************************************************************
--
-- Title		SCC-SW-MIB
-- Purpose:		This MIB defines SCC specific objects for the
--                      Sidewinder systems. 
-- Required MIBs	rfc-1155, scc-mib
-- Revision:		1.2
-- Date:		Oct. 27, 1997
--
-- SCC Support Contact:	1-800-700-8328
-- 			support@sctc.com
--
-- Version Description: 
-- 		v1.0:	Initial version of this MIB module.
--              v1.1:   Fixed some errors.  
--              v1.2:   Fixed additional errors found by SMICng.
--              v1.3:   Defined a new trap for IPSEC.


SCC-SW-MIB DEFINITIONS ::= BEGIN

   IMPORTS
--      enterprises, Counter, IpAddress,
        Counter, IpAddress,
        TimeTicks, Gauge          FROM RFC1155-SMI
        OBJECT-TYPE               FROM RFC-1212
        TRAP-TYPE                 FROM RFC-1215
        DisplayString,
        sysDescr, sysUpTime,
        PhysAddress		  FROM RFC1213-MIB
        sccMibSw, sccSidewinder   FROM SCC-MIB;



-- 
-- The Sidewinder specific objects are arranged into the following groups:
-- 

--    Proxy 
--    Burb
--    BurbedMib2
--    Trap


          swProxy        OBJECT IDENTIFIER ::= { sccMibSw 5 }
          swBurb         OBJECT IDENTIFIER ::= { sccMibSw 6 }
          swBurbedMib2   OBJECT IDENTIFIER ::= { sccMibSw 7 }
          swTrap         OBJECT IDENTIFIER ::= { sccMibSw 10 }


--
--   Proxy group  
--            
--     proxy table table.
--


          swProxyTable OBJECT-TYPE
              SYNTAX  SEQUENCE OF SwProxyEntry
              ACCESS  not-accessible
              STATUS  mandatory
              DESCRIPTION
                      "A list of proxy entries."
              ::= { swProxy 1 }

          swProxyEntry OBJECT-TYPE
              SYNTAX  SwProxyEntry
              ACCESS  not-accessible
              STATUS  mandatory
              DESCRIPTION
                      "An entry containing objects of a proxy."
              INDEX   { swProxyIndex } 
              ::= { swProxyTable 1 }

          SwProxyEntry ::=
              SEQUENCE {
                  swProxyIndex
                      INTEGER,
                  swProxyName
                      DisplayString,
                  swProxyAdminStatus
                      INTEGER,
                  swProxyOperStatus
                      INTEGER
               }


          swProxyIndex OBJECT-TYPE
              SYNTAX  INTEGER
              ACCESS  read-only
              STATUS  mandatory
              DESCRIPTION
                      "The index of a proxy entry in the proxy table."
              ::= { swProxyEntry 1 }

          swProxyName OBJECT-TYPE
              SYNTAX  DisplayString (SIZE (0..255))
              ACCESS  read-only
              STATUS  mandatory
              DESCRIPTION
                      "The name of a proxy."
              ::= { swProxyEntry 2 }

          swProxyAdminStatus OBJECT-TYPE
              SYNTAX  INTEGER {
                          enabled(1), 
                          disabled(2)
                      }
              ACCESS  read-only
              STATUS  mandatory
              DESCRIPTION
                      "The configured status of a proxy."
              ::= { swProxyEntry 3 }

          swProxyOperStatus OBJECT-TYPE
              SYNTAX  INTEGER {
                          up(1),   
                          down(2)
                      }
              ACCESS  read-only
              STATUS  mandatory
              DESCRIPTION
                      "The current operational status of a proxy."
              ::= { swProxyEntry 4 }



--
--   Burb group 
--            
--      burb view table.
--

          swBurbTotal OBJECT-TYPE
              SYNTAX INTEGER
              ACCESS read-only
              STATUS mandatory 
              DESCRIPTION
                     "The total number of configured Burbs."
              ::= { swBurb 1 }

          swBurbViewTable OBJECT-TYPE
              SYNTAX  SEQUENCE OF SwBurbViewEntry
              ACCESS  not-accessible
              STATUS  mandatory
              DESCRIPTION
                      "A list of burb view community name entries."
              ::= { swBurb 2 }

          swBurbViewEntry OBJECT-TYPE
              SYNTAX  SwBurbViewEntry
              ACCESS  not-accessible
              STATUS  mandatory
              DESCRIPTION
                      "An entry containing objects of a burb view."
              INDEX   { swBurbIndex } 
              ::= { swBurbViewTable 1 }

          SwBurbViewEntry ::=
              SEQUENCE {
                  swBurbIndex 
                      INTEGER,
                  swBurbViewName
                      DisplayString
               }


          swBurbIndex OBJECT-TYPE
              SYNTAX INTEGER
              ACCESS read-only
              STATUS mandatory 
              DESCRIPTION
                     "The Burb Index."
              ::= { swBurbViewEntry 1 }

          swBurbViewName OBJECT-TYPE
              SYNTAX  DisplayString (SIZE (0..255))
              ACCESS  read-only
              STATUS  mandatory
              DESCRIPTION
                      "Community name for the viewing the burb related 
                       information."
              ::= { swBurbViewEntry 2 }


--
--    BurbedMib2 group   contains burb oriented information for
--
--                 Interfaces group
--                 Ip group
--                 Tcp group
--                 Udp group.

          swInterfaces    OBJECT IDENTIFIER ::= { swBurbedMib2 1 }
          swIp            OBJECT IDENTIFIER ::= { swBurbedMib2 2 }
          swTcp           OBJECT IDENTIFIER ::= { swBurbedMib2 3 }
          swUdp           OBJECT IDENTIFIER ::= { swBurbedMib2 4 }

--  Interfaces group

          swIfNumber OBJECT-TYPE
              SYNTAX  INTEGER
              ACCESS  read-only
              STATUS  mandatory
              DESCRIPTION
                      "The number of network interfaces (regardless of
                      their current state) present on this system."
              ::= { swInterfaces 1 }

--     the Interfaces table

          -- The Interfaces table contains information on the entity's
          -- interfaces.  Each interface is thought of as being
          -- attached to a `subnetwork'.  Note that this term should
          -- not be confused with `subnet' which refers to an
          -- addressing partitioning scheme used in the Internet suite
          -- of protocols.

          swIfTable OBJECT-TYPE
              SYNTAX  SEQUENCE OF SwIfEntry
              ACCESS  not-accessible
              STATUS  mandatory
              DESCRIPTION
                      "A list of interface entries.  The number of
                      entries is given by the value of ifNumber."
              ::= { swInterfaces 2 }

          swIfEntry OBJECT-TYPE
              SYNTAX  SwIfEntry
              ACCESS  not-accessible
              STATUS  mandatory
              DESCRIPTION
                      "An interface entry containing objects at the
                      subnetwork layer and below for a particular
                      interface."
              INDEX   { swIfBurbIndex, 
                        swIfIndex }
              ::= { swIfTable 1 }

          SwIfEntry ::=
              SEQUENCE {
                  swIfIndex
                      INTEGER,
                  swIfDescr
                      DisplayString,
                  swIfType
                      INTEGER,
                  swIfMtu
                      INTEGER,
                  swIfSpeed
                      Gauge,
                  swIfPhysAddress
                      PhysAddress,
                  swIfAdminStatus
                      INTEGER,
                  swIfOperStatus
                      INTEGER,
                  swIfLastChange
                      TimeTicks,
                  swIfInOctets
                      Counter,
                  swIfInUcastPkts
                      Counter,
                  swIfInNUcastPkts
                      Counter,
                  swIfInDiscards
                      Counter,
                  swIfInErrors
                      Counter,
                  swIfInUnknownProtos
                      Counter,
                  swIfOutOctets
                      Counter,
                  swIfOutUcastPkts
                      Counter,
                  swIfOutNUcastPkts
                      Counter,
                  swIfOutDiscards
                      Counter,
                  swIfOutErrors
                      Counter,
                  swIfOutQLen
                      Gauge,
                  swIfSpecific
                      OBJECT IDENTIFIER,
                  swIfBurbIndex
                      INTEGER
              }


          swIfIndex OBJECT-TYPE
              SYNTAX  INTEGER
              ACCESS  read-only
              STATUS  mandatory
              DESCRIPTION
                      "A unique value for each interface.  Its value
                      ranges between 1 and the value of ifNumber.  The
                      value for each interface must remain constant at
                      least from one re-initialization of the entity's
                      network management system to the next re-
                      initialization."
              ::= { swIfEntry 1 }

          swIfDescr OBJECT-TYPE
              SYNTAX  DisplayString (SIZE (0..255))
              ACCESS  read-only
              STATUS  mandatory
              DESCRIPTION
                      "A textual string containing information about the
                      interface.  This string should include the name of
                      the manufacturer, the product name and the version
                      of the hardware interface."
              ::= { swIfEntry 2 }

          swIfType OBJECT-TYPE
              SYNTAX  INTEGER {
                          other(1),          -- none of the following
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           -- T-1
                          e1(19),            -- european equiv. of T-1
                          basicISDN(20),
                          primaryISDN(21),   -- proprietary serial
                          propPointToPointSerial(22),
                          ppp(23),
                          softwareLoopback(24),
                          eon(25),            -- CLNP over IP [11]
                          ethernet-3Mbit(26),
                          nsip(27),           -- XNS over IP
                          slip(28),           -- generic SLIP
                          ultra(29),          -- ULTRA technologies
                          ds3(30),            -- T-3
                          sip(31),            -- SMDS
                          frame-relay(32)
                      }
              ACCESS  read-only
              STATUS  mandatory
              DESCRIPTION
                      "The type of interface, distinguished according to
                      the physical/link protocol(s) immediately `below'
                      the network layer in the protocol stack."
              ::= { swIfEntry 3 }

          swIfMtu OBJECT-TYPE
              SYNTAX  INTEGER
              ACCESS  read-only
              STATUS  mandatory
              DESCRIPTION
                      "The size of the largest datagram which can be
                      sent/received on the interface, specified in
                      octets.  For interfaces that are used for
                      transmitting network datagrams, this is the size
                      of the largest network datagram that can be sent
                      on the interface."
              ::= { swIfEntry 4 }

          swIfSpeed OBJECT-TYPE
              SYNTAX  Gauge
              ACCESS  read-only
              STATUS  mandatory
              DESCRIPTION
                      "An estimate of the interface's current bandwidth
                      in bits per second.  For interfaces which do not
                      vary in bandwidth or for those where no accurate
                      estimation can be made, this object should contain
                      the nominal bandwidth."
              ::= { swIfEntry 5 }

          swIfPhysAddress OBJECT-TYPE
              SYNTAX  PhysAddress
              ACCESS  read-only
              STATUS  mandatory
              DESCRIPTION
                      "The interface's address at the protocol layer
                      immediately `below' the network layer in the
                      protocol stack.  For interfaces which do not have
                      such an address (e.g., a serial line), this object
                      should contain an octet string of zero length."
              ::= { swIfEntry 6 }

          swIfAdminStatus OBJECT-TYPE
              SYNTAX  INTEGER {
                          up(1),       -- ready to pass packets
                          down(2),
                          testing(3)   -- in some test mode
                      }
              ACCESS  read-write
              STATUS  mandatory
              DESCRIPTION
                      "The desired state of the interface.  The
                      testing(3) state indicates that no operational
                      packets can be passed."
              ::= { swIfEntry 7 }

          swIfOperStatus OBJECT-TYPE
              SYNTAX  INTEGER {
                          up(1),       -- ready to pass packets
                          down(2),
                          testing(3)   -- in some test mode
                      }
              ACCESS  read-only
              STATUS  mandatory
              DESCRIPTION
                      "The current operational state of the interface.
                      The testing(3) state indicates that no operational
                      packets can be passed."
              ::= { swIfEntry 8 }

          swIfLastChange OBJECT-TYPE
              SYNTAX  TimeTicks
              ACCESS  read-only
              STATUS  mandatory
              DESCRIPTION
                      "The value of sysUpTime at the time the interface
                      entered its current operational state.  If the
                      current state was entered prior to the last re-
                      initialization of the local network management
                      subsystem, then this object contains a zero
                      value."
              ::= { swIfEntry 9 }

          swIfInOctets OBJECT-TYPE
              SYNTAX  Counter
              ACCESS  read-only
              STATUS  mandatory
              DESCRIPTION
                      "The total number of octets received on the
                      interface, including framing characters."
              ::= { swIfEntry 10 }

          swIfInUcastPkts OBJECT-TYPE
              SYNTAX  Counter
              ACCESS  read-only
              STATUS  mandatory
              DESCRIPTION
                      "The number of subnetwork-unicast packets
                      delivered to a higher-layer protocol."
              ::= { swIfEntry 11 }

          swIfInNUcastPkts OBJECT-TYPE
              SYNTAX  Counter
              ACCESS  read-only
              STATUS  mandatory
              DESCRIPTION
                      "The number of non-unicast (i.e., subnetwork-
                      broadcast or subnetwork-multicast) packets
                      delivered to a higher-layer protocol."
              ::= { swIfEntry 12 }

          swIfInDiscards OBJECT-TYPE
              SYNTAX  Counter
              ACCESS  read-only
              STATUS  mandatory
              DESCRIPTION
                      "The number of inbound packets which were chosen
                      to be discarded even though no errors had been
                      detected to prevent their being deliverable to a
                      higher-layer protocol.  One possible reason for
                      discarding such a packet could be to free up
                      buffer space."
              ::= { swIfEntry 13 }

          swIfInErrors OBJECT-TYPE
              SYNTAX  Counter
              ACCESS  read-only
              STATUS  mandatory
              DESCRIPTION
                      "The number of inbound packets that contained
                      errors preventing them from being deliverable to a
                      higher-layer protocol."
              ::= { swIfEntry 14 }

          swIfInUnknownProtos OBJECT-TYPE
              SYNTAX  Counter
              ACCESS  read-only
              STATUS  mandatory
              DESCRIPTION
                      "The number of packets received via the interface
                      which were discarded because of an unknown or
                      unsupported protocol."
              ::= { swIfEntry 15 }

          swIfOutOctets OBJECT-TYPE
              SYNTAX  Counter
              ACCESS  read-only
              STATUS  mandatory
              DESCRIPTION
                      "The total number of octets transmitted out of the
                      interface, including framing characters."
              ::= { swIfEntry 16 }

          swIfOutUcastPkts OBJECT-TYPE
              SYNTAX  Counter
              ACCESS  read-only
              STATUS  mandatory
              DESCRIPTION
                      "The total number of packets that higher-level
                      protocols requested be transmitted to a
                      subnetwork-unicast address, including those that
                      were discarded or not sent."
              ::= { swIfEntry 17 }

          swIfOutNUcastPkts OBJECT-TYPE
              SYNTAX  Counter
              ACCESS  read-only
              STATUS  mandatory
              DESCRIPTION
                      "The total number of packets that higher-level
                      protocols requested be transmitted to a non-
                      unicast (i.e., a subnetwork-broadcast or
                      subnetwork-multicast) address, including those
                      that were discarded or not sent."
              ::= { swIfEntry 18 }

          swIfOutDiscards OBJECT-TYPE
              SYNTAX  Counter
              ACCESS  read-only
              STATUS  mandatory
              DESCRIPTION
                      "The number of outbound packets which were chosen
                      to be discarded even though no errors had been
                      detected to prevent their being transmitted.  One
                      possible reason for discarding such a packet could
                      be to free up buffer space."
              ::= { swIfEntry 19 }

          swIfOutErrors OBJECT-TYPE
              SYNTAX  Counter
              ACCESS  read-only
              STATUS  mandatory
              DESCRIPTION
                      "The number of outbound packets that could not be
                      transmitted because of errors."
              ::= { swIfEntry 20 }

          swIfOutQLen OBJECT-TYPE
              SYNTAX  Gauge
              ACCESS  read-only
              STATUS  mandatory
              DESCRIPTION
                      "The length of the output packet queue (in
                      packets)."
              ::= { swIfEntry 21 }

          swIfSpecific OBJECT-TYPE
              SYNTAX  OBJECT IDENTIFIER
              ACCESS  read-only
              STATUS  mandatory
              DESCRIPTION
                      "A reference to MIB definitions specific to the
                      particular media being used to realize the
                      interface.  For example, if the interface is
                      realized by an ethernet, then the value of this
                      object refers to a document defining objects
                      specific to ethernet.  If this information is not
                      present, its value should be set to the OBJECT
                      IDENTIFIER { 0 0 }, which is a syntatically valid
                      object identifier, and any conformant
                      implementation of ASN.1 and BER must be able to
                      generate and recognize this value."
              ::= { swIfEntry 22 }

          swIfBurbIndex OBJECT-TYPE
              SYNTAX  INTEGER
--            ACCESS  not-accessible
              ACCESS  read-only
              STATUS  mandatory
              DESCRIPTION
                      "A unique value of the Sidewinder suburb index."
              ::= { swIfEntry 23 }


--  IP group

--    IP address table

          -- The IP address table contains this entity's IP addressing
          -- information.

          swIpAddrTable OBJECT-TYPE
              SYNTAX  SEQUENCE OF SwIpAddrEntry
              ACCESS  not-accessible
              STATUS  mandatory
              DESCRIPTION
                      "The table of addressing information relevant to
                      this entity's IP addresses."
              ::= { swIp 1 }

          swIpAddrEntry OBJECT-TYPE
              SYNTAX  SwIpAddrEntry
              ACCESS  not-accessible
              STATUS  mandatory
              DESCRIPTION
                      "The addressing information for one of this
                      entity's IP addresses."
              INDEX   { swIpAdEntBurbIndex, 
                        swIpAdEntAddr }
              ::= { swIpAddrTable 1 }

          SwIpAddrEntry ::=
              SEQUENCE {
                  swIpAdEntAddr
                      IpAddress,
                  swIpAdEntIfIndex
                      INTEGER,
                  swIpAdEntNetMask
                      IpAddress,
                  swIpAdEntBcastAddr
                      INTEGER,
                  swIpAdEntReasmMaxSize
                      INTEGER (0..65535),
                  swIpAdEntBurbIndex
                      INTEGER

              }

          swIpAdEntAddr OBJECT-TYPE
              SYNTAX  IpAddress
              ACCESS  read-only
              STATUS  mandatory
              DESCRIPTION
                      "The IP address to which this entry's addressing
                      information pertains."
              ::= { swIpAddrEntry 1 }

          swIpAdEntIfIndex OBJECT-TYPE
              SYNTAX  INTEGER
              ACCESS  read-only
              STATUS  mandatory
              DESCRIPTION
                      "The index value which uniquely identifies the
                      interface to which this entry is applicable.  The
                      interface identified by a particular value of this
                      index is the same interface as identified by the
                      same value of ifIndex."
              ::= { swIpAddrEntry 2 }

          swIpAdEntNetMask OBJECT-TYPE
              SYNTAX  IpAddress
              ACCESS  read-only
              STATUS  mandatory
              DESCRIPTION
                      "The subnet mask associated with the IP address of
                      this entry.  The value of the mask is an IP
                      address with all the network bits set to 1 and all
                      the hosts bits set to 0."
              ::= { swIpAddrEntry 3 }

          swIpAdEntBcastAddr OBJECT-TYPE
              SYNTAX  INTEGER
              ACCESS  read-only
              STATUS  mandatory
              DESCRIPTION
                      "The value of the least-significant bit in the IP
                      broadcast address used for sending datagrams on
                      the (logical) interface associated with the IP
                      address of this entry.  For example, when the
                      Internet standard all-ones broadcast address is
                      used, the value will be 1.  This value applies to
                      both the subnet and network broadcasts addresses
                      used by the entity on this (logical) interface."
              ::= { swIpAddrEntry 4 }

          swIpAdEntReasmMaxSize OBJECT-TYPE
              SYNTAX  INTEGER (0..65535)
              ACCESS  read-only
              STATUS  mandatory
              DESCRIPTION
                      "The size of the largest IP datagram which this
                      entity can re-assemble from incoming IP fragmented
                      datagrams received on this interface."
              ::= { swIpAddrEntry 5 }

          swIpAdEntBurbIndex OBJECT-TYPE
              SYNTAX  INTEGER
--            ACCESS  not-accessible
              ACCESS  read-only
              STATUS  mandatory
              DESCRIPTION
                      "A unique value of the Sidewinder suburb index."
              ::= { swIpAddrEntry 6 }




--     IP routing table

          -- The IP routing table contains an entry for each route
          -- presently known to this entity.

          swIpRouteTable OBJECT-TYPE
              SYNTAX  SEQUENCE OF SwIpRouteEntry
              ACCESS  not-accessible
              STATUS  mandatory
              DESCRIPTION
                      "This entity's IP Routing table."
              ::= { swIp 2 }

          swIpRouteEntry OBJECT-TYPE
              SYNTAX  SwIpRouteEntry
              ACCESS  not-accessible
              STATUS  mandatory
              DESCRIPTION
                      "A route to a particular destination."
              INDEX   { swIpRouteBurbIndex,
                        swIpRouteDest }
              ::= { swIpRouteTable 1 }

          SwIpRouteEntry ::=
              SEQUENCE {
                  swIpRouteDest
                      IpAddress,
                  swIpRouteIfIndex
                      INTEGER,
                  swIpRouteMetric1
                      INTEGER,
                  swIpRouteMetric2
                      INTEGER,
                  swIpRouteMetric3
                      INTEGER,
                  swIpRouteMetric4
                      INTEGER,
                  swIpRouteNextHop
                      IpAddress,
                  swIpRouteType
                      INTEGER,
                  swIpRouteProto
                      INTEGER,
                  swIpRouteAge
                      INTEGER,
                  swIpRouteMask
                      IpAddress,
                  swIpRouteMetric5
                      INTEGER,
                  swIpRouteInfo
                      OBJECT IDENTIFIER,
                  swIpRouteBurbIndex
                      INTEGER
              }

          swIpRouteDest OBJECT-TYPE
              SYNTAX  IpAddress
              ACCESS  read-write
              STATUS  mandatory
              DESCRIPTION
                      "The destination IP address of this route.  An
                      entry with a value of 0.0.0.0 is considered a
                      default route.  Multiple routes to a single
                      destination can appear in the table, but access to
                      such multiple entries is dependent on the table-
                      access mechanisms defined by the network
                      management protocol in use."
              ::= { swIpRouteEntry 1 }

          swIpRouteIfIndex OBJECT-TYPE
              SYNTAX  INTEGER
              ACCESS  read-write
              STATUS  mandatory
              DESCRIPTION
                      "The index value which uniquely identifies the
                      local interface through which the next hop of this
                      route should be reached.  The interface identified
                      by a particular value of this index is the same
                      interface as identified by the same value of
                      ifIndex."
              ::= { swIpRouteEntry 2 }

          swIpRouteMetric1 OBJECT-TYPE
              SYNTAX  INTEGER
              ACCESS  read-write
              STATUS  mandatory
              DESCRIPTION
                      "The primary routing metric for this route.  The
                      semantics of this metric are determined by the
                      routing-protocol specified in the route's
                      ipRouteProto value.  If this metric is not used,
                      its value should be set to -1."
              ::= { swIpRouteEntry 3 }

          swIpRouteMetric2 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { swIpRouteEntry 4 }

          swIpRouteMetric3 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { swIpRouteEntry 5 }

          swIpRouteMetric4 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { swIpRouteEntry 6 }

          swIpRouteNextHop OBJECT-TYPE
              SYNTAX  IpAddress
              ACCESS  read-write
              STATUS  mandatory
              DESCRIPTION
                      "The IP address of the next hop of this route.
                      (In the case of a route bound to an interface
                      which is realized via a broadcast media, the value
                      of this field is the agent's IP address on that
                      interface.)"
              ::= { swIpRouteEntry 7 }

          swIpRouteType OBJECT-TYPE
              SYNTAX  INTEGER {
                          other(1),        -- none of the following

                          invalid(2),      -- an invalidated route

                                           -- route to directly
                          direct(3),       -- connected (sub-)network

                                           -- route to a non-local
                          indirect(4)      -- host/network/sub-network
                      }
              ACCESS  read-write
              STATUS  mandatory
              DESCRIPTION
                      "The type of route.  Note that the values
                      direct(3) and indirect(4) refer to the notion of
                      direct and indirect routing in the IP
                      architecture.

                      Setting this object to the value invalid(2) has
                      the effect of invalidating the corresponding entry
                      in the ipRouteTable object.  That is, it
                      effectively dissasociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { swIpRouteEntry 8 }

          swIpRouteProto OBJECT-TYPE
              SYNTAX  INTEGER {
                          other(1),       -- none of the following

                                          -- non-protocol information,
                                          -- e.g., manually configured
                          local(2),       -- entries

                                          -- set via a network
                          netmgmt(3),     -- management protocol

                                          -- obtained via ICMP,
                          icmp(4),        -- e.g., Redirect

                                          -- the remaining values are
                                          -- all gateway routing
                                          -- protocols
                          egp(5),
                          ggp(6),
                          hello(7),
                          rip(8),
                          is-is(9),
                          es-is(10),
                          ciscoIgrp(11),
                          bbnSpfIgp(12),
                          ospf(13),
                          bgp(14)
                      }
              ACCESS  read-only
              STATUS  mandatory
              DESCRIPTION
                      "The routing mechanism via which this route was
                      learned.  Inclusion of values for gateway routing
                      protocols is not intended to imply that hosts
                      should support those protocols."
              ::= { swIpRouteEntry 9 }

          swIpRouteAge OBJECT-TYPE
              SYNTAX  INTEGER
              ACCESS  read-write
              STATUS  mandatory
              DESCRIPTION
                      "The number of seconds since this route was last
                      updated or otherwise determined to be correct.
                      Note that no semantics of `too old' can be implied
                      except through knowledge of the routing protocol
                      by which the route was learned."
              ::= { swIpRouteEntry 10 }

          swIpRouteMask OBJECT-TYPE
              SYNTAX  IpAddress
              ACCESS  read-write
              STATUS  mandatory
              DESCRIPTION
                      "Indicate the mask to be logical-ANDed with the
                      destination address before being compared to the
                      value in the ipRouteDest field.  For those systems
                      that do not support arbitrary subnet masks, an
                      agent constructs the value of the ipRouteMask by
                      determining whether the value of the correspondent
                      ipRouteDest field belong to a class-A, B, or C
                      network, and then using one of:

                           mask           network
                           255.0.0.0      class-A
                           255.255.0.0    class-B
                           255.255.255.0  class-C

                      If the value of the ipRouteDest is 0.0.0.0 (a
                      default route), then the mask value is also
                      0.0.0.0.  It should be noted that all IP routing
                      subsystems implicitly use this mechanism."
              ::= { swIpRouteEntry 11 }

          swIpRouteMetric5 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { swIpRouteEntry 12 }

          swIpRouteInfo OBJECT-TYPE
              SYNTAX  OBJECT IDENTIFIER
              ACCESS  read-only
              STATUS  mandatory
              DESCRIPTION
                      "A reference to MIB definitions specific to the
                      particular routing protocol which is responsible
                      for this route, as determined by the value
                      specified in the route's ipRouteProto value.  If
                      this information is not present, its value should
                      be set to the OBJECT IDENTIFIER { 0 0 }, which is
                      a syntatically valid object identifier, and any
                      conformant implementation of ASN.1 and BER must be
                      able to generate and recognize this value."
              ::= { swIpRouteEntry 13 }

          swIpRouteBurbIndex OBJECT-TYPE
              SYNTAX  INTEGER
--            ACCESS  not-accessible
              ACCESS  read-only
              STATUS  mandatory
              DESCRIPTION
                      "A unique value of the Sidewinder suburb index."
              ::= { swIpRouteEntry 14 }


-- TCP group

--     TCP Connection table

          -- The TCP connection table contains information about this
          -- entity's existing TCP connections.

          swTcpConnTable OBJECT-TYPE
              SYNTAX  SEQUENCE OF SwTcpConnEntry
              ACCESS  not-accessible
              STATUS  mandatory
              DESCRIPTION
                      "A table containing TCP connection-specific
                      information."
              ::= { swTcp 1 }

          swTcpConnEntry OBJECT-TYPE
              SYNTAX  SwTcpConnEntry
              ACCESS  not-accessible
              STATUS  mandatory
              DESCRIPTION
                      "Information about a particular current TCP
                      connection.  An object of this type is transient,
                      in that it ceases to exist when (or soon after)
                      the connection makes the transition to the CLOSED
                      state."
              INDEX   { swTcpConnBurbIndex,
                        swTcpConnLocalAddress,
                        swTcpConnLocalPort,
                        swTcpConnRemAddress,
                        swTcpConnRemPort }
              ::= { swTcpConnTable 1 }

          SwTcpConnEntry ::=
              SEQUENCE {
                  swTcpConnState
                      INTEGER,
                  swTcpConnLocalAddress
                      IpAddress,
                  swTcpConnLocalPort
                      INTEGER (0..65535),
                  swTcpConnRemAddress
                      IpAddress,
                  swTcpConnRemPort
                      INTEGER (0..65535),
                  swTcpConnBurbIndex
                      INTEGER

              }

          swTcpConnState OBJECT-TYPE
              SYNTAX  INTEGER {
                          closed(1),
                          listen(2),
                          synSent(3),
                          synReceived(4),
                          established(5),
                          finWait1(6),
                          finWait2(7),
                          closeWait(8),
                          lastAck(9),
                          closing(10),
                          timeWait(11),
                          deleteTCB(12)
                      }
              ACCESS  read-write
              STATUS  mandatory
              DESCRIPTION
                      "The state of this TCP connection.

                      The only value which may be set by a management
                      station is deleteTCB(12).  Accordingly, it is
                      appropriate for an agent to return a `badValue'
                      response if a management station attempts to set
                      this object to any other value.

                      If a management station sets this object to the
                      value deleteTCB(12), then this has the effect of
                      deleting the TCB (as defined in RFC 793) of the
                      corresponding connection on the managed node,
                      resulting in immediate termination of the
                      connection.

                      As an implementation-specific option, a RST
                      segment may be sent from the managed node to the
                      other TCP endpoint (note however that RST segments
                      are not sent reliably)."
              ::= { swTcpConnEntry 1 }

          swTcpConnLocalAddress OBJECT-TYPE
              SYNTAX  IpAddress
              ACCESS  read-only
              STATUS  mandatory
              DESCRIPTION
                      "The local IP address for this TCP connection.  In
                      the case of a connection in the listen state which
                      is willing to accept connections for any IP
                      interface associated with the node, the value
                      0.0.0.0 is used."
              ::= { swTcpConnEntry 2 }

          swTcpConnLocalPort OBJECT-TYPE
              SYNTAX  INTEGER (0..65535)
              ACCESS  read-only
              STATUS  mandatory
              DESCRIPTION
                      "The local port number for this TCP connection."
              ::= { swTcpConnEntry 3 }

          swTcpConnRemAddress OBJECT-TYPE
              SYNTAX  IpAddress
              ACCESS  read-only
              STATUS  mandatory
              DESCRIPTION
                      "The remote IP address for this TCP connection."
              ::= { swTcpConnEntry 4 }

          swTcpConnRemPort OBJECT-TYPE
              SYNTAX  INTEGER (0..65535)
              ACCESS  read-only
              STATUS  mandatory
              DESCRIPTION
                      "The remote port number for this TCP connection."
              ::= { swTcpConnEntry 5 }

          swTcpConnBurbIndex OBJECT-TYPE
              SYNTAX  INTEGER
--            ACCESS  not-accessible
              ACCESS  read-only
              STATUS  mandatory
              DESCRIPTION
                      "A unique value of the Sidewinder suburb index."
              ::= { swTcpConnEntry 6 }



--  UDP group

--    UDP Listener table

          -- The UDP listener table contains information about this
          -- entity's UDP end-points on which a local application is
          -- currently accepting datagrams.

          swUdpTable OBJECT-TYPE
              SYNTAX  SEQUENCE OF SwUdpEntry
              ACCESS  not-accessible
              STATUS  mandatory
              DESCRIPTION
                      "A table containing UDP listener information."
              ::= { swUdp 1 }

          swUdpEntry OBJECT-TYPE
              SYNTAX  SwUdpEntry
              ACCESS  not-accessible
              STATUS  mandatory
              DESCRIPTION
                      "Information about a particular current UDP
                      listener."
              INDEX   { swUdpBurbIndex,
                        swUdpLocalAddress, 
                        swUdpLocalPort }
              ::= { swUdpTable 1 }

          SwUdpEntry ::=
              SEQUENCE {
                  swUdpLocalAddress
                      IpAddress,
                  swUdpLocalPort
                      INTEGER (0..65535),
                  swUdpBurbIndex
                      INTEGER

              }

          swUdpLocalAddress OBJECT-TYPE
              SYNTAX  IpAddress
              ACCESS  read-only
              STATUS  mandatory
              DESCRIPTION
                      "The local IP address for this UDP listener.  In
                      the case of a UDP listener which is willing to
                      accept datagrams for any IP interface associated
                      with the node, the value 0.0.0.0 is used."
              ::= { swUdpEntry 1 }

          swUdpLocalPort OBJECT-TYPE
              SYNTAX  INTEGER (0..65535)
              ACCESS  read-only
              STATUS  mandatory
              DESCRIPTION
                      "The local port number for this UDP listener."
              ::= { swUdpEntry 2 }

          swUdpBurbIndex OBJECT-TYPE
              SYNTAX  INTEGER
--            ACCESS  not-accessible
              ACCESS  read-only
              STATUS  mandatory
              DESCRIPTION
                      "A unique value of the Sidewinder suburb index."
              ::= { swUdpEntry 3 }



    -- ***************************************************************
    -- the Sidewinder SNMP Traps
    -- ***************************************************************

    --
    -- Textual Conventions
    --


	sccAuthenFailSrcIp	   OBJECT-TYPE
              SYNTAX               IpAddress
--            ACCESS               not-accessible
              ACCESS               read-only
              STATUS               mandatory
              DESCRIPTION          "The IP address of the host which issued an
                                   unauthenticated get or set command"
              ::= { swTrap  1 }

	sccAuthenFailSrcCommName   OBJECT-TYPE
              SYNTAX               OCTET STRING
--            ACCESS               not-accessible
              ACCESS               read-only
              STATUS               mandatory
              DESCRIPTION          "The community name that comes with the 
                                   unauthenticated get or set command"
              ::= { swTrap  2 }

        swUser                     OBJECT-TYPE
              SYNTAX               DisplayString (SIZE (0..255))
--            ACCESS               not-accessible
              ACCESS               read-only
              STATUS  mandatory
              DESCRIPTION
                      ""
              ::= { swTrap  3 }

        swSRoleUser                OBJECT-TYPE
              SYNTAX               DisplayString (SIZE (0..255))
--            ACCESS               not-accessible
              ACCESS               read-only
              STATUS  mandatory
              DESCRIPTION
                      ""
              ::= { swTrap  4 }

        swSRoleName                 OBJECT-TYPE
              SYNTAX               DisplayString (SIZE (0..255))
--            ACCESS               not-accessible
              ACCESS               read-only
              STATUS  mandatory
              DESCRIPTION
                      ""
              ::= { swTrap  5 }


    -- ++++++++++++++++++++++++++++++
    -- *Standard* Traps
    -- ++++++++++++++++++++++++++++++
    --
    -- The standard traps are redefined here to describe
    -- the variables that come with the traps.
    --


          swColdStart            TRAP-TYPE
              ENTERPRISE         sccSidewinder
              VARIABLES          { sysDescr,
                                   sysUpTime }
              DESCRIPTION
                          "A coldStart trap signifies that the sending
                          protocol entity is reinitializing itself such
                          that the agent's configuration or the rotocol
                          entity implementation may be altered."
              ::= 0

          swAuthenticationFailure TRAP-TYPE
              ENTERPRISE        sccSidewinder
              VARIABLES        { sccAuthenFailSrcIp, 
                                 sccAuthenFailSrcCommName }
              DESCRIPTION
                          "An authenticationFailure trap signifies that
                          the sending protocol entity is the addressee
                          of a protocol message that is not properly
                          authenticated.  While implementations of the
                          SNMP must be capable of generating this trap,
                          they must also be capable of suppressing the
                          emission of such traps via an implementation-
                          specific mechanism."
              ::= 4




    -- ++++++++++++++++++++++++++++++
    -- Security Traps
    -- ++++++++++++++++++++++++++++++

          swNetTrafficThresholds TRAP-TYPE
              ENTERPRISE       sccSidewinder
              DESCRIPTION      "The trap occurs when the number of traffix audit
                                events written by the various proxies going 
                                through the Sidewinder exceeds a specified 
                                number in a specified time period."
              ::= 201

          swAttackAttempt        TRAP-TYPE
              ENTERPRISE       sccSidewinder
              DESCRIPTION      "The trap occurs when one of the services on the
                                Sidewinder sees a suspecious occurrence."
              ::= 202

          swTeViolation          TRAP-TYPE
              ENTERPRISE       sccSidewinder
              DESCRIPTION      "The trap occurs when an unauthorizeduser tries
                                to read, write, or execute a protected file on
                                the Sidewinder."
              ::= 203

          swAclThresholds        TRAP-TYPE
              ENTERPRISE       sccSidewinder
              DESCRIPTION      "The trap occurs when the number of times users
                                are denied access to services exceeds a  
                                specified number."
              ::= 204

          swBadProxyAuth         TRAP-TYPE
              ENTERPRISE       sccSidewinder
              DESCRIPTION      "The trap occurs when a user tries to get  
                                authenticated to the telnet or FTP proxy and he
                                or she enters invalid data."
              ::= 205

          swNetProbeAttempt      TRAP-TYPE
              ENTERPRISE       sccSidewinder
              DESCRIPTION      "The trap occurs when a user try to connect or 
                                send a message to a TCP or UDP port that either
                                has no service associated with it of is 
                                associated with an unsupported service."
              ::= 206

          swMailFilterFailure    TRAP-TYPE
	      ENTERPRISE       sccSidewinder
	      DESCRIPTION      "The trap occurs when the number of mail messages
				that failed the filter exceeds a specified 
				threshold in a specified time period."
              ::= 207

          swIPSECFailure        TRAP-TYPE
              ENTERPRISE       sccSidewinder
              DESCRIPTION      "The trap occurs when the IPSEC subsystem 
                               detects a failure in authentication or
                               encryption of network traffic.  This can be
                               caused by a number of things ranging from
                               key configuration errors, ISAKMP problems, 
                               interoperability issues, and network attacks."
              ::= 208

          swFAILOVEREvent      TRAP-TYPE
              ENTERPRISE       sccSidewinder
              DESCRIPTION      "The trap occurs when failover events occur.
                               These events include a master starting,
                               a slave becoming a master or releasing control,
                               or possible failover errors."
              ::= 209

END
