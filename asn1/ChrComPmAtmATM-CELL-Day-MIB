ChrComPmAtmATM-CELL-Day-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmAtm				FROM  Chromatis-MIB
	chrComIfifIndex					FROM  ChrComIfifTable-MIB
	TruthValue				FROM  ChrTyp-MIB
	Gauge32				FROM  SNMPv2-SMI;

-- chrComPmAtmATM-CELL-Day Table

chrComPmAtmATM-CELL-DayTable		OBJECT-TYPE
	SYNTAX		SEQUENCE OF ChrComPmAtmATM-CELL-DayEntry
	MAX-ACCESS	not-accessible
	STATUS		current
	DESCRIPTION
	""
	::= { chrComPmAtm 3}

chrComPmAtmATM-CELL-DayEntry		OBJECT-TYPE
	SYNTAX		ChrComPmAtmATM-CELL-DayEntry
	MAX-ACCESS	not-accessible
	STATUS		current
	DESCRIPTION
	""
	INDEX  {  chrComIfifIndex, chrComPmAtmDayNumber }

--DEFAULT  get-function-async  MNIL_GetRoutine
--DEFAULT  set-function-async  MNIL_SetRoutine
--DEFAULT  next-function-async MNIL_NextRoutine
--DEFAULT  test-function-async MNIL_TestRoutine
--DEFAULT  cookie "ATM-CELL-Day"
	::= { chrComPmAtmATM-CELL-DayTable  1 }

ChrComPmAtmATM-CELL-DayEntry  ::=
	SEQUENCE  {
	chrComPmAtmDayNumber		Unsigned32	(1..2),
	chrComPmAtmSuspectedInterval	TruthValue,
	chrComPmAtmElapsedTime		Unsigned32	(0..4294967295),
	chrComPmAtmSuppressedIntrvls	Gauge32			(0..4294967295),
	chrComPmAtmOCDS			Gauge32			(0..4294967295),
	chrComPmAtmHECCells		Gauge32			(0..4294967295),
	chrComPmAtmCorrectableHECCells	Gauge32			(0..4294967295),
	chrComPmAtmDiscardedCells		Gauge32			(0..4294967295),
	chrComPmAtmReceivedCells		Gauge32			(0..4294967295),
	chrComPmAtmTransmittedCells	Gauge32			(0..4294967295),
	chrComPmAtmDiscardedIngCells	Gauge32			(0..4294967295),
	chrComPmAtmDiscardedIngHighPrCells	Gauge32			(0..4294967295),
	chrComPmAtmDiscardedEgCells	Gauge32			(0..4294967295),
	chrComPmAtmDiscardedEgHighPrCells	Gauge32			(0..4294967295),
	chrComPmAtmDiscardedUPC		Gauge32			(0..4294967295),
	chrComPmAtmTaggedUPC		Gauge32			(0..4294967295),
	chrComPmAtmThresholdProfIndex	Unsigned32	(0..4294967295),
	chrComPmAtmResetPmCountersAction	TruthValue
}

chrComPmAtmDayNumber 	OBJECT-TYPE
	SYNTAX		Unsigned32	(1..2)
	MAX-ACCESS 	read-only
	STATUS 		current
	DESCRIPTION
	""
	::= { chrComPmAtmATM-CELL-DayEntry  1 }

chrComPmAtmSuspectedInterval 	OBJECT-TYPE
	SYNTAX		TruthValue
	MAX-ACCESS 	read-only
	STATUS 		current
	DESCRIPTION
	""
	::= { chrComPmAtmATM-CELL-DayEntry  2 }

chrComPmAtmElapsedTime 	OBJECT-TYPE
	SYNTAX		Unsigned32	(0..4294967295)
	MAX-ACCESS 	read-only
	STATUS 		current
	DESCRIPTION
	""
	::= { chrComPmAtmATM-CELL-DayEntry  3 }

chrComPmAtmSuppressedIntrvls 	OBJECT-TYPE
	SYNTAX		Gauge32			(0..4294967295)
	MAX-ACCESS 	read-only
	STATUS 		current
	DESCRIPTION
	""
	::= { chrComPmAtmATM-CELL-DayEntry  4 }

chrComPmAtmOCDS 	OBJECT-TYPE
	SYNTAX		Gauge32			(0..4294967295)
	MAX-ACCESS 	read-only
	STATUS 		current
	DESCRIPTION
	""
	::= { chrComPmAtmATM-CELL-DayEntry  5 }

chrComPmAtmHECCells 	OBJECT-TYPE
	SYNTAX		Gauge32			(0..4294967295)
	MAX-ACCESS 	read-only
	STATUS 		current
	DESCRIPTION
	""
	::= { chrComPmAtmATM-CELL-DayEntry  6 }

chrComPmAtmCorrectableHECCells 	OBJECT-TYPE
	SYNTAX		Gauge32			(0..4294967295)
	MAX-ACCESS 	read-only
	STATUS 		current
	DESCRIPTION
	""
	::= { chrComPmAtmATM-CELL-DayEntry  7 }

chrComPmAtmDiscardedCells 	OBJECT-TYPE
	SYNTAX		Gauge32			(0..4294967295)
	MAX-ACCESS 	read-only
	STATUS 		current
	DESCRIPTION
	""
	::= { chrComPmAtmATM-CELL-DayEntry  8 }

chrComPmAtmReceivedCells 	OBJECT-TYPE
	SYNTAX		Gauge32			(0..4294967295)
	MAX-ACCESS 	read-only
	STATUS 		current
	DESCRIPTION
	""
	::= { chrComPmAtmATM-CELL-DayEntry  9 }

chrComPmAtmTransmittedCells 	OBJECT-TYPE
	SYNTAX		Gauge32			(0..4294967295)
	MAX-ACCESS 	read-only
	STATUS 		current
	DESCRIPTION
	""
	::= { chrComPmAtmATM-CELL-DayEntry  10 }

chrComPmAtmDiscardedIngCells 	OBJECT-TYPE
	SYNTAX		Gauge32			(0..4294967295)
	MAX-ACCESS 	read-only
	STATUS 		current
	DESCRIPTION
	""
	::= { chrComPmAtmATM-CELL-DayEntry  11 }

chrComPmAtmDiscardedIngHighPrCells 	OBJECT-TYPE
	SYNTAX		Gauge32			(0..4294967295)
	MAX-ACCESS 	read-only
	STATUS 		current
	DESCRIPTION
	""
	::= { chrComPmAtmATM-CELL-DayEntry  12 }

chrComPmAtmDiscardedEgCells 	OBJECT-TYPE
	SYNTAX		Gauge32			(0..4294967295)
	MAX-ACCESS 	read-only
	STATUS 		current
	DESCRIPTION
	""
	::= { chrComPmAtmATM-CELL-DayEntry  13 }

chrComPmAtmDiscardedEgHighPrCells 	OBJECT-TYPE
	SYNTAX		Gauge32			(0..4294967295)
	MAX-ACCESS 	read-only
	STATUS 		current
	DESCRIPTION
	""
	::= { chrComPmAtmATM-CELL-DayEntry  14 }

chrComPmAtmDiscardedUPC 	OBJECT-TYPE
	SYNTAX		Gauge32			(0..4294967295)
	MAX-ACCESS 	read-only
	STATUS 		current
	DESCRIPTION
	""
	::= { chrComPmAtmATM-CELL-DayEntry  15 }

chrComPmAtmTaggedUPC 	OBJECT-TYPE
	SYNTAX		Gauge32			(0..4294967295)
	MAX-ACCESS 	read-only
	STATUS 		current
	DESCRIPTION
	""
	::= { chrComPmAtmATM-CELL-DayEntry  16 }

chrComPmAtmThresholdProfIndex 	OBJECT-TYPE
	SYNTAX		Unsigned32	(0..4294967295)
	MAX-ACCESS 	read-write
	STATUS 		current
	DESCRIPTION
	""
	::= { chrComPmAtmATM-CELL-DayEntry  17 }

chrComPmAtmResetPmCountersAction 	OBJECT-TYPE
	SYNTAX		TruthValue
	MAX-ACCESS 	read-write
	STATUS 		current
	DESCRIPTION
	""
	::= { chrComPmAtmATM-CELL-DayEntry  18 }


END
