-- @(#)WSCCS w/mibs-isdb.mib 1.4 3/18/98
Wellfleet-ISDB-MIB DEFINITIONS ::= BEGIN

    IMPORTS

      Counter
        FROM RFC1155-SMI
      OBJECT-TYPE
        FROM RFC-1212
      DisplayString
        FROM RFC1213-MIB
      wfIsdbGroup
        FROM Wellfleet-COMMON-MIB;

    wfIsdbCfgTable OBJECT-TYPE
        SYNTAX  SEQUENCE OF WfIsdbCfgEntry
        ACCESS  not-accessible
        STATUS  mandatory
        DESCRIPTION
                "Table of Isdb Config Objects"
        ::= { wfIsdbGroup 1 }

    wfIsdbCfgEntry OBJECT-TYPE
        SYNTAX  WfIsdbCfgEntry
        ACCESS  not-accessible
        STATUS  mandatory
        DESCRIPTION
                "An entry in the Isdb Config Table"
        INDEX   { wfIsdbCfgSlot,
                  wfIsdbCfgConnector }
        ::= { wfIsdbCfgTable 1 }

    WfIsdbCfgEntry ::= SEQUENCE {
            wfIsdbCfgDelete
                INTEGER,
            wfIsdbCfgDisable
                INTEGER,
            wfIsdbCfgState
                INTEGER,
            wfIsdbCfgSlot
                INTEGER,
            wfIsdbCfgConnector
                INTEGER,
            wfIsdbCfgCircuit
                INTEGER,
            wfIsdbCfgLogFilter
                INTEGER,
            wfIsdbCfgPollInterval
                INTEGER,
            wfIsdbCfgAutoRestart
                INTEGER,
            wfIsdbCfgAutoUld
                INTEGER,
            wfIsdbCfgUldVolume
                INTEGER,
            wfIsdbImageVersion
                INTEGER,
            wfIsdbImageDate
                DisplayString,
            wfIsdbDiagVersion
                OCTET STRING,
            wfIsdbDiagDate
                DisplayString

    }

    wfIsdbCfgDelete OBJECT-TYPE
        SYNTAX  INTEGER {
                    created(1),
                    deleted(2)
                }
        ACCESS  read-write
        STATUS  mandatory
        DESCRIPTION
                "Create/Delete parameter"
        DEFVAL  { created }
        ::= { wfIsdbCfgEntry 1 }

    wfIsdbCfgDisable OBJECT-TYPE
        SYNTAX  INTEGER {
                    enabled(1),
                    disabled(2)
                }
        ACCESS  read-write
        STATUS  mandatory
        DESCRIPTION
                "Enable/Disable parameter"
        DEFVAL  { enabled }
        ::= { wfIsdbCfgEntry 2 }

    wfIsdbCfgState OBJECT-TYPE
        SYNTAX  INTEGER {
                    up(1),
                    down(2),
                    init(3)
                }
        ACCESS  read-only
        STATUS  mandatory
        DESCRIPTION
               "Current state of the Async port on the I-SDB"
        DEFVAL  { down }
        ::= { wfIsdbCfgEntry 3 }

    wfIsdbCfgSlot OBJECT-TYPE
        SYNTAX  INTEGER
        ACCESS  read-only
        STATUS  mandatory
        DESCRIPTION
                "Instance ID Slot, filled in by the ISDB mib gate"
        ::= { wfIsdbCfgEntry 4 }

    wfIsdbCfgConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfIsdbCfgEntry 5 }

    wfIsdbCfgCircuit OBJECT-TYPE
        SYNTAX  INTEGER
        ACCESS  read-write
        STATUS  mandatory
        DESCRIPTION
                "Circuit number, filled in by the ISDB mib gate"
        ::= { wfIsdbCfgEntry 6 }

    wfIsdbCfgLogFilter OBJECT-TYPE
        SYNTAX  INTEGER
        ACCESS  read-write
        STATUS  mandatory
        DESCRIPTION
                "Log Filters"
        ::= { wfIsdbCfgEntry 7 }

    wfIsdbCfgPollInterval OBJECT-TYPE
        SYNTAX  INTEGER
        ACCESS  read-write
        STATUS  mandatory
        DESCRIPTION
                "Interval that ISDB gate polls ISDB"
        DEFVAL  { 5 }
        ::= { wfIsdbCfgEntry 8 }

    wfIsdbCfgAutoRestart OBJECT-TYPE
        SYNTAX  INTEGER
        ACCESS  read-write
        STATUS  mandatory
        DESCRIPTION
                "Auto restart of ISDB after crash"
        DEFVAL  { 1 }
        ::= { wfIsdbCfgEntry 9 }

    wfIsdbCfgAutoUld OBJECT-TYPE
        SYNTAX  INTEGER
        ACCESS  read-write
        STATUS  mandatory
        DESCRIPTION
                "Auto Up load memory image when ISDB crashes"
        DEFVAL  { 0 }
        ::= { wfIsdbCfgEntry 10 }

    wfIsdbCfgUldVolume OBJECT-TYPE
        SYNTAX  INTEGER
        ACCESS  read-write
        STATUS  mandatory
        DESCRIPTION
                "Volume to Up load memory image on ISDB crash"
        DEFVAL  { 1 }
        ::= { wfIsdbCfgEntry 11 }

    wfIsdbImageVersion OBJECT-TYPE
        SYNTAX  INTEGER 
        ACCESS  read-only
        STATUS  mandatory
        DESCRIPTION
               "Version of code running on the Isdb board"
        ::= { wfIsdbCfgEntry 12 }

    wfIsdbImageDate OBJECT-TYPE
        SYNTAX  DisplayString
        ACCESS  read-only
        STATUS  mandatory
        DESCRIPTION
                "The creation date of the Isdb Flash Image "
        ::= { wfIsdbCfgEntry 13 }

    wfIsdbDiagVersion OBJECT-TYPE
        SYNTAX  OCTET STRING
        ACCESS  read-only
        STATUS  mandatory
        DESCRIPTION
              "The revision level of the Diagnostic Flash. Major revision
               level is in the upper 2 bytes, minor revision level in the  
               lower 2 bytes."
        ::= { wfIsdbCfgEntry 14 }

    wfIsdbDiagDate OBJECT-TYPE
        SYNTAX  DisplayString
        ACCESS  read-only
        STATUS  mandatory
        DESCRIPTION
                "The creation date of the Diagnostic Flash"
        ::= { wfIsdbCfgEntry 15 }




    wfIsdbStatTable OBJECT-TYPE
        SYNTAX  SEQUENCE OF WfIsdbStatEntry
        ACCESS  not-accessible
        STATUS  mandatory
        DESCRIPTION
                "Table of Isdb Config Objects"
        ::= { wfIsdbGroup 2 }

    wfIsdbStatEntry OBJECT-TYPE
        SYNTAX  WfIsdbStatEntry
        ACCESS  not-accessible
        STATUS  mandatory
        DESCRIPTION
                "An entry in the Isdb Config Table"
        INDEX   { wfIsdbStatSlot,
                  wfIsdbStatConnector }
        ::= { wfIsdbStatTable 1 }

    WfIsdbStatEntry ::= SEQUENCE {
            wfIsdbStatState
                INTEGER,
            wfIsdbStatSlot
                INTEGER,
            wfIsdbStatConnector
                INTEGER,
            wfIsdbStatVersion
                INTEGER,
            wfIsdbStatCurrentConnCount
                Counter,
            wfIsdbStatTotalConnCount
                Counter,
            wfIsdbStatStartCount
                Counter,
            wfIsdbStatCpuIdleCurrent
                INTEGER,
	    wfIsdbStatCpuIdleTotal
                INTEGER,
            wfIsdbStatMemoryFree
                INTEGER,
	    wfIsdbStatMemoryLargestBlock
		INTEGER,
	    wfIsdbStatTaskCount
	        Counter,
	    wfIsdbStatMsgQueueLacks
		Counter,
	    wfIsdbStatHardwareTimeouts
	        Counter,
	    wfIsdbStatAlarmCount
		Counter,
	    wfIsdbStatAuthorUnknown
		Counter,
	    wfIsdbStatAv1Ints
	        Counter,
	    wfIsdbStatAv2Ints
                Counter,
            wfIsdbStatAv3Ints
                Counter,
            wfIsdbStatAv4Ints
                Counter,
            wfIsdbStatAv5Ints
                Counter,
            wfIsdbStatAv6Ints
                Counter,            
	    wfIsdbStatAv7Ints
                Counter,
	    wfIsdbStatScc3Ints
		Counter,
	    wfIsdbStatErrorInts
		Counter,
	    wfIsdbStatTimer1Ints
		Counter,
	    wfIsdbStatTimer2Ints
                Counter,
            wfIsdbStatTimer3Ints
                Counter,
            wfIsdbStatTimer4Ints
                Counter,
            wfIsdbStatBusErrors
                Counter,
	    wfIsdbStatRxFrames
		Counter,
	    wfIsdbStatRxOctets
                Counter,
            wfIsdbStatRxLacks
                Counter,
            wfIsdbStatRxDataLinkMsgLacks
                Counter,
            wfIsdbStatRxManagementMsgLacks
                Counter,
            wfIsdbStatRxBadFrames
                Counter,
            wfIsdbStatRxOverFlows
                Counter,
            wfIsdbStatRxRunts
                Counter,
            wfIsdbStatRxLargeFrames
                Counter,
            wfIsdbStatRxSmallFrames
                Counter,
            wfIsdbStatRxIncompleteFrames
                Counter,
            wfIsdbStatRxInts
                Counter,
            wfIsdbStatRxDataLinkFrames
                Counter,
            wfIsdbStatRxDataLinkDiscards
                Counter,
            wfIsdbStatRxManagementFrames
                Counter,
            wfIsdbStatRxUnknownFrames
                Counter,
            wfIsdbStatTxFrames
                Counter,
            wfIsdbStatTxOctets
                Counter,
            wfIsdbStatTxLacks
                Counter,
            wfIsdbStatTxUnderFlows
                Counter,
            wfIsdbStatTxAbortedFrames
                Counter,
            wfIsdbStatTxMsgs
                Counter,
            wfIsdbStatTxLargeMsgs
                Counter,
            wfIsdbStatTxSmallMsgs
                Counter,
            wfIsdbStatTxInts
                Counter,
            wfIsdbStatTxDataLinkFrames
                Counter,
            wfIsdbStatTxManagementFrames
                Counter,
            wfIsdbStatTxUnknownFrames
                Counter
    }

    wfIsdbStatState OBJECT-TYPE
        SYNTAX  INTEGER {
                    up(1),
                    down(2),
                    init(3)
                }
        ACCESS  read-only
        STATUS  mandatory
        DESCRIPTION
               "Current state of the Async port on the I-SDB"
        DEFVAL  { down }
        ::= { wfIsdbStatEntry 1 }

    wfIsdbStatSlot OBJECT-TYPE
        SYNTAX  INTEGER
        ACCESS  read-only
        STATUS  mandatory
        DESCRIPTION
                "Instance ID Slot, filled in by the ISDB mib gate"
        ::= { wfIsdbStatEntry 2 }

    wfIsdbStatConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfIsdbStatEntry 3 }

    wfIsdbStatVersion OBJECT-TYPE
        SYNTAX  INTEGER
        ACCESS  read-only
        STATUS  mandatory
        DESCRIPTION
                "Version of code running on the Isdb board"
        ::= { wfIsdbStatEntry 4 }

    wfIsdbStatCurrentConnCount OBJECT-TYPE
        SYNTAX  Counter
        ACCESS  read-only
        STATUS  mandatory
        DESCRIPTION
                "Current number of connections made to the Isdb"
        ::= { wfIsdbStatEntry 5 }

    wfIsdbStatTotalConnCount OBJECT-TYPE
        SYNTAX  Counter
        ACCESS  read-only
        STATUS  mandatory
        DESCRIPTION
                "Total number of connections made to the Isdb"
        ::= { wfIsdbStatEntry 6 }

    wfIsdbStatStartCount OBJECT-TYPE
        SYNTAX  Counter
        ACCESS  read-only
        STATUS  mandatory
        DESCRIPTION
                "Number of start commands sent to the Isdb"
        ::= { wfIsdbStatEntry 7 }

    wfIsdbStatCpuIdleCurrent OBJECT-TYPE
        SYNTAX  INTEGER
        ACCESS  read-only
        STATUS  mandatory
        DESCRIPTION
                "Number of idle cycles since the last query of this mib"
        ::= { wfIsdbStatEntry 8 }

    wfIsdbStatCpuIdleTotal OBJECT-TYPE
        SYNTAX  INTEGER
        ACCESS  read-only
        STATUS  mandatory
        DESCRIPTION
                "Total number of cpu idle cycles since bootup"
        ::= { wfIsdbStatEntry 9 }

    wfIsdbStatMemoryFree OBJECT-TYPE
        SYNTAX  INTEGER
        ACCESS  read-only
        STATUS  mandatory
        DESCRIPTION
                "Amount of free memory on Isdb "
        ::= { wfIsdbStatEntry 10 }

    wfIsdbStatMemoryLargestBlock OBJECT-TYPE
        SYNTAX  INTEGER
        ACCESS  read-only
        STATUS  mandatory
        DESCRIPTION
                "Largest block of memory on Isdb "
        ::= { wfIsdbStatEntry 11 }

    wfIsdbStatTaskCount OBJECT-TYPE
        SYNTAX  Counter
        ACCESS  read-only
        STATUS  mandatory
        DESCRIPTION
                "Number of active tasks on Isdb "
        ::= { wfIsdbStatEntry 12 }

    wfIsdbStatMsgQueueLacks OBJECT-TYPE
        SYNTAX  Counter
        ACCESS  read-only
        STATUS  mandatory
        DESCRIPTION
                "Number of message queue lack of resources "
        ::= { wfIsdbStatEntry 13 }

    wfIsdbStatHardwareTimeouts OBJECT-TYPE
        SYNTAX  Counter
        ACCESS  read-only
        STATUS  mandatory
        DESCRIPTION
                "Number of hardware timeouts"
        ::= { wfIsdbStatEntry 14 }

    wfIsdbStatAlarmCount OBJECT-TYPE
        SYNTAX  Counter
        ACCESS  read-only
        STATUS  mandatory
        DESCRIPTION
                "Number of alarms on Isdb"
        ::= { wfIsdbStatEntry 15 }

    wfIsdbStatAuthorUnknown OBJECT-TYPE
        SYNTAX  Counter 
        ACCESS  read-only
        STATUS  mandatory
        DESCRIPTION
                "Not currently used"
        ::= { wfIsdbStatEntry 16 }

    wfIsdbStatAv1Ints OBJECT-TYPE
        SYNTAX  Counter
        ACCESS  read-only
        STATUS  mandatory
        DESCRIPTION
                "Auto Vector Interrupt 1"
        ::= { wfIsdbStatEntry 17 }

    wfIsdbStatAv2Ints OBJECT-TYPE
        SYNTAX  Counter
        ACCESS  read-only
        STATUS  mandatory
        DESCRIPTION
                "Auto Vector Interrupt 2"
        ::= { wfIsdbStatEntry 18 }

    wfIsdbStatAv3Ints OBJECT-TYPE
        SYNTAX  Counter
        ACCESS  read-only
        STATUS  mandatory
        DESCRIPTION
                "Auto Vector Interrupt 3"
        ::= { wfIsdbStatEntry 19 }

    wfIsdbStatAv4Ints OBJECT-TYPE
        SYNTAX  Counter
        ACCESS  read-only
        STATUS  mandatory
        DESCRIPTION
                "Auto Vector Interrupt 4"
        ::= { wfIsdbStatEntry 20 }

    wfIsdbStatAv5Ints OBJECT-TYPE
        SYNTAX  Counter
        ACCESS  read-only
        STATUS  mandatory
        DESCRIPTION
                "Auto Vector Interrupt 5 "
        ::= { wfIsdbStatEntry 21 }

    wfIsdbStatAv6Ints OBJECT-TYPE
        SYNTAX  Counter
        ACCESS  read-only
        STATUS  mandatory
        DESCRIPTION
                "Auto Vector Interrupt 6"
        ::= { wfIsdbStatEntry 22 }

    wfIsdbStatAv7Ints OBJECT-TYPE
        SYNTAX  Counter
        ACCESS  read-only
        STATUS  mandatory
        DESCRIPTION
                "Auto Vector Interrupt 7"
        ::= { wfIsdbStatEntry 23 }

    wfIsdbStatScc3Ints OBJECT-TYPE
        SYNTAX  Counter
        ACCESS  read-only
        STATUS  mandatory
        DESCRIPTION
                "Serial communications controller interrupts"
        ::= { wfIsdbStatEntry 24 }

    wfIsdbStatErrorInts OBJECT-TYPE
        SYNTAX  Counter
        ACCESS  read-only
        STATUS  mandatory
        DESCRIPTION
                "Interrupts caused by errors"
        ::= { wfIsdbStatEntry 25 }

    wfIsdbStatTimer1Ints OBJECT-TYPE
        SYNTAX  Counter
        ACCESS  read-only
        STATUS  mandatory
        DESCRIPTION
                "Timer 1 Interrupt"
        ::= { wfIsdbStatEntry 26 }

    wfIsdbStatTimer2Ints OBJECT-TYPE
        SYNTAX  Counter
        ACCESS  read-only
        STATUS  mandatory
        DESCRIPTION
                "Timer 2 Interrupt"
        ::= { wfIsdbStatEntry 27 }

    wfIsdbStatTimer3Ints OBJECT-TYPE
        SYNTAX  Counter
        ACCESS  read-only
        STATUS  mandatory
        DESCRIPTION
                "Timer 3 Interrupt"
        ::= { wfIsdbStatEntry 28 }

    wfIsdbStatTimer4Ints OBJECT-TYPE
        SYNTAX  Counter
        ACCESS  read-only
        STATUS  mandatory
        DESCRIPTION
                "Timer 4 Interrupt"
        ::= { wfIsdbStatEntry 29 }

    wfIsdbStatBusErrors OBJECT-TYPE
        SYNTAX  Counter
        ACCESS  read-only
        STATUS  mandatory
        DESCRIPTION
                "Bus errors on Isdb"
        ::= { wfIsdbStatEntry 30 }

    wfIsdbStatRxFrames OBJECT-TYPE
        SYNTAX  Counter
        ACCESS  read-only
        STATUS  mandatory
        DESCRIPTION
                "Number of frames received without error"
        ::= { wfIsdbStatEntry 31 }

    wfIsdbStatRxOctets OBJECT-TYPE
        SYNTAX  Counter
        ACCESS  read-only
        STATUS  mandatory
        DESCRIPTION
                "Number of octets received without error"
        ::= { wfIsdbStatEntry 32 }

    wfIsdbStatRxLacks OBJECT-TYPE
        SYNTAX  Counter
        ACCESS  read-only
        STATUS  mandatory
        DESCRIPTION
                "Number of Rx frames dropped due to lack of buffer resources"
        ::= { wfIsdbStatEntry 33 }

    wfIsdbStatRxDataLinkMsgLacks OBJECT-TYPE
        SYNTAX  Counter
        ACCESS  read-only
        STATUS  mandatory
        DESCRIPTION
                "Number of datalink frames dropped due to lack of buffer resources"
        ::= { wfIsdbStatEntry 34 }

    wfIsdbStatRxManagementMsgLacks OBJECT-TYPE
        SYNTAX  Counter
        ACCESS  read-only
        STATUS  mandatory
        DESCRIPTION
                "Number managment messages dropped due to lack of buffer resources"
        ::= { wfIsdbStatEntry 35 }

    wfIsdbStatRxBadFrames OBJECT-TYPE
        SYNTAX  Counter
        ACCESS  read-only
        STATUS  mandatory
        DESCRIPTION
                "Number of bad receive frames, caused by FCS errors 
		or non octet aligned. "
        ::= { wfIsdbStatEntry 36 }

    wfIsdbStatRxOverFlows OBJECT-TYPE
        SYNTAX  Counter
        ACCESS  read-only
        STATUS  mandatory
        DESCRIPTION
                "Number of receive overflows, device FIFO overflowed before next
                DMA cycle granted.  No buffer resources available."
        ::= { wfIsdbStatEntry 37 }

    wfIsdbStatRxRunts OBJECT-TYPE
        SYNTAX  Counter
        ACCESS  read-only
        STATUS  mandatory
        DESCRIPTION
                "Number of runt frames received or number of frames where
                 the Carrier Detect signal was lost during reception."
        ::= { wfIsdbStatEntry 38 }

    wfIsdbStatRxLargeFrames OBJECT-TYPE
        SYNTAX  Counter
        ACCESS  read-only
        STATUS  mandatory
        DESCRIPTION
                "Number of frames received that exceed the size of
		a frame with a datalink header + X.25 header + 256 bytes
		of data (total 265 bytes)"
        ::= { wfIsdbStatEntry 39 }

    wfIsdbStatRxSmallFrames OBJECT-TYPE
        SYNTAX  Counter
        ACCESS  read-only
        STATUS  mandatory
        DESCRIPTION
                "Number of frames received that are less than the size of
		the datalink header (< 2 bytes)"
        ::= { wfIsdbStatEntry 40 }

    wfIsdbStatRxIncompleteFrames OBJECT-TYPE
        SYNTAX  Counter
        ACCESS  read-only
        STATUS  mandatory
        DESCRIPTION
                "Number of frames which were incompletely received. These are frames
                which may have resulted from FRMRR errors."
        ::= { wfIsdbStatEntry 41 }

    wfIsdbStatRxInts OBJECT-TYPE
        SYNTAX  Counter
        ACCESS  read-only
        STATUS  mandatory
        DESCRIPTION
                "Total number of receive interrupts on the isdb board"
        ::= { wfIsdbStatEntry 42 }

    wfIsdbStatRxDataLinkFrames OBJECT-TYPE
        SYNTAX  Counter
        ACCESS  read-only
        STATUS  mandatory
        DESCRIPTION
                "Total number of datalink frames received"
        ::= { wfIsdbStatEntry 43 }

    wfIsdbStatRxDataLinkDiscards OBJECT-TYPE
        SYNTAX  Counter
        ACCESS  read-only
        STATUS  mandatory
        DESCRIPTION
                "Number of datalink frames that were discarded"
        ::= { wfIsdbStatEntry 44 }

    wfIsdbStatRxManagementFrames OBJECT-TYPE
        SYNTAX  Counter
        ACCESS  read-only
        STATUS  mandatory
        DESCRIPTION
                "Number of management frames received"
        ::= { wfIsdbStatEntry 45 }

    wfIsdbStatRxUnknownFrames OBJECT-TYPE
        SYNTAX  Counter
        ACCESS  read-only
        STATUS  mandatory
        DESCRIPTION
                "Number of unknown frames received"
        ::= { wfIsdbStatEntry 46 }

    wfIsdbStatTxFrames OBJECT-TYPE
        SYNTAX  Counter
        ACCESS  read-only
        STATUS  mandatory
        DESCRIPTION
                "Total number of frames transmitted without error"
        ::= { wfIsdbStatEntry 47 }

    wfIsdbStatTxOctets OBJECT-TYPE
        SYNTAX  Counter
        ACCESS  read-only
        STATUS  mandatory
        DESCRIPTION
                "Total number of octets transmitted without error"
        ::= { wfIsdbStatEntry 48 }

    wfIsdbStatTxLacks OBJECT-TYPE
        SYNTAX  Counter
        ACCESS  read-only
        STATUS  mandatory
        DESCRIPTION
                "Number of frames clipped in driver's transmit 
		routine due to transmit congestion. "
        ::= { wfIsdbStatEntry 49 }

    wfIsdbStatTxUnderFlows OBJECT-TYPE
        SYNTAX  Counter
        ACCESS  read-only
        STATUS  mandatory
        DESCRIPTION
                "Number of transmission underflows, device FIFO went empty before
                next DMA request was granted. "
        ::= { wfIsdbStatEntry 50 }

    wfIsdbStatTxAbortedFrames OBJECT-TYPE
        SYNTAX  Counter
        ACCESS  read-only
        STATUS  mandatory
        DESCRIPTION
                "Number of frames where CTS was lost during transmission. "
        ::= { wfIsdbStatEntry 51 }

    wfIsdbStatTxMsgs OBJECT-TYPE
        SYNTAX  Counter
        ACCESS  read-only
        STATUS  mandatory
        DESCRIPTION
                "Total number of messages transmitted"
        ::= { wfIsdbStatEntry 52 }

    wfIsdbStatTxLargeMsgs OBJECT-TYPE
        SYNTAX  Counter
        ACCESS  read-only
        STATUS  mandatory
        DESCRIPTION
                "Number of messages transmitted to the driver that
		exceed the size of the datalink header + X.25 header +
		256 bytes of data (total 265 bytes)"
        ::= { wfIsdbStatEntry 53 }

    wfIsdbStatTxSmallMsgs OBJECT-TYPE
        SYNTAX  Counter
        ACCESS  read-only
        STATUS  mandatory
        DESCRIPTION
                "Number of messages transmitted to the driver that
		are less than the size of the datalink header ( < 2 bytes)"
        ::= { wfIsdbStatEntry 54 }

    wfIsdbStatTxInts OBJECT-TYPE
        SYNTAX  Counter
        ACCESS  read-only
        STATUS  mandatory
        DESCRIPTION
                "Total number of transmit interrupts on the isdb board"
        ::= { wfIsdbStatEntry 55 }

    wfIsdbStatTxDataLinkFrames OBJECT-TYPE
        SYNTAX  Counter
        ACCESS  read-only
        STATUS  mandatory
        DESCRIPTION
                "Number of datalink frames transmitted"
        ::= { wfIsdbStatEntry 56 }

    wfIsdbStatTxManagementFrames OBJECT-TYPE
        SYNTAX  Counter
        ACCESS  read-only
        STATUS  mandatory
        DESCRIPTION
                "Number of management frames transmitted"
        ::= { wfIsdbStatEntry 57 }

    wfIsdbStatTxUnknownFrames OBJECT-TYPE
        SYNTAX  Counter
        ACCESS  read-only
        STATUS  mandatory
        DESCRIPTION
                "Number of unknown frames transmitted"
        ::= { wfIsdbStatEntry 58 }


    wfIsdbPortDefaultCfgTable OBJECT-TYPE
        SYNTAX  SEQUENCE OF WfIsdbPortDefaultCfgEntry
        ACCESS  not-accessible
        STATUS  mandatory
        DESCRIPTION
                "ASYNC  line record"
        ::= { wfIsdbGroup 3 }

    wfIsdbPortDefaultCfgEntry OBJECT-TYPE
        SYNTAX  WfIsdbPortDefaultCfgEntry
        ACCESS  not-accessible
        STATUS  mandatory
        DESCRIPTION
                "An entry in the ASYNC table"
        INDEX   { wfIsdbPortDefaultCfgSlot,
                  wfIsdbPortDefaultCfgConnector,
                  wfIsdbPortDefaultCfgNumber }
        ::= { wfIsdbPortDefaultCfgTable 1 }

    WfIsdbPortDefaultCfgEntry ::= SEQUENCE {
            wfIsdbPortDefaultCfgDelete
                INTEGER,
            wfIsdbPortDefaultCfgDisable
                INTEGER,
            wfIsdbPortDefaultCfgState
                INTEGER,
            wfIsdbPortDefaultCfgSlot
                INTEGER,
            wfIsdbPortDefaultCfgConnector
                INTEGER,
            wfIsdbPortDefaultCfgNumber
                INTEGER,
            wfIsdbPortDefaultCfgBaudRate
                INTEGER,
            wfIsdbPortDefaultCfgDataBits
                INTEGER,
            wfIsdbPortDefaultCfgParity
                INTEGER,
            wfIsdbPortDefaultCfgStopBits
                INTEGER,
            wfIsdbPortDefaultCfgCts
                INTEGER,
            wfIsdbPortDefaultCfgDsr
                INTEGER,
            wfIsdbPortDefaultCfgDcd
                INTEGER,
            wfIsdbPortDefaultCfgPrompt
                DisplayString,
            wfIsdbPortDefaultCfgCommandParser
                INTEGER,
            wfIsdbPortDefaultCfgInactivityTimeOut
                INTEGER,
	    wfIsdbPortDefaultCfgRxQueueSize
                INTEGER,
	    wfIsdbPortDefaultCfgTxQueueSize
                INTEGER,
	    wfIsdbPortDefaultCfgRxXoff
		INTEGER,
	    wfIsdbPortDefaultCfgTxXoff
		INTEGER,
	    wfIsdbPortDefaultCfgDtrAction
		INTEGER,
	    wfIsdbPortDefaultCfgRxXoffAction
		INTEGER
      }

    wfIsdbPortDefaultCfgDelete OBJECT-TYPE
        SYNTAX  INTEGER {
                    created(1),
                    deleted(2)
                }
        ACCESS  read-write
        STATUS  mandatory
        DESCRIPTION
                "Create/Delete parameter"
        DEFVAL  { created }
        ::= { wfIsdbPortDefaultCfgEntry 1 }

    wfIsdbPortDefaultCfgDisable OBJECT-TYPE
        SYNTAX  INTEGER {
                    enabled(1),
                    disabled(2)
                }
        ACCESS  read-write
        STATUS  mandatory
        DESCRIPTION
                "Enable/Disable parameter"
        DEFVAL  { enabled }
        ::= { wfIsdbPortDefaultCfgEntry 2 }

    wfIsdbPortDefaultCfgState OBJECT-TYPE
        SYNTAX  INTEGER {
                    up(1),
                    down(2),
                    init(3)
                }
        ACCESS  read-only
        STATUS  mandatory
        DESCRIPTION
               "Current state of the Async port on the I-SDB"
        DEFVAL  { down }
        ::= { wfIsdbPortDefaultCfgEntry 3 }

    wfIsdbPortDefaultCfgSlot OBJECT-TYPE
        SYNTAX  INTEGER
        ACCESS  read-only
        STATUS  mandatory
        DESCRIPTION
                "Instance ID Slot, filled in by the ISDB mib gate"
        ::= { wfIsdbPortDefaultCfgEntry 4 }

    wfIsdbPortDefaultCfgConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfIsdbPortDefaultCfgEntry 5 }

    wfIsdbPortDefaultCfgNumber OBJECT-TYPE
        SYNTAX  INTEGER
        ACCESS  read-only
        STATUS  mandatory
        DESCRIPTION
                "Instance ID Async Port, filled in by the ISDB mib gate"
        ::= { wfIsdbPortDefaultCfgEntry 6 }

    wfIsdbPortDefaultCfgBaudRate OBJECT-TYPE
        SYNTAX  INTEGER {
			baudrate300b(300),
                        baudrate1200b(1200),
                        baudrate2400b(2400),
                        baudrate4800b(4800),
                        baudrate9600b(9600),
                        baudrate19200b(19200)
                        }
        ACCESS  read-write
        STATUS  mandatory
        DESCRIPTION
                "Baud rate configured on this Async Port"
        DEFVAL  { baudrate9600b }
        ::= { wfIsdbPortDefaultCfgEntry 7 }

    wfIsdbPortDefaultCfgDataBits OBJECT-TYPE
        SYNTAX  INTEGER {
                    five(5),
                    six(6),
                    seven(7),
                    eight(8)
                }
        ACCESS  read-write
        STATUS  mandatory
        DESCRIPTION
                "Number of data bits configured on this Async Port"
        DEFVAL  { eight }
        ::= { wfIsdbPortDefaultCfgEntry 8 }

    wfIsdbPortDefaultCfgParity OBJECT-TYPE
        SYNTAX  INTEGER {
                    none(1),
                    odd(2),
                    even(3),
                    mark(4),
		    space(5)
                }
        ACCESS  read-write
        STATUS  mandatory
        DESCRIPTION
                "Type of parity configured on this Async Port"
        DEFVAL  { none }
        ::= { wfIsdbPortDefaultCfgEntry 9 }

    wfIsdbPortDefaultCfgStopBits OBJECT-TYPE
        SYNTAX  INTEGER {
                    s1bit(1),
                    s15bit(2),
                    s2bit(3)
                }
        ACCESS  read-write
        STATUS  mandatory
        DESCRIPTION
                "Number of stop bits configured on this Async Port"
        DEFVAL  { s1bit }
        ::= { wfIsdbPortDefaultCfgEntry 10 }

    wfIsdbPortDefaultCfgCts OBJECT-TYPE
        SYNTAX  INTEGER {
                    alwaysOn(1),
                    alwaysOff(2),
                    followFlowControl(3),
		    followRTS(4)
                }
        ACCESS  read-write
        STATUS  mandatory
        DESCRIPTION
                "DCE (output) configuration of the CTS signal"
        DEFVAL  { alwaysOn }
        ::= { wfIsdbPortDefaultCfgEntry 11 }

    wfIsdbPortDefaultCfgDsr OBJECT-TYPE
        SYNTAX  INTEGER {
                    alwaysOn(1),
                    alwaysOff(2),
		    followDTR(3),
		    toggleOnDisconnect(4)
                }
        ACCESS  read-write
        STATUS  mandatory
        DESCRIPTION
                "DCE (output) configuration of the DSR signal"
        DEFVAL  { alwaysOn }
        ::= { wfIsdbPortDefaultCfgEntry 12 }

    wfIsdbPortDefaultCfgDcd OBJECT-TYPE
        SYNTAX  INTEGER {
                    alwaysOn(1),
                    alwaysOff(2),
		    followDTR(3),
		    followVC(4)
                }
        ACCESS  read-write
        STATUS  mandatory
        DESCRIPTION
                "DCE (output) configuration of the DCD signal"
        DEFVAL  { alwaysOn }
        ::= { wfIsdbPortDefaultCfgEntry 13 }

    wfIsdbPortDefaultCfgPrompt OBJECT-TYPE
        SYNTAX  DisplayString (SIZE (0..15))
        ACCESS  read-write
        STATUS  mandatory
        DESCRIPTION
                "Character string to be used for Async Port prompt"
        ::= { wfIsdbPortDefaultCfgEntry 14 }

    wfIsdbPortDefaultCfgCommandParser OBJECT-TYPE
        SYNTAX  INTEGER {
                    menu(1),
                    test(2),
                    x25pad(3),
		    loopback(4)
                }
        ACCESS  read-write
        STATUS  mandatory
        DESCRIPTION
                "Default command parser for Async Port"
        DEFVAL  { x25pad }
        ::= { wfIsdbPortDefaultCfgEntry 15 }

    wfIsdbPortDefaultCfgInactivityTimeOut OBJECT-TYPE
        SYNTAX  INTEGER(0..99)
        ACCESS  read-write
        STATUS  mandatory
        DESCRIPTION
                "Async port is reset after inactivity period"
        DEFVAL { 0 }
        ::= { wfIsdbPortDefaultCfgEntry 16 }

    wfIsdbPortDefaultCfgRxQueueSize OBJECT-TYPE
        SYNTAX  INTEGER(8..8192)
        ACCESS  read-write
        STATUS  mandatory
        DESCRIPTION
                "Size of the async port's receive queue"
        DEFVAL { 8192 }
        ::= { wfIsdbPortDefaultCfgEntry 17 }

    wfIsdbPortDefaultCfgTxQueueSize OBJECT-TYPE
        SYNTAX  INTEGER(8..8192)
        ACCESS  read-write
        STATUS  mandatory
        DESCRIPTION
                "Size of the async port's transmit queue"
        DEFVAL { 8192 }
        ::= { wfIsdbPortDefaultCfgEntry 18 }

    wfIsdbPortDefaultCfgRxXoff OBJECT-TYPE
        SYNTAX  INTEGER {
                    enabled(1),
                    disabled(2)
                }
        ACCESS  read-write
        STATUS  mandatory
        DESCRIPTION
                "Flow Control Xon/Xoff for Isdb's async port"
        DEFVAL  { enabled }
        ::= { wfIsdbPortDefaultCfgEntry 19 }

    wfIsdbPortDefaultCfgTxXoff OBJECT-TYPE
        SYNTAX  INTEGER {
                    enabled(1),
                    disabled(2)
                }
        ACCESS  read-write
        STATUS  mandatory
        DESCRIPTION
                "Flow Control Xon/Xoff for remote terminal"
        DEFVAL  { disabled }
        ::= { wfIsdbPortDefaultCfgEntry 20 }

    wfIsdbPortDefaultCfgDtrAction OBJECT-TYPE
        SYNTAX  INTEGER{
                    enabled(1),
                    disabled(2)
                } 
        ACCESS  read-write
        STATUS  mandatory
        DESCRIPTION
                "Determines whether or not an action is taken
		when the DTR signal changes"		
        DEFVAL  { enabled }
        ::= { wfIsdbPortDefaultCfgEntry 21 }

    wfIsdbPortDefaultCfgRxXoffAction OBJECT-TYPE
        SYNTAX  INTEGER{
                    enabled(1),
                    disabled(2)
                }
        ACCESS  read-write
        STATUS  mandatory
        DESCRIPTION
                "Determine whether or not we notify the application when
		an Xon or Xoff change occurs"                
        DEFVAL  { enabled }
        ::= { wfIsdbPortDefaultCfgEntry 22 }

    wfIsdbPortCurrentCfgTable OBJECT-TYPE
        SYNTAX  SEQUENCE OF WfIsdbPortCurrentCfgEntry
        ACCESS  not-accessible
        STATUS  mandatory
        DESCRIPTION
                "ASYNC Current line record"
        ::= { wfIsdbGroup 4 }

    wfIsdbPortCurrentCfgEntry OBJECT-TYPE
        SYNTAX  WfIsdbPortCurrentCfgEntry
        ACCESS  not-accessible
        STATUS  mandatory
        DESCRIPTION
                "An entry in the ASYNC table"
        INDEX   { wfIsdbPortCurrentCfgSlot,
                  wfIsdbPortCurrentCfgConnector,
                  wfIsdbPortCurrentCfgNumber }
        ::= { wfIsdbPortCurrentCfgTable 1 }

    WfIsdbPortCurrentCfgEntry ::= SEQUENCE {
            wfIsdbPortCurrentCfgState
                INTEGER,
            wfIsdbPortCurrentCfgSlot
                INTEGER,
            wfIsdbPortCurrentCfgConnector
                INTEGER,
            wfIsdbPortCurrentCfgNumber
                INTEGER,
            wfIsdbPortCurrentCfgBaudRate
                INTEGER,
            wfIsdbPortCurrentCfgDataBits
                INTEGER,
            wfIsdbPortCurrentCfgParity
                INTEGER,
            wfIsdbPortCurrentCfgStopBits
                INTEGER,
            wfIsdbPortCurrentCfgCts
                INTEGER,
            wfIsdbPortCurrentCfgDsr
                INTEGER,
            wfIsdbPortCurrentCfgDcd
                INTEGER,
            wfIsdbPortCurrentCfgPrompt
                DisplayString,
            wfIsdbPortCurrentCfgCommandParser
                INTEGER,
            wfIsdbPortCurrentCfgInactivityTimeout
                INTEGER,
	    wfIsdbPortCurrentCfgRxQueueSize
                INTEGER,
	    wfIsdbPortCurrentCfgTxQueueSize
                INTEGER,
            wfIsdbPortCurrentCfgRxXoff
                INTEGER,
            wfIsdbPortCurrentCfgTxXoff
                INTEGER,
            wfIsdbPortCurrentCfgDtrAction
                INTEGER,
            wfIsdbPortCurrentCfgRxXoffAction
                INTEGER
      }

    wfIsdbPortCurrentCfgState OBJECT-TYPE
        SYNTAX  INTEGER {
                    up(1),
                    down(2),
                    init(3)
                }
        ACCESS  read-only
        STATUS  mandatory
        DESCRIPTION
               "Current state of the Async port on the I-SDB"
        DEFVAL  { down }
        ::= { wfIsdbPortCurrentCfgEntry 1 }

    wfIsdbPortCurrentCfgSlot OBJECT-TYPE
        SYNTAX  INTEGER
        ACCESS  read-only
        STATUS  mandatory
        DESCRIPTION
                "Instance ID Slot, filled in by the ISDB mib gate"
        ::= { wfIsdbPortCurrentCfgEntry 2 }

    wfIsdbPortCurrentCfgConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfIsdbPortCurrentCfgEntry 3 }

    wfIsdbPortCurrentCfgNumber OBJECT-TYPE
        SYNTAX  INTEGER
        ACCESS  read-only
        STATUS  mandatory
        DESCRIPTION
                "Instance ID Async Port, filled in by the ISDB mib gate"
        ::= { wfIsdbPortCurrentCfgEntry 4 }

    wfIsdbPortCurrentCfgBaudRate OBJECT-TYPE
        SYNTAX  INTEGER {
			baudrate300b(300),
                        baudrate1200b(1200),
                        baudrate2400b(2400),
                        baudrate4800b(4800),
                        baudrate9600b(9600),
                        baudrate19200b(19200)
                        }
        ACCESS  read-only
        STATUS  mandatory
        DESCRIPTION
                "Baud rate configured on this Async Port"
        ::= { wfIsdbPortCurrentCfgEntry 5 }

    wfIsdbPortCurrentCfgDataBits OBJECT-TYPE
        SYNTAX  INTEGER {
                    five(5),
                    six(6),
                    seven(7),
                    eight(8)
                }
        ACCESS  read-only
        STATUS  mandatory
        DESCRIPTION
                "Number of data bits configured on this Async Port"
        ::= { wfIsdbPortCurrentCfgEntry 6 }

    wfIsdbPortCurrentCfgParity OBJECT-TYPE
        SYNTAX  INTEGER {
                    none(1),
                    odd(2),
                    even(3),
		    mark(4),
		    space(5)
                }
        ACCESS  read-only
        STATUS  mandatory
        DESCRIPTION
                "Type of parity configured on this Async Port"
        ::= { wfIsdbPortCurrentCfgEntry 7 }

    wfIsdbPortCurrentCfgStopBits OBJECT-TYPE
        SYNTAX  INTEGER {
                    s1bit(1),
                    s15bit(2),
                    s2bit(3)
                }
        ACCESS  read-only
        STATUS  mandatory
        DESCRIPTION
                "Number of stop bits configured on this Async Port"
        ::= { wfIsdbPortCurrentCfgEntry 8 }

    wfIsdbPortCurrentCfgCts OBJECT-TYPE
        SYNTAX  INTEGER {
                    alwaysOn(1),
                    alwaysOff(2),
                    followFlowControl(3),
                    followRTS(4)
                }
        ACCESS  read-only
        STATUS  mandatory
        DESCRIPTION
                "DCE (output) configuration of the CTS signal"
        ::= { wfIsdbPortCurrentCfgEntry 9 }

    wfIsdbPortCurrentCfgDsr OBJECT-TYPE
        SYNTAX  INTEGER {
                    alwaysOn(1),
                    alwaysOff(2),
                    followDTR(3),
                    toggleOnDisconnect(4)
                }
        ACCESS  read-only
        STATUS  mandatory
        DESCRIPTION
                "DCE (output) configuration of the DSR signal"
        ::= { wfIsdbPortCurrentCfgEntry 10 }

    wfIsdbPortCurrentCfgDcd OBJECT-TYPE
        SYNTAX  INTEGER {
                    alwaysOn(1),
                    alwaysOff(2),
                    followDTR(3),
                    followVC(4)
                }
        ACCESS  read-only
        STATUS  mandatory
        DESCRIPTION
                "DCE (output) configuration of the DCD signal"
        ::= { wfIsdbPortCurrentCfgEntry 11 }

    wfIsdbPortCurrentCfgPrompt OBJECT-TYPE
        SYNTAX  DisplayString (SIZE (0..15))
        ACCESS  read-only
        STATUS  mandatory
        DESCRIPTION
                "Character string to be used for Async Port prompt"
        ::= { wfIsdbPortCurrentCfgEntry 12 }

    wfIsdbPortCurrentCfgCommandParser OBJECT-TYPE
        SYNTAX  INTEGER {
                    menu(1),
                    test(2),
                    x25pad(3),
		    loopback(4)
                }
        ACCESS  read-only
        STATUS  mandatory
        DESCRIPTION
                "Current command parser for Async Port"
        ::= { wfIsdbPortCurrentCfgEntry 13 }

    wfIsdbPortCurrentCfgInactivityTimeout OBJECT-TYPE
        SYNTAX  INTEGER(1..99)
        ACCESS  read-only
        STATUS  mandatory
        DESCRIPTION
                "Async port is reset after inactivity period"
        ::= { wfIsdbPortCurrentCfgEntry 14 }

    wfIsdbPortCurrentCfgRxQueueSize OBJECT-TYPE
        SYNTAX  INTEGER(8..8192)
        ACCESS  read-only
        STATUS  mandatory
        DESCRIPTION
                "Size of the async port's receive queue"
        ::= { wfIsdbPortCurrentCfgEntry 15 }

    wfIsdbPortCurrentCfgTxQueueSize OBJECT-TYPE
        SYNTAX  INTEGER(8..8192)
        ACCESS  read-only
        STATUS  mandatory
        DESCRIPTION
                "Size of the async port's transmit queue"
        ::= { wfIsdbPortCurrentCfgEntry 16 }

    wfIsdbPortCurrentCfgRxXoff OBJECT-TYPE
        SYNTAX  INTEGER {
                    enabled(1),
                    disabled(2)
                }
        ACCESS  read-only
        STATUS  mandatory
        DESCRIPTION
                "Flow Control Xon/Xoff for Isdb's async port"
        DEFVAL  { enabled }
        ::= { wfIsdbPortCurrentCfgEntry 17 }

    wfIsdbPortCurrentCfgTxXoff OBJECT-TYPE
        SYNTAX  INTEGER {
                    enabled(1),
                    disabled(2)
                }
        ACCESS  read-only
        STATUS  mandatory
        DESCRIPTION
                "Flow Control Xon/Xoff for remote terminal"
        DEFVAL  { disabled }
        ::= { wfIsdbPortCurrentCfgEntry 18 }

    wfIsdbPortCurrentCfgDtrAction OBJECT-TYPE
        SYNTAX  INTEGER{
                    enabled(1),
                    disabled(2)
                }
        ACCESS  read-only
        STATUS  mandatory
        DESCRIPTION
                "Determines whether or not an action is taken
                when the DTR signal changes"
        DEFVAL  { enabled }
        ::= { wfIsdbPortCurrentCfgEntry 19 }

    wfIsdbPortCurrentCfgRxXoffAction OBJECT-TYPE
        SYNTAX  INTEGER{
                    enabled(1),
                    disabled(2)
                }
        ACCESS  read-only
        STATUS  mandatory
        DESCRIPTION
                "Determine whether or not we notify the application when
                an Xon or Xoff change occurs "
        DEFVAL  { enabled }
        ::= { wfIsdbPortCurrentCfgEntry 20 }

    wfIsdbPortStatTable OBJECT-TYPE
        SYNTAX  SEQUENCE OF WfIsdbPortStatEntry
        ACCESS  not-accessible
        STATUS  mandatory
        DESCRIPTION
                "ASYNC  line record"
        ::= { wfIsdbGroup 5 }

    wfIsdbPortStatEntry OBJECT-TYPE
        SYNTAX  WfIsdbPortStatEntry
        ACCESS  not-accessible
        STATUS  mandatory
        DESCRIPTION
                "An entry in the ASYNC table"
        INDEX   { wfIsdbPortStatSlot,
                  wfIsdbPortStatConnector,
                  wfIsdbPortStatNumber }
        ::= { wfIsdbPortStatTable 1 }

    WfIsdbPortStatEntry ::= SEQUENCE {
            wfIsdbPortStatState
                INTEGER,
            wfIsdbPortStatSlot
                INTEGER,
            wfIsdbPortStatConnector
                INTEGER,
            wfIsdbPortStatNumber
                INTEGER,
            wfIsdbPortStatRxOctets
                Counter,
	    wfIsdbPortStatRxLacks
    		Counter,
	    wfIsdbPortStatRxWaits
		Counter,
            wfIsdbPortStatTxOctets
                Counter,
            wfIsdbPortStatTxLacks
		Counter,
	    wfIsdbPortStatTxWaits
		Counter,
            wfIsdbPortStatBreaksDetected
                Counter,
            wfIsdbPortStatParityErrors
                Counter,
            wfIsdbPortStatFramingErrors
                Counter,
            wfIsdbPortStatOverrunErrors
                Counter,
            wfIsdbPortStatCtsState
                INTEGER,
            wfIsdbPortStatCtsTransitions
                Counter,
            wfIsdbPortStatRtsState
                INTEGER,
            wfIsdbPortStatRtsTransitions
                Counter,
            wfIsdbPortStatDsrState
                INTEGER,
            wfIsdbPortStatDsrTransitions
                Counter,
            wfIsdbPortStatDcdState
                INTEGER,
            wfIsdbPortStatDcdTransitions
                Counter,
            wfIsdbPortStatDtrState
                INTEGER,
            wfIsdbPortStatDtrTransitions
                Counter,
	    wfIsdbPortStatRxInts
		Counter,
	    wfIsdbPortStatTxInts
		Counter,
	    wfIsdbPortStatModemInts
		Counter,
	    wfIsdbPortStatSpecialCharCount
		Counter,
	    wfIsdbPortStatRxState
		INTEGER,
	    wfIsdbPortStatRxFlowState
		INTEGER,
	    wfIsdbPortStatTxState
		INTEGER,
	    wfIsdbPortStatTxFlowState
		INTEGER
       }

    wfIsdbPortStatState OBJECT-TYPE
        SYNTAX  INTEGER {
                    up(1),
                    down(2),
                    init(3)
                }
        ACCESS  read-only
        STATUS  mandatory
        DESCRIPTION
               "Current state of the Async port on the I-SDB"
        DEFVAL  { down }
        ::= { wfIsdbPortStatEntry 1 }

    wfIsdbPortStatSlot OBJECT-TYPE
        SYNTAX  INTEGER
        ACCESS  read-only
        STATUS  mandatory
        DESCRIPTION
                "Instance ID Slot, filled in by the ISDB mib gate"
        ::= { wfIsdbPortStatEntry 2 }

    wfIsdbPortStatConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfIsdbPortStatEntry 3 }

    wfIsdbPortStatNumber OBJECT-TYPE
        SYNTAX  INTEGER
        ACCESS  read-only
        STATUS  mandatory
        DESCRIPTION
                "Instance ID Async Port, filled in by the ISDB mib gate"
        ::= { wfIsdbPortStatEntry 4 }

    wfIsdbPortStatRxOctets OBJECT-TYPE
        SYNTAX  Counter
        ACCESS  read-only
        STATUS  mandatory
        DESCRIPTION
                "Number of octets received on Async Port"
        ::= { wfIsdbPortStatEntry 5 }

     wfIsdbPortStatRxLacks OBJECT-TYPE
        SYNTAX  Counter
        ACCESS  read-only
        STATUS  mandatory
        DESCRIPTION
                "Number of lack of resources encountered while receiving
		 on Async Port"
        ::= { wfIsdbPortStatEntry 6 }

     wfIsdbPortStatRxWaits OBJECT-TYPE
        SYNTAX  Counter
        ACCESS  read-only
        STATUS  mandatory
        DESCRIPTION
                "Number of times we had to wait because the receive queue
		was full"
        ::= { wfIsdbPortStatEntry 7 }

    wfIsdbPortStatTxOctets OBJECT-TYPE
        SYNTAX  Counter
        ACCESS  read-only
        STATUS  mandatory
        DESCRIPTION
                "Number of octets transmitted on Async Port"
        ::= { wfIsdbPortStatEntry 8 }

    wfIsdbPortStatTxLacks OBJECT-TYPE
        SYNTAX  Counter
        ACCESS  read-only
        STATUS  mandatory
        DESCRIPTION
                "Number of lack of resources encountered when transmitting
		 on Async Port"
        ::= { wfIsdbPortStatEntry 9 }

    wfIsdbPortStatTxWaits OBJECT-TYPE
        SYNTAX  Counter
        ACCESS  read-only
        STATUS  mandatory
        DESCRIPTION
                "Number of times we had to wait because the transmit queue
		was full"
        ::= { wfIsdbPortStatEntry 10 }

    wfIsdbPortStatBreaksDetected OBJECT-TYPE
        SYNTAX  Counter
        ACCESS  read-only
        STATUS  mandatory
        DESCRIPTION
                "Number of Breaks detected on Async Port"
        ::= { wfIsdbPortStatEntry 11 }

    wfIsdbPortStatParityErrors OBJECT-TYPE
        SYNTAX  Counter
        ACCESS  read-only
        STATUS  mandatory
        DESCRIPTION
                "Number of Parity Errors detected on Async Port"
        ::= { wfIsdbPortStatEntry 12 }

    wfIsdbPortStatFramingErrors OBJECT-TYPE
        SYNTAX  Counter
        ACCESS  read-only
        STATUS  mandatory
        DESCRIPTION
                "Number of Framing Errors detected on Async Port"
        ::= { wfIsdbPortStatEntry 13 }

    wfIsdbPortStatOverrunErrors OBJECT-TYPE
        SYNTAX  Counter
        ACCESS  read-only
        STATUS  mandatory
        DESCRIPTION
                "Async port is reset after inactivity period"
        ::= { wfIsdbPortStatEntry 14 }

    wfIsdbPortStatCtsState OBJECT-TYPE
        SYNTAX  INTEGER {
                    on(1),
                    off(2)
                }
        ACCESS  read-only
        STATUS  mandatory
        DESCRIPTION
                "Current CTS state"
        ::= { wfIsdbPortStatEntry 15 }

    wfIsdbPortStatCtsTransitions OBJECT-TYPE
        SYNTAX  Counter
        ACCESS  read-only
        STATUS  mandatory
        DESCRIPTION
                "Number of times CTS has changed state"
        ::= { wfIsdbPortStatEntry 16 }

    wfIsdbPortStatRtsState OBJECT-TYPE
        SYNTAX  INTEGER {
                    on(1),
                    off(2)
                }
        ACCESS  read-only
        STATUS  mandatory
        DESCRIPTION
                "Current RTS state"
        ::= { wfIsdbPortStatEntry 17 }

    wfIsdbPortStatRtsTransitions OBJECT-TYPE
        SYNTAX  Counter
        ACCESS  read-only
        STATUS  mandatory
        DESCRIPTION
                "Number of times that RTS has changed state"
        ::= { wfIsdbPortStatEntry 18 }

    wfIsdbPortStatDsrState OBJECT-TYPE
        SYNTAX  INTEGER {
                    on(1),
                    off(2)
                }
        ACCESS  read-only
        STATUS  mandatory
        DESCRIPTION
                "Current DSR state"
        ::= { wfIsdbPortStatEntry 19 }

    wfIsdbPortStatDsrTransitions OBJECT-TYPE
        SYNTAX  Counter
        ACCESS  read-only
        STATUS  mandatory
        DESCRIPTION
                "Number of times DSR has changed state"
        ::= { wfIsdbPortStatEntry 20 }

    wfIsdbPortStatDcdState OBJECT-TYPE
        SYNTAX  INTEGER {
                    on(1),
                    off(2)
                }
        ACCESS  read-only
        STATUS  mandatory
        DESCRIPTION
                "Current DCD state"
        ::= { wfIsdbPortStatEntry 21 }

    wfIsdbPortStatDcdTransitions OBJECT-TYPE
        SYNTAX  Counter
        ACCESS  read-only
        STATUS  mandatory
        DESCRIPTION
                "Number of times DCD has changed state"
        ::= { wfIsdbPortStatEntry 22 }

    wfIsdbPortStatDtrState OBJECT-TYPE
        SYNTAX  INTEGER {
                    on(1),
                    off(2)
                }
        ACCESS  read-only
        STATUS  mandatory
        DESCRIPTION
                "Current DTR state"
        ::= { wfIsdbPortStatEntry 23 }

    wfIsdbPortStatDtrTransitions OBJECT-TYPE
        SYNTAX  Counter
        ACCESS  read-only
        STATUS  mandatory
        DESCRIPTION
                "Number of times DTR has changed state"
        ::= { wfIsdbPortStatEntry 24 }

    wfIsdbPortStatRxInts OBJECT-TYPE
        SYNTAX  Counter
        ACCESS  read-only
        STATUS  mandatory
        DESCRIPTION
                "Number of receive interrupts on this port"
        ::= { wfIsdbPortStatEntry 25 }

    wfIsdbPortStatTxInts OBJECT-TYPE
        SYNTAX  Counter
        ACCESS  read-only
        STATUS  mandatory
        DESCRIPTION
                "Number of transmit interrupts on this port"
        ::= { wfIsdbPortStatEntry 26 }

    wfIsdbPortStatModemInts OBJECT-TYPE
        SYNTAX  Counter
        ACCESS  read-only
        STATUS  mandatory
        DESCRIPTION
                "Number of modem interrupts on this port"
        ::= { wfIsdbPortStatEntry 27 }

    wfIsdbPortStatSpecialCharCount OBJECT-TYPE
        SYNTAX  Counter
        ACCESS  read-only
        STATUS  mandatory
        DESCRIPTION
                "Count of the number of times XON/XOFF changes are detected"
        ::= { wfIsdbPortStatEntry 28 }

    wfIsdbPortStatRxState OBJECT-TYPE
        SYNTAX  INTEGER {
                    enabled(1),
                    disabled(2)
                } 
        ACCESS  read-only
        STATUS  mandatory
        DESCRIPTION
                "Hardware chip enabled/disabled for receiving"
        ::= { wfIsdbPortStatEntry 29 }


    wfIsdbPortStatRxFlowState OBJECT-TYPE
	SYNTAX  INTEGER {
                    on(1),
                    off(2),
		    normal(3)
	        }
        ACCESS  read-only
        STATUS  mandatory
        DESCRIPTION
                "Isdb board suspends/resumes output to the remote terminal "
        ::= { wfIsdbPortStatEntry 30 }

    wfIsdbPortStatTxState OBJECT-TYPE
        SYNTAX  INTEGER {
                    enabled(1),
                    disabled(2)
                }
        ACCESS  read-only
        STATUS  mandatory
        DESCRIPTION
                "Hardware chip enabled/disabled for transmitting"
        ::= { wfIsdbPortStatEntry 31 }

    wfIsdbPortStatTxFlowState OBJECT-TYPE
        SYNTAX  INTEGER {
                    on(1),
                    off(2),
                    normal(3)
                }
        ACCESS  read-only
        STATUS  mandatory
        DESCRIPTION
                "Remote terminal suspends/resumes output to the isdb board "
        ::= { wfIsdbPortStatEntry 32 }

    END  -- Wellfleet-ISDB-MIB
