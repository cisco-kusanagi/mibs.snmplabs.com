-- extracted from draft-ietf-ipcdn-cable-gateway-config-mib-00.txt
-- at Wed Jun 25 06:13:38 2003

   CABH-IETF-CDP-MIB DEFINITIONS ::= BEGIN 
    
   IMPORTS 
       MODULE-IDENTITY, 
       OBJECT-TYPE, 
       Integer32,  
       Unsigned32, 
       mib-2                 FROM SNMPv2-SMI  
       MacAddress,               
       TruthValue, 
       TimeStamp, 
       DateAndTime, 
       RowStatus             FROM SNMPv2-TC  -- RFC2579 
       OBJECT-GROUP, 
       MODULE-COMPLIANCE     FROM SNMPv2-CONF  -- RFC2580 
       InetAddressType, 
       InetAddress           FROM INET-ADDRESS-MIB   -- RFC3291 
       SnmpAdminString       FROM SNMP-FRAMEWORK-MIB; -- RFC2571 
    
   cabhCdpMib MODULE-IDENTITY 
       LAST-UPDATED    "200306210000Z" -- Jun 21, 2003 
       ORGANIZATION    "IETF IPCDN Working Group" 
       CONTACT-INFO 
               "Kevin Luehrs 
               Postal: Cable Television Laboratories, Inc. 
               400 Centennial Parkway 
               Louisville, Colorado 80027-1266 
               U.S.A. 
               Phone:  +1 303-661-9100 
               Fax:    +1 303-661-9199 
               E-mail: k.luehrs@cablelabs.com; mibs@cablelabs.com 
    
               IETF IPCDN Working Group 
               General Discussion: ipcdn@ietf.org 
               Subscribe: http://www.ietf.org/mailman/listinfo/ipcdn 
               Archive: ftp://ftp.ietf.org/ietf-mail-archive/ipcdn 
               Co-chairs: Richard Woundy, 
                          Richard_Woundy@cable.comcast.com 
                          Jean-Francois Mule, jf.mule@cablelabs.com" 
       DESCRIPTION 
               "This MIB module supplies the basic management objects 
               for the CableHome DHCP Portal (CDP) portion of the PS 
               database. 
    
               Copyright (C) The Internet Society (2003). This version 
               of this MIB module is part of RFC xxxx; see the RFC 
               itself for full legal notices." 
       REVISION         "200306210000Z" -- Jun 21, 2003 
       DESCRIPTION 
               "Initial version, published as RFC xxxx." 
         -- RFC editor to assign xxxx 
      ::= { mib-2 xx }    
       -- xx to be assigned by IANA 
    
        
   cabhCdpObjects         OBJECT IDENTIFIER ::= { cabhCdpMib 1 } 
   cabhCdpBase            OBJECT IDENTIFIER ::= { cabhCdpObjects 1 } 
   cabhCdpAddr            OBJECT IDENTIFIER ::= { cabhCdpObjects 2 } 
   cabhCdpServer          OBJECT IDENTIFIER ::= { cabhCdpObjects 3 } 
    
   -- 
   --  The following group describes the base objects in the CableHome 
   --  DHCP Portal.  The rest of this group deals addresses defined on 
   --  the LAN side. 
   -- 
    
   cabhCdpSetToFactory    OBJECT-TYPE 
       SYNTAX      TruthValue 
       MAX-ACCESS  read-write 
       STATUS      current 
       DESCRIPTION 
               "Reading this object always returns false(2). When the  
               cabhCdpSetToFactory object is set to true(1), the PS 
               must take the following actions: 
             
               1. Clear all cabhCdpLanAddrEntries in the CDP LAN Address  
                  Table. 
               2. The CDS must offer the factory default DHCP options at  
                  the next lease renewal time. 
               3. Reset the following objects to their factory default 
                  values: 
    
                  cabhCdpLanTransThreshold, 
                  cabhCdpLanTransAction, 
                  cabhCdpWanDataIpAddrCount, 
                  cabhCdpLanPoolStartType, 
                  cabhCdpLanPoolStart, 
                  cabhCdpLanPoolEndType, 
                  cabhCdpLanPoolEnd, 
                  cabhCdpServerNetworkNumberType, 
                  cabhCdpServerNetworkNumber, 
                  cabhCdpServerSubnetMaskType, 
                  cabhCdpServerSubnetMask, 
                  cabhCdpServerTimeOffset, 
                  cabhCdpServerRouterType, 
                  cabhCdpServerRouter, 
                  cabhCdpServerDnsAddressType, 
                  cabhCdpServerDnsAddress, 
                  cabhCdpServerSyslogAddressType, 
                  cabhCdpServerSyslogAddress, 
                  cabhCdpServerDomainName, 
                  cabhCdpServerTTL, 
                  cabhCdpServerInterfaceMTU, 
                  cabhCdpServerVendorSpecific, 
                  cabhCdpServerLeaseTime, 
                  cabhCdpServerDhcpAddressType, 
                  cabhCdpServerDhcpAddress, 
                  cabhCdpServerCommitStatus" 
       ::= { cabhCdpBase 1 } 
    
    
    
   cabhCdpLanTransCurCount OBJECT-TYPE 
       SYNTAX      Unsigned32 
       MAX-ACCESS  read-only 
       STATUS      current 
       DESCRIPTION 
               "The current number of active leases in the  
               cabhCdpLanAddrTable (the number of row entries in the 
               table that have a cabhCdpLanAddrMethod value of  
               reservationActive(2) or dynamicActive (4)). This count 
               does not include expired leases or reservations not 
               associated with a current lease." 
       ::= { cabhCdpBase 2 } 
    
   cabhCdpLanTransThreshold OBJECT-TYPE 
       SYNTAX      INTEGER (0..65533) 
       MAX-ACCESS  read-write 
       STATUS      current 
       DESCRIPTION 
               "The threshold number of LAN-Trans IP addresses allocated 
               or assigned  above  which the PS generates an alarm 
               condition. Whenever an attempt is made to allocate a 
               LAN-Trans IP address when cabhCdpLanTransCurCount is 
               greater than or equal to cabhCdpLanTransThreshold, an 
               event is generated. A value of 0 indicates that the CDP 
               sets the threshold at the highest number of addresses in 
               the  LAN address pool." 
       DEFVAL { 0 } 
       ::= { cabhCdpBase 3 } 
    
   cabhCdpLanTransAction OBJECT-TYPE 
       SYNTAX      INTEGER { 
                       normal(1), 
                       noAssignment(2) 
                   } 

       MAX-ACCESS  read-write 
       STATUS      current 
       DESCRIPTION 
               "The action taken when the CDS assigns a LAN-Trans 
               address and the number of LAN-Trans addresses assigned  
               (cabhCdpLanTransCurCount) is greater than the threshold  
               (cabhCdpLanTransThreshold). The actions are as follows: 
             
               normal - assign a LAN-Trans IP address as would normally  
                        occur if the threshold was not exceed. 
                   
               noAssignment - do not assign a LAN-Trans IP address" 
       DEFVAL { normal } 
       ::= { cabhCdpBase 4 } 
    
   cabhCdpWanDataIpAddrCount OBJECT-TYPE 
       SYNTAX      INTEGER ( 0..63 ) 
       MAX-ACCESS  read-write 
       STATUS      current 
       DESCRIPTION 
               "This is the number of WAN-Data IP addresses the PS's CDC  
               must attempt to acquire via DHCP."  
       DEFVAL { 0 } 
       ::= { cabhCdpBase 5 } 
    
    
   cabhCdpLastSetToFactory    OBJECT-TYPE 
           SYNTAX       TimeStamp 
           MAX-ACCESS   read-only 
           STATUS       current 
           DESCRIPTION 
                   "The value of sysUpTime when cabhCdpSetToFactory was  
                   last set to true. Zero if never reset." 
       ::= { cabhCdpBase 6 } 
    
   -- 
   --  CDP Address Management Tables 
   -- 
   --============================================================== 
   -- 
   --  cabhCdpLanAddrTable (CDP LAN Address Table) 
   -- 
   --  The cabhCdpLanAddrTable contains the DHCP parameters 
   --  for each IP address served to the LAN-Trans realm. 
   -- 
   --  This table contains a list of entries for the LAN side CDP 
   --  parameters. These parameters can be set either by the CDP or 
   --  by the cable operator through the CMP. 
   -- 
   --================================================================ 
   cabhCdpLanAddrTable OBJECT-TYPE 
       SYNTAX      SEQUENCE OF CabhCdpLanAddrEntry 
       MAX-ACCESS  not-accessible 
       STATUS      current 
       DESCRIPTION 
               "This table is a list of LAN-Trans realm parameters. 
               This table has one row entry for each allocated LAN-Trans  
               IP address. Each row must have at least a valid  
               cabhCdpLanAddrMethod, a cabhCdpLanAddrIpType, a unique  
               cabhCdpLanAddrIp, and a unique cabhCdpLanAddrClientId 
               value. 
                            
               Static/Manual address assignment: To create a new DHCP  
               address reservation, the NMS creates a row with: an index 
               comprised of a new cabhCdpLanAddrIp and its  
               cabhCdpLanAddrIpType, a new unique cabhCdpLanAddrClientID 
               (an empty LeaseCreateTime and empty LeaseExpireTime,) 
               and a cabhCdpLanDataAddrRowStatus of createAndGo(4).  
               If the syntax and values of the new row - indicating a  
               reservation - are valid, the PS must set   
               cabhCdpLanAddrMethod to reservationInactive(1) and 
               cabhCdpLanDataAddrRowStatus to active(1). When the PS 
               grants a lease for a reserved IP, it must set the  
               cabhCdpLanAddrMethod object for that row to  
               reservationActive(2). When a lease for a reserved IP  
               expires, the PS must set the corresponding rowÆs 
               cabhCdpLanAddrMethod object to reservationInactive(1). 
               For row entries that represent lease reservations - rows 
               in which the cabhCdpLanAddrMethod object has a value of 
               either reservationInactive(1) or reservationActive(2) - 
               the cabhCdpLanAddrIpType, cabhCdpLanAddrIp,  
               cabhCdpLanAddrClientID, cabhCdpLanAddrMethod, and  
               cabhCdpLanAddrHostName object values must persist across 
               PS reboots. 
                 
               Dynamic address assignment: When the PS grants a lease 
               for a non-reserved IP, it must set the 
               cabhCdpLanAddrMethod object for that row to 
               dynamicActive(4). When a lease for a non-reserved IP 
               expires, the PS must set the corresponding rowÆs 
               cabhCdpLanAddrMethod object to dynamicInactive(3). 
               The PS must create new row entries using 
               cabhCdpLanAddrIp values that are unique to this table. 
                
               If all cabhCdpLanAddrIp values in the range defined by  
               cabhCdpLanPoolStart and cabhCdpLanPoolEnd are in use in 
               this table, the PS may overwrite the 
               cabhCdpLanAddrClientId of a row that has a 
               cabhCdpLanAddrMethod object with a value of  
               dynamicInactive(3) with a new cabhCdpLanAddrClientId 
               value and use that cabhCdpLanAddrIp as part of a new 
               lease. For row entries that represent active leases - 
               rows in which the cabhCdpLanAddrMethod object has a value 
               of dynamicActive(4) - the cabhCdpLanAddrIpType,  
               cabhCdpLanAddrIp, cabhCdpLanAddrClientID,  
               cabhCdpLanAddrMethod, and cabhCdpLanAddrHostName object  
               values must persist across PS reboots." 
                
       ::= {  cabhCdpAddr 1 } 
    
   cabhCdpLanAddrEntry OBJECT-TYPE 
       SYNTAX      CabhCdpLanAddrEntry 
       MAX-ACCESS  not-accessible 
       STATUS      current 
       DESCRIPTION 
               "List of general parameters pertaining to LAN-Trans IP  
               address reservations and leases. 
    
               Implementors need to be aware that if the size 
               of cabhCdpLanAddrIp exceeds 115 octets then OIDs 
               of column instances in this table will have more 
               than 128 sub-identifiers and cannot be accessed 
               using SNMPv1, SNMPv2c, or SNMPv3." 
       INDEX { cabhCdpLanAddrIpType, cabhCdpLanAddrIp } 
       ::= { cabhCdpLanAddrTable 1 } 
    
   CabhCdpLanAddrEntry ::= SEQUENCE { 
       cabhCdpLanAddrIpType            InetAddressType, 
       cabhCdpLanAddrIp                InetAddress, 
       cabhCdpLanAddrClientID          MacAddress, 
       cabhCdpLanAddrLeaseCreateTime   DateAndTime, 
       cabhCdpLanAddrLeaseExpireTime   DateAndTime, 
       cabhCdpLanAddrMethod            INTEGER, 
       cabhCdpLanAddrHostName          SnmpAdminString, 
       cabhCdpLanAddrRowStatus         RowStatus 
       } 
    
   cabhCdpLanAddrIpType OBJECT-TYPE 
       SYNTAX      InetAddressType 
       MAX-ACCESS  not-accessible 
       STATUS      current 
       DESCRIPTION 
               "The type of IP address assigned to the LAN IP Device in 
               the LAN-Trans Realm." 
     
       ::= { cabhCdpLanAddrEntry 1 } 

   cabhCdpLanAddrIp OBJECT-TYPE 
       SYNTAX      InetAddress 
       MAX-ACCESS  not-accessible 
       STATUS      current 
       DESCRIPTION  
               "The address assigned to the LAN IP Device. This 
               parameter is entered by the CDP when the CDS grants a 
               lease to a LAN IP Device in the LAN-Trans realm and 
               creates a row in this table. 
               Alternatively, this parameter can be entered by the NMS  
               through the CMP, when the NMS creates a new DHCP address  
               reservation.  
               Each cabhCdpLanAddrIp in the table must fall within the  
               range of IPs defined inclusively by cabhCdpLanPoolStart 
               and cabhCdpLanPoolEnd. The PS must return an 
               inconsistentValue error if the NMS attempts to create a 
               row entry with a cabhCdpLanAddrIP value that falls 
               outside of this range or is not unique fom all existing 
               cabhCdpLanAddrIP entries in this table. The address type 
               of this object is specified by cabhCdpLanAddrIpType." 
           
       ::= { cabhCdpLanAddrEntry 2 } 
    
   cabhCdpLanAddrClientID OBJECT-TYPE 
       SYNTAX      MacAddress 
       MAX-ACCESS  read-create 
       STATUS      current 
       DESCRIPTION 
               "The client's (i.e., LAN IP Device's) hardware address 
               as indicated in the chaddr field of its DHCP REQUEST 
               message. There is a one-to-one relationship between the 
               hardware address and the LAN IP Device. This parameter 
               is entered by the PS (CDP) when the CDS grants a lease 
               to a LAN IP Device in the LAN-Trans realm and creates a 
               row in this table.  Alternatively this parameter can be 
               created by the NMS through the CMP, when the NMS creates 
               a new DHCP address reservation by accessing the 
               cabhCdpLanDataAddrRowStatus object with an index 
               comprised of a unique cabhCdpLanAddrIp and creating a 
               row with a unique cabhCdpLanAddrClientID." 
       ::= { cabhCdpLanAddrEntry 3 } 
    
   cabhCdpLanAddrLeaseCreateTime OBJECT-TYPE 
       SYNTAX      DateAndTime 
       MAX-ACCESS  read-only 
       STATUS      current 
       DESCRIPTION 
               "This is the date and time that the LAN-Trans lease 
               was created (if it has not yet been renewed) or last 
               renewed." 
       ::= { cabhCdpLanAddrEntry 4 } 
    
   cabhCdpLanAddrLeaseExpireTime OBJECT-TYPE 
       SYNTAX      DateAndTime 
       MAX-ACCESS  read-only 
       STATUS      current 
       DESCRIPTION 
           "This is the date and time that the LAN-trans lease expired 
           or will expire." 
       ::= { cabhCdpLanAddrEntry 5 } 
    
   cabhCdpLanAddrMethod OBJECT-TYPE 
       SYNTAX INTEGER { 
                  reservationInactive(1), 
                  reservationActive(2), 
                  dynamicInactive(3), 
                  dynamicActive(4) 
               } 
       MAX-ACCESS   read-only 
       STATUS       current 
       DESCRIPTION 
               "The IP allocation method indicated by this row. 
               reservationInactive(1) indicates a reserved IP that has 
               not yet been leased or that has an expired lease. 
               reservationActive(2) indicates a reserved IP that has 
               an active lease. 
               dynamicInactive(3) indicates an IP that was once 
               dynamically assigned to a LAN-Trans device but currently 
               has an expired lease. 
               dynamicActive(4) indicates an IP that was dynamically  
               assigned to a LAN-Trans device that has a current lease." 
       ::= { cabhCdpLanAddrEntry 6 }     
    
   cabhCdpLanAddrHostName OBJECT-TYPE 
       SYNTAX      SnmpAdminString(SIZE(0..80)) 
       MAX-ACCESS  read-only 
       STATUS      current 
       DESCRIPTION 
               "This is the Host Name of the LAN IP address, based on 
               DHCP option 12." 
       ::= { cabhCdpLanAddrEntry 7 } 
    
    
   cabhCdpLanAddrRowStatus OBJECT-TYPE 
       SYNTAX      RowStatus 
       MAX-ACCESS  read-create 
       STATUS      current 
       DESCRIPTION 
               "The RowStatus interlock for creation and deletion of 
               row entries. The PS must not allow the NMS to set 
               RowStatus to notInService(2). The PS must assign a 
               RowStatus of notInService(2) to any new row entry 
               created with a non-unique cabhCdpLanAddrClientID value. 
               The PS must assign a RowStatus of notReady(3) to any new 
               row entry created without a cabhCdpLanAddrClientID.  The 
               PS will prevent modification of this tableÆs columns and 
               return an inconsistentValue error, if the NMS attempts 
               to make such modifications while the RowStatus is 
               active(1)." 
       ::= { cabhCdpLanAddrEntry 8 } 
    
    
   --============================================================== 
   -- 
   --  cabhCdpWanDataAddrTable (CDP WAN-Data Address Table) 
   -- 
   --  The cabhCdpWanDataAddrTable contains the configuration or DHCP 
   --  parameters for each IP address mapping per WAN-Data IP Address.      
   -- 
   --============================================================== 
    
   cabhCdpWanDataAddrTable OBJECT-TYPE 
       SYNTAX      SEQUENCE OF CabhCdpWanDataAddrEntry 
       MAX-ACCESS  not-accessible 
       STATUS      current 
       DESCRIPTION 
               "This table contains WAN-Data address realm information."  
       ::= {  cabhCdpAddr 2 } 
    
   cabhCdpWanDataAddrEntry OBJECT-TYPE 
       SYNTAX      CabhCdpWanDataAddrEntry 
       MAX-ACCESS  not-accessible 
       STATUS      current 
       DESCRIPTION 
               "List of general parameter for CDP WAN-Data address 
               realm." 
       INDEX { cabhCdpWanDataAddrIndex } 
       ::= { cabhCdpWanDataAddrTable 1 } 
    
   CabhCdpWanDataAddrEntry ::= SEQUENCE { 
       cabhCdpWanDataAddrIndex         INTEGER, 
       cabhCdpWanDataAddrClientId      OCTET STRING, 
       cabhCdpWanDataAddrIpType        InetAddressType, 
       cabhCdpWanDataAddrIp            InetAddress, 
       cabhCdpWanDataAddrRenewalTime   Integer32, 
       cabhCdpWanDataAddrRowStatus     RowStatus 
       } 
    
    
   cabhCdpWanDataAddrIndex OBJECT-TYPE 
       SYNTAX      INTEGER (1..65535) 
       MAX-ACCESS  not-accessible 
       STATUS      current 
       DESCRIPTION 
               "Index into table." 
       ::= { cabhCdpWanDataAddrEntry 1 } 
    
   cabhCdpWanDataAddrClientId OBJECT-TYPE 
       SYNTAX OCTET STRING (SIZE (1..80)) 
       MAX-ACCESS  read-create 
       STATUS      current 
       DESCRIPTION 
               "A unique WAN-Data ClientID used when attempting the 
               acquire a WAN-Data IP Address via DHCP." 
       ::= { cabhCdpWanDataAddrEntry 2 } 
    
   cabhCdpWanDataAddrIpType OBJECT-TYPE 
       SYNTAX      InetAddressType 
       MAX-ACCESS  read-only 
       STATUS      current 
       DESCRIPTION 
               "The address type assigned on the WAN-Data side." 
       DEFVAL { ipv4 } 
       ::= { cabhCdpWanDataAddrEntry 3 } 
    
   cabhCdpWanDataAddrIp OBJECT-TYPE 
       SYNTAX      InetAddress 
       MAX-ACCESS  read-only 
       STATUS      current 
       DESCRIPTION 
               "The address assigned on the WAN-Data side." 
       ::= { cabhCdpWanDataAddrEntry 4 } 
        
   cabhCdpWanDataAddrRenewalTime OBJECT-TYPE 
       SYNTAX      Integer32 
       MAX-ACCESS  read-only 
       STATUS      current 
       DESCRIPTION 
               "This is the time remaining before the lease expires. 
               This is based on DHCP Option 51." 
       ::= { cabhCdpWanDataAddrEntry 5 } 
    
   cabhCdpWanDataAddrRowStatus OBJECT-TYPE 
       SYNTAX      RowStatus 
       MAX-ACCESS  read-create 
       STATUS      current 
       DESCRIPTION 
               "The RowStatus interlock for creation and deletion of 
               row entries. Any writable object in a row can be 
               modified at any time while the row is active(1). The PS 
               must assign a RowStatus of notInService(2) to any new 
               row entry created with a cabhCdpWanDataAddrClientId that 
               is not unique within this table." 
       ::= { cabhCdpWanDataAddrEntry 6 } 
    
   --============================================================== 
   -- 
   --  cabhCdpWanDnsServerTable (CDP WAN DNS Server Table) 
   -- 
   --  The cabhCdpWanDnsServerTable is a table of 3 cable network  
   --  and Internet DNS Servers. 
   -- 
   --============================================================== 
    
   cabhCdpWanDnsServerTable OBJECT-TYPE 
       SYNTAX      SEQUENCE OF CabhCdpWanDnsServerEntry 
       MAX-ACCESS  not-accessible 
       STATUS      current 
       DESCRIPTION 
               "This table contains the IP addresses of cable network 
               and Internet DNS servers, in the order of preference in 
               which the PSÆs CNP will query them, when it cannot 
               resolve a DNS query using local information. Entries in 
               this table are updated with the information contained in 
               DHCP Option 6, received during both the WAN-Man and 
               WAN-Data IP acquisition processes." 
       ::= {  cabhCdpAddr 3 } 
    
   cabhCdpWanDnsServerEntry OBJECT-TYPE 
       SYNTAX      CabhCdpWanDnsServerEntry 
       MAX-ACCESS  not-accessible 
       STATUS      current 
       DESCRIPTION 
               "List of cable network and Internet DNS servers." 
       INDEX { cabhCdpWanDnsServerOrder } 
       ::= { cabhCdpWanDnsServerTable 1 } 
    
   CabhCdpWanDnsServerEntry ::= SEQUENCE { 
       cabhCdpWanDnsServerOrder INTEGER, 
       cabhCdpWanDnsServerIpType InetAddressType, 
       cabhCdpWanDnsServerIp InetAddress 
       } 
    
    
   cabhCdpWanDnsServerOrder OBJECT-TYPE 
       SYNTAX      INTEGER {  
                       primary(1), 
                       secondary(2), 
                       tertiary(3) 
                   } 

       MAX-ACCESS  not-accessible 
       STATUS      current 
       DESCRIPTION 
               "The order of preference for cable network and Internet 
               DNS servers, as listed in DHCP option 6 (Domain Server). 
               Any time the CDC receives valid IP address information  
               within DHCP Option 6, as part of lease acquisition or  
               renewal of a WAN-Man or WAN-Data IP, it must update this  
               information into this table. As entries in DHCP Option 6  
               are listed in order of preference the highest priority  
               entry in DHCP Option 6 must correspond to the row with a  
               cabhCdpWanDataAddrDnsOrder equal to 1. If DHCP Option 6  
               contains 2 valid IP addresses, the PS must update the 
               rows with cabhCdpWanDataAddrDnsOrder values of 1 and 2. 
               If DHCP Option 6 contains 3 valid IP addresses, the PS 
               must update rows with cabhCdpWanDataAddrDnsOrder values 
               of 1, 2, and 3. Any DNS server information included in 
               DHCP Option 6 beyond primary, secondary and tertiary 
               will not be represented in this table." 
       ::= { cabhCdpWanDnsServerEntry 1 } 
    
    
   cabhCdpWanDnsServerIpType OBJECT-TYPE 
       SYNTAX      InetAddressType 
       MAX-ACCESS  read-only 
       STATUS      current 
       DESCRIPTION 
               "This parameter indicates the IP address Type of a WAN 
               DNS server." 
       DEFVAL { ipv4 } 
       ::= { cabhCdpWanDnsServerEntry 2 } 
    
   cabhCdpWanDnsServerIp OBJECT-TYPE 
       SYNTAX      InetAddress 
       MAX-ACCESS  read-only 
       STATUS      current 
       DESCRIPTION 
               "This parameter indicates the IP address of the WAN DNS 
               server. The type of this address is specified by  
               cabhCdpWanDnsServerIpType." 
       ::= { cabhCdpWanDnsServerEntry 3 } 
    
    
   -- 
   --  DHCP Server Side (CDS) Option Values for the LAN-Trans realm 
   --                            
    
    
   cabhCdpLanPoolStartType OBJECT-TYPE 
       SYNTAX      InetAddressType 
       MAX-ACCESS  read-write 
       STATUS      current 
       DESCRIPTION 
               "The Address type of the start of range LAN Trans IP  
               Addresses." 
       DEFVAL { ipv4 }     
       ::= { cabhCdpServer 1 } 
    
   cabhCdpLanPoolStart OBJECT-TYPE 
       SYNTAX      InetAddress 
       MAX-ACCESS  read-write 
       STATUS      current 
       DESCRIPTION 
               "The start of range LAN Trans IP Addresses. The type of 
               this address is specified by cabhCdpLanPoolStartType." 
       DEFVAL { 'c0a8000a'h }    -- 192.168.0.10  
           --192.168.0.0 is the network number 
       -- 192.168.0.255 is broadcast  
       -- address and 192.168.0.1 
       -- is reserved for the router 
       ::= { cabhCdpServer 2 } 
    
   cabhCdpLanPoolEndType OBJECT-TYPE 
       SYNTAX      InetAddressType 
       MAX-ACCESS  read-write 
       STATUS      current 
       DESCRIPTION 
               "The Address type of the end of range LAN Trans IP  
               Addresses." 
       DEFVAL { ipv4 }     
       ::= { cabhCdpServer 3 } 
    
   cabhCdpLanPoolEnd OBJECT-TYPE 
       SYNTAX      InetAddress 
       MAX-ACCESS  read-write 
       STATUS      current 
       DESCRIPTION 
               "The end of range for LAN-Trans IP Addresses. The type 
               of this address is specified by cabhCdpLanPoolEndType." 
       DEFVAL { 'c0a800fe'h }    -- 192.168.0.254 
       ::= { cabhCdpServer 4 } 
    
   cabhCdpServerNetworkNumberType    OBJECT-TYPE 
       SYNTAX      InetAddressType 
       MAX-ACCESS    read-write 
       STATUS      current 
       DESCRIPTION 
               "The IP address type of the LAN-Trans network number." 
       DEFVAL  { ipv4 } 
   ::= { cabhCdpServer 5 } 
   cabhCdpServerNetworkNumber        OBJECT-TYPE 
       SYNTAX        InetAddress 
       MAX-ACCESS    read-write 
       STATUS        current 
       DESCRIPTION 
               "The LAN-Trans network number. The type of this address  
               is specified by cabhCdpServerNetworkNumberType." 
       DEFVAL  { 'c0a80000'h }  
   ::= { cabhCdpServer 6 } 
    
    
    
   cabhCdpServerSubnetMaskType OBJECT-TYPE 
       SYNTAX      InetAddressType 
       MAX-ACCESS  read-write 
       STATUS      current 
       DESCRIPTION 
               "Type of LAN-Trans Subnet Mask." 
       DEFVAL { ipv4 } 
       ::= { cabhCdpServer 7 } 
    
   cabhCdpServerSubnetMask    OBJECT-TYPE 
       SYNTAX      InetAddress 
       MAX-ACCESS  read-write 
       STATUS      current 
       DESCRIPTION 
               "Option value 1 - Value of LAN-Trans Subnet Mask." 
       DEFVAL { 'ffffff00'h }    -- 255.255.255.0 
       ::= { cabhCdpServer 8 } 
    
   cabhCdpServerTimeOffset    OBJECT-TYPE 
       SYNTAX      Integer32 (-86400..86400) --0 to 24 hours(in seconds) 
       UNITS    "seconds" 
       MAX-ACCESS  read-write 
       STATUS      current 
       DESCRIPTION 
               "Option value 2 - Value of LAN-Trans Time Offset from  
               Coordinated Universal Time (UTC)." 
       DEFVAL { 0 }    -- UTC 
       ::= { cabhCdpServer 9 } 
    
   cabhCdpServerRouterType    OBJECT-TYPE 
       SYNTAX  InetAddressType 
       MAX-ACCESS  read-write 
       STATUS      current 
       DESCRIPTION 
               "Type of Address, Router for the LAN-Trans address 
               realm." 
       DEFVAL { ipv4 }  
       ::= { cabhCdpServer 10 } 
    
   cabhCdpServerRouter    OBJECT-TYPE 
       SYNTAX  InetAddress 
       MAX-ACCESS  read-write 
       STATUS      current 
       DESCRIPTION 
               "Option value 3 - Router for the LAN-Trans address realm.  
               The type of this address is specified by  
               cabhCdpServerRouterType." 
       DEFVAL { 'c0a80001'h }    -- 192.168.0.1 
       ::= { cabhCdpServer 11 } 
    
   cabhCdpServerDnsAddressType OBJECT-TYPE 
       SYNTAX      InetAddressType 
       MAX-ACCESS  read-write 
       STATUS      current 
       DESCRIPTION 
               "The Type of IP Addresses of the LAN-Trans address realm  
               DNS servers."   
       DEFVAL { ipv4 }  
       ::= { cabhCdpServer 12 } 
    
   cabhCdpServerDnsAddress OBJECT-TYPE 
       SYNTAX      InetAddress 
       MAX-ACCESS  read-write 
       STATUS      current 
       DESCRIPTION 
               "The IP Addresses of the LAN-Trans address realm DNS 
               servers. As a default there is only one DNS server and 
               it is the address specified in Option Value 3 - 
               cabhCdpServerRouter. Only one address is specified. The 
               type of this address is specified by 
               cabhCdpServerDnsAddressType." 
       DEFVAL { 'c0a80001'h }    -- 192.168.0.1 
       ::= { cabhCdpServer 13 } 
    
   cabhCdpServerSyslogAddressType OBJECT-TYPE 
       SYNTAX      InetAddressType 
       MAX-ACCESS  read-write 
       STATUS      current 
       DESCRIPTION 
               "The Type of IP Address of the LAN-Trans SYSLOG servers."   
       DEFVAL { ipv4 }   
       ::= { cabhCdpServer 14 } 
    
   cabhCdpServerSyslogAddress OBJECT-TYPE 
       SYNTAX      InetAddress 
       MAX-ACCESS  read-write 
       STATUS      current 
       DESCRIPTION 
               "The IP Addresses of the LAN-Trans SYSLOG servers. 
               As a default there are no SYSLOG Servers. The factory  
               defaults contains the indication of no Syslog Server 
               value equals (0.0.0.0)." 
       DEFVAL { '00000000'h }    -- 0.0.0.0 
       ::= { cabhCdpServer 15 } 
    
   cabhCdpServerDomainName    OBJECT-TYPE 
       SYNTAX      SnmpAdminString(SIZE(0..128)) 
       MAX-ACCESS  read-write 
       STATUS      current 
       DESCRIPTION 
               "Option value 15 - Domain name of LAN-Trans address 
               realm." 
       DEFVAL {""} 
       ::= { cabhCdpServer 16 } 
    
   cabhCdpServerTTL    OBJECT-TYPE 
       SYNTAX      INTEGER (0..255) 
       MAX-ACCESS  read-write 
       STATUS      current 
       DESCRIPTION 
               "Option value 23 - LAN-Trans Time to Live." 
       DEFVAL  { 64 } 
       ::= { cabhCdpServer 17 } 
    
   cabhCdpServerInterfaceMTU    OBJECT-TYPE 
       SYNTAX      INTEGER (0| 68..4096) 
       MAX-ACCESS  read-write 
       STATUS      current 
       DESCRIPTION 
               "Option value 26 - LAN-Trans Interface MTU. if the value 
               of this object is 0, the PS must not include this option 
               in its DHCP offer or DHCP Ack messages to LAN IP devices" 
       DEFVAL { 0 } 
       ::= { cabhCdpServer 18 } 
    
   cabhCdpServerVendorSpecific    OBJECT-TYPE 
       SYNTAX      OCTET STRING (SIZE(0..255)) 
       MAX-ACCESS  read-write 
       STATUS      current 
       DESCRIPTION 
               "Option value 43 - Vendor Specific Options." 
       DEFVAL  { ''h }  
       ::= { cabhCdpServer 19 } 
    
   cabhCdpServerLeaseTime    OBJECT-TYPE 
       SYNTAX      Unsigned32 
       UNITS       "seconds" 
       MAX-ACCESS  read-write 
       STATUS      current 
       DESCRIPTION 
               "Option value 51 ûLease Time for LAN IP Devices in the  
               LAN-Trans realm (seconds)." 
       DEFVAL  { 3600 } 
       ::= { cabhCdpServer 20 } 
    
   cabhCdpServerDhcpAddressType    OBJECT-TYPE 
       SYNTAX      InetAddressType 
       MAX-ACCESS  read-write 
       STATUS      current 
       DESCRIPTION 
               "Option value 54 - Type of LAN-Trans DHCP server IP  
               address."  
       DEFVAL { ipv4 } 
       ::= { cabhCdpServer 21 } 
    
   cabhCdpServerDhcpAddress    OBJECT-TYPE 
       SYNTAX      InetAddress 
       MAX-ACCESS  read-write 
       STATUS      current 
       DESCRIPTION 
               "Option value 54 - LAN-Trans DHCP server IP address.  
               It defaults to the router address as specified in  
               cabhCdpServerRouter.  Alternatively a vendor may want to  
               separate CDS address from router address. The type of 
               this address is specified by 
               cabhCdpServerDhcpAddressType." 
       DEFVAL { 'c0a80001'h }        --    192.168.0.1 
       ::= { cabhCdpServer 22 } 
    
    
   cabhCdpServerControl OBJECT-TYPE 
       SYNTAX      INTEGER { 
                      restoreConfig(1), 
                      commitConfig(2) 
                    } 
       MAX-ACCESS read-write 
       STATUS current 
       DESCRIPTION 
               "The control for the CDS (DHCP Server) configuration. 
               All changes to the cabhCdpServer mib objects are 
               reflected when reading the value of the mib objects; 
               however, those changes are NOT applied to the running 
               configuration of the CDS until they are successfully 
               committed via use of the cabhCdpServerControl object. 
               If changes are made to the cabhCdpServer mib objects 
               which are not yet successfully committed to the CDS, 
               the cabhCdpServerControl object can be used to rollback 
               all changes to the last valid CDS configuration and 
               discard all intermediate changes. 
         
               restoreConfig - Setting cabhCdpServerControl to this 
                               value will cause any changes to the 
                               cabhCdpServer objects not yet committed 
                               be reset to the values from the current 
                               running configuration of the CDS. 
               commitConfig û  Setting cabhCdpServerControl to this 
                               value will cause the CDS to validate and 
                               apply the valid cabhCdpServer mib 
                               settings to its running configuration. 
                               The cabhCdpServerCommitStatus object 
                               will detail the status of this 
                               operation." 
       DEFVAL { restoreConfig } 
   ::= { cabhCdpServer 23 } 
    
    
   cabhCdpServerCommitStatus OBJECT-TYPE 
       SYNTAX      INTEGER { 
                     commitSucceeded (1), 
                     commitNeeded (2), 
                     commitFailed (3) 
                 } 
       MAX-ACCESS  read-only 
       STATUS current 
       DESCRIPTION 
               "Indicates the status of commiting the current 
               cabhCdpServer mib object values to the running 
               configuration of the CDS (DHCP Server).  
            
               commitSucceeded - indicates the current cabhCdpServer mib  
                                 object values are valid and have been  
                                 successfully committed to the running  
                                 configuration of the CDS.  
    
               commitNeeded -    indicates that the value of one or 
                                 more objects in cabhCdpServer mib group 
                                 have been changed but not yet committed 
                                 to the running configuration of the 
                                 CDS. 
    
               commitFailed û    indicates the PS was unable to commit 
                                 the cabhCdpServer mib object values to 
                                 the running configuration of the CDS 
                                 due to conflicts in those values." 
       DEFVAL { commitSucceeded } 
   ::= { cabhCdpServer 24 } 
   -- 
   -- notification group is for future extension. 
   --  
    
   cabhCdpNotification  OBJECT IDENTIFIER ::= { cabhCdpMib 2 } 
   cabhCdpNotifications OBJECT IDENTIFIER ::= { cabhCdpNotification 0 } 
   cabhCdpConformance   OBJECT IDENTIFIER ::= { cabhCdpMib 3 } 
   cabhCdpCompliances   OBJECT IDENTIFIER ::= { cabhCdpConformance 1 } 
   cabhCdpGroups        OBJECT IDENTIFIER ::= { cabhCdpConformance 2 } 
    
   -- 
   --    Notification Group 
   -- 
    
    
   -- compliance statements 
    
   cabhCdpBasicCompliance MODULE-COMPLIANCE 
       STATUS     current 
       DESCRIPTION 
               "The compliance statement for devices that implement the  
               CableHome Portal Services functionality." 
       MODULE   --cabhCdpMib 
    
    
   -- unconditionally mandatory groups 
    
       MANDATORY-GROUPS { 
               cabhCdpGroup 
       } 
    
       OBJECT cabhCdpLanAddrIpType 
          SYNTAX InetAddressType { ipv4(1) } 
          DESCRIPTION 
              "An implementation is only required to support IPv4 
               addresses." 
    
       OBJECT cabhCdpLanAddrIp 
          SYNTAX  InetAddress (SIZE(4)) 
          DESCRIPTION 
              "An implementation is only required to support IPv4 
               addresses." 
    
       OBJECT cabhCdpWanDataAddrIpType 
          SYNTAX InetAddressType { ipv4(1) } 
          DESCRIPTION 
              "An implementation is only required to support IPv4 
               addresses." 

       OBJECT cabhCdpWanDataAddrIp 
          SYNTAX  InetAddress (SIZE(4)) 
          DESCRIPTION 
              "An implementation is only required to support IPv4 
               addresses." 
    
       OBJECT cabhCdpWanDnsServerIpType 
          SYNTAX InetAddressType { ipv4(1) } 
          DESCRIPTION 
              "An implementation is only required to support IPv4 
               addresses." 
    
       OBJECT cabhCdpWanDnsServerIp 
          SYNTAX  InetAddress (SIZE(4)) 
          DESCRIPTION 
              "An implementation is only required to support IPv4 
               addresses." 
    
       OBJECT cabhCdpLanPoolStartType 
          SYNTAX InetAddressType { ipv4(1) } 
          DESCRIPTION 
              "An implementation is only required to support IPv4 
               addresses." 
    
       OBJECT cabhCdpLanPoolStart 
          SYNTAX  InetAddress (SIZE(4)) 
          DESCRIPTION 
              "An implementation is only required to support IPv4 
               addresses." 
    
       OBJECT cabhCdpLanPoolEndType 
          SYNTAX InetAddressType { ipv4(1) } 
          DESCRIPTION 
              "An implementation is only required to support IPv4 
               addresses." 
    
       OBJECT cabhCdpLanPoolEnd 
          SYNTAX  InetAddress (SIZE(4)) 
          DESCRIPTION 
              "An implementation is only required to support IPv4 
               addresses." 
    
       OBJECT cabhCdpServerNetworkNumberType 
          SYNTAX InetAddressType { ipv4(1) } 
          DESCRIPTION 
              "An implementation is only required to support IPv4 
               addresses." 
    
       OBJECT cabhCdpServerNetworkNumber 
          SYNTAX  InetAddress (SIZE(4)) 
          DESCRIPTION 
              "An implementation is only required to support IPv4 
               addresses." 
    
       OBJECT cabhCdpServerSubnetMaskType 
          SYNTAX InetAddressType { ipv4(1) } 
          DESCRIPTION 
              "An implementation is only required to support IPv4 
               addresses." 
    
       OBJECT cabhCdpServerSubnetMask 
          SYNTAX  InetAddress (SIZE(4)) 
          DESCRIPTION 
              "An implementation is only required to support IPv4 
               addresses." 
    
       OBJECT cabhCdpServerRouterType 
          SYNTAX InetAddressType { ipv4(1) } 
          DESCRIPTION 
              "An implementation is only required to support IPv4 
               addresses." 
    
       OBJECT cabhCdpServerRouter 
          SYNTAX  InetAddress (SIZE(4)) 
          DESCRIPTION 
              "An implementation is only required to support IPv4 
               addresses." 
    
       OBJECT cabhCdpServerDnsAddressType 
          SYNTAX InetAddressType { ipv4(1) } 
          DESCRIPTION 
              "An implementation is only required to support IPv4 
               addresses." 
    
       OBJECT cabhCdpServerDnsAddress 
          SYNTAX  InetAddress (SIZE(4)) 
          DESCRIPTION 
              "An implementation is only required to support IPv4 
               addresses." 
    
       OBJECT cabhCdpServerSyslogAddressType 
          SYNTAX InetAddressType { ipv4(1) } 
          DESCRIPTION 
              "An implementation is only required to support IPv4 
               addresses." 
    
       OBJECT cabhCdpServerSyslogAddress 
          SYNTAX  InetAddress (SIZE(4)) 
          DESCRIPTION 
              "An implementation is only required to support IPv4 
               addresses." 
    
       OBJECT cabhCdpServerDhcpAddressType 
          SYNTAX InetAddressType { ipv4(1) } 
          DESCRIPTION 
              "An implementation is only required to support IPv4 
               addresses." 
    
       OBJECT cabhCdpServerDhcpAddress 
          SYNTAX  InetAddress (SIZE(4)) 
          DESCRIPTION 
              "An implementation is only required to support IPv4 
               addresses." 
    
    
   ::= { cabhCdpCompliances 3 } 
    
    
   cabhCdpGroup        OBJECT-GROUP  
    
       OBJECTS { 
    
           cabhCdpSetToFactory, 
           cabhCdpLanTransCurCount, 
           cabhCdpLanTransThreshold, 
           cabhCdpLanTransAction, 
           cabhCdpWanDataIpAddrCount, 
           cabhCdpLastSetToFactory, 
    
           cabhCdpLanAddrClientID, 
           cabhCdpLanAddrLeaseCreateTime, 
           cabhCdpLanAddrLeaseExpireTime, 
           cabhCdpLanAddrMethod, 
           cabhCdpLanAddrHostName, 
           cabhCdpLanAddrRowStatus, 
    
           cabhCdpWanDataAddrClientId, 
           cabhCdpWanDataAddrIpType, 
           cabhCdpWanDataAddrIp, 
           cabhCdpWanDataAddrRenewalTime, 
           cabhCdpWanDataAddrRowStatus, 
    
           cabhCdpWanDnsServerIpType, 
           cabhCdpWanDnsServerIp, 
    
           cabhCdpLanPoolStartType, 
           cabhCdpLanPoolStart, 
           cabhCdpLanPoolEndType, 
           cabhCdpLanPoolEnd, 
           cabhCdpServerNetworkNumberType, 
           cabhCdpServerNetworkNumber, 
           cabhCdpServerSubnetMaskType, 
           cabhCdpServerSubnetMask, 
           cabhCdpServerTimeOffset, 
    
           cabhCdpServerRouterType, 
           cabhCdpServerRouter, 
    
           cabhCdpServerDnsAddressType, 
           cabhCdpServerDnsAddress, 
           cabhCdpServerSyslogAddressType, 
           cabhCdpServerSyslogAddress, 
           cabhCdpServerDomainName, 
           cabhCdpServerTTL, 
           cabhCdpServerInterfaceMTU, 
           cabhCdpServerVendorSpecific, 
           cabhCdpServerLeaseTime, 
           cabhCdpServerDhcpAddressType, 
           cabhCdpServerDhcpAddress, 
           cabhCdpServerControl, 
           cabhCdpServerCommitStatus 
       } 
       STATUS    current 
       DESCRIPTION 
               "Group of objects for CableHome CDP MIB." 
       ::= { cabhCdpGroups 1 }  
    
   END 

--  
--    Copyright (C) The Internet Society (2003). All Rights Reserved. 
--     
--    This document and translations of it may be copied and furnished to 
--    others, and derivative works that comment on or otherwise explain it 
--    or assist in its implementation may be prepared, copied, published 
--    and distributed, in whole or in part, without restriction of any 
--    kind, provided that the above copyright notice and this paragraph are 
--    included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE."
