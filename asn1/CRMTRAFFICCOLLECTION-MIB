-- automatically generated by mosy 7.1 #1 (elc), do not edit!

CRMTRAFFICCOLLECTION-MIB DEFINITIONS ::= BEGIN


IMPORTS
	DisplayString
		FROM RFC1213-MIB
	OBJECT-TYPE
		FROM RFC-1212
	Counter, IpAddress
		FROM RFC1155-SMI
	mib-2, ifIndex
		FROM RFC1213-MIB
	RowStatus, TimeStamp, DateAndTime
		FROM SNMPv2-TC;

org OBJECT IDENTIFIER ::= { iso  3 }

dod OBJECT IDENTIFIER ::= { org  6 }

internet OBJECT IDENTIFIER ::= { dod  1 }

private OBJECT IDENTIFIER ::= { internet  4 }

enterprises OBJECT IDENTIFIER ::= { private  1 }

ntt OBJECT IDENTIFIER ::= { enterprises  210 }

mibDoc OBJECT IDENTIFIER ::= { ntt  2 }

ba3000 OBJECT IDENTIFIER ::= { mibDoc  8 }

crmCommon OBJECT IDENTIFIER ::= { ba3000  1 }

-- created from crmTraffic (9605221200Z)

crmTraffic OBJECT IDENTIFIER ::= { crmCommon  4 }

crmTrCollectIntervalTable OBJECT-TYPE
    SYNTAX  SEQUENCE OF CrmTrCollectIntervalEntry
    ACCESS  not-accessible
    STATUS  mandatory
    DESCRIPTION
           "DUMMY"
    ::= { crmTraffic  1 }

crmTrCollectIntervalEntry OBJECT-TYPE
    SYNTAX  CrmTrCollectIntervalEntry
    ACCESS  not-accessible
    STATUS  mandatory
    DESCRIPTION
           "DUMMY"
    INDEX   { crmTrCollectIntervalType }
    ::= { crmTrCollectIntervalTable  1 }

CrmTrCollectIntervalEntry ::=
    SEQUENCE {
        crmTrCollectIntervalType
            INTEGER,

        crmTrCollectIntervalTime
            INTEGER (-2147483648..2147483647),

        crmTrCollectIntervalIfPoints
            INTEGER (-2147483648..2147483647),

        crmTrCollectIntervalVpcPoints
            INTEGER (-2147483648..2147483647),

        crmTrCollectIntervalVccPoints
            INTEGER (-2147483648..2147483647),

        crmTrCollectIntervalPriPoints
            INTEGER (-2147483648..2147483647),

        crmTrCollectIntervalFrIfPoints
            INTEGER (-2147483648..2147483647),

        crmTrCollectIntervalFrDlciPoints
            INTEGER (-2147483648..2147483647)
    }

crmTrCollectIntervalType OBJECT-TYPE
    SYNTAX  INTEGER {
    none(1),
    five-seconds(2),
    one-minitutes(3),
    ten-miniutes(4),
    one-hour(5)
}
    ACCESS  not-accessible
    STATUS  mandatory
    DESCRIPTION
           "DUMMY"
    ::= { crmTrCollectIntervalEntry  1 }

crmTrCollectIntervalTime OBJECT-TYPE
    SYNTAX  INTEGER (-2147483648..2147483647)
    ACCESS  read-write
    STATUS  mandatory
    DESCRIPTION
           "DUMMY"
    ::= { crmTrCollectIntervalEntry  2 }

crmTrCollectIntervalIfPoints OBJECT-TYPE
    SYNTAX  INTEGER (-2147483648..2147483647)
    ACCESS  read-only
    STATUS  mandatory
    DESCRIPTION
           "DUMMY"
    ::= { crmTrCollectIntervalEntry  3 }

crmTrCollectIntervalVpcPoints OBJECT-TYPE
    SYNTAX  INTEGER (-2147483648..2147483647)
    ACCESS  read-only
    STATUS  mandatory
    DESCRIPTION
           "DUMMY"
    ::= { crmTrCollectIntervalEntry  4 }

crmTrCollectIntervalVccPoints OBJECT-TYPE
    SYNTAX  INTEGER (-2147483648..2147483647)
    ACCESS  read-only
    STATUS  mandatory
    DESCRIPTION
           "DUMMY"
    ::= { crmTrCollectIntervalEntry  5 }

crmTrCollectIntervalPriPoints OBJECT-TYPE
    SYNTAX  INTEGER (-2147483648..2147483647)
    ACCESS  read-only
    STATUS  mandatory
    DESCRIPTION
           "DUMMY"
    ::= { crmTrCollectIntervalEntry  6 }

crmTrCollectIntervalFrIfPoints OBJECT-TYPE
    SYNTAX  INTEGER (-2147483648..2147483647)
    ACCESS  read-only
    STATUS  mandatory
    DESCRIPTION
           "DUMMY"
    ::= { crmTrCollectIntervalEntry  7 }

crmTrCollectIntervalFrDlciPoints OBJECT-TYPE
    SYNTAX  INTEGER (-2147483648..2147483647)
    ACCESS  read-only
    STATUS  mandatory
    DESCRIPTION
           "DUMMY"
    ::= { crmTrCollectIntervalEntry  8 }

crmTrCollectIfTable OBJECT-TYPE
    SYNTAX  SEQUENCE OF CrmTrCollectIfEntry
    ACCESS  not-accessible
    STATUS  mandatory
    DESCRIPTION
           "DUMMY"
    ::= { crmTraffic  2 }

crmTrCollectIfEntry OBJECT-TYPE
    SYNTAX  CrmTrCollectIfEntry
    ACCESS  not-accessible
    STATUS  mandatory
    DESCRIPTION
           "DUMMY"
    INDEX   { crmTrCollectIfIfIndex,  crmTrCollectIfDirect }
    ::= { crmTrCollectIfTable  1 }

CrmTrCollectIfEntry ::=
    SEQUENCE {
        crmTrCollectIfIfIndex
            INTEGER (-2147483648..2147483647),

        crmTrCollectIfDirect
            INTEGER,

        crmTrCollectIfInterval
            INTEGER,

        crmTrCollectIfThroughCells
            Counter,

        crmTrCollectIfDisRes1
            INTEGER,

        crmTrCollectIfDisCells1
            Counter,

        crmTrCollectIfDisRes2
            INTEGER,

        crmTrCollectIfDisCells2
            Counter,

        crmTrCollectIfDisRes3
            INTEGER,

        crmTrCollectIfDisCells3
            Counter,

        crmTrCollectIfDisRes4
            INTEGER,

        crmTrCollectIfDisCells4
            Counter,

        crmTrCollectIfDisRes5
            INTEGER,

        crmTrCollectIfDisCells5
            Counter,

        crmTrCollectIfDisRes6
            INTEGER,

        crmTrCollectIfDisCells6
            Counter,

        crmTrCollectIfDisRes7
            INTEGER,

        crmTrCollectIfDisCells7
            Counter,

        crmTrCollectIfDisRes8
            INTEGER,

        crmTrCollectIfDisCells8
            Counter,

        crmTrCollectIfStartTime
            DateAndTime,

        crmTrCollectIfEndTime
            DateAndTime,

        crmTrCollectIfRowStatus
            INTEGER (-2147483648..2147483647)
    }

crmTrCollectIfIfIndex OBJECT-TYPE
    SYNTAX  INTEGER (-2147483648..2147483647)
    ACCESS  not-accessible
    STATUS  mandatory
    DESCRIPTION
           "DUMMY"
    ::= { crmTrCollectIfEntry  1 }

crmTrCollectIfDirect OBJECT-TYPE
    SYNTAX  INTEGER {
    ifp2sw(1),
    sw2ifp(2)
}
    ACCESS  not-accessible
    STATUS  mandatory
    DESCRIPTION
           "DUMMY"
    ::= { crmTrCollectIfEntry  2 }

crmTrCollectIfInterval OBJECT-TYPE
    SYNTAX  INTEGER {
    none(1),
    five-seconds(2),
    one-minitutes(3),
    ten-miniutes(4),
    one-hour(5)
}
    ACCESS  read-write
    STATUS  mandatory
    DESCRIPTION
           "DUMMY"
    DEFVAL {  1  }

    ::= { crmTrCollectIfEntry  3 }

crmTrCollectIfThroughCells OBJECT-TYPE
    SYNTAX  Counter
    ACCESS  read-only
    STATUS  mandatory
    DESCRIPTION
           "DUMMY"
    ::= { crmTrCollectIfEntry  4 }

crmTrCollectIfDisRes1 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectIfEntry  5 }

crmTrCollectIfDisCells1 OBJECT-TYPE
    SYNTAX  Counter
    ACCESS  read-only
    STATUS  mandatory
    DESCRIPTION
           "DUMMY"
    ::= { crmTrCollectIfEntry  6 }

crmTrCollectIfDisRes2 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectIfEntry  7 }

crmTrCollectIfDisCells2 OBJECT-TYPE
    SYNTAX  Counter
    ACCESS  read-only
    STATUS  mandatory
    DESCRIPTION
           "DUMMY"
    ::= { crmTrCollectIfEntry  8 }

crmTrCollectIfDisRes3 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectIfEntry  9 }

crmTrCollectIfDisCells3 OBJECT-TYPE
    SYNTAX  Counter
    ACCESS  read-only
    STATUS  mandatory
    DESCRIPTION
           "DUMMY"
    ::= { crmTrCollectIfEntry  10 }

crmTrCollectIfDisRes4 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectIfEntry  11 }

crmTrCollectIfDisCells4 OBJECT-TYPE
    SYNTAX  Counter
    ACCESS  read-only
    STATUS  mandatory
    DESCRIPTION
           "DUMMY"
    ::= { crmTrCollectIfEntry  12 }

crmTrCollectIfDisRes5 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectIfEntry  13 }

crmTrCollectIfDisCells5 OBJECT-TYPE
    SYNTAX  Counter
    ACCESS  read-only
    STATUS  mandatory
    DESCRIPTION
           "DUMMY"
    ::= { crmTrCollectIfEntry  14 }

crmTrCollectIfDisRes6 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectIfEntry  15 }

crmTrCollectIfDisCells6 OBJECT-TYPE
    SYNTAX  Counter
    ACCESS  read-only
    STATUS  mandatory
    DESCRIPTION
           "DUMMY"
    ::= { crmTrCollectIfEntry  16 }

crmTrCollectIfDisRes7 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectIfEntry  17 }

crmTrCollectIfDisCells7 OBJECT-TYPE
    SYNTAX  Counter
    ACCESS  read-only
    STATUS  mandatory
    DESCRIPTION
           "DUMMY"
    ::= { crmTrCollectIfEntry  18 }

crmTrCollectIfDisRes8 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectIfEntry  19 }

crmTrCollectIfDisCells8 OBJECT-TYPE
    SYNTAX  Counter
    ACCESS  read-only
    STATUS  mandatory
    DESCRIPTION
           "DUMMY"
    ::= { crmTrCollectIfEntry  20 }

crmTrCollectIfStartTime OBJECT-TYPE
    SYNTAX  DateAndTime
    ACCESS  read-write
    STATUS  mandatory
    DESCRIPTION
           "DUMMY"
    ::= { crmTrCollectIfEntry  21 }

crmTrCollectIfEndTime OBJECT-TYPE
    SYNTAX  DateAndTime
    ACCESS  read-write
    STATUS  mandatory
    DESCRIPTION
           "DUMMY"
    ::= { crmTrCollectIfEntry  22 }

crmTrCollectIfRowStatus OBJECT-TYPE
    SYNTAX  INTEGER (-2147483648..2147483647)
    ACCESS  read-write
    STATUS  mandatory
    DESCRIPTION
           "DUMMY"
    DEFVAL {  2  }

    ::= { crmTrCollectIfEntry  23 }

crmTrCollectVpcTable OBJECT-TYPE
    SYNTAX  SEQUENCE OF CrmTrCollectVpcEntry
    ACCESS  not-accessible
    STATUS  mandatory
    DESCRIPTION
           "DUMMY"
    ::= { crmTraffic  3 }

crmTrCollectVpcEntry OBJECT-TYPE
    SYNTAX  CrmTrCollectVpcEntry
    ACCESS  not-accessible
    STATUS  mandatory
    DESCRIPTION
           "DUMMY"
    INDEX   { crmTrCollectVpcIfIndex,  crmTrCollectVpcVpi,  crmTrCollectVpcDirect }
    ::= { crmTrCollectVpcTable  1 }

CrmTrCollectVpcEntry ::=
    SEQUENCE {
        crmTrCollectVpcIfIndex
            INTEGER (-2147483648..2147483647),

        crmTrCollectVpcVpi
            INTEGER (-2147483648..2147483647),

        crmTrCollectVpcDirect
            INTEGER,

        crmTrCollectVpcInterval
            INTEGER,

        crmTrCollectVpcThroughCells
            Counter,

        crmTrCollectVpcDisRes1
            INTEGER,

        crmTrCollectVpcDisCells1
            Counter,

        crmTrCollectVpcDisRes2
            INTEGER,

        crmTrCollectVpcDisCells2
            Counter,

        crmTrCollectVpcDisRes3
            INTEGER,

        crmTrCollectVpcDisCells3
            Counter,

        crmTrCollectVpcDisRes4
            INTEGER,

        crmTrCollectVpcDisCells4
            Counter,

        crmTrCollectVpcDisRes5
            INTEGER,

        crmTrCollectVpcDisCells5
            Counter,

        crmTrCollectVpcDisRes6
            INTEGER,

        crmTrCollectVpcDisCells6
            Counter,

        crmTrCollectVpcDisRes7
            INTEGER,

        crmTrCollectVpcDisCells7
            Counter,

        crmTrCollectVpcDisRes8
            INTEGER,

        crmTrCollectVpcDisCells8
            Counter,

        crmTrCollectVpcStartTime
            DateAndTime,

        crmTrCollectVpcEndTime
            DateAndTime,

        crmTrCollectVpcRowStatus
            INTEGER (-2147483648..2147483647)
    }

crmTrCollectVpcIfIndex OBJECT-TYPE
    SYNTAX  INTEGER (-2147483648..2147483647)
    ACCESS  not-accessible
    STATUS  mandatory
    DESCRIPTION
           "DUMMY"
    ::= { crmTrCollectVpcEntry  1 }

crmTrCollectVpcVpi OBJECT-TYPE
    SYNTAX  INTEGER (-2147483648..2147483647)
    ACCESS  not-accessible
    STATUS  mandatory
    DESCRIPTION
           "DUMMY"
    ::= { crmTrCollectVpcEntry  2 }

crmTrCollectVpcDirect OBJECT-TYPE
    SYNTAX  INTEGER {
    ifp2sw(1),
    sw2ifp(2)
}
    ACCESS  not-accessible
    STATUS  mandatory
    DESCRIPTION
           "DUMMY"
    ::= { crmTrCollectVpcEntry  3 }

crmTrCollectVpcInterval OBJECT-TYPE
    SYNTAX  INTEGER {
    none(1),
    five-seconds(2),
    one-minitutes(3),
    ten-miniutes(4),
    one-hour(5)
}
    ACCESS  read-write
    STATUS  mandatory
    DESCRIPTION
           "DUMMY"
    DEFVAL {  1  }

    ::= { crmTrCollectVpcEntry  4 }

crmTrCollectVpcThroughCells OBJECT-TYPE
    SYNTAX  Counter
    ACCESS  read-only
    STATUS  mandatory
    DESCRIPTION
           "DUMMY"
    ::= { crmTrCollectVpcEntry  5 }

crmTrCollectVpcDisRes1 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVpcEntry  6 }

crmTrCollectVpcDisCells1 OBJECT-TYPE
    SYNTAX  Counter
    ACCESS  read-only
    STATUS  mandatory
    DESCRIPTION
           "DUMMY"
    ::= { crmTrCollectVpcEntry  7 }

crmTrCollectVpcDisRes2 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVpcEntry  8 }

crmTrCollectVpcDisCells2 OBJECT-TYPE
    SYNTAX  Counter
    ACCESS  read-only
    STATUS  mandatory
    DESCRIPTION
           "DUMMY"
    ::= { crmTrCollectVpcEntry  9 }

crmTrCollectVpcDisRes3 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVpcEntry  10 }

crmTrCollectVpcDisCells3 OBJECT-TYPE
    SYNTAX  Counter
    ACCESS  read-only
    STATUS  mandatory
    DESCRIPTION
           "DUMMY"
    ::= { crmTrCollectVpcEntry  11 }

crmTrCollectVpcDisRes4 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVpcEntry  12 }

crmTrCollectVpcDisCells4 OBJECT-TYPE
    SYNTAX  Counter
    ACCESS  read-only
    STATUS  mandatory
    DESCRIPTION
           "DUMMY"
    ::= { crmTrCollectVpcEntry  13 }

crmTrCollectVpcDisRes5 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVpcEntry  14 }

crmTrCollectVpcDisCells5 OBJECT-TYPE
    SYNTAX  Counter
    ACCESS  read-only
    STATUS  mandatory
    DESCRIPTION
           "DUMMY"
    ::= { crmTrCollectVpcEntry  15 }

crmTrCollectVpcDisRes6 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVpcEntry  16 }

crmTrCollectVpcDisCells6 OBJECT-TYPE
    SYNTAX  Counter
    ACCESS  read-only
    STATUS  mandatory
    DESCRIPTION
           "DUMMY"
    ::= { crmTrCollectVpcEntry  17 }

crmTrCollectVpcDisRes7 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVpcEntry  18 }

crmTrCollectVpcDisCells7 OBJECT-TYPE
    SYNTAX  Counter
    ACCESS  read-only
    STATUS  mandatory
    DESCRIPTION
           "DUMMY"
    ::= { crmTrCollectVpcEntry  19 }

crmTrCollectVpcDisRes8 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVpcEntry  20 }

crmTrCollectVpcDisCells8 OBJECT-TYPE
    SYNTAX  Counter
    ACCESS  read-only
    STATUS  mandatory
    DESCRIPTION
           "DUMMY"
    ::= { crmTrCollectVpcEntry  21 }

crmTrCollectVpcStartTime OBJECT-TYPE
    SYNTAX  DateAndTime
    ACCESS  read-write
    STATUS  mandatory
    DESCRIPTION
           "DUMMY"
    ::= { crmTrCollectVpcEntry  22 }

crmTrCollectVpcEndTime OBJECT-TYPE
    SYNTAX  DateAndTime
    ACCESS  read-write
    STATUS  mandatory
    DESCRIPTION
           "DUMMY"
    ::= { crmTrCollectVpcEntry  23 }

crmTrCollectVpcRowStatus OBJECT-TYPE
    SYNTAX  INTEGER (-2147483648..2147483647)
    ACCESS  read-write
    STATUS  mandatory
    DESCRIPTION
           "DUMMY"
    DEFVAL {  2  }

    ::= { crmTrCollectVpcEntry  24 }

crmTrCollectVccTable OBJECT-TYPE
    SYNTAX  SEQUENCE OF CrmTrCollectVccEntry
    ACCESS  not-accessible
    STATUS  mandatory
    DESCRIPTION
           "DUMMY"
    ::= { crmTraffic  4 }

crmTrCollectVccEntry OBJECT-TYPE
    SYNTAX  CrmTrCollectVccEntry
    ACCESS  not-accessible
    STATUS  mandatory
    DESCRIPTION
           "DUMMY"
    INDEX   { crmTrCollectVccIfIndex,  crmTrCollectVccVpi,  crmTrCollectVccVci,  crmTrCollectVccDirect }
    ::= { crmTrCollectVccTable  1 }

CrmTrCollectVccEntry ::=
    SEQUENCE {
        crmTrCollectVccIfIndex
            INTEGER (-2147483648..2147483647),

        crmTrCollectVccVpi
            INTEGER (-2147483648..2147483647),

        crmTrCollectVccVci
            INTEGER (-2147483648..2147483647),

        crmTrCollectVccDirect
            INTEGER,

        crmTrCollectVccInterval
            INTEGER,

        crmTrCollectVccThroughCells
            Counter,

        crmTrCollectVccDisRes1
            INTEGER,

        crmTrCollectVccDisCells1
            Counter,

        crmTrCollectVccDisRes2
            INTEGER,

        crmTrCollectVccDisCells2
            Counter,

        crmTrCollectVccDisRes3
            INTEGER,

        crmTrCollectVccDisCells3
            Counter,

        crmTrCollectVccDisRes4
            INTEGER,

        crmTrCollectVccDisCells4
            Counter,

        crmTrCollectVccDisRes5
            INTEGER,

        crmTrCollectVccDisCells5
            Counter,

        crmTrCollectVccDisRes6
            INTEGER,

        crmTrCollectVccDisCells6
            Counter,

        crmTrCollectVccDisRes7
            INTEGER,

        crmTrCollectVccDisCells7
            Counter,

        crmTrCollectVccDisRes8
            INTEGER,

        crmTrCollectVccDisCells8
            Counter,

        crmTrCollectVccStartTime
            DateAndTime,

        crmTrCollectVccEndTime
            DateAndTime,

        crmTrCollectVccRowStatus
            INTEGER (-2147483648..2147483647)
    }

crmTrCollectVccIfIndex OBJECT-TYPE
    SYNTAX  INTEGER (-2147483648..2147483647)
    ACCESS  not-accessible
    STATUS  mandatory
    DESCRIPTION
           "DUMMY"
    ::= { crmTrCollectVccEntry  1 }

crmTrCollectVccVpi OBJECT-TYPE
    SYNTAX  INTEGER (-2147483648..2147483647)
    ACCESS  not-accessible
    STATUS  mandatory
    DESCRIPTION
           "DUMMY"
    ::= { crmTrCollectVccEntry  2 }

crmTrCollectVccVci OBJECT-TYPE
    SYNTAX  INTEGER (-2147483648..2147483647)
    ACCESS  not-accessible
    STATUS  mandatory
    DESCRIPTION
           "DUMMY"
    ::= { crmTrCollectVccEntry  3 }

crmTrCollectVccDirect OBJECT-TYPE
    SYNTAX  INTEGER {
    sw2ifp(1),
    ifp2sw(2)
}
    ACCESS  not-accessible
    STATUS  mandatory
    DESCRIPTION
           "DUMMY"
    ::= { crmTrCollectVccEntry  4 }

crmTrCollectVccInterval OBJECT-TYPE
    SYNTAX  INTEGER {
    none(1),
    five-seconds(2),
    one-minitutes(3),
    ten-miniutes(4),
    one-hour(5)
}
    ACCESS  read-write
    STATUS  mandatory
    DESCRIPTION
           "DUMMY"
    DEFVAL {  1  }

    ::= { crmTrCollectVccEntry  5 }

crmTrCollectVccThroughCells OBJECT-TYPE
    SYNTAX  Counter
    ACCESS  read-only
    STATUS  mandatory
    DESCRIPTION
           "DUMMY"
    ::= { crmTrCollectVccEntry  6 }

crmTrCollectVccDisRes1 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVccEntry  7 }

crmTrCollectVccDisCells1 OBJECT-TYPE
    SYNTAX  Counter
    ACCESS  read-only
    STATUS  mandatory
    DESCRIPTION
           "DUMMY"
    ::= { crmTrCollectVccEntry  8 }

crmTrCollectVccDisRes2 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVccEntry  9 }

crmTrCollectVccDisCells2 OBJECT-TYPE
    SYNTAX  Counter
    ACCESS  read-only
    STATUS  mandatory
    DESCRIPTION
           "DUMMY"
    ::= { crmTrCollectVccEntry  10 }

crmTrCollectVccDisRes3 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVccEntry  11 }

crmTrCollectVccDisCells3 OBJECT-TYPE
    SYNTAX  Counter
    ACCESS  read-only
    STATUS  mandatory
    DESCRIPTION
           "DUMMY"
    ::= { crmTrCollectVccEntry  12 }

crmTrCollectVccDisRes4 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVccEntry  13 }

crmTrCollectVccDisCells4 OBJECT-TYPE
    SYNTAX  Counter
    ACCESS  read-only
    STATUS  mandatory
    DESCRIPTION
           "DUMMY"
    ::= { crmTrCollectVccEntry  14 }

crmTrCollectVccDisRes5 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVccEntry  15 }

crmTrCollectVccDisCells5 OBJECT-TYPE
    SYNTAX  Counter
    ACCESS  read-only
    STATUS  mandatory
    DESCRIPTION
           "DUMMY"
    ::= { crmTrCollectVccEntry  16 }

crmTrCollectVccDisRes6 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVccEntry  17 }

crmTrCollectVccDisCells6 OBJECT-TYPE
    SYNTAX  Counter
    ACCESS  read-only
    STATUS  mandatory
    DESCRIPTION
           "DUMMY"
    ::= { crmTrCollectVccEntry  18 }

crmTrCollectVccDisRes7 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVccEntry  19 }

crmTrCollectVccDisCells7 OBJECT-TYPE
    SYNTAX  Counter
    ACCESS  read-only
    STATUS  mandatory
    DESCRIPTION
           "DUMMY"
    ::= { crmTrCollectVccEntry  20 }

crmTrCollectVccDisRes8 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectVccEntry  21 }

crmTrCollectVccDisCells8 OBJECT-TYPE
    SYNTAX  Counter
    ACCESS  read-only
    STATUS  mandatory
    DESCRIPTION
           "DUMMY"
    ::= { crmTrCollectVccEntry  22 }

crmTrCollectVccStartTime OBJECT-TYPE
    SYNTAX  DateAndTime
    ACCESS  read-write
    STATUS  mandatory
    DESCRIPTION
           "DUMMY"
    ::= { crmTrCollectVccEntry  23 }

crmTrCollectVccEndTime OBJECT-TYPE
    SYNTAX  DateAndTime
    ACCESS  read-write
    STATUS  mandatory
    DESCRIPTION
           "DUMMY"
    ::= { crmTrCollectVccEntry  24 }

crmTrCollectVccRowStatus OBJECT-TYPE
    SYNTAX  INTEGER (-2147483648..2147483647)
    ACCESS  read-write
    STATUS  mandatory
    DESCRIPTION
           "DUMMY"
    DEFVAL {  2  }

    ::= { crmTrCollectVccEntry  25 }

crmTrCollectPriTable OBJECT-TYPE
    SYNTAX  SEQUENCE OF CrmTrCollectPriEntry
    ACCESS  not-accessible
    STATUS  mandatory
    DESCRIPTION
           "DUMMY"
    ::= { crmTraffic  5 }

crmTrCollectPriEntry OBJECT-TYPE
    SYNTAX  CrmTrCollectPriEntry
    ACCESS  not-accessible
    STATUS  mandatory
    DESCRIPTION
           "DUMMY"
    INDEX   { crmTrCollectPriIfIndex,  crmTrCollectPriClass,  crmTrCollectPriDirect }
    ::= { crmTrCollectPriTable  1 }

CrmTrCollectPriEntry ::=
    SEQUENCE {
        crmTrCollectPriIfIndex
            INTEGER (-2147483648..2147483647),

        crmTrCollectPriClass
            INTEGER,

        crmTrCollectPriDirect
            INTEGER,

        crmTrCollectPriInterval
            INTEGER,

        crmTrCollectPriThroughCells
            Counter,

        crmTrCollectPriDisRes1
            INTEGER,

        crmTrCollectPriDisCells1
            Counter,

        crmTrCollectPriDisRes2
            INTEGER,

        crmTrCollectPriDisCells2
            Counter,

        crmTrCollectPriDisRes3
            INTEGER,

        crmTrCollectPriDisCells3
            Counter,

        crmTrCollectPriDisRes4
            INTEGER,

        crmTrCollectPriDisCells4
            Counter,

        crmTrCollectPriDisRes5
            INTEGER,

        crmTrCollectPriDisCells5
            Counter,

        crmTrCollectPriDisRes6
            INTEGER,

        crmTrCollectPriDisCells6
            Counter,

        crmTrCollectPriDisRes7
            INTEGER,

        crmTrCollectPriDisCells7
            Counter,

        crmTrCollectPriDisRes8
            INTEGER,

        crmTrCollectPriDisCells8
            Counter,

        crmTrCollectPriStartTime
            DateAndTime,

        crmTrCollectPriEndTime
            DateAndTime,

        crmTrCollectPriRowStatus
            INTEGER (-2147483648..2147483647)
    }

crmTrCollectPriIfIndex OBJECT-TYPE
    SYNTAX  INTEGER (-2147483648..2147483647)
    ACCESS  not-accessible
    STATUS  mandatory
    DESCRIPTION
           "DUMMY"
    ::= { crmTrCollectPriEntry  1 }

crmTrCollectPriClass OBJECT-TYPE
    SYNTAX  INTEGER
    ACCESS  not-accessible
    STATUS  mandatory
    DESCRIPTION
           "DUMMY"
    ::= { crmTrCollectPriEntry  2 }

crmTrCollectPriDirect OBJECT-TYPE
    SYNTAX  INTEGER {
    sw2ifp(1),
    ifp2sw(2)
}
    ACCESS  not-accessible
    STATUS  mandatory
    DESCRIPTION
           "DUMMY"
    ::= { crmTrCollectPriEntry  3 }

crmTrCollectPriInterval OBJECT-TYPE
    SYNTAX  INTEGER {
    none(1),
    five-seconds(2),
    one-minitutes(3),
    ten-miniutes(4),
    one-hour(5)
}
    ACCESS  read-write
    STATUS  mandatory
    DESCRIPTION
           "DUMMY"
    DEFVAL {  1  }

    ::= { crmTrCollectPriEntry  4 }

crmTrCollectPriThroughCells OBJECT-TYPE
    SYNTAX  Counter
    ACCESS  read-only
    STATUS  mandatory
    DESCRIPTION
           "DUMMY"
    ::= { crmTrCollectPriEntry  5 }

crmTrCollectPriDisRes1 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectPriEntry  6 }

crmTrCollectPriDisCells1 OBJECT-TYPE
    SYNTAX  Counter
    ACCESS  read-only
    STATUS  mandatory
    DESCRIPTION
           "DUMMY"
    ::= { crmTrCollectPriEntry  7 }

crmTrCollectPriDisRes2 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectPriEntry  8 }

crmTrCollectPriDisCells2 OBJECT-TYPE
    SYNTAX  Counter
    ACCESS  read-only
    STATUS  mandatory
    DESCRIPTION
           "DUMMY"
    ::= { crmTrCollectPriEntry  9 }

crmTrCollectPriDisRes3 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectPriEntry  10 }

crmTrCollectPriDisCells3 OBJECT-TYPE
    SYNTAX  Counter
    ACCESS  read-only
    STATUS  mandatory
    DESCRIPTION
           "DUMMY"
    ::= { crmTrCollectPriEntry  11 }

crmTrCollectPriDisRes4 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectPriEntry  12 }

crmTrCollectPriDisCells4 OBJECT-TYPE
    SYNTAX  Counter
    ACCESS  read-only
    STATUS  mandatory
    DESCRIPTION
           "DUMMY"
    ::= { crmTrCollectPriEntry  13 }
crmTrCollectPriDisRes5 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectPriEntry  14 }

crmTrCollectPriDisCells5 OBJECT-TYPE
    SYNTAX  Counter
    ACCESS  read-only
    STATUS  mandatory
    DESCRIPTION
           "DUMMY"
    ::= { crmTrCollectPriEntry  15 }

crmTrCollectPriDisRes6 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectPriEntry  16 }

crmTrCollectPriDisCells6 OBJECT-TYPE
    SYNTAX  Counter
    ACCESS  read-only
    STATUS  mandatory
    DESCRIPTION
           "DUMMY"
    ::= { crmTrCollectPriEntry  17 }

crmTrCollectPriDisRes7 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectPriEntry  18 }

crmTrCollectPriDisCells7 OBJECT-TYPE
    SYNTAX  Counter
    ACCESS  read-only
    STATUS  mandatory
    DESCRIPTION
           "DUMMY"
    ::= { crmTrCollectPriEntry  19 }

crmTrCollectPriDisRes8 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectPriEntry  20 }

crmTrCollectPriDisCells8 OBJECT-TYPE
    SYNTAX  Counter
    ACCESS  read-only
    STATUS  mandatory
    DESCRIPTION
           "DUMMY"
    ::= { crmTrCollectPriEntry  21 }

crmTrCollectPriStartTime OBJECT-TYPE
    SYNTAX  DateAndTime
    ACCESS  read-write
    STATUS  mandatory
    DESCRIPTION
           "DUMMY"
    ::= { crmTrCollectPriEntry  22 }

crmTrCollectPriEndTime OBJECT-TYPE
    SYNTAX  DateAndTime
    ACCESS  read-write
    STATUS  mandatory
    DESCRIPTION
           "DUMMY"
    ::= { crmTrCollectPriEntry  23 }

crmTrCollectPriRowStatus OBJECT-TYPE
    SYNTAX  INTEGER (-2147483648..2147483647)
    ACCESS  read-write
    STATUS  mandatory
    DESCRIPTION
           "DUMMY"
    DEFVAL {  2  }

    ::= { crmTrCollectPriEntry  24 }

crmTrCollectFrIfTable OBJECT-TYPE
    SYNTAX  SEQUENCE OF CrmTrCollectFrIfEntry
    ACCESS  not-accessible
    STATUS  mandatory
    DESCRIPTION
           "DUMMY"
    ::= { crmTraffic  6 }

crmTrCollectFrIfEntry OBJECT-TYPE
    SYNTAX  CrmTrCollectFrIfEntry
    ACCESS  not-accessible
    STATUS  mandatory
    DESCRIPTION
           "DUMMY"
    INDEX   { crmTrCollectFrIfIfIndex,  crmTrCollectFrIfDirect }
    ::= { crmTrCollectFrIfTable  1 }

CrmTrCollectFrIfEntry ::=
    SEQUENCE {
        crmTrCollectFrIfIfIndex
            INTEGER (-2147483648..2147483647),

        crmTrCollectFrIfDirect
            INTEGER,

        crmTrCollectFrIfInterval
            INTEGER,

        crmTrCollectFrIfThroughCells
            Counter,

        crmTrCollectFrIfDisRes1
            INTEGER,

        crmTrCollectFrIfDisCells1
            Counter,

        crmTrCollectFrIfDisRes2
            INTEGER,

        crmTrCollectFrIfDisCells2
            Counter,

        crmTrCollectFrIfDisRes3
            INTEGER,

        crmTrCollectFrIfDisCells3
            Counter,

        crmTrCollectFrIfDisRes4
            INTEGER,

        crmTrCollectFrIfDisCells4
            Counter,

        crmTrCollectFrIfDisRes5
            INTEGER,

        crmTrCollectFrIfDisCells5
            Counter,

        crmTrCollectFrIfDisRes6
            INTEGER,

        crmTrCollectFrIfDisCells6
            Counter,

        crmTrCollectFrIfDisRes7
            INTEGER,

        crmTrCollectFrIfDisCells7
            Counter,

        crmTrCollectFrIfDisRes8
            INTEGER,

        crmTrCollectFrIfDisCells8
            Counter,

        crmTrCollectFrIfStartTime
            DateAndTime,

        crmTrCollectFrIfEndTime
            DateAndTime,

        crmTrCollectFrIfRowStatus
            INTEGER (-2147483648..2147483647)
    }

crmTrCollectFrIfIfIndex OBJECT-TYPE
    SYNTAX  INTEGER (-2147483648..2147483647)
    ACCESS  not-accessible
    STATUS  mandatory
    DESCRIPTION
           "DUMMY"
    ::= { crmTrCollectFrIfEntry  1 }

crmTrCollectFrIfDirect OBJECT-TYPE
    SYNTAX  INTEGER {
    sw2ifp(1),
    ifp2sw(2)
}
    ACCESS  not-accessible
    STATUS  mandatory
    DESCRIPTION
           "DUMMY"
    ::= { crmTrCollectFrIfEntry  2 }

crmTrCollectFrIfInterval OBJECT-TYPE
    SYNTAX  INTEGER {
    none(1),
    five-seconds(2),
    one-minitutes(3),
    ten-miniutes(4),
    one-hour(5)
}
    ACCESS  read-write
    STATUS  mandatory
    DESCRIPTION
           "DUMMY"
    DEFVAL {  1  }

    ::= { crmTrCollectFrIfEntry  3 }

crmTrCollectFrIfThroughCells OBJECT-TYPE
    SYNTAX  Counter
    ACCESS  read-only
    STATUS  mandatory
    DESCRIPTION
           "DUMMY"
    ::= { crmTrCollectFrIfEntry  4 }

crmTrCollectFrIfDisRes1 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrIfEntry  5 }

crmTrCollectFrIfDisCells1 OBJECT-TYPE
    SYNTAX  Counter
    ACCESS  read-only
    STATUS  mandatory
    DESCRIPTION
           "DUMMY"
    ::= { crmTrCollectFrIfEntry  6 }

crmTrCollectFrIfDisRes2 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrIfEntry  7 }

crmTrCollectFrIfDisCells2 OBJECT-TYPE
    SYNTAX  Counter
    ACCESS  read-only
    STATUS  mandatory
    DESCRIPTION
           "DUMMY"
    ::= { crmTrCollectFrIfEntry  8 }

crmTrCollectFrIfDisRes3 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrIfEntry  9 }

crmTrCollectFrIfDisCells3 OBJECT-TYPE
    SYNTAX  Counter
    ACCESS  read-only
    STATUS  mandatory
    DESCRIPTION
           "DUMMY"
    ::= { crmTrCollectFrIfEntry  10 }

crmTrCollectFrIfDisRes4 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrIfEntry  11 }

crmTrCollectFrIfDisCells4 OBJECT-TYPE
    SYNTAX  Counter
    ACCESS  read-only
    STATUS  mandatory
    DESCRIPTION
           "DUMMY"
    ::= { crmTrCollectFrIfEntry  12 }

crmTrCollectFrIfDisRes5 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrIfEntry  13 }

crmTrCollectFrIfDisCells5 OBJECT-TYPE
    SYNTAX  Counter
    ACCESS  read-only
    STATUS  mandatory
    DESCRIPTION
           "DUMMY"
    ::= { crmTrCollectFrIfEntry  14 }

crmTrCollectFrIfDisRes6 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrIfEntry  15 }

crmTrCollectFrIfDisCells6 OBJECT-TYPE
    SYNTAX  Counter
    ACCESS  read-only
    STATUS  mandatory
    DESCRIPTION
           "DUMMY"
    ::= { crmTrCollectFrIfEntry  16 }

crmTrCollectFrIfDisRes7 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrIfEntry  17 }

crmTrCollectFrIfDisCells7 OBJECT-TYPE
    SYNTAX  Counter
    ACCESS  read-only
    STATUS  mandatory
    DESCRIPTION
           "DUMMY"
    ::= { crmTrCollectFrIfEntry  18 }

crmTrCollectFrIfDisRes8 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrIfEntry  19 }

crmTrCollectFrIfDisCells8 OBJECT-TYPE
    SYNTAX  Counter
    ACCESS  read-only
    STATUS  mandatory
    DESCRIPTION
           "DUMMY"
    ::= { crmTrCollectFrIfEntry  20 }

crmTrCollectFrIfStartTime OBJECT-TYPE
    SYNTAX  DateAndTime
    ACCESS  read-write
    STATUS  mandatory
    DESCRIPTION
           "DUMMY"
    ::= { crmTrCollectFrIfEntry  21 }

crmTrCollectFrIfEndTime OBJECT-TYPE
    SYNTAX  DateAndTime
    ACCESS  read-write
    STATUS  mandatory
    DESCRIPTION
           "DUMMY"
    ::= { crmTrCollectFrIfEntry  22 }

crmTrCollectFrIfRowStatus OBJECT-TYPE
    SYNTAX  INTEGER (-2147483648..2147483647)
    ACCESS  read-write
    STATUS  mandatory
    DESCRIPTION
           "DUMMY"
    DEFVAL {  2  }

    ::= { crmTrCollectFrIfEntry  23 }

crmTrCollectFrDlciTable OBJECT-TYPE
    SYNTAX  SEQUENCE OF CrmTrCollectFrDlciEntry
    ACCESS  not-accessible
    STATUS  mandatory
    DESCRIPTION
           "DUMMY"
    ::= { crmTraffic  7 }

crmTrCollectFrDlciEntry OBJECT-TYPE
    SYNTAX  CrmTrCollectFrDlciEntry
    ACCESS  not-accessible
    STATUS  mandatory
    DESCRIPTION
           "DUMMY"
    INDEX   { crmTrCollectFrDlciIfIndex,  crmTrCollectFrDlciDlci,  crmTrCollectFrDlciDirect }
    ::= { crmTrCollectFrDlciTable  1 }

CrmTrCollectFrDlciEntry ::=
    SEQUENCE {
        crmTrCollectFrDlciIfIndex
            INTEGER (-2147483648..2147483647),

        crmTrCollectFrDlciDlci
            INTEGER (-2147483648..2147483647),

        crmTrCollectFrDlciDirect
            INTEGER,

        crmTrCollectFrDlciInterval
            INTEGER,

        crmTrCollectFrDlciThroughCells
            Counter,

        crmTrCollectFrDlciDisRes1
            INTEGER,

        crmTrCollectFrDlciDisCells1
            Counter,

        crmTrCollectFrDlciDisRes2
            INTEGER,

        crmTrCollectFrDlciDisCells2
            Counter,

        crmTrCollectFrDlciDisRes3
            INTEGER,

        crmTrCollectFrDlciDisCells3
            Counter,

        crmTrCollectFrDlciDisRes4
            INTEGER,

        crmTrCollectFrDlciDisCells4
            Counter,

        crmTrCollectFrDlciDisRes5
            INTEGER,

        crmTrCollectFrDlciDisCells5
            Counter,

        crmTrCollectFrDlciDisRes6
            INTEGER,

        crmTrCollectFrDlciDisCells6
            Counter,

        crmTrCollectFrDlciDisRes7
            INTEGER,

        crmTrCollectFrDlciDisCells7
            Counter,

        crmTrCollectFrDlciDisRes8
            INTEGER,

        crmTrCollectFrDlciDisCells8
            Counter,

        crmTrCollectFrDlciStartTime
            DateAndTime,

        crmTrCollectFrDlciEndTime
            DateAndTime,

        crmTrCollectFrDlciRowStatus
            INTEGER (-2147483648..2147483647)
    }

crmTrCollectFrDlciIfIndex OBJECT-TYPE
    SYNTAX  INTEGER (-2147483648..2147483647)
    ACCESS  not-accessible
    STATUS  mandatory
    DESCRIPTION
           "DUMMY"
    ::= { crmTrCollectFrDlciEntry  1 }

crmTrCollectFrDlciDlci OBJECT-TYPE
    SYNTAX  INTEGER (-2147483648..2147483647)
    ACCESS  not-accessible
    STATUS  mandatory
    DESCRIPTION
           "DUMMY"
    ::= { crmTrCollectFrDlciEntry  2 }

crmTrCollectFrDlciDirect OBJECT-TYPE
    SYNTAX  INTEGER {
    sw2ifp(1),
    ifp2sw(2)
}
    ACCESS  not-accessible
    STATUS  mandatory
    DESCRIPTION
           "DUMMY"
    ::= { crmTrCollectFrDlciEntry  3 }

crmTrCollectFrDlciInterval OBJECT-TYPE
    SYNTAX  INTEGER {
    none(1),
    five-seconds(2),
    one-minitutes(3),
    ten-miniutes(4),
    one-hour(5)
}
    ACCESS  read-write
    STATUS  mandatory
    DESCRIPTION
           "DUMMY"
    DEFVAL {  1  }

    ::= { crmTrCollectFrDlciEntry  4 }

crmTrCollectFrDlciThroughCells OBJECT-TYPE
    SYNTAX  Counter
    ACCESS  read-only
    STATUS  mandatory
    DESCRIPTION
           "DUMMY"
    ::= { crmTrCollectFrDlciEntry  5 }

crmTrCollectFrDlciDisRes1 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrDlciEntry  6 }

crmTrCollectFrDlciDisCells1 OBJECT-TYPE
    SYNTAX  Counter
    ACCESS  read-only
    STATUS  mandatory
    DESCRIPTION
           "DUMMY"
    ::= { crmTrCollectFrDlciEntry  7 }

crmTrCollectFrDlciDisRes2 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrDlciEntry  8 }

crmTrCollectFrDlciDisCells2 OBJECT-TYPE
    SYNTAX  Counter
    ACCESS  read-only
    STATUS  mandatory
    DESCRIPTION
           "DUMMY"
    ::= { crmTrCollectFrDlciEntry  9 }

crmTrCollectFrDlciDisRes3 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrDlciEntry  10 }

crmTrCollectFrDlciDisCells3 OBJECT-TYPE
    SYNTAX  Counter
    ACCESS  read-only
    STATUS  mandatory
    DESCRIPTION
           "DUMMY"
    ::= { crmTrCollectFrDlciEntry  11 }

crmTrCollectFrDlciDisRes4 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrDlciEntry  12 }

crmTrCollectFrDlciDisCells4 OBJECT-TYPE
    SYNTAX  Counter
    ACCESS  read-only
    STATUS  mandatory
    DESCRIPTION
           "DUMMY"
    ::= { crmTrCollectFrDlciEntry  13 }

crmTrCollectFrDlciDisRes5 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrDlciEntry  14 }

crmTrCollectFrDlciDisCells5 OBJECT-TYPE
    SYNTAX  Counter
    ACCESS  read-only
    STATUS  mandatory
    DESCRIPTION
           "DUMMY"
    ::= { crmTrCollectFrDlciEntry  15 }

crmTrCollectFrDlciDisRes6 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrDlciEntry  16 }

crmTrCollectFrDlciDisCells6 OBJECT-TYPE
    SYNTAX  Counter
    ACCESS  read-only
    STATUS  mandatory
    DESCRIPTION
           "DUMMY"
    ::= { crmTrCollectFrDlciEntry  17 }

crmTrCollectFrDlciDisRes7 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrDlciEntry  18 }

crmTrCollectFrDlciDisCells7 OBJECT-TYPE
    SYNTAX  Counter
    ACCESS  read-only
    STATUS  mandatory
    DESCRIPTION
           "DUMMY"
    ::= { crmTrCollectFrDlciEntry  19 }

crmTrCollectFrDlciDisRes8 OBJECT-TYPE
    SYNTAX  INTEGER {
    notMeasurement(0),
    bufferOverflow(1),
    policingViolation(2),
    parityError(3),
    aal1(4),
    priBufferOverflow(5),
    sarCsError(10),
    cellHeaderError(20),
    sectionParityError(30),
    pathParityError(31),
    tenMifParityError(32),
    hdlcError(33),
    dsn-ifuMessage(34),
    parityErrorFrame(35),
    frAbnormal(40),
    frExcess(41),
    frLogical(42),
    other1(50),
    other2(51),
    other3(52),
    aal2IllegalFrame(60),
    aal2SellLoss(61),
    aal2IllegalSell(63),
    aal2DelaySuppress(64),
    aal2VoiceSells(65),
    aal2FaxSells(66),
    aal2PbSells(67),
    aal1SnOut(68),
    aal1SnError(69),
    vcAis(80),
    vcFerf(81),
    vpLoopback(82),
    vcLoopback(83)
}
    ACCESS  read-only
    STATUS  mandatory
    DESCRIPTION
           "DUMMY"
    ::= { crmTrCollectFrDlciEntry  20 }

crmTrCollectFrDlciDisCells8 OBJECT-TYPE
    SYNTAX  Counter
    ACCESS  read-only
    STATUS  mandatory
    DESCRIPTION
           "DUMMY"
    ::= { crmTrCollectFrDlciEntry  21 }

crmTrCollectFrDlciStartTime OBJECT-TYPE
    SYNTAX  DateAndTime
    ACCESS  read-write
    STATUS  mandatory
    DESCRIPTION
           "DUMMY"
    ::= { crmTrCollectFrDlciEntry  22 }

crmTrCollectFrDlciEndTime OBJECT-TYPE
    SYNTAX  DateAndTime
    ACCESS  read-write
    STATUS  mandatory
    DESCRIPTION
           "DUMMY"
    ::= { crmTrCollectFrDlciEntry  23 }

crmTrCollectFrDlciRowStatus OBJECT-TYPE
    SYNTAX  INTEGER (-2147483648..2147483647)
    ACCESS  read-write
    STATUS  mandatory
    DESCRIPTION
           "DUMMY"
    DEFVAL {  2  }

    ::= { crmTrCollectFrDlciEntry  24 }

END
