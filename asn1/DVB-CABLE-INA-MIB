-- extracted from draft-ietf-ipcdn-dvbdev-mib-00.txt
-- at Wed Apr  4 06:05:00 2001

DVB-CABLE-INA-MIB DEFINITIONS ::= BEGIN
IMPORTS
       MODULE-IDENTITY,
       OBJECT-TYPE,
       Counter32,
       Integer32,
       Unsigned32,
       experimental
           FROM SNMPv2-SMI
       RowStatus,
       DateAndTime,
       DisplayString,
       TruthValue,
       TEXTUAL-CONVENTION,
       MacAddress
           FROM SNMPv2-TC

Pedersen         Informational - Expires August 2001                7
                       DVB Cable INA Device MIB               Feb 2001

       SnmpAdminString
           FROM SNMP-FRAMEWORK-MIB
       InetAddress,
       InetAddressType
           FROM INET-ADDRESS-MIB
       OBJECT-GROUP,
       MODULE-COMPLIANCE
           FROM SNMPv2-CONF
       InterfaceIndexOrZero,
       InterfaceIndex
           FROM IF-MIB;

   -- Before this MIB will parse it requires a valid SMI subtree
   -- For the purposes of parsing the MIB I have put the MIB under the
   -- 'experimental' subtree.  Strictly this is reserved for MIBs being
   -- developed by IETF working groups. xx should be replaced with a
   -- numeric value which will not clash with any MIBs local to your
   -- organisation and it should only be used for the purpose of
   -- testing.  If this MIB becomes part of the IETF IPCDN work then
   -- the issue of a valid subtree will be resolved, otherwise it is
   -- recommended that ECCA obtain an enterprise number from IANA under
   -- which this MIB can be placed.

   dvbDevice OBJECT IDENTIFIER ::= { experimental 1 } -- See Above

   dvbIna MODULE-IDENTITY

       LAST-UPDATED    "200101100000Z"

       ORGANIZATION    "DVB/DAVIC Interoperability Consortium Technical
                        Working Group"
       CONTACT-INFO
              "        Ian Wheelock
               Postal: Com21, Ireland
                       4400 Cork Airport Business Park
                       Kinsale Road,
                       Cork,
                       IRELAND

                  Tel: +353 2173 05800
                  Fax: +353 2143 21972
               E-mail: ianw@com21.com"

       DESCRIPTION     "The MIB modules for INAs that
                        conform to the EuroModem specification.  This
                        MIB assumes the INA implements MIB-II RFC 1213

                        The original MIB definition work was carried
                        out for the DVB-RC group by
                        Bert Van Willigen
                        Philips Research Laboratory Eindhoven,
                        The Netherlands."

       REVISION         "200101100000Z"

Pedersen         Informational - Expires August 2001                8
                       DVB Cable INA Device MIB               Feb 2001

       DESCRIPTION      "Changed all groups to be optional.
                         jmp@cisco.com"

       REVISION         "200012210000Z"
       DESCRIPTION      "Changed TOS map in IP filter.
                         Correcting errors.
                         jmp@cisco.com"

       REVISION         "200011160000Z"
       DESCRIPTION      "Shortening lines.
                         Corrections of typing errors.
                         jmp@cisco.com"

       REVISION         "200011140000Z"
       DESCRIPTION      "DHCP table made optional.
                         Corrections of typing errors."

       REVISION         "200011080000Z"
       DESCRIPTION      "New agreement on mandatory groups.
                         NIU IP table made. Server table and alarm
                         summary removed."

       REVISION         "200010020000Z"
       DESCRIPTION      "Update of Device-MIB to include proper
                         conformance section and addition of InetAddress
                         and InetAddressType."

       REVISION        "200008310000Z"
       DESCRIPTION     "The original mib organisation that included the
                        the Device and IF related information in one
                        large MIB.
                        Split of the MIB was proposed by the WGT on
                        the 29 August 2000. This resulted in this
                        Device-MIB being created."

       REVISION        "200008190000Z"
       DESCRIPTION     "The original MIB organisation that included the
                        Device and IF related information in one large
                        MIB."
   ::= {dvbDevice 4}

   -- Sub divided dvbIna into MIB Objects and conformance
   dvbInaMibObjects OBJECT IDENTIFIER ::= {dvbIna 1}
   dvbInaMibConform OBJECT IDENTIFIER ::= {dvbIna 2}

   -- Define identifiers under dvbInaMibObjects

   dvbInaDevice         OBJECT IDENTIFIER ::= {dvbInaMibObjects 1}
   dvbInaNmAccess       OBJECT IDENTIFIER ::= {dvbInaMibObjects 2}
   dvbInaSw             OBJECT IDENTIFIER ::= {dvbInaMibObjects 3}
   dvbInaDhcp           OBJECT IDENTIFIER ::= {dvbInaMibObjects 4}
   dvbInaEvent          OBJECT IDENTIFIER ::= {dvbInaMibObjects 5}
   dvbInaIpFilter       OBJECT IDENTIFIER ::= {dvbInaMibObjects 6}
   dvbInaEthFilter      OBJECT IDENTIFIER ::= {dvbInaMibObjects 7}

Pedersen         Informational - Expires August 2001                9
                       DVB Cable INA Device MIB               Feb 2001

   dvbInaNiuError       OBJECT IDENTIFIER ::= {dvbInaMibObjects 8}
   dvbInaNiuIp          OBJECT IDENTIFIER ::= {dvbInaMibObjects 9}

   -- Define identifiers under dvbInaMibConform

   dvbInaCompliances    OBJECT IDENTIFIER ::= {dvbInaMibConform 1}
   dvbInaGroups         OBJECT IDENTIFIER ::= {dvbInaMibConform 2}

-- - - - - - - - - - - - - - - - - - - - - - - - - - - - - - - - - -
-- Device group
--
-- The device group provides general information and control of
-- the device.
-- It is a supplement to the MIB-II system group.
-- - - - - - - - - - - - - - - - - - - - - - - - - - - - - - - - - -

dvbInaDeviceDateTime OBJECT-TYPE
        SYNTAX      DateAndTime
        MAX-ACCESS  read-write
        STATUS      current
        DESCRIPTION
            "The date and time, with optional timezone information."
        ::= { dvbInaDevice 1 }

dvbInaDeviceResetNow OBJECT-TYPE
        SYNTAX      TruthValue
        MAX-ACCESS  read-write
        STATUS      current
        DESCRIPTION
            "Setting this object to true(1) causes the device to reset.
             Reading this object always returns false(2)."
        ::= { dvbInaDevice 2 }

dvbInaDeviceSerialNumber OBJECT-TYPE
        SYNTAX      DisplayString
        MAX-ACCESS  read-only
        STATUS      current
        DESCRIPTION
            "The manufacturer's serial number for this device."
        ::= { dvbInaDevice 3 }

dvbInaDeviceUptime OBJECT-TYPE
        SYNTAX      TimeTicks
        MAX-ACCESS  read-only
        STATUS      current
        DESCRIPTION
            "The amount of time since this device was last initialized.
             Note that this is different from sysUpTime in MIB-II
             because sysUpTime is the uptime of the network management
             portion of the device."
        ::= { dvbInaDevice 4 }

dvbInaDeviceCurrentState OBJECT-TYPE
        SYNTAX      INTEGER {

Pedersen         Informational - Expires August 2001               10
                       DVB Cable INA Device MIB               Feb 2001

            init (1),
            starting (2),
            operational (3),
            standby (4),
            stopping (5),
            alarm (6),
            dead (7)
        }
        MAX-ACCESS  read-only
        STATUS      current
        DESCRIPTION
            "Current (operational) state of the INA."
        ::= { dvbInaDevice 5 }

dvbInaDeviceDesiredState OBJECT-TYPE
        SYNTAX      INTEGER {
            init (1),
            operational (3),
            standby (4)
        }
        MAX-ACCESS  read-write
        STATUS      current
        DESCRIPTION
            "The desired state of the INA. The following values are
             possible: 'Standby(4)' and 'Operational(3)'"
        DEFVAL { standby }
        ::= { dvbInaDevice 6 }

dvbInaDeviceMibVersion OBJECT-TYPE
        SYNTAX      DisplayString
        MAX-ACCESS  read-only
        STATUS      current
        DESCRIPTION
            "This string object specifies the MIB version number of this
             MIB Default is '1.0' "
        ::= { dvbInaDevice 7 }

dvbInaDeviceDhcpRelaySupport    OBJECT-TYPE
        SYNTAX      TruthValue
        MAX-ACCESS  read-only
        STATUS      current
        DESCRIPTION
            "Specifies whether the INA support DHCP relay.
             If this parameter is true, the INA support DHCP relay."
        ::= { dvbInaDevice 8 }

-- --------------------------------------------------------------------
--
-- NMS Access Table
--
-- NMS Access Table controls access to the INA by the Network Management
-- Stations (NMSs).
-- Note. Enabling and disabling of trap levels is needed to specify for
-- each manager the individual priority levels of which it is going to

Pedersen         Informational - Expires August 2001               11
                       DVB Cable INA Device MIB               Feb 2001

-- receive traps. This is done to reduce the number of traps a manager
-- is going to receive.
--
-- --------------------------------------------------------------------

dvbInaNmAccessTable OBJECT-TYPE
        SYNTAX      SEQUENCE OF DvbInaNmAccessEntry
        MAX-ACCESS  not-accessible
        STATUS      current
        DESCRIPTION
            "This table controls access to SNMP objects by network
             management stations. If the table is empty, access
             to SNMP objects is unrestricted."
        ::= { dvbInaNmAccess 1 }

dvbInaNmAccessEntry OBJECT-TYPE
        SYNTAX      DvbInaNmAccessEntry
        MAX-ACCESS  not-accessible
        STATUS      current
        DESCRIPTION
            "Controls access to SNMP objects by a particular network
             management station. For each entry in this table, the
             contents are not readable unless the management station
             has read-write permission."
        INDEX { dvbInaNmAccessIndex  }
        ::= {  dvbInaNmAccessTable 1 }

DvbInaNmAccessEntry ::= SEQUENCE {
            dvbInaNmAccessIndex         Integer32,
            dvbInaNmAccessIpType        InetAddressType,
            dvbInaNmAccessIp            InetAddress,
            dvbInaNmAccessIpMaskType    InetAddressType,
            dvbInaNmAccessIpMask        InetAddress,
            dvbInaNmAccessCommunity     DisplayString,
            dvbInaNmAccessControl       INTEGER,
            dvbInaNmAccessInterfaces    OCTET STRING,
            dvbInaNmAccessStatus        RowStatus,
            dvbInaNmAccessLevelEnable   BITS
        }

dvbInaNmAccessIndex OBJECT-TYPE
        SYNTAX      Integer32 (1..2147483647)
        MAX-ACCESS  not-accessible
        STATUS      current
        DESCRIPTION
            "Index used to order the application of access entries."
        ::= { dvbInaNmAccessEntry 1 }

dvbInaNmAccessIpType OBJECT-TYPE
        SYNTAX      InetAddressType
        MAX-ACCESS  read-create
        STATUS      current
        DESCRIPTION
            "Specifies the format of the IP address"

Pedersen         Informational - Expires August 2001               12
                       DVB Cable INA Device MIB               Feb 2001

        ::= { dvbInaNmAccessEntry 2 }

dvbInaNmAccessIp OBJECT-TYPE
        SYNTAX      InetAddress
        MAX-ACCESS  read-create
        STATUS      current
        DESCRIPTION
            "The IP address (or subnet) of the network management
             station. The address 255.255.255.255 is defined to mean
             any NMS. If traps are enabled for this entry, then the
             value must be the address of a specific device."
        DEFVAL { 'ffffffff'h }
        ::= { dvbInaNmAccessEntry 3 }

dvbInaNmAccessIpMaskType OBJECT-TYPE
        SYNTAX      InetAddressType
        MAX-ACCESS  read-create
        STATUS      current
        DESCRIPTION
            "Specifies the format of the IP address"
        ::= { dvbInaNmAccessEntry 4 }

dvbInaNmAccessIpMask OBJECT-TYPE
        SYNTAX      InetAddress
        MAX-ACCESS  read-create
        STATUS      current
        DESCRIPTION
            "The IP subnet mask of the network management stations.
             If traps are enabled for this entry, then the value must
             be 255.255.255.255."
        DEFVAL { 'ffffffff'h }
        ::= { dvbInaNmAccessEntry 5 }

dvbInaNmAccessCommunity OBJECT-TYPE
        SYNTAX      DisplayString
        MAX-ACCESS  read-create
        STATUS      current
        DESCRIPTION
            "The community string to be matched for access by this
             entry. If set to the null string then any community string
             will match."
        DEFVAL { "public" }
        ::= { dvbInaNmAccessEntry 6 }

dvbInaNmAccessControl OBJECT-TYPE
        SYNTAX      INTEGER {
            none(1),
            read(2),
            readWrite(3),
            roWithTraps(4),
            rwWithTraps(5),
            trapsOnly(6)
        }
        MAX-ACCESS  read-create

Pedersen         Informational - Expires August 2001               13
                       DVB Cable INA Device MIB               Feb 2001

        STATUS      current
        DESCRIPTION
            "Specifies the type of access allowed to this NMS. Setting
             this object to none(1) causes the table entry to be
             destroyed. Read(2) allows access by 'get' and 'get-next'
             PDUs. ReadWrite(3) allows access by 'set' as well.
             RoWithtraps(4), rwWithTraps(5), and trapsOnly(6)
             control distribution of Trap PDUs transmitted by this
             device."
        DEFVAL { read }
        ::= { dvbInaNmAccessEntry 7 }

dvbInaNmAccessInterfaces OBJECT-TYPE
        SYNTAX      OCTET STRING ( SIZE(4) )
        MAX-ACCESS  read-create
        STATUS      current
        DESCRIPTION
            "Specifies the set of interfaces from which requests from
             this NMS will be accepted.
             Each octet within the value of this object specifies a set
             of eight interfaces, with the first octet specifying
             interfaces 1 through 8, the second octet specifying
             interfaces 9 through 16, etc.  Within each octet, the most
             significant bit represents the lowest numbered interface,
             and the least significant bit represents the highest
             numbered interface. Thus, each interface is represented by
             a single bit within the value of this object. If that bit
             has a value of '1' then that interface is included in the
             set.

             Note that entries in this table apply only to link-layer
             interfaces (e.g., Ethernet and CATV MAC). Upstream and
             downstream channel interfaces must not be specified."
        ::= { dvbInaNmAccessEntry 8 }

dvbInaNmAccessStatus OBJECT-TYPE
        SYNTAX      RowStatus
        MAX-ACCESS  read-create
        STATUS      current
        DESCRIPTION
            "Controls and reflects the status of rows in this table."
        ::= { dvbInaNmAccessEntry 9 }

dvbInaNmAccessLevelEnable OBJECT-TYPE
        SYNTAX      BITS
        MAX-ACCESS  read-create
        STATUS      current
        DESCRIPTION
            "Each bit of this 16 bit unsigned object flags whether the
             manager in question shall receive traps of the associated
             priority level. Bit 0 specifies whether the manager shall
             receive traps of level 1, bit 1 of level 2 etc.
             Bit 0 is the least significant bit of this object."
        ::= { dvbInaNmAccessEntry 10 }

Pedersen         Informational - Expires August 2001               14
                       DVB Cable INA Device MIB               Feb 2001



-- - - - - - - - - - - - - - - - - - - - - - - - - - - - - - - - - -
-- Software Group
--
-- The Software Group controls software upload from and download into
-- the INA using TFTP. This group includes the Software Version Table.
-- The group is optional.
-- - - - - - - - - - - - - - - - - - - - - - - - - - - - - - - - - -

dvbInaSwTftpServerAddrType OBJECT-TYPE
        SYNTAX      InetAddressType
        MAX-ACCESS  read-write
        STATUS      current
        DESCRIPTION
            "Format of IP address of the Tftp Server"
        ::= { dvbInaSw 1 }

dvbInaSwTftpServer OBJECT-TYPE
        SYNTAX      InetAddress
        MAX-ACCESS  read-write
        STATUS      current
        DESCRIPTION
            "Cached IP address of the TFTP server for software
             upgrades."
        ::= { dvbInaSw 2 }

dvbInaSwTftpFilename OBJECT-TYPE
        SYNTAX      DisplayString (SIZE (0..64))
        MAX-ACCESS  read-write
        STATUS      current
        DESCRIPTION
            "File name of file on TFTP server. In the case of a file
            upload, this object contains the filename of the file on
            the TFTP server. In the case of a file download this object
            contains the path and file name of the file to be
            downloaded on the TFTP server."
        ::= { dvbInaSw 3 }

dvbInaSwFilename OBJECT-TYPE
        SYNTAX      DisplayString (SIZE (0..64))
        MAX-ACCESS  read-write
        STATUS      current
        DESCRIPTION
            "File name of file on INA. In the case of a file upload,
             this object contains the file on the INA to be uploaded.
             In the case of a file download this object contains the
             path and file name of the file on the INA."
        ::= { dvbInaSw 4 }

dvbInaSwAdminStatus OBJECT-TYPE
        SYNTAX      INTEGER {
            initImageDownLoad(1),
            initImageUpLoad(2),

Pedersen         Informational - Expires August 2001               15
                       DVB Cable INA Device MIB               Feb 2001

            initFileDownLoad(3),
            initFileUpLoad(4),
            idle(8)
        }
        MAX-ACCESS  read-write
        STATUS      current
        DESCRIPTION
            "Request software download or upload. The following values
             can be set: 'InitImageDownLoad(1)', 'InitImageUpLoad(1)',
             'InitFileDownLoad(1)', 'InitFileUpLoad(1)' and 'Idle(8)'.
             Default value of this parameter is 'Idle(8)'. As long as
             a file or image transfer is in progress its value is equal
             to the value set, otherwise 'Idle(8)'."
        ::= { dvbInaSw 5 }

dvbInaSwOperStatus OBJECT-TYPE
        SYNTAX      INTEGER {
            initImageDownload(1),
            contactingTFTPServer(2),
            downloadInprogress(3),
            failed(4),
            downloadSuccessful(5),
            idle(6),
            initImageUpLoad(7),
            imageDownLoad(8),
            initFileDownload(9),
            initFileUpload(10),
            uploadInprogress(11),
            uploadSuccessful(12)
        }
        MAX-ACCESS  read-only
        STATUS      current
        DESCRIPTION
            "Indicates actual status of TFTP download. This object can
             have one of the following states:
                 'InitImageDownload(1)',
                 'ContactingTFTPServer(2)',
                 'DownloadInprogress(3)',
                 'Failure(4)',
                 'DownloadSuccessful(5)',
                 'Idle(6)',
                 'InitImageUpLoad(7)',
                 'ImageDownload(8)',
                 'InitFileDownLoad(9)',
                 'InitFileUpLoad(10)',
                 'UploadInprogress(11)'
             and 'UploadSuccessful(12)'.
             After reset the state is 'Idle(6)'."
        ::= { dvbInaSw 6 }

dvbInaSwDownLoadSlot OBJECT-TYPE
        SYNTAX      Integer32 (0..10)
        MAX-ACCESS  read-write
        STATUS      current

Pedersen         Informational - Expires August 2001               16
                       DVB Cable INA Device MIB               Feb 2001

        DESCRIPTION
            "This identifies the image slot in which the image is to be
             downloaded. Slot 0 is a special case that is used to
             identify a direct to RAM download. This can be used e.g.
             for diagnostics or debugging purposes.
             By default this object will point to the first empty slot.
             If there are no empty slots, it will point to the first
             backup image."
        ::= { dvbInaSw 7 }


-- - - - - - - - - - - - - - - - - - - - - - - - - - - - - - - - - - -
-- Software Version Table
--
-- The software version table contains a number of entries i.e. slots.
-- Each slot can contain an image and information about the image
-- in question
-- The table is optional.
-- - - - - - - - - - - - - - - - - - - - - - - - - - - - - - - - - - -

dvbInaSwVersTable OBJECT-TYPE
        SYNTAX      SEQUENCE OF DvbInaSwVersEntry
        MAX-ACCESS  not-accessible
        STATUS      current
        DESCRIPTION
            "This table contains a number of entries i.e. slots.
             Each slot can contain an image and information
             about the image."
        ::= { dvbInaSw 8 }

dvbInaSwVersEntry OBJECT-TYPE
        SYNTAX      DvbInaSwVersEntry
        MAX-ACCESS  not-accessible
        STATUS      current
        DESCRIPTION
            ""
        INDEX { dvbInaSwIndex  }
        ::= {  dvbInaSwVersTable 1 }

DvbInaSwVersEntry ::= SEQUENCE {
            dvbInaSwIndex         Integer32,
            dvbInaSwSlot          Integer32,
            dvbInaSwVersion       DisplayString,
            dvbInaSwState         INTEGER,
            dvbInaSwAction        INTEGER,
            dvbInaSwDateTime      DateAndTime
        }

dvbInaSwIndex OBJECT-TYPE
        SYNTAX      Integer32
        MAX-ACCESS  not-accessible
        STATUS      current
        DESCRIPTION
            "This 32-bit integer is the current index of this entry."

Pedersen         Informational - Expires August 2001               17
                       DVB Cable INA Device MIB               Feb 2001

        ::= { dvbInaSwVersEntry 1 }

dvbInaSwSlot OBJECT-TYPE
        SYNTAX      Integer32 (0..10)
        MAX-ACCESS  read-only
        STATUS      current
        DESCRIPTION
            "This is the image slot number of this entry. Slot 0 is
             reserved for RAM, it is used to identify an image directly
             loaded into RAM e.g. for debugging purposes."
        ::= { dvbInaSwVersEntry 2 }

dvbInaSwVersion OBJECT-TYPE
        SYNTAX      DisplayString
        MAX-ACCESS  read-only
        STATUS      current
        DESCRIPTION
            "The version of the software loaded in this slot. This is a
             manufacturer dependent string."
        ::= { dvbInaSwVersEntry 3 }

dvbInaSwState OBJECT-TYPE
        SYNTAX      INTEGER {
             executing(1),
             failed(2),
             none(3)
        }
        MAX-ACCESS  read-only
        STATUS      current
        DESCRIPTION
            "The execution state of the image in this slot.
             The following states are possible:
                'Executing(1)', 'Failed(2)' or 'None(3)'."
        ::= { dvbInaSwVersEntry 4 }

dvbInaSwAction OBJECT-TYPE
        SYNTAX      INTEGER {
             boot(1),
             backup(2),
             none(3),
             emptySlot(4)
        }
        MAX-ACCESS  read-only
        STATUS      current
        DESCRIPTION
            "This identifies the image to be used during boot.
             The following actions are possible:
                'Boot(1)', 'Backup(2)', 'None(3)' and 'EmptySlot(4)'."
        ::= { dvbInaSwVersEntry 5 }

dvbInaSwDateTime OBJECT-TYPE
        SYNTAX      DateAndTime
        MAX-ACCESS  read-only
        STATUS      current

Pedersen         Informational - Expires August 2001               18
                       DVB Cable INA Device MIB               Feb 2001

        DESCRIPTION
            "This specifies the date and time the image was loaded
             in this slot.
             This identifies the image to be used during boot."
        ::= { dvbInaSwVersEntry 6 }


-- - - - - - - - - - - - - - - - - - - - - - - - - - - - - - - - - - -
-- BOOTP/DHCP Table
--
-- The BOOTP/DHCP Table contains the BOOTP and DHCP servers used by this
-- INA. The index into this table is the ifIndex and the IP address of
-- the BOOTP or DHCP server in question.
-- The table is mandatory if the DHCP relay function is supported.
-- Otherwise it is optional.
-- - - - - - - - - - - - - - - - - - - - - - - - - - - - - - - - - - -

dvbInaDhcpServerTable OBJECT-TYPE
        SYNTAX      SEQUENCE OF DvbInaDhcpServerEntry
        MAX-ACCESS  not-accessible
        STATUS      current
        DESCRIPTION
           "Server table contains the DHCP/BOOTP servers used by this
            INA."
        ::= { dvbInaDhcp 1 }

dvbInaDhcpServerEntry OBJECT-TYPE
        SYNTAX      DvbInaDhcpServerEntry
        MAX-ACCESS  not-accessible
        STATUS      current
        DESCRIPTION
            "Server table is indexed through the ifIndex and the
             IP address of the BOOTP or DHCP server in question."
        INDEX {dvbInaDhcpServerIfIndex,
               dvbInaDhcpServerIpType,
               dvbInaDhcpServerIp}
        ::= { dvbInaDhcpServerTable 1 }

DvbInaDhcpServerEntry ::= SEQUENCE {
            dvbInaDhcpServerIfIndex            InterfaceIndexOrZero,
            dvbInaDhcpServerIpType             InetAddressType,
            dvbInaDhcpServerIp                 InetAddress,
            dvbInaDhcpServerRowAccessStatus    RowStatus,
            dvbInaDhcpServerRelayEnable        TruthValue,
            dvbInaDhcpServerAssociation        INTEGER,
            dvbInaDhcpServerPrimaryOrSecondary INTEGER
        }

dvbInaDhcpServerIfIndex OBJECT-TYPE
        SYNTAX      InterfaceIndexOrZero
        MAX-ACCESS  not-accessible
        STATUS      current
        DESCRIPTION
            "This object contains the ifIndex of the interface via

Pedersen         Informational - Expires August 2001               19
                       DVB Cable INA Device MIB               Feb 2001

             which the DHCP server is communicating with the INA."
        ::= { dvbInaDhcpServerEntry 1 }

dvbInaDhcpServerIpType OBJECT-TYPE
        SYNTAX      InetAddressType
        MAX-ACCESS  not-accessible
        STATUS      current
        DESCRIPTION
            "Specifies the format of the IP Address"
        ::= { dvbInaDhcpServerEntry 2 }

dvbInaDhcpServerIp OBJECT-TYPE
        SYNTAX      InetAddress
        MAX-ACCESS  not-accessible
        STATUS      current
        DESCRIPTION
            "The IP address of this DHCP server. In the case the IP
             address is the all ones address, the DHCP message will
             be broadcast on the connected IP network."
        ::= { dvbInaDhcpServerEntry 3 }

dvbInaDhcpServerRowAccessStatus OBJECT-TYPE
        SYNTAX      RowStatus
        MAX-ACCESS  read-create
        STATUS      current
        DESCRIPTION
            "Controls and reflects the status of this row in
             this table."
        ::= { dvbInaDhcpServerEntry 4 }

dvbInaDhcpServerRelayEnable OBJECT-TYPE
        SYNTAX      TruthValue
        MAX-ACCESS  read-create
        STATUS      current
        DESCRIPTION
            "This object enables or disables the INA to relay the DHCP
             message to this DHCP server."
        ::= { dvbInaDhcpServerEntry 5 }

dvbInaDhcpServerAssociation OBJECT-TYPE
        SYNTAX      INTEGER {
             ina(1),
             niu(2),
             client(3)
        }
        MAX-ACCESS  read-create
        STATUS      current
        DESCRIPTION
            "This object defines the server association either
             ina/niu/client.
             It is optional to support the ina value."
        ::= { dvbInaDhcpServerEntry 6 }

dvbInaDhcpServerPrimaryOrSecondary OBJECT-TYPE

Pedersen         Informational - Expires August 2001               20
                       DVB Cable INA Device MIB               Feb 2001

        SYNTAX      INTEGER {
             primary(1),
             secondary(2)
        }
        MAX-ACCESS  read-create
        STATUS      current
        DESCRIPTION
            "This object defines the Primary/Secondary server
             association."
        ::= { dvbInaDhcpServerEntry 7 }


-- - - - - - - - - - - - - - - - - - - - - - - - - - - - - - - - - - -
-- Event Group
--
-- The Event Group is used for trap throttling, event filtering and
-- event logging
-- - - - - - - - - - - - - - - - - - - - - - - - - - - - - - - - - - -

dvbInaEvControl OBJECT-TYPE
        SYNTAX      INTEGER {
             resetLog(1),
             useDefaultReporting(2)
        }
        MAX-ACCESS  read-write
        STATUS      current
        DESCRIPTION
            "Setting this object to resetLog(1) empties the event log.
             All data is deleted. Setting it to useDefaultReporting(2)
             returns all event priorities to their factory-default
             reporting. Reading this object always returns
             useDefaultReporting(2)."
        ::= { dvbInaEvent 1 }

dvbInaEvSyslogIpType OBJECT-TYPE
        SYNTAX      InetAddressType
        MAX-ACCESS  read-write
        STATUS      current
        DESCRIPTION
            "The IP address type of the SysLog server."
        ::= { dvbInaEvent 2}

dvbInaEvSyslogIp    OBJECT-TYPE
        SYNTAX      InetAddress
        MAX-ACCESS  read-write
        STATUS      current
        DESCRIPTION
            "The IP address of the Syslog server. If 0.0.0.0, syslog
             transmission is inhibited."
        ::= { dvbInaEvent 3}

dvbInaEvThrottleAdminStatus     OBJECT-TYPE
        SYNTAX      INTEGER {
                    unconstrained(1),

Pedersen         Informational - Expires August 2001               21
                       DVB Cable INA Device MIB               Feb 2001

                    maintainBelowThreshold(2),
                    stopAtThreshold(3),
                    inhibited(4)
                    }
        MAX-ACCESS  read-write
        STATUS      current
        DESCRIPTION
            "Controls the transmission of traps and syslog messages
             with respect to the trap pacing threshold.

             unconstrained(1) causes traps and syslog messages to be
             transmitted without regard to the threshold settings.

             maintainBelowThreshold(2) causes trap transmission and
             syslog messages to be suppressed if the number of traps
             would otherwise exceed the threshold.

             stopAtThreshold(3) causes trap transmission to cease
             at the threshold, and not resume until directed to do so.

             inhibited(4) causes all trap transmission and syslog
             messages to be suppressed.

             A single event is always treated as a single event for
             threshold counting. That is, an event causing both a trap
             and a syslog message is still treated as a single event.

             Writing to this object resets the thresholding state.

             At initial startup, this object has a default value of
             unconstrained(1)."
        ::= { dvbInaEvent 4 }

dvbInaEvThrottleInhibited       OBJECT-TYPE
        SYNTAX      TruthValue
        MAX-ACCESS  read-only
        STATUS      current
        DESCRIPTION
            "If true(1), trap and syslog transmission is currently
             inhibited due to thresholds and/or the current setting of
             dvbInaEvThrottleAdminStatus. In addition, this is set to
             true(1) if transmission is inhibited due to no
             syslog (dvbInaEvSyslogIp) or trap (dvbInaNmAccessEntry)
             destinations having been set."
        ::= { dvbInaEvent 5 }

dvbInaEvThrottleThreshold       OBJECT-TYPE
        SYNTAX      Unsigned32
        MAX-ACCESS  read-write
        STATUS      current
        DESCRIPTION
            "Number of trap/syslog events per dvbInaEvThrottleInterval
             to be transmitted before throttling.


Pedersen         Informational - Expires August 2001               22
                       DVB Cable INA Device MIB               Feb 2001

             A single event is always treated as a single event for
             threshold counting. That is, an event causing both a trap
             and a syslog message is still treated as a single event.

             At initial startup, this object returns 0."
        ::= { dvbInaEvent 6 }

dvbInaEvThrottleInterval        OBJECT-TYPE
        SYNTAX      Integer32 ( 1..2147483647 )
        UNITS       "seconds"
        MAX-ACCESS  read-write
        STATUS      current
        DESCRIPTION
            "The interval over which the trap threshold applies.
             At initial startup, this object has a value of 1."
        ::= { dvbInaEvent 7 }


    -- - - - - - - - - - - - - - - -
    -- Event Control Table
    -- - - - - - - - - - - - - - - -

dvbInaEvControlTable OBJECT-TYPE
        SYNTAX      SEQUENCE OF DvbInaEvControlEntry
        MAX-ACCESS  not-accessible
        STATUS      current
        DESCRIPTION
            "The Event Control Table allows configuration of the
             reporting mechanisms used for a particular event
             priority. The event priority level indexes the table"
        ::= {  dvbInaEvent 9 }


dvbInaEvControlEntry OBJECT-TYPE
        SYNTAX      DvbInaEvControlEntry
        MAX-ACCESS  not-accessible
        STATUS      current
        DESCRIPTION
            "Allows configuration of the reporting mechanisms for a
             particular event priority."
        INDEX { dvbInaEvPriority }
        ::= { dvbInaEvControlTable 1 }

DvbInaEvControlEntry ::= SEQUENCE {
            dvbInaEvPriority        INTEGER,
            dvbInaEvReporting       BITS
        }

dvbInaEvPriority OBJECT-TYPE
        SYNTAX INTEGER {
            emergency (1),
            alert (2),
            critical (3),
            error (4),

Pedersen         Informational - Expires August 2001               23
                       DVB Cable INA Device MIB               Feb 2001

            warning (5),
            notice (6),
            information (7),
            debug (8)
        }
        MAX-ACCESS  not-accessible
        STATUS      current
        DESCRIPTION
            "The priority level that is controlled by this entry."
        ::= { dvbInaEvControlEntry 1 }

dvbInaEvReporting OBJECT-TYPE
        SYNTAX BITS {
            local (0),
            traps (1),
            syslog (2)
        }
        MAX-ACCESS  read-write
        STATUS      current
        DESCRIPTION
            "Defines the action to be taken on occurrence of this
             event class. If the local(0) bit is set, then log to the
             internal log, if the traps(1) bit is set, then generate
             a trap, if the syslog(2) bit is set, then send a syslog
             message."
        ::= { dvbInaEvControlEntry 2 }

    -- - - - - - - - - - - - - - - -
    -- Event Table
    -- - - - - - - - - - - - - - - -

dvbInaEvTable OBJECT-TYPE
        SYNTAX      SEQUENCE OF DvbInaEvEntry
        MAX-ACCESS  not-accessible
        STATUS      current
        DESCRIPTION
            "The Event Table contains a log of network and device
             events. The table is indexed by an arbitrary integer."
        ::= {  dvbInaEvent 10 }

dvbInaEvMaxNumberOfEntries OBJECT-TYPE
        SYNTAX      Integer32 (1..2147483647)
        MAX-ACCESS  read-write
        STATUS            current
        DESCRIPTION
            "Describes the maximum number of entries that can be
             contained in the Event table"
        ::= { dvbInaEvent 11 }

dvbInaEvEntry OBJECT-TYPE
        SYNTAX      DvbInaEvEntry
        MAX-ACCESS  not-accessible
        STATUS      current
        DESCRIPTION

Pedersen         Informational - Expires August 2001               24
                       DVB Cable INA Device MIB               Feb 2001

            "Describes a network or device event that may be of
             interest in fault isolation and troubleshooting."
        INDEX { dvbInaEvIndex }
        ::= { dvbInaEvTable 1 }

DvbInaEvEntry ::= SEQUENCE {
            dvbInaEvIndex           Integer32,
            dvbInaEvFirstTime       DateAndTime,
            dvbInaEvLastTime        DateAndTime,
            dvbInaEvCount           Counter32,
            dvbInaEvLevel           Integer32,
            dvbInaEvId              Unsigned32,
            dvbInaEvText            DisplayString
        }

dvbInaEvIndex OBJECT-TYPE
        SYNTAX      Integer32 (1..2147483647)
        MAX-ACCESS  not-accessible
        STATUS      current
        DESCRIPTION
            "Provides relative ordering of the objects in the event
             log. This object will always increase except when
             (a) the log is reset via dvbInaEvControl,
             (b) the device reboots and does not implement nonvolatile
             storage for this log, or (c) it reaches the value 2^31.
             The next entry for all the above cases is 1."
        ::= { dvbInaEvEntry 1 }

dvbInaEvFirstTime OBJECT-TYPE
        SYNTAX      DateAndTime
        MAX-ACCESS  read-only
        STATUS      current
        DESCRIPTION
            "The time that this entry was created."
        ::= { dvbInaEvEntry 2 }

dvbInaEvLastTime OBJECT-TYPE
        SYNTAX      DateAndTime
        MAX-ACCESS  read-only
        STATUS      current
        DESCRIPTION
            "If multiple events are reported via the same entry, the
             time that the last event for this entry occurred."
        ::= { dvbInaEvEntry 3 }

dvbInaEvCount OBJECT-TYPE
        SYNTAX      Counter32
        MAX-ACCESS  read-only
        STATUS      current
        DESCRIPTION
            "The number of consecutive event instances reported by
             this entry."
        ::= { dvbInaEvEntry 4 }


Pedersen         Informational - Expires August 2001               25
                       DVB Cable INA Device MIB               Feb 2001

dvbInaEvLevel OBJECT-TYPE
        SYNTAX      Integer32 (0..255)
        MAX-ACCESS  read-only
        STATUS      current
        DESCRIPTION
            "The priority level of this event as defined by the
             vendor."
        ::= { dvbInaEvEntry 5 }

--
-- Vendors will provide their own enumerations for the following.
-- The interpretation of the enumeration is unambiguous for a
-- particular value of the vendor's enterprise number in sysObjectID.
--

dvbInaEvId OBJECT-TYPE
        SYNTAX      Unsigned32
        MAX-ACCESS  read-only
        STATUS      current
        DESCRIPTION
            "For this product, uniquely identifies the type of event
             that is reported by this entry."
        ::= { dvbInaEvEntry 6 }

dvbInaEvText OBJECT-TYPE
        SYNTAX      DisplayString
        MAX-ACCESS  read-only
        STATUS      current
        DESCRIPTION
            "Provides a human-readable description of the event."
        ::= { dvbInaEvEntry 7 }


-- - - - - - - - - - - - - - - - - - - - - - - - - - - - - - - - - -
-- Optional IP Filter Group
--
-- The IP Filter Group is used to configure IP filters. These filters
-- can be configured to forward packets or to drop packets matching a
-- set of layer three protocols.
-- - - - - - - - - - - - - - - - - - - - - - - - - - - - - - - - - -

dvbInaIpFilterEnable OBJECT-TYPE
        SYNTAX INTEGER {
            enable (1),
            enableAuto (2),
            countHits (3),
            disabled (4)
        }
        MAX-ACCESS  read-write
        STATUS      current
        DESCRIPTION
            "This controls the IP filter table. This object can be set
            to the following values:
            'enable(1)': Enables the IP filter table.

Pedersen         Informational - Expires August 2001               26
                       DVB Cable INA Device MIB               Feb 2001

            'enableAuto(2)': Enables the IP filter table with automatic
            IP anti-spoofing population by sniffing DHCP messages.
            'countHits(3)': This option is used to debug the filter
            table.  It allows packets to be checked against the filter
            table and increments dvbInaIpFilterMaches for a matching
            filter.  However, all packets are allowed through.
            'disabled(4)': Disables IP filtering, all packets are
            allowed through."
        ::= { dvbInaIpFilter 1 }

dvbInaIpFilterTable OBJECT-TYPE
        SYNTAX      SEQUENCE OF DvbInaIpFilterEntry
        MAX-ACCESS  not-accessible
        STATUS      current
        DESCRIPTION
            "The IP Filter Table describes a filter to apply to IP
             traffic as received on a specified interface. Both source
             and destination addresses must match for the filter to
             apply.  To create an entry in this table,
             dvbInaIpFilterIndex must be specified. Filter application
             is ordered by the filter index."
        ::= { dvbInaIpFilter 2 }

dvbInaIpFilterEntry OBJECT-TYPE
        SYNTAX      DvbInaIpFilterEntry
        MAX-ACCESS  not-accessible
        STATUS      current
        DESCRIPTION
            "Describes a filter to apply to IP traffic received on a
             specified interface. Both source and destination
             addresses must match for the filter to apply."
        INDEX { dvbInaIpFilterIndex }
        ::= { dvbInaIpFilterTable 1 }

DvbInaIpFilterEntry ::= SEQUENCE {
            dvbInaIpFilterIndex             Integer32,
            dvbInaIpFilterStatus            RowStatus,
            dvbInaIpFilterAssignedBy        INTEGER,
            dvbInaIpFilterIfIndex           InterfaceIndexOrZero,
            dvbInaIpFilterDirection         INTEGER,
            dvbInaIpFilterTos               OCTET STRING,
            dvbInaIpFilterTosMask           OCTET STRING,
            dvbInaIpFilterSrcAddrType       InetAddressType,
            dvbInaIpFilterSrcAddr           InetAddress,
            dvbInaIpFilterSrcMaskType       InetAddressType,
            dvbInaIpFilterSrcMask           InetAddress,
            dvbInaIpFilterDstAddrType       InetAddressType,
            dvbInaIpFilterDstAddr           InetAddress,
            dvbInaIpFilterDstMaskType       InetAddressType,
            dvbInaIpFilterDstMask           InetAddress,
            dvbInaIpFilterProtocol          INTEGER,
            dvbInaIpFilterSourcePortLow     Integer32,
            dvbInaIpFilterSourcePortHigh    Integer32,
            dvbInaIpFilterDestPortLow       Integer32,

Pedersen         Informational - Expires August 2001               27
                       DVB Cable INA Device MIB               Feb 2001

            dvbInaIpFilterDestPortHigh      Integer32,
            dvbInaIpFilterAction            INTEGER,
            dvbInaIpFilterMatches           Counter32,
            dvbInaIpFilterContinue          TruthValue,
            dvbInaIpFilterTosMapIndex       Integer32
        }

dvbInaIpFilterIndex OBJECT-TYPE
        SYNTAX      Integer32 (1..2147483647)
        MAX-ACCESS  not-accessible
        STATUS      current
        DESCRIPTION
            "Index used to order the application of filters.
             The filter with the lowest index is always applied
             first."
        ::= { dvbInaIpFilterEntry 1 }

dvbInaIpFilterStatus OBJECT-TYPE
        SYNTAX      RowStatus
        MAX-ACCESS  read-create
        STATUS      current
        DESCRIPTION
            "Controls and reflects the status of rows in this table.
             The filter is not applied until this object is set to
             (or changes to) active."
        ::= { dvbInaIpFilterEntry 2 }

dvbInaIpFilterAssignedBy OBJECT-TYPE
        SYNTAX INTEGER {
            dhcp (1),
            static (2),
            snmp (3)
        }
        MAX-ACCESS  read-create
        STATUS      current
        DESCRIPTION
            "This object identifies what created this entry and is
             automatically set when a filter is created. This object
             shall have one of the following values: 'dhcp(1)',
             'static(2)' and 'snmp(3)'."
        ::= { dvbInaIpFilterEntry 3 }

dvbInaIpFilterIfIndex OBJECT-TYPE
        SYNTAX      InterfaceIndexOrZero
        MAX-ACCESS  read-create
        STATUS      current
        DESCRIPTION
            "The entry interface to which this filter applies. The
             value corresponds to ifIndex for either a CATV MAC or
             another network interface."
        ::= { dvbInaIpFilterEntry 4 }

dvbInaIpFilterDirection OBJECT-TYPE
        SYNTAX INTEGER {

Pedersen         Informational - Expires August 2001               28
                       DVB Cable INA Device MIB               Feb 2001

            inbound (1),
            outbound (2),
            both (3)
        }
        MAX-ACCESS  read-create
        STATUS      current
        DESCRIPTION
            "Determines whether the filter is applied to inbound(1)
             traffic, outbound(2) traffic, or traffic in both(3)
             directions."
        ::= { dvbInaIpFilterEntry 5 }

dvbInaIpFilterTos OBJECT-TYPE
        SYNTAX      OCTET STRING ( SIZE (1))
        MAX-ACCESS  read-create
        STATUS      current
        DESCRIPTION
            "This is the value to be matched to the packet's TOS
             (Type of Service) value (after the TOS value is AND'd
             with  dvbInaIpFilterTosMask)."
        ::= { dvbInaIpFilterEntry 6 }

dvbInaIpFilterTosMask OBJECT-TYPE
        SYNTAX      OCTET STRING ( SIZE (1))
        MAX-ACCESS  read-create
        STATUS      current
        DESCRIPTION
            "The mask to be applied to the packet's TOS value before
             matching."
        ::= { dvbInaIpFilterEntry 7 }

dvbInaIpFilterSrcAddrType OBJECT-TYPE
        SYNTAX      InetAddressType
        MAX-ACCESS  read-create
        STATUS      current
        DESCRIPTION
            "The type of the source IP address."
        ::= { dvbInaIpFilterEntry 8 }

dvbInaIpFilterSrcAddr OBJECT-TYPE
        SYNTAX      InetAddress
        MAX-ACCESS  read-create
        STATUS      current
        DESCRIPTION
            "The source IP address, or portion thereof, that is to be
             matched for this filter."
        ::= { dvbInaIpFilterEntry 9 }

dvbInaIpFilterSrcMaskType OBJECT-TYPE
        SYNTAX      InetAddressType
        MAX-ACCESS  read-create
        STATUS      current
        DESCRIPTION
            "The type of the source mask IP address."

Pedersen         Informational - Expires August 2001               29
                       DVB Cable INA Device MIB               Feb 2001

        ::= { dvbInaIpFilterEntry 10 }

dvbInaIpFilterSrcMask OBJECT-TYPE
        SYNTAX      InetAddress
        MAX-ACCESS  read-create
        STATUS      current
        DESCRIPTION
            "A bit mask that is to be applied to the source address
             prior to matching. This mask is not necessarily the same
             as a subnet mask, but 1's bits must be leftmost and
             contiguous."
        ::= { dvbInaIpFilterEntry 11 }

dvbInaIpFilterDstAddrType OBJECT-TYPE
        SYNTAX      InetAddressType
        MAX-ACCESS  read-create
        STATUS      current
        DESCRIPTION
            "The type of the destination IP address."
        ::= { dvbInaIpFilterEntry 12 }

dvbInaIpFilterDstAddr OBJECT-TYPE
        SYNTAX      InetAddress
        MAX-ACCESS  read-create
        STATUS      current
        DESCRIPTION
            "The destination IP address, or portion thereof, that is
             to be matched for this filter."
        ::= { dvbInaIpFilterEntry 13 }

dvbInaIpFilterDstMaskType OBJECT-TYPE
        SYNTAX      InetAddressType
        MAX-ACCESS  read-create
        STATUS      current
        DESCRIPTION
            "The type of the destination mask IP address."
        ::= { dvbInaIpFilterEntry 14 }

dvbInaIpFilterDstMask OBJECT-TYPE
        SYNTAX      InetAddress
        MAX-ACCESS  read-create
        STATUS      current
        DESCRIPTION
            "A bit mask that is to be applied to the destination
             address prior to matching. This mask is not necessarily
             the same as a subnet mask, but 1's bits must be leftmost
             and contiguous "
        ::= { dvbInaIpFilterEntry 15 }

dvbInaIpFilterProtocol OBJECT-TYPE
        SYNTAX INTEGER {
            icmp (1),
            tcp (6),
            udp (17),

Pedersen         Informational - Expires August 2001               30
                       DVB Cable INA Device MIB               Feb 2001

            any (256)
        }
        MAX-ACCESS  read-create
        STATUS      current
        DESCRIPTION
            "The IP protocol value that is to be matched. For
             example: icmp is 1, tcp is 6, udp is 17. A value of
             256 matches ANY protocol."
        ::= { dvbInaIpFilterEntry 16 }

dvbInaIpFilterSourcePortLow OBJECT-TYPE
        SYNTAX      Integer32 (0..65535)
        MAX-ACCESS  read-create
        STATUS      current
        DESCRIPTION
            "If dvbInaIpFilterProtocol is udp or tcp, this is the
             inclusive lower bound of the transport-layer source
             port range that is to be matched."
        ::= { dvbInaIpFilterEntry 17 }

dvbInaIpFilterSourcePortHigh OBJECT-TYPE
        SYNTAX      Integer32 (0..65535)
        MAX-ACCESS  read-create
        STATUS      current
        DESCRIPTION
            "If dvbInaIpFilterProtocol is udp or tcp, this is the
             inclusive upper bound of the transport-layer source
             port range that is to be matched."
        ::= { dvbInaIpFilterEntry 18 }

dvbInaIpFilterDestPortLow OBJECT-TYPE
        SYNTAX      Integer32 (0..65535)
        MAX-ACCESS  read-create
        STATUS      current
        DESCRIPTION
            "If dvbInaIpFilterProtocol is udp or tcp, this is the
             inclusive lower bound of the transport-layer
             destination port range that is to be matched."
        ::= { dvbInaIpFilterEntry 19 }

dvbInaIpFilterDestPortHigh OBJECT-TYPE
        SYNTAX      Integer32 (0..65535)
        MAX-ACCESS  read-create
        STATUS      current
        DESCRIPTION
            "If dvbInaIpFilterProtocol is udp or tcp, this is the
             inclusive upper bound of the transport-layer
             destination port range that is to be matched."
        ::= { dvbInaIpFilterEntry 20 }

dvbInaIpFilterAction OBJECT-TYPE
        SYNTAX INTEGER {
            discard (1),
            accept (2),

Pedersen         Informational - Expires August 2001               31
                       DVB Cable INA Device MIB               Feb 2001

            tosmap (3)
        }
        MAX-ACCESS  read-create
        STATUS      current
        DESCRIPTION
            "discard(1) : Discard all packets matching this filter.

             accept(2)  : Accept packet for further processing.
                          If dvbInaIpFilterContinue is set to true,
                          see if there are other matches, otherwise
                          done.

             tosmap(3)  : Change the TOS in the IP packet according to
                          the specification in the TOS MAP table.
                          If the TOS MAP index is 0 or no entry is
                          found in the TOS MAP table. Otherwise treat as
                          accept.
                          If dvbInaIpFilterContinue is set to true,
                          see if there are other matches, otherwise
                          done."
        ::= { dvbInaIpFilterEntry 21 }

dvbInaIpFilterMatches OBJECT-TYPE
        SYNTAX      Counter32
        MAX-ACCESS  read-only
        STATUS      current
        DESCRIPTION
            "Counts the number of times this filter was matched."
        ::= { dvbInaIpFilterEntry 22 }

dvbInaIpFilterContinue OBJECT-TYPE
        SYNTAX      TruthValue
        MAX-ACCESS  read-create
        STATUS      current
        DESCRIPTION
            "If this value is set to true(1), and
             dvbInaIpFilterControl is anything but discard(1),
             continue test of next filter rows and applying actions."
        ::= { dvbInaIpFilterEntry 23 }

dvbInaIpFilterTosMapIndex OBJECT-TYPE
        SYNTAX      Integer32 (0..65535)
        MAX-ACCESS  read-create
        STATUS      current
        DESCRIPTION
            "This object points to an entry in dvbInaIpTosMapTable.
             If dvbInaIpFilterControl is set to tosmap(3), do the
             TOS mapping in dvbInaIpTosMapTable with this index.
             If no matching TOS map index exists, treat as if
             dvbInaIpFilterControl were set to accept(1).
             If this object is set ot the value of 0, there is no
             matching TOS map."
        ::= { dvbInaIpFilterEntry 24 }


Pedersen         Informational - Expires August 2001               32
                       DVB Cable INA Device MIB               Feb 2001

  -- TOS Map Table

dvbInaIpTosMapTable OBJECT-TYPE
       SYNTAX      SEQUENCE OF DvbInaIpTosMapEntry
       MAX-ACCESS  not-accessible
       STATUS      current
       DESCRIPTION
           "A table which specifies a TOS change.
            dvbInaIpFilterTosMapIndex points to a specific row in this
            table that specifies a TOS change.
            This table applies only to the TOS within the IP header.
            Index 0 is reserved."
       ::= { dvbInaIpFilter 3 }

dvbInaIpTosMapEntry OBJECT-TYPE
       SYNTAX      DvbInaIpTosMapEntry
       MAX-ACCESS  not-accessible
       STATUS      current
       DESCRIPTION
           "Table used to describe Type of Service (TOS) bits
            processing.

            If the action in a filter row in dvbInaIpFilterTable is
            tosmap and dvbInaIpFilterTosMapIndex points on a row in this
            table, then the Type of Service bits in the IP header of the
            matched packet is manipulated as follows:
            Set the tosBits of the packet to
            (tosBits & dvbInaIpTosMapAndMask) | dvbInaIpTosMapOrMask

            This construct allows you to do a clear and set of all
            the TOS bits in a flexible manner."
       INDEX { dvbInaIpTosMapIndex }
       ::= { dvbInaIpTosMapTable 1 }

DvbInaIpTosMapEntry ::= SEQUENCE {
       dvbInaIpTosMapIndex     Integer32,
       dvbInaIpTosMapStatus    RowStatus,
       dvbInaIpTosMapAndMask   OCTET STRING (SIZE (1)),
       dvbInaIpTosMapOrMask    OCTET STRING (SIZE (1))
       }

dvbInaIpTosMapIndex OBJECT-TYPE
       SYNTAX      Integer32 (1..65535)
       MAX-ACCESS  not-accessible
       STATUS      current
       DESCRIPTION
           "The index for this row."
       ::= { dvbInaIpTosMapEntry 1 }

dvbInaIpTosMapStatus OBJECT-TYPE
       SYNTAX      RowStatus
       MAX-ACCESS  read-create
       STATUS      current
       DESCRIPTION

Pedersen         Informational - Expires August 2001               33
                       DVB Cable INA Device MIB               Feb 2001

           "The object used to create and delete entries in this
            table. A row created by specifying just this object
            results in a row which specifies no change to the TOS
            bits.   A row may be created using either the create-and-go
            or create-and-wait paradigms. There is no restriction on
            the ability to change values in this row while the row is
            active."
       ::= { dvbInaIpTosMapEntry 2 }

dvbInaIpTosMapAndMask OBJECT-TYPE
       SYNTAX      OCTET STRING (SIZE (1))
       MAX-ACCESS  read-create
       STATUS      current
       DESCRIPTION
           "This value is bitwise AND'd with the matched  packet's
           TOS bits."
       DEFVAL { 'ff'h }
       ::= { dvbInaIpTosMapEntry 3 }

dvbInaIpTosMapOrMask OBJECT-TYPE
       SYNTAX      OCTET STRING (SIZE (1))
       MAX-ACCESS  read-create
       STATUS      current
       DESCRIPTION
           "After bitwise AND'ing with the above bits, the packet's
            TOS bits are bitwise OR'd with these bits."
       DEFVAL { '00'h }
       ::= { dvbInaIpTosMapEntry 4 }

   -- End of TOS Map table


-- - - - - - - - - - - - - - - - - - - - - - - - - - - - - - - - - -
-- Optional Ethernet Filter Group
--
--  The Ethernet Filter Table describes a filter to apply to Ethernet
-- traffic as received on a specified interface. To create an entry in
-- this table, dvbInaEthFilterIfIndex must be specified. Filter
-- application is ordered by the filter index.
--
-- - - - - - - - - - - - - - - - - - - - - - - - - - - - - - - - - -

dvbInaEthFilterEnable OBJECT-TYPE
        SYNTAX INTEGER {
            enable (1),
            countHits (2),
            disabled (3)
        }
        MAX-ACCESS  read-write
        STATUS      current
        DESCRIPTION
            "This contols the Ethernet filter table. This object
             can be set to the following values:
             'enable(1)': Enables the Ethernet filter table.

Pedersen         Informational - Expires August 2001               34
                       DVB Cable INA Device MIB               Feb 2001


             'countHits(2)': This option is used to debug the
             filter table. It allows packets to be checked against
             the filter table and increments dvbInaEthFilterMaches
             for a matching filter. However, all packets are allowed
             through.

             'disabled(3)': Disables Ethernet filtering, all packets
             are allowed through."
        ::= { dvbInaEthFilter 1 }

dvbInaEthFilterTable OBJECT-TYPE
        SYNTAX      SEQUENCE OF DvbInaEthFilterEntry
        MAX-ACCESS  not-accessible
        STATUS      current
        DESCRIPTION
            "The Ethernet Filter Table describes a filter to apply
            to Ethernet traffic as received on a specified interface.
            To create an entry in this table,
            dvbInaEthFilterIndex must be specified. Filter
            application only relates to Ethernet Port Number"
        ::= { dvbInaEthFilter 2 }

dvbInaEthFilterEntry OBJECT-TYPE
        SYNTAX      DvbInaEthFilterEntry
        MAX-ACCESS  not-accessible
        STATUS      current
        DESCRIPTION
            "Describes a filter to apply to Ethernet traffic received
            on a specified interface. Traffic is filtered only on
            ethernet port addresses."

        INDEX { dvbInaEthFilterIndex }
        ::= { dvbInaEthFilterTable 1 }

DvbInaEthFilterEntry ::= SEQUENCE {
            dvbInaEthFilterIndex       Integer32,
            dvbInaEthFilterStatus      RowStatus,
            dvbInaEthFilterIfIndex     InterfaceIndexOrZero,
            dvbInaEthFilterEtherType   INTEGER,
            dvbInaEthFilterProtocol    Integer32,
            dvbInaEthFilterAction      INTEGER,
            dvbInaEthFilterMatches     Counter32
        }

dvbInaEthFilterIndex OBJECT-TYPE
        SYNTAX      Integer32 (1..2147483647)
        MAX-ACCESS  not-accessible
        STATUS      current
        DESCRIPTION
            "Index used to order the application of filters.
             The filter with the lowest index is always applied
             first."
        ::= { dvbInaEthFilterEntry 1 }

Pedersen         Informational - Expires August 2001               35
                       DVB Cable INA Device MIB               Feb 2001


dvbInaEthFilterStatus OBJECT-TYPE
        SYNTAX      RowStatus
        MAX-ACCESS  read-create
        STATUS      current
        DESCRIPTION
            "Controls and reflects the status of rows in this table.
             The filter is not applied until this object is set to
             (or changes to) active."
        ::= { dvbInaEthFilterEntry 2 }

dvbInaEthFilterIfIndex OBJECT-TYPE
        SYNTAX      InterfaceIndexOrZero
        MAX-ACCESS  read-create
        STATUS      current
        DESCRIPTION
            "The ifIndex of the interface to which this filter
            applies."
        ::= { dvbInaEthFilterEntry 3 }

dvbInaEthFilterEtherType OBJECT-TYPE
        SYNTAX      INTEGER {
                       ethernet2(1),
                       snap(2),
                       llc(3)
                    }
        MAX-ACCESS  read-create
        STATUS      current
        DESCRIPTION
            "The format of the Ethernet of the ethernet frame
             to which this filter is applicable"
        ::= { dvbInaEthFilterEntry 4 }

dvbInaEthFilterProtocol OBJECT-TYPE
        SYNTAX      Integer32 ( 0..65535 )
        MAX-ACCESS  read-create
        STATUS      current
        DESCRIPTION
            "The protocol to filter on."
        ::= { dvbInaEthFilterEntry 5 }

dvbInaEthFilterAction OBJECT-TYPE
        SYNTAX INTEGER {
            accept (1),
            discard (2)
        }
        MAX-ACCESS  read-create
        STATUS      current
        DESCRIPTION
            "The action to be taken when there is a filter match.
            This object shall have one the following values:
            'accept(1)' or 'discard(2)'."
        ::= { dvbInaEthFilterEntry 6 }


Pedersen         Informational - Expires August 2001               36
                       DVB Cable INA Device MIB               Feb 2001

dvbInaEthFilterMatches OBJECT-TYPE
        SYNTAX      Counter32
        MAX-ACCESS  read-only
        STATUS      current
        DESCRIPTION
            "Counts the number of times this filter was matched."
        ::= { dvbInaEthFilterEntry 7 }


-- - - - - - - - - - - - - - - - - - - - - - - - - - - - - - - - - - -
-- NIU Error Table
--
-- The NIU Error Table contains the errors reported by the NIU in
-- question.
--
-- - - - - - - - - - - - - - - - - - - - - - - - - - - - - - - - - - -

dvbInaNiuErrorReset             OBJECT-TYPE
        SYNTAX      TruthValue
        MAX-ACCESS  read-write
        STATUS      current
        DESCRIPTION
            "If true the NIU error table is cleared.
             If read it always returns false."
        ::= { dvbInaNiuError 1 }

dvbInaNiuErrorMaxTableSize      OBJECT-TYPE
        SYNTAX      Integer32 ( 1..65535 )
        MAX-ACCESS  read-write
        STATUS      current
        DESCRIPTION
            "The maximum size of the NIU error table."
        ::= { dvbInaNiuError 2 }

dvbInaNiuErrorStatReqInterval   OBJECT-TYPE
        SYNTAX      Integer32 ( 1..65535 )
        UNITS       "minutes"
        MAX-ACCESS  read-write
        STATUS      current
        DESCRIPTION
            "The Status Request Message interval."
        ::= { dvbInaNiuError 3 }

dvbInaNiuErrorTable OBJECT-TYPE
        SYNTAX      SEQUENCE OF DvbInaNiuErrorEntry
        MAX-ACCESS  not-accessible
        STATUS      current
        DESCRIPTION
            "This table contains the errors reported by all NIUs"
        ::= { dvbInaNiuError 4 }

dvbInaNiuErrorEntry OBJECT-TYPE
        SYNTAX      DvbInaNiuErrorEntry
        MAX-ACCESS  not-accessible

Pedersen         Informational - Expires August 2001               37
                       DVB Cable INA Device MIB               Feb 2001

        STATUS      current
        DESCRIPTION
            "The entry contains information about the errors
             reported by all NIUs.
             The table is indexed by an arbitrary integer.
             The table is updated according to the NIU
             status response messages."
        INDEX { dvbInaNiuErrorIndex }
        ::= { dvbInaNiuErrorTable 1 }

DvbInaNiuErrorEntry ::= SEQUENCE {
            dvbInaNiuErrorIndex        Unsigned32,
            dvbInaNiuErrorMacAddress   MacAddress,
            dvbInaNiuErrorParamCode    INTEGER,
            dvbInaNiuErrorParamValue   Unsigned32
        }

dvbInaNiuErrorIndex         OBJECT-TYPE
        SYNTAX      Unsigned32 ( 1..65535 )
        MAX-ACCESS  not-accessible
        STATUS      current
        DESCRIPTION
            "Specifies the index for this error."
        ::= { dvbInaNiuErrorEntry 1 }

dvbInaNiuErrorMacAddress OBJECT-TYPE
        SYNTAX      MacAddress
        MAX-ACCESS  read-only
        STATUS      current
        DESCRIPTION
            "Specifies the MAC address of the NIU by which this error
            is reported."
        ::= { dvbInaNiuErrorEntry 2 }

dvbInaNiuErrorParamCode OBJECT-TYPE
        SYNTAX      INTEGER (0..255)
        MAX-ACCESS  read-only
        STATUS      current
        DESCRIPTION
            "Specifies the type of error reported by the NIU."
        ::= { dvbInaNiuErrorEntry 3 }

dvbInaNiuErrorParamValue OBJECT-TYPE
        SYNTAX      Unsigned32 (0..65535)
        MAX-ACCESS  read-only
        STATUS      current
        DESCRIPTION
            "Specifies the value of this error."
        ::= { dvbInaNiuErrorEntry 4 }


-- - - - - - - - - - - - - - - - - - - - - - - - - - - - - - - - - - -
-- NIU IP Table
--

Pedersen         Informational - Expires August 2001               38
                       DVB Cable INA Device MIB               Feb 2001

-- The NIU IP Table contains information on the IP addresses and
-- subnets of the NIU.
-- - - - - - - - - - - - - - - - - - - - - - - - - - - - - - - - - - -

 dvbInaNiuIpTable OBJECT-TYPE
        SYNTAX      SEQUENCE OF DvbInaNiuIpEntry
        MAX-ACCESS  not-accessible
        STATUS      current
        DESCRIPTION
            "Describes the attributes of Network Interface Units."
        ::= { dvbInaNiuIp 1 }

dvbInaNiuIpEntry OBJECT-TYPE
        SYNTAX      DvbInaNiuIpEntry
        MAX-ACCESS  not-accessible
        STATUS      current
        DESCRIPTION
            "Initially the table shall be empty. A new entry for a NIU
             is automatically created when the NIU in question signs on.
             Furthermore, the manager through the
             dvbInaNiuIpRowAccessStatus object can create new entries.
             This can be used in the case of re-provisioning where by
             the manager first makes an entry and sets all relevant
             parameters before the NIU is re-provisioned to this INA.

            When a NIU entry is deleted, also all associated connection
            entries are deleted."

        INDEX { dvbInaNiuIpMacAddress }
        ::= { dvbInaNiuIpTable 1 }

DvbInaNiuIpEntry ::= SEQUENCE {
            dvbInaNiuIpMacAddress             MacAddress,
            dvbInaNiuIpRowAccessStatus        RowStatus,
            dvbInaNiuIpHfcIpAddrType          InetAddressType,
            dvbInaNiuIpHfcIpAddr              InetAddress,
            dvbInaNiuIpHfcIpMaskType          InetAddressType,
            dvbInaNiuIpHfcIpMask              InetAddress,
            dvbInaNiuIpNetIpAddrType          InetAddressType,
            dvbInaNiuIpNetIpAddr              InetAddress,
            dvbInaNiuIpNetIpMaskType          InetAddressType,
            dvbInaNiuIpNetIpMask              InetAddress,
            dvbInaNiuIpAddressConfigType      INTEGER,
            dvbInaNiuIpDhcpPrimarySrvType     InetAddressType,
            dvbInaNiuIpDhcpPrimarySrv         InetAddress,
            dvbInaNiuIpDhcpSecondarySrvType   InetAddressType,
            dvbInaNiuIpDhcpSecondarySrv       InetAddress
        }

dvbInaNiuIpMacAddress OBJECT-TYPE
        SYNTAX      MacAddress
        MAX-ACCESS  not-accessible
        STATUS      current
        DESCRIPTION

Pedersen         Informational - Expires August 2001               39
                       DVB Cable INA Device MIB               Feb 2001

            " A 48-bit value representing the unique MAC address of
            the NIU. "
        ::= { dvbInaNiuIpEntry 1 }

dvbInaNiuIpRowAccessStatus OBJECT-TYPE
        SYNTAX      RowStatus
        MAX-ACCESS  read-create
        STATUS      current
        DESCRIPTION
            " Controls and reflects the status of this row in this
            table. "
        ::= { dvbInaNiuIpEntry 2 }

dvbInaNiuIpHfcIpAddrType              OBJECT-TYPE
        SYNTAX      InetAddressType
        MAX-ACCESS  read-create
        STATUS      current
        DESCRIPTION
            " The type of address used for the HFC side."
        ::= { dvbInaNiuIpEntry 3 }

dvbInaNiuIpHfcIpAddr                  OBJECT-TYPE
        SYNTAX      InetAddress
        MAX-ACCESS  read-create
        STATUS      current
        DESCRIPTION
            " Specifies the IP Address on the HFC side."
        ::= { dvbInaNiuIpEntry 4 }

dvbInaNiuIpHfcIpMaskType              OBJECT-TYPE
        SYNTAX      InetAddressType
        MAX-ACCESS  read-create
        STATUS      current
        DESCRIPTION
            " The type of address used for the HFC side."
        ::= { dvbInaNiuIpEntry 5 }

dvbInaNiuIpHfcIpMask                  OBJECT-TYPE
        SYNTAX      InetAddress
        MAX-ACCESS  read-create
        STATUS      current
        DESCRIPTION
            " Specifies the IP Mask on the HFC side."
        ::= { dvbInaNiuIpEntry 6 }

dvbInaNiuIpNetIpAddrType              OBJECT-TYPE
        SYNTAX      InetAddressType
        MAX-ACCESS  read-create
        STATUS      current
        DESCRIPTION
            " The type of address used for the network side."
        ::= { dvbInaNiuIpEntry 7 }

dvbInaNiuIpNetIpAddr                  OBJECT-TYPE

Pedersen         Informational - Expires August 2001               40
                       DVB Cable INA Device MIB               Feb 2001

        SYNTAX      InetAddress
        MAX-ACCESS  read-create
        STATUS      current
        DESCRIPTION
            " Specifies the IP Address on the network (client) side."
        ::= { dvbInaNiuIpEntry 8 }

dvbInaNiuIpNetIpMaskType              OBJECT-TYPE
        SYNTAX      InetAddressType
        MAX-ACCESS  read-create
        STATUS      current
        DESCRIPTION
            " The type of address used for the network side."
        ::= { dvbInaNiuIpEntry 9 }

dvbInaNiuIpNetIpMask OBJECT-TYPE
        SYNTAX      InetAddress
        MAX-ACCESS  read-create
        STATUS      current
        DESCRIPTION
            " Specifies the IP Address on the network (client) side."
        ::= { dvbInaNiuIpEntry 10 }

dvbInaNiuIpAddressConfigType OBJECT-TYPE
        SYNTAX            INTEGER {
            static(1),
            dhcp(2)
        }
        MAX-ACCESS  read-create
        STATUS      current
        DESCRIPTION
            "Specifies if the NIU HFC address was received through
             static configuration or through DHCP"
        ::= { dvbInaNiuIpEntry 11 }

dvbInaNiuIpDhcpPrimarySrvType OBJECT-TYPE
        SYNTAX      InetAddressType
        MAX-ACCESS  read-create
        STATUS      current
        DESCRIPTION
            " Specifies the address type of the DHCP primary server."
        ::= { dvbInaNiuIpEntry 12 }

dvbInaNiuIpDhcpPrimarySrv OBJECT-TYPE
        SYNTAX      InetAddress
        MAX-ACCESS  read-create
        STATUS      current
        DESCRIPTION
            " Specifies the DHCP primary server."
        ::= { dvbInaNiuIpEntry 13 }


dvbInaNiuIpDhcpSecondarySrvType OBJECT-TYPE
        SYNTAX      InetAddressType

Pedersen         Informational - Expires August 2001               41
                       DVB Cable INA Device MIB               Feb 2001

        MAX-ACCESS  read-create
        STATUS      current
        DESCRIPTION
            " Specifies the address type of the DHCP secondary server."
        ::= { dvbInaNiuIpEntry 14 }

dvbInaNiuIpDhcpSecondarySrv OBJECT-TYPE
        SYNTAX      InetAddress
        MAX-ACCESS  read-create
        STATUS      current
        DESCRIPTION
            " Specifies the DHCP secondary server."
        ::= { dvbInaNiuIpEntry 15 }


-- - - - - - - - - - - - - - - - - - - - - - - - - - - - - - - - - - -
-- Conformance statements
-- - - - - - - - - - - - - - - - - - - - - - - - - - - - - - - - - - -

dvbInaCompliance MODULE-COMPLIANCE
        STATUS      current
        DESCRIPTION
            "The compliance statement for EuroModem INAs
             which implement the DVB-CABLE-INA-MIB MIB.  An
             implementation only has to support IPv4 addresses to be
             compliant."


MODULE  -- dvbIna
        GROUP dvbInaDeviceGroup
            DESCRIPTION
                "The Device group is optional to implement."

        GROUP dvbInaNmAccessGroup
            DESCRIPTION
                "The NM Access group is optional to implement."

        GROUP dvbInaSwGroup
            DESCRIPTION
                "Th SW group is optional to implement."

        GROUP dvbInaDhcpGroup
            DESCRIPTION
                "The DHCP group is optional to implement."

        GROUP dvbInaEventGroup
            DESCRIPTION
                "The Event group is optional to implement."

        GROUP dvbInaIpFilterGroup
            DESCRIPTION
                "The IP filter group is optional to implement."

        GROUP dvbInaEthFilterGroup

Pedersen         Informational - Expires August 2001               42
                       DVB Cable INA Device MIB               Feb 2001

            DESCRIPTION
                "The Ethernet filter group is optional to implement."

        GROUP dvbInaNiuErrorGroup
            DESCRIPTION
                "The NIU Error group is optional to implement."

        GROUP dvbInaNiuIpGroup
            DESCRIPTION
                "The NIU IP group is optional to implement."

        OBJECT dvbInaDeviceFixedIpAddress
            MIN-ACCESS  read-only
            DESCRIPTION
                "It is compliant to implement this object as read-only."

        OBJECT dvbInaNiuIpHfcIpAddrType
            MIN-ACCESS  read-only
            DESCRIPTION
                "It is compliant to implement this object as read-only."

        OBJECT dvbInaNiuIpHfcIpAddr
            MIN-ACCESS  read-only
            DESCRIPTION
                "It is compliant to implement this object as read-only."

        OBJECT dvbInaNiuIpHfcIpMaskType
            MIN-ACCESS  read-only
            DESCRIPTION
                "It is compliant to implement this object as read-only."

        OBJECT dvbInaNiuIpHfcIpMask
            MIN-ACCESS  read-only
            DESCRIPTION
                "It is compliant to implement this object as read-only."

        OBJECT dvbInaNiuIpNetIpAddrType
            MIN-ACCESS  read-only
            DESCRIPTION
                "It is compliant to implement this object as read-only."

        OBJECT dvbInaNiuIpNetIpAddr
            MIN-ACCESS  read-only
            DESCRIPTION
                "It is compliant to implement this object as read-only."

        OBJECT dvbInaNiuIpNetIpMaskType
            MIN-ACCESS  read-only
            DESCRIPTION
                "It is compliant to implement this object as read-only."

        OBJECT dvbInaNiuIpNetIpMask
            MIN-ACCESS  read-only
            DESCRIPTION

Pedersen         Informational - Expires August 2001               43
                       DVB Cable INA Device MIB               Feb 2001

                "It is compliant to implement this object as read-only."

        OBJECT dvbInaNiuIpAddressConfigType
            MIN-ACCESS  read-only
            DESCRIPTION
                "It is compliant to implement this object as read-only."

        OBJECT dvbInaNiuIpDhcpPrimarySrvType
            MIN-ACCESS  read-only
            DESCRIPTION
                "It is compliant to implement this object as read-only."

        OBJECT dvbInaNiuIpDhcpPrimarySrv
            MIN-ACCESS  read-only
            DESCRIPTION
                "It is compliant to implement this object as read-only."

        OBJECT dvbInaNiuIpDhcpSecondarySrvType
            MIN-ACCESS  read-only
            DESCRIPTION
                "It is compliant to implement this object as read-only."

        OBJECT dvbInaNiuIpDhcpSecondarySrv
            MIN-ACCESS  read-only
            DESCRIPTION
                "It is compliant to implement this object as read-only."

        OBJECT dvbInaNiuIpErrorMaxTableSize
            MIN-ACCESS  read-only
            DESCRIPTION
                "It is compliant to implement this object as read-only."

        OBJECT dvbInaNiuIpErrorStatReqInterval
            MIN-ACCESS  read-only
            DESCRIPTION
                "It is compliant to implement this object as read-only."

        ::= { dvbInaCompliances 1 }

dvbInaDeviceGroup OBJECT-GROUP
        OBJECTS   {
                    dvbInaDeviceDateTime,
                    dvbInaDeviceResetNow,
                    dvbInaDeviceSerialNumber,
                    dvbInaDeviceUptime,
                    dvbInaDeviceCurrentState,
                    dvbInaDeviceDesiredState,
                    dvbInaDeviceMibVersion,
                    dvbInaDeviceDhcpRelaySupport
                  }
        STATUS      current
        DESCRIPTION
            "A collection of objects for managing the state of the
            INA."

Pedersen         Informational - Expires August 2001               44
                       DVB Cable INA Device MIB               Feb 2001

        ::= { dvbInaGroups 1 }

dvbInaNmAccessGroup OBJECT-GROUP
        OBJECTS   {
                    dvbInaNmAccessIndex,
                    dvbInaNmAccessIpType,
                    dvbInaNmAccessIp,
                    dvbInaNmAccessIpMaskType,
                    dvbInaNmAccessIpMask,
                    dvbInaNmAccessCommunity,
                    dvbInaNmAccessControl,
                    dvbInaNmAccessInterfaces,
                    dvbInaNmAccessStatus,
                    dvbInaNmAccessLevelEnable
                  }
        STATUS      current
        DESCRIPTION
            "A collection of objects for managing the state of the
            INA."
        ::= { dvbInaGroups 2 }

dvbInaSwGroup OBJECT-GROUP
        OBJECTS   {
                    dvbInaSwTftpServerAddrType,
                    dvbInaSwTftpServer,
                    dvbInaSwTftpFilename,
                    dvbInaSwFilename,
                    dvbInaSwAdminStatus,
                    dvbInaSwOperStatus,
                    dvbInaSwDownLoadSlot,
                    dvbInaSwIndex,
                    dvbInaSwSlot,
                    dvbInaSwVersion,
                    dvbInaSwState,
                    dvbInaSwAction,
                    dvbInaSwDateTime
                  }
        STATUS      current
        DESCRIPTION
            "A collection of objects for managing the state of the
            INA."
        ::= { dvbInaGroups 3 }

dvbInaDhcpGroup OBJECT-GROUP
        OBJECTS   {
                    dvbInaDhcpServerIfIndex,
                    dvbInaDhcpServerIpType,
                    dvbInaDhcpServerIp,
                    dvbInaDhcpServerRowAccessStatus,
                    dvbInaDhcpServerRelayEnable,
                    dvbInaDhcpServerAssociation,
                    dvbInaDhcpServerPrimaryOrSecondary
                  }
        STATUS      current

Pedersen         Informational - Expires August 2001               45
                       DVB Cable INA Device MIB               Feb 2001

        DESCRIPTION
            "A collection of objects providing control over the INAs
             DHCP/BOOTP functionality."
        ::= { dvbInaGroups 4 }

dvbInaEventGroup OBJECT-GROUP
        OBJECTS   {
                    dvbInaEvControl,
                    dvbInaEvSyslogIpType,
                    dvbInaEvSyslogIp,
                    dvbInaEvThrottleAdminStatus,
                    dvbInaEvThrottleInhibited,
                    dvbInaEvThrottleThreshold,
                    dvbInaEvThrottleInterval,
                    dvbInaEvPriority,
                    dvbInaEvReporting,
                    dvbInaEvMaxNumberOfEntries,
                    dvbInaEvIndex,
                    dvbInaEvFirstTime,
                    dvbInaEvLastTime,
                    dvbInaEvCount,
                    dvbInaEvLevel,
                    dvbInaEvId,
                    dvbInaEvText
                  }
        STATUS      current
        DESCRIPTION
            "A collection of objects used to control and monitor events
             generated at and by the INA."
        ::= { dvbInaGroups 5 }

dvbInaIpFilterGroup OBJECT-GROUP
        OBJECTS   {
                    dvbInaIpFilterEnable,
                    dvbInaIpFilterIndex,
                    dvbInaIpFilterStatus,
                    dvbInaIpFilterAssignedBy,
                    dvbInaIpFilterIfIndex,
                    dvbInaIpFilterDirection,
                    dvbInaIpFilterTos,
                    dvbInaIpFilterTosMask,
                    dvbInaIpFilterSrcAddrType,
                    dvbInaIpFilterSrcAddr,
                    dvbInaIpFilterSrcMaskType,
                    dvbInaIpFilterSrcMask,
                    dvbInaIpFilterDstAddrType,
                    dvbInaIpFilterDstAddr,
                    dvbInaIpFilterDstMaskType,
                    dvbInaIpFilterDstMask,
                    dvbInaIpFilterProtocol,
                    dvbInaIpFilterSourcePortLow,
                    dvbInaIpFilterSourcePortHigh,
                    dvbInaIpFilterDestPortLow,
                    dvbInaIpFilterDestPortHigh,

Pedersen         Informational - Expires August 2001               46
                       DVB Cable INA Device MIB               Feb 2001

                    dvbInaIpFilterAction,
                    dvbInaIpFilterMatches,
                    dvbInaIpFilterContinue,
                    dvbInaIpFilterTosMapIndex,
                    dvbInaIpTosMapIndex,
                    dvbInaIpTosMapStatus,
                    dvbInaIpTosMapAndMask,
                    dvbInaIpTosMapOrMask
                  }
        STATUS      current
        DESCRIPTION
            "A collection of objects providing a filtering capability
             at the IP layer."
        ::= { dvbInaGroups 6 }

dvbInaEthFilterGroup OBJECT-GROUP
        OBJECTS   {
                    dvbInaEthFilterEnable,
                    dvbInaEthFilterIndex,
                    dvbInaEthFilterStatus,
                    dvbInaEthFilterIfIndex,
                    dvbInaEthFilterEtherType,
                    dvbInaEthFilterProtocol,
                    dvbInaEthFilterAction,
                    dvbInaEthFilterMatches
                  }
        STATUS      current
        DESCRIPTION
            "A collection of objects providing a filtering capability
             at the Ethernet layer."
        ::= { dvbInaGroups 7 }

dvbInaNiuErrorGroup OBJECT-GROUP
        OBJECTS   {
                    dvbInaNiuErrorReset,
                    dvbInaNiuErrorMaxTableSize,
                    dvbInaNiuErrorStatReqInterval,
                    dvbInaNiuErrorIndex,
                    dvbInaNiuErrorMacAddress,
                    dvbInaNiuErrorParamCode,
                    dvbInaNiuErrorParamValue
                  }
        STATUS      current
        DESCRIPTION
            "A collection of objects representing errors associated
             with all NIUs attached to the INA."
        ::= { dvbInaGroups 9 }

dvbInaNiuIpGroup    OBJECT-GROUP
        OBJECTS   {
                    dvbInaNiuIpMacAddress,
                    dvbInaNiuIpRowAccessStatus,
                    dvbInaNiuIpHfcIpAddrType,
                    dvbInaNiuIpHfcIpAddr,

Pedersen         Informational - Expires August 2001               47
                       DVB Cable INA Device MIB               Feb 2001

                    dvbInaNiuIpHfcIpMaskType,
                    dvbInaNiuIpHfcIpMask,
                    dvbInaNiuIpNetIpAddrType,
                    dvbInaNiuIpNetIpAddr,
                    dvbInaNiuIpNetIpMaskType,
                    dvbInaNiuIpNetIpMask,
                    dvbInaNiuIpAddressConfigType,
                    dvbInaNiuIpDhcpPrimarySrvType,
                    dvbInaNiuIpDhcpPrimarySrv,
                    dvbInaNiuIpDhcpSecondarySrvType,
                    dvbInaNiuIpDhcpSecondarySrv
                  }
        STATUS      current
        DESCRIPTION
            "A collection of objects describing the IP address
             off all NIUs attached to the INA."
        ::= { dvbInaGroups 10 }

END

-- 
--    "Copyright (C) The Internet Society (December 2000). All Rights
--    Reserved. This document and translations of it may be copied and
--    furnished to others, and derivative works that comment on or
--    otherwise explain it or assist in its implementation may be prepared,
--    copied, published and distributed, in whole or in part, without
--    restriction of any kind, provided that the above copyright notice and
--    this paragraph are included on all such copies and derivative works.
--    However, this document itself may not be modified in any way, such as
--    by removing the copyright notice or references to the Internet
--    Society or other Internet organizations, except as needed for the
--    purpose of developing Internet standards in which case the procedures
--    for copyrights defined in the Internet Standards process must be
--    followed, or as required to translate it into.
-- 
-- 
-- 
-- 
-- 
-- 
-- 
-- 
-- 
-- 
-- 
-- 
-- 
-- Pedersen         Informational - Expires August 2001               50
