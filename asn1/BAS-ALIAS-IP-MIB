BAS-ALIAS-IP-MIB DEFINITIONS ::= BEGIN

IMPORTS
	MODULE-IDENTITY, OBJECT-TYPE, 
	Integer32, Counter32			FROM SNMPv2-SMI

	basAliasIp, BasChassisId,
	BasSlotId, BasInterfaceId,
	BasLogicalPortId				FROM BAS-MIB;

basAliasIpMib MODULE-IDENTITY
	LAST-UPDATED "9810081200Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the Alias IP MIB objects
		 for a Broadband Access System Cluster."
	::= { basAliasIp 1 }

basIpAlias			OBJECT IDENTIFIER ::= { basAliasIpMib 1 }
basIcmp			OBJECT IDENTIFIER ::= { basAliasIpMib 2 }

-- the IP group

basIpTable OBJECT-TYPE
	SYNTAX		SEQUENCE OF BasIpEntry
	MAX-ACCESS	not-accessible
	STATUS		current
	DESCRIPTION
		"Per Chassis Stack IP objects."
	::= { basIpAlias 1 }

basIpEntry OBJECT-TYPE
	SYNTAX		BasIpEntry
	MAX-ACCESS	not-accessible
	STATUS		current
	DESCRIPTION
		"IP objects for a Chassis Stack."
	INDEX		{ 
					basIpChassis,
					basIpSlot,
					basIpIf,
					basIpLPort
				}
	::= { basIpTable 1 }

BasIpEntry ::= SEQUENCE {
		basIpForwarding			INTEGER,
		basIpDefaultTTL			INTEGER,
		basIpInReceives			Counter32,
		basIpInHdrErrors		Counter32,
		basIpInAddrErrors		Counter32,
		basIpForwDatagrams		Counter32,
		basIpInUnknownProtos	Counter32,
		basIpInDiscards			Counter32,
		basIpInDelivers			Counter32,
		basIpOutRequests		Counter32,
		basIpOutDiscards		Counter32,
		basIpOutNoRoutes		Counter32,
		basIpReasmTimeout		Integer32,
		basIpReasmReqds			Counter32,
		basIpReasmOKs			Counter32,
		basIpReasmFails			Counter32,
		basIpFragOKs			Counter32,
		basIpFragFails			Counter32,
		basIpFragCreates		Counter32,
		basIpChassis			BasChassisId,
		basIpSlot				BasSlotId,
		basIpIf					BasInterfaceId,
		basIpLPort				BasLogicalPortId
	}

basIpForwarding OBJECT-TYPE
    SYNTAX      INTEGER {
                    forwarding(1),    -- acting as a router
                    notForwarding(2)  -- NOT acting as a router
                }
    MAX-ACCESS  read-write
    STATUS      current
    DESCRIPTION
            "The indication of whether this entity is acting as an IP
            router in respect to the forwarding of datagrams received
            by, but not addressed to, this entity.  IP routers forward
            datagrams.  IP hosts do not (except those source-routed via
            the host)."
    ::= { basIpEntry 1 }

basIpDefaultTTL OBJECT-TYPE
    SYNTAX      INTEGER (1..255)
    MAX-ACCESS  read-write
    STATUS      current
    DESCRIPTION
            "The default value inserted into the Time-To-Live field of
            the IP header of datagrams originated at this entity,
            whenever a TTL value is not supplied by the transport layer
            protocol."
    ::= { basIpEntry 2 }

basIpInReceives OBJECT-TYPE
    SYNTAX      Counter32
    MAX-ACCESS  read-only
    STATUS      current
    DESCRIPTION
            "The total number of input datagrams received from
            interfaces, including those received in error."
    ::= { basIpEntry 3 }


basIpInHdrErrors OBJECT-TYPE
    SYNTAX      Counter32
    MAX-ACCESS  read-only
    STATUS      current
    DESCRIPTION
            "The number of input datagrams discarded due to errors in
            their IP headers, including bad checksums, version number
            mismatch, other format errors, time-to-live exceeded, errors
            discovered in processing their IP options, etc."
    ::= { basIpEntry 4 }

basIpInAddrErrors OBJECT-TYPE
    SYNTAX      Counter32
    MAX-ACCESS  read-only
    STATUS      current
    DESCRIPTION
            "The number of input datagrams discarded because the IP
            address in their IP header's destination field was not a
            valid address to be received at this entity.  This count
            includes invalid addresses (e.g., 0.0.0.0) and addresses of
            unsupported Classes (e.g., Class E).  For entities which are
            not IP routers and therefore do not forward datagrams, this
            counter includes datagrams discarded because the destination
            address was not a local address."
    ::= { basIpEntry 5 }

basIpForwDatagrams OBJECT-TYPE
    SYNTAX      Counter32
    MAX-ACCESS  read-only
    STATUS      current
    DESCRIPTION
            "The number of input datagrams for which this entity was not
            their final IP destination, as a result of which an attempt
            was made to find a route to forward them to that final
            destination.  In entities which do not act as IP routers,
            this counter will include only those packets which were
            Source-Routed via this entity, and the Source-Route option
            processing was successful."
    ::= { basIpEntry 6 }

basIpInUnknownProtos OBJECT-TYPE
    SYNTAX      Counter32
    MAX-ACCESS  read-only
    STATUS      current
    DESCRIPTION
            "The number of locally-addressed datagrams received
            successfully but discarded because of an unknown or
            unsupported protocol."


    ::= { basIpEntry 7 }

basIpInDiscards OBJECT-TYPE
    SYNTAX      Counter32
    MAX-ACCESS  read-only
    STATUS      current
    DESCRIPTION
            "The number of input IP datagrams for which no problems were
            encountered to prevent their continued processing, but which
            were discarded (e.g., for lack of buffer space).  Note that
            this counter does not include any datagrams discarded while
            awaiting re-assembly."
    ::= { basIpEntry 8 }

basIpInDelivers OBJECT-TYPE
    SYNTAX      Counter32
    MAX-ACCESS  read-only
    STATUS      current
    DESCRIPTION
            "The total number of input datagrams successfully delivered
            to IP user-protocols (including ICMP)."
    ::= { basIpEntry 9 }

basIpOutRequests OBJECT-TYPE
    SYNTAX      Counter32
    MAX-ACCESS  read-only
    STATUS      current
    DESCRIPTION
            "The total number of IP datagrams which local IP user-
            protocols (including ICMP) supplied to IP in requests for
            transmission.  Note that this counter does not include any
            datagrams counted in ipForwDatagrams."
    ::= { basIpEntry 10 }

basIpOutDiscards OBJECT-TYPE
    SYNTAX      Counter32
    MAX-ACCESS  read-only
    STATUS      current
    DESCRIPTION
            "The number of output IP datagrams for which no problem was
            encountered to prevent their transmission to their
            destination, but which were discarded (e.g., for lack of
            buffer space).  Note that this counter would include
            datagrams counted in ipForwDatagrams if any such packets met
            this (discretionary) discard criterion."
    ::= { basIpEntry 11 }

basIpOutNoRoutes OBJECT-TYPE
    SYNTAX      Counter32
    MAX-ACCESS  read-only
    STATUS      current
    DESCRIPTION
            "The number of IP datagrams discarded because no route could
            be found to transmit them to their destination.  Note that
            this counter includes any packets counted in ipForwDatagrams
            which meet this `no-route' criterion.  Note that this
            includes any datagrams which a host cannot route because all
            of its default routers are down."
    ::= { basIpEntry 12 }

basIpReasmTimeout OBJECT-TYPE
    SYNTAX      Integer32
    MAX-ACCESS  read-only
    STATUS      current
    DESCRIPTION
            "The maximum number of seconds which received fragments are
            held while they are awaiting reassembly at this entity."
    ::= { basIpEntry 13 }

basIpReasmReqds OBJECT-TYPE
    SYNTAX      Counter32
    MAX-ACCESS  read-only
    STATUS      current
    DESCRIPTION
            "The number of IP fragments received which needed to be
            reassembled at this entity."
    ::= { basIpEntry 14 }

basIpReasmOKs OBJECT-TYPE
    SYNTAX      Counter32
    MAX-ACCESS  read-only
    STATUS      current
    DESCRIPTION
            "The number of IP datagrams successfully re-assembled."
    ::= { basIpEntry 15 }

basIpReasmFails OBJECT-TYPE
    SYNTAX      Counter32
    MAX-ACCESS  read-only
    STATUS      current
    DESCRIPTION
            "The number of failures detected by the IP re-assembly
            algorithm (for whatever reason: timed out, errors, etc).
            Note that this is not necessarily a count of discarded IP
            fragments since some algorithms (notably the algorithm in
            RFC 815) can lose track of the number of fragments by


            combining them as they are received."
    ::= { basIpEntry 16 }

basIpFragOKs OBJECT-TYPE
    SYNTAX      Counter32
    MAX-ACCESS  read-only
    STATUS      current
    DESCRIPTION
            "The number of IP datagrams that have been successfully
            fragmented at this entity."
    ::= { basIpEntry 17 }

basIpFragFails OBJECT-TYPE
    SYNTAX      Counter32
    MAX-ACCESS  read-only
    STATUS      current
    DESCRIPTION
            "The number of IP datagrams that have been discarded because
            they needed to be fragmented at this entity but could not
            be, e.g., because their Don't Fragment flag was set."
    ::= { basIpEntry 18 }

basIpFragCreates OBJECT-TYPE
    SYNTAX      Counter32
    MAX-ACCESS  read-only
    STATUS      current
    DESCRIPTION
            "The number of IP datagram fragments that have been
            generated as a result of fragmentation at this entity."
    ::= { basIpEntry 19 }

basIpChassis OBJECT-TYPE
	SYNTAX		BasChassisId
	MAX-ACCESS	not-accessible
	STATUS		current
	DESCRIPTION
		"The BAS Chassis ID of this card."
	::= { basIpEntry 20 }

basIpSlot OBJECT-TYPE
	SYNTAX		BasSlotId
	MAX-ACCESS	not-accessible
	STATUS		current
	DESCRIPTION
		"The BAS Slot ID of this card."
	::= { basIpEntry 21 }

basIpIf OBJECT-TYPE
	SYNTAX		BasInterfaceId
	MAX-ACCESS	not-accessible
	STATUS		current
	DESCRIPTION
		"The BAS interface ID of this card."
	::= { basIpEntry 22 }

basIpLPort OBJECT-TYPE
	SYNTAX		BasLogicalPortId
	MAX-ACCESS	not-accessible
	STATUS		current
	DESCRIPTION
		"The BAS logical port ID of this card."
	::= { basIpEntry 23 }

-- the ICMP group

basIcmpTable OBJECT-TYPE
	SYNTAX		SEQUENCE OF BasIcmpEntry
	MAX-ACCESS	not-accessible
	STATUS		current
	DESCRIPTION
		"Per Chassis Stack ICMP objects."
	::= { basIcmp 1 }

basIcmpEntry OBJECT-TYPE
	SYNTAX		BasIcmpEntry
	MAX-ACCESS	not-accessible
	STATUS		current
	DESCRIPTION
		"ICMP objects for a Chassis Stack."
	INDEX		{ 
					basIcmpChassis,
					basIcmpSlot,
					basIcmpIf,
					basIcmpLPort
				}
	::= { basIcmpTable 1 }

BasIcmpEntry ::= SEQUENCE {
		basIcmpInMsgs			Counter32,
		basIcmpInErrors			Counter32,
		basIcmpInDestUnreachs	Counter32,
		basIcmpInTimeExcds		Counter32,
		basIcmpInParmProbs		Counter32,
		basIcmpInSrcQuenchs		Counter32,
		basIcmpInRedirects		Counter32,
		basIcmpInEchos			Counter32,
		basIcmpInEchoReps		Counter32,
		basIcmpInTimestamps		Counter32,
		basIcmpInTimestampReps	Counter32,
		basIcmpInAddrMasks		Counter32,
		basIcmpInAddrMaskReps	Counter32,
		basIcmpOutMsgs			Counter32,
		basIcmpOutErrors		Counter32,
		basIcmpOutDestUnreachs	Counter32,
		basIcmpOutTimeExcds		Counter32,
		basIcmpOutParmProbs		Counter32,
		basIcmpOutSrcQuenchs	Counter32,
		basIcmpOutRedirects		Counter32,
		basIcmpOutEchos			Counter32,
		basIcmpOutEchoReps		Counter32,
		basIcmpOutTimestamps	Counter32,
		basIcmpOutTimestampReps	Counter32,
		basIcmpOutAddrMasks		Counter32,
		basIcmpOutAddrMaskReps	Counter32,
		basIcmpChassis			BasChassisId,
		basIcmpSlot				BasSlotId,
		basIcmpIf				BasInterfaceId,
		basIcmpLPort			BasLogicalPortId
	}

basIcmpInMsgs OBJECT-TYPE
    SYNTAX      Counter32
    MAX-ACCESS  read-only
    STATUS      current
    DESCRIPTION
            "The total number of ICMP messages which the entity
            received.  Note that this counter includes all those counted
            by icmpInErrors."
    ::= { basIcmpEntry 1 }

basIcmpInErrors OBJECT-TYPE
    SYNTAX      Counter32
    MAX-ACCESS  read-only
    STATUS      current
    DESCRIPTION
            "The number of ICMP messages which the entity received but
            determined as having ICMP-specific errors (bad ICMP
            checksums, bad length, etc.)."
    ::= { basIcmpEntry 2 }

basIcmpInDestUnreachs OBJECT-TYPE
    SYNTAX      Counter32
    MAX-ACCESS  read-only
    STATUS      current
    DESCRIPTION
            "The number of ICMP Destination Unreachable messages
            received."
    ::= { basIcmpEntry 3 }

basIcmpInTimeExcds OBJECT-TYPE
    SYNTAX      Counter32
    MAX-ACCESS  read-only
    STATUS      current
    DESCRIPTION
            "The number of ICMP Time Exceeded messages received."
    ::= { basIcmpEntry 4 }

basIcmpInParmProbs OBJECT-TYPE
    SYNTAX      Counter32
    MAX-ACCESS  read-only
    STATUS      current
    DESCRIPTION
            "The number of ICMP Parameter Problem messages received."
    ::= { basIcmpEntry 5 }

basIcmpInSrcQuenchs OBJECT-TYPE
    SYNTAX      Counter32
    MAX-ACCESS  read-only
    STATUS      current
    DESCRIPTION
            "The number of ICMP Source Quench messages received."
    ::= { basIcmpEntry 6 }

basIcmpInRedirects OBJECT-TYPE
    SYNTAX      Counter32
    MAX-ACCESS  read-only
    STATUS      current
    DESCRIPTION
            "The number of ICMP Redirect messages received."
    ::= { basIcmpEntry 7 }

basIcmpInEchos OBJECT-TYPE
    SYNTAX      Counter32
    MAX-ACCESS  read-only
    STATUS      current
    DESCRIPTION
            "The number of ICMP Echo (request) messages received."
    ::= { basIcmpEntry 8 }

basIcmpInEchoReps OBJECT-TYPE
    SYNTAX      Counter32
    MAX-ACCESS  read-only
    STATUS      current
    DESCRIPTION
            "The number of ICMP Echo Reply messages received."
    ::= { basIcmpEntry 9 }

basIcmpInTimestamps OBJECT-TYPE
    SYNTAX      Counter32
    MAX-ACCESS  read-only
    STATUS      current
    DESCRIPTION
            "The number of ICMP Timestamp (request) messages received."
    ::= { basIcmpEntry 10 }

basIcmpInTimestampReps OBJECT-TYPE
    SYNTAX      Counter32
    MAX-ACCESS  read-only
    STATUS      current
    DESCRIPTION
            "The number of ICMP Timestamp Reply messages received."
    ::= { basIcmpEntry 11 }

basIcmpInAddrMasks OBJECT-TYPE
    SYNTAX      Counter32
    MAX-ACCESS  read-only
    STATUS      current
    DESCRIPTION
            "The number of ICMP Address Mask Request messages received."
    ::= { basIcmpEntry 12 }

basIcmpInAddrMaskReps OBJECT-TYPE
    SYNTAX      Counter32
    MAX-ACCESS  read-only
    STATUS      current
    DESCRIPTION
            "The number of ICMP Address Mask Reply messages received."
    ::= { basIcmpEntry 13 }

basIcmpOutMsgs OBJECT-TYPE
    SYNTAX      Counter32
    MAX-ACCESS  read-only
    STATUS      current
    DESCRIPTION
            "The total number of ICMP messages which this entity
            attempted to send.  Note that this counter includes all
            those counted by icmpOutErrors."
    ::= { basIcmpEntry 14 }

basIcmpOutErrors OBJECT-TYPE
    SYNTAX      Counter32
    MAX-ACCESS  read-only
    STATUS      current
    DESCRIPTION
            "The number of ICMP messages which this entity did not send
            due to problems discovered within ICMP such as a lack of
            buffers.  This value should not include errors discovered
            outside the ICMP layer such as the inability of IP to route
            the resultant datagram.  In some implementations there may
            be no types of error which contribute to this counter's
            value."
    ::= { basIcmpEntry 15 }

basIcmpOutDestUnreachs OBJECT-TYPE
    SYNTAX      Counter32
    MAX-ACCESS  read-only
    STATUS      current
    DESCRIPTION
            "The number of ICMP Destination Unreachable messages sent."
    ::= { basIcmpEntry 16 }

basIcmpOutTimeExcds OBJECT-TYPE
    SYNTAX      Counter32
    MAX-ACCESS  read-only
    STATUS      current
    DESCRIPTION
            "The number of ICMP Time Exceeded messages sent."
    ::= { basIcmpEntry 17 }

basIcmpOutParmProbs OBJECT-TYPE
    SYNTAX      Counter32
    MAX-ACCESS  read-only
    STATUS      current
    DESCRIPTION
            "The number of ICMP Parameter Problem messages sent."
    ::= { basIcmpEntry 18 }

basIcmpOutSrcQuenchs OBJECT-TYPE
    SYNTAX      Counter32
    MAX-ACCESS  read-only
    STATUS      current
    DESCRIPTION
            "The number of ICMP Source Quench messages sent."
    ::= { basIcmpEntry 19 }

basIcmpOutRedirects OBJECT-TYPE
    SYNTAX      Counter32
    MAX-ACCESS  read-only
    STATUS      current
    DESCRIPTION
            "The number of ICMP Redirect messages sent.  For a host,
            this object will always be zero, since hosts do not send
            redirects."
    ::= { basIcmpEntry 20 }

basIcmpOutEchos OBJECT-TYPE
    SYNTAX      Counter32
    MAX-ACCESS  read-only
    STATUS      current
    DESCRIPTION
            "The number of ICMP Echo (request) messages sent."
    ::= { basIcmpEntry 21 }

basIcmpOutEchoReps OBJECT-TYPE
    SYNTAX      Counter32
    MAX-ACCESS  read-only
    STATUS      current
    DESCRIPTION
            "The number of ICMP Echo Reply messages sent."
    ::= { basIcmpEntry 22 }

basIcmpOutTimestamps OBJECT-TYPE
    SYNTAX      Counter32
    MAX-ACCESS  read-only
    STATUS      current
    DESCRIPTION
            "The number of ICMP Timestamp (request) messages sent."
    ::= { basIcmpEntry 23 }

basIcmpOutTimestampReps OBJECT-TYPE
    SYNTAX      Counter32
    MAX-ACCESS  read-only
    STATUS      current
    DESCRIPTION
            "The number of ICMP Timestamp Reply messages sent."
    ::= { basIcmpEntry 24 }

basIcmpOutAddrMasks OBJECT-TYPE
    SYNTAX      Counter32
    MAX-ACCESS  read-only
    STATUS      current
    DESCRIPTION
            "The number of ICMP Address Mask Request messages sent."
    ::= { basIcmpEntry 25 }

basIcmpOutAddrMaskReps OBJECT-TYPE
    SYNTAX      Counter32
    MAX-ACCESS  read-only
    STATUS      current
    DESCRIPTION
            "The number of ICMP Address Mask Reply messages sent."
    ::= { basIcmpEntry 26 }

basIcmpChassis OBJECT-TYPE
	SYNTAX		BasChassisId
	MAX-ACCESS	not-accessible
	STATUS		current
	DESCRIPTION
		"The BAS Chassis ID of this card."
	::= { basIcmpEntry 27 }

basIcmpSlot OBJECT-TYPE
	SYNTAX		BasSlotId
	MAX-ACCESS	not-accessible
	STATUS		current
	DESCRIPTION
		"The BAS Slot ID of this card."
	::= { basIcmpEntry 28 }

basIcmpIf OBJECT-TYPE
	SYNTAX		BasInterfaceId
	MAX-ACCESS	not-accessible
	STATUS		current
	DESCRIPTION
		"The BAS interface ID of this card."
	::= { basIcmpEntry 29 }

basIcmpLPort OBJECT-TYPE
	SYNTAX		BasLogicalPortId
	MAX-ACCESS	not-accessible
	STATUS		current
	DESCRIPTION
		"The BAS logical port ID of this card."
	::= { basIcmpEntry 30 }

END
