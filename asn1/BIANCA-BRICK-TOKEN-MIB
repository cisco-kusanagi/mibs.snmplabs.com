-- This file is corresponding to Release 6.1.2.100 from 2001/09/26 00:00:00
-- (C)opyright 1991-1999 BinTec Communications AG, All Rights Reserved
--  $RCSfile: mibtoken,v $ 
-- $Revision: 1.6 $ 

BIANCA-BRICK-TOKEN-MIB DEFINITIONS ::= BEGIN
 
        IMPORTS
            Counter
                FROM RFC1155-SMI
 
            OBJECT-TYPE
                FROM RFC-1212
		PhysAddress FROM SNMPv2-TC;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    tokenring	OBJECT IDENTIFIER 
	::= { bibo 11 }


    -- Interfaces Group

    -- Management Information for the TokenRing Subsystem of the BIANCA/BRICK

	Date ::= INTEGER
	HexValue ::= INTEGER


        tokenringIfTable OBJECT-TYPE
            SYNTAX  SEQUENCE OF TokenRingIfEntry
            ACCESS  not-accessible
            STATUS  mandatory
            DESCRIPTION
		"The tokenringIfTable contains information relating to the 
                interfaces found on the system. Each entry corresponds to
                a connected TokenRing interface. Entries can only be added or 
		deleted by the system. 

                Creating entries: Entries are created by the system
                only when a new TokenRing module is installed.

                Deleting entries: Entries are removed by the system
                after the appropriate TokenRing module is removed."
	::= { tokenring 1 }

	tokenringIfEntry OBJECT-TYPE
            SYNTAX  TokenRingIfEntry
            ACCESS  not-accessible
            STATUS  mandatory
            DESCRIPTION
		""
	    INDEX   { tokenringIfSlot }
              ::= { tokenringIfTable 1 }

	TokenRingIfEntry ::=
            SEQUENCE {
                tokenringIfSlot				INTEGER,
		tokenringState				INTEGER,
		tokenringIfRingRate			INTEGER,
		tokenringIfEarlyTokenRelease		INTEGER,
		tokenringIfWrapInterface		INTEGER,
	        tokenringIfMtu  	                INTEGER,
                tokenringIfOverwritePhysAddress         PhysAddress,
		tokenringIfNAUN				PhysAddress,

		-- Statistics
		tokenringIfLineError			Counter,
		tokenringIfBurstError			Counter,
		tokenringIfAriFciError			Counter,
		tokenringIfLostFrameError		Counter,
		tokenringIfReceiveCongestionError	Counter,
		tokenringIfFrameCopiedError		Counter,
		tokenringIfTokenError			Counter,
		tokenringIfDmaBusError			Counter,
		tokenringIfDmaParityError		Counter,
		tokenringIfSoftError			Counter,
		tokenringIfSourceRouting		INTEGER
            }

	tokenringIfSlot OBJECT-TYPE
            SYNTAX  INTEGER
            ACCESS  read-only
            STATUS  mandatory

            DESCRIPTION
                "Unique Slot of the TokenRing interface."
	::= { tokenringIfEntry 1 }

	tokenringIfState OBJECT-TYPE
            SYNTAX  INTEGER {
	        down(1), 	-- inactive
		start(2),       -- start initialization
		download(3),	-- download adapter microcode
	        reset(4),
		bud(5),		-- bring up diagnostics
		tferipb(6),	-- transfer initialization parameter block
		wait1(7),
		open(8),	-- open onto the ring
		wait2(9),
		delay1(10),
		receive(11),	-- enable receive
		wait3(12),
		done(13),	-- successful initialization
		close(14),	-- close adapter
		error(15)	-- unrecoverable error
        	}
            ACCESS  read-only
            STATUS  mandatory

            DESCRIPTION
                "The TokenRing adapter initialization state"
	::= { tokenringIfEntry 2 }

	tokenringIfRingRate OBJECT-TYPE
            SYNTAX  INTEGER {
		tr-4Mbit(1), tr-16Mbit(2)
	    }
            ACCESS  read-write
            STATUS  mandatory

            DESCRIPTION
                "speed of the token ring."
	::= { tokenringIfEntry 3 }

	tokenringIfEarlyTokenRelease OBJECT-TYPE
            SYNTAX  INTEGER {
		enabled(1), disabled (2)
	    }
            ACCESS  read-write
            STATUS  mandatory

            DESCRIPTION
                "enable or disable early token release. This feature is only
		 valid with the 16 Mbps ring rate"
	::= { tokenringIfEntry 4 }

	tokenringIfWrapInterface OBJECT-TYPE
            SYNTAX  INTEGER {
		enabled(1), disabled (2)
	    }
            ACCESS  read-write
            STATUS  mandatory

            DESCRIPTION
                "enable or disable the wrap interface option. If enabled the 
		 ring insertion process is omitted and all user-transmit data
		 appears as receive data."
	::= { tokenringIfEntry 5 }

        tokenringIfMtu OBJECT-TYPE
            SYNTAX  INTEGER (15..17800)
            ACCESS  read-write
            STATUS  mandatory

            DESCRIPTION
                "The size of the largest datagram which can be
                 sent/received on the interface, specified in
                 octets."
        ::= { tokenringIfEntry 6 }

        tokenringIfOverwritePhysAddress OBJECT-TYPE
            SYNTAX  PhysAddress
            ACCESS  read-write
            STATUS  mandatory

            DESCRIPTION
                "The interface's address at the protocol layer
                 immediately `below' the network layer in the
                 protocol stack. This overwrites the address 
	         defined in the adapter PROM."
        ::= { tokenringIfEntry 7 }
	
        tokenringIfNAUN OBJECT-TYPE
            SYNTAX  PhysAddress
            ACCESS  read-only
            STATUS  mandatory
            DESCRIPTION
                "The interface's address of the nearest upstream
                 neighbour."
        ::= { tokenringIfEntry 8 }

	tokenringIfLineError OBJECT-TYPE
            SYNTAX  Counter
            ACCESS  read-only
            STATUS  mandatory

            DESCRIPTION
                "Count of line errors. This counter is incremented whenever
		 1) a frame is repeated or copied, and
		 2) the Error Detected Indicator (EDI) is zero in the incoming
		    frame, and
		 3) at least one of the following conditions exists:
			a) a code violation between SDEL and EDEL
			b) a code violation in a token
			c) a FCS error"

	::= { tokenringIfEntry 9 }

	tokenringIfBurstError OBJECT-TYPE
            SYNTAX  Counter
            ACCESS  read-only
            STATUS  mandatory

            DESCRIPTION
                "Count of burst errors. This counter is incremented whenever
		 the interface detects the absence of transitions for five
		 half-bit times between SDEL and EDEL, or EDEL and SDEL"

	::= { tokenringIfEntry 10 }

	tokenringIfAriFciError OBJECT-TYPE
            SYNTAX  Counter
            ACCESS  read-only
            STATUS  mandatory

            DESCRIPTION
                "Count of ARI/FCI errors. This counter is incremented whenever
		 the interface receives an Active Monitor Present (AMP) MAC
		 frame with the ARI/FCI bit equal to zero and a Standby Monitor
		 Present (SMP) MAC frame with the ARI/FCI bits equal to zero,
		 or more than one SMP MAC frame with the ARI/FCI bits equal
		 to zero, without receiving an intervening AMP MAC frame."
	::= { tokenringIfEntry 11 }

	tokenringIfLostFrameError OBJECT-TYPE
            SYNTAX  Counter
            ACCESS  read-only
            STATUS  mandatory

            DESCRIPTION
                "Count of lost frames errors. This counter is incremented
		 whenever the interface is in transmit (stripping) mode and
		 fails to receive the end of the frame it transmitted"

	::= { tokenringIfEntry 12 }

	tokenringIfReceiveCongestionError OBJECT-TYPE
            SYNTAX  Counter
            ACCESS  read-only
            STATUS  mandatory

            DESCRIPTION
                "Count of receive congestion errors. This counter is 
		 incremented whenever the interface in the repeat mode
		 recognizes a frame addressed to it but has no buffer space
		 to copy the frame"

	::= { tokenringIfEntry 13 }

	tokenringIfFrameCopiedError OBJECT-TYPE
            SYNTAX  Counter
            ACCESS  read-only
            STATUS  mandatory

            DESCRIPTION
                "Count of frame copied errors. This counter is incremented 
		 whenever the interface in the receive/repeat mode recognizes
		 a frame addressed to its specific address but finds the 
		 ARI bits not equal to zero"

	::= { tokenringIfEntry 14 }

	tokenringIfTokenError OBJECT-TYPE
            SYNTAX  Counter
            ACCESS  read-only
            STATUS  mandatory

            DESCRIPTION
                "Count of token errors. This counter is only active in the 
		 active monitor station. It is incremented when the active
		 monitor detects an error in the token protocol"

	::= { tokenringIfEntry 15 }

	tokenringIfDmaBusError OBJECT-TYPE
            SYNTAX  Counter
            ACCESS  read-only
            STATUS  mandatory

            DESCRIPTION
                "Count of DMA bus errors. This counter is counts the occurences
		 of DMA bus errors that do not exceed the specified abort
		 thresholds"

	::= { tokenringIfEntry 16 }

	tokenringIfDmaParityError OBJECT-TYPE
            SYNTAX  Counter
            ACCESS  read-only
            STATUS  mandatory

            DESCRIPTION
                "Count of DMA parity errors. This counter counts the occurences
		 of DMA parity errors that do not exceed the specified abort
		 thresholds"

	::= { tokenringIfEntry 17 }

	tokenringIfSoftError OBJECT-TYPE
            SYNTAX  Counter
            ACCESS  read-only
            STATUS  mandatory

            DESCRIPTION
                "Count of soft errors that occur during normal operation. A soft
		 error is an error condition that temporarily degrades system
		 performance; however the ring recovers by using the protocols
		 of the adapter. The adapter counts these errors and can report
		 them to both the attached product and the ring error monitor."

	::= { tokenringIfEntry 18 }

	tokenringIfSourceRouting OBJECT-TYPE
            SYNTAX  INTEGER {
		enabled(1), disabled (2)
	    }
            ACCESS  read-write
            STATUS  mandatory

            DESCRIPTION
                "enable or disable source routing. If enabled, a routing 
		 information field is added to the frame sent over this 
		 interface."
	::= { tokenringIfEntry 19 }


END		-- of Tokenring definitions
