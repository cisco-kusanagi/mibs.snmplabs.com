-- MODULE-IDENTITY
--  OrgName
--    Netasq
--  ContactInfo
--     Customer Support
--     
--     3, rue Archimède
--     59650 Villeneuve d'Ascq
--     FRANCE
--    
--     Tel: +33 03 20 61 96 30
--     E-mail: support@netasq.com
--     Http://www.netasq.com

--
--  Last modified date: 10/03/2003
--    

NETASQ-ALARM-MIB DEFINITIONS ::= BEGIN
IMPORTS

    OBJECT-TYPE , NOTIFICATION-TYPE, Integer32 FROM SNMPv2-SMI
	SnmpAdminString FROM SNMP-FRAMEWORK-MIB	
    ntqAlarm, ntqNotifications	FROM NETASQ-SMI-MIB;
	
		ntqATable OBJECT-TYPE
                SYNTAX 		SEQUENCE OF NtqAEntry
				MAX-ACCESS  not-accessible
				STATUS      current
                DESCRIPTION 
                        "Alarm Table"
                ::= { ntqAlarm 0 }
				
        ntqAEntry OBJECT-TYPE
			SYNTAX  NtqAEntry
			MAX-ACCESS  not-accessible
			STATUS      current
			DESCRIPTION
				   "Alarm table entry"
			INDEX   { ntqAIndex }
			::= {  ntqATable 1 }
        
       NtqAEntry ::=
                SEQUENCE {
					ntqAIndex						Integer32,
					ntqATime						OCTET STRING,
					ntqASif							OCTET STRING,
					ntqADif							OCTET STRING,
					ntqAProto						OCTET STRING,
					ntqASaddr						OCTET STRING,
					ntqADaddr						OCTET STRING,
					ntqASport						Integer32,
					ntqADport						Integer32,
					ntqASname						OCTET STRING,
					ntqADname						OCTET STRING,
					ntqAMessage						SnmpAdminString
				}

		ntqAIndex OBJECT-TYPE
			SYNTAX Integer32 (1..2147483647)
			MAX-ACCESS  not-accessible
			STATUS      current
			DESCRIPTION
					"Index of each line in table"
		::= { ntqAEntry 0 }
				
		ntqATime OBJECT-TYPE
			SYNTAX      OCTET STRING
			MAX-ACCESS  read-only
			STATUS      current
			DESCRIPTION
					"alarm date"
		::= { ntqAEntry 1 }
				
		ntqASif OBJECT-TYPE
			SYNTAX      OCTET STRING
			MAX-ACCESS  read-only
			STATUS      current
			DESCRIPTION
					"source interface"
		::= { ntqAEntry 2 }
				
		ntqADif OBJECT-TYPE
			SYNTAX      OCTET STRING
			MAX-ACCESS  read-only
			STATUS      current
			DESCRIPTION
					"destination interface"
		::= { ntqAEntry 3 }
				
		ntqAProto OBJECT-TYPE
			SYNTAX      OCTET STRING
			MAX-ACCESS  read-only
			STATUS      current
			DESCRIPTION
					"IP protocol"
		::= { ntqAEntry 4 }
				
		ntqASaddr OBJECT-TYPE
			SYNTAX      OCTET STRING
			MAX-ACCESS  read-only
			STATUS      current
			DESCRIPTION
					"source IP adress"
		::= { ntqAEntry 5 }
				
		ntqADaddr OBJECT-TYPE
			SYNTAX      OCTET STRING
			MAX-ACCESS  read-only
			STATUS      current
			DESCRIPTION
					"destination IP address"
		::= { ntqAEntry 6 }
				
		ntqASport OBJECT-TYPE
			SYNTAX      Integer32
			MAX-ACCESS  read-only
			STATUS      current
			DESCRIPTION
					"Source port"
		::= { ntqAEntry 7 }
				
		ntqADport OBJECT-TYPE
			SYNTAX      Integer32
			MAX-ACCESS  read-only
			STATUS      current
			DESCRIPTION
					"Destination port"
		::= { ntqAEntry 8 }
			
		ntqASname OBJECT-TYPE
			SYNTAX      OCTET STRING
			MAX-ACCESS  read-only
			STATUS      current
			DESCRIPTION
					"IP source name"
		::= { ntqAEntry 9 }
				
		ntqADname OBJECT-TYPE
			SYNTAX      OCTET STRING
			MAX-ACCESS  read-only
			STATUS      current
			DESCRIPTION
					"IP destination name"
		::= { ntqAEntry 10 }
				
		ntqAMessage OBJECT-TYPE
			SYNTAX      SnmpAdminString
			MAX-ACCESS  read-only
			STATUS      current
			DESCRIPTION
					"Alarm Message"
		::= { ntqAEntry 11 }

		ntqAicmpTable OBJECT-TYPE
			SYNTAX SEQUENCE OF NtqAicmpEntry
			MAX-ACCESS  not-accessible
			STATUS      current
			DESCRIPTION 
					"ICMP alarm table"
		::= { ntqAlarm 1 }
                
        ntqAicmpEntry OBJECT-TYPE
			SYNTAX  NtqAicmpEntry
			MAX-ACCESS  not-accessible
			STATUS      current
			DESCRIPTION
				   "Entry in the ntqAicmpTable."
			INDEX   { ntqAicmpIndex }
        ::= { ntqAicmpTable 1 }
        
       NtqAicmpEntry ::=
                SEQUENCE {
					ntqAicmpIndex
						Integer32,
					ntqAicmpTime
						OCTET STRING,
					ntqAicmpSif
						OCTET STRING,
					ntqAicmpDif
						OCTET STRING,
					ntqAicmpSaddr
						OCTET STRING,
					ntqAicmpDaddr
						OCTET STRING,
					ntqAicmpType
						Integer32,
					ntqAicmpCode
						Integer32,
					ntqAicmpSname
						OCTET STRING,
					ntqAicmpDname
						OCTET STRING,
					ntqAicmpMessage
						SnmpAdminString
				}

        ntqAicmpIndex OBJECT-TYPE
			SYNTAX  Integer32 (1..2147483647)
			MAX-ACCESS  not-accessible
			STATUS      current
			DESCRIPTION
				 "A unique value for phase one table.  Its value
				  ranges between 1 and 65535 and may not be contigous. 
				  the index has no other meaning but a pure index" 
        ::= { ntqAicmpEntry 0 }
		
		ntqAicmpTime OBJECT-TYPE
			SYNTAX      OCTET STRING
			MAX-ACCESS  read-only
			STATUS      current
			DESCRIPTION
				 "Alarm date" 
        ::= { ntqAicmpEntry 1 }
		
		ntqAicmpSif OBJECT-TYPE
			SYNTAX      OCTET STRING
			MAX-ACCESS  read-only
			STATUS      current
			DESCRIPTION
				 "source interface" 
        ::= { ntqAicmpEntry 2 }
		
		ntqAicmpDif OBJECT-TYPE
			SYNTAX      OCTET STRING
			MAX-ACCESS  read-only
			STATUS      current
			DESCRIPTION
				 "destination interface" 
        ::= { ntqAicmpEntry 3 }
		
		ntqAicmpSaddr OBJECT-TYPE
			SYNTAX      OCTET STRING
			MAX-ACCESS  read-only
			STATUS      current
			DESCRIPTION
				 "IP source address" 
        ::= { ntqAicmpEntry 4 }
		
		ntqAicmpDaddr OBJECT-TYPE
			SYNTAX      OCTET STRING
			MAX-ACCESS  read-only
			STATUS      current
			DESCRIPTION
				 "IP destination address" 
        ::= { ntqAicmpEntry 5 }
		
		ntqAicmpType OBJECT-TYPE
			SYNTAX      Integer32
			MAX-ACCESS  read-only
			STATUS      current
			DESCRIPTION
				 "ICMP type" 
        ::= { ntqAicmpEntry 6 }
		
		ntqAicmpCode OBJECT-TYPE
			SYNTAX      Integer32
			MAX-ACCESS  read-only
			STATUS      current
			DESCRIPTION
				 "ICMP code" 
        ::= { ntqAicmpEntry 7 }
		
		ntqAicmpSname OBJECT-TYPE
			SYNTAX      OCTET STRING
			MAX-ACCESS  read-only
			STATUS      current
			DESCRIPTION
				 "IP source name" 
        ::= { ntqAicmpEntry 8 }
		
		ntqAicmpDname OBJECT-TYPE
			SYNTAX      OCTET STRING
			MAX-ACCESS  read-only
			STATUS      current
			DESCRIPTION
				 "IP destination name" 
        ::= { ntqAicmpEntry 9 }
		
		ntqAicmpMessage OBJECT-TYPE
			SYNTAX      SnmpAdminString
			MAX-ACCESS  read-only
			STATUS      current
			DESCRIPTION
				 "Alarm message" 
        ::= { ntqAicmpEntry 10 }
		
		ntqNotification NOTIFICATION-TYPE
			OBJECTS { ntqATime, ntqASif, ntqASaddr, ntqADaddr, ntqAMessage }
			STATUS current
			DESCRIPTION
				"notification"
		::= { ntqNotifications 1 }
END
