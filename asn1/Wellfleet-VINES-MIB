Wellfleet-VINES-MIB DEFINITIONS ::= BEGIN

-- Created by mdl2asn version 3.1
-- Creation date: Wed Aug 30 16:49:46 EDT 1995


    IMPORTS

      Counter, Gauge
        FROM RFC1155-SMI
      OBJECT-TYPE
        FROM RFC-1212
      DisplayString
        FROM RFC1213-MIB
      wfVinesGroup
        FROM Wellfleet-COMMON-MIB;


    wfVinesBase	OBJECT IDENTIFIER ::= { wfVinesGroup 1 }

    wfVinesBaseDelete OBJECT-TYPE
        SYNTAX	INTEGER {
    		    created(1),
    		    deleted(2)
    		}
        ACCESS	read-write
        STATUS	mandatory
        DESCRIPTION
                "Create/Delete parameter.  This value determines whether or not VINES
                is configured on this slot."
        DEFVAL	{ created }
        ::= { wfVinesBase 1 }

    wfVinesBaseDisable OBJECT-TYPE
        SYNTAX	INTEGER {
    		    enabled(1),
    		    disabled(2)
    		}
        ACCESS	read-write
        STATUS	mandatory
        DESCRIPTION
                "This parameter determines whether or not VINES is to startup."
        DEFVAL	{ enabled }
        ::= { wfVinesBase 2 }

    wfVinesBaseState OBJECT-TYPE
        SYNTAX	INTEGER {
    		    up(1),
    		    down(2),
    		    init(3),
    		    notpresent(4)
    		}
        ACCESS	read-only
        STATUS	mandatory
        DESCRIPTION
                "This parameter reflects the current state of VINES."
        DEFVAL	{ notpresent }
        ::= { wfVinesBase 3 }

    wfVinesBaseUserNetid OBJECT-TYPE
        SYNTAX	INTEGER(1..2097151)
        ACCESS	read-write
        STATUS	mandatory
        DESCRIPTION
                "The network ID as defined by the user.  A null value indicates
                that the user is not configuring a Network ID and that the
                the router should assign it."
        ::= { wfVinesBase 4 }

    wfVinesBaseRouterNetid OBJECT-TYPE
        SYNTAX	Counter
        ACCESS	read-only
        STATUS	mandatory
        DESCRIPTION
                "The network ID as defined by the router.  If the user configures
                a Network ID in the above attribute, we will take that value
                and add in the Wellfleet code for VINES and save it here."
        ::= { wfVinesBase 5 }

    wfVinesBaseBcastClass OBJECT-TYPE
        SYNTAX	INTEGER {
    		    bcast(1),
    		    chrg(2),
    		    cost(3),
    		    lans(4),
    		    srvr(5),
    		    nochrg(6),
    		    locost(7),
    		    alllans(8)
    		}
        ACCESS	read-write
        STATUS	mandatory
        DESCRIPTION
                "The broadcast modifier.  This value defines the
                class of broadcast packets that are originated
                by this node."
        DEFVAL	{ bcast }
        ::= { wfVinesBase 6 }

    wfVinesBaseNetworkSize OBJECT-TYPE
        SYNTAX	INTEGER
        ACCESS	read-write
        STATUS	mandatory
        DESCRIPTION
                "Allows the network administrator to pre-configure the size of the
                network.  The default is 0."
        ::= { wfVinesBase 7 }

    wfVinesBaseHostSize OBJECT-TYPE
        SYNTAX	INTEGER
        ACCESS	read-write
        STATUS	mandatory
        DESCRIPTION
                "Allows the network administrator to pre-configure the expected number
                of neighbor.  The dafault is 0."
        ::= { wfVinesBase 8 }

    wfVinesBaseRtpMode OBJECT-TYPE
        SYNTAX	INTEGER {
    		    automode(1),
    		    seq(2),
    		    sequenced(3)
    		}
        ACCESS	read-write
        STATUS	mandatory
        DESCRIPTION
                "This parameter will determine whether sequenced RTP or
                Non Sequenced RTP will be supported or both modes will
                be available."
        DEFVAL	{ automode }
        ::= { wfVinesBase 9 }

    wfVinesBaseLogFilter OBJECT-TYPE
        SYNTAX	INTEGER {
    		    nothing(2147483647),
    		    debug(1),
    		    info(2),
    		    trace(16),
    		    debuginfo(3),
    		    debugtrace(17),
    		    infotrace(18),
    		    debuginfotrace(19)
    		}
        ACCESS	read-write
        STATUS	mandatory
        DESCRIPTION
                "Filter out some log messages, Default filters out
                trace messages. ??? Change this later to FILTER_TRACE ??? "
        DEFVAL	{ nothing }
        ::= { wfVinesBase 10 }

    wfVinesBaseRouterSeqNumber OBJECT-TYPE
        SYNTAX	Counter
        ACCESS	read-only
        STATUS	mandatory
        DESCRIPTION
                "This parameter keeps track of the of current router
                sequence number"
        ::= { wfVinesBase 11 }

    wfVinesBaseSoloSlotMask OBJECT-TYPE
        SYNTAX	Gauge
        ACCESS	read-write
        STATUS	mandatory
        DESCRIPTION
		"Slot mask for which slots VINES soloist is eligible
                to run on.  The MSBit represents slot 1, the
                next most significant bit represents slot 2,
                and so on...  Slots can be 1-14.
                Default is all slots on a BCN."
	 DEFVAL  { 4294705152 }
        ::= { wfVinesBase 12 }

    wfVinesBaseSoloistSlot OBJECT-TYPE
        SYNTAX	INTEGER
        ACCESS	read-only
        STATUS	mandatory
        DESCRIPTION
                "Tells which slot the VINES soloist is running on"
        ::= { wfVinesBase 13 }


    wfVinesIp	OBJECT IDENTIFIER ::= { wfVinesGroup 2 }

    wfVinesIpTotIn OBJECT-TYPE
        SYNTAX	Counter
        ACCESS	read-only
        STATUS	mandatory
        DESCRIPTION
                "The total number of VINES IP packets received."
        ::= { wfVinesIp 1 }

    wfVinesIpTotOut OBJECT-TYPE
        SYNTAX	Counter
        ACCESS	read-only
        STATUS	mandatory
        DESCRIPTION
                "The total number of VINES IP packets sent."
        ::= { wfVinesIp 2 }

    wfVinesIpBad OBJECT-TYPE
        SYNTAX	Counter
        ACCESS	read-only
        STATUS	mandatory
        DESCRIPTION
                "The total number of badly formed packets that were received.
                This field is incremented when a packet is received with an
                improper checksum.  "
        ::= { wfVinesIp 3 }

    wfVinesIpRouted OBJECT-TYPE
        SYNTAX	Counter
        ACCESS	read-only
        STATUS	mandatory
        DESCRIPTION
                "The total number of packets received that were routed to another
                node.  This statistic includes the number of IP packets
                encapsulated within routed VINES IP headers.  Each routed packet
                counts as both an incoming and outgoing packet."
        ::= { wfVinesIp 4 }

    wfVinesIpRoutedHWM OBJECT-TYPE
        SYNTAX	INTEGER
        ACCESS	read-only
        STATUS	mandatory
        DESCRIPTION
                "The largest number of packets routed in one second since the server
                was last booted."
        ::= { wfVinesIp 5 }

    wfVinesIpBcast OBJECT-TYPE
        SYNTAX	Counter
        ACCESS	read-only
        STATUS	mandatory
        DESCRIPTION
                "The number of VINES IP broadcast packets sent, both locally
                generated and routed from other nodes.  "
        ::= { wfVinesIp 6 }

    wfVinesIpBcastHWM OBJECT-TYPE
        SYNTAX	INTEGER
        ACCESS	read-only
        STATUS	mandatory
        DESCRIPTION
                "The largest number of packets broadcast in one second since the server
                was last booted."
        ::= { wfVinesIp 7 }

    wfVinesIpReass OBJECT-TYPE
        SYNTAX	Counter
        ACCESS	read-only
        STATUS	mandatory
        DESCRIPTION
                "The number of times that packets were reassembled.  Reassemblies
                result from the transmission of packets that must be broken into
                smaller pieces, then reassembled due to differences in transmission
                media."
        ::= { wfVinesIp 8 }

    wfVinesIpFrags OBJECT-TYPE
        SYNTAX	Counter
        ACCESS	read-only
        STATUS	mandatory
        DESCRIPTION
                "The number of packet fragmentations performed."
        ::= { wfVinesIp 9 }

    wfVinesIpToDodIP OBJECT-TYPE
        SYNTAX	Counter
        ACCESS	read-only
        STATUS	mandatory
        DESCRIPTION
                "The number of packets that VINES IP passed to IP for encapsulation in
                IP headers.  These packets were initially handled by VINES IP, but
                were passed to IP for routing.  If the TCP/IP Server-to-Server
                option is not installed, this value will be zero."
        ::= { wfVinesIp 10 }

    wfVinesIpFromDodIP OBJECT-TYPE
        SYNTAX	Counter
        ACCESS	read-only
        STATUS	mandatory
        DESCRIPTION
                "The number of packets that VINES IP received from IP to be
                decapsulated into VINES packets.  IP initially handled these packets,
                but had to pass them on to VINES IP for routing.  If the server is
                not running a TCP/IP option, this value will be zero."
        ::= { wfVinesIp 11 }

    wfVinesRtpNbr	OBJECT IDENTIFIER ::= { wfVinesGroup 3 }

    wfVinesRtpNbrNumber OBJECT-TYPE
        SYNTAX	INTEGER
        ACCESS	read-only
        STATUS	mandatory
        DESCRIPTION
                "Number of entries in the Table of Neighbors."
        ::= { wfVinesRtpNbr 1 }

    wfVinesRtpNbrTable OBJECT-TYPE
        SYNTAX	SEQUENCE OF WfVinesRtpNbrEntry
        ACCESS	not-accessible
        STATUS	mandatory
        DESCRIPTION
                "This is the Table of Neighbors."
        ::= { wfVinesGroup 4 }

    wfVinesRtpNbrEntry OBJECT-TYPE
        SYNTAX	WfVinesRtpNbrEntry
        ACCESS	not-accessible
        STATUS	mandatory
        DESCRIPTION
                "An entry in the Table of Neighbors."
        INDEX { wfVinesRtpNbrNetId,
                wfVinesRtpNbrSubNetId }
        ::= { wfVinesRtpNbrTable 1 }

    WfVinesRtpNbrEntry ::= SEQUENCE {
    	    wfVinesRtpNbrNetId
    		Counter,
    	    wfVinesRtpNbrSubNetId
    		INTEGER,
    	    wfVinesRtpNbrType
    		INTEGER,
    	    wfVinesRtpNbrIfType
    		INTEGER,
    	    wfVinesRtpNbrRemAdr
    		OCTET STRING,
    	    wfVinesRtpNbrLocAdr
    		OCTET STRING,
    	    wfVinesRtpNbrLocSlot
    		INTEGER,
    	    wfVinesRtpNbrLocLine
    		INTEGER,
    	    wfVinesRtpNbrSvrName
    		OCTET STRING,
    	    wfVinesRtpNbrCost
    		INTEGER,
    	    wfVinesSeqRtpNbrState
    		INTEGER,
    	    wfVinesSeqRtpNbrSeqNumber
    		Counter,
    	    wfVinesRtpNbrRtType
    		INTEGER,
    	    wfVinesRtpNbrNumPaths
    		Counter
        }

    wfVinesRtpNbrNetId OBJECT-TYPE
        SYNTAX	Counter
        ACCESS	read-only
        STATUS	mandatory
        DESCRIPTION
                "The network ID of this neighbor."
        ::= { wfVinesRtpNbrEntry 1 }

    wfVinesRtpNbrSubNetId OBJECT-TYPE
        SYNTAX	INTEGER
        ACCESS	read-only
        STATUS	mandatory
        DESCRIPTION
                "The subnetwork ID of this neighbor."
        ::= { wfVinesRtpNbrEntry 2 }

    wfVinesRtpNbrType OBJECT-TYPE
        SYNTAX	INTEGER {
    		    workst(1),
    		    server(2)
    		}
        ACCESS	read-only
        STATUS	mandatory
        DESCRIPTION
                "The type of node: client or server."
        ::= { wfVinesRtpNbrEntry 3 }

    wfVinesRtpNbrIfType OBJECT-TYPE
        SYNTAX	INTEGER {
    		    enet(1),
    		    tr4k(2),
    		    tr16k(3),
    		    hdlc1200(4),
    		    hdlc4800(5),
    		    hdlc9600(6),
    		    hdlc56000(7),
    		    async1200(8),
    		    async4800(9),
    		    async9600(10),
    		    async56000(11),
    		    x251200(12),
    		    x254800(13),
    		    x259600(14),
    		    x2556000(15),
    		    t145k(16),
    		    t1128k(17),
    		    t1192k(18),
    		    t1256k(19),
    		    t1320k(20),
    		    t1384k(21),
    		    t1448k(22),
    		    t1512k(23),
    		    t1576k(24),
    		    t1640k(25),
    		    t1704k(26),
    		    t1896k(27),
    		    t11088k(28),
    		    t11344k(29),
    		    tunnel(30),
    		    fddi(31)
    		}
        ACCESS	read-only
        STATUS	mandatory
        DESCRIPTION
                "This describes the type of interface."
        ::= { wfVinesRtpNbrEntry 4 }

    wfVinesRtpNbrRemAdr OBJECT-TYPE
        SYNTAX	OCTET STRING
        ACCESS	read-only
        STATUS	mandatory
        DESCRIPTION
                "Remote MAC address."
        ::= { wfVinesRtpNbrEntry 5 }

    wfVinesRtpNbrLocAdr OBJECT-TYPE
        SYNTAX	OCTET STRING
        ACCESS	read-only
        STATUS	mandatory
        DESCRIPTION
                "Local MAC address."
        ::= { wfVinesRtpNbrEntry 6 }

    wfVinesRtpNbrLocSlot OBJECT-TYPE
        SYNTAX	INTEGER
        ACCESS	read-only
        STATUS	mandatory
        DESCRIPTION
                "Slot connected to this neighbor."
        ::= { wfVinesRtpNbrEntry 7 }

    wfVinesRtpNbrLocLine OBJECT-TYPE
        SYNTAX	INTEGER
        ACCESS	read-only
        STATUS	mandatory
        DESCRIPTION
                "Line connected to this neighbor."
        ::= { wfVinesRtpNbrEntry 8 }

    wfVinesRtpNbrSvrName OBJECT-TYPE
        SYNTAX	OCTET STRING
        ACCESS	read-only
        STATUS	mandatory
        DESCRIPTION
                "Name of the server (N/A)."
        ::= { wfVinesRtpNbrEntry 9 }

    wfVinesRtpNbrCost OBJECT-TYPE
        SYNTAX	INTEGER
        ACCESS	read-only
        STATUS	mandatory
        DESCRIPTION
                "Cost for this neighbor."
        ::= { wfVinesRtpNbrEntry 10 }

    wfVinesSeqRtpNbrState OBJECT-TYPE
        SYNTAX	INTEGER {
    		    init(1),
    		    fullrqst(2),
    		    chgrqst(3),
    		    up(4)
    		}
        ACCESS	read-only
        STATUS	mandatory
        DESCRIPTION
                "Current state of the Nbr"
        DEFVAL	{ up }
        ::= { wfVinesRtpNbrEntry 11 }

    wfVinesSeqRtpNbrSeqNumber OBJECT-TYPE
        SYNTAX	Counter
        ACCESS	read-only
        STATUS	mandatory
        DESCRIPTION
                "The Nbr's own sequence number"
        ::= { wfVinesRtpNbrEntry 12 }

    wfVinesRtpNbrRtType OBJECT-TYPE
        SYNTAX	INTEGER {
    		    seq(1),
    		    sequenced(2)
    		}
        ACCESS	read-only
        STATUS	mandatory
        DESCRIPTION
                "The route type of this nbr"
        ::= { wfVinesRtpNbrEntry 13 }

    wfVinesRtpNbrNumPaths OBJECT-TYPE
        SYNTAX	Counter
        ACCESS	read-only
        STATUS	mandatory
        DESCRIPTION
                "The number of paths to the Nbr"
        ::= { wfVinesRtpNbrEntry 14 }

    wfVinesRtpRt	OBJECT IDENTIFIER ::= { wfVinesGroup 5 }

    wfVinesRtpRtNumber OBJECT-TYPE
        SYNTAX	INTEGER
        ACCESS	read-only
        STATUS	mandatory
        DESCRIPTION
                "Number of entries in the Table of Networks."
        ::= { wfVinesRtpRt 1 }

    wfVinesRtpRtTable OBJECT-TYPE
        SYNTAX	SEQUENCE OF WfVinesRtpRtEntry
        ACCESS	not-accessible
        STATUS	mandatory
        DESCRIPTION
                "This is the Table of Networks."
        ::= { wfVinesGroup 6 }

    wfVinesRtpRtEntry OBJECT-TYPE
        SYNTAX	WfVinesRtpRtEntry
        ACCESS	not-accessible
        STATUS	mandatory
        DESCRIPTION
                "An entry in the Table of Networks."
        INDEX	{ wfVinesRtpRtNetid }
        ::= { wfVinesRtpRtTable 1 }

    WfVinesRtpRtEntry ::= SEQUENCE {
    	    wfVinesRtpRtNetid
    		Counter,
    	    wfVinesRtpRtMetric
    		INTEGER,
    	    wfVinesRtpRtIdle
    		INTEGER,
    	    wfVinesRtpRtGateNetid
    		Counter,
    	    wfVinesRtpRtSvrName
    		OCTET STRING,
    	    wfVinesRtpRtGateSvrName
    		OCTET STRING,
    	    wfVinesRtpRtLocSlot
    		INTEGER,
    	    wfVinesRtpRtLocLine
    		INTEGER,
    	    wfVinesRtpRtIfType
    		INTEGER,
    	    wfVinesRtpRtGateHwAddr
    		OCTET STRING,
    	    wfVinesRtpRtType
    		INTEGER,
    	    wfVinesRtpRtSeqNumber
    		Counter,
    	    wfVinesRtpRtTimeStamp
    		Counter,
    	    wfVinesRtpRtNumPaths
    		Counter
        }

    wfVinesRtpRtNetid OBJECT-TYPE
        SYNTAX	Counter
        ACCESS	read-only
        STATUS	mandatory
        DESCRIPTION
                "The network ID number."
        ::= { wfVinesRtpRtEntry 1 }

    wfVinesRtpRtMetric OBJECT-TYPE
        SYNTAX	INTEGER
        ACCESS	read-only
        STATUS	mandatory
        DESCRIPTION
                "The routing metric to get to this network."
        ::= { wfVinesRtpRtEntry 2 }

    wfVinesRtpRtIdle OBJECT-TYPE
        SYNTAX	INTEGER
        ACCESS	read-only
        STATUS	mandatory
        DESCRIPTION
                "The idle time for this network."
        ::= { wfVinesRtpRtEntry 3 }

    wfVinesRtpRtGateNetid OBJECT-TYPE
        SYNTAX	Counter
        ACCESS	read-only
        STATUS	mandatory
        DESCRIPTION
                "The network ID of the gateway to this network."
        ::= { wfVinesRtpRtEntry 4 }

    wfVinesRtpRtSvrName OBJECT-TYPE
        SYNTAX	OCTET STRING
        ACCESS	read-only
        STATUS	mandatory
        DESCRIPTION
                "The servers name (N/A)."
        ::= { wfVinesRtpRtEntry 5 }

    wfVinesRtpRtGateSvrName OBJECT-TYPE
        SYNTAX	OCTET STRING
        ACCESS	read-only
        STATUS	mandatory
        DESCRIPTION
                "The name of the gateway server."
        ::= { wfVinesRtpRtEntry 6 }

    wfVinesRtpRtLocSlot OBJECT-TYPE
        SYNTAX	INTEGER
        ACCESS	read-only
        STATUS	mandatory
        DESCRIPTION
                "Slot connected to this Network."
        ::= { wfVinesRtpRtEntry 7 }

    wfVinesRtpRtLocLine OBJECT-TYPE
        SYNTAX	INTEGER
        ACCESS	read-only
        STATUS	mandatory
        DESCRIPTION
                "Line connected to this Network."
        ::= { wfVinesRtpRtEntry 8 }

    wfVinesRtpRtIfType OBJECT-TYPE
        SYNTAX	INTEGER {
    		    enet(1),
    		    tr4k(2),
    		    tr16k(3),
    		    hdlc1200(4),
    		    hdlc4800(5),
    		    hdlc9600(6),
    		    hdlc56000(7),
    		    async1200(8),
    		    async4800(9),
    		    async9600(10),
    		    async56000(11),
    		    x251200(12),
    		    x254800(13),
    		    x259600(14),
    		    x2556000(15),
    		    t145k(16),
    		    t1128k(17),
    		    t1192k(18),
    		    t1256k(19),
    		    t1320k(20),
    		    t1384k(21),
    		    t1448k(22),
    		    t1512k(23),
    		    t1576k(24),
    		    t1640k(25),
    		    t1704k(26),
    		    t1896k(27),
    		    t11088k(28),
    		    t11344k(29),
    		    tunnel(30),
    		    fddi(31)
    		}
        ACCESS	read-only
        STATUS	mandatory
        DESCRIPTION
                "This describes the type of interface."
        ::= { wfVinesRtpRtEntry 9 }

    wfVinesRtpRtGateHwAddr OBJECT-TYPE
        SYNTAX	OCTET STRING
        ACCESS	read-only
        STATUS	mandatory
        DESCRIPTION
                "Remote MAC address."
        ::= { wfVinesRtpRtEntry 10 }

    wfVinesRtpRtType OBJECT-TYPE
        SYNTAX	INTEGER {
    		    seq(1),
    		    sequenced(2)
    		}
        ACCESS	read-only
        STATUS	mandatory
        DESCRIPTION
                "This indicates the whether this is a VINES 5.50 router or
                a VINES 4.11 Router/Server. If learnt as part of a 4.11
                RTP or thro' a sequenced RTP or by looking at the network
                flag in the tuple of a sequenced update"
        ::= { wfVinesRtpRtEntry 11 }

    wfVinesRtpRtSeqNumber OBJECT-TYPE
        SYNTAX	Counter
        ACCESS	read-only
        STATUS	mandatory
        DESCRIPTION
                "This attribute will always have a value of 0x0"
        ::= { wfVinesRtpRtEntry 12 }

    wfVinesRtpRtTimeStamp OBJECT-TYPE
        SYNTAX	Counter
        ACCESS	read-only
        STATUS	mandatory
        DESCRIPTION
                "This attribute will always have a value of 0x0"
        ::= { wfVinesRtpRtEntry 13 }

    wfVinesRtpRtNumPaths OBJECT-TYPE
        SYNTAX	Counter
        ACCESS	read-only
        STATUS	mandatory
        DESCRIPTION
                "The number of paths to the Network"
        ::= { wfVinesRtpRtEntry 14 }

    wfVinesIf	OBJECT IDENTIFIER ::= { wfVinesGroup 7 }

    wfVinesIfNumber OBJECT-TYPE
        SYNTAX	INTEGER
        ACCESS	read-only
        STATUS	mandatory
        DESCRIPTION
                "This is the number of entries in the Interfaces Table."
        ::= { wfVinesIf 1 }

    wfVinesIfTable OBJECT-TYPE
        SYNTAX	SEQUENCE OF WfVinesIfEntry
        ACCESS	not-accessible
        STATUS	mandatory
        DESCRIPTION
                "This is the Table of Interfaces."
        ::= { wfVinesGroup 8 }

    wfVinesIfEntry OBJECT-TYPE
        SYNTAX	WfVinesIfEntry
        ACCESS	not-accessible
        STATUS	mandatory
        DESCRIPTION
                "An entry to the Interface Table."
        INDEX	{ wfVinesIfCct }
        ::= { wfVinesIfTable 1 }

    WfVinesIfEntry ::= SEQUENCE {
    	    wfVinesIfDelete
    		INTEGER,
    	    wfVinesIfDisable
    		INTEGER,
    	    wfVinesIfState
    		INTEGER,
    	    wfVinesIfSlot
    		INTEGER,
    	    wfVinesIfLine
    		INTEGER,
    	    wfVinesIfCct
    		INTEGER,
    	    wfVinesIfSession
    		INTEGER,
    	    wfVinesIfType
    		INTEGER,
    	    wfVinesIfDescr
    		OCTET STRING,
    	    wfVinesIfAdr
    		OCTET STRING,
    	    wfVinesIfDodIpDisable
    		INTEGER,
    	    wfVinesIfArpDisable
    		INTEGER,
    	    wfVinesIfTrEndStation
    		INTEGER,
    	    wfVinesIfInPkts
    		Counter,
    	    wfVinesIfInErrs
    		Counter,
    	    wfVinesIfOutPkts
    		Counter,
    	    wfVinesIfOutErrs
    		Counter,
    	    wfVinesIfInMsgs
    		Counter,
    	    wfVinesIfMux
    		INTEGER,
    	    wfVinesIfFwdDrops
    		Counter,
    	    wfVinesIfZeroHopDrops
    		Counter,
    	    wfVinesIfIcpInErrorNotifs
    		Counter,
    	    wfVinesIfIcpInMetricNotifs
    		Counter,
    	    wfVinesIfIcpInErrors
    		Counter,
    	    wfVinesIfIcpOutErrorNotifs
    		Counter,
    	    wfVinesIfIcpOutMetricNotifs
    		Counter,
    	    wfVinesIfArpInQueries
    		Counter,
    	    wfVinesIfArpInAssgReqs
    		Counter,
    	    wfVinesIfArpInErrors
    		Counter,
    	    wfVinesIfArpOutServRsps
    		Counter,
    	    wfVinesIfArpOutAssgRsps
    		Counter,
    	    wfVinesIfInRedirects
    		Counter,
    	    wfVinesIfOutRedirects
    		Counter,
    	    wfVinesIfEchoInPkts
    		Counter,
    	    wfVinesIfEchoOutPkts
    		Counter,
    	    wfVinesIfReassFails
    		Counter,
    	    wfVinesIfRemClientPrivDisable
    		INTEGER,
    	    wfVinesIfSplitHorizonDisable
    		INTEGER,
    	    wfVinesIfCost
    		INTEGER,
    	    wfVinesIfSyncPortNumber
    		INTEGER,
    	    wfVinesIfInLackRescError
    		Counter,
    	    wfVinesIfOutLackRescError
    		Counter,
    	    wfVinesIfRtpRecv
    		Counter,
    	    wfVinesIfRtpSent
    		Counter,
    	    wfVinesIfSMDSGroupAddress
    		OCTET STRING,
    	    wfVinesIfFRBcastDlci
    		OCTET STRING,
    	    wfVinesIfCfgAdr
    		OCTET STRING,
    	    wfVinesIfNumRoutes
    		Counter,
    	    wfVinesIfCfgCost
    		INTEGER,
    	    wfVinesIfCostUsed
    		INTEGER,
    	    wfVinesIfFrpEnable
    		INTEGER,
    	    wfVinesIfSeqArpInQueries
    		Counter,
    	    wfVinesIfSeqArpInAssgReqs
    		Counter,
    	    wfVinesIfSeqArpInErrors
    		Counter,
    	    wfVinesIfSeqArpOutServRsps
    		Counter,
    	    wfVinesIfSeqArpOutAssgRsps
    		Counter,
    	    wfVinesIfInSeqRedirects
    		Counter,
    	    wfVinesIfOutSeqRedirects
    		Counter,
    	    wfVinesIfSeqRtpRecv
    		Counter,
    	    wfVinesIfSeqRtpSent
    		Counter,
    	    wfVinesIfRtpGenerationDisable
    		INTEGER,
    	    wfVinesIfInverseArpEnable
    		INTEGER,
    	    wfVinesIfSTalkSplitHorizon
    		INTEGER,
    	    wfVinesIfPermWanNbr
    		INTEGER,
    	    wfVinesIfNumFwdEntries
    		Counter,
    	    wfVinesIfNumNonSeqNbrs
    		Counter,
    	    wfVinesIfNumSeqNbrs
    		Counter,
    	    wfVinesIfRedirectEnable
    		INTEGER
        }

    wfVinesIfDelete OBJECT-TYPE
        SYNTAX	INTEGER {
    		    created(1),
    		    deleted(2)
    		}
        ACCESS	read-write
        STATUS	mandatory
        DESCRIPTION
                "Create/Delete parameter.  Users perform an SNMP set command to
                create/delete a VINES interface. "
        DEFVAL	{ created }
        ::= { wfVinesIfEntry 1 }

    wfVinesIfDisable OBJECT-TYPE
        SYNTAX	INTEGER {
    		    enabled(1),
    		    disabled(2)
    		}
        ACCESS	read-write
        STATUS	mandatory
        DESCRIPTION
                "Enable/Disable parameter.  Users perform an SNMP set command to
                enable/disable a VINES interface. "
        DEFVAL	{ enabled }
        ::= { wfVinesIfEntry 2 }

    wfVinesIfState OBJECT-TYPE
        SYNTAX	INTEGER {
    		    up(1),
    		    down(2),
    		    init(3),
    		    notpresent(4)
    		}
        ACCESS	read-only
        STATUS	mandatory
        DESCRIPTION
                "This parameter reflects the current state of the VINES interface."
        DEFVAL	{ notpresent }
        ::= { wfVinesIfEntry 3 }

    wfVinesIfSlot OBJECT-TYPE
        SYNTAX	INTEGER
        ACCESS	read-only
        STATUS	mandatory
        DESCRIPTION
                "The slot on which this interface is configured."
        ::= { wfVinesIfEntry 4 }

    wfVinesIfLine OBJECT-TYPE
        SYNTAX	INTEGER
        ACCESS	read-only
        STATUS	mandatory
        DESCRIPTION
                "The line on which this interface is configured."
        ::= { wfVinesIfEntry 5 }

    wfVinesIfCct OBJECT-TYPE
        SYNTAX	INTEGER
        ACCESS	read-only
        STATUS	mandatory
        DESCRIPTION
                "The circuit number for this interface."
        ::= { wfVinesIfEntry 6 }

    wfVinesIfSession OBJECT-TYPE
        SYNTAX	INTEGER
        ACCESS	read-only
        STATUS	mandatory
        DESCRIPTION
                "The session number for this interface."
        ::= { wfVinesIfEntry 7 }

    wfVinesIfType OBJECT-TYPE
        SYNTAX	INTEGER {
    		    enet(1),
    		    tr4k(2),
    		    tr16k(3),
    		    hdlc1200(4),
    		    hdlc4800(5),
    		    hdlc9600(6),
    		    hdlc56000(7),
    		    async1200(8),
    		    async4800(9),
    		    async9600(10),
    		    async56000(11),
    		    x251200(12),
    		    x254800(13),
    		    x259600(14),
    		    x2556000(15),
    		    t145k(16),
    		    t1128k(17),
    		    t1192k(18),
    		    t1256k(19),
    		    t1320k(20),
    		    t1384k(21),
    		    t1448k(22),
    		    t1512k(23),
    		    t1576k(24),
    		    t1640k(25),
    		    t1704k(26),
    		    t1896k(27),
    		    t11088k(28),
    		    t11344k(29),
    		    tunnel(30),
    		    fddi(31)
    		}
        ACCESS	read-write
        STATUS	mandatory
        DESCRIPTION
                "The type of interface this is."
        DEFVAL	{ enet }
        ::= { wfVinesIfEntry 8 }

    wfVinesIfDescr OBJECT-TYPE
        SYNTAX	OCTET STRING
        ACCESS	read-only
        STATUS	mandatory
        DESCRIPTION
                "Description of this interface."
        ::= { wfVinesIfEntry 9 }

    wfVinesIfAdr OBJECT-TYPE
        SYNTAX	OCTET STRING
        ACCESS	read-only
        STATUS	mandatory
        DESCRIPTION
                "The MAC address of this interface."
        ::= { wfVinesIfEntry 10 }

    wfVinesIfDodIpDisable OBJECT-TYPE
        SYNTAX	INTEGER {
    		    enabled(1),
    		    disabled(2)
    		}
        ACCESS	read-write
        STATUS	mandatory
        DESCRIPTION
                "This parameter indicates if this interface is enabled to  encapsulate
                VINES packets over DoD IP."
        DEFVAL	{ disabled }
        ::= { wfVinesIfEntry 11 }

    wfVinesIfArpDisable OBJECT-TYPE
        SYNTAX	INTEGER {
    		    enabled(1),
    		    disabled(2)
    		}
        ACCESS	read-write
        STATUS	mandatory
        DESCRIPTION
                "This parameter indicates if this interface is enabled to support
                VINES ARP. "
        DEFVAL	{ disabled }
        ::= { wfVinesIfEntry 12 }

    wfVinesIfTrEndStation OBJECT-TYPE
        SYNTAX	INTEGER {
    		    enabled(1),
    		    disabled(2)
    		}
        ACCESS	read-write
        STATUS	mandatory
        DESCRIPTION
                "This parameter indicates if this interface is enabled for source
                routing end station support. "
        DEFVAL	{ disabled }
        ::= { wfVinesIfEntry 13 }

    wfVinesIfInPkts OBJECT-TYPE
        SYNTAX	Counter
        ACCESS	read-only
        STATUS	mandatory
        DESCRIPTION
                "The number of packets received on this interface."
        ::= { wfVinesIfEntry 14 }

    wfVinesIfInErrs OBJECT-TYPE
        SYNTAX	Counter
        ACCESS	read-only
        STATUS	mandatory
        DESCRIPTION
                "The number of packets received with errors."
        ::= { wfVinesIfEntry 15 }

    wfVinesIfOutPkts OBJECT-TYPE
        SYNTAX	Counter
        ACCESS	read-only
        STATUS	mandatory
        DESCRIPTION
                "The number of packets transmitted on this interface."
        ::= { wfVinesIfEntry 16 }

    wfVinesIfOutErrs OBJECT-TYPE
        SYNTAX	Counter
        ACCESS	read-only
        STATUS	mandatory
        DESCRIPTION
                "The number of errors on packets transmitted."
        ::= { wfVinesIfEntry 17 }

    wfVinesIfInMsgs OBJECT-TYPE
        SYNTAX	Counter
        ACCESS	read-only
        STATUS	mandatory
        DESCRIPTION
                "The number of messages received on this interface."
        ::= { wfVinesIfEntry 18 }

    wfVinesIfMux OBJECT-TYPE
        SYNTAX	INTEGER {
    		    enet(1),
    		    snap(2)
    		}
        ACCESS	read-write
        STATUS	mandatory
        DESCRIPTION
                "Muxing scheme for this interface.  VINES currently only supports
                Ethernet encapsulation, but they plan to switch to SNAP."
        DEFVAL	{ enet }
        ::= { wfVinesIfEntry 19 }

    wfVinesIfFwdDrops OBJECT-TYPE
        SYNTAX	Counter
        ACCESS	read-only
        STATUS	mandatory
        DESCRIPTION
                "The number of pakets that were dropped because of no forwarding
                information for the destination."
        ::= { wfVinesIfEntry 20 }

    wfVinesIfZeroHopDrops OBJECT-TYPE
        SYNTAX	Counter
        ACCESS	read-only
        STATUS	mandatory
        DESCRIPTION
                "The number of pakets that were dropped because of a zero hop count."
        ::= { wfVinesIfEntry 21 }

    wfVinesIfIcpInErrorNotifs OBJECT-TYPE
        SYNTAX	Counter
        ACCESS	read-only
        STATUS	mandatory
        DESCRIPTION
                "The number of ICP error notification packets received."
        ::= { wfVinesIfEntry 22 }

    wfVinesIfIcpInMetricNotifs OBJECT-TYPE
        SYNTAX	Counter
        ACCESS	read-only
        STATUS	mandatory
        DESCRIPTION
                "The number of ICP metric notification packets received."
        ::= { wfVinesIfEntry 23 }

    wfVinesIfIcpInErrors OBJECT-TYPE
        SYNTAX	Counter
        ACCESS	read-only
        STATUS	mandatory
        DESCRIPTION
                "The number of ICP packets received with errors."
        ::= { wfVinesIfEntry 24 }

    wfVinesIfIcpOutErrorNotifs OBJECT-TYPE
        SYNTAX	Counter
        ACCESS	read-only
        STATUS	mandatory
        DESCRIPTION
                "The number of ICP error notification packets transmitted."
        ::= { wfVinesIfEntry 25 }

    wfVinesIfIcpOutMetricNotifs OBJECT-TYPE
        SYNTAX	Counter
        ACCESS	read-only
        STATUS	mandatory
        DESCRIPTION
                "The number of ICP metric notification packets transmitted."
        ::= { wfVinesIfEntry 26 }

    wfVinesIfArpInQueries OBJECT-TYPE
        SYNTAX	Counter
        ACCESS	read-only
        STATUS	mandatory
        DESCRIPTION
                "The number of ARP queries received."
        ::= { wfVinesIfEntry 27 }

    wfVinesIfArpInAssgReqs OBJECT-TYPE
        SYNTAX	Counter
        ACCESS	read-only
        STATUS	mandatory
        DESCRIPTION
                "The number of ARP assignment requests received."
        ::= { wfVinesIfEntry 28 }

    wfVinesIfArpInErrors OBJECT-TYPE
        SYNTAX	Counter
        ACCESS	read-only
        STATUS	mandatory
        DESCRIPTION
                "The number of ARP packets received with errors."
        ::= { wfVinesIfEntry 29 }

    wfVinesIfArpOutServRsps OBJECT-TYPE
        SYNTAX	Counter
        ACCESS	read-only
        STATUS	mandatory
        DESCRIPTION
                "The number of ARP service responses sent."
        ::= { wfVinesIfEntry 30 }

    wfVinesIfArpOutAssgRsps OBJECT-TYPE
        SYNTAX	Counter
        ACCESS	read-only
        STATUS	mandatory
        DESCRIPTION
                "The number of ARP assignment responses sent."
        ::= { wfVinesIfEntry 31 }

    wfVinesIfInRedirects OBJECT-TYPE
        SYNTAX	Counter
        ACCESS	read-only
        STATUS	mandatory
        DESCRIPTION
                "The number of Redirect packets received."
        ::= { wfVinesIfEntry 32 }

    wfVinesIfOutRedirects OBJECT-TYPE
        SYNTAX	Counter
        ACCESS	read-only
        STATUS	mandatory
        DESCRIPTION
                "The number of Redirect packets sent."
        ::= { wfVinesIfEntry 33 }

    wfVinesIfEchoInPkts OBJECT-TYPE
        SYNTAX	Counter
        ACCESS	read-only
        STATUS	mandatory
        DESCRIPTION
                "The number of Echo packets received."
        ::= { wfVinesIfEntry 34 }

    wfVinesIfEchoOutPkts OBJECT-TYPE
        SYNTAX	Counter
        ACCESS	read-only
        STATUS	mandatory
        DESCRIPTION
                "The number of Echo packets sent."
        ::= { wfVinesIfEntry 35 }

    wfVinesIfReassFails OBJECT-TYPE
        SYNTAX	Counter
        ACCESS	read-only
        STATUS	mandatory
        DESCRIPTION
                "The number of packet reassemblies that failed."
        ::= { wfVinesIfEntry 36 }

    wfVinesIfRemClientPrivDisable OBJECT-TYPE
        SYNTAX	INTEGER {
    		    enabled(1),
    		    disabled(2)
    		}
        ACCESS	read-write
        STATUS	mandatory
        DESCRIPTION
                "This parameter indicates that this interface will allow remote
                clients privileges on this segment.  This means that a client
                is not restricted to being within one hop of a VINES server. "
        DEFVAL	{ disabled }
        ::= { wfVinesIfEntry 37 }

    wfVinesIfSplitHorizonDisable OBJECT-TYPE
        SYNTAX	INTEGER {
    		    enabled(1),
    		    disabled(2)
    		}
        ACCESS	read-write
        STATUS	mandatory
        DESCRIPTION
                "Split Horizon"
        DEFVAL	{ disabled }
        ::= { wfVinesIfEntry 38 }

    wfVinesIfCost OBJECT-TYPE
        SYNTAX	INTEGER
        ACCESS	read-write
        STATUS	obsolete
        DESCRIPTION
                "The Interface Cost
                The default is null - meaning use the Banyan specified cost.
                Otherwise, the configured value wfVinesIfCfgCost will be used."
        ::= { wfVinesIfEntry 39 }

    wfVinesIfSyncPortNumber OBJECT-TYPE
        SYNTAX	INTEGER
        ACCESS	read-write
        STATUS	obsolete
        DESCRIPTION
                "The Sync port number required to determine number of RTP
                packets sent for each network.  It can only take a value
                between 1 - 4.  It correspond to the Sync port number on this
                slot only.
                If it is 4.2 for example, then the port number should be 2."
        ::= { wfVinesIfEntry 40 }

    wfVinesIfInLackRescError OBJECT-TYPE
        SYNTAX	Counter
        ACCESS	read-only
        STATUS	mandatory
        DESCRIPTION
                "Failed to duplicate packet due to lack of resource."
        ::= { wfVinesIfEntry 41 }

    wfVinesIfOutLackRescError OBJECT-TYPE
        SYNTAX	Counter
        ACCESS	read-only
        STATUS	mandatory
        DESCRIPTION
                "Failed to duplicate packet due to lack of resource."
        ::= { wfVinesIfEntry 42 }

    wfVinesIfRtpRecv OBJECT-TYPE
        SYNTAX	Counter
        ACCESS	read-only
        STATUS	mandatory
        DESCRIPTION
                "The number of RTP packets received."
        ::= { wfVinesIfEntry 43 }

    wfVinesIfRtpSent OBJECT-TYPE
        SYNTAX	Counter
        ACCESS	read-only
        STATUS	mandatory
        DESCRIPTION
                "The number of RTP packets sent."
        ::= { wfVinesIfEntry 44 }

    wfVinesIfSMDSGroupAddress OBJECT-TYPE
        SYNTAX	OCTET STRING
        ACCESS	read-write
        STATUS	mandatory
        DESCRIPTION
                "Configurable SMDS broadcast address"
        ::= { wfVinesIfEntry 45 }

    wfVinesIfFRBcastDlci OBJECT-TYPE
        SYNTAX	OCTET STRING
        ACCESS	read-write
        STATUS	mandatory
        DESCRIPTION
                "Configurable FRAME RELAY broadcast address"
        ::= { wfVinesIfEntry 46 }

    wfVinesIfCfgAdr OBJECT-TYPE
        SYNTAX	OCTET STRING
        ACCESS	read-write
        STATUS	mandatory
        DESCRIPTION
                "The configured MAC address of this interface."
        ::= { wfVinesIfEntry 47 }

    wfVinesIfNumRoutes OBJECT-TYPE
        SYNTAX	Counter
        ACCESS	read-only
        STATUS	obsolete
        DESCRIPTION
                "Number of routes cached in the forwarding table"
        ::= { wfVinesIfEntry 48 }

    wfVinesIfCfgCost OBJECT-TYPE
        SYNTAX	INTEGER
        ACCESS	read-write
        STATUS	mandatory
        DESCRIPTION
                "The configured interface cost"
        ::= { wfVinesIfEntry 49 }

    wfVinesIfCostUsed OBJECT-TYPE
        SYNTAX	INTEGER
        ACCESS	read-only
        STATUS	mandatory
        DESCRIPTION
                "The Interface Cost used by the router"
        ::= { wfVinesIfEntry 50 }

    wfVinesIfFrpEnable OBJECT-TYPE
        SYNTAX	INTEGER {
    		    enabled(1),
    		    disabled(2)
    		}
        ACCESS	read-write
        STATUS	mandatory
        DESCRIPTION
                "Parameter to indicate whether this interface is to support
                the use of FRP header "
        DEFVAL	{ enabled }
        ::= { wfVinesIfEntry 51 }

    wfVinesIfSeqArpInQueries OBJECT-TYPE
        SYNTAX	Counter
        ACCESS	read-only
        STATUS	mandatory
        DESCRIPTION
                "The number of Sequenced ARP queries received."
        ::= { wfVinesIfEntry 52 }

    wfVinesIfSeqArpInAssgReqs OBJECT-TYPE
        SYNTAX	Counter
        ACCESS	read-only
        STATUS	mandatory
        DESCRIPTION
                "The number of Sequenced ARP assignment requests received."
        ::= { wfVinesIfEntry 53 }

    wfVinesIfSeqArpInErrors OBJECT-TYPE
        SYNTAX	Counter
        ACCESS	read-only
        STATUS	mandatory
        DESCRIPTION
                "The number of Sequenced ARP packets received with errors."
        ::= { wfVinesIfEntry 54 }

    wfVinesIfSeqArpOutServRsps OBJECT-TYPE
        SYNTAX	Counter
        ACCESS	read-only
        STATUS	mandatory
        DESCRIPTION
                "The number of Sequenced ARP service responses sent."
        ::= { wfVinesIfEntry 55 }

    wfVinesIfSeqArpOutAssgRsps OBJECT-TYPE
        SYNTAX	Counter
        ACCESS	read-only
        STATUS	mandatory
        DESCRIPTION
                "The number of Sequenced ARP assignment responses sent."
        ::= { wfVinesIfEntry 56 }

    wfVinesIfInSeqRedirects OBJECT-TYPE
        SYNTAX	Counter
        ACCESS	read-only
        STATUS	mandatory
        DESCRIPTION
                "The number of Sequenced Redirect packets received."
        ::= { wfVinesIfEntry 57 }

    wfVinesIfOutSeqRedirects OBJECT-TYPE
        SYNTAX	Counter
        ACCESS	read-only
        STATUS	mandatory
        DESCRIPTION
                "The number of Sequenced Redirect packets sent."
        ::= { wfVinesIfEntry 58 }

    wfVinesIfSeqRtpRecv OBJECT-TYPE
        SYNTAX	Counter
        ACCESS	read-only
        STATUS	mandatory
        DESCRIPTION
                "The number of RTP packets received."
        ::= { wfVinesIfEntry 59 }

    wfVinesIfSeqRtpSent OBJECT-TYPE
        SYNTAX	Counter
        ACCESS	read-only
        STATUS	mandatory
        DESCRIPTION
                "The number of RTP packets sent."
        ::= { wfVinesIfEntry 60 }

    wfVinesIfRtpGenerationDisable OBJECT-TYPE
        SYNTAX	INTEGER {
    		    enabled(1),
    		    disabled(2)
    		}
        ACCESS	read-write
        STATUS	mandatory
        DESCRIPTION
                "This parameter will be used to disable the RTP generation on
                an interface, where static routes may be configured"
        DEFVAL	{ enabled }
        ::= { wfVinesIfEntry 61 }

    wfVinesIfInverseArpEnable OBJECT-TYPE
        SYNTAX	INTEGER {
    		    enabled(1),
    		    disabled(2)
    		}
        ACCESS	read-write
        STATUS	mandatory
        DESCRIPTION
                "This is to enable the use of Inverse ARP protocol to learn
                nbrs in a Frame Relay/ATM network when a new dlci comes up"
        DEFVAL	{ disabled }
        ::= { wfVinesIfEntry 62 }

    wfVinesIfSTalkSplitHorizon OBJECT-TYPE
        SYNTAX	INTEGER {
    		    enabled(1),
    		    disabled(2)
    		}
        ACCESS	read-write
        STATUS	mandatory
        DESCRIPTION
                "This is to disable the use of split horizon for STALK
                packets so as to support a partially meshed Frame Relay
                Network for VINES"
        DEFVAL	{ enabled }
        ::= { wfVinesIfEntry 63 }

    wfVinesIfPermWanNbr OBJECT-TYPE
        SYNTAX	INTEGER {
    		    enabled(1),
    		    disabled(2)
    		}
        ACCESS	read-write
        STATUS	mandatory
        DESCRIPTION
                "This is to enable the use of Permanent Non sequenced Nbrs
                for Non sequenced neighbors over a WAN link, so that
                these are not aged every 1 hour, when using Automode/Sequenced Mode."
        DEFVAL	{ disabled }
        ::= { wfVinesIfEntry 64 }

    wfVinesIfNumFwdEntries OBJECT-TYPE
        SYNTAX	Counter
        ACCESS	read-only
        STATUS	mandatory
        DESCRIPTION
                "This counts the number of forwarding entries on this
                interface"
        ::= { wfVinesIfEntry 65 }

    wfVinesIfNumNonSeqNbrs OBJECT-TYPE
        SYNTAX	Counter
        ACCESS	read-only
        STATUS	mandatory
        DESCRIPTION
                "This counts the number of Non sequenced Nbrs"
        ::= { wfVinesIfEntry 66 }

    wfVinesIfNumSeqNbrs OBJECT-TYPE
        SYNTAX	Counter
        ACCESS	read-only
        STATUS	mandatory
        DESCRIPTION
                "This counts the number of sequenced Nbrs"
        ::= { wfVinesIfEntry 67 }

    wfVinesIfRedirectEnable OBJECT-TYPE
        SYNTAX	INTEGER {
    		    enabled(1),
    		    disabled(2)
    		}
        ACCESS	read-write
        STATUS	mandatory
        DESCRIPTION
                "Parameter to indicate whether this interface is to 
                generate RTP redirect packets "
        DEFVAL	{ enabled }
        ::= { wfVinesIfEntry 68 }

    wfVinesIfX25VC	OBJECT IDENTIFIER ::= { wfVinesGroup 9 }

    wfVinesIfX25VCNumber OBJECT-TYPE
        SYNTAX	INTEGER
        ACCESS	read-only
        STATUS	mandatory
        DESCRIPTION
                "This is the number of entries in the X.25 Virtual Circuit Table."
        ::= { wfVinesIfX25VC 1 }

    wfVinesIfX25VCTable OBJECT-TYPE
        SYNTAX	SEQUENCE OF WfVinesIfX25VCEntry
        ACCESS	not-accessible
        STATUS	mandatory
        DESCRIPTION
                "This is the Table of X.25 Virtual Circuits."
        ::= { wfVinesGroup 10 }

    wfVinesIfX25VCEntry OBJECT-TYPE
        SYNTAX	WfVinesIfX25VCEntry
        ACCESS	not-accessible
        STATUS	mandatory
        DESCRIPTION
                "An entry in the Table of X.25 Virtual Circuits."
        INDEX	{ wfVinesIfX25VCCct }
        ::= { wfVinesIfX25VCTable 1 }

    WfVinesIfX25VCEntry ::= SEQUENCE {
    	    wfVinesIfX25VCSlot
    		INTEGER,
    	    wfVinesIfX25VCLine
    		INTEGER,
    	    wfVinesIfX25VCCct
    		INTEGER,
    	    wfVinesIfX25VCSession
    		INTEGER,
    	    wfVinesIfX25VCTotIn
    		Counter,
    	    wfVinesIfX25VCTotOut
    		Counter,
    	    wfVinesIfX25VCInErrs
    		Counter,
    	    wfVinesIfX25VCOutErrs
    		Counter,
    	    wfVinesIfX25VCPktsOut
    		Counter,
    	    wfVinesIfX25VCPktsAwaitAck
    		INTEGER,
    	    wfVinesIfX25VCBytesOut
    		Counter,
    	    wfVinesIfX25VCBytesAwaitAck
    		INTEGER,
    	    wfVinesIfX25VCPktsIn
    		Counter,
    	    wfVinesIfX25VCBytesIn
    		Counter,
    	    wfVinesIfX25VCResetsIn
    		Counter,
    	    wfVinesIfX25VCResetsOut
    		Counter
        }

    wfVinesIfX25VCSlot OBJECT-TYPE
        SYNTAX	INTEGER
        ACCESS	read-only
        STATUS	mandatory
        DESCRIPTION
                "The number of the slot in which the card is installed."
        ::= { wfVinesIfX25VCEntry 1 }

    wfVinesIfX25VCLine OBJECT-TYPE
        SYNTAX	INTEGER
        ACCESS	read-only
        STATUS	mandatory
        DESCRIPTION
                "For a serial line, this is the number of the line on the card."
        ::= { wfVinesIfX25VCEntry 2 }

    wfVinesIfX25VCCct OBJECT-TYPE
        SYNTAX	INTEGER
        ACCESS	read-only
        STATUS	mandatory
        DESCRIPTION
                "Local circuit number for this Virtual Circuit."
        ::= { wfVinesIfX25VCEntry 3 }

    wfVinesIfX25VCSession OBJECT-TYPE
        SYNTAX	INTEGER
        ACCESS	read-only
        STATUS	mandatory
        DESCRIPTION
                "Local session number for this Virtual Circuit."
        ::= { wfVinesIfX25VCEntry 4 }

    wfVinesIfX25VCTotIn OBJECT-TYPE
        SYNTAX	Counter
        ACCESS	read-only
        STATUS	mandatory
        DESCRIPTION
                "The total number of VINES IP packets received on this VC.
                Depending on the size of the X.25 packets received, more than one
                X.25 packet can make up a VINES IP packet."
        ::= { wfVinesIfX25VCEntry 5 }

    wfVinesIfX25VCTotOut OBJECT-TYPE
        SYNTAX	Counter
        ACCESS	read-only
        STATUS	mandatory
        DESCRIPTION
                "The total number of VINES IP packets sent on this VC.  Depending
                on the size of the X.25 packets sent, more than one X.25 packet can
                make up a VINES IP packet."
        ::= { wfVinesIfX25VCEntry 6 }

    wfVinesIfX25VCInErrs OBJECT-TYPE
        SYNTAX	Counter
        ACCESS	read-only
        STATUS	mandatory
        DESCRIPTION
                "The total number of input errors."
        ::= { wfVinesIfX25VCEntry 7 }

    wfVinesIfX25VCOutErrs OBJECT-TYPE
        SYNTAX	Counter
        ACCESS	read-only
        STATUS	mandatory
        DESCRIPTION
                "The total number of output errors."
        ::= { wfVinesIfX25VCEntry 8 }

    wfVinesIfX25VCPktsOut OBJECT-TYPE
        SYNTAX	Counter
        ACCESS	read-only
        STATUS	mandatory
        DESCRIPTION
                "The total number of X.25 packets transmitted on this VC."
        ::= { wfVinesIfX25VCEntry 9 }

    wfVinesIfX25VCPktsAwaitAck OBJECT-TYPE
        SYNTAX	INTEGER
        ACCESS	read-only
        STATUS	mandatory
        DESCRIPTION
                "Total number of X.25 packets transmitted on this VC waiting for ACK."
        ::= { wfVinesIfX25VCEntry 10 }

    wfVinesIfX25VCBytesOut OBJECT-TYPE
        SYNTAX	Counter
        ACCESS	read-only
        STATUS	mandatory
        DESCRIPTION
                "Total Bytes transmitted on this VC."
        ::= { wfVinesIfX25VCEntry 11 }

    wfVinesIfX25VCBytesAwaitAck OBJECT-TYPE
        SYNTAX	INTEGER
        ACCESS	read-only
        STATUS	mandatory
        DESCRIPTION
                "Total bytes transmitted on this VC that are waiting for ACK."
        ::= { wfVinesIfX25VCEntry 12 }

    wfVinesIfX25VCPktsIn OBJECT-TYPE
        SYNTAX	Counter
        ACCESS	read-only
        STATUS	mandatory
        DESCRIPTION
                "Total X.25 packets received on this VC."
        ::= { wfVinesIfX25VCEntry 13 }

    wfVinesIfX25VCBytesIn OBJECT-TYPE
        SYNTAX	Counter
        ACCESS	read-only
        STATUS	mandatory
        DESCRIPTION
                "Total Bytes received on this VC."
        ::= { wfVinesIfX25VCEntry 14 }

    wfVinesIfX25VCResetsIn OBJECT-TYPE
        SYNTAX	Counter
        ACCESS	read-only
        STATUS	mandatory
        DESCRIPTION
                "Number of X.25 reset packets received on this VC."
        ::= { wfVinesIfX25VCEntry 15 }

    wfVinesIfX25VCResetsOut OBJECT-TYPE
        SYNTAX	Counter
        ACCESS	read-only
        STATUS	mandatory
        DESCRIPTION
                "Number of X.25 reset packets transmitted on this VC."
        ::= { wfVinesIfX25VCEntry 16 }

    wfVinesTrafficFilterTable OBJECT-TYPE
        SYNTAX	SEQUENCE OF WfVinesTrafficFilterEntry
        ACCESS	not-accessible
        STATUS	mandatory
        DESCRIPTION
                "VINES Traffic Filters"
        ::= { wfVinesGroup 11 }

    wfVinesTrafficFilterEntry OBJECT-TYPE
        SYNTAX	WfVinesTrafficFilterEntry
        ACCESS	not-accessible
        STATUS	mandatory
        DESCRIPTION
                "An entry in WfVinesTrafficFilterTable."
        INDEX	{ wfVinesTrafficFilterCircuit,
    		  wfVinesTrafficFilterRuleNumber,
    		  wfVinesTrafficFilterFragment }
        ::= { wfVinesTrafficFilterTable 1 }

    WfVinesTrafficFilterEntry ::= SEQUENCE {
    	    wfVinesTrafficFilterCreate
    		INTEGER,
    	    wfVinesTrafficFilterEnable
    		INTEGER,
    	    wfVinesTrafficFilterStatus
    		INTEGER,
    	    wfVinesTrafficFilterCounter
    		Counter,
    	    wfVinesTrafficFilterDefinition
    		OCTET STRING,
    	    wfVinesTrafficFilterReserved
    		INTEGER,
    	    wfVinesTrafficFilterCircuit
    		INTEGER,
    	    wfVinesTrafficFilterRuleNumber
    		INTEGER,
    	    wfVinesTrafficFilterFragment
    		INTEGER,
    	    wfVinesTrafficFilterName
    		DisplayString
        }

    wfVinesTrafficFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfVinesTrafficFilterEntry 1 }

    wfVinesTrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfVinesTrafficFilterEntry 2 }

    wfVinesTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfVinesTrafficFilterEntry 3 }

    wfVinesTrafficFilterCounter OBJECT-TYPE
        SYNTAX	Counter
        ACCESS	read-only
        STATUS	mandatory
        DESCRIPTION
                "The number of received packets that have
                matched this rule."
        ::= { wfVinesTrafficFilterEntry 4 }

    wfVinesTrafficFilterDefinition OBJECT-TYPE
        SYNTAX	OCTET STRING
        ACCESS	read-write
        STATUS	mandatory
        DESCRIPTION
                "The filter rule definition."
        ::= { wfVinesTrafficFilterEntry 5 }

    wfVinesTrafficFilterReserved OBJECT-TYPE
        SYNTAX	INTEGER
        ACCESS	read-only
        STATUS	mandatory
        DESCRIPTION
                "Reserved field."
        ::= { wfVinesTrafficFilterEntry 6 }

    wfVinesTrafficFilterCircuit OBJECT-TYPE
        SYNTAX	INTEGER
        ACCESS	read-only
        STATUS	mandatory
        DESCRIPTION
                "The ID of the Circuit to which the
                filter is applied."
        ::= { wfVinesTrafficFilterEntry 7 }

    wfVinesTrafficFilterRuleNumber OBJECT-TYPE
        SYNTAX	INTEGER
        ACCESS	read-only
        STATUS	mandatory
        DESCRIPTION
                "ID for the rule."
        ::= { wfVinesTrafficFilterEntry 8 }

    wfVinesTrafficFilterFragment OBJECT-TYPE
        SYNTAX	INTEGER
        ACCESS	read-only
        STATUS	mandatory
        DESCRIPTION
                "Fragment number - for large rules."
        ::= { wfVinesTrafficFilterEntry 9 }

    wfVinesTrafficFilterName OBJECT-TYPE
        SYNTAX	DisplayString
        ACCESS	read-write
        STATUS	mandatory
        DESCRIPTION
                "Name of the rule number."
        ::= { wfVinesTrafficFilterEntry 10 }

    wfVinesNameTable OBJECT-TYPE
        SYNTAX	SEQUENCE OF WfVinesNameEntry
        ACCESS	not-accessible
        STATUS	mandatory
        DESCRIPTION
                "This is the Name-to-Address Binding Table."
        ::= { wfVinesGroup 12 }

    wfVinesNameEntry OBJECT-TYPE
        SYNTAX	WfVinesNameEntry
        ACCESS	not-accessible
        STATUS	mandatory
        DESCRIPTION
                "An entry in the Table of Names."
        INDEX	{ wfVinesNameNetid }
        ::= { wfVinesNameTable 1 }

    WfVinesNameEntry ::= SEQUENCE {
    	    wfVinesNameDelete
    		INTEGER,
    	    wfVinesNameDisable
    		INTEGER,
    	    wfVinesNameNetid
    		Counter,
    	    wfVinesNameHost
    		DisplayString,
    	    wfVinesNameSubNetid
    		INTEGER
        }

    wfVinesNameDelete OBJECT-TYPE
        SYNTAX	INTEGER {
    		    created(1),
    		    deleted(2)
    		}
        ACCESS	read-write
        STATUS	mandatory
        DESCRIPTION
                "Create/Delete parameter.  Users perform an SNMP set command to
                create/delete this name. "
        DEFVAL	{ created }
        ::= { wfVinesNameEntry 1 }

    wfVinesNameDisable OBJECT-TYPE
        SYNTAX	INTEGER {
    		    enabled(1),
    		    disabled(2)
    		}
        ACCESS	read-write
        STATUS	mandatory
        DESCRIPTION
                "Enable/Disable parameter.  Users perform an SNMP set command to
                enable/disable a name. "
        DEFVAL	{ enabled }
        ::= { wfVinesNameEntry 2 }

    wfVinesNameNetid OBJECT-TYPE
        SYNTAX	Counter
        ACCESS	read-only
        STATUS	mandatory
        DESCRIPTION
                "This is the network number for the host."
        ::= { wfVinesNameEntry 3 }

    wfVinesNameHost OBJECT-TYPE
        SYNTAX	DisplayString
        ACCESS	read-write
        STATUS	mandatory
        DESCRIPTION
                "This is the name of the host."
        ::= { wfVinesNameEntry 4 }

    wfVinesNameSubNetid OBJECT-TYPE
        SYNTAX	INTEGER
        ACCESS	read-write
        STATUS	mandatory
        DESCRIPTION
                "This is the subnetwork number for the host."
        ::= { wfVinesNameEntry 5 }

    wfVinesArp	OBJECT IDENTIFIER ::= { wfVinesGroup 13 }

    wfVinesArpDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete ARP."
        DEFVAL	{ created }
        ::= { wfVinesArp 1 }

    wfVinesArpDisable OBJECT-TYPE
        SYNTAX	INTEGER {
    		    enabled(1),
    		    disabled(2)
    		}
        ACCESS	read-write
        STATUS	mandatory
        DESCRIPTION
                "Enable/Disable Parameter indicates whether
                this ARP record is enabled or disabled."
        DEFVAL	{ enabled }
        ::= { wfVinesArp 2 }

    wfVinesArpState OBJECT-TYPE
        SYNTAX	INTEGER {
    		    up(1),
    		    down(2)
    		}
        ACCESS	read-only
        STATUS	mandatory
        DESCRIPTION
                "State of ARP."
        DEFVAL	{ down }
        ::= { wfVinesArp 3 }

    wfVinesArpSubnetid OBJECT-TYPE
        SYNTAX	INTEGER
        ACCESS	read-only
        STATUS	mandatory
        DESCRIPTION
                "The next subnetwork ID to be assigned. "
        ::= { wfVinesArp 4 }

    wfVinesArpSubnetBlock OBJECT-TYPE
        SYNTAX	INTEGER(1..32)
        ACCESS	read-write
        STATUS	mandatory
        DESCRIPTION
                "The size of the block of subnet ids a slot can grab. "
        DEFVAL	{ 2 }
        ::= { wfVinesArp 5 }

    wfVinesArpAssignDeniedPkts OBJECT-TYPE
        SYNTAX	Counter
        ACCESS	read-only
        STATUS	mandatory
        DESCRIPTION
                "Number of ARP Assignment packets received for which we
                didn't have a free subnet number."
        ::= { wfVinesArp 6 }

    wfVinesSeqRtpNbr	OBJECT IDENTIFIER ::= { wfVinesGroup 14 }

    wfVinesSeqRtpNbrNumber OBJECT-TYPE
        SYNTAX	INTEGER
        ACCESS	read-only
        STATUS	mandatory
        DESCRIPTION
                "Number of entries in the Table of 5.5 Neighbors."
        ::= { wfVinesSeqRtpNbr 1 }

    wfVinesAggrStats	OBJECT IDENTIFIER ::= { wfVinesGroup 15 }

    wfVinesAggrInPkts OBJECT-TYPE
        SYNTAX	Counter
        ACCESS	read-only
        STATUS	mandatory
        DESCRIPTION
                "The total number of packets received"
        ::= { wfVinesAggrStats 1 }

    wfVinesAggrOutPkts OBJECT-TYPE
        SYNTAX	Counter
        ACCESS	read-only
        STATUS	mandatory
        DESCRIPTION
                "The total number of datagrams sent (includes datagrams
                forwarded)"
        ::= { wfVinesAggrStats 2 }

    wfVinesAggrFwdPkts OBJECT-TYPE
        SYNTAX	Counter
        ACCESS	read-only
        STATUS	mandatory
        DESCRIPTION
                "The total number of datagrams forwarded"
        ::= { wfVinesAggrStats 3 }

    wfVinesAggrInXsumErrs OBJECT-TYPE
        SYNTAX	Counter
        ACCESS	read-only
        STATUS	mandatory
        DESCRIPTION
                "The total number of datagrams destined for a local
                entity that were dropped because of a checksum error."
        ::= { wfVinesAggrStats 4 }

    wfVinesAggrBcastPkts OBJECT-TYPE
        SYNTAX	Counter
        ACCESS	read-only
        STATUS	mandatory
        DESCRIPTION
                "The total number of broadcast packets sent (includes
                locally generated broadcasts)."
        ::= { wfVinesAggrStats 5 }

    wfVinesAggrOutNoRoutes OBJECT-TYPE
        SYNTAX	Counter
        ACCESS	read-only
        STATUS	mandatory
        DESCRIPTION
                "The total number of packets queued for transmission thet
                were discarded because the destination was unreachable."
        ::= { wfVinesAggrStats 6 }

    wfVinesAggrInHopCountErrs OBJECT-TYPE
        SYNTAX	Counter
        ACCESS	read-only
        STATUS	mandatory
        DESCRIPTION
                "The total number of pakets that were dropped because of
                a zero hop count."
        ::= { wfVinesAggrStats 7 }

    wfVinesAggrInIcpErrs OBJECT-TYPE
        SYNTAX	Counter
        ACCESS	read-only
        STATUS	mandatory
        DESCRIPTION
                "The total number of ICP error notification packets
                received."
        ::= { wfVinesAggrStats 8 }

    wfVinesAggrInIcpMetrics OBJECT-TYPE
        SYNTAX	Counter
        ACCESS	read-only
        STATUS	mandatory
        DESCRIPTION
                "The total number of ICP metric notification packets
                received."
        ::= { wfVinesAggrStats 9 }

    wfVinesAggrOutIcpErrs OBJECT-TYPE
        SYNTAX	Counter
        ACCESS	read-only
        STATUS	mandatory
        DESCRIPTION
                "The total number of ICP error notification packets
                transmitted."
        ::= { wfVinesAggrStats 10 }

    wfVinesAggrOutIcpMetrics OBJECT-TYPE
        SYNTAX	Counter
        ACCESS	read-only
        STATUS	mandatory
        DESCRIPTION
                "The total number of ICP metric notification packets
                transmitted."
        ::= { wfVinesAggrStats 11 }

    wfVinesAggrInArpQueries OBJECT-TYPE
        SYNTAX	Counter
        ACCESS	read-only
        STATUS	mandatory
        DESCRIPTION
                "The total number of ARP queries received."
        ::= { wfVinesAggrStats 12 }

    wfVinesAggrInArpAssigns OBJECT-TYPE
        SYNTAX	Counter
        ACCESS	read-only
        STATUS	mandatory
        DESCRIPTION
                "The total number of ARP assignment requests received."
        ::= { wfVinesAggrStats 13 }

    wfVinesAggrInArpErrs OBJECT-TYPE
        SYNTAX	Counter
        ACCESS	read-only
        STATUS	mandatory
        DESCRIPTION
                "The total number of ARP packets received with errors."
        ::= { wfVinesAggrStats 14 }

    wfVinesAggrOutArpServResps OBJECT-TYPE
        SYNTAX	Counter
        ACCESS	read-only
        STATUS	mandatory
        DESCRIPTION
                "The total number of ARP service responses sent."
        ::= { wfVinesAggrStats 15 }

    wfVinesAggrOutArpAssigns OBJECT-TYPE
        SYNTAX	Counter
        ACCESS	read-only
        STATUS	mandatory
        DESCRIPTION
                "The total number of ARP assignment responses sent."
        ::= { wfVinesAggrStats 16 }

    wfVinesAggrInRedirects OBJECT-TYPE
        SYNTAX	Counter
        ACCESS	read-only
        STATUS	mandatory
        DESCRIPTION
                "The total number of Redirect packets received."
        ::= { wfVinesAggrStats 17 }

    wfVinesAggrOutRedirects OBJECT-TYPE
        SYNTAX	Counter
        ACCESS	read-only
        STATUS	mandatory
        DESCRIPTION
                "The total number of Redirect packets sent."
        ::= { wfVinesAggrStats 18 }

    wfVinesAggrInEchos OBJECT-TYPE
        SYNTAX	Counter
        ACCESS	read-only
        STATUS	mandatory
        DESCRIPTION
                "The total number of Echo packets received."
        ::= { wfVinesAggrStats 19 }

    wfVinesAggrOutEchos OBJECT-TYPE
        SYNTAX	Counter
        ACCESS	read-only
        STATUS	mandatory
        DESCRIPTION
                "The total number of Echo packets sent."
        ::= { wfVinesAggrStats 20 }

    END  -- Wellfleet-VINES-MIB
