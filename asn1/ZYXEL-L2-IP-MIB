-- ZyXEL Communications Corporation
-- Private Enterprise MIB definition 
                          
-- This file describes the ZyXEL Communications Corporation Enterprise MIB.
-- It contains ZyXEL products OIDs, and common managed objects.
                             
-- $Log: ZYXEL-L2-IP-MIB.mib $ 
-- Revision 1.6  2013/12/06 07:06:20  ccho 
-- remove uncessary imports 
-- Revision 1.5  2013/11/20 06:52:30  ccho 
-- renaming identifier name for SMI.V2 
-- Revision 1.4  2013/11/06 05:41:45  ccho 
-- fix mib style 
-- Revision 1.3  2012/09/19 07:39:05  Kevin 
-- if it's leaf node, revise the vender name from zyxel to zy 
-- Revision 1.2  2012/07/05 06:23:14  Kevin 
-- 1. upgrade from SNMP to SNMPv2  
-- 2. clean warning 
-- Revision 1.1  2012/05/30 07:49:42  Kevin 
-- Initial revision 

ZYXEL-L2-IP-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579
		
	EnabledStatus
		FROM  P-BRIDGE-MIB

	IpAddress
		FROM SNMPv2-SMI

	esMgmt			
		FROM ZYXEL-ES-SMI;

	zyxelL2Ip MODULE-IDENTITY
		LAST-UPDATED	"201207010000Z"    
		ORGANIZATION "Enterprise Solution ZyXEL"     
		CONTACT-INFO
			""	   
		DESCRIPTION
			"The subtree for layer 2 switch ip address"
		::= { esMgmt 38 }		
	
	zyxelLayer2IpSetup  	OBJECT IDENTIFIER ::= { zyxelL2Ip 1 }  
--
--
--  38.zyxelL2Ip
--
--
        zyLayer2IpDnsIpAddress OBJECT-TYPE
        SYNTAX  IpAddress
        MAX-ACCESS  read-write
        STATUS  current
        DESCRIPTION
        "Enter a domain name server IP address in order to be able to use a domain name instead of an IP address."
        ::= { zyxelLayer2IpSetup 1 }
        
        zyLayer2IpDefaultMgmt OBJECT-TYPE
        SYNTAX  INTEGER {
        	inBand(0),
        	outOfBand(1)
        }
        MAX-ACCESS  read-write
        STATUS  current
        DESCRIPTION
 		"Specify which traffic flow (In-Band or Out-of-band) the switch is to send packets originating 
		 from it or packets with unknown source."
        ::= { zyxelLayer2IpSetup 2 }		

		zyxelLayer2IpInbandDefaultSetup     	OBJECT IDENTIFIER ::= { zyxelLayer2IpSetup 3 }

        zyLayer2IpInbandDefaultType OBJECT-TYPE
        SYNTAX  INTEGER {
        	dhcpClient(0),
        	staticIp(1)
        }
        MAX-ACCESS  read-write
        STATUS  current
        DESCRIPTION
        "The type of in-band IP address."
        ::= { zyxelLayer2IpInbandDefaultSetup 1 }
        
        zyLayer2IpInbandDefaultVid OBJECT-TYPE
        SYNTAX  INTEGER 
        MAX-ACCESS  read-write
        STATUS  current
        DESCRIPTION
        "The VLAN identification number associated with the switch IP address. 
		 This is the VLAN ID of the CPU and is used for management only."
        ::= { zyxelLayer2IpInbandDefaultSetup 2 }	
	
        zyLayer2IpInbandDefaultStaticIpAddress OBJECT-TYPE
        SYNTAX  IpAddress 
        MAX-ACCESS  read-write
        STATUS  current
        DESCRIPTION
        "IP address of your switch."
        ::= { zyxelLayer2IpInbandDefaultSetup 3 }	
	
        zyLayer2IpInbandDefaultStaticMask OBJECT-TYPE
        SYNTAX  IpAddress 
        MAX-ACCESS  read-write
        STATUS  current
        DESCRIPTION
        "The IP subnet mask of your switch."
        ::= { zyxelLayer2IpInbandDefaultSetup 4 }	

        zyLayer2IpInbandDefaultStaticGateway OBJECT-TYPE
        SYNTAX  IpAddress 
        MAX-ACCESS  read-write
        STATUS  current
        DESCRIPTION
		"IP address of the default outgoing gateway."
        ::= { zyxelLayer2IpInbandDefaultSetup 5 }	

        zyLayer2IpInbandMaxNumberOfInterfaces OBJECT-TYPE
        SYNTAX  INTEGER
        MAX-ACCESS  read-only
        STATUS  current
        DESCRIPTION
		"The maximum number of in-band IP that can be created."
        ::= { zyxelLayer2IpSetup 4 }

--  zyxelLayer2IpInbandTable
        zyxelLayer2IpInbandTable	OBJECT-TYPE
        SYNTAX	SEQUENCE OF ZyxelLayer2IpInbandEntry
        MAX-ACCESS  not-accessible
        STATUS  current
        DESCRIPTION
		"The table contains layer 2 IP in-band configuration. "
        ::= { zyxelLayer2IpSetup 5 }
        
	zyxelLayer2IpInbandEntry OBJECT-TYPE
        SYNTAX	ZyxelLayer2IpInbandEntry
        MAX-ACCESS	not-accessible
        STATUS	current
        DESCRIPTION    	
        "An entry contains layer 2 IP in-band configuration. "
        INDEX          	{ zyLayer2IpInbandIpAddress, zyLayer2IpInbandVid }
        ::= { zyxelLayer2IpInbandTable 1 }

        ZyxelLayer2IpInbandEntry ::=
		SEQUENCE {
        	zyLayer2IpInbandIpAddress		IpAddress,
        	zyLayer2IpInbandMask			IpAddress,
        	zyLayer2IpInbandGateway			IpAddress,
        	zyLayer2IpInbandVid				INTEGER,  
        	zyLayer2IpInbandManageableState EnabledStatus,
        	zyLayer2IpInbandRowStatus		RowStatus
        }

        zyLayer2IpInbandIpAddress OBJECT-TYPE
        SYNTAX  IpAddress
        MAX-ACCESS  not-accessible
        STATUS  current
        DESCRIPTION
		"IP address for managing the switch by the members of the VLAN specified in the VLAN ID field."
        ::= { zyxelLayer2IpInbandEntry 1 }

        zyLayer2IpInbandMask OBJECT-TYPE
        SYNTAX  IpAddress
        MAX-ACCESS  read-write
        STATUS  current
        DESCRIPTION
		"The IP subnet mask."
        ::= { zyxelLayer2IpInbandEntry 2 }

        zyLayer2IpInbandGateway OBJECT-TYPE
        SYNTAX  IpAddress
        MAX-ACCESS  read-write
        STATUS  current
        DESCRIPTION
		"The IP address of the default outgoing gateway."
        ::= { zyxelLayer2IpInbandEntry 3 }

        zyLayer2IpInbandVid OBJECT-TYPE
        SYNTAX  INTEGER
        MAX-ACCESS  not-accessible
        STATUS  current
        DESCRIPTION
		"Type the VLAN group identification number."
        ::= { zyxelLayer2IpInbandEntry 4 }

        zyLayer2IpInbandManageableState OBJECT-TYPE
        SYNTAX  EnabledStatus
        MAX-ACCESS  read-write
        STATUS  current
        DESCRIPTION
		"Enable/Disable the specified IP address as manageable."
        ::= { zyxelLayer2IpInbandEntry 5 }

        zyLayer2IpInbandRowStatus OBJECT-TYPE
        SYNTAX  RowStatus
        MAX-ACCESS  read-create
        STATUS  current
        DESCRIPTION
		"This object allows entries to be created and deleted from the in-band IP table."
        ::= { zyxelLayer2IpInbandEntry 6 }

END
