CXQLLC-MIB DEFINITIONS ::= BEGIN

--#CURRENT_VERSION 1

IMPORTS
Counter                    FROM RFC1155-SMI
OBJECT-TYPE                FROM RFC-1212
DisplayString            FROM RFC1213-MIB
cxQLLC,SapIndex,Alias,ThruputClass
                           FROM CXProduct-SMI;

-- Proprietary Data Types

X25Address      ::=     DisplayString (SIZE (0..15))

PacketSize     ::=  INTEGER {
               bytes16   (4),
               bytes32   (5),
               bytes64   (6),
               bytes128  (7),
               bytes256  (8),
               bytes512  (9),
               bytes1024 (10),
               bytes2048 (11),
               bytes4096 (12)
               }
-- Service Access Point Configuration Table

qllcSapTable OBJECT-TYPE
SYNTAX    SEQUENCE OF QllcSapEntry
ACCESS    not-accessible
STATUS    mandatory
DESCRIPTION
"A table containing configuration information for each QLLC service access 
point."
REFERENCE
     "Memotec Communications Inc."
::= { cxQLLC 1 }

qllcSapEntry OBJECT-TYPE
     SYNTAX    QllcSapEntry
     ACCESS    not-accessible
     STATUS    mandatory
     DESCRIPTION
"Defines a row in the qllcSapTable. Each row contains the objects which 
are used to define a service access point."
     INDEX { qllcSapNumber }
     ::= { qllcSapTable 1 }

QllcSapEntry ::=
     SEQUENCE {
-- Parameters
          qllcSapNumber                 SapIndex,
          qllcSapRowStatus                   INTEGER,
          qllcSapType                        INTEGER,
          qllcSapAlias                       Alias,
          qllcSapCompanionAlias              Alias,
          qllcSapSnalcRef                    INTEGER,
-- Status
          qllcSapOperationalMode             INTEGER
          }
-- The Objects for the Service Access Point Configuration Table

qllcSapNumber OBJECT-TYPE
     SYNTAX    SapIndex
     ACCESS    read-only
     STATUS    mandatory
     DESCRIPTION
"Identifies a SAP (service access point) in the qllcSapTable."
::= { qllcSapEntry 1 }


qllcSapRowStatus OBJECT-TYPE
     SYNTAX    INTEGER {
                    invalid        (1),
                    valid          (2)
                    }
     ACCESS    read-write
     STATUS    mandatory
     DESCRIPTION
"Determines the status of the objects in a table row.

Options:
invalid (1): Row is flagged, after next reset the values will be disabled 
and the row will be deleted from the table.

valid (2): Values are enabled.

Configuration Changed: administrative"
     ::= { qllcSapEntry 2 }


qllcSapType OBJECT-TYPE
     SYNTAX    INTEGER {
                    lower     (1),
                    upper     (2)
                    }
     ACCESS    read-write
     STATUS    mandatory
     DESCRIPTION
"Specifies this SAP (service access point) as either 'upper' or 'lower'.

Options:
lower (1): This is a lower SAP which communicates with the X.25 layer.

upper (2): This is an upper SAP, which acts as an inter-layer port 
communicating with the SNA Link Conversion layer.

Configuration Changed: administrative"
     ::={ qllcSapEntry 3 }

qllcSapAlias OBJECT-TYPE
     SYNTAX    Alias
     ACCESS    read-write
     STATUS    mandatory
     DESCRIPTION
"Identifies this service access point by a textual name. Names must be 
unique across all service access points at all layers. 

Range of Values: 1 - 16 alphanumeric characters (first character must be a 
letter)

Default Value: none

Configuration Changed: administrative"
     ::= { qllcSapEntry 4 }

qllcSapCompanionAlias OBJECT-TYPE
     SYNTAX    Alias
     ACCESS    read-write
     STATUS    mandatory
     DESCRIPTION
"Identifies the X.25 SAP that this SAP communicates with. 

Range of Values: 1 - 16 alphanumeric characters (first character must be a 
letter)

Default Value: none

Configuration Changed: administrative"
     ::= { qllcSapEntry 5 }


qllcSapSnalcRef OBJECT-TYPE
     SYNTAX    INTEGER  (0..8)
     ACCESS    read-write
     STATUS    mandatory
     DESCRIPTION
"This object applies only to lower SAPs (service access points).

Determines the upper SAP (service access point) that is associated with 
this SAP.

Range of Values: 0 - 8

Default Value: none

Configuration Changed: administrative"
     ::={ qllcSapEntry 6 }

qllcSapOperationalMode OBJECT-TYPE
     SYNTAX    INTEGER {
                    offline   (1),
                    online    (2)
                    }
     ACCESS    read-only
     STATUS    mandatory
     DESCRIPTION
"Identifies the operational state of this SAP (service access point).

Options:
offLine (1): Indicates that this SAP is not operational.

onLine (2): Indicates that this SAP is operational."
     ::={ qllcSapEntry 20 }





--The DTE Table for the Terminal Interface Units

qllcDteTable OBJECT-TYPE
SYNTAX    SEQUENCE OF QllcDteEntry
ACCESS    not-accessible
STATUS    mandatory
DESCRIPTION
"The DTE table contains the parameter settings that are used to create an 
X.25 Call Request packet for calls established by a particular lower 
service access point for a particular control unit."
::= { cxQLLC 2 }

qllcDteEntry OBJECT-TYPE
     SYNTAX    QllcDteEntry
     ACCESS    not-accessible
     STATUS    mandatory
     DESCRIPTION
"Defines a row in the qllcDteTable. Each row contains the objects which 
are used to define a the parameters for an X.25 Call Request packet."
     INDEX     { qllcDteSap,qllcDteIndex }
     ::= { qllcDteTable 1 }


QllcDteEntry ::=
     SEQUENCE {
               qllcDteSap               SapIndex,
               qllcDteIndex             INTEGER,
               qllcDteRowStatus         INTEGER,
               qllcDteType              INTEGER,
               qllcDteCalledAddress     X25Address,
               qllcDteCallingAddress    X25Address,
               qllcDteDBitCall          INTEGER,
               qllcDteWindow            INTEGER,
               qllcDtePacketSize        PacketSize,
               qllcDteThroughput        ThruputClass,
               qllcDteUserData          DisplayString,
               qllcDteFacility          OCTET STRING,
               qllcDteMemotec           INTEGER,
               qllcDtePvc               INTEGER,
               qllcDteConnectMethod     INTEGER,
               qllcDteControl           INTEGER,
               qllcDteStatus            INTEGER,
               qllcDteOperationalMode   INTEGER,
               qllcDteState             INTEGER,
					qllcDteConnectionType    INTEGER,
               qllcDteCalls             Counter,
               qllcDteClears            Counter,
               qllcDteTxPackets         Counter,
               qllcDteRxPackets         Counter,
               qllcDteQdc               Counter,
               qllcDteQxid              Counter,
               qllcDteQua               Counter,
               qllcDteQsm               Counter,
               qllcDteX25Reset          Counter,
               qllcDteSnalcRnr          Counter,
               qllcDteSnalcRr           Counter,
               qllcDteX25Rnr            Counter,
               qllcDteX25Rr             Counter
               }







--The Objects for the DTE Table used by the Terminal Interface Units

qllcDteSap OBJECT-TYPE
     SYNTAX    SapIndex
     ACCESS    read-only
     STATUS    mandatory
     DESCRIPTION
"Identifies the SAP (service access point) associated with this entry.

Configuration Changed: administrative "
     ::= { qllcDteEntry 1 }

qllcDteIndex OBJECT-TYPE
     SYNTAX    INTEGER (1..64)
     ACCESS    read-only
     STATUS    mandatory
     DESCRIPTION
"Identifies the control unit address associated with this DTE entry. 

Configuration Changed: administrative "
     ::= { qllcDteEntry 2 }

qllcDteRowStatus OBJECT-TYPE
     SYNTAX    INTEGER {
                    invalid        (1),
                    valid          (2)
                    }
     ACCESS    read-write
     STATUS    mandatory
     DESCRIPTION
"Determines the status of the objects in a table row.

Options:
invalid (1): Row is flagged, after next reset the values will be disabled 
and the row will be deleted from the table.

valid (2): Values are enabled.

Configuration Changed: administrative"
     ::= { qllcDteEntry 3 }






qllcDteType    OBJECT-TYPE
     SYNTAX    INTEGER {
                    terminalInterfaceUnit    (1),
                    hostInterfaceUnit   (2)
                    }
     ACCESS    read-write
     STATUS    mandatory
     DESCRIPTION
"Determines the type of interface (HIU or TIU) associated with this DTE.

Options:
terminalInterfaceUnit (1): The SAP type is a TIU, which means it is 
connected to one or more control units (secondary link stations). The TIU 
emulates a primary link station, and polls the attached control units. The 
SDLC interface can support a total of 64 control units across all TIU 
SAPs.

hostInterfaceUnit (2): The SAP type is an HIU, which means it is connected 
to an SNA host (primary link station). The HIU emulates the control units 
connected to a TIU. It responds to polls issued by the host.

Default Value: terminalInterfaceUnit (1)

Configuration Changed: administrative"
     DEFVAL { terminalInterfaceUnit }
     ::= { qllcDteEntry 4 }


qllcDteCalledAddress OBJECT-TYPE
     SYNTAX    X25Address
     ACCESS    read-write
     STATUS    mandatory
     DESCRIPTION
"Determines the DTE to call to establish a QLLC connection.

Range of Values: DTE address enclosed in quotes (up to 15 characters in 
length)

Default Value: none

Configuration Changed: administrative and operative"
     ::= { qllcDteEntry 5}

qllcDteCallingAddress OBJECT-TYPE
     SYNTAX    X25Address
     ACCESS    read-write
     STATUS    mandatory
     DESCRIPTION
"Determines the DTE address of the caller.

Range of Values: DTE address enclosed in quotes (up to 15 characters in 
length)

Default Value: none

Configuration Changed: administrative and operative"
     ::= { qllcDteEntry 6}

qllcDteDBitCall OBJECT-TYPE
     SYNTAX    INTEGER {
                    no   (1),
                    yes  (2)
                    }
     ACCESS    read-write
     STATUS    mandatory
     DESCRIPTION
"Determines if segmentation is supported and is to be performed by the 
QLLC layer for the specific DTE entry.

Options:
no (1): QLLC does not support segmentation.

yes (2): QLLC supports segmentation. (For future use.)

Default Value: yes (2)

Configuration Changed: administrative and operative"
     DEFVAL { yes }
     ::= { qllcDteEntry 7 }

qllcDteWindow OBJECT-TYPE
     SYNTAX    INTEGER (1..7)
     ACCESS    read-write
     STATUS    mandatory
     DESCRIPTION
"Determines the transmit and receive window sizes for this DTE. This 
window size is used when establishing calls from this DTE, or when 
receiving calls at this DTE.

QLLC only supports modulo 8 window size.

Range of Values: 1 - 7

Default Value: 7

Configuration Changed: administrative and operative"
DEFVAL { 7 }
     ::= { qllcDteEntry 8 }


qllcDtePacketSize OBJECT-TYPE
     SYNTAX  PacketSize
     ACCESS  read-write
     STATUS  mandatory
     DESCRIPTION
"Determines the transmit and receive packet size for this DTE when flow 
control negotiation (x25SapSbscrFlowCntrlParamNegotiation) is not 
subscribed to, or when a D-bit call is routed through this SAP.

Options:
bytes16 (4): 16 bytes

bytes32 (5): 32 bytes

bytes64 (6): 64 bytes

bytes128 (7): 128 bytes

bytes256 (8): 256 bytes

bytes512 (9): 512 bytes

bytes1024 (10): 1024 bytes

bytes2048 (11): 2048 bytes

bytes4096 (12): 4096 bytes

Default Value: bytes128 (7)

Related Objects: x25SapSbscrFlowCntrlParamNegotiation

Configuration Changed: administrative and operative"
     DEFVAL { bytes128 }
     ::= { qllcDteEntry 9 }

qllcDteThroughput OBJECT-TYPE
     SYNTAX  ThruputClass
     ACCESS  read-write
     STATUS  mandatory
     DESCRIPTION
"Determines the transmit and receive throughput class for this DTE when 
flow control negotiation (x25SapSbscrThruputClassNegotiation) is not 
subscribed to, or when a D-bit call is routed through this SAP.

Options:
bps75 (3)

bps150 (4)

bps300 (5)

bps600 (6)

bps1200 (7)

bps2400 (8)

bps4800 (9)

bps9600 (10)

bps19200 (11)

bps38400 (12)

bps64000 (13)

 Default Value: bps9600 (10)

Related Objects: x25SapSbscrThruputClassNegotiation

Configuration Changed: administrative and operative"
     DEFVAL { bps9600 }
     ::= { qllcDteEntry 10 }

qllcDteUserData OBJECT-TYPE
     SYNTAX    DisplayString (SIZE (0..12))
     ACCESS    read-write
     STATUS    mandatory
     DESCRIPTION
"Determines the data included in the call user data field of each outgoing 
call initiated by this DTE. Call user data can only be included when 
calling non-Memotec devices. In this case, up to 12 characters can be 
specified.

The format of the call user data field is determined by the value of the 
qllcDteMemotec object.

Related Object: qllcDteMemotec

Range of Values: 0 - 12 characters

Default Value: none

Configuration Changed: administrative and operative"
     ::= { qllcDteEntry 11 }


qllcDteFacility OBJECT-TYPE
     SYNTAX    OCTET STRING
     ACCESS    read-write
     STATUS    mandatory
     DESCRIPTION
"Determines the facility codes and associated parameters for this DTE. 

Default Value: 0

Range of Values: 0 - 20 hexadecimal characters

Configuration Changed: administrative and operative"
     ::= { qllcDteEntry 12 }

qllcDteMemotec OBJECT-TYPE
     SYNTAX    INTEGER {
                    nonmemotec  (1),
                    cx900       (2),
                    legacy      (3),
                    pvc         (4)
                    }
     ACCESS    read-write
     STATUS    mandatory
     DESCRIPTION
"Determines the type of product that the called DTE address is associated 
with, which in turn determines how the call user data (CUD) field is constructed 
for all outgoing calls from this DTE. This object also determines whether 
the call is associated to a Switched Virtual Circuit (SVC) or a Permanent 
Virtual Circuit (PVC). 

Options:
(1): Called DTE address is a non- Memotec product. CUD field = QLLC 
protocol ID + value of object qllcDteUserData

(2): Called DTE is a Memotec CX900 product. CUD field = QLLC protocol ID + 
value of object qllcDteIndex 

(3): Called DTE is an older Memotec product (including CX1000). CUD field 
= QLLC protocol ID + / + Port Group GE + CU Alias + FF + Port + FF + FF

(4): The DTE is connected through a Permanent Virtual Circuit (PVC), and 
can be either TIU or HIU. 

Note that if the DTE is configured for an SVC but a PVC call is received, 
the QLLC layer will attempt to connect to the PVC.

Default Value: cx900 (2)

Related Objects: qllcDteUserData qllcDteCalledAddress qllcDteConnectMethod

Configuration Changed: administrative and operative"
     DEFVAL { cx900 }
     ::= { qllcDteEntry 13 }

qllcDtePvc OBJECT-TYPE
     SYNTAX    INTEGER {
                    no   (1),
                    yes  (2)
                    }
     ACCESS    read-write
     STATUS    mandatory
     DESCRIPTION
"Determines if this DTE makes its calls on a PVC (permanent virtual 
circuit).

Options:
no (1): This DTE does not make its calls on a PVC (all calls are 
switched).

yes (2): This DTE makes its calls on a PVC. (For future use.)

Default Value: no (1)

Configuration Changed: administrative "
     DEFVAL { no }
     ::= { qllcDteEntry 14 }

qllcDteConnectMethod OBJECT-TYPE
     SYNTAX    INTEGER {
                    userdata        (1),
                    callingaddress  (2)
                    }
     ACCESS    read-write
     STATUS    mandatory
     DESCRIPTION
"Determines if this DTE accepts calls by validating the user-data field, 
or by matching the calling address with its corresponding called address. 

Note: This object only applies to the HIU.

Options:   

userdata (1): The HIU DTE validates the call using the user-data field.

callingaddress (2): The HIU DTE validates the call by matching the call's 
calling address with the configured called address.

Default Value: userdata (1)

 Configuration Changed: administrative "
     DEFVAL { userdata }
     --#STARTING_VERSION 1
     ::= { qllcDteEntry 15 }

qllcDteControl OBJECT-TYPE
     SYNTAX    INTEGER {
                    clearStats     (1)
                    }
     ACCESS    write-only
     STATUS    mandatory
     DESCRIPTION
"Clears all statistics for this service access point.

Options:
clearStats (1): Clear statistics.

Default Value: none

Configuration Changed: administrative and operative"
     ::= { qllcDteEntry  20 }


qllcDteStatus OBJECT-TYPE
     SYNTAX    INTEGER   {
                    connected               (1),
                    pendingConnect     (2),
                    disconnected           (3),
                    pendingDisconnect (4)
                     }
     ACCESS    read-only
     STATUS    mandatory
     DESCRIPTION
"Indicates the connection status of this DTE.

Options:
connected (1): This DTE is connected.

pendingConnect (2): This DTE has issued a call and is waiting for it to 
complete.

disconnected (3): This DTE is not connected.

pendingDisconnect (4): This DTE has issued a call clear and is waiting for 
it to complete.

Configuration Changed: administrative and operative"
     ::= { qllcDteEntry 30 }


qllcDteOperationalMode OBJECT-TYPE
     SYNTAX    INTEGER   {
                    offline   (1),
                    online    (2)
                    }
     ACCESS    read-only
     STATUS    mandatory
     DESCRIPTION
"Indicates the operational state of this DTE.

Options:
offLine (1): Indicates that this DTE is not operational.

onLine (2): Indicates that this DTE is operational."
::= { qllcDteEntry 31}


qllcDteState OBJECT-TYPE
     SYNTAX    INTEGER   {
                    opened    (1),
                    closed    (2),
                    xidcmd    (3),
                    tstcmd    (4),
                    xidrsp    (5),
                    tstrsp    (6),
                    reset     (7),
                    setmode   (8),
                    disc      (9),
                    reqdisc   (10),
                    unknown   (11)
                     }
     ACCESS    read-only
     STATUS    mandatory
     DESCRIPTION
"Indicates the state of this DTE with regards to SNA traffic.

Options: 

opened (1): Indicates that this DTE is in data transfer mode (a 
QSM was sent and a QUA was received).

closed (2): Indicates that this DTE is not in data transfer mode (QSM not 
sent or QUA not received).

xidcmd (3): Indicates that an XID was sent by the TIU and received by the 
HIU.

tstcmd (4): Indicates that a TEST was sent by the TIU and received by the 
HIU.

xiddrsp (5): Indicates that the HIU received an XID response from the TIU, 
or that the TIU received an XID response from the control unit.

tsttrsp (6): Indicates that the HIU received a TEST response from the TIU, 
or that the TIU received a TEST response from the control unit. 

reset (7): Indicates that an X.25 reset was received.

setmode (8): Indicates that a QSM was received.

disc (9): Indicates that the HIU received a DISC from the host, or that 
the TIU sent a DISC to the control unit.

reqdisc (10): Indicates that the HIU sent a DISC to the host, or that the 
TIU received a DISC from the control unit.

unknown (11): Indicates that an unknown condition has occurred.
"
::= { qllcDteEntry 32 }


qllcDteConnectionType OBJECT-TYPE
     SYNTAX    INTEGER   {
                    none    (1),
                    svc     (2),
                    pvc     (3)
                     }
     ACCESS    read-only
     STATUS    mandatory
     DESCRIPTION
"Identifies the type of X.25 connection that the DTE is supporting.

Options:
none (1): No X.25 connection exists yet. 

svc (2): The QLLC DTE is transmitting SNA data over a Switched Virtual 
Circuit (SVC). 

pvc (3): The QLLC DTE is transmitting SNA data over a Permanent Virtual 
Circuit (PVC)."
     --#STARTING_VERSION 1
::= { qllcDteEntry 33 }


qllcDteCalls OBJECT-TYPE
     SYNTAX    Counter
     ACCESS    read-only
     STATUS    mandatory
     DESCRIPTION
"Indicates the number of incoming calls received by this DTE."
     ::= { qllcDteEntry 40}


qllcDteClears OBJECT-TYPE
     SYNTAX    Counter
     ACCESS    read-only
     STATUS    mandatory
     DESCRIPTION
"Indicates the number of calls cleared by this DTE."
     ::= { qllcDteEntry 41}

qllcDteTxPackets OBJECT-TYPE
     SYNTAX    Counter
     ACCESS    read-only
     STATUS    mandatory
     DESCRIPTION
"Indicates the number of data packets sent by this DTE."
     ::= { qllcDteEntry 42 }

qllcDteRxPackets OBJECT-TYPE
     SYNTAX    Counter
     ACCESS    read-only
     STATUS    mandatory
     DESCRIPTION
"Indicates the number of data packets received by this DTE."
     ::= { qllcDteEntry 43 }

qllcDteQdc OBJECT-TYPE
     SYNTAX    Counter
     ACCESS    read-only
     STATUS    mandatory
     DESCRIPTION
"Indicates the number of SNA disconnects sent and received by this DTE."
     ::= { qllcDteEntry 44 }

qllcDteQxid OBJECT-TYPE
     SYNTAX    Counter
     ACCESS    read-only
     STATUS    mandatory
     DESCRIPTION
"Indicates the number of SNA XIDs sent and received by this DTE."
     ::= { qllcDteEntry  45 }

qllcDteQua OBJECT-TYPE
     SYNTAX    Counter
     ACCESS    read-only
     STATUS    mandatory
     DESCRIPTION
"Indicates the number of unnumbered acknowledgments sent and received by 
this DTE."
     ::= { qllcDteEntry  46 }


qllcDteQsm OBJECT-TYPE
     SYNTAX    Counter
     ACCESS    read-only
     STATUS    mandatory
     DESCRIPTION
"Indicates the number of SNRMs sent and received by this DTE."
     ::= { qllcDteEntry  47 }

qllcDteX25Reset OBJECT-TYPE
     SYNTAX    Counter
     ACCESS    read-only
     STATUS    mandatory
     DESCRIPTION
"Indicates the number of X.25 resets sent and received by this DTE."
     ::= { qllcDteEntry  48}

qllcDteSnalcRnr OBJECT-TYPE
     SYNTAX    Counter
     ACCESS    read-only
     STATUS    mandatory
     DESCRIPTION
"Indicates the number of SNA link conversion layer flow control RNRs sent 
and received by this DTE."
     ::= { qllcDteEntry  49}

qllcDteSnalcRr OBJECT-TYPE
     SYNTAX    Counter
     ACCESS    read-only
     STATUS    mandatory
     DESCRIPTION
"Indicates the number of SNA link conversion layer flow control RRs sent 
and received by this DTE."
     ::= { qllcDteEntry  50}

qllcDteX25Rnr OBJECT-TYPE
     SYNTAX    Counter
     ACCESS    read-only
     STATUS    mandatory
     DESCRIPTION
"Indicates the number of X.25 flow control RNRs sent and received by this 
DTE."
     ::= { qllcDteEntry  51}


qllcDteX25Rr OBJECT-TYPE
     SYNTAX    Counter
     ACCESS    read-only
     STATUS    mandatory
     DESCRIPTION
"Indicates the number of X.25 flow control RRs sent and received by this 
DTE."
     ::= { qllcDteEntry  52}


qllcMibLevel OBJECT-TYPE
	SYNTAX	INTEGER
	ACCESS	read-only
	STATUS	mandatory
	DESCRIPTION
"Used to determine current MIB module release supported
by the agent. Object is in decimal."
	DEFVAL { 0 }
	--#STARTING_VERSION 1
	::= { cxQLLC 3 }

END
