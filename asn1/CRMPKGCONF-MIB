-- automatically generated by mosy 7.1 #1 (elc), do not edit!
-- crmPkgFrLineTable add object(99.3.30 kameishi)

CRMPKGCONF-MIB DEFINITIONS ::= BEGIN


IMPORTS
	DisplayString
		FROM RFC1213-MIB
	OBJECT-TYPE
		FROM RFC-1212
	Counter, IpAddress
		FROM RFC1155-SMI
	InterfaceIndex
		FROM IF-MIB
	mib-2, ifIndex
		FROM RFC1213-MIB
	RowStatus, TimeStamp
		FROM SNMPv2-TC;

org OBJECT IDENTIFIER ::= { iso  3 }

dod OBJECT IDENTIFIER ::= { org  6 }

internet OBJECT IDENTIFIER ::= { dod  1 }

private OBJECT IDENTIFIER ::= { internet  4 }

enterprises OBJECT IDENTIFIER ::= { private  1 }

ntt OBJECT IDENTIFIER ::= { enterprises  210 }

mibDoc OBJECT IDENTIFIER ::= { ntt  2 }

ba3000 OBJECT IDENTIFIER ::= { mibDoc  8 }

crmCommon OBJECT IDENTIFIER ::= { ba3000  1 }

-- created from crmPkgConf (9605221200Z)

crmPkgConf OBJECT IDENTIFIER ::= { crmCommon  2 }

crmPkgDirectionTable OBJECT-TYPE
    SYNTAX  SEQUENCE OF CrmPkgDirectionEntry
    ACCESS  not-accessible
    STATUS  mandatory
    DESCRIPTION
           "DUMMY"
    ::= { crmPkgConf  1 }

crmPkgDirectionEntry OBJECT-TYPE
    SYNTAX  CrmPkgDirectionEntry
    ACCESS  not-accessible
    STATUS  mandatory
    DESCRIPTION
           "DUMMY"
    INDEX   { ifIndex }
    ::= { crmPkgDirectionTable  1 }

CrmPkgDirectionEntry ::=
    SEQUENCE {
        crmPkgDirectionNumber
            INTEGER
    }

crmPkgDirectionNumber OBJECT-TYPE
    SYNTAX  INTEGER
    ACCESS  read-only
    STATUS  mandatory
    DESCRIPTION
           "DUMMY"
    ::= { crmPkgDirectionEntry  1 }

crmPkgHsdTable OBJECT-TYPE
    SYNTAX  SEQUENCE OF CrmPkgHsdEntry
    ACCESS  not-accessible
    STATUS  mandatory
    DESCRIPTION
           "DUMMY"
    ::= { crmPkgConf  2 }

crmPkgHsdEntry OBJECT-TYPE
    SYNTAX  CrmPkgHsdEntry
    ACCESS  not-accessible
    STATUS  mandatory
    DESCRIPTION
           "DUMMY"
    INDEX   { ifIndex,  crmPkgHsdIfIndex }
    ::= { crmPkgHsdTable  1 }

CrmPkgHsdEntry ::=
    SEQUENCE {
        crmPkgHsdIfIndex
            INTEGER,

        crmPkgHsdLogIndex
            InterfaceIndex,

        crmPkgHsdFirstTsNumber
            INTEGER,

        crmPkgHsdSubUsageInfo
            INTEGER,

        crmPkgHsdAdminStatus
            INTEGER,

        crmPkgHsdOperStatus
            INTEGER,

        crmPkgHsdRowStatus
            INTEGER (-2147483648..2147483647)
    }

crmPkgHsdIfIndex OBJECT-TYPE
    SYNTAX  INTEGER
    ACCESS  not-accessible
    STATUS  mandatory
    DESCRIPTION
           "DUMMY"
    ::= { crmPkgHsdEntry  1 }

crmPkgHsdLogIndex OBJECT-TYPE
    SYNTAX  InterfaceIndex
    ACCESS  read-only
    STATUS  mandatory
    DESCRIPTION
           "DUMMY"
    ::= { crmPkgHsdEntry  2 }

crmPkgHsdFirstTsNumber OBJECT-TYPE
    SYNTAX  INTEGER
    ACCESS  read-write
    STATUS  mandatory
    DESCRIPTION
           "DUMMY"
    ::= { crmPkgHsdEntry  3 }

crmPkgHsdSubUsageInfo OBJECT-TYPE
    SYNTAX  INTEGER
    ACCESS  read-write
    STATUS  mandatory
    DESCRIPTION
           "DUMMY"
    ::= { crmPkgHsdEntry  4 }

crmPkgHsdAdminStatus OBJECT-TYPE
    SYNTAX  INTEGER {
    up(1),
    down(2)
}
    ACCESS  read-write
    STATUS  mandatory
    DESCRIPTION
           "DUMMY"
    ::= { crmPkgHsdEntry  5 }

crmPkgHsdOperStatus OBJECT-TYPE
    SYNTAX  INTEGER {
    up(1),
    down(2)
}
    ACCESS  read-only
    STATUS  mandatory
    DESCRIPTION
           "DUMMY"
    ::= { crmPkgHsdEntry  6 }

crmPkgHsdRowStatus OBJECT-TYPE
    SYNTAX  INTEGER (-2147483648..2147483647)
    ACCESS  read-write
    STATUS  mandatory
    DESCRIPTION
           "DUMMY"
    ::= { crmPkgHsdEntry  7 }

crmPkgHsdAtmChgTable OBJECT-TYPE
    SYNTAX  SEQUENCE OF CrmPkgHsdAtmChgEntry
    ACCESS  not-accessible
    STATUS  mandatory
    DESCRIPTION
           "DUMMY"
    ::= { crmPkgConf  3 }

crmPkgHsdAtmChgEntry OBJECT-TYPE
    SYNTAX  CrmPkgHsdAtmChgEntry
    ACCESS  not-accessible
    STATUS  mandatory
    DESCRIPTION
           "DUMMY"
    INDEX   { ifIndex,  crmPkgHsdAtmChgVpi }
    ::= { crmPkgHsdAtmChgTable  1 }

CrmPkgHsdAtmChgEntry ::=
    SEQUENCE {
        crmPkgHsdAtmChgVpi
            INTEGER (-2147483648..2147483647),

        crmPkgHsdAtmChgIndex
            INTEGER,

        crmPkgHsdAtmAdminStatus
            INTEGER,

        crmPkgHsdAtmOperStatus
            INTEGER,

        crmPkgHsdAtmRowStatus
            INTEGER (-2147483648..2147483647)
    }

crmPkgHsdAtmChgVpi OBJECT-TYPE
    SYNTAX  INTEGER (-2147483648..2147483647)
    ACCESS  not-accessible
    STATUS  mandatory
    DESCRIPTION
           "DUMMY"
    ::= { crmPkgHsdAtmChgEntry  1 }

crmPkgHsdAtmChgIndex OBJECT-TYPE
    SYNTAX  INTEGER
    ACCESS  read-write
    STATUS  mandatory
    DESCRIPTION
           "DUMMY"
    ::= { crmPkgHsdAtmChgEntry  2 }

crmPkgHsdAtmAdminStatus OBJECT-TYPE
    SYNTAX  INTEGER {
    up(1),
    down(2)
}
    ACCESS  read-write
    STATUS  mandatory
    DESCRIPTION
           "DUMMY"
    ::= { crmPkgHsdAtmChgEntry  3 }

crmPkgHsdAtmOperStatus OBJECT-TYPE
    SYNTAX  INTEGER {
    up(1),
    down(2)
}
    ACCESS  read-only
    STATUS  mandatory
    DESCRIPTION
           "DUMMY"
    ::= { crmPkgHsdAtmChgEntry  4 }

crmPkgHsdAtmRowStatus OBJECT-TYPE
    SYNTAX  INTEGER (-2147483648..2147483647)
    ACCESS  read-write
    STATUS  mandatory
    DESCRIPTION
           "DUMMY"
    ::= { crmPkgHsdAtmChgEntry  5 }

crmPkgHsdcTable OBJECT-TYPE
    SYNTAX  SEQUENCE OF CrmPkgHsdcEntry
    ACCESS  not-accessible
    STATUS  mandatory
    DESCRIPTION
           "DUMMY"
    ::= { crmPkgConf  4 }

crmPkgHsdcEntry OBJECT-TYPE
    SYNTAX  CrmPkgHsdcEntry
    ACCESS  not-accessible
    STATUS  mandatory
    DESCRIPTION
           "DUMMY"
    INDEX   { ifIndex,  crmPkgHsdcIfIndex }
    ::= { crmPkgHsdcTable  1 }

CrmPkgHsdcEntry ::=
    SEQUENCE {
        crmPkgHsdcIfIndex
            INTEGER,

        crmPkgHsdcLogIndex
            InterfaceIndex,

        crmPkgHsdcFirstTsNumber
            INTEGER,

        crmPkgHsdcSubUsageInfo
            INTEGER,

        crmPkgHsdcRowStatus
            INTEGER (-2147483648..2147483647)
    }

crmPkgHsdcIfIndex OBJECT-TYPE
    SYNTAX  INTEGER
    ACCESS  not-accessible
    STATUS  mandatory
    DESCRIPTION
           "DUMMY"
    ::= { crmPkgHsdcEntry  1 }

crmPkgHsdcLogIndex OBJECT-TYPE
    SYNTAX  InterfaceIndex
    ACCESS  read-only
    STATUS  mandatory
    DESCRIPTION
           "DUMMY"
    ::= { crmPkgHsdcEntry  2 }

crmPkgHsdcFirstTsNumber OBJECT-TYPE
    SYNTAX  INTEGER
    ACCESS  read-write
    STATUS  mandatory
    DESCRIPTION
           "DUMMY"
    ::= { crmPkgHsdcEntry  3 }

crmPkgHsdcSubUsageInfo OBJECT-TYPE
    SYNTAX  INTEGER
    ACCESS  read-write
    STATUS  mandatory
    DESCRIPTION
           "DUMMY"
    ::= { crmPkgHsdcEntry  4 }

crmPkgHsdcRowStatus OBJECT-TYPE
    SYNTAX  INTEGER (-2147483648..2147483647)
    ACCESS  read-write
    STATUS  mandatory
    DESCRIPTION
           "DUMMY"
    ::= { crmPkgHsdcEntry  5 }

crmPkgHsdcAtmChgTable OBJECT-TYPE
    SYNTAX  SEQUENCE OF CrmPkgHsdcAtmChgEntry
    ACCESS  not-accessible
    STATUS  mandatory
    DESCRIPTION
           "DUMMY"
    ::= { crmPkgConf  5 }

crmPkgHsdcAtmChgEntry OBJECT-TYPE
    SYNTAX  CrmPkgHsdcAtmChgEntry
    ACCESS  not-accessible
    STATUS  mandatory
    DESCRIPTION
           "DUMMY"
    INDEX   { ifIndex,  crmPkgHsdcAtmChgIndex }
    ::= { crmPkgHsdcAtmChgTable  1 }

CrmPkgHsdcAtmChgEntry ::=
    SEQUENCE {
        crmPkgHsdcAtmChgIndex
            INTEGER,

        crmPkgHsdcAtmChgVpi
            INTEGER (-2147483648..2147483647),

        crmPkgHsdcAtmChgVci
            INTEGER (-2147483648..2147483647),

        crmPkgHsdcAtmCsPduLength
            INTEGER (-2147483648..2147483647),

        crmPkgHsdcAtmAdminStatus
            INTEGER,

        crmPkgHsdcAtmOperStatus
            INTEGER,

        crmPkgHsdcAtmRowStatus
            INTEGER (-2147483648..2147483647)
    }

crmPkgHsdcAtmChgIndex OBJECT-TYPE
    SYNTAX  INTEGER
    ACCESS  not-accessible
    STATUS  mandatory
    DESCRIPTION
           "DUMMY"
    ::= { crmPkgHsdcAtmChgEntry  1 }

crmPkgHsdcAtmChgVpi OBJECT-TYPE
    SYNTAX  INTEGER (-2147483648..2147483647)
    ACCESS  read-write
    STATUS  mandatory
    DESCRIPTION
           "DUMMY"
    ::= { crmPkgHsdcAtmChgEntry  2 }

crmPkgHsdcAtmChgVci OBJECT-TYPE
    SYNTAX  INTEGER (-2147483648..2147483647)
    ACCESS  read-write
    STATUS  mandatory
    DESCRIPTION
           "DUMMY"
    ::= { crmPkgHsdcAtmChgEntry  3 }

crmPkgHsdcAtmCsPduLength OBJECT-TYPE
    SYNTAX  INTEGER (-2147483648..2147483647)
    ACCESS  read-write
    STATUS  mandatory
    DESCRIPTION
           "DUMMY"
    ::= { crmPkgHsdcAtmChgEntry  4 }

crmPkgHsdcAtmAdminStatus OBJECT-TYPE
    SYNTAX  INTEGER {
    up(1),
    down(2)
}
    ACCESS  read-write
    STATUS  mandatory
    DESCRIPTION
           "DUMMY"
    ::= { crmPkgHsdcAtmChgEntry  5 }

crmPkgHsdcAtmOperStatus OBJECT-TYPE
    SYNTAX  INTEGER {
    up(1),
    down(2)
}
    ACCESS  read-only
    STATUS  mandatory
    DESCRIPTION
           "DUMMY"
    ::= { crmPkgHsdcAtmChgEntry  6 }

crmPkgHsdcAtmRowStatus OBJECT-TYPE
    SYNTAX  INTEGER (-2147483648..2147483647)
    ACCESS  read-write
    STATUS  mandatory
    DESCRIPTION
           "DUMMY"
    ::= { crmPkgHsdcAtmChgEntry  7 }

crmPkgFrLineTable OBJECT-TYPE
    SYNTAX  SEQUENCE OF CrmPkgFrLineEntry
    ACCESS  not-accessible
    STATUS  mandatory
    DESCRIPTION
           "DUMMY"
    ::= { crmPkgConf  6 }

crmPkgFrLineEntry OBJECT-TYPE
    SYNTAX  CrmPkgFrLineEntry
    ACCESS  not-accessible
    STATUS  mandatory
    DESCRIPTION
           "DUMMY"
    INDEX   { ifIndex }
    ::= { crmPkgFrLineTable  1 }

CrmPkgFrLineEntry ::=
    SEQUENCE {
        crmPkgFrLineStMode
            INTEGER,

        crmPkgFrLineRate
            INTEGER,

        crmPkgFrLineProtcol
            INTEGER,

        crmPkgFrLineAalMode
            INTEGER,

        crmPkgFrLineFrameLength
            INTEGER (-2147483648..2147483647),

        crmPkgFrLineLmiMode
            INTEGER,

        crmPkgFrLineDeClpMode
            INTEGER,

        crmPkgFrLineClpDeMode
            INTEGER,

        crmPkgFrLineFecnEfciMode
            INTEGER,

        crmPkgFrLineEfciFecnMode
            INTEGER,

        crmPkgFrLineFrSwLightSet
            INTEGER,

        crmPkgFrLineFrSwLightCancel
            INTEGER,

        crmPkgFrLineFrSwHeavySet
            INTEGER,

        crmPkgFrLineFrSwHeavyCancel
            INTEGER,

        crmPkgFrLineSwFrLightSet
            INTEGER,

        crmPkgFrLineSwFrLightCancel
            INTEGER,

        crmPkgFrLineSwFrHeavySet
            INTEGER,

        crmPkgFrLineSwFrHeavyCancel
            INTEGER,

        crmPkgFrLineT392Timer
            INTEGER,

        crmPkgFrLineN392Counter
            INTEGER,

        crmPkgFrLineN393Counter
            INTEGER,

        crmPkgFrLineArrivedCellTimer
            INTEGER,

        crmPkgFrLineShapingLevel1
            INTEGER (-2147483648..2147483647),

        crmPkgFrLineShapingLevel2
            INTEGER (-2147483648..2147483647),

        crmPkgFrLineShapingLevel3
            INTEGER (-2147483648..2147483647),

        crmPkgFrLineShapingLevel4
            INTEGER (-2147483648..2147483647),

        crmPkgFrLineAdminStatus
            INTEGER,

        crmPkgFrLineOperStatus
            INTEGER,

        crmPkgFrLineRowStatus
            INTEGER (-2147483648..2147483647),
-- add object
        crmPkgFrLineAbrMode
            INTEGER
-- end
    }

crmPkgFrLineStMode OBJECT-TYPE
    SYNTAX  INTEGER {
    st1-mode(1),
    st2-mode(2)
}
    ACCESS  read-write
    STATUS  mandatory
    DESCRIPTION
           "DUMMY"
    DEFVAL {  2  }

    ::= { crmPkgFrLineEntry  1 }

crmPkgFrLineRate OBJECT-TYPE
    SYNTAX  INTEGER {
    bps64K(1),
    bps128k(2),
    bps192k(3),
    bps256k(4),
    bps384k(5),
    bps512k(6),
    bps768k(7),
    bps1024k(8),
    bps1536k(9),
    bps2048k(10)
}
    ACCESS  read-write
    STATUS  mandatory
    DESCRIPTION
           "DUMMY"
    ::= { crmPkgFrLineEntry  2 }

crmPkgFrLineProtcol OBJECT-TYPE
    SYNTAX  INTEGER {
    itu(1),
    ansi(2)
}
    ACCESS  read-write
    STATUS  mandatory
    DESCRIPTION
           "DUMMY"
    DEFVAL {  1  }

    ::= { crmPkgFrLineEntry  3 }

crmPkgFrLineAalMode OBJECT-TYPE
    SYNTAX  INTEGER {
    stream-mode(1),
    message-mode-assured(2),
    message-mode-unassured(3)
}
    ACCESS  read-write
    STATUS  mandatory
    DESCRIPTION
           "DUMMY"
    DEFVAL {  3  }

    ::= { crmPkgFrLineEntry  4 }

crmPkgFrLineFrameLength OBJECT-TYPE
    SYNTAX  INTEGER (-2147483648..2147483647)
    ACCESS  read-write
    STATUS  mandatory
    DESCRIPTION
           "DUMMY"
    DEFVAL {  4  }

    ::= { crmPkgFrLineEntry  5 }

crmPkgFrLineLmiMode OBJECT-TYPE
    SYNTAX  INTEGER {
    off(1),
    on(2)
}
    ACCESS  read-write
    STATUS  mandatory
    DESCRIPTION
           "DUMMY"
    DEFVAL {  2  }

    ::= { crmPkgFrLineEntry  6 }

crmPkgFrLineDeClpMode OBJECT-TYPE
    SYNTAX  INTEGER {
    off-mode(1),
    on-mode(2),
    user-info-mode(3)
}
    ACCESS  read-write
    STATUS  mandatory
    DESCRIPTION
           "DUMMY"
    DEFVAL {  1  }

    ::= { crmPkgFrLineEntry  7 }

crmPkgFrLineClpDeMode OBJECT-TYPE
    SYNTAX  INTEGER {
    off-mode(1),
    on-mode(2),
    user-info-mode(3),
    mapping-mode(4)
}
    ACCESS  read-write
    STATUS  mandatory
    DESCRIPTION
           "DUMMY"
    DEFVAL {  3  }

    ::= { crmPkgFrLineEntry  8 }

crmPkgFrLineFecnEfciMode OBJECT-TYPE
    SYNTAX  INTEGER {
    off-mode(1),
    on-mode(2),
    user-info-mode(3)
}
    ACCESS  read-write
    STATUS  mandatory
    DESCRIPTION
           "DUMMY"
    DEFVAL {  1  }

    ::= { crmPkgFrLineEntry  9 }

crmPkgFrLineEfciFecnMode OBJECT-TYPE
    SYNTAX  INTEGER {
    off-mode(1),
    on-mode(2),
    user-info-mode(3),
    mapping-mode(4)
}
    ACCESS  read-write
    STATUS  mandatory
    DESCRIPTION
           "DUMMY"
    DEFVAL {  3  }

    ::= { crmPkgFrLineEntry  10 }

crmPkgFrLineFrSwLightSet OBJECT-TYPE
    SYNTAX  INTEGER
    ACCESS  read-write
    STATUS  mandatory
    DESCRIPTION
           "DUMMY"
    DEFVAL {  60  }

    ::= { crmPkgFrLineEntry  11 }

crmPkgFrLineFrSwLightCancel OBJECT-TYPE
    SYNTAX  INTEGER
    ACCESS  read-write
    STATUS  mandatory
    DESCRIPTION
           "DUMMY"
    DEFVAL {  50  }

    ::= { crmPkgFrLineEntry  12 }

crmPkgFrLineFrSwHeavySet OBJECT-TYPE
    SYNTAX  INTEGER
    ACCESS  read-write
    STATUS  mandatory
    DESCRIPTION
           "DUMMY"
    DEFVAL {  80  }

    ::= { crmPkgFrLineEntry  13 }

crmPkgFrLineFrSwHeavyCancel OBJECT-TYPE
    SYNTAX  INTEGER
    ACCESS  read-write
    STATUS  mandatory
    DESCRIPTION
           "DUMMY"
    DEFVAL {  70  }

    ::= { crmPkgFrLineEntry  14 }

crmPkgFrLineSwFrLightSet OBJECT-TYPE
    SYNTAX  INTEGER
    ACCESS  read-write
    STATUS  mandatory
    DESCRIPTION
           "DUMMY"
    DEFVAL {  60  }

    ::= { crmPkgFrLineEntry  15 }

crmPkgFrLineSwFrLightCancel OBJECT-TYPE
    SYNTAX  INTEGER
    ACCESS  read-write
    STATUS  mandatory
    DESCRIPTION
           "DUMMY"
    DEFVAL {  50  }

    ::= { crmPkgFrLineEntry  16 }

crmPkgFrLineSwFrHeavySet OBJECT-TYPE
    SYNTAX  INTEGER
    ACCESS  read-write
    STATUS  mandatory
    DESCRIPTION
           "DUMMY"
    DEFVAL {  80  }

    ::= { crmPkgFrLineEntry  17 }

crmPkgFrLineSwFrHeavyCancel OBJECT-TYPE
    SYNTAX  INTEGER
    ACCESS  read-write
    STATUS  mandatory
    DESCRIPTION
           "DUMMY"
    DEFVAL {  70  }

    ::= { crmPkgFrLineEntry  18 }

crmPkgFrLineT392Timer OBJECT-TYPE
    SYNTAX  INTEGER
    ACCESS  read-write
    STATUS  mandatory
    DESCRIPTION
           "DUMMY"
    DEFVAL {  15  }

    ::= { crmPkgFrLineEntry  19 }

crmPkgFrLineN392Counter OBJECT-TYPE
    SYNTAX  INTEGER
    ACCESS  read-write
    STATUS  mandatory
    DESCRIPTION
           "DUMMY"
    DEFVAL {  3  }

    ::= { crmPkgFrLineEntry  20 }

crmPkgFrLineN393Counter OBJECT-TYPE
    SYNTAX  INTEGER
    ACCESS  read-write
    STATUS  mandatory
    DESCRIPTION
           "DUMMY"
    DEFVAL {  4  }

    ::= { crmPkgFrLineEntry  21 }

crmPkgFrLineArrivedCellTimer OBJECT-TYPE
    SYNTAX  INTEGER
    ACCESS  read-write
    STATUS  mandatory
    DESCRIPTION
           "DUMMY"
    DEFVAL {  10  }

    ::= { crmPkgFrLineEntry  22 }

crmPkgFrLineShapingLevel1 OBJECT-TYPE
    SYNTAX  INTEGER (-2147483648..2147483647)
    ACCESS  read-write
    STATUS  mandatory
    DESCRIPTION
           "DUMMY"
    DEFVAL {  1908  }

    ::= { crmPkgFrLineEntry  23 }

crmPkgFrLineShapingLevel2 OBJECT-TYPE
    SYNTAX  INTEGER (-2147483648..2147483647)
    ACCESS  read-write
    STATUS  mandatory
    DESCRIPTION
           "DUMMY"
    DEFVAL {  2544  }

    ::= { crmPkgFrLineEntry  24 }

crmPkgFrLineShapingLevel3 OBJECT-TYPE
    SYNTAX  INTEGER (-2147483648..2147483647)
    ACCESS  read-write
    STATUS  mandatory
    DESCRIPTION
           "DUMMY"
    DEFVAL {  6452  }

    ::= { crmPkgFrLineEntry  25 }

crmPkgFrLineShapingLevel4 OBJECT-TYPE
    SYNTAX  INTEGER (-2147483648..2147483647)
    ACCESS  read-write
    STATUS  mandatory
    DESCRIPTION
           "DUMMY"
    DEFVAL {  155883  }

    ::= { crmPkgFrLineEntry  26 }

crmPkgFrLineAdminStatus OBJECT-TYPE
    SYNTAX  INTEGER {
    up(1),
    down(2)
}
    ACCESS  read-write
    STATUS  mandatory
    DESCRIPTION
           "DUMMY"
    ::= { crmPkgFrLineEntry  27 }

crmPkgFrLineOperStatus OBJECT-TYPE
    SYNTAX  INTEGER {
    up(1),
    down(2)
}
    ACCESS  read-only
    STATUS  mandatory
    DESCRIPTION
           "DUMMY"
    ::= { crmPkgFrLineEntry  28 }

crmPkgFrLineRowStatus OBJECT-TYPE
    SYNTAX  INTEGER (-2147483648..2147483647)
    ACCESS  read-write
    STATUS  mandatory
    DESCRIPTION
           "DUMMY"
    ::= { crmPkgFrLineEntry  29 }

-- add object
crmPkgFrLineAbrMode OBJECT-TYPE
    SYNTAX  INTEGER
    ACCESS  read-write
    STATUS  mandatory
    DESCRIPTION
           "DUMMY"
    DEFVAL {  1  }
    ::= { crmPkgFrLineEntry  30 }
-- end

crmPkgFrDlcTable OBJECT-TYPE
    SYNTAX  SEQUENCE OF CrmPkgFrDlcEntry
    ACCESS  not-accessible
    STATUS  mandatory
    DESCRIPTION
           "DUMMY"
    ::= { crmPkgConf  7 }

crmPkgFrDlcEntry OBJECT-TYPE
    SYNTAX  CrmPkgFrDlcEntry
    ACCESS  not-accessible
    STATUS  mandatory
    DESCRIPTION
           "DUMMY"
    INDEX   { ifIndex,  crmPkgFrDlcIndex }
    ::= { crmPkgFrDlcTable  1 }

CrmPkgFrDlcEntry ::=
    SEQUENCE {
        crmPkgFrDlcIndex
            INTEGER,

        crmPkgFrDlcCir
            INTEGER,

        crmPkgFrDlcEir
            INTEGER,

        crmPkgFrDlcTc
            INTEGER (-2147483648..2147483647),

        crmPkgFrDlcRowStatus
            INTEGER (-2147483648..2147483647)
    }

crmPkgFrDlcIndex OBJECT-TYPE
    SYNTAX  INTEGER
    ACCESS  not-accessible
    STATUS  mandatory
    DESCRIPTION
           "DUMMY"
    ::= { crmPkgFrDlcEntry  1 }

crmPkgFrDlcCir OBJECT-TYPE
    SYNTAX  INTEGER
    ACCESS  read-write
    STATUS  mandatory
    DESCRIPTION
           "DUMMY"
    ::= { crmPkgFrDlcEntry  2 }

crmPkgFrDlcEir OBJECT-TYPE
    SYNTAX  INTEGER
    ACCESS  read-write
    STATUS  mandatory
    DESCRIPTION
           "DUMMY"
    ::= { crmPkgFrDlcEntry  3 }

crmPkgFrDlcTc OBJECT-TYPE
    SYNTAX  INTEGER (-2147483648..2147483647)
    ACCESS  read-write
    STATUS  mandatory
    DESCRIPTION
           "DUMMY"
    ::= { crmPkgFrDlcEntry  4 }

crmPkgFrDlcRowStatus OBJECT-TYPE
    SYNTAX  INTEGER (-2147483648..2147483647)
    ACCESS  read-write
    STATUS  mandatory
    DESCRIPTION
           "DUMMY"
    ::= { crmPkgFrDlcEntry  5 }

crmPkgFrAtmChgTable OBJECT-TYPE
    SYNTAX  SEQUENCE OF CrmPkgFrAtmChgEntry
    ACCESS  not-accessible
    STATUS  mandatory
    DESCRIPTION
           "DUMMY"
    ::= { crmPkgConf  8 }

crmPkgFrAtmChgEntry OBJECT-TYPE
    SYNTAX  CrmPkgFrAtmChgEntry
    ACCESS  not-accessible
    STATUS  mandatory
    DESCRIPTION
           "DUMMY"
    INDEX   { ifIndex,  crmPkgFrAtmChgDlci }
    ::= { crmPkgFrAtmChgTable  1 }

CrmPkgFrAtmChgEntry ::=
    SEQUENCE {
        crmPkgFrAtmChgDlci
            INTEGER,

        crmPkgFrAtmChgSscsDlci
            INTEGER,

        crmPkgFrAtmChgVpi
            INTEGER (-2147483648..2147483647),

        crmPkgFrAtmChgVci
            INTEGER (-2147483648..2147483647),

        crmPkgFrAtmChgAdminStatus
            INTEGER,

        crmPkgFrAtmChgOperStatus
            INTEGER,

        crmPkgFrAtmChgRowStatus
            INTEGER (-2147483648..2147483647)
    }

crmPkgFrAtmChgDlci OBJECT-TYPE
    SYNTAX  INTEGER
    ACCESS  not-accessible
    STATUS  mandatory
    DESCRIPTION
           "DUMMY"
    ::= { crmPkgFrAtmChgEntry  1 }

crmPkgFrAtmChgSscsDlci OBJECT-TYPE
    SYNTAX  INTEGER
    ACCESS  read-write
    STATUS  mandatory
    DESCRIPTION
           "DUMMY"
    ::= { crmPkgFrAtmChgEntry  2 }

crmPkgFrAtmChgVpi OBJECT-TYPE
    SYNTAX  INTEGER (-2147483648..2147483647)
    ACCESS  read-write
    STATUS  mandatory
    DESCRIPTION
           "DUMMY"
    ::= { crmPkgFrAtmChgEntry  3 }

crmPkgFrAtmChgVci OBJECT-TYPE
    SYNTAX  INTEGER (-2147483648..2147483647)
    ACCESS  read-write
    STATUS  mandatory
    DESCRIPTION
           "DUMMY"
    ::= { crmPkgFrAtmChgEntry  4 }

crmPkgFrAtmChgAdminStatus OBJECT-TYPE
    SYNTAX  INTEGER {
    up(1),
    down(2)
}
    ACCESS  read-write
    STATUS  mandatory
    DESCRIPTION
           "DUMMY"
    ::= { crmPkgFrAtmChgEntry  5 }

crmPkgFrAtmChgOperStatus OBJECT-TYPE
    SYNTAX  INTEGER {
    up(1),
    down(2)
}
    ACCESS  read-only
    STATUS  mandatory
    DESCRIPTION
           "DUMMY"
    ::= { crmPkgFrAtmChgEntry  6 }

crmPkgFrAtmChgRowStatus OBJECT-TYPE
    SYNTAX  INTEGER (-2147483648..2147483647)
    ACCESS  read-write
    STATUS  mandatory
    DESCRIPTION
           "DUMMY"
    ::= { crmPkgFrAtmChgEntry  7 }

crmPkgInsDchTable OBJECT-TYPE
    SYNTAX  SEQUENCE OF CrmPkgInsDchEntry
    ACCESS  not-accessible
    STATUS  mandatory
    DESCRIPTION
           "DUMMY"
    ::= { crmPkgConf  9 }

crmPkgInsDchEntry OBJECT-TYPE
    SYNTAX  CrmPkgInsDchEntry
    ACCESS  not-accessible
    STATUS  mandatory
    DESCRIPTION
           "DUMMY"
    INDEX   { ifIndex }
    ::= { crmPkgInsDchTable  1 }

CrmPkgInsDchEntry ::=
    SEQUENCE {
        crmPkgInsDch
            INTEGER (-2147483648..2147483647),

        crmPkgInsDchRowStatus
            INTEGER (-2147483648..2147483647)
    }

crmPkgInsDch OBJECT-TYPE
    SYNTAX  INTEGER (-2147483648..2147483647)
    ACCESS  read-write
    STATUS  mandatory
    DESCRIPTION
           "DUMMY"
    ::= { crmPkgInsDchEntry  1 }

crmPkgInsDchRowStatus OBJECT-TYPE
    SYNTAX  INTEGER (-2147483648..2147483647)
    ACCESS  read-write
    STATUS  mandatory
    DESCRIPTION
           "DUMMY"
    ::= { crmPkgInsDchEntry  2 }

crmPkgInsTable OBJECT-TYPE
    SYNTAX  SEQUENCE OF CrmPkgInsEntry
    ACCESS  not-accessible
    STATUS  mandatory
    DESCRIPTION
           "DUMMY"
    ::= { crmPkgConf  10 }

crmPkgInsEntry OBJECT-TYPE
    SYNTAX  CrmPkgInsEntry
    ACCESS  not-accessible
    STATUS  mandatory
    DESCRIPTION
           "DUMMY"
    INDEX   { ifIndex,  crmPkgInsChNumber }
    ::= { crmPkgInsTable  1 }

CrmPkgInsEntry ::=
    SEQUENCE {
        crmPkgInsChNumber
            INTEGER,

        crmPkgInsLogIndex
            InterfaceIndex,

        crmPkgInsIfid
            INTEGER (-2147483648..2147483647),

        crmPkgInsAdminStatus
            INTEGER,

        crmPkgInsOperStatus
            INTEGER,

        crmPkgInsRowStatus
            INTEGER (-2147483648..2147483647)
    }

crmPkgInsChNumber OBJECT-TYPE
    SYNTAX  INTEGER
    ACCESS  not-accessible
    STATUS  mandatory
    DESCRIPTION
           "DUMMY"
    ::= { crmPkgInsEntry  1 }

crmPkgInsLogIndex OBJECT-TYPE
    SYNTAX  InterfaceIndex
    ACCESS  read-only
    STATUS  mandatory
    DESCRIPTION
           "DUMMY"
    ::= { crmPkgInsEntry  2 }

crmPkgInsIfid OBJECT-TYPE
    SYNTAX  INTEGER (-2147483648..2147483647)
    ACCESS  read-write
    STATUS  mandatory
    DESCRIPTION
           "DUMMY"
    DEFVAL {  0  }

    ::= { crmPkgInsEntry  3 }

crmPkgInsAdminStatus OBJECT-TYPE
    SYNTAX  INTEGER {
    up(1),
    down(2)
}
    ACCESS  read-write
    STATUS  mandatory
    DESCRIPTION
           "DUMMY"
    ::= { crmPkgInsEntry  4 }

crmPkgInsOperStatus OBJECT-TYPE
    SYNTAX  INTEGER {
    up(1),
    down(2)
}
    ACCESS  read-only
    STATUS  mandatory
    DESCRIPTION
           "DUMMY"
    ::= { crmPkgInsEntry  5 }

crmPkgInsRowStatus OBJECT-TYPE
    SYNTAX  INTEGER (-2147483648..2147483647)
    ACCESS  read-write
    STATUS  mandatory
    DESCRIPTION
           "DUMMY"
    ::= { crmPkgInsEntry  6 }

crmPkgInsAtmChgTable OBJECT-TYPE
    SYNTAX  SEQUENCE OF CrmPkgInsAtmChgEntry
    ACCESS  not-accessible
    STATUS  mandatory
    DESCRIPTION
           "DUMMY"
    ::= { crmPkgConf  11 }

crmPkgInsAtmChgEntry OBJECT-TYPE
    SYNTAX  CrmPkgInsAtmChgEntry
    ACCESS  not-accessible
    STATUS  mandatory
    DESCRIPTION
           "DUMMY"
    INDEX   { ifIndex,  crmPkgInsAtmChgVpi }
    ::= { crmPkgInsAtmChgTable  1 }

CrmPkgInsAtmChgEntry ::=
    SEQUENCE {
        crmPkgInsAtmChgVpi
            INTEGER (-2147483648..2147483647),

        crmPkgInsAtmChNumber
            INTEGER,

        crmPkgInsAtmAdminStatus
            INTEGER,

        crmPkgInsAtmOperStatus
            INTEGER,

        crmPkgInsAtmRowStatus
            INTEGER (-2147483648..2147483647)
    }

crmPkgInsAtmChgVpi OBJECT-TYPE
    SYNTAX  INTEGER (-2147483648..2147483647)
    ACCESS  not-accessible
    STATUS  mandatory
    DESCRIPTION
           "DUMMY"
    ::= { crmPkgInsAtmChgEntry  1 }

crmPkgInsAtmChNumber OBJECT-TYPE
    SYNTAX  INTEGER
    ACCESS  read-write
    STATUS  mandatory
    DESCRIPTION
           "DUMMY"
    ::= { crmPkgInsAtmChgEntry  2 }

crmPkgInsAtmAdminStatus OBJECT-TYPE
    SYNTAX  INTEGER {
    up(1),
    down(2)
}
    ACCESS  read-write
    STATUS  mandatory
    DESCRIPTION
           "DUMMY"
    ::= { crmPkgInsAtmChgEntry  3 }

crmPkgInsAtmOperStatus OBJECT-TYPE
    SYNTAX  INTEGER {
    up(1),
    down(2)
}
    ACCESS  read-only
    STATUS  mandatory
    DESCRIPTION
           "DUMMY"
    ::= { crmPkgInsAtmChgEntry  4 }

crmPkgInsAtmRowStatus OBJECT-TYPE
    SYNTAX  INTEGER (-2147483648..2147483647)
    ACCESS  read-write
    STATUS  mandatory
    DESCRIPTION
           "DUMMY"
    ::= { crmPkgInsAtmChgEntry  5 }

crmPkgRs449Table OBJECT-TYPE
    SYNTAX  SEQUENCE OF CrmPkgRs449Entry
    ACCESS  not-accessible
    STATUS  mandatory
    DESCRIPTION
           "DUMMY"
    ::= { crmPkgConf  12 }

crmPkgRs449Entry OBJECT-TYPE
    SYNTAX  CrmPkgRs449Entry
    ACCESS  not-accessible
    STATUS  mandatory
    DESCRIPTION
           "DUMMY"
    INDEX   { ifIndex }
    ::= { crmPkgRs449Table  1 }

CrmPkgRs449Entry ::=
    SEQUENCE {
        crmPkgRs449LineRate
            INTEGER,

        crmPkgRs449AdminStatus
            INTEGER,

        crmPkgRs449OperStatus
            INTEGER,

        crmPkgRs449RowStatus
            INTEGER (-2147483648..2147483647)
    }

crmPkgRs449LineRate OBJECT-TYPE
    SYNTAX  INTEGER {
    bps64k(1),
    bps128k(2),
    bps192k(3),
    bps256k(4),
    bps384k(5),
    bps512k(6),
    bps576k(7),
    bps768k(8),
    bps1024k(9),
    bps1152k(10),
    bps1536k(11),
    bps2048k(12),
    bps2304k(13),
    bps3072k(14),
    bps4608k(15),
    bps6144k(16)
}
    ACCESS  read-write
    STATUS  mandatory
    DESCRIPTION
           "DUMMY"
    ::= { crmPkgRs449Entry  1 }

crmPkgRs449AdminStatus OBJECT-TYPE
    SYNTAX  INTEGER {
    up(1),
    down(2)
}
    ACCESS  read-write
    STATUS  mandatory
    DESCRIPTION
           "DUMMY"
    ::= { crmPkgRs449Entry  2 }

crmPkgRs449OperStatus OBJECT-TYPE
    SYNTAX  INTEGER {
    up(1),
    down(2)
}
    ACCESS  read-only
    STATUS  mandatory
    DESCRIPTION
           "DUMMY"
    ::= { crmPkgRs449Entry  3 }

crmPkgRs449RowStatus OBJECT-TYPE
    SYNTAX  INTEGER (-2147483648..2147483647)
    ACCESS  read-write
    STATUS  mandatory
    DESCRIPTION
           "DUMMY"
    ::= { crmPkgRs449Entry  4 }

END
