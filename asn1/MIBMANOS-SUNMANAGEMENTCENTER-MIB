-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
MIBMANOS-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
--modules         OBJECT IDENTIFIER ::= { agent 2 }
--hardware        OBJECT IDENTIFIER ::= { modules 1 }
--
--
mibman    OBJECT IDENTIFIER ::= { base 1 }

operatingSystem	OBJECT IDENTIFIER ::= { modules 2 }

finder		OBJECT IDENTIFIER ::= { mibman 1 }
loader		OBJECT IDENTIFIER ::= { mibman 2 }
browserRoot	OBJECT IDENTIFIER ::= { mibman 3 }
checker		OBJECT IDENTIFIER ::= { mibman 4 }
moduleRegistry	OBJECT IDENTIFIER ::= { mibman 5 }
modules		OBJECT IDENTIFIER ::= { mibman 6 }
schedule	OBJECT IDENTIFIER ::= { mibman 7 }

moduleEntry	OBJECT IDENTIFIER ::= { moduleTable 1 }
modspec	OBJECT IDENTIFIER ::= { moduleEntry 1 }
name	OBJECT IDENTIFIER ::= { moduleEntry 2 }
i18nName	OBJECT IDENTIFIER ::= { moduleEntry 3 }
version	OBJECT IDENTIFIER ::= { moduleEntry 4 }
url	OBJECT IDENTIFIER ::= { moduleEntry 5 }
status	OBJECT IDENTIFIER ::= { moduleEntry 6 }
id	OBJECT IDENTIFIER ::= { moduleEntry 7 }
operatingSystem	OBJECT IDENTIFIER ::= { modules 2 }
moduleTable	OBJECT IDENTIFIER ::= { operatingSystem 1 }

END
