SUBSCRIBEEXT-MIB

--	FORCE-INCLUDE <mib.h>
--	FORCE-INCLUDE <snmpdefs.h>
--	FORCE-INCLUDE <snmpstat.h>
--	FORCE-INCLUDE "mibproto.h"

	DEFINITIONS ::= BEGIN

	IMPORTS
	   MODULE-IDENTITY, OBJECT-TYPE, Integer32, IpAddress
	   FROM SNMPv2-SMI
	DisplayString
		FROM SNMPv2-TC
	subscribeExt
		FROM APENT-MIB;

--SUBSCRIBEEXT MIB

	apSubscribeExtMib MODULE-IDENTITY
	  LAST-UPDATED "0006082000Z"
	  ORGANIZATION "ArrowPoint Communications Inc."
	  CONTACT-INFO
	  "
	  Postal:               ArrowPoint Communications Inc.
				                 50 Nagog Park
				                 Acton, Massachusetts 01720
	   Tel:                   +1 978-206-3000  option 1
	   E-Mail:                support@arrowpoint.com"
	   DESCRIPTION
	"The MIB module used to describe the ArrowPoint Communications subscriber"
	::= { subscribeExt 1}
	
apSubTable OBJECT-TYPE
	SYNTAX		SEQUENCE OF APSubEntry
	MAX-ACCESS	not-accessible
	STATUS		current
	DESCRIPTION
		"A list of Subscribers"
	::= { subscribeExt 2}
	
apSubEntry OBJECT-TYPE
	SYNTAX			APSubEntry
	MAX-ACCESS		not-accessible
	STATUS			current
	DESCRIPTION		
		"A group of information uniqely identifying a subscriber."
	INDEX	{ apSubName }
	::= {apSubTable 1 }
	
APSubEntry ::= SEQUENCE {
	apSubName			DisplayString,
	apSubState			INTEGER,
	apSubAccessError    DisplayString,
	apSubAccessIP		IpAddress,
	apSubAccessUserName	DisplayString,
	apSubSubscribedFiles	INTEGER,
	apSubLastMethod		DisplayString,
    apSubSynchronized	INTEGER,
	apSubAccessType		INTEGER,
	apSubAccessPort		INTEGER,
	apSubAccessBaseDir	DisplayString,
	apSubSubscribedBytes	Integer32,
	apSubLastTime		DisplayString   
}

apSubName OBJECT-TYPE
	SYNTAX			DisplayString      
	MAX-ACCESS		read-only
	STATUS			current
	DESCRIPTION		"The name of the Subsriber service"
	::= {apSubEntry 1}
	
apSubState OBJECT-TYPE
	SYNTAX	INTEGER{
					accessFail(0),
					ready(1),
					busy(2),
					busyRetry(3),
					online(4),
					suspended(5),
					down(6),
					initializing(7),
					waitsConfig(8),
					invalid(9)
					}
	MAX-ACCESS		read-only
	STATUS			current
	DESCRIPTION		         
		"The status of our subscriber."
	::= {apSubEntry 2}
apSubAccessError	OBJECT-TYPE
	SYNTAX			DisplayString
	MAX-ACCESS		read-only
	STATUS			current
	DESCRIPTION
		"The error returned if apSubState is accessFail(0)"
	::= {apSubEntry 3}
apSubAccessIP	OBJECT-TYPE
	SYNTAX		IpAddress   
	MAX-ACCESS	read-only
	STATUS		current
	DESCRIPTION
		"The IP address of the publisher."          
	::= {apSubEntry 4}
	
apSubAccessUserName	OBJECT-TYPE
	SYNTAX		DisplayString
	MAX-ACCESS	read-only
	STATUS		current
	DESCRIPTION
		"Usernmae to use when logging in to a publisher."
	::= {apSubEntry 5}

apSubSubscribedFiles	OBJECT-TYPE
	SYNTAX		INTEGER
	MAX-ACCESS	read-only
	STATUS		current
	DESCRIPTION
		"The total number of subscribed files."
	::= {apSubEntry 6}
	
apSubLastMethod		OBJECT-TYPE
	SYNTAX		DisplayString
	MAX-ACCESS	read-only
	STATUS		current
	DESCRIPTION
		"The last method of retrieval."
	::= {apSubEntry 7}
	
apSubSynchronized	OBJECT-TYPE
	SYNTAX		INTEGER
	MAX-ACCESS	read-only
	STATUS		current
	DESCRIPTION
		"Is our subscriber sync'd with the server?"
	::= {apSubEntry 8}

apSubAccessType	OBJECT-TYPE
	SYNTAX		INTEGER{
						ftp(0),
						http(1)
						}
	MAX-ACCESS	read-only
	STATUS		current
	DESCRIPTION
		"The type of access to the publisher."
	::= {apSubEntry 9}
	
apSubAccessPort	OBJECT-TYPE
	SYNTAX		INTEGER
	MAX-ACCESS	read-only
	STATUS		current
	DESCRIPTION
		"The port to access content on the publisher."
	::= {apSubEntry 10}

apSubAccessBaseDir	OBJECT-TYPE
	SYNTAX		DisplayString
	MAX-ACCESS	read-only
	STATUS		current
	DESCRIPTION
		"The base directory to access content on the publisher."
	::= {apSubEntry 11}

apSubSubscribedBytes	OBJECT-TYPE
	SYNTAX		Integer32
	MAX-ACCESS	read-only
	STATUS		current
	DESCRIPTION
		"The total number of bytes received from a publisher."
	::= {apSubEntry 12}

apSubLastTime		OBJECT-TYPE
	SYNTAX		DisplayString
	MAX-ACCESS	read-only
	STATUS		current
	DESCRIPTION
		"The last time we subscribed!"
	::= {apSubEntry 13}
END
