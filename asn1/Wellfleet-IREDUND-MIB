Wellfleet-IREDUND-MIB DEFINITIONS ::= BEGIN

-- Created by mdl2asn version 3.1
-- Creation date: Wed Aug 30 16:44:24 EDT 1995


    IMPORTS

      OBJECT-TYPE
        FROM RFC-1212
      wfIRedundGroup
        FROM Wellfleet-COMMON-MIB;


    wfIRedundIfTable OBJECT-TYPE
        SYNTAX	SEQUENCE OF WfIRedundIfEntry
        ACCESS	not-accessible
        STATUS	mandatory
        DESCRIPTION
                "WF_IREDUND_INTERFACE_TABLE - Interface REDUNDANCY

                This tabulates the interfaces within an interface redundancy group.
                All interfaces are indexed according to their physical slot and
                connector designation.  All interfaces in the same circuit act as
                redundant (hot stand-by) interfaces for that circuit.

                At any given time, one hot stand-by interface is chosen to be the
                active interface for a circuit.  The active interface is the only
                interface that is reading and writing data to/from the media."
        ::= { wfIRedundGroup 1 }

    wfIRedundIfEntry OBJECT-TYPE
        SYNTAX	WfIRedundIfEntry
        ACCESS	not-accessible
        STATUS	mandatory
        DESCRIPTION
                "Redundant interface entries."
        INDEX	{ wfIRedundIfSlot,
    		  wfIRedundIfPort }
        ::= { wfIRedundIfTable 1 }

    WfIRedundIfEntry ::= SEQUENCE {
    	    wfIRedundIfDelete
    		INTEGER,
    	    wfIRedundIfDisable
    		INTEGER,
    	    wfIRedundIfCct
    		INTEGER,
    	    wfIRedundIfSlot
    		INTEGER,
    	    wfIRedundIfPort
    		INTEGER,
    	    wfIRedundIfPrimary
    		INTEGER,
    	    wfIRedundIfActive
    		INTEGER,
    	    wfIRedundIfMACAddr
    		OCTET STRING
        }

    wfIRedundIfDelete OBJECT-TYPE
        SYNTAX	INTEGER {
    		    created(1),
    		    deleted(2)
    		}
        ACCESS	read-write
        STATUS	mandatory
        DESCRIPTION
                "Creation and deletion flag for this record. When set, it will cause
                this entry to be deleted from the MIB."
        DEFVAL	{ created }
        ::= { wfIRedundIfEntry 1 }

    wfIRedundIfDisable OBJECT-TYPE
        SYNTAX	INTEGER {
    		    enabled(1),
    		    disabled(2)
    		}
        ACCESS	read-write
        STATUS	mandatory
        DESCRIPTION
                "Enable/Disable parameter. A disabled interface will never be selected
                as the active interface for a circuit."
        DEFVAL	{ enabled }
        ::= { wfIRedundIfEntry 2 }

    wfIRedundIfCct OBJECT-TYPE
        SYNTAX	INTEGER(1..1023)
        ACCESS	read-write
        STATUS	mandatory
        DESCRIPTION
                "The circuit number of the circuit to which the interface belongs.
                This interface will either act as the active interface for the
                the circuit or as a hot stand-by."
        ::= { wfIRedundIfEntry 3 }

    wfIRedundIfSlot OBJECT-TYPE
        SYNTAX	INTEGER(1..14)
        ACCESS	read-only
        STATUS	mandatory
        DESCRIPTION
                "Slot ID of the interface, used as instance ID"
        ::= { wfIRedundIfEntry 4 }

    wfIRedundIfPort OBJECT-TYPE
        SYNTAX	INTEGER(1..44)
        ACCESS	read-only
        STATUS	mandatory
        DESCRIPTION
                "Port ID of the interface, used as instance ID"
        ::= { wfIRedundIfEntry 5 }

    wfIRedundIfPrimary OBJECT-TYPE
        SYNTAX	INTEGER {
    		    primary(1),
    		    nonprimary(2)
    		}
        ACCESS	read-write
        STATUS	mandatory
        DESCRIPTION
                "Primary flag, indicates if this has been chosen as the primary interface.
                Only one interface in any circuit can be selected as a PRIMARY interface.
                The PRIMARY interface will have priority when an active interface is
                selected for a circuit.  In general, if a PRIMARY circuit is available
                at active interface selection time, it will be chosen as the active
                interface."
        DEFVAL	{ nonprimary }
        ::= { wfIRedundIfEntry 6 }

    wfIRedundIfActive OBJECT-TYPE
        SYNTAX	INTEGER {
    		    notavailable(1),
    		    standby(2),
    		    active(3)
    		}
        ACCESS	read-only
        STATUS	mandatory
        DESCRIPTION
                "Active flag, indicates if this interface is the current active interface
                for the Interface Redundancy Group, or a standby interface, or not
                available to be used as active interface."
        DEFVAL	{ notavailable }
        ::= { wfIRedundIfEntry 7 }

    wfIRedundIfMACAddr OBJECT-TYPE
        SYNTAX  OCTET STRING
        ACCESS  read-only
        STATUS  mandatory
        DESCRIPTION
                "MAC Address being used by Interface Redundancy as Primary MAC Address."
        ::= { wfIRedundIfEntry 8 }

    END  -- Wellfleet-IREDUND-MIB
