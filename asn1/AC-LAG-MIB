AC-LAG-MIB DEFINITIONS ::= BEGIN

-- -------------------------------------------------------------
-- Very similiar to IEEE 802.3ad MIB
-- The indexing has been changed, instead of IF-MIB's ifIndex,
-- it uses the heirarchical node/slot/port
-- -------------------------------------------------------------

IMPORTS

    acPport, AcOpStatus, AcAdminStatus,
    AcSlotNumber, AcPortNumber, AcNodeId
        FROM APPIAN-SMI-MIB

    MODULE-IDENTITY, OBJECT-TYPE, Counter32, TimeTicks
        FROM SNMPv2-SMI
    DisplayString, MacAddress, TEXTUAL-CONVENTION, TruthValue
        FROM SNMPv2-TC
    MODULE-COMPLIANCE, OBJECT-GROUP
        FROM SNMPv2-CONF
--    InterfaceIndex
--        FROM IF-MIB
--    PortList
--        FROM Q-BRIDGE-MIB
    ;


acLagMIB MODULE-IDENTITY
    LAST-UPDATED    "0002231600Z"
    ORGANIZATION "Appian Communications, Inc."
    CONTACT-INFO
        " David Ward"
    DESCRIPTION
        "The Appian Communications Link Aggregation module for managing
         IEEE Std 802.3ad."

-- The standard IEEE LAG MIB lives at -
--    ::= { iso(1) member-body(2) us(840) 802dot3(10006)
--          snmpmibs(300) 43 }
-- Ours is tied into Pport -
    ::= { acPport 8 }

lagMIBObjects OBJECT IDENTIFIER ::= { acLagMIB 1 }


-- -------------------------------------------------------------
-- Textual Conventions
-- -------------------------------------------------------------


LacpKey ::= TEXTUAL-CONVENTION
    STATUS       current
    DESCRIPTION
        "The Actor or Partner Key value."
    SYNTAX      INTEGER (0..65535)


LacpState ::= TEXTUAL-CONVENTION
    STATUS      current
    DESCRIPTION
        "The Actor and Partner State values from the LACPDU."
    SYNTAX      BITS {
                    lacpActivity(0),
                    lacpTimeout(1),
                    aggregation(2),
                    synchronization(3),
                    collecting(4),
                    distributing(5),
                    defaulted(6),
                    expired(7)
                }


ChurnState ::= TEXTUAL-CONVENTION
    STATUS       current
    DESCRIPTION
        "The state of the Churn Detection machine."
    SYNTAX      INTEGER {
                    noChurn(1),
                    churn(2),
                    churnMonitor(3)
                }


-- Copied from Q-BRIDGE-MIB
--
PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING


-- Added (instead of using ifIndex)
---
AcAggInstanceIndex    ::= TEXTUAL-CONVENTION
    STATUS  current
    DESCRIPTION
                "An instance of an aggregation group within this OSAP
                which is within the range of (1..64)."
    SYNTAX  INTEGER (1..64)


AcAggInstanceValue    ::= TEXTUAL-CONVENTION
    STATUS  current
    DESCRIPTION
                "An instance of an aggregation group within this OSAP
                which is within the range of (1..64).  A value of zero
                indicates the aggregator instance has not been determined."
    SYNTAX  INTEGER (0..64)


-- -------------------------------------------------------------


-- -------------------------------------------------------------
-- groups in the LAG MIB
-- -------------------------------------------------------------


acDot3adAgg OBJECT IDENTIFIER ::= { lagMIBObjects 1 }
acDot3adAggPort OBJECT IDENTIFIER ::= { lagMIBObjects 2 }


-- -------------------------------------------------------------

-- -------------------------------------------------------------
-- The Tables Last Changed Object
-- -------------------------------------------------------------

acDot3adTablesLastChanged OBJECT-TYPE
    SYNTAX      TimeTicks
    MAX-ACCESS read-only
    STATUS      current
    DESCRIPTION
        "This object indicates the time of the most recent
        change to the acDot3adAggTable, acDot3adAggPortListTable, or
        acDot3adAggPortTable."
::= { lagMIBObjects 3 }

-- -------------------------------------------------------------
-- The Aggregator Configuration Table
-- -------------------------------------------------------------


acDot3adAggTable OBJECT-TYPE
    SYNTAX      SEQUENCE OF AcDot3adAggEntry
    MAX-ACCESS  not-accessible
    STATUS      current
    DESCRIPTION
        "A table that contains information about every
        Aggregator that is associated with this System."
    REFERENCE
        "IEEE 802.3 Subclause 30.7.1"
    ::= { acDot3adAgg 1 }


acDot3adAggEntry OBJECT-TYPE
    SYNTAX      AcDot3adAggEntry
    MAX-ACCESS  not-accessible
    STATUS      current
    DESCRIPTION
        "A list of the Aggregator parameters.
        This is indexed by OSAP node ID - supporting one
        Aggregator per OSAP."
    INDEX { acDot3adAggNodeIdIndex, acDot3adAggInstanceIndex }
    ::= { acDot3adAggTable 1 }


AcDot3adAggEntry ::=
    SEQUENCE {
        acDot3adAggNodeIdIndex       AcNodeId,
        acDot3adAggInstanceIndex     AcAggInstanceIndex,
        acDot3adAggMACAddress
            MacAddress,
        acDot3adAggActorSystemPriority
            INTEGER,
        acDot3adAggActorSystemID
            MacAddress,
        acDot3adAggAggregateOrIndividual
            TruthValue,
        acDot3adAggActorAdminKey
            LacpKey,
        acDot3adAggActorOperKey
            LacpKey,
        acDot3adAggPartnerSystemID
            MacAddress,
        acDot3adAggPartnerSystemPriority
            INTEGER,
        acDot3adAggPartnerOperKey
            LacpKey,
        acDot3adAggCollectorMaxDelay
            INTEGER
    }


acDot3adAggNodeIdIndex OBJECT-TYPE
    SYNTAX       AcNodeId
    MAX-ACCESS   not-accessible
    STATUS       current
    DESCRIPTION
    "The node id is the id for this specific node in the OSAP ring."
    ::= { acDot3adAggEntry 1 }


acDot3adAggInstanceIndex OBJECT-TYPE
    SYNTAX       AcAggInstanceIndex
    MAX-ACCESS   not-accessible
    STATUS       current
    DESCRIPTION
    "The instance of this aggregator within this OSAP."
    ::= { acDot3adAggEntry 2 }


acDot3adAggMACAddress OBJECT-TYPE
    SYNTAX       MacAddress
    MAX-ACCESS   read-only
    STATUS       current
    DESCRIPTION
        "A 6-octet read-only value carrying the individual
       MAC address assigned to the Aggregator."
    REFERENCE
        "IEEE 802.3 Subclause 30.7.1.1.9"
    ::= { acDot3adAggEntry 3 }


acDot3adAggActorSystemPriority OBJECT-TYPE
    SYNTAX       INTEGER (0..65535)
    MAX-ACCESS   read-write
    STATUS       current
    DESCRIPTION
        "A 2-octet read-write value indicating the priority
        value associated with the Actor's System ID."
    REFERENCE
        "IEEE 802.3 Subclause 30.7.1.1.5"
    ::= { acDot3adAggEntry 4 }


acDot3adAggActorSystemID OBJECT-TYPE
    SYNTAX       MacAddress
    MAX-ACCESS   read-only
    STATUS       current
    DESCRIPTION
        "A 6-octet read-write MAC address value used as a unique
        identifier for the System that contains this Aggregator.
        NOTE-From the perspective of the Link Aggregation
        mechanisms described in Clause 43, only a single
        combination of Actor's System ID and System Priority are
        considered, and no distinction is made between the
        values of these parameters for an Aggregator and the
        port(s) that are associated with it; i.e., the protocol
        is described in terms of the operation of aggregation
        within a single System. However, the managed objects
        provided for the Aggregator and the port both allow
        management of these parameters. The result of this is to
        permit a single piece of equipment to be configured by
        management to contain more than one System from the
        point of view of the operation of Link Aggregation. This
        may be of particular use in the configuration of
        equipment that has limited aggregation capability (see
        43.6)."
    REFERENCE
        "IEEE 802.3 Subclause 30.7.1.1.4"
    ::= { acDot3adAggEntry 5 }


acDot3adAggAggregateOrIndividual OBJECT-TYPE
    SYNTAX       TruthValue
    MAX-ACCESS   read-only
    STATUS       current
    DESCRIPTION
        "A read-only Boolean value indicating whether the
        Aggregator represents an Aggregate (`TRUE') or
        an Individual link (`FALSE')."
    REFERENCE
        "IEEE 802.3 Subclause 30.7.1.1.6"
    ::= { acDot3adAggEntry 6 }


acDot3adAggActorAdminKey OBJECT-TYPE
    SYNTAX       LacpKey
    MAX-ACCESS   read-write
    STATUS       current
    DESCRIPTION
        "The current administrative value of the Key for the
        Aggregator. The administrative Key value may differ from
        the operational Key value for the reasons discussed in
        43.6.2. This is a 16-bit, read-write value. The meaning
        of particular Key values is of local significance."
    REFERENCE
        "IEEE 802.3 Subclause 30.7.1.1.7"
    ::= { acDot3adAggEntry 7 }


acDot3adAggActorOperKey OBJECT-TYPE
    SYNTAX       LacpKey
    MAX-ACCESS   read-only
    STATUS       current
    DESCRIPTION
        "The current operational value of the Key for the
        Aggregator. The administrative Key value may differ from
        the operational Key value for the reasons discussed in
        43.6.2.  This is a 16-bit read-only value. The meaning
        of particular Key values is of local significance."
    REFERENCE
        "IEEE 802.3 Subclause 30.7.1.1.8"
    ::= { acDot3adAggEntry 8 }


acDot3adAggPartnerSystemID OBJECT-TYPE
    SYNTAX       MacAddress
    MAX-ACCESS   read-only
    STATUS       current
    DESCRIPTION
        "A 6-octet read-only MAC address value consisting of the
        unique identifier for the current protocol Partner of
        this Aggregator. A value of zero indicates that there is
        no known Partner. If the aggregation is manually
        configured, this System ID value will be a value
        assigned by the local System."
    REFERENCE
        "IEEE 802.3 Subclause 30.7.1.1.10"
    ::= { acDot3adAggEntry 9 }


acDot3adAggPartnerSystemPriority OBJECT-TYPE
    SYNTAX       INTEGER (0..65535)
    MAX-ACCESS   read-only
    STATUS       current
    DESCRIPTION
        "A 2-octet read-only value that indicates the priority
        value associated with the Partner's System ID. If the
        aggregation is manually configured, this System Priority
        value will be a value assigned by the local System."
    REFERENCE
        "IEEE 802.3 Subclause 30.7.1.1.11"
    ::= { acDot3adAggEntry 10 }


acDot3adAggPartnerOperKey OBJECT-TYPE
    SYNTAX       LacpKey
    MAX-ACCESS   read-only
    STATUS       current
    DESCRIPTION
        "The current operational value of the Key for the
        Aggregator's current protocol Partner. This is a 16-bit
        read-only value. If the aggregation is manually
        configured, this Key value will be a value assigned by
        the local System."
    REFERENCE
        "IEEE 802.3 Subclause 30.7.1.1.12"
    ::= { acDot3adAggEntry 11 }


acDot3adAggCollectorMaxDelay OBJECT-TYPE
    SYNTAX       INTEGER (0..65535)
    MAX-ACCESS   read-write
    STATUS       current
    DESCRIPTION
        "The value of this 16-bit read-write attribute defines
        the maximum delay, in tens of microseconds, that may be
        imposed by the Frame Collector between receiving a frame
        from an Aggregator Parser, and either delivering the
        frame to its MAC Client or discarding the frame (see
        43.2.3.1.1)."
    REFERENCE
        "IEEE 802.3 Subclause 30.7.1.1.32"
    ::= { acDot3adAggEntry 12 }


-- -------------------------------------------------------------
-- The Aggregation Port List Table
-- -------------------------------------------------------------


acDot3adAggPortListTable OBJECT-TYPE
    SYNTAX      SEQUENCE OF AcDot3adAggPortListEntry
    MAX-ACCESS  not-accessible
    STATUS      current
    DESCRIPTION
        "A table that contains a list of all the ports
        associated with each Aggregator."
    REFERENCE
        "IEEE 802.3 Subclause 30.7.1.1.30"
    ::= { acDot3adAgg 2 }


acDot3adAggPortListEntry OBJECT-TYPE
    SYNTAX      AcDot3adAggPortListEntry
    MAX-ACCESS  not-accessible
    STATUS      current
    DESCRIPTION
        "A list of the ports associated with a given Aggregator.
         This is indexed by OSAP node ID - supporting one Aggregator
         per OSAP."
    INDEX { acDot3adAggNodeIdIndex, acDot3adAggInstanceIndex}
    ::= { acDot3adAggPortListTable 1 }


AcDot3adAggPortListEntry ::=
    SEQUENCE {
        acDot3adAggPortListPorts
            PortList
    }


acDot3adAggPortListPorts OBJECT-TYPE
    SYNTAX      PortList
    MAX-ACCESS  read-only
    STATUS      current
    DESCRIPTION
        "The complete set of ports currently associated with
        this Aggregator.  Each bit set in this list represents
        an Actor Port member of this Link Aggregation."
    REFERENCE
        "IEEE 802.3 Subclause 30.7.1.1.30"
    ::= { acDot3adAggPortListEntry 1 }


-- -------------------------------------------------------------
-- The Aggregation Port Table
-- -------------------------------------------------------------


acDot3adAggPortTable OBJECT-TYPE
    SYNTAX      SEQUENCE OF AcDot3adAggPortEntry
    MAX-ACCESS  not-accessible
    STATUS      current
    DESCRIPTION
        "A table that contains Link Aggregation Control
        configuration information about every
        Aggregation Port associated with this device.
        A row appears in this table for each physical port."
    REFERENCE
        "IEEE 802.3 Subclause 30.7.2"
    ::= { acDot3adAggPort 1 }


acDot3adAggPortEntry OBJECT-TYPE
    SYNTAX      AcDot3adAggPortEntry
    MAX-ACCESS  not-accessible
    STATUS      current
    DESCRIPTION
        "A list of Link Aggregation Control configuration
        parameters for each Aggregation Port on this device."
    INDEX { acDot3adAggPortNodeIdIndex, acDot3adAggPortSlotIndex, acDot3adAggPortPortIndex  }
    ::= { acDot3adAggPortTable 1 }


AcDot3adAggPortEntry ::=
    SEQUENCE {
        acDot3adAggPortNodeIdIndex       AcNodeId,
        acDot3adAggPortSlotIndex         AcSlotNumber,
        acDot3adAggPortPortIndex         AcPortNumber,
        acDot3adAggPortActorSystemPriority
            INTEGER,
        acDot3adAggPortActorSystemID
            MacAddress,
        acDot3adAggPortActorAdminKey
            LacpKey,
        acDot3adAggPortActorOperKey
            LacpKey,
        acDot3adAggPortPartnerAdminSystemPriority
            INTEGER,
        acDot3adAggPortPartnerOperSystemPriority
            INTEGER,
        acDot3adAggPortPartnerAdminSystemID
            MacAddress,
        acDot3adAggPortPartnerOperSystemID
            MacAddress,
        acDot3adAggPortPartnerAdminKey
            LacpKey,
        acDot3adAggPortPartnerOperKey
            LacpKey,
        acDot3adAggPortSelectedAggID
            AcAggInstanceValue,
--            InterfaceIndex,
        acDot3adAggPortAttachedAggID
            AcAggInstanceValue,
--            InterfaceIndex,
        acDot3adAggPortActorPort
            INTEGER,
        acDot3adAggPortActorPortPriority
            INTEGER,
        acDot3adAggPortPartnerAdminPort
            INTEGER,
        acDot3adAggPortPartnerOperPort
            INTEGER,
        acDot3adAggPortPartnerAdminPortPriority
            INTEGER,
        acDot3adAggPortPartnerOperPortPriority
            INTEGER,
        acDot3adAggPortActorAdminState
            LacpState,
        acDot3adAggPortActorOperState
            LacpState,
        acDot3adAggPortPartnerAdminState
            LacpState,
        acDot3adAggPortPartnerOperState
            LacpState,
        acDot3adAggPortAggregateOrIndividual
            TruthValue
    }


acDot3adAggPortNodeIdIndex OBJECT-TYPE
    SYNTAX       AcNodeId
    MAX-ACCESS   not-accessible
    STATUS       current
    DESCRIPTION
    "The node id is the id for this specific node in the OSAP ring."
    ::= { acDot3adAggPortEntry 1 }


acDot3adAggPortSlotIndex OBJECT-TYPE
    SYNTAX       AcSlotNumber
    MAX-ACCESS   not-accessible
    STATUS       current
    DESCRIPTION
    "The slot number within the chassis where this module entry resides."
    ::= { acDot3adAggPortEntry 2 }


acDot3adAggPortPortIndex OBJECT-TYPE
    SYNTAX       AcPortNumber
    MAX-ACCESS   not-accessible
    STATUS       current
    DESCRIPTION
   "The port number on the module which represents this instance of an
    Ethernet access port."
    ::= { acDot3adAggPortEntry 3 }


acDot3adAggPortActorSystemPriority OBJECT-TYPE
    SYNTAX       INTEGER (0..255)
    MAX-ACCESS   read-write
    STATUS       current
    DESCRIPTION
        "A 2-octet read-write value used to define the priority
        value associated with the Actor's System ID."
    REFERENCE
        "IEEE 802.3 Subclause 30.7.2.1.2"
    ::= { acDot3adAggPortEntry 4 }


acDot3adAggPortActorSystemID OBJECT-TYPE
    SYNTAX       MacAddress
    MAX-ACCESS   read-only
    STATUS       current
    DESCRIPTION
        "A 6-octet read-only MAC address value that defines the
        value of the System ID for the System that contains this
        Aggregation Port."
    REFERENCE
        "IEEE 802.3 Subclause 30.7.2.1.3"
    ::= { acDot3adAggPortEntry 5 }


acDot3adAggPortActorAdminKey OBJECT-TYPE
    SYNTAX       LacpKey
    MAX-ACCESS   read-write
    STATUS       current
    DESCRIPTION
        "The current administrative value of the Key for the
        Aggregation Port. This is a 16-bit read-write value.
        The meaning of particular Key values is of local
        significance."
    REFERENCE
        "IEEE 802.3 Subclause 30.7.2.1.4"
    ::= { acDot3adAggPortEntry 6 }


acDot3adAggPortActorOperKey OBJECT-TYPE
    SYNTAX       LacpKey
    MAX-ACCESS   read-write
    STATUS       current
    DESCRIPTION
        "The current operational value of the Key for the
        Aggregation Port. This is a 16-bit read-only value.
        The meaning of particular Key values is of local
        significance."
    REFERENCE
        "IEEE 802.3 Subclause 30.7.2.1.5"
    ::= { acDot3adAggPortEntry 7 }


acDot3adAggPortPartnerAdminSystemPriority OBJECT-TYPE
    SYNTAX       INTEGER (0..255)
    MAX-ACCESS   read-write
    STATUS       current
    DESCRIPTION
        "A 2-octet read-write value used to define the
        administrative value of priority associated with the
        Partner's System ID. The assigned value is used, along
        with the value of aAggPortPartnerAdminSystemID,
        aAggPortPartnerAdminKey, aAggPortPartnerAdminPort, and
        aAggPortPartnerAdminPortPriority, in order to achieve
        manually configured aggregation."
    REFERENCE
        "IEEE 802.3 Subclause 30.7.2.1.6"
    ::= { acDot3adAggPortEntry 8 }


acDot3adAggPortPartnerOperSystemPriority OBJECT-TYPE
    SYNTAX       INTEGER (0..255)
    MAX-ACCESS   read-only
    STATUS       current
    DESCRIPTION
        "A 2-octet read-only value indicating the operational
        value of priority associated with the Partner's System
        ID. The value of this attribute may contain the manually
        configured value carried in
        aAggPortPartnerAdminSystemPriority if there is no
        protocol Partner."
    REFERENCE
        "IEEE 802.3 Subclause 30.7.2.1.7"
    ::= { acDot3adAggPortEntry 9 }


acDot3adAggPortPartnerAdminSystemID OBJECT-TYPE
    SYNTAX       MacAddress
    MAX-ACCESS   read-write
    STATUS       current
    DESCRIPTION
        "A 6-octet read-write MACAddress value representing the
        administrative value of the Aggregation Port's protocol
        Partner's System ID. The assigned value is used, along
        with the value of aAggPortPartnerAdminSystemPriority,
        aAggPortPartnerAdminKey, aAggPortPartnerAdminPort, and
        aAggPortPartnerAdminPortPriority, in order to achieve
        manually configured aggregation."
    REFERENCE
        "IEEE 802.3 Subclause 30.7.2.1.8"
    ::= { acDot3adAggPortEntry 10 }


acDot3adAggPortPartnerOperSystemID OBJECT-TYPE
    SYNTAX       MacAddress
    MAX-ACCESS   read-only
    STATUS       current
    DESCRIPTION
        "A 6-octet read-only MACAddress value representing the
        current value of the Aggregation Port's protocol
        Partner's System ID. A value of zero indicates that
        there is no known protocol Partner. The value of this
        attribute may contain the manually configured value
        carried in aAggPortPartnerAdminSystemID if there is no
        protocol Partner."
    REFERENCE
        "IEEE 802.3 Subclause 30.7.2.1.9"
    ::= { acDot3adAggPortEntry 11 }


acDot3adAggPortPartnerAdminKey OBJECT-TYPE
    SYNTAX       LacpKey
    MAX-ACCESS   read-write
    STATUS       current
    DESCRIPTION
        "The current administrative value of the Key for the
        protocol Partner. This is a 16-bit read-write value.
        The assigned value is used, along with the value of
        aAggPortPartnerAdminSystemPriority,
        aAggPortPartnerAdminSystemID, aAggPortPartnerAdminPort,
        and aAggPortPartnerAdminPortPriority, in order to
        achieve manually configured aggregation."
    REFERENCE
        "IEEE 802.3 Subclause 30.7.2.1.10"
    ::= { acDot3adAggPortEntry 12 }


acDot3adAggPortPartnerOperKey OBJECT-TYPE
    SYNTAX       LacpKey
    MAX-ACCESS   read-only
    STATUS       current
    DESCRIPTION
        "The current operational value of the Key for the
        protocol Partner. The value of this attribute may
        contain the manually configured value carried in
        aAggPortPartnerAdminKey if there is no protocol Partner.
        This is a 16-bit read-only value."
    REFERENCE
        "IEEE 802.3 Subclause 30.7.2.1.11"
    ::= { acDot3adAggPortEntry 13 }


acDot3adAggPortSelectedAggID OBJECT-TYPE
    SYNTAX       AcAggInstanceValue
--    SYNTAX       InterfaceIndex
    MAX-ACCESS   read-only
    STATUS       current
    DESCRIPTION
        "The identifier value of the Aggregator that this
        Aggregation Port has currently selected. Zero indicates
        that the Aggregation Port has not selected an
        Aggregator, either because it is in the process of
        detaching from an Aggregator or because there is no
        suitable Aggregator available for it to select.
        This value is read-only."
    REFERENCE
        "IEEE 802.3 Subclause 30.7.2.1.12"
    ::= { acDot3adAggPortEntry 14 }


acDot3adAggPortAttachedAggID OBJECT-TYPE
    SYNTAX       AcAggInstanceValue
--    SYNTAX       InterfaceIndex
    MAX-ACCESS   read-only
    STATUS       current
    DESCRIPTION
        "The identifier value of the Aggregator that this
        Aggregation Port is currently attached to. Zero
        indicates that the Aggregation Port is not currently
        attached to an Aggregator.  This value is read-only."
    REFERENCE
        "IEEE 802.3 Subclause 30.7.2.1.13"
    ::= { acDot3adAggPortEntry 15 }


acDot3adAggPortActorPort OBJECT-TYPE
    SYNTAX       INTEGER (0..65535)
    MAX-ACCESS   read-only
    STATUS       current
    DESCRIPTION
        "The port number locally assigned to the Aggregation
        Port. The port number is communicated in LACPDUs as the
        Actor_Port. This value is read-only."
    REFERENCE
        "IEEE 802.3 Subclause 30.7.2.1.14"
    ::= { acDot3adAggPortEntry 16 }


acDot3adAggPortActorPortPriority OBJECT-TYPE
    SYNTAX       INTEGER (0..255)
    MAX-ACCESS   read-write
    STATUS       current
    DESCRIPTION
        "The priority value assigned to this Aggregation Port.
        This 16-bit value is read-write."
    REFERENCE
        "IEEE 802.3 Subclause 30.7.2.1.15"
    ::= { acDot3adAggPortEntry 17 }


acDot3adAggPortPartnerAdminPort OBJECT-TYPE
    SYNTAX       INTEGER (0..65535)
    MAX-ACCESS   read-write
    STATUS       current
    DESCRIPTION
        "The current administrative value of the port number for
        the protocol Partner. This is a 16-bit read-write value.
        The assigned value is used, along with the value of
        aAggPortPartnerAdminSystemPriority,
        aAggPortPartnerAdminSystemID, aAggPortPartnerAdminKey,
        and aAggPortPartnerAdminPortPriority, in order to
        achieve manually configured aggregation."
    REFERENCE
        "IEEE 802.3 Subclause 30.7.2.1.16"
    ::= { acDot3adAggPortEntry 18 }


acDot3adAggPortPartnerOperPort OBJECT-TYPE
    SYNTAX       INTEGER (0..65535)
    MAX-ACCESS   read-only
    STATUS       current
    DESCRIPTION
        "The operational port number assigned to this
        Aggregation Port by the Aggregation Port's protocol
        Partner. The value of this attribute may contain the
        manually configured value carried in
        aAggPortPartnerAdminPort if there is no protocol
        Partner. This 16-bit value is read-only."
    REFERENCE
        "IEEE 802.3 Subclause 30.7.2.1.17"
    ::= { acDot3adAggPortEntry 19 }


acDot3adAggPortPartnerAdminPortPriority OBJECT-TYPE
    SYNTAX       INTEGER (0..255)
    MAX-ACCESS   read-write
    STATUS       current
    DESCRIPTION
        "The current administrative value of the port priority
        for the protocol Partner. This is a 16-bit read-write
        value. The assigned value is used, along with the value
        of aAggPortPartnerAdminSystemPriority,
        aAggPortPartnerAdminSystemID, aAggPortPartnerAdminKey,
        and aAggPortPartnerAdminPort, in order to achieve
        manually configured aggregation."
    REFERENCE
        "IEEE 802.3 Subclause 30.7.2.1.18"
    ::= { acDot3adAggPortEntry 20 }


acDot3adAggPortPartnerOperPortPriority OBJECT-TYPE
    SYNTAX       INTEGER (0..255)
    MAX-ACCESS   read-only
    STATUS       current
    DESCRIPTION
        "The priority value assigned to this Aggregation Port by
        the Partner. The value of this attribute may contain the
        manually configured value carried in
        aAggPortPartnerAdminPortPriority if there is no protocol
        Partner. This 16-bit value is read-only."
    REFERENCE
        "IEEE 802.3 Subclause 30.7.2.1.19"
    ::= { acDot3adAggPortEntry 21 }


acDot3adAggPortActorAdminState OBJECT-TYPE
    SYNTAX       LacpState
    MAX-ACCESS   read-write
    STATUS       current
    DESCRIPTION
        "A string of 8 bits, corresponding to the administrative
        values of Actor_State (43.4.2) as transmitted by the
        Actor in LACPDUs. The first bit corresponds to bit 0 of
        Actor_State (LACP_Activity),
        the second bit corresponds to bit 1 (LACP_Timeout),
        the third bit corresponds to bit 2 (Aggregation),
        the fourth bit corresponds to bit 3 (Synchronization),
        the fifth bit corresponds to bit 4 (Collecting),
        the sixth bit corresponds to bit 5 (Distributing),
        the seventh bit corresponds to bit 6 (Defaulted),
        and the eighth bit corresponds to bit 7 (Expired).
        These values allow administrative control over the
        values of LACP_Activity, LACP_Timeout and Aggregation.
        This attribute value is read-write."
    REFERENCE
        "IEEE 802.3 Subclause 30.7.2.1.20"
    ::= { acDot3adAggPortEntry 22 }


acDot3adAggPortActorOperState OBJECT-TYPE
    SYNTAX       LacpState
    MAX-ACCESS   read-only
    STATUS       current
    DESCRIPTION
        "A string of 8 bits, corresponding to the current
        operational values of Actor_State as transmitted by the
        Actor in LACPDUs. The bit allocations are as defined in
        30.7.2.1.20. This attribute value is read-only."
    REFERENCE
        "IEEE 802.3 Subclause 30.7.2.1.21"
    ::= { acDot3adAggPortEntry 23 }


acDot3adAggPortPartnerAdminState OBJECT-TYPE
    SYNTAX       LacpState
    MAX-ACCESS   read-write
    STATUS       current
    DESCRIPTION
        "A string of 8 bits, corresponding to the current
        administrative value of Actor_State for the protocol
        Partner. The bit allocations are as defined in
        30.7.2.1.20. This attribute value is read-write. The
        assigned value is used in order to achieve manually
        configured aggregation."
    REFERENCE
        "IEEE 802.3 Subclause 30.7.2.1.22"
    ::= { acDot3adAggPortEntry 24 }


acDot3adAggPortPartnerOperState OBJECT-TYPE
    SYNTAX       LacpState
    MAX-ACCESS   read-only
    STATUS       current
    DESCRIPTION
        "A string of 8 bits, corresponding to the current values
        of Actor_State in the most recently received LACPDU
        transmitted by the protocol Partner. The bit allocations
        are as defined in 30.7.2.1.20. In the absence of an
        active protocol Partner, this value may reflect the
        manually configured value aAggPortPartnerAdminState.
        This attribute value is read-only."
    REFERENCE
        "IEEE 802.3 Subclause 30.7.2.1.23"
    ::= { acDot3adAggPortEntry 25 }


acDot3adAggPortAggregateOrIndividual OBJECT-TYPE
    SYNTAX       TruthValue
    MAX-ACCESS   read-only
    STATUS       current
    DESCRIPTION
        "A read-only Boolean value indicating whether the
        Aggregation Port is able to Aggregate (`TRUE') or is
        only able to operate as an Individual link (`FALSE')."
    REFERENCE
        "IEEE 802.3 Subclause 30.7.2.1.24"
    ::= { acDot3adAggPortEntry 26 }


-- -------------------------------------------------------------
-- LACP Statistics Table
-- -------------------------------------------------------------


acDot3adAggPortStatsTable OBJECT-TYPE
    SYNTAX      SEQUENCE OF AcDot3adAggPortStatsEntry
    MAX-ACCESS  not-accessible
    STATUS      current
    DESCRIPTION
        "A table that contains Link Aggregation information
        about every port that is associated with this device.
        A row appears in this table for each physical port."
    REFERENCE
        "IEEE 802.3 Subclause 30.7.3"
    ::= { acDot3adAggPort 2 }


acDot3adAggPortStatsEntry OBJECT-TYPE
    SYNTAX      AcDot3adAggPortStatsEntry
    MAX-ACCESS  not-accessible
    STATUS      current
    DESCRIPTION
        "A list of Link Aggregation Control Protocol statistics
        for each port on this device."
    INDEX { acDot3adAggPortNodeIdIndex, acDot3adAggPortSlotIndex, acDot3adAggPortPortIndex  }
    ::= { acDot3adAggPortStatsTable 1 }


AcDot3adAggPortStatsEntry ::=
    SEQUENCE {
        acDot3adAggPortStatsLACPDUsRx
            Counter32,
        acDot3adAggPortStatsMarkerPDUsRx
            Counter32,
        acDot3adAggPortStatsMarkerResponsePDUsRx
            Counter32,
        acDot3adAggPortStatsUnknownRx
            Counter32,
        acDot3adAggPortStatsIllegalRx
            Counter32,
        acDot3adAggPortStatsLACPDUsTx
            Counter32,
        acDot3adAggPortStatsMarkerPDUsTx
            Counter32,
        acDot3adAggPortStatsMarkerResponsePDUsTx
            Counter32
    }


acDot3adAggPortStatsLACPDUsRx OBJECT-TYPE
    SYNTAX       Counter32
    MAX-ACCESS   read-only
    STATUS       current
    DESCRIPTION
        "The number of valid LACPDUs received on this
        Aggregation Port. This value is read-only."
    REFERENCE
        "IEEE 802.3 Subclause 30.7.3.1.2"
    ::= { acDot3adAggPortStatsEntry 1 }


acDot3adAggPortStatsMarkerPDUsRx OBJECT-TYPE
    SYNTAX       Counter32
    MAX-ACCESS   read-only
    STATUS       current
    DESCRIPTION
        "The number of valid Marker PDUs received on this
        Aggregation Port. This value is read-only."
    REFERENCE
        "IEEE 802.3 Subclause 30.7.3.1.3"
    ::= { acDot3adAggPortStatsEntry 2 }


acDot3adAggPortStatsMarkerResponsePDUsRx OBJECT-TYPE
    SYNTAX       Counter32
    MAX-ACCESS   read-only
    STATUS       current
    DESCRIPTION
        "The number of valid Marker Response PDUs received on
        this Aggregation Port. This value is read-only."
    REFERENCE
        "IEEE 802.3 Subclause 30.7.3.1.4"
    ::= { acDot3adAggPortStatsEntry 3 }


acDot3adAggPortStatsUnknownRx OBJECT-TYPE
    SYNTAX       Counter32
    MAX-ACCESS   read-only
    STATUS       current
    DESCRIPTION
        "The number of frames received that either:
        - carry the Slow Protocols Ethernet Type value (43B.4),
          but contain an unknown PDU,  or:
        - are addressed to the Slow Protocols group MAC
          Address (43B.3), but do not carry the Slow Protocols
          Ethernet Type.
        This value is read-only."
    REFERENCE
        "IEEE 802.3 Subclause 30.7.3.1.5"
    ::= { acDot3adAggPortStatsEntry 4 }


acDot3adAggPortStatsIllegalRx OBJECT-TYPE
    SYNTAX       Counter32
    MAX-ACCESS   read-only
    STATUS       current
    DESCRIPTION
        "The number of frames received that carry the Slow
        Protocols Ethernet Type value (43B.4), but contain a
        badly formed PDU or an illegal value of Protocol Subtype
        (43B.4). This value is read-only."
    REFERENCE
        "IEEE 802.3 Subclause 30.7.3.1.6"
    ::= { acDot3adAggPortStatsEntry 5 }


acDot3adAggPortStatsLACPDUsTx OBJECT-TYPE
    SYNTAX       Counter32
    MAX-ACCESS   read-only
    STATUS       current
    DESCRIPTION
        "The number of LACPDUs transmitted on this
        Aggregation Port. This value is read-only."
    REFERENCE
        "IEEE 802.3 Subclause 30.7.3.1.7"
    ::= { acDot3adAggPortStatsEntry 6 }


acDot3adAggPortStatsMarkerPDUsTx OBJECT-TYPE
    SYNTAX       Counter32
    MAX-ACCESS   read-only
    STATUS       current
    DESCRIPTION
        "The number of Marker PDUs transmitted on this
        Aggregation Port. This value is read-only."
    REFERENCE
        "IEEE 802.3 Subclause 30.7.3.1.8"
    ::= { acDot3adAggPortStatsEntry 7 }


acDot3adAggPortStatsMarkerResponsePDUsTx OBJECT-TYPE
    SYNTAX       Counter32
    MAX-ACCESS   read-only
    STATUS       current
    DESCRIPTION
        "The number of Marker Response PDUs transmitted
        on this Aggregation Port. This value is read-only."
    REFERENCE
        "IEEE 802.3 Subclause 30.7.3.1.9"
    ::= { acDot3adAggPortStatsEntry 8 }


-- -------------------------------------------------------------
-- LACP Debug Table
-- -------------------------------------------------------------
acDot3adAggPortDebugTable OBJECT-TYPE
    SYNTAX      SEQUENCE OF AcDot3adAggPortDebugEntry
    MAX-ACCESS  not-accessible
    STATUS      current
    DESCRIPTION
        "A table that contains Link Aggregation debug
        information about every port that is associated with
        this device.  A row appears in this table for each
        physical port."
    REFERENCE
        "IEEE 802.3 Subclause 30.7.4"
    ::= { acDot3adAggPort 3 }


acDot3adAggPortDebugEntry OBJECT-TYPE
    SYNTAX      AcDot3adAggPortDebugEntry
    MAX-ACCESS  not-accessible
    STATUS      current
    DESCRIPTION
        "A list of the debug parameters for a port."
    INDEX { acDot3adAggPortNodeIdIndex, acDot3adAggPortSlotIndex, acDot3adAggPortPortIndex  }
    ::= { acDot3adAggPortDebugTable 1 }


AcDot3adAggPortDebugEntry ::=
    SEQUENCE {
        acDot3adAggPortDebugRxState
            INTEGER,
        acDot3adAggPortDebugLastRxTime
            TimeTicks,
        acDot3adAggPortDebugMuxState
            INTEGER,
        acDot3adAggPortDebugMuxReason
            DisplayString,
        acDot3adAggPortDebugActorChurnState
            ChurnState,
        acDot3adAggPortDebugPartnerChurnState
            ChurnState,
        acDot3adAggPortDebugActorChurnCount
            Counter32,
        acDot3adAggPortDebugPartnerChurnCount
            Counter32,
        acDot3adAggPortDebugActorSyncTransitionCount
            Counter32,
        acDot3adAggPortDebugPartnerSyncTransitionCount
            Counter32,
        acDot3adAggPortDebugActorChangeCount
            Counter32,
        acDot3adAggPortDebugPartnerChangeCount
            Counter32
    }


acDot3adAggPortDebugRxState OBJECT-TYPE
    SYNTAX       INTEGER {
                    currentRx(1),
                    expired(2),
                    defaulted(3),
                    initialize(4),
                    lacpDisabled(5),
                    portDisabled(6)
                }
    MAX-ACCESS   read-only
    STATUS       current
    DESCRIPTION
        "This attribute holds the value `currentRx' if the
        Receive state machine for the Aggregation Port is in the
        CURRENT state, `expired' if the Receive state machine is
        in the EXPIRED state, `defaulted' if the Receive state
        machine is in the DEFAULTED state, `initialize' if the
        Receive state machine is in the INITIALIZE state,
        `lacpDisabled' if the Receive state machine is in the
        LACP_DISABLED state, or `portDisabled' if the Receive
        state machine is in the PORT_DISABLED state.
        This value is read-only."
    REFERENCE
        "IEEE 802.3 Subclause 30.7.4.1.2"
    ::= { acDot3adAggPortDebugEntry 1 }


acDot3adAggPortDebugLastRxTime OBJECT-TYPE
    SYNTAX       TimeTicks
    MAX-ACCESS   read-only
    STATUS       current
    DESCRIPTION
        "The value of aTimeSinceSystemReset (F.2.1) when
        the last LACPDU was received by this Aggregation Port.
        This value is read-only."
    REFERENCE
        "IEEE 802.3 Subclause 30.7.4.1.3"
    ::= { acDot3adAggPortDebugEntry 2 }


acDot3adAggPortDebugMuxState OBJECT-TYPE
    SYNTAX       INTEGER {
                    detached(1),
                    waiting(2),
                    attached(3),
                    collecting(4),
                    distributing(5),
                    collectingDistributing(6)
             }
    MAX-ACCESS   read-only
    STATUS       current
    DESCRIPTION
        "This attribute holds the value `detached' if the Mux
        state machine (43.4.14) for the Aggregation Port is in
        the DETACHED state, `waiting' if the Mux state machine
        is in the WAITING state, `attached' if the Mux state
        machine for the Aggregation Port is in the ATTACHED
        state, `collecting' if the Mux state machine for the
        Aggregation Port is in the COLLECTING state,
        `distributing' if the Mux state machine for the
        Aggregation Port is in the DISTRIBUTING state, and
        `collectingDistributing' if the Mux state machine for
        the Aggregation Port is in the COLLECTING_DISTRIBUTING
        state. This value is read-only."
    REFERENCE
        "IEEE 802.3 Subclause 30.7.4.1.4"
    ::= { acDot3adAggPortDebugEntry 3 }


acDot3adAggPortDebugMuxReason OBJECT-TYPE
    SYNTAX       DisplayString
    MAX-ACCESS   read-only
    STATUS       current
    DESCRIPTION
        "A human-readable text string indicating the reason
        for the most recent change of Mux machine state.
        This value is read-only."
    REFERENCE
        "IEEE 802.3 Subclause 30.7.4.1.5"
    ::= { acDot3adAggPortDebugEntry 4 }


acDot3adAggPortDebugActorChurnState OBJECT-TYPE
    SYNTAX       ChurnState
    MAX-ACCESS   read-only
    STATUS       current
    DESCRIPTION
        "The state of the Actor Churn Detection machine
        (43.4.17) for the Aggregation Port. A value of `noChurn'
        indicates that the state machine is in either the
        NO_ACTOR_CHURN or the ACTOR_CHURN_MONITOR state, and
        `churn' indicates that the state machine is in the
        ACTOR_CHURN state. This value is read-only."
    REFERENCE
        "IEEE 802.3 Subclause 30.7.4.1.6"
    ::= { acDot3adAggPortDebugEntry 5 }


acDot3adAggPortDebugPartnerChurnState OBJECT-TYPE
    SYNTAX       ChurnState
    MAX-ACCESS   read-only
    STATUS       current
    DESCRIPTION
        "The state of the Partner Churn Detection machine
        (43.4.17) for the Aggregation Port. A value of `noChurn'
        indicates that the state machine is in either the
        NO_PARTNER_CHURN or the PARTNER_CHURN_MONITOR state, and
        `churn' indicates that the state machine is in the
        PARTNER_CHURN state. This value is read-only."
    REFERENCE
        "IEEE 802.3 Subclause 30.7.4.1.7"
    ::= { acDot3adAggPortDebugEntry 6 }


acDot3adAggPortDebugActorChurnCount OBJECT-TYPE
    SYNTAX       Counter32
    MAX-ACCESS   read-only
    STATUS       current
    DESCRIPTION
        "Count of the number of times the Actor Churn state
        machine has entered the ACTOR_CHURN state.
        This value is read-only."
    REFERENCE
        "IEEE 802.3 Subclause 30.7.4.1.8"
    ::= { acDot3adAggPortDebugEntry 7 }


acDot3adAggPortDebugPartnerChurnCount OBJECT-TYPE
    SYNTAX       Counter32
    MAX-ACCESS   read-only
    STATUS       current
    DESCRIPTION
        "Count of the number of times the Partner Churn
        state machine has entered the PARTNER_CHURN state.
        This value is read-only."
    REFERENCE
        "IEEE 802.3 Subclause 30.7.4.1.9"
    ::= { acDot3adAggPortDebugEntry 8 }


acDot3adAggPortDebugActorSyncTransitionCount OBJECT-TYPE
    SYNTAX       Counter32
    MAX-ACCESS   read-only
    STATUS       current
    DESCRIPTION
        "Count of the number of times the Actor's Mux state
        machine (43.4.15) has entered the IN_SYNC state.
        This value is read-only."
    REFERENCE
        "IEEE 802.3 Subclause 30.7.4.1.10"
    ::= { acDot3adAggPortDebugEntry 9 }


acDot3adAggPortDebugPartnerSyncTransitionCount OBJECT-TYPE
    SYNTAX       Counter32
    MAX-ACCESS   read-only
    STATUS       current
    DESCRIPTION
        "Count of the number of times the Partner's Mux
        state machine (43.4.15) has entered the IN_SYNC state.
        This value is read-only."
    REFERENCE
        "IEEE 802.3 Subclause 30.7.4.1.11"
    ::= { acDot3adAggPortDebugEntry 10 }


acDot3adAggPortDebugActorChangeCount OBJECT-TYPE
    SYNTAX       Counter32
    MAX-ACCESS   read-only
    STATUS       current
    DESCRIPTION
        "Count of the number of times the Actor's perception of
        the LAG ID for this Aggregation Port has changed.
        This value is read-only."
    REFERENCE
        "IEEE 802.3 Subclause 30.7.4.1.12"
    ::= { acDot3adAggPortDebugEntry 11 }


acDot3adAggPortDebugPartnerChangeCount OBJECT-TYPE
    SYNTAX       Counter32
    MAX-ACCESS   read-only
    STATUS       current
    DESCRIPTION
        "Count of the number of times the Partner's perception
        of the LAG ID (see 43.3.6.1) for this Aggregation Port
        has changed. This value is read-only."
    REFERENCE
        "IEEE 802.3 Subclause 30.7.4.1.13"
    ::= { acDot3adAggPortDebugEntry 12 }

-- -------------------------------------------------------------
-- IEEE 802.3ad MIB - Conformance Information
-- -------------------------------------------------------------

acDot3adAggConformance OBJECT IDENTIFIER ::= { acLagMIB 2 }


acDot3adAggGroups OBJECT IDENTIFIER ::= { acDot3adAggConformance 1 }


acDot3adAggCompliances OBJECT IDENTIFIER
    ::= { acDot3adAggConformance 2 }

-- -------------------------------------------------------------
-- units of conformance
-- -------------------------------------------------------------

acDot3adAggGroup OBJECT-GROUP
    OBJECTS {
        acDot3adAggActorSystemID,
        acDot3adAggActorSystemPriority,
        acDot3adAggAggregateOrIndividual,
        acDot3adAggActorAdminKey,
        acDot3adAggMACAddress,
        acDot3adAggActorOperKey,
        acDot3adAggPartnerSystemID,
        acDot3adAggPartnerSystemPriority,
        acDot3adAggPartnerOperKey,
        acDot3adAggCollectorMaxDelay
    }
    STATUS      current
    DESCRIPTION
        "A collection of objects providing information about an
        aggregation."
    ::= { acDot3adAggGroups 1 }


acDot3adAggPortListGroup OBJECT-GROUP
    OBJECTS {
        acDot3adAggPortListPorts
    }
    STATUS      current
    DESCRIPTION
        "A collection of objects providing information about
        every port in an aggregation."
    ::= { acDot3adAggGroups 2 }


acDot3adAggPortGroup OBJECT-GROUP
    OBJECTS {
        acDot3adAggPortActorSystemPriority,
        acDot3adAggPortActorSystemID,
        acDot3adAggPortActorAdminKey,
        acDot3adAggPortActorOperKey,
        acDot3adAggPortPartnerAdminSystemPriority,
        acDot3adAggPortPartnerOperSystemPriority,
        acDot3adAggPortPartnerAdminSystemID,
        acDot3adAggPortPartnerOperSystemID,
        acDot3adAggPortPartnerAdminKey,
        acDot3adAggPortPartnerOperKey,
        acDot3adAggPortSelectedAggID,
        acDot3adAggPortAttachedAggID,
        acDot3adAggPortActorPort,
        acDot3adAggPortActorPortPriority,
        acDot3adAggPortPartnerAdminPort,
        acDot3adAggPortPartnerOperPort,
        acDot3adAggPortPartnerAdminPortPriority,
        acDot3adAggPortPartnerOperPortPriority,
        acDot3adAggPortActorAdminState,
        acDot3adAggPortActorOperState,
        acDot3adAggPortPartnerAdminState,
        acDot3adAggPortPartnerOperState,
        acDot3adAggPortAggregateOrIndividual
    }
    STATUS      current
    DESCRIPTION
        "A collection of objects providing information about
        every port in an aggregation."
    ::= { acDot3adAggGroups 3 }


acDot3adAggPortStatsGroup OBJECT-GROUP
    OBJECTS {
        acDot3adAggPortStatsLACPDUsRx,
        acDot3adAggPortStatsMarkerPDUsRx,
        acDot3adAggPortStatsMarkerResponsePDUsRx,
        acDot3adAggPortStatsUnknownRx,
        acDot3adAggPortStatsIllegalRx,
        acDot3adAggPortStatsLACPDUsTx,
        acDot3adAggPortStatsMarkerPDUsTx,
        acDot3adAggPortStatsMarkerResponsePDUsTx
    }
    STATUS      current
    DESCRIPTION
        "A collection of objects providing information about
        every port in an aggregation."
    ::= { acDot3adAggGroups 4 }


acDot3adAggPortDebugGroup OBJECT-GROUP
    OBJECTS {
        acDot3adAggPortDebugRxState,
        acDot3adAggPortDebugLastRxTime,
        acDot3adAggPortDebugMuxState,
        acDot3adAggPortDebugMuxReason,
        acDot3adAggPortDebugActorChurnState,
        acDot3adAggPortDebugPartnerChurnState,
        acDot3adAggPortDebugActorChurnCount,
        acDot3adAggPortDebugPartnerChurnCount,
        acDot3adAggPortDebugActorSyncTransitionCount,
        acDot3adAggPortDebugPartnerSyncTransitionCount,
        acDot3adAggPortDebugActorChangeCount,
        acDot3adAggPortDebugPartnerChangeCount
    }
    STATUS      current
    DESCRIPTION
        "A collection of objects providing debug information
        about every aggregated port."
    ::= { acDot3adAggGroups 5 }

acDot3adTablesLastChangedGroup OBJECT-GROUP
    OBJECTS {
        acDot3adTablesLastChanged
    }
    STATUS   current
    DESCRIPTION
        "A collection of objects providing information about the
        time of changes to the configuration of aggregations and
        their ports."
::= { acDot3adAggGroup 6 }

-- -------------------------------------------------------------
-- compliance statements
-- -------------------------------------------------------------


acDot3adAggCompliance MODULE-COMPLIANCE
    STATUS  current
    DESCRIPTION
        "The compliance statement for device support of
        Link Aggregation."


    MODULE
        MANDATORY-GROUPS {
            acDot3adAggGroup,
            acDot3adAggPortGroup,
           acDot3adTablesLastChangedGroup
        }


        GROUP       acDot3adAggPortListGroup
        DESCRIPTION
            "This group is optional."


        GROUP       acDot3adAggPortStatsGroup
        DESCRIPTION
            "This group is optional."


        GROUP       acDot3adAggPortDebugGroup
        DESCRIPTION
            "This group is optional."


    ::= { acDot3adAggCompliances 1 }


END
