-------------------------------------------------------------------------------
-- file: NncCEFillLevelStatistics.mib
--
-- description:
--      This file contains the SNMP definitions for the Circuit Emulation 
--      Fill level Statistics for aal1 stats which are not supported by 
--	the standard mib.
--
-- %%history-start%%
-- 97.08.27 dpochop 31A1019: Creation 
-- 97.09.02 jwei 31A1019: Fixed mibTran error 
-- %%history-end%%
--
-- Copyright 1997 Newbridge Networks Corporation.  All Rights Reserved
-------------------------------------------------------------------------------
NNCCEFILLLEVELSTATISTICS-MIB DEFINITIONS ::= BEGIN
 
  IMPORTS
    MODULE-IDENTITY, OBJECT-TYPE		FROM SNMPv2-SMI
    MODULE-COMPLIANCE, OBJECT-GROUP		FROM SNMPv2-CONF
    ifIndex                                     FROM IF-MIB
    nncExtensions				FROM NNCGNI0001-SMI;

nncCEFillLevelStatistics MODULE-IDENTITY
  LAST-UPDATED    "9708271200Z"
  ORGANIZATION    "Newbridge Networks Corporation"
  CONTACT-INFO
                  "Newbridge Networks Corporation
                   Postal: 600 March Road
                   Kanata, Ontario
                   Canada K2K 2E6
 
                   Phone:  +1 613 591 3600
                   Fax:    +1 613 591 3680"
 
  DESCRIPTION     "This module contains definitions for
		   monitoring aal1 fill level statistics."
 
  ::= { nncExtensions 47 }
 
 
  nncCEFillLevelStatisticsObjects OBJECT IDENTIFIER ::= { nncCEFillLevelStatistics 1 }
  nncCEFillLevelStatisticsGroups OBJECT IDENTIFIER ::= { nncCEFillLevelStatistics 2 }
  nncCEFillLevelStatisticsCompliances OBJECT IDENTIFIER ::= { nncCEFillLevelStatistics 3 } 
 
--------------------------------------------------------------------------------
-- CE Fill Level Statistics Table
--------------------------------------------------------------------------------
 
nncCEFillLevelStatisticsTable    OBJECT-TYPE
    SYNTAX        SEQUENCE OF NncCEFillLevelStatisticsEntry
    MAX-ACCESS    not-accessible
    STATUS        current
    DESCRIPTION
        "The nncCEFillLevelStatisticsTable contains objects
	for monitoring the maximum and minimum fill levels
	reached by the playout buffer"
    ::= { nncCEFillLevelStatisticsObjects 1 }
 
nncCEFillLevelStatisticsEntry    OBJECT-TYPE
    SYNTAX        NncCEFillLevelStatisticsEntry
    MAX-ACCESS    not-accessible
    STATUS        current
    DESCRIPTION
        "An entry in the nncCEFillLevelStatisticsTable."
    INDEX  { ifIndex }
    ::= { nncCEFillLevelStatisticsTable 1 }
 
NncCEFillLevelStatisticsEntry ::= SEQUENCE  {
    nncCEMinFillLevel           INTEGER,
    nncCEMaxFillLevel           INTEGER
    }

nncCEMinFillLevel         OBJECT-TYPE
    SYNTAX        INTEGER (0..6000)
    MAX-ACCESS    read-only
    STATUS        current
    DESCRIPTION
	"This value represents the minimum fill level reached by
	the playout buffer measured in micro seconds."
    ::= { nncCEFillLevelStatisticsEntry 1 }

nncCEMaxFillLevel         OBJECT-TYPE
    SYNTAX        INTEGER (0..6000)
    MAX-ACCESS    read-only
    STATUS        current
    DESCRIPTION
        "This value represents the maximum fill level reached by
        the playout buffer measured in micro seconds."
    ::= { nncCEFillLevelStatisticsEntry 2 }

 
--------------------------------------------------------------------------------
-- Conformance Group Definitions
--------------------------------------------------------------------------------
 
nncCERawFillLevelStatisticsGroups        OBJECT-GROUP
  OBJECTS {
    nncCEMinFillLevel,
    nncCEMaxFillLevel
  }
  STATUS          current
  DESCRIPTION     "Collection of objects providing raw fill stats."
  ::= { nncCEFillLevelStatisticsGroups 1 }

--------------------------------------------------------------------------------
-- Compliance Statements (mandatory)
--------------------------------------------------------------------------------
nncCEFillLevelStatisticsCompliance    MODULE-COMPLIANCE
  STATUS          current
  DESCRIPTION     "The compliance statement for Newbridge SNMP."
  MODULE
    MANDATORY-GROUPS {
      nncCERawFillLevelStatisticsGroups
    }
  ::= { nncCEFillLevelStatisticsCompliances 1 }
 
 
-------------------------------------------------------------------------------
--      Review Minutes
-------------------------------------------------------------------------------
END -- DEFINITION OF NNCCEFILLLEVELSTATISTICS-MIB
