-- 
-- Copyright 1999 by Fore Systems, Inc. 
-- Converted to SMIv2 rfc 2578,2579,2580 - STD 58
--
-- Copyright 1999 by Fore Systems, Inc.
-- All Rights Reserved
--
-- This mib implements management information for the ATM
-- traffic convergence layer in an atm interface.  The
-- reference model for this looks like:
--
-- Cells -> AtmInterface -> TC -> Physical Interface
--
-- In the case of a DS3 carrying cells in PLCP frames
-- the model looks like
--
-- Cells -> Atm Interface -> TC -> PLCP Framer -> Phy
--
-- This mib is organized into 3 tables
--
-- Configuration Table
-- Total Table
-- Diagnostics Table
--

Fore-TC-MIB DEFINITIONS ::= BEGIN

IMPORTS
         Integer32,
	 Counter32,
	 OBJECT-TYPE,
	 NOTIFICATION-TYPE,
	 MODULE-IDENTITY      	FROM	SNMPv2-SMI
	 asx		      	FROM	Fore-Common-MIB
	 ifIndex,ifName	       	FROM	IF-MIB
	 trapLogIndex		FROM	Fore-TrapLog-MIB;

foreTcMib            MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "
	      This mib implements management information for the ATM
	      traffic convergence layer in an atm interface."
    ::= { asx 12 }

foreTcConfigTable OBJECT-TYPE
	 SYNTAX	SEQUENCE OF ForeTcConfigEntry
	 MAX-ACCESS	not-accessible
	 STATUS	current
	 DESCRIPTION
		 "A table of ATM Cell Convergence Layer
		  configuration parameters."
	 ::= { foreTcMib 1 }

foreTcConfigEntry OBJECT-TYPE
	 SYNTAX	ForeTcConfigEntry
	 MAX-ACCESS	not-accessible
	 STATUS	current
	 DESCRIPTION
		 "A table entry containing ATM Cell convergence layer
		 configuration information for each atm interface."
	 INDEX	{  ifIndex }
	 ::= { foreTcConfigTable 1 }

ForeTcConfigEntry ::=
	 SEQUENCE {
		foreTcConfigCellScrambling      INTEGER,
		foreTcConfigEmptyCell	    	INTEGER,
		foreTcConfigLoopback	     	INTEGER,
		foreTcConfigFramingMode	   	INTEGER,
		foreTcConfigStatus		Integer32
	}

foreTcConfigCellScrambling OBJECT-TYPE
	SYNTAX		INTEGER {
		scrambling(1),
		noScrambling(2)
		}
	MAX-ACCESS		read-write
	STATUS		current
	DESCRIPTION
		 "This variable indicates if cell payload scrambling
		  is enabled.  If enabled, all outgoing
		  cell payloads are scrambled via the X**43+1 generator
		  polynomial as defined in ITU I.432.1 and all
		  incoming cell payloads are descrambled by the same
		  mechanism."
	 ::= { foreTcConfigEntry 1 }

foreTcConfigEmptyCell OBJECT-TYPE
	SYNTAX		INTEGER {
			idle(1),
			unassigned(2)
			}
	MAX-ACCESS		read-write
	STATUS		current
	DESCRIPTION
		"This variable indicates the type of ATM cells inserted
		 into the outgoing data stream when there is no real
		 data to send.  There are two choices:

		    idle -> All bits 0 except that CLP is set to 1
		    unassigned -> All bits 0
		
		 The default value is to send unassigned cells."
	::= { foreTcConfigEntry 2 }

foreTcConfigLoopback  OBJECT-TYPE
	SYNTAX	 INTEGER {
			    tcNoLoop(1),
			    tcDiagLoop(2),
			    tcPayloadLoop(3)
			}
	MAX-ACCESS		read-write
	STATUS		current
	DESCRIPTION
		"This variable indicates if cell loopback is enabled
		at the TC layer.  There are three choices:

		 tcNoLoop - Normal operating mode, cells are passed through.
		 tcDiagLoop - Diagnostic mode.  Transmitted cells are looped
			      back to the ATM interface.
		 tcPayloadLoop - Payload Loopback.  Received cells are looped
			      back to the Phy port."
	::= { foreTcConfigEntry 3 }

foreTcConfigFramingMode OBJECT-TYPE
	SYNTAX	INTEGER {
		   tcFramingDirect(1),
		   tcFramingPlcp(2)
		}
	MAX-ACCESS	read-write
	STATUS	current
	DESCRIPTION
		"This variable configures and indicates the method
		 used to encapsulate ATM cells in the data stream.
		 There are two choices:

		 tcFramingDirect - Direct insertion of cells into
				   the data stream.
		 tcFramingPlcp   - Use PLCP framing. Typically this
				   is used on T1/E1 and T3/E3 lines.

		 Not all interfaces may support all modes.  It is
		 possible on some interfaces, for example Sonet,
		 that this is implemented as a read-only variable
		 set to tcFramingDirect."
	::= { foreTcConfigEntry 4 }

foreTcConfigStatus OBJECT-TYPE
	SYNTAX	Integer32
	MAX-ACCESS	read-only
	STATUS	current
	DESCRIPTION
		"This variable indicates the ATM Status of the interface.
		 The variable is a bit map represented as a sum, therefore
		 it can represent multiple defects simultaneously.  The
		 sonetAtmNoDefect should be set if and only if no other flag
		 is set.

		 The various bit mask values  are:
		  1  sonetAtmNoDefect
		  2  sonetAtmLCD	Loss of Cell Delineation was detected.
					LCD is declared when a 'normal pointer
					value' is not found for eight 
					consecutive frames.
		  4  sonetAtmPlcpLOF    Valid PLCP frames were not detected at
                                        the interface.
                  8  sonetAtmPlcpYellow Plcp Yellow alarm was detected in the
                                        incoming PLCP frame stream."
	DEFVAL { 1 }
	::= { foreTcConfigEntry 5 }

foreTcTotalTable OBJECT-TYPE
	 SYNTAX	SEQUENCE OF ForeTcTotalEntry
	 MAX-ACCESS	not-accessible
	 STATUS	current
	 DESCRIPTION
		 "A table of ATM Cell Convergence Layer statistics."
	 ::= { foreTcMib 2 }

foreTcTotalEntry OBJECT-TYPE
	 SYNTAX	ForeTcTotalEntry
	 MAX-ACCESS	not-accessible
	 STATUS	current
	 DESCRIPTION
		 "A table entry containing ATM Cell convergence layer
		 statistics for each atm interface."
	 INDEX	{  ifIndex }
	 ::= { foreTcTotalTable 1 }

ForeTcTotalEntry ::=
	 SEQUENCE {
		foreTcTotalLcdSeconds       Counter32,
		foreTcTotalCorrectableHcs   Counter32,
		foreTcTotalUncorrectableHcs Counter32,
		foreTcTotalTxCells	  Counter32,
		foreTcTotalRxCells	  Counter32
	}

foreTcTotalLcdSeconds OBJECT-TYPE
	SYNTAX		Counter32
	MAX-ACCESS		read-only
	STATUS		current
	DESCRIPTION
		"The number of seconds in which the LCD (loss of cell
		 delineation) defect occured.  An LCD defect is detected
		 when an out of cell delineation state has persisted for
		 4ms.  The defect is cleared when sync state has been
		 maintained for 4ms."
	::= { foreTcTotalEntry 1 }

foreTcTotalCorrectableHcs OBJECT-TYPE
	SYNTAX		Counter32
	MAX-ACCESS		read-only
	STATUS		current
	DESCRIPTION
		"The number of correctable Header Check Sequence (HCS) 
		 error events that have occured since the port has been reset."
	::= { foreTcTotalEntry 2 }

foreTcTotalUncorrectableHcs OBJECT-TYPE
	SYNTAX		Counter32
	MAX-ACCESS		read-only
	STATUS		current
	DESCRIPTION
		"The number of uncorrectable Header Check Sequence (HCS) 
		 error events that have occured since the port has been reset."
	::= { foreTcTotalEntry 3 }

foreTcTotalTxCells OBJECT-TYPE
	SYNTAX	Counter32
	MAX-ACCESS	read-only
	STATUS	current
	DESCRIPTION
		"The number of cells that were transmitted 
		for this atm interface."
	::= { foreTcTotalEntry 4 }

foreTcTotalRxCells OBJECT-TYPE
	SYNTAX	Counter32
	MAX-ACCESS	read-only
	STATUS	current
	DESCRIPTION
		"The number of cells that were received 
		on this atm interface."
	::= { foreTcTotalEntry 5 }


-- foreTcDiagnosticsTable OBJECT-TYPE
--	 SYNTAX	SEQUENCE OF ForeTcDiagnosticsEntry
--	 MAX-ACCESS	not-accessible
--	 STATUS	current
--	 DESCRIPTION
--		 "A table of ATM Cell Convergence Layer
--		  diagnostics control parameters."
--	 ::= { foreTcMib 3 }

foreTcCurrentTable OBJECT-TYPE
         SYNTAX SEQUENCE OF ForeTcCurrentEntry
         MAX-ACCESS not-accessible
         STATUS current
         DESCRIPTION
                 "A table of ATM Cell Convergence Layer statistics."
         ::= { foreTcMib 4 }

foreTcCurrentEntry OBJECT-TYPE
         SYNTAX ForeTcCurrentEntry
         MAX-ACCESS not-accessible
         STATUS current
         DESCRIPTION
                 "A table entry containing ATM Cell convergence layer
                 statistics for each atm interface."
         INDEX  {  ifIndex }
         ::= { foreTcCurrentTable 1 }

ForeTcCurrentEntry ::=
         SEQUENCE {
                foreTcCurrentErrSeconds       Counter32,
                foreTcCurrentSevErrSeconds    Counter32,
                foreTcCurrentUnavailSeconds Counter32,
                foreTcCurrentCorrectableHcs   Counter32,
                foreTcCurrentUncorrectableHcs Counter32
        }

foreTcCurrentErrSeconds OBJECT-TYPE
        SYNTAX          Counter32
        MAX-ACCESS          read-only
        STATUS          current
        DESCRIPTION
          "Number of Errored Seconds"
        ::= { foreTcCurrentEntry 1 }

foreTcCurrentSevErrSeconds OBJECT-TYPE
        SYNTAX          Counter32
        MAX-ACCESS      read-only
        STATUS          current
        DESCRIPTION
          "Number of Severely Errored Seconds"
        ::= { foreTcCurrentEntry 2 }

foreTcCurrentUnavailSeconds OBJECT-TYPE
        SYNTAX          Counter32
        MAX-ACCESS      read-only
        STATUS          current
        DESCRIPTION
          "Number of Unavailable Seconds"
        ::= { foreTcCurrentEntry 3 }

foreTcCurrentCorrectableHcs OBJECT-TYPE
        SYNTAX          Counter32
        MAX-ACCESS      read-only
        STATUS          current
        DESCRIPTION
                "The number of correctable Header Check Sequence (HCS)
                 error events that have occured since the port has been reset."
        ::= { foreTcCurrentEntry 4 }

foreTcCurrentUncorrectableHcs OBJECT-TYPE
        SYNTAX          Counter32
        MAX-ACCESS      read-only
        STATUS          current
        DESCRIPTION
                "The number of uncorrectable Header Check Sequence (HCS)
                 error events that have occured since the port has been reset."
        ::= { foreTcCurrentEntry 5 }

foreTcIntervalTable OBJECT-TYPE
         SYNTAX SEQUENCE OF ForeTcIntervalEntry
         MAX-ACCESS not-accessible
         STATUS current
         DESCRIPTION
                 "A table of ATM Cell Convergence Layer statistics."
         ::= { foreTcMib 5 }

foreTcIntervalEntry OBJECT-TYPE
         SYNTAX ForeTcIntervalEntry
         MAX-ACCESS not-accessible
         STATUS current
         DESCRIPTION
                 "A table entry containing ATM Cell convergence layer
                 statistics for each atm interface."
         INDEX  { ifIndex, foreTcInterval}
         ::= { foreTcIntervalTable 1 }

ForeTcIntervalEntry ::=
         SEQUENCE {
                foreTcInterval                 Integer32,
                foreTcIntervalErrSeconds       Counter32,
                foreTcIntervalSevErrSeconds    Counter32,
                foreTcIntervalUnavailSeconds   Counter32,
                foreTcIntervalCorrectableHcs   Counter32,
                foreTcIntervalUncorrectableHcs Counter32
        }

foreTcInterval OBJECT-TYPE
        SYNTAX          Integer32 
        MAX-ACCESS      read-only 
        STATUS          current
        DESCRIPTION
          "Interval number"
        ::= { foreTcIntervalEntry 1 }

foreTcIntervalErrSeconds OBJECT-TYPE
        SYNTAX          Counter32
        MAX-ACCESS       read-only
        STATUS           current
        DESCRIPTION
          "Number of Errored Seconds"
        ::= { foreTcIntervalEntry 2 }

foreTcIntervalSevErrSeconds OBJECT-TYPE
        SYNTAX          Counter32
        MAX-ACCESS      read-only
        STATUS          current
        DESCRIPTION
          "Number of Severely Errored Seconds"
        ::= { foreTcIntervalEntry 3 }

foreTcIntervalUnavailSeconds OBJECT-TYPE
        SYNTAX          Counter32
        MAX-ACCESS      read-only
        STATUS          current
        DESCRIPTION
          "Number of Unavailable Seconds"
        ::= { foreTcIntervalEntry 4 }

foreTcIntervalCorrectableHcs OBJECT-TYPE
        SYNTAX          Counter32
        MAX-ACCESS      read-only
        STATUS          current
        DESCRIPTION
                "The number of correctable Header Check Sequence (HCS)
                 error events that have occured since the port has been reset."
        ::= { foreTcIntervalEntry 5 }

foreTcIntervalUncorrectableHcs OBJECT-TYPE
        SYNTAX          Counter32
        MAX-ACCESS      read-only
        STATUS          current
        DESCRIPTION
                "The number of uncorrectable Header Check Sequence (HCS)
                 error events that have occured since the port has been reset."
        ::= { foreTcIntervalEntry 6 }

-- The diagnostics table format will be fully defined later.  These
-- definitions are tentative and are subject to change.

-- foreTcDiagnosticsEntry OBJECT-TYPE
-- 	 SYNTAX	ForeTcDiagnosticsEntry
-- 	 ACCESS	not-accessible
-- 	 STATUS	mandatory
-- 	 DESCRIPTION
-- 		 "A table entry containing ATM Transmission
-- 		  Convergence layer diagnostics control
-- 		  information."
-- 	 INDEX	{  ifIndex }
-- 	 ::= { foreTcDiagnosticsTable 1 }
-- 
-- ForeTcDiagnosticsEntry ::=
-- 	 SEQUENCE {
-- 		foreTcDiagnosticsAtmDiagnostic   INTEGER
-- 	}
-- 
-- foreTcDiagnosticsAtmDiagnostic OBJECT-TYPE
-- 	SYNTAX	INTEGER
-- 	ACCESS	read-write
-- 	STATUS	mandatory
-- 	DESCRIPTION
-- 		"This variable controls the insertion of various types
-- 		of atm diagnostic bit patterns in the transmit
-- 		stream.  It is a bit map that is netmod specific.
-- 		Under normal operation it should be set to:
-- 
-- 		1 None : No diagnostics
-- 
-- 		2 DHCS : Controls the insertion of HCS errors.  When
-- 		DHCS is on, the HCS octet is inverted prior to
-- 		insertion in the synchronous payload envelope.  DHCS
-- 		takes effect unconditionally regardless of whether a
-- 		null/unassigned cell is being transmitted or whether
-- 		the HCS octet has been read from the FIFO.
-- 
-- 		Note that not all available diagnostics may be available
-- 		for all interfaces.
-- 		"
-- 	DEFVAL { 1 }
-- 	::= { foreTcDiagnosticsEntry 1 }
-- 
 
-- Trap Section
 
foreTcLCDDetected NOTIFICATION-TYPE
	OBJECTS { ifIndex, ifName, trapLogIndex }
	STATUS      current
	DESCRIPTION
		"This trap indicates that the specified SONET port is
		experiencing Loss of Cell Deliniation (LCD). A LCD
		failure is declared when the LCD defect persists for a
		period of 2.5 +/- 0.5 seconds."
	::= { foreTcMib 0 1 }

foreTcLCDCleared NOTIFICATION-TYPE
	OBJECTS { ifIndex,  ifName, trapLogIndex }
	STATUS      current
	DESCRIPTION
		"This trap indicates that the LCD failure identified
		by trap asxSonetAtmLCDDetected has been cleared. A LCD
		failure is cleared when the LCD defect is absent for
		10 +/- 0.5 seconds."
	::= { foreTcMib 0 2 }

END
