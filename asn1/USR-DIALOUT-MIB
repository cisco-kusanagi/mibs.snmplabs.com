USR-DIALOUT-MIB DEFINITIONS ::= BEGIN
     IMPORTS
            OBJECT-TYPE, MODULE-IDENTITY,
            IpAddress, Integer32
                  FROM SNMPv2-SMI
            DisplayString
                  FROM SNMPv2-TC
            common, UsrConfigStatus
                  FROM USR-DEFINITIONS-MIB;
usrDialout MODULE-IDENTITY
        LAST-UPDATED "200205011316Z"
        ORGANIZATION "CommWorks Corporation, a 3Com Company"
        CONTACT-INFO "Customer Support"
        DESCRIPTION
                "The commWorks enterprise defined MIB objects
                 for Dialout."
--      REVISION "200205011316Z"
--      DESCRIPTION "Converted to SNMPv2"
        ::= { common 25 }
-- textual conventions
-- 
-- textual conventions are like pre-processor macro in 'C'
--        (i.e. #define statements)
-- Use them to define your own 'datatypes'
-- memory size, expressed in units of 1024bytes
usrDialoutConfigFileName OBJECT-TYPE
     SYNTAX DisplayString
     MAX-ACCESS read-only
     STATUS     current
     DESCRIPTION
       "The name of a ConfigFile to read/write permanent database
        records. If the value of this object is an empty string,
        then the Dial-out process uses the default name
        `@file://DialOutProcess.cfg'."
::= { usrDialout 1 }
usrDialoutCFMStatusFlag  OBJECT-TYPE
     SYNTAX UsrConfigStatus
     MAX-ACCESS read-write
     STATUS     current
     DESCRIPTION
       "Setting the value of this object to `save' causes the values
        of the Dial-out Group to be written out to the current config
        file, which is stored in the usrDialoutConfigFileName object.
        While the new ConfigFile is being written, the Dial-out process
        will set the value of this flag to `saving''. Any
        attempts to set the value while it is not `normal'
        (i.e. the file is currently being written to the
        ConfigFile) while result in a badValue error being
        returned. Setting the value to `normal' will result in no
        action."
::= { usrDialout 2 }
usrDialoutSecurity OBJECT-TYPE
	SYNTAX      INTEGER {
                    no(1),
                    yes(2)
                    }
	MAX-ACCESS      read-write
	STATUS          current
	DESCRIPTION
       "Setting the value of this object to yes(2) will instruct the
        Dial-out process to authenticate all network users who attempt to
        connect to a virtual port. Setting the value of this object to
        no(1) will instruct the Dial-out process to bypass the user
        authentication process."
     DEFVAL { yes }
     --CONFIGURABLE
::= { usrDialout 3 }
usrDialoutWorkstationTimeout OBJECT-TYPE
	SYNTAX      Integer32 (0..180)
	MAX-ACCESS      read-write
	STATUS          current
	DESCRIPTION
       "Even when it appears there is no activity on a connected virtual
        port, the client and server are still actively sending and
        receiving messages. If the client is re-booted, or if the client
        experiences a system error that interrupts this activity, the
        server will wait a certain amount of time before terminating the
        connection. Depending on what caused the interruption, this
        period of time may allow the client to restore the connection.
        This time-out value is specified in minutes. The default is 5
        minutes. To disable workstation time-out, set this object to 0."
     DEFVAL { 5 }
     --CONFIGURABLE
::= { usrDialout 4 }
usrDialoutUserTimeout OBJECT-TYPE
	SYNTAX      Integer32 (0..180)
	MAX-ACCESS      read-write
	STATUS          current
	DESCRIPTION
       "The User time-out is provided so that a virtual port will be
        freed for use by others when the current user is not actively
        using the virtual port. If the server does not receive any
        transmit data requests from the client for the period of the
        time-out, the session is disconnected. The time-out value is
        specified in minutes. The default is 5 minutes. To disable
        user time-out, set this object to 0."
     DEFVAL { 5 }
     --CONFIGURABLE
::= { usrDialout 5 }
usrDialoutPortTable OBJECT-TYPE
     SYNTAX     SEQUENCE OF UsrDialoutPortEntry
     MAX-ACCESS     not-accessible
     STATUS         current
     DESCRIPTION
       "A list of virtual ports available for dial-out."
::= { usrDialout 6 }
usrDialoutPortEntry OBJECT-TYPE
     SYNTAX      UsrDialoutPortEntry
     MAX-ACCESS      not-accessible
     STATUS          current
     DESCRIPTION
       "An entry containing management information applicable to a
        particular virtual port."
     INDEX { usrDialoutPortNumber }
::= { usrDialoutPortTable 1}
UsrDialoutPortEntry ::=
     SEQUENCE {
          usrDialoutPortNumber Integer32,
          usrDialoutPortGeneralName DisplayString,
          usrDialoutPortSpecificName DisplayString,
          usrDialoutPortState INTEGER,
          usrDialoutPortClientType INTEGER,
          usrDialoutPortIpxClientAddress OCTET STRING,
          usrDialoutPortIpClientAddress IpAddress
          }
usrDialoutPortNumber OBJECT-TYPE
	SYNTAX      Integer32
	MAX-ACCESS      not-accessible
	STATUS          current
	DESCRIPTION
       "The virtual port number of the dial-out port."
::= { usrDialoutPortEntry 1}
usrDialoutPortGeneralName OBJECT-TYPE
	SYNTAX      DisplayString (SIZE(8))
	MAX-ACCESS      read-only
	STATUS          current
	DESCRIPTION
       "The general service name associated with a virtual port. When a
        network user requires access to a type of service, rather than a
        specific port, the user is able to request a service by its
        general name. This provides network users access to the
        communication server ports without requiring the user to know
        the specific name or location of a port."
::= { usrDialoutPortEntry 2}
usrDialoutPortSpecificName OBJECT-TYPE
	SYNTAX      DisplayString (SIZE(14))
	MAX-ACCESS      read-only
	STATUS          current
	DESCRIPTION
       "The specific name associated with a virtual port. This allows a
        network user to locate a particular port for access to a specific
        service associated with that port."
::= { usrDialoutPortEntry 3}
usrDialoutPortState OBJECT-TYPE
	SYNTAX      INTEGER {
                    available(1),
                    unavailable(2),
                    in-use(3),
                    disconnect(4)
                    }
	MAX-ACCESS      read-write
	STATUS          current
	DESCRIPTION
       "The state of the virtual port. When a port is in the available(1)
        state, it is available to a network user. When a port is in the
        unavailable(2) state, it is not available to a network user. When
        a port is in the in-use(3) state, it is currently in use by a
        network user. Setting this object to disconnect(4) will cause a
        supervisory disconnect of the current user. Setting this object
        to any other value will have no effect."
::= { usrDialoutPortEntry 4}
usrDialoutPortClientType OBJECT-TYPE
	SYNTAX      INTEGER {
                    none(0),
                    ip(1),
                    ipx(2)
                    }
	MAX-ACCESS      read-only
	STATUS          current
	DESCRIPTION
       "The type of client that is attached to this port. This object
        is set to none(0) if no client is attached to the port."
::= { usrDialoutPortEntry 5}
usrDialoutPortIpxClientAddress OBJECT-TYPE
	SYNTAX      OCTET STRING (SIZE(6))
	MAX-ACCESS      read-only
	STATUS          current
	DESCRIPTION
       "The Ethernet address of the IPX client workstation attached
        to the port. If no client is attached to the port or an IP
        client is attached to the port, this object is set to all
        zeros."
::= { usrDialoutPortEntry 6}
usrDialoutPortIpClientAddress OBJECT-TYPE
	SYNTAX      IpAddress
	MAX-ACCESS      read-only
	STATUS          current
	DESCRIPTION
       "The IP address of the IP client workstation attached to
        the port. If no client is attached to the port or an IPX
        client is attached to the port, this object is set to all
        zeros."
::= { usrDialoutPortEntry 7}
END         -- End of USR-DIALOUT-MIB DEFINITIONS
-- ************************************************************************
--
--	usr_cli.mib
--
-- Author:         Clarise Patton
--
