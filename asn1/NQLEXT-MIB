NQLEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, IpAddress, Integer32
			FROM SNMPv2-SMI
		DisplayString, RowStatus
			FROM SNMPv2-TC
		nqlExt
			FROM APENT-MIB;

--NQLEXT MIB

    apNqlExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  Network Qualifier Lists (NQLs)"
      ::= { nqlExt 1}


apNqlTable OBJECT-TYPE
	SYNTAX          SEQUENCE OF APNqlEntry
	MAX-ACCESS      not-accessible
	STATUS          current
	DESCRIPTION
		"A list of NQLs"
	::= { nqlExt 2 }

apNqlEntry OBJECT-TYPE
	SYNTAX          APNqlEntry
	MAX-ACCESS      not-accessible
	STATUS          current
	DESCRIPTION
		"A group of information uniquely identifying an NQL. One entry
         exists for each NQL"
	INDEX   { apNqlName }
	::= { apNqlTable 1 }

APNqlEntry ::= SEQUENCE {
	apNqlStatus			RowStatus,
	apNqlName			DisplayString,
	apNqlDescription	DisplayString
}


apNqlStatus OBJECT-TYPE
	SYNTAX          RowStatus
	MAX-ACCESS      read-create
	STATUS          current
	DESCRIPTION      
		"Status entry for this row "
	::= {apNqlEntry 1}

apNqlName OBJECT-TYPE
	SYNTAX          DisplayString (SIZE(1..31))
	MAX-ACCESS      read-create
	STATUS          current
	DESCRIPTION     
			"The name of the NQL"
	::= {apNqlEntry 2}

apNqlDescription OBJECT-TYPE
	SYNTAX          DisplayString (SIZE(0..63))
	MAX-ACCESS      read-create
	STATUS          current
	DESCRIPTION     
			"An NQL description"
	::= {apNqlEntry 3}

apNqlExtTable OBJECT-TYPE
	SYNTAX          SEQUENCE OF APNqlExtEntry
	MAX-ACCESS      not-accessible
	STATUS          current
	DESCRIPTION
		"A list of IP Addresses associated with an NQL"
	::= { nqlExt 3 }

apNqlExtEntry OBJECT-TYPE
	SYNTAX          APNqlExtEntry
	MAX-ACCESS      not-accessible
	STATUS          current
	DESCRIPTION
		"Information uniquely identifying a network address within an NQL"
	INDEX   { apNqlName,apNqlExtAddress }
	::= { apNqlExtTable 1 }

APNqlExtEntry ::= SEQUENCE {
	apNqlExtStatus      RowStatus,
	apNqlExtAddress     IpAddress,
	apNqlExtPrefixLen	Integer32,
	apNqlExtDescription	DisplayString,
	apNqlExtLogEnable   INTEGER
}

apNqlExtStatus OBJECT-TYPE
	SYNTAX          RowStatus
	MAX-ACCESS      read-create
	STATUS          current
	DESCRIPTION      
		"Status entry for this row"
	::= {apNqlExtEntry 1}

apNqlExtAddress OBJECT-TYPE
	SYNTAX          IpAddress
	MAX-ACCESS      read-create
	STATUS          current
	DESCRIPTION     
			"The IP Address"
	::= {apNqlExtEntry 2}

apNqlExtPrefixLen OBJECT-TYPE
	SYNTAX          Integer32 (8..32)
	MAX-ACCESS      read-create
	STATUS          current
	DESCRIPTION     
			"The length of the IP Address Network mask"
	::= {apNqlExtEntry 3}

apNqlExtDescription OBJECT-TYPE
	SYNTAX          DisplayString (SIZE(0..63))
	MAX-ACCESS      read-create
	STATUS          current
	DESCRIPTION      
		"Description of this address range"
	::= {apNqlExtEntry 4}

apNqlExtLogEnable  OBJECT-TYPE
	SYNTAX  INTEGER {
					disable(0),
					enable(1)
 					}
	MAX-ACCESS      read-create
	STATUS          current
	DESCRIPTION      
		"Enable logging for address matches"
	::= {apNqlExtEntry 5}

END
