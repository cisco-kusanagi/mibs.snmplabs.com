Wellfleet-IPXA-MIB DEFINITIONS ::= BEGIN

-- Created by mdl2asn version 3.1
-- Creation date: Wed Aug 30 16:44:03 EDT 1995


    IMPORTS

      Counter, Opaque
        FROM RFC1155-SMI
      OBJECT-TYPE
        FROM RFC-1212
      DisplayString
        FROM RFC1213-MIB
      wfIpxGroup
        FROM Wellfleet-COMMON-MIB;


    wfIpxBasicSysTable OBJECT-TYPE
        SYNTAX SEQUENCE OF WfIpxBasicSysEntry
        ACCESS not-accessible
        STATUS mandatory
        DESCRIPTION
                "Wellfleet IPX Basic System Table"
        ::= { wfIpxGroup 15 }

    wfIpxBasicSysEntry OBJECT-TYPE
        SYNTAX WfIpxBasicSysEntry
        ACCESS not-accessible
        STATUS mandatory
        DESCRIPTION
                "An entry in the IPX Circ Table"
        INDEX  { wfIpxBasicSysInstance }
        ::= { wfIpxBasicSysTable 1 }

    WfIpxBasicSysEntry ::= SEQUENCE {
          wfIpxBasicSysDelete
         INTEGER,
          wfIpxBasicSysDisable
         INTEGER,
          wfIpxBasicSysState
         INTEGER,
          wfIpxBasicSysInstance
         INTEGER,
          wfIpxBasicSysPrimaryNetworkNumber
         OCTET STRING,
          wfIpxBasicSysMultipleHostAddresses
         INTEGER,
          wfIpxBasicSysCfgHostAddress
         OCTET STRING,
          wfIpxBasicSysHostAddress
         OCTET STRING,
          wfIpxBasicSysRouterName
         DisplayString,
          wfIpxBasicSysInReceives
         Counter,
          wfIpxBasicSysInHdrErrors
         Counter,
          wfIpxBasicSysInUnknownSockets
         Counter,
          wfIpxBasicSysInDiscards
         Counter,
          wfIpxBasicSysInBadChecksums
         Counter,
          wfIpxBasicSysInDelivers
         Counter,
          wfIpxBasicSysNoRoutes
         Counter,
          wfIpxBasicSysOutRequests
         Counter,
          wfIpxBasicSysOutMalformedRequests
         Counter,
          wfIpxBasicSysOutPackets
         Counter,
          wfIpxBasicSysOpenEncapsFails
         Counter,
          wfIpxBasicSysOutDiscards
         Counter
        }

    wfIpxBasicSysDelete OBJECT-TYPE
        SYNTAX INTEGER {
             created(1),
             deleted(2)
         }
        ACCESS read-write
        STATUS mandatory
        DESCRIPTION
                "Create/Delete parameter. Default is created.
                Users perform an SNMP SET operation on this
                object in order to create/delete IPX."
        DEFVAL { created }
        ::= { wfIpxBasicSysEntry 1 }

    wfIpxBasicSysDisable OBJECT-TYPE
        SYNTAX INTEGER {
             enabled(1),
             disabled(2)
         }
        ACCESS read-write
        STATUS mandatory
        DESCRIPTION
                "Enable/Disable parameter. Default is enabled.
                Users perform an SNMP SET operation on this
                object in order to enable/disable IPX."
        DEFVAL { enabled }
        ::= { wfIpxBasicSysEntry 2 }

    wfIpxBasicSysState OBJECT-TYPE
        SYNTAX INTEGER {
             up(1),
             down(2),
             init(3),
             notpresent(4)
         }
        ACCESS read-only
        STATUS mandatory
        DESCRIPTION
                "The current state of the entire IPX Router."
        DEFVAL { notpresent }
        ::= { wfIpxBasicSysEntry 3 }

    wfIpxBasicSysInstance OBJECT-TYPE
        SYNTAX INTEGER
        ACCESS read-only
        STATUS mandatory
        DESCRIPTION
                "The unique identifier for the instance of IPX."
        ::= { wfIpxBasicSysEntry 4 }

    wfIpxBasicSysPrimaryNetworkNumber OBJECT-TYPE
        SYNTAX OCTET STRING
        ACCESS read-write
        STATUS mandatory
        DESCRIPTION
                "The 'internal' network number, used for IPXWAN"
        ::= { wfIpxBasicSysEntry 5 }

    wfIpxBasicSysMultipleHostAddresses OBJECT-TYPE
        SYNTAX INTEGER {
             enabled(1),
             disabled(2)
         }
        ACCESS read-write
        STATUS mandatory
        DESCRIPTION
                "Allow the user to configure one host/mac addr for the whole box (default)
                where, if configured, the CfgHostAddress is used (becomes HostAddress)
                otherwise if left unconfigured the Host address is discerned from the
                backplane serial number.  If Multiple host is Enabled and the host number is
                configured in the interface record the configured value is used as the
                hostid/mac addr of the interface (except Token Ring which can't go into
                promiscous mode, uses Token Ring Mac as hostid/mac of interface). If the
                host number in left unconfigured then the hostid/mac is gotten from the
                mac of the circuit."
        DEFVAL { enabled }
        ::= { wfIpxBasicSysEntry 6 }

    wfIpxBasicSysCfgHostAddress OBJECT-TYPE
        SYNTAX OCTET STRING
        ACCESS read-write
        STATUS mandatory
        DESCRIPTION
                "Host Number of Router and potential MAC address of box.
                This host number will be used to overide the default
                box generated host address."
        ::= { wfIpxBasicSysEntry 7 }

    wfIpxBasicSysHostAddress OBJECT-TYPE
        SYNTAX OCTET STRING
        ACCESS read-only
        STATUS mandatory
        DESCRIPTION
                "Host Number of Router and potential MAC address of box.
                This is not a restart variable because this will be
                filled in from the IPX code after reading it from
                either the configurable host number or from a box
                generated variable."
        ::= { wfIpxBasicSysEntry 8 }

    wfIpxBasicSysRouterName OBJECT-TYPE
        SYNTAX DisplayString
        ACCESS read-write
        STATUS mandatory
        DESCRIPTION
                "The Name of the Router, used for IPXWAN"
        ::= { wfIpxBasicSysEntry 9 }

    wfIpxBasicSysInReceives OBJECT-TYPE
        SYNTAX Counter
        ACCESS read-only
        STATUS mandatory
        DESCRIPTION
                "The total number of IPX packets received, including errors"
        ::= { wfIpxBasicSysEntry 10 }

    wfIpxBasicSysInHdrErrors OBJECT-TYPE
        SYNTAX Counter
        ACCESS read-only
        STATUS mandatory
        DESCRIPTION
                "The number of IPX packets discarded due to errors in
                their headers, including any IPX packet with a size less
                than the minimum of 30 bytes"
        ::= { wfIpxBasicSysEntry 11 }

    wfIpxBasicSysInUnknownSockets OBJECT-TYPE
        SYNTAX Counter
        ACCESS read-only
        STATUS mandatory
        DESCRIPTION
                "The number of IPX packets discarded because the
                destination was the router and the socket was not known"
        ::= { wfIpxBasicSysEntry 12 }

    wfIpxBasicSysInDiscards OBJECT-TYPE
        SYNTAX Counter
        ACCESS read-only
        STATUS mandatory
        DESCRIPTION
                "The number of IPX packets received but discarded due to
                reasons other than those accounted for by
                wfIpxBasicSysInHdrErrors , wfIpxBasicSysInUnknownSockets,
                wfIpxBasicSysAdvSysInDiscards, and wfIpxAdvSysInCompressDiscards"
        ::= { wfIpxBasicSysEntry 13 }

    wfIpxBasicSysInBadChecksums OBJECT-TYPE
        SYNTAX Counter
        ACCESS read-only
        STATUS mandatory
        DESCRIPTION
                "The number of IPX packets received with incorrect checksums"
        ::= { wfIpxBasicSysEntry 14 }

    wfIpxBasicSysInDelivers OBJECT-TYPE
        SYNTAX Counter
        ACCESS read-only
        STATUS mandatory
        DESCRIPTION
                "The number of IPX packets delivered locally"
        ::= { wfIpxBasicSysEntry 15 }

    wfIpxBasicSysNoRoutes OBJECT-TYPE
        SYNTAX Counter
        ACCESS read-only
        STATUS mandatory
        DESCRIPTION
                "The number of times no route to a destination was found"
        ::= { wfIpxBasicSysEntry 16 }

    wfIpxBasicSysOutRequests OBJECT-TYPE
        SYNTAX Counter
        ACCESS read-only
        STATUS mandatory
        DESCRIPTION
                "The number of IPX packets supplied locally for
                transmission, not including any packets counted in
                wfIpxAdvSysForwPackets"
        ::= { wfIpxBasicSysEntry 17 }

    wfIpxBasicSysOutMalformedRequests OBJECT-TYPE
        SYNTAX Counter
        ACCESS read-only
        STATUS mandatory
        DESCRIPTION
                "The number of outgoing IPX packets discarded due to
                reasons other than those accounted for in
                wfIpxBasicSysOutMalformedRequest, wfIpxAdvSysOutFiltered,
                and wfIpxAdvSysOutCompressDiscards"
        ::= { wfIpxBasicSysEntry 18 }

    wfIpxBasicSysOutPackets OBJECT-TYPE
        SYNTAX Counter
        ACCESS read-only
        STATUS mandatory
        DESCRIPTION
                "The total number of IPX packets transmitted"
        ::= { wfIpxBasicSysEntry 19 }

    wfIpxBasicSysOpenEncapsFails OBJECT-TYPE
        SYNTAX Counter
        ACCESS read-only
        STATUS mandatory
        DESCRIPTION
                "The number of IPX encaps open calls which failed"
        ::= { wfIpxBasicSysEntry 20 }

    wfIpxBasicSysOutDiscards OBJECT-TYPE
        SYNTAX Counter
        ACCESS read-only
        STATUS mandatory
        DESCRIPTION
                "The number of outgoing IPX packets discarded due to
                reasons other than those accounted for by
                wfIpxBasicSysOutMalformedRequests,
                wfIpxBasicSysAdvSysOutFiltered, and wfIpxAdvSysOutCompressDiscards"
        ::= { wfIpxBasicSysEntry 21 }

    wfIpxAdvSysTable OBJECT-TYPE
        SYNTAX SEQUENCE OF WfIpxAdvSysEntry
        ACCESS not-accessible
        STATUS mandatory
        DESCRIPTION
                "Wellfleet IPX Advanced System Table"
        ::= { wfIpxGroup 16 }

    wfIpxAdvSysEntry OBJECT-TYPE
        SYNTAX WfIpxAdvSysEntry
        ACCESS not-accessible
        STATUS mandatory
        DESCRIPTION
                "An entry in the IPX Circ Table"
        INDEX  { wfIpxAdvSysInstance }
        ::= { wfIpxAdvSysTable 1 }

    WfIpxAdvSysEntry ::= SEQUENCE {
          wfIpxAdvSysDelete
         INTEGER,
          wfIpxAdvSysInstance
         INTEGER,
          wfIpxAdvSysRoutingMethod
         INTEGER,
          wfIpxAdvSysLogFilter
         INTEGER,
          wfIpxAdvSysMaximumPath
         INTEGER,
          wfIpxAdvSysMaxPathSplits
         INTEGER,
          wfIpxAdvSysMaxHops
         INTEGER,
          wfIpxAdvSysInTooManyHops
         Counter,
          wfIpxAdvSysInFiltered
         Counter,
          wfIpxAdvSysInCompressDiscards
         Counter,
          wfIpxAdvSysNETBIOSPackets
         Counter,
          wfIpxAdvSysForwPackets
         Counter,
          wfIpxAdvSysOutFiltered
         Counter,
          wfIpxAdvSysOutCompressDiscards
         Counter,
          wfIpxAdvSysNovellCertificationConformanceDisable
         INTEGER,
          wfIpxAdvSysCircCount
         Counter,
          wfIpxAdvSysCfgDestCount
         INTEGER,
          wfIpxAdvSysDestCount
         Counter,
          wfIpxAdvSysCfgServCount
         INTEGER,
          wfIpxAdvSysServCount
         Counter,
          wfIpxAdvSysCfgHostCount
         INTEGER,
          wfIpxAdvSysHostCount
         Counter,
          wfIpxAdvSysAgingFrequency
         INTEGER,
          wfIpxAdvSysAgingPendingFrequency
         INTEGER,
          wfIpxAdvSysDefaultRouteEnable
         INTEGER,
          wfIpxAdvSysSapViaDefaultRouteEnable
         INTEGER,
          wfIpxAdvSysCT
         INTEGER,
          wfIpxAdvSysMibReplySlots
	     DisplayString,
 	      wfIpxAdvSysGNSRespMode
         INTEGER,
          wfIpxAdvSysMaxNetTblSize
         INTEGER,
          wfIpxAdvSysNetTblFillNotify
         INTEGER,
          wfIpxAdvSysGlobalTrigUpdate
         INTEGER,
          wfIpxAdvSysTrigUpdateDelay
         INTEGER,
          wfIpxAdvSysLostRouteDelay
         INTEGER
        }

    wfIpxAdvSysDelete OBJECT-TYPE
        SYNTAX INTEGER {
             created(1),
             deleted(2)
         }
        ACCESS read-write
        STATUS mandatory
        DESCRIPTION
                "Create/Delete parameter. Default is created.
                Users perform an SNMP SET operation on this
                object in order to create/delete the IPX
                advanced system group."
        DEFVAL { created }
        ::= { wfIpxAdvSysEntry 1 }

    wfIpxAdvSysInstance OBJECT-TYPE
        SYNTAX INTEGER
        ACCESS read-only
        STATUS mandatory
        DESCRIPTION
                "The unique identifier for the instance of IPX."
        ::= { wfIpxAdvSysEntry 2 }

    wfIpxAdvSysRoutingMethod OBJECT-TYPE
        SYNTAX INTEGER {
             hop(1),
             tick(2)
         }
        ACCESS read-write
        STATUS mandatory
        DESCRIPTION
                "Choose either Tick or Hop based routing"
        DEFVAL { tick }
        ::= { wfIpxAdvSysEntry 3 }

    wfIpxAdvSysLogFilter OBJECT-TYPE
        SYNTAX INTEGER {
             debug(1),
             info(2),
             trace(16),
             debuginfo(3),
             debugtrace(17),
             infotrace(18),
             debuginfotrace(19)
         }
        ACCESS read-write
        STATUS mandatory
        DESCRIPTION
                "Filter out some log messages, Default filters out
                trace messages."
        DEFVAL { trace }
        ::= { wfIpxAdvSysEntry 4 }

    wfIpxAdvSysMaximumPath OBJECT-TYPE
        SYNTAX INTEGER
        ACCESS read-write
        STATUS mandatory
        DESCRIPTION
                "Declare Maximum number of paths stored for a given destination
                        network"
        DEFVAL { 1 }
        ::= { wfIpxAdvSysEntry 5 }

    wfIpxAdvSysMaxPathSplits OBJECT-TYPE
        SYNTAX INTEGER
        ACCESS read-write
        STATUS mandatory
        DESCRIPTION
                "A non-zero value enables load sharing between equal cost
                        paths with the best metric when forwarding packets"
        DEFVAL { 1 }
        ::= { wfIpxAdvSysEntry 6 }

    wfIpxAdvSysMaxHops OBJECT-TYPE
        SYNTAX INTEGER
        ACCESS read-write
        STATUS mandatory
        DESCRIPTION
                "The maximum number of hops a packet may take"
        DEFVAL { 16 }
        ::= { wfIpxAdvSysEntry 7 }

    wfIpxAdvSysInTooManyHops OBJECT-TYPE
        SYNTAX Counter
        ACCESS read-only
        STATUS mandatory
        DESCRIPTION
                "The number of IPX packets discarded due to exceeding the
                maximum hop count."
        ::= { wfIpxAdvSysEntry 8 }

    wfIpxAdvSysInFiltered OBJECT-TYPE
        SYNTAX Counter
        ACCESS read-only
        STATUS mandatory
        DESCRIPTION
                "The number of incoming IPX packets discarded due to
                filtering, not including those counted in
                wfIpxTrafficFilterCounter"
        ::= { wfIpxAdvSysEntry 9 }

    wfIpxAdvSysInCompressDiscards OBJECT-TYPE
        SYNTAX Counter
        ACCESS read-only
        STATUS mandatory
        DESCRIPTION
                "Then number of incoming IPX packets discarded due to
                decompression errors."
        ::= { wfIpxAdvSysEntry 10 }

    wfIpxAdvSysNETBIOSPackets OBJECT-TYPE
        SYNTAX Counter
        ACCESS read-only
        STATUS mandatory
        DESCRIPTION
                "The number of NETBIOS packets received"
        ::= { wfIpxAdvSysEntry 11 }

    wfIpxAdvSysForwPackets OBJECT-TYPE
        SYNTAX Counter
        ACCESS read-only
        STATUS mandatory
        DESCRIPTION
                "The number of IPX packets forwarded"
        ::= { wfIpxAdvSysEntry 12 }

    wfIpxAdvSysOutFiltered OBJECT-TYPE
        SYNTAX Counter
        ACCESS read-only
        STATUS mandatory
        DESCRIPTION
                "The number of outgoing IPX packets discarded due to filtering"
        ::= { wfIpxAdvSysEntry 13 }

    wfIpxAdvSysOutCompressDiscards OBJECT-TYPE
        SYNTAX Counter
        ACCESS read-only
        STATUS mandatory
        DESCRIPTION
                "The number of outgoing IPX packets discarded due to
                compression errors"
        ::= { wfIpxAdvSysEntry 14 }

    wfIpxAdvSysNovellCertificationConformanceDisable OBJECT-TYPE
        SYNTAX INTEGER {
             enabled(1),
             disabled(2)
         }
        ACCESS read-write
        STATUS mandatory
        DESCRIPTION
                "enable/disable Novell certification, disable/enable Wellfleet specifics"
        DEFVAL { enabled }
        ::= { wfIpxAdvSysEntry 15 }

    wfIpxAdvSysCircCount OBJECT-TYPE
        SYNTAX Counter
        ACCESS read-only
        STATUS mandatory
        DESCRIPTION
                "The number of IPX Circuits (interfaces)."
        ::= { wfIpxAdvSysEntry 16 }

    wfIpxAdvSysCfgDestCount OBJECT-TYPE
        SYNTAX INTEGER
        ACCESS read-write
        STATUS mandatory
        DESCRIPTION
                "A value indicating the maximum destinations (networks) that
                the user expects the router to learn. This is used to
                pre-allocate table sizes for network tables. Changing this
                value can greatly effect the memory used by IPX, however it
                can also speed learning times."
        ::= { wfIpxAdvSysEntry 17 }

    wfIpxAdvSysDestCount OBJECT-TYPE
        SYNTAX Counter
        ACCESS read-only
        STATUS mandatory
        DESCRIPTION
                "The number of currently reachable destinations known to IPX"
        ::= { wfIpxAdvSysEntry 18 }

    wfIpxAdvSysCfgServCount OBJECT-TYPE
        SYNTAX INTEGER
        ACCESS read-write
        STATUS mandatory
        DESCRIPTION
                "A value indicating the maximum services that the user
                expects the router to learn. This is used to pre-allocate
                table sizes for service tables. Changing this value
                can greatly effect the memory used by IPX, however it
                can also speed learning times."
        ::= { wfIpxAdvSysEntry 19 }

    wfIpxAdvSysServCount OBJECT-TYPE
        SYNTAX Counter
        ACCESS read-only
        STATUS mandatory
        DESCRIPTION
                "The number of currently reachable services known to IPX"
        ::= { wfIpxAdvSysEntry 20 }

    wfIpxAdvSysCfgHostCount OBJECT-TYPE
        SYNTAX INTEGER
        ACCESS read-write
        STATUS mandatory
        DESCRIPTION
                "A value indicating the maximum next hop hosts that the user
                expects the router to learn. This is used to pre-allocate
                table sizes for host tables. Changing this value
                can greatly effect the memory used by IPX, however it
                can also speed learning times."
        ::= { wfIpxAdvSysEntry 21 }

    wfIpxAdvSysHostCount OBJECT-TYPE
        SYNTAX Counter
        ACCESS read-only
        STATUS mandatory
        DESCRIPTION
                "The number of currently reachable hosts known to IPX"
        ::= { wfIpxAdvSysEntry 22 }

    wfIpxAdvSysAgingFrequency OBJECT-TYPE
        SYNTAX INTEGER
        ACCESS read-write
        STATUS mandatory
        DESCRIPTION
                "The frequency, in seconds, for aging RIP and SAP
                information."
        DEFVAL { 10 }
        ::= { wfIpxAdvSysEntry 23 }

    wfIpxAdvSysAgingPendingFrequency OBJECT-TYPE
        SYNTAX INTEGER
        ACCESS read-write
        STATUS mandatory
        DESCRIPTION
                "The number of routes and services to age before pending."
        DEFVAL { 100 }
        ::= { wfIpxAdvSysEntry 24 }

    wfIpxAdvSysDefaultRouteEnable OBJECT-TYPE
        SYNTAX INTEGER {
             enabled(1),
             disabled(2)
         }
        ACCESS read-write
        STATUS mandatory
        DESCRIPTION
                "This parameter indicates whether or not default route is used
                for unknown networks."
        DEFVAL { enabled }
        ::= { wfIpxAdvSysEntry 25 }

    wfIpxAdvSysSapViaDefaultRouteEnable OBJECT-TYPE
        SYNTAX INTEGER {
             enabled(1),
             disabled(2)
         }
        ACCESS read-write
        STATUS mandatory
        DESCRIPTION
                "This parameter indicates whether or not a SAP advertisement
                can be learned from an interface if the network number advertised
                in the SAP advertisement is unreachable but default route is
                accessible from that interface.  Note that the router may not be
                compatible with other router implementations when this feature is
                enabled."
        DEFVAL { disabled }
        ::= { wfIpxAdvSysEntry 26 }

    wfIpxAdvSysCT OBJECT-TYPE
        SYNTAX INTEGER {
             enabled(1),
             disabled(2)
         }
        ACCESS read-write
        STATUS mandatory
        DESCRIPTION
                "The NLSP Certification Test compatibility flag."
        DEFVAL { disabled }
        ::= { wfIpxAdvSysEntry 27 }

    wfIpxAdvSysMibReplySlots OBJECT-TYPE
      SYNTAX   DisplayString
        ACCESS read-write
        STATUS mandatory
        DESCRIPTION
                "The slots running IPX which should reply to MIB
      Proxy requests"
        ::= { wfIpxAdvSysEntry 28 }

    wfIpxAdvSysGNSRespMode OBJECT-TYPE
      SYNTAX   INTEGER {
             alphabetical(1),
             lastlearned(2)
            }
        ACCESS read-write
        STATUS mandatory
        DESCRIPTION
                "Algorithm used to determine the server to choose when
                         responding to a Get Nearest Server Request"
        DEFVAL { alphabetical }
        ::= { wfIpxAdvSysEntry 29 }

    wfIpxAdvSysMaxNetTblSize OBJECT-TYPE
        SYNTAX  INTEGER
        ACCESS  read-write
        STATUS  mandatory
        DESCRIPTION
                "maximum allowed size of the network table"
          DEFVAL  { 0 }
        ::= { wfIpxAdvSysEntry 30 }

    wfIpxAdvSysNetTblFillNotify OBJECT-TYPE
        SYNTAX  INTEGER(1..100)
        ACCESS  read-write
        STATUS  mandatory
        DESCRIPTION
                "notify when (configured) percentage is reached"
        DEFVAL  { 100 }
        ::= { wfIpxAdvSysEntry 31 }


    wfIpxAdvSysGlobalTrigUpdate OBJECT-TYPE
        SYNTAX  INTEGER {
                    enabled(1),
                    disabled(2)
                }
        ACCESS  read-write
        STATUS  mandatory
        DESCRIPTION
                "enable/disable triggered rip/sap updates box wide."
        DEFVAL  { enabled }
        ::= { wfIpxAdvSysEntry 32 }

    wfIpxAdvSysTrigUpdateDelay OBJECT-TYPE
        SYNTAX  INTEGER
        ACCESS  read-write
        STATUS  mandatory
        DESCRIPTION
                "Delay before performing immediate update (10ths)"
          DEFVAL  { 0 }
        ::= { wfIpxAdvSysEntry 33 }

    wfIpxAdvSysLostRouteDelay OBJECT-TYPE
        SYNTAX  INTEGER
        ACCESS  read-write
        STATUS  mandatory
        DESCRIPTION
                "Delay before performing lost route algorithm (10ths)"
          DEFVAL  { 5 }
        ::= { wfIpxAdvSysEntry 34 }


    wfIpxCircTable OBJECT-TYPE
        SYNTAX SEQUENCE OF WfIpxCircEntry
        ACCESS not-accessible
        STATUS mandatory
        DESCRIPTION
                "Wellfleet IPX Circuit Table"
        ::= { wfIpxGroup 17 }

    wfIpxCircEntry OBJECT-TYPE
        SYNTAX WfIpxCircEntry
        ACCESS not-accessible
        STATUS mandatory
        DESCRIPTION
                "An entry in the IPX Circuit Table"
        INDEX  { wfIpxCircSysInstance,
           wfIpxCircIndex }
        ::= { wfIpxCircTable 1 }

    WfIpxCircEntry ::= SEQUENCE {
          wfIpxCircDelete
         INTEGER,
          wfIpxCircDisable
         INTEGER,
          wfIpxCircState
         INTEGER,
          wfIpxCircSysInstance
         INTEGER,
          wfIpxCircIndex
         INTEGER,
          wfIpxCircIfIndex
         INTEGER,
          wfIpxCircName
         DisplayString,
          wfIpxCircCfgType
         INTEGER,
          wfIpxCircLocalMaxPacketSize
         INTEGER,
          wfIpxCircCfgCompressState
         INTEGER,
          wfIpxCircCompressState
         INTEGER,
          wfIpxCircCompressSlots
         INTEGER,
          wfIpxCircCompressedSent
         Counter,
          wfIpxCircCompressedInitSent
         Counter,
          wfIpxCircCompressedRejectsSent
         Counter,
          wfIpxCircUncompressedSent
         Counter,
          wfIpxCircCompressedReceived
         Counter,
          wfIpxCircCompressedInitReceived
         Counter,
          wfIpxCircCompressedRejectsReceived
         Counter,
          wfIpxCircUncompressedReceived
         Counter,
          wfIpxCircMediaType
         INTEGER,
          wfIpxCircCfgNetworkNumber
         OCTET STRING,
          wfIpxCircNetworkNumber
         OCTET STRING,
          wfIpxCircCommonNetworkNumber
         OCTET STRING,
          wfIpxCircCfgHostAddress
         OCTET STRING,
          wfIpxCircHostAddress
         OCTET STRING,
          wfIpxCircMacAddress
         OCTET STRING,
          wfIpxCircCfgBroadcastAddress
         OCTET STRING,
          wfIpxCircBroadcastAddress
         OCTET STRING,
          wfIpxCircCfgMulticastAddress
         OCTET STRING,
          wfIpxCircMulticastAddress
         OCTET STRING,
          wfIpxCircStateChanges
         Counter,
          wfIpxCircInitFails
         Counter,
          wfIpxCircDelay
         INTEGER,
          wfIpxCircThroughput
         INTEGER,
          wfIpxCircNeighRouterName
         DisplayString,
          wfIpxCircNeighInternalNetNum
         OCTET STRING,
          wfIpxCircCost
         INTEGER,
          wfIpxCircChecksum
         INTEGER,
          wfIpxCircCfgEncaps
         INTEGER,
          wfIpxCircEncaps
         INTEGER,
          wfIpxCircInTooManyHops
         Counter,
          wfIpxCircInFiltered
         Counter,
          wfIpxCircInHdrErrors
         Counter,
          wfIpxCircInUnknownSockets
         Counter,
          wfIpxCircNETBIOSPackets
         Counter,
          wfIpxCircInBadChecksums
         Counter,
          wfIpxCircInDelivers
         Counter,
          wfIpxCircInDiscards
         Counter,
          wfIpxCircNoRoutes
         Counter,
          wfIpxCircOutRequests
         Counter,
          wfIpxCircOutMalformedRequests
         Counter,
          wfIpxCircOutDiscards
         Counter,
          wfIpxCircOutFiltered
         Counter,
          wfIpxCircDestCount
         Counter,
          wfIpxCircServCount
         Counter,
          wfIpxCircHostCount
         Counter,
          wfIpxCircForwardCount
         Counter,
          wfIpxCircTrEndStation
         INTEGER,
          wfIpxCircNetbiosAccept
         INTEGER,
          wfIpxCircNetbiosDeliver
         INTEGER,
          wfIpxCircSMDSIndividualAddress
         OCTET STRING,
          wfIpxCircType
         INTEGER,
          wfIpxCircWatchdogSpoof
         INTEGER,
          wfIpxCircIPXOutWatchdogSpoofRsps
         Counter,
          wfIpxCircCfgDelay
         INTEGER,
          wfIpxCircCfgThroughput
         INTEGER,
          wfIpxCircSPXOutWatchdogSpoofRsps
         Counter,
          wfIpxCircInitStabilizationTimer
         INTEGER,
          wfIpxCircSVCBroadcast
         INTEGER,
          wfIpxCircVRRPTriggerState
         INTEGER
        }

    wfIpxCircDelete OBJECT-TYPE
        SYNTAX INTEGER {
             created(1),
             deleted(2)
         }
        ACCESS read-write
        STATUS mandatory
        DESCRIPTION
                "Create/Delete parameter. Default is created.
                Users perform an SNMP SET operation on this
                object in order to create/delete this entry."
        DEFVAL { created }
        ::= { wfIpxCircEntry 1 }

    wfIpxCircDisable OBJECT-TYPE
        SYNTAX INTEGER {
             enabled(1),
             disabled(2)
         }
        ACCESS read-write
        STATUS mandatory
        DESCRIPTION
                "Enable/Disable parameter. Default is enabled.
                Users perform an SNMP SET operation on this
                object in order to enable/disable an entry."
        DEFVAL { enabled }
        ::= { wfIpxCircEntry 2 }

    wfIpxCircState OBJECT-TYPE
        SYNTAX INTEGER {
             up(1),
             down(2),
             init(3),
             notpresent(4)
         }
        ACCESS read-only
        STATUS mandatory
        DESCRIPTION
                "The current state of this entry"
        DEFVAL { notpresent }
        ::= { wfIpxCircEntry 3 }

    wfIpxCircSysInstance OBJECT-TYPE
        SYNTAX INTEGER
        ACCESS read-only
        STATUS mandatory
        DESCRIPTION
                "The unique identifier of the instance of IPX
                to which this entry corresponds."
        ::= { wfIpxCircEntry 4 }

    wfIpxCircIndex OBJECT-TYPE
        SYNTAX INTEGER
        ACCESS read-only
        STATUS mandatory
        DESCRIPTION
                "The identifier of this circuit, unique within the
                instance of RIP. This value corresponds to the IPX circuit
                identifier found in wfIpxCircIndex."
        ::= { wfIpxCircEntry 5 }

    wfIpxCircIfIndex OBJECT-TYPE
        SYNTAX INTEGER
        ACCESS read-write
        STATUS mandatory
        DESCRIPTION
                "The identifier of the DP circuit to which this IPX circuit
                is linked."
        ::= { wfIpxCircEntry 6 }

    wfIpxCircName OBJECT-TYPE
        SYNTAX DisplayString
        ACCESS read-write
        STATUS mandatory
        DESCRIPTION
                "The Name of this IPX circuit"
        ::= { wfIpxCircEntry 7 }

    wfIpxCircCfgType OBJECT-TYPE
        SYNTAX INTEGER {
             other(1),
             broadcast(2),
             pt(4),
             wanrip(8),
             unnumberedrip(16),
             dynamic(32),
             ws(64),
             nlsp(128)
         }
        ACCESS read-write
        STATUS mandatory
        DESCRIPTION
                "The type assigned by the user to this IPX circuit.
                To enable IPXWAN negotiations on this (WAN) circuit,
                set one or more of WAN_RIP, UNNUMBERED_RIP, and
                WAN_NLSP."
        DEFVAL { dynamic }
        ::= { wfIpxCircEntry 8 }

    wfIpxCircLocalMaxPacketSize OBJECT-TYPE
        SYNTAX INTEGER
        ACCESS read-only
        STATUS mandatory
        DESCRIPTION
                "The maximum size (including header), in bytes that the
                media supports on this DP circuit."
        ::= { wfIpxCircEntry 9 }

    wfIpxCircCfgCompressState OBJECT-TYPE
        SYNTAX INTEGER {
             enabled(1),
             disabled(2)
         }
        ACCESS read-write
        STATUS mandatory
        DESCRIPTION
                "The configured compression state of this IPX circuit."
        DEFVAL { disabled }
        ::= { wfIpxCircEntry 10 }

    wfIpxCircCompressState OBJECT-TYPE
        SYNTAX INTEGER {
             enabled(1),
             disabled(2)
         }
        ACCESS read-only
        STATUS mandatory
        DESCRIPTION
                "The actual compression state on this IPX circuit."
        DEFVAL { disabled }
        ::= { wfIpxCircEntry 11 }

    wfIpxCircCompressSlots OBJECT-TYPE
        SYNTAX INTEGER
        ACCESS read-write
        STATUS mandatory
        DESCRIPTION
                "The number of compression slots available on this circuit."
        DEFVAL { 16 }
        ::= { wfIpxCircEntry 12 }

    wfIpxCircCompressedSent OBJECT-TYPE
        SYNTAX Counter
        ACCESS read-only
        STATUS mandatory
        DESCRIPTION
                "The number of compressed packets sent."
        ::= { wfIpxCircEntry 13 }

    wfIpxCircCompressedInitSent OBJECT-TYPE
        SYNTAX Counter
        ACCESS read-only
        STATUS mandatory
        DESCRIPTION
                "The number of compression initialization packets sent."
        ::= { wfIpxCircEntry 14 }

    wfIpxCircCompressedRejectsSent OBJECT-TYPE
        SYNTAX Counter
        ACCESS read-only
        STATUS mandatory
        DESCRIPTION
                "The number of compressed packet rejected packets sent."
        ::= { wfIpxCircEntry 15 }

    wfIpxCircUncompressedSent OBJECT-TYPE
        SYNTAX Counter
        ACCESS read-only
        STATUS mandatory
        DESCRIPTION
                "The number of uncompressed packets sent without being compressed
                even though compression was turned on for this IPX circuit."
        ::= { wfIpxCircEntry 16 }

    wfIpxCircCompressedReceived OBJECT-TYPE
        SYNTAX Counter
        ACCESS read-only
        STATUS mandatory
        DESCRIPTION
                "The number of compressed packets received."
        ::= { wfIpxCircEntry 17 }

    wfIpxCircCompressedInitReceived OBJECT-TYPE
        SYNTAX Counter
        ACCESS read-only
        STATUS mandatory
        DESCRIPTION
                "The number of compression initialization packets received."
        ::= { wfIpxCircEntry 18 }

    wfIpxCircCompressedRejectsReceived OBJECT-TYPE
        SYNTAX Counter
        ACCESS read-only
        STATUS mandatory
        DESCRIPTION
                "The number of compressed packet rejected packets received."
        ::= { wfIpxCircEntry 19 }

    wfIpxCircUncompressedReceived OBJECT-TYPE
        SYNTAX Counter
        ACCESS read-only
        STATUS mandatory
        DESCRIPTION
                "The number of packets received without having been
                compressed even though compression was turned on for
                this IPX circuit."
        ::= { wfIpxCircEntry 20 }

    wfIpxCircMediaType OBJECT-TYPE
        SYNTAX INTEGER
        ACCESS read-only
        STATUS mandatory
        DESCRIPTION
                "The media type used on this IPX circuit."
        ::= { wfIpxCircEntry 21 }

    wfIpxCircCfgNetworkNumber OBJECT-TYPE
        SYNTAX OCTET STRING
        ACCESS read-write
        STATUS mandatory
        DESCRIPTION
                "The IPX network number assigned by the user to this
                IPX circuit."
        ::= { wfIpxCircEntry 22 }

    wfIpxCircNetworkNumber OBJECT-TYPE
        SYNTAX OCTET STRING
        ACCESS read-only
        STATUS mandatory
        DESCRIPTION
                "The IPX network number of this IPX circuit."
        ::= { wfIpxCircEntry 23 }

    wfIpxCircCommonNetworkNumber OBJECT-TYPE
        SYNTAX OCTET STRING
        ACCESS read-write
        STATUS mandatory
        DESCRIPTION
                "The IPX common network number assigned to this IPX circuit."
        ::= { wfIpxCircEntry 24 }

    wfIpxCircCfgHostAddress OBJECT-TYPE
        SYNTAX OCTET STRING (SIZE (6))
        ACCESS read-write
        STATUS mandatory
        DESCRIPTION
                "The IPX Host Address assigned by the user to this
                IPX circuit."
        ::= { wfIpxCircEntry 25 }

    wfIpxCircHostAddress OBJECT-TYPE
        SYNTAX OCTET STRING
        ACCESS read-only
        STATUS mandatory
        DESCRIPTION
                "The IPX Host Address of this IPX circuit."
        ::= { wfIpxCircEntry 26 }

    wfIpxCircMacAddress OBJECT-TYPE
        SYNTAX OCTET STRING
        ACCESS read-only
        STATUS mandatory
        DESCRIPTION
                "The IPX Host Address of this IPX circuit."
        ::= { wfIpxCircEntry 27 }

    wfIpxCircCfgBroadcastAddress OBJECT-TYPE
        SYNTAX OCTET STRING
        ACCESS read-write
        STATUS mandatory
        DESCRIPTION
                "The Broadcast Address assigned by the user to this
                IPX circuit."
        ::= { wfIpxCircEntry 28 }

    wfIpxCircBroadcastAddress OBJECT-TYPE
        SYNTAX OCTET STRING
        ACCESS read-only
        STATUS mandatory
        DESCRIPTION
                "The Broadcast Address of this IPX circuit."
        ::= { wfIpxCircEntry 29 }

    wfIpxCircCfgMulticastAddress OBJECT-TYPE
        SYNTAX OCTET STRING
        ACCESS read-write
        STATUS mandatory
        DESCRIPTION
                "The Multicast Address assigned by the user to this
                IPX circuit."
        ::= { wfIpxCircEntry 30 }

    wfIpxCircMulticastAddress OBJECT-TYPE
        SYNTAX OCTET STRING
        ACCESS read-only
        STATUS mandatory
        DESCRIPTION
                "The Multicast Address of this IPX circuit."
        ::= { wfIpxCircEntry 31 }

    wfIpxCircStateChanges OBJECT-TYPE
        SYNTAX Counter
        ACCESS read-only
        STATUS mandatory
        DESCRIPTION
                "The number of times this IPX circuit has changed state."
        ::= { wfIpxCircEntry 32 }

    wfIpxCircInitFails OBJECT-TYPE
        SYNTAX Counter
        ACCESS read-only
        STATUS mandatory
        DESCRIPTION
                "The number of times that initialization of this
                circuit has failed."
        ::= { wfIpxCircEntry 33 }

    wfIpxCircDelay OBJECT-TYPE
        SYNTAX INTEGER
        ACCESS read-only
        STATUS mandatory
        DESCRIPTION
                "The period of time, in microseconds, that it takes to
                transmit one byte of data, excluding protocol headers,
                to a destination on the other end of this IPX circuit,
                if the IPX circuit is free of other traffic.  This
                value will be filled in by IPX to be either the value
                configured or a computed value."
        ::= { wfIpxCircEntry 34 }

    wfIpxCircThroughput OBJECT-TYPE
        SYNTAX INTEGER
        ACCESS read-only
        STATUS mandatory
        DESCRIPTION
                "The amount of data, in bits per second, that may flow
                through this IPX circuit if there is no other traffic.
                This value will be filled in by IPX to be either the value
                configured or a computed value."
        ::= { wfIpxCircEntry 35 }

    wfIpxCircNeighRouterName OBJECT-TYPE
        SYNTAX DisplayString
        ACCESS read-only
        STATUS mandatory
        DESCRIPTION
                "The name of the neighboring router on a IPXWAN circuit."
        ::= { wfIpxCircEntry 36 }

    wfIpxCircNeighInternalNetNum OBJECT-TYPE
        SYNTAX OCTET STRING
        ACCESS read-only
        STATUS mandatory
        DESCRIPTION
                "The internal network number of the neighboring router
                on an IPXWAN circuit."
        ::= { wfIpxCircEntry 37 }

    wfIpxCircCost OBJECT-TYPE
        SYNTAX INTEGER
        ACCESS read-write
        STATUS mandatory
        DESCRIPTION
                "The cost of this interface, in ticks or hops dependant on
                the wfIpxAdvSysRoutingMethod field."
        DEFVAL { 0 }
        ::= { wfIpxCircEntry 38 }

    wfIpxCircChecksum OBJECT-TYPE
        SYNTAX INTEGER {
             enabled(1),
             disabled(2)
         }
        ACCESS read-write
        STATUS mandatory
        DESCRIPTION
                "Whether or not to check checksums of packets coming into
                this IPX circuit."
        DEFVAL { disabled }
        ::= { wfIpxCircEntry 39 }

    wfIpxCircCfgEncaps OBJECT-TYPE
        SYNTAX INTEGER {
             ethernet(1),
             lsap(2),
             novell(3),
             snap(4),
             ppp(5)
         }
        ACCESS read-write
        STATUS mandatory
        DESCRIPTION
                "The encapsulation assigned by the user to this
                IPX circuit."
        DEFVAL { ethernet }
        ::= { wfIpxCircEntry 40 }

    wfIpxCircEncaps OBJECT-TYPE
        SYNTAX INTEGER {
             ethernet(1),
             lsap(2),
             novell(3),
             snap(4),
             ppp(5)
         }
        ACCESS read-only
        STATUS mandatory
        DESCRIPTION
                "The encapsulation used on this IPX circuit."
        DEFVAL { ethernet }
        ::= { wfIpxCircEntry 41 }

    wfIpxCircInTooManyHops OBJECT-TYPE
        SYNTAX Counter
        ACCESS read-only
        STATUS mandatory
        DESCRIPTION
                "The number of IPX packets discarded due to exceeding the
                maximum hops count set for this IPX circuit."
        ::= { wfIpxCircEntry 42 }

    wfIpxCircInFiltered OBJECT-TYPE
        SYNTAX Counter
        ACCESS read-only
        STATUS mandatory
        DESCRIPTION
                "The number of incoming IPX packets discarded due to
                filtering, not including those counted in
                wfIpxTrafficFilterCounter."
        ::= { wfIpxCircEntry 43 }

    wfIpxCircInHdrErrors OBJECT-TYPE
        SYNTAX Counter
        ACCESS read-only
        STATUS mandatory
        DESCRIPTION
                "The number of IPX packets discarded due to errors in
                their headers, including any IPX packet with a size less
                than the minimum of 30 bytes."
        ::= { wfIpxCircEntry 44 }

    wfIpxCircInUnknownSockets OBJECT-TYPE
        SYNTAX Counter
        ACCESS read-only
        STATUS mandatory
        DESCRIPTION
                "The number of IPX packets discarded because the
                destination socket was not known."
        ::= { wfIpxCircEntry 45 }

    wfIpxCircNETBIOSPackets OBJECT-TYPE
        SYNTAX Counter
        ACCESS read-only
        STATUS mandatory
        DESCRIPTION
                "The number of NETBIOS packets received on this
                IPX circuit."
        ::= { wfIpxCircEntry 46 }

    wfIpxCircInBadChecksums OBJECT-TYPE
        SYNTAX Counter
        ACCESS read-only
        STATUS mandatory
        DESCRIPTION
                "The number of IPX packets discarded because the
                checksum was incorrect."
        ::= { wfIpxCircEntry 47 }

    wfIpxCircInDelivers OBJECT-TYPE
        SYNTAX Counter
        ACCESS read-only
        STATUS mandatory
        DESCRIPTION
                "The number of IPX packets delivered locally"
        ::= { wfIpxCircEntry 48 }

    wfIpxCircInDiscards OBJECT-TYPE
        SYNTAX Counter
        ACCESS read-only
        STATUS mandatory
        DESCRIPTION
                "The number of IPX packets received but discarded due to
                reasons other than those accounted for by
                wfIpxCircInHdrErrors, wfIpxCircInUnknownSockets"
        ::= { wfIpxCircEntry 49 }

    wfIpxCircNoRoutes OBJECT-TYPE
        SYNTAX Counter
        ACCESS read-only
        STATUS mandatory
        DESCRIPTION
                "The number of times no route to a destination was
                found."
        ::= { wfIpxCircEntry 50 }

    wfIpxCircOutRequests OBJECT-TYPE
        SYNTAX Counter
        ACCESS read-only
        STATUS mandatory
        DESCRIPTION
                "The number of IPX packets supplied locally for
                transmission."
        ::= { wfIpxCircEntry 51 }

    wfIpxCircOutMalformedRequests OBJECT-TYPE
        SYNTAX Counter
        ACCESS read-only
        STATUS mandatory
        DESCRIPTION
                "The number of IPX packets supplied locally that contained
                errors in their structure."
        ::= { wfIpxCircEntry 52 }

    wfIpxCircOutDiscards OBJECT-TYPE
        SYNTAX Counter
        ACCESS read-only
        STATUS mandatory
        DESCRIPTION
                "The number of outgoing IPX packets discarded due to
                reasons other than those accounted for in"
        ::= { wfIpxCircEntry 53 }

    wfIpxCircOutFiltered OBJECT-TYPE
        SYNTAX Counter
        ACCESS read-only
        STATUS mandatory
        DESCRIPTION
                "The number of outgoing IPX packets diecarded due to
                filtering."
        ::= { wfIpxCircEntry 54 }

    wfIpxCircDestCount OBJECT-TYPE
        SYNTAX Counter
        ACCESS read-only
        STATUS mandatory
        DESCRIPTION
                "The number of networks known to the IPX router
                from this IPX circuit."
        ::= { wfIpxCircEntry 55 }

    wfIpxCircServCount OBJECT-TYPE
        SYNTAX Counter
        ACCESS read-only
        STATUS mandatory
        DESCRIPTION
                "The number of services known to the IPX router
                from this IPX circuit."
        ::= { wfIpxCircEntry 56 }

    wfIpxCircHostCount OBJECT-TYPE
        SYNTAX Counter
        ACCESS read-only
        STATUS mandatory
        DESCRIPTION
                "The number of hosts known to the IPX router
                from this IPX circuit."
        ::= { wfIpxCircEntry 57 }

    wfIpxCircForwardCount OBJECT-TYPE
        SYNTAX Counter
        ACCESS read-only
        STATUS mandatory
        DESCRIPTION
                "The number of forward entries in the IPX router
                forwarding table for this IPX circuit."
        ::= { wfIpxCircEntry 58 }

    wfIpxCircTrEndStation OBJECT-TYPE
        SYNTAX INTEGER {
             enabled(1),
             disabled(2)
         }
        ACCESS read-write
        STATUS mandatory
        DESCRIPTION
                "Whether or not to do Source Routing, only valid
                on token ring media."
        DEFVAL { disabled }
        ::= { wfIpxCircEntry 59 }

    wfIpxCircNetbiosAccept OBJECT-TYPE
        SYNTAX INTEGER {
             enabled(1),
             disabled(2)
         }
        ACCESS read-write
        STATUS mandatory
        DESCRIPTION
                "Accept NetBios All Networks Broadcast Packets"
        DEFVAL { disabled }
        ::= { wfIpxCircEntry 60 }

    wfIpxCircNetbiosDeliver OBJECT-TYPE
        SYNTAX INTEGER {
             enabled(1),
             disabled(2)
         }
        ACCESS read-write
        STATUS mandatory
        DESCRIPTION
                "Deliver NetBios All Networks Broadcast Packets"
        DEFVAL { disabled }
        ::= { wfIpxCircEntry 61 }

    wfIpxCircSMDSIndividualAddress OBJECT-TYPE
        SYNTAX OCTET STRING
        ACCESS read-write
        STATUS mandatory
        DESCRIPTION
                "The SMDS individual address for this IPX circuit."
        ::= { wfIpxCircEntry 62 }

    wfIpxCircType OBJECT-TYPE
        SYNTAX INTEGER {
             other(1),
             broadcast(2),
             pt(3),
             wanrip(4),
             unnumberedrip(5),
             dynamic(6),
             ws(7),
             nlsp(8)
         }
        ACCESS read-only
        STATUS mandatory
        DESCRIPTION
                "The type of the circuit. If IPXWAN was enabled on
                this circuit, this attribute will indicate the
                negotiated routing type."
        ::= { wfIpxCircEntry 63 }

    wfIpxCircWatchdogSpoof OBJECT-TYPE
        SYNTAX INTEGER {
             enabled(1),
             disabled(2)
         }
        ACCESS read-write
        STATUS mandatory
        DESCRIPTION
                "Whether or not to do Watchdog Spoofing."
        DEFVAL { disabled }
        ::= { wfIpxCircEntry 64 }

    wfIpxCircIPXOutWatchdogSpoofRsps OBJECT-TYPE
        SYNTAX Counter
        ACCESS read-only
        STATUS mandatory
        DESCRIPTION
                "The number of Watchdog response packets sent to
                IPX servers in response to Watchdog queries."
        ::= { wfIpxCircEntry 65 }

    wfIpxCircCfgDelay OBJECT-TYPE
        SYNTAX INTEGER
        ACCESS read-write
        STATUS mandatory
        DESCRIPTION
                "The period of time, in microseconds, that it takes to
                transmit one byte of data, excluding protocol headers,
                to a destination on the other end of this IPX circuit,
                if the IPX circuit is free of other traffic.  This
                value is assigned by the user."
        ::= { wfIpxCircEntry 66 }

    wfIpxCircCfgThroughput OBJECT-TYPE
        SYNTAX INTEGER
        ACCESS read-write
        STATUS mandatory
        DESCRIPTION
                "The amount of data, in bits per second, that may flow
                through this IPX circuit if there is no other traffic.
                This value is assigned by the user."
        ::= { wfIpxCircEntry 67 }

    wfIpxCircSPXOutWatchdogSpoofRsps OBJECT-TYPE
        SYNTAX Counter
        ACCESS read-only
        STATUS mandatory
        DESCRIPTION
                "The number of SPX Watchdog response packets sent to
                SPX endpoint in response to Watchdog requests."
        ::= { wfIpxCircEntry 68 }

      wfIpxCircInitStabilizationTimer OBJECT-TYPE
         SYNTAX  INTEGER
            ACCESS  read-write
            STATUS  mandatory
            DESCRIPTION
            "The circuit RIP/SAP start delay timer to allow routes to stabilize, in seconds"
            DEFVAL  { 0 }
            ::= { wfIpxCircEntry 69 }

    wfIpxCircSVCBroadcast OBJECT-TYPE
        SYNTAX INTEGER {
             enabled(1),
             disabled(2)
         }
        ACCESS read-write
        STATUS mandatory
        DESCRIPTION
                "Enable if Frame Relay SVCs should be established for
                all adjacent hosts before sending RIP and SAP updates."
        DEFVAL { disabled }
        ::= { wfIpxCircEntry 70 }

    wfIpxCircVRRPTriggerState OBJECT-TYPE
        SYNTAX  INTEGER {
                    enabled(1),
                    disabled(2)
                }
        ACCESS  read-only
        STATUS  mandatory
        DESCRIPTION
                "Indicates whether VRRP subsystem wants this IPX Intf to
                 be enabled or disabled."
        DEFVAL  { enabled }
        ::= { wfIpxCircEntry 71 }


    wfIpxDestEntryTable OBJECT-TYPE
        SYNTAX SEQUENCE OF WfIpxDestEntry
        ACCESS not-accessible
        STATUS mandatory
        DESCRIPTION
                "IPX Dest table, contains information about all known
                destinations."
        ::= { wfIpxGroup 18 }

    wfIpxDestEntry OBJECT-TYPE
        SYNTAX WfIpxDestEntry
        ACCESS not-accessible
        STATUS mandatory
        DESCRIPTION
                "Destination table contains information about all known destinations"
        INDEX  { wfIpxDestSysInstance,
           wfIpxDestNetNum }
        ::= { wfIpxDestEntryTable 1 }

    WfIpxDestEntry ::= SEQUENCE {
          wfIpxDestSysInstance
         INTEGER,
          wfIpxDestNetNum
         OCTET STRING,
          wfIpxDestProtocol
         INTEGER,
          wfIpxDestTicks
         INTEGER,
          wfIpxDestHopCount
         INTEGER,
          wfIpxDestNextHopCircIndex
         INTEGER,
          wfIpxDestNextHopHostAddress
         OCTET STRING,
          wfIpxDestNextHopNetNum
         OCTET STRING,
          wfIpxDestAge
         INTEGER
        }

    wfIpxDestSysInstance OBJECT-TYPE
        SYNTAX INTEGER
        ACCESS read-only
        STATUS mandatory
        DESCRIPTION
                "The unique identifier of the instance of IPX
                to which this entry corresponds."
        ::= { wfIpxDestEntry 1 }

    wfIpxDestNetNum OBJECT-TYPE
        SYNTAX OCTET STRING (SIZE (4))
        ACCESS read-only
        STATUS mandatory
        DESCRIPTION
                "The identifier of this circuit, unique within the
                instance. This value corresponds to the IPX circuit
                identifier found in wfIpxCircIndex."
        ::= { wfIpxDestEntry 2 }

    wfIpxDestProtocol OBJECT-TYPE
        SYNTAX INTEGER {
             other(1),
             local(2),
             rip(3),
             nlsp(4),
             static(5)
         }
        ACCESS read-only
        STATUS mandatory
        DESCRIPTION
                "The routing protocol from which knowledge of this
                destination was obtained."
        DEFVAL { other }
        ::= { wfIpxDestEntry 3 }

    wfIpxDestTicks OBJECT-TYPE
        SYNTAX INTEGER
        ACCESS read-only
        STATUS mandatory
        DESCRIPTION
                "The delay in ticks to reach this destination."
        ::= { wfIpxDestEntry 4 }

    wfIpxDestHopCount OBJECT-TYPE
        SYNTAX INTEGER
        ACCESS read-only
        STATUS mandatory
        DESCRIPTION
                "The number of hops necessary to reach the destination."
        ::= { wfIpxDestEntry 5 }

    wfIpxDestNextHopCircIndex OBJECT-TYPE
        SYNTAX INTEGER
        ACCESS read-only
        STATUS mandatory
        DESCRIPTION
                "The unique identifier of the IPX circuit used to reach
                the next hop."
        ::= { wfIpxDestEntry 6 }

    wfIpxDestNextHopHostAddress OBJECT-TYPE
        SYNTAX OCTET STRING
        ACCESS read-only
        STATUS mandatory
        DESCRIPTION
                "The Host address of the Next Hop."
        ::= { wfIpxDestEntry 7 }

    wfIpxDestNextHopNetNum OBJECT-TYPE
        SYNTAX OCTET STRING
        ACCESS read-only
        STATUS mandatory
        DESCRIPTION
                "The IPX network number of the next hop."
        ::= { wfIpxDestEntry 8 }

    wfIpxDestAge OBJECT-TYPE
        SYNTAX INTEGER
        ACCESS read-only
        STATUS mandatory
        DESCRIPTION
                "The current age of this entry, in seconds. Local,
                Static, and NLSP destinations are not aged."
        ::= { wfIpxDestEntry 9 }

    wfIpxUserStaticRouteEntryTable OBJECT-TYPE
        SYNTAX SEQUENCE OF WfIpxUserStaticRouteEntry
        ACCESS not-accessible
        STATUS mandatory
        DESCRIPTION
                "Wellfleet IPX Static Route Table"
        ::= { wfIpxGroup 19 }

    wfIpxUserStaticRouteEntry OBJECT-TYPE
        SYNTAX WfIpxUserStaticRouteEntry
        ACCESS not-accessible
        STATUS mandatory
        DESCRIPTION
                "The Static Routes table contains information about all
                destinations reached via user statically configured routes."
        INDEX  { wfIpxUserStaticRouteSysInstance,
           wfIpxUserStaticRouteCircIndex,
           wfIpxUserStaticRouteNetNum }
        ::= { wfIpxUserStaticRouteEntryTable 1 }

    WfIpxUserStaticRouteEntry ::= SEQUENCE {
          wfIpxUserStaticRouteDelete
         INTEGER,
          wfIpxUserStaticRouteDisable
         INTEGER,
          wfIpxUserStaticRouteSysInstance
         INTEGER,
          wfIpxUserStaticRouteCircIndex
         INTEGER,
          wfIpxUserStaticRouteNetNum
         OCTET STRING,
          wfIpxUserStaticRouteTicks
         INTEGER,
          wfIpxUserStaticRouteHopCount
         INTEGER,
          wfIpxUserStaticRouteNextHopHostAddress
         OCTET STRING
        }

    wfIpxUserStaticRouteDelete OBJECT-TYPE
        SYNTAX INTEGER {
             created(1),
             deleted(2)
         }
        ACCESS read-write
        STATUS mandatory
        DESCRIPTION
                "Create/Delete parameter. Default is created.
                Users perform an SNMP SET operation on this
                object in order to create/delete this entry."
        DEFVAL { created }
        ::= { wfIpxUserStaticRouteEntry 1 }

    wfIpxUserStaticRouteDisable OBJECT-TYPE
        SYNTAX INTEGER {
             enabled(1),
             disabled(2)
         }
        ACCESS read-write
        STATUS mandatory
        DESCRIPTION
                "Enable/Disable parameter. Default is enabled.
                Users perform an SNMP SET operation on this
                object in order to enable/disable an entry."
        DEFVAL { enabled }
        ::= { wfIpxUserStaticRouteEntry 2 }

    wfIpxUserStaticRouteSysInstance OBJECT-TYPE
        SYNTAX INTEGER
        ACCESS read-only
        STATUS mandatory
        DESCRIPTION
                "The unique identifier of the instance of IPX
                to which this entry corresponds."
        ::= { wfIpxUserStaticRouteEntry 3 }

    wfIpxUserStaticRouteCircIndex OBJECT-TYPE
        SYNTAX INTEGER
        ACCESS read-only
        STATUS mandatory
        DESCRIPTION
                "The identifier of this circuit, unique within the
                instance of RIP. This value corresponds to the IPX circuit
                identifier found in wfIpxCircIndex."
        ::= { wfIpxUserStaticRouteEntry 4 }

    wfIpxUserStaticRouteNetNum OBJECT-TYPE
        SYNTAX OCTET STRING (SIZE (4))
        ACCESS read-only
        STATUS mandatory
        DESCRIPTION
                "The network number of this static route."
        ::= { wfIpxUserStaticRouteEntry 5 }

    wfIpxUserStaticRouteTicks OBJECT-TYPE
        SYNTAX INTEGER
        ACCESS read-write
        STATUS mandatory
        DESCRIPTION
                "The cost in ticks of this static route entry."
        ::= { wfIpxUserStaticRouteEntry 6 }

    wfIpxUserStaticRouteHopCount OBJECT-TYPE
        SYNTAX INTEGER
        ACCESS read-write
        STATUS mandatory
        DESCRIPTION
                "The hop count to this static route."
        ::= { wfIpxUserStaticRouteEntry 7 }

    wfIpxUserStaticRouteNextHopHostAddress OBJECT-TYPE
        SYNTAX OCTET STRING
        ACCESS read-write
        STATUS mandatory
        DESCRIPTION
                "The next hop host address of this entry"
        ::= { wfIpxUserStaticRouteEntry 8 }

    wfIpxAutoStaticRouteEntryTable OBJECT-TYPE
        SYNTAX SEQUENCE OF WfIpxAutoStaticRouteEntry
        ACCESS not-accessible
        STATUS mandatory
        DESCRIPTION
                "Wellfleet IPX Automatic Static Route Table"
        ::= { wfIpxGroup 20 }

    wfIpxAutoStaticRouteEntry OBJECT-TYPE
        SYNTAX WfIpxAutoStaticRouteEntry
        ACCESS not-accessible
        STATUS mandatory
        DESCRIPTION
                "The Auto Static Routes table contains information about all
                destinations reached via Auto statically configured routes."
        INDEX  { wfIpxAutoStaticRouteSysInstance,
           wfIpxAutoStaticRouteCircIndex,
           wfIpxAutoStaticRouteNetNum }
        ::= { wfIpxAutoStaticRouteEntryTable 1 }

    WfIpxAutoStaticRouteEntry ::= SEQUENCE {
          wfIpxAutoStaticRouteDelete
         INTEGER,
          wfIpxAutoStaticRouteDisable
         INTEGER,
          wfIpxAutoStaticRouteSysInstance
         INTEGER,
          wfIpxAutoStaticRouteCircIndex
         INTEGER,
          wfIpxAutoStaticRouteNetNum
         OCTET STRING,
          wfIpxAutoStaticRouteTicks
         INTEGER,
          wfIpxAutoStaticRouteHopCount
         INTEGER,
          wfIpxAutoStaticRouteNextHopHostAddress
         OCTET STRING
        }

    wfIpxAutoStaticRouteDelete OBJECT-TYPE
        SYNTAX INTEGER {
             created(1),
             deleted(2)
         }
        ACCESS read-write
        STATUS mandatory
        DESCRIPTION
                "Create/Delete parameter. Default is created.
                Users perform an SNMP SET operation on this
                object in order to create/delete this entry."
        DEFVAL { created }
        ::= { wfIpxAutoStaticRouteEntry 1 }

    wfIpxAutoStaticRouteDisable OBJECT-TYPE
        SYNTAX INTEGER {
             enabled(1),
             disabled(2)
         }
        ACCESS read-write
        STATUS mandatory
        DESCRIPTION
                "Enable/Disable parameter. Default is enabled.
                Users perform an SNMP SET operation on this
                object in order to enable/disable an entry."
        DEFVAL { enabled }
        ::= { wfIpxAutoStaticRouteEntry 2 }

    wfIpxAutoStaticRouteSysInstance OBJECT-TYPE
        SYNTAX INTEGER
        ACCESS read-only
        STATUS mandatory
        DESCRIPTION
                "The unique identifier of the instance of IPX
                to which this entry corresponds."
        ::= { wfIpxAutoStaticRouteEntry 3 }

    wfIpxAutoStaticRouteCircIndex OBJECT-TYPE
        SYNTAX INTEGER
        ACCESS read-only
        STATUS mandatory
        DESCRIPTION
                "The identifier of this circuit, unique within the
                instance of RIP. This value corresponds to the IPX circuit
                identifier found in wfIpxCircIndex."
        ::= { wfIpxAutoStaticRouteEntry 4 }

    wfIpxAutoStaticRouteNetNum OBJECT-TYPE
        SYNTAX OCTET STRING (SIZE (4))
        ACCESS read-only
        STATUS mandatory
        DESCRIPTION
                "The network number of this static route."
        ::= { wfIpxAutoStaticRouteEntry 5 }

    wfIpxAutoStaticRouteTicks OBJECT-TYPE
        SYNTAX INTEGER
        ACCESS read-only
        STATUS mandatory
        DESCRIPTION
                "The cost in ticks of this static route entry."
        ::= { wfIpxAutoStaticRouteEntry 6 }

    wfIpxAutoStaticRouteHopCount OBJECT-TYPE
        SYNTAX INTEGER
        ACCESS read-only
        STATUS mandatory
        DESCRIPTION
                "The hop count to this static route."
        ::= { wfIpxAutoStaticRouteEntry 7 }

    wfIpxAutoStaticRouteNextHopHostAddress OBJECT-TYPE
        SYNTAX OCTET STRING
        ACCESS read-only
        STATUS mandatory
        DESCRIPTION
                "The next hop host address of this entry"
        ::= { wfIpxAutoStaticRouteEntry 8 }

    wfIpxStaticRouteMaskEntryTable OBJECT-TYPE
        SYNTAX SEQUENCE OF WfIpxStaticRouteMaskEntry
        ACCESS not-accessible
        STATUS mandatory
        DESCRIPTION
                "Wellfleet IPX Static Route Mask Table"
        ::= { wfIpxGroup 21 }

    wfIpxStaticRouteMaskEntry OBJECT-TYPE
        SYNTAX WfIpxStaticRouteMaskEntry
        ACCESS not-accessible
        STATUS mandatory
        DESCRIPTION
                "The static route mask table only allows auto static route
                entries to be made when the net fits the netmask."
        INDEX  { wfIpxStaticRouteMaskSysInstance,
           wfIpxStaticRouteMaskCircIndex,
           wfIpxStaticRouteMaskNetwork,
           wfIpxStaticRouteMaskNetworkMask }
        ::= { wfIpxStaticRouteMaskEntryTable 1 }

    WfIpxStaticRouteMaskEntry ::= SEQUENCE {
          wfIpxStaticRouteMaskDelete
         INTEGER,
          wfIpxStaticRouteMaskDisable
         INTEGER,
          wfIpxStaticRouteMaskSysInstance
         INTEGER,
          wfIpxStaticRouteMaskCircIndex
         INTEGER,
          wfIpxStaticRouteMaskNetwork
         OCTET STRING,
          wfIpxStaticRouteMaskNetworkMask
         OCTET STRING
        }

    wfIpxStaticRouteMaskDelete OBJECT-TYPE
        SYNTAX INTEGER {
             created(1),
             deleted(2)
         }
        ACCESS read-write
        STATUS mandatory
        DESCRIPTION
                "Create/Delete parameter. Default is created.
                Users perform an SNMP SET operation on this
                object in order to create/delete this entry."
        DEFVAL { created }
        ::= { wfIpxStaticRouteMaskEntry 1 }

    wfIpxStaticRouteMaskDisable OBJECT-TYPE
        SYNTAX INTEGER {
             enabled(1),
             disabled(2)
         }
        ACCESS read-write
        STATUS mandatory
        DESCRIPTION
                "Enable/Disable parameter. Default is enabled.
                Users perform an SNMP SET operation on this
                object in order to enable/disable an entry."
        DEFVAL { enabled }
        ::= { wfIpxStaticRouteMaskEntry 2 }

    wfIpxStaticRouteMaskSysInstance OBJECT-TYPE
        SYNTAX INTEGER
        ACCESS read-only
        STATUS mandatory
        DESCRIPTION
                "The unique identifier of the instance of IPX
                to which this entry corresponds."
        ::= { wfIpxStaticRouteMaskEntry 3 }

    wfIpxStaticRouteMaskCircIndex OBJECT-TYPE
        SYNTAX INTEGER
        ACCESS read-only
        STATUS mandatory
        DESCRIPTION
                "The identifier of this circuit, unique within the
                instance of RIP. This value corresponds to the IPX circuit
                identifier found in wfIpxCircIndex."
        ::= { wfIpxStaticRouteMaskEntry 4 }

    wfIpxStaticRouteMaskNetwork OBJECT-TYPE
        SYNTAX OCTET STRING (SIZE (4))
        ACCESS read-only
        STATUS mandatory
        DESCRIPTION
                "The network"
        ::= { wfIpxStaticRouteMaskEntry 5 }

    wfIpxStaticRouteMaskNetworkMask OBJECT-TYPE
        SYNTAX OCTET STRING (SIZE (4))
        ACCESS read-only
        STATUS mandatory
        DESCRIPTION
                "The network mask."
        ::= { wfIpxStaticRouteMaskEntry 6 }

    wfIpxServEntryTable OBJECT-TYPE
        SYNTAX SEQUENCE OF WfIpxServEntry
        ACCESS not-accessible
        STATUS mandatory
        DESCRIPTION
                "Wellfleet IPX service Table"
        ::= { wfIpxGroup 22 }

    wfIpxServEntry OBJECT-TYPE
        SYNTAX WfIpxServEntry
        ACCESS not-accessible
        STATUS mandatory
        DESCRIPTION
                "Table of services, indexed by type and name.
                NOTE: In the instance id wfIpxServName is
                      prefixed by the service name's length."
        INDEX  { wfIpxServSysInstance,
           wfIpxServType,
           wfIpxServName }
        ::= { wfIpxServEntryTable 1 }

    WfIpxServEntry ::= SEQUENCE {
          wfIpxServSysInstance
         INTEGER,
          wfIpxServType
         OCTET STRING,
          wfIpxServName
         DisplayString,
          wfIpxServProtocol
         INTEGER,
          wfIpxServNetNum
         OCTET STRING,
          wfIpxServNode
         OCTET STRING,
          wfIpxServSocket
         OCTET STRING,
          wfIpxServHopCount
         INTEGER,
          wfIpxServNextHopCircIndex
         INTEGER,
          wfIpxServNextHopHostAddress
         OCTET STRING,
          wfIpxServNextHopNetNum
         OCTET STRING,
          wfIpxServAge
         INTEGER
        }

    wfIpxServSysInstance OBJECT-TYPE
        SYNTAX INTEGER
        ACCESS read-only
        STATUS mandatory
        DESCRIPTION
                "The unique identifier of the instance of IPX
                to which this entry corresponds."
        ::= { wfIpxServEntry 1 }

    wfIpxServType OBJECT-TYPE
        SYNTAX OCTET STRING (SIZE (2))
        ACCESS read-only
        STATUS mandatory
        DESCRIPTION
                "The Service type."
        ::= { wfIpxServEntry 2 }

    wfIpxServName OBJECT-TYPE
        SYNTAX DisplayString
        ACCESS read-only
        STATUS mandatory
        DESCRIPTION
                "The Service name.
                NOTE: This is a variable length field, 2-47 chars."
        ::= { wfIpxServEntry 3 }

    wfIpxServProtocol OBJECT-TYPE
        SYNTAX INTEGER {
             other(1),
             local(2),
             nlsp(4),
             static(5),
             sap(6)
         }
        ACCESS read-only
        STATUS mandatory
        DESCRIPTION
                "The protocol from which knowledge of service was
                obtained."
        DEFVAL { other }
        ::= { wfIpxServEntry 4 }

    wfIpxServNetNum OBJECT-TYPE
        SYNTAX OCTET STRING
        ACCESS read-only
        STATUS mandatory
        DESCRIPTION
                "The IPX network number portion of the IPX address of the
                service."
        ::= { wfIpxServEntry 5 }

    wfIpxServNode OBJECT-TYPE
        SYNTAX OCTET STRING
        ACCESS read-only
        STATUS mandatory
        DESCRIPTION
                "The node portion of the IPX address of the service."
        ::= { wfIpxServEntry 6 }

    wfIpxServSocket OBJECT-TYPE
        SYNTAX OCTET STRING
        ACCESS read-only
        STATUS mandatory
        DESCRIPTION
                "The socket portion of the IPX address of the service."
        ::= { wfIpxServEntry 7 }

    wfIpxServHopCount OBJECT-TYPE
        SYNTAX INTEGER
        ACCESS read-only
        STATUS mandatory
        DESCRIPTION
                "The number of hops to the service."
        ::= { wfIpxServEntry 8 }

    wfIpxServNextHopCircIndex OBJECT-TYPE
        SYNTAX INTEGER
        ACCESS read-only
        STATUS mandatory
        DESCRIPTION
                "The unique identifier of the IPX circuit used to reach
                the next hop."
        ::= { wfIpxServEntry 9 }

    wfIpxServNextHopHostAddress OBJECT-TYPE
        SYNTAX OCTET STRING
        ACCESS read-only
        STATUS mandatory
        DESCRIPTION
                "The Host address of the Next Hop."
        ::= { wfIpxServEntry 10 }

    wfIpxServNextHopNetNum OBJECT-TYPE
        SYNTAX OCTET STRING
        ACCESS read-only
        STATUS mandatory
        DESCRIPTION
                "The IPX network number of the next hop."
        ::= { wfIpxServEntry 11 }

    wfIpxServAge OBJECT-TYPE
        SYNTAX INTEGER
        ACCESS read-only
        STATUS mandatory
        DESCRIPTION
                "The current age of this entry, in seconds. Local,
                Static, and NLSP services are not aged."
        ::= { wfIpxServEntry 12 }

    wfIpxUserStaticServEntryTable OBJECT-TYPE
        SYNTAX SEQUENCE OF WfIpxUserStaticServEntry
        ACCESS not-accessible
        STATUS mandatory
        DESCRIPTION
                "Wellfleet IPX User Static Service Table"
        ::= { wfIpxGroup 23 }

    wfIpxUserStaticServEntry OBJECT-TYPE
        SYNTAX WfIpxUserStaticServEntry
        ACCESS not-accessible
        STATUS mandatory
        DESCRIPTION
                "The Static Servs table contains information about all
                destinations reached via user statically configured Servs.
                NOTE: In the instance id wfIpxUserStaticServName is
                      prefixed by the service name's length."
        INDEX  { wfIpxUserStaticServSysInstance,
           wfIpxUserStaticServCircIndex,
           wfIpxUserStaticServName,
           wfIpxUserStaticServType }
        ::= { wfIpxUserStaticServEntryTable 1 }

    WfIpxUserStaticServEntry ::= SEQUENCE {
          wfIpxUserStaticServDelete
         INTEGER,
          wfIpxUserStaticServDisable
         INTEGER,
          wfIpxUserStaticServSysInstance
         INTEGER,
          wfIpxUserStaticServCircIndex
         INTEGER,
          wfIpxUserStaticServName
         DisplayString,
          wfIpxUserStaticServType
         OCTET STRING,
          wfIpxUserStaticServNetNum
         OCTET STRING,
          wfIpxUserStaticServHostAddress
         OCTET STRING,
          wfIpxUserStaticServSocket
         OCTET STRING,
          wfIpxUserStaticServHopCount
         INTEGER
        }

    wfIpxUserStaticServDelete OBJECT-TYPE
        SYNTAX INTEGER {
             created(1),
             deleted(2)
         }
        ACCESS read-write
        STATUS mandatory
        DESCRIPTION
                "Create/Delete parameter. Default is created.
                Users perform an SNMP SET operation on this
                object in order to create/delete this entry."
        DEFVAL { created }
        ::= { wfIpxUserStaticServEntry 1 }

    wfIpxUserStaticServDisable OBJECT-TYPE
        SYNTAX INTEGER {
             enabled(1),
             disabled(2)
         }
        ACCESS read-write
        STATUS mandatory
        DESCRIPTION
                "Enable/Disable parameter. Default is enabled.
                Users perform an SNMP SET operation on this
                object in order to enable/disable an entry."
        DEFVAL { enabled }
        ::= { wfIpxUserStaticServEntry 2 }

    wfIpxUserStaticServSysInstance OBJECT-TYPE
        SYNTAX INTEGER
        ACCESS read-only
        STATUS mandatory
        DESCRIPTION
                "The unique identifier of the instance of IPX
                to which this entry corresponds."
        ::= { wfIpxUserStaticServEntry 3 }

    wfIpxUserStaticServCircIndex OBJECT-TYPE
        SYNTAX INTEGER
        ACCESS read-only
        STATUS mandatory
        DESCRIPTION
                "The identifier of this circuit, unique within the
                instance of RIP. This value corresponds to the IPX circuit
                identifier found in wfIpxCircIndex."
        ::= { wfIpxUserStaticServEntry 4 }

    wfIpxUserStaticServName OBJECT-TYPE
        SYNTAX DisplayString
        ACCESS read-only
        STATUS mandatory
        DESCRIPTION
                "The service name.
                NOTE: This is a variable length field, 2-47 chars."
        ::= { wfIpxUserStaticServEntry 5 }

    wfIpxUserStaticServType OBJECT-TYPE
        SYNTAX OCTET STRING (SIZE (2))
        ACCESS read-only
        STATUS mandatory
        DESCRIPTION
                "The service type."
        ::= { wfIpxUserStaticServEntry 6 }

    wfIpxUserStaticServNetNum OBJECT-TYPE
        SYNTAX OCTET STRING
        ACCESS read-write
        STATUS mandatory
        DESCRIPTION
                "The network number of this static service."
        ::= { wfIpxUserStaticServEntry 7 }

    wfIpxUserStaticServHostAddress OBJECT-TYPE
        SYNTAX OCTET STRING
        ACCESS read-write
        STATUS mandatory
        DESCRIPTION
                "The host address of this static service."
        ::= { wfIpxUserStaticServEntry 8 }

    wfIpxUserStaticServSocket OBJECT-TYPE
        SYNTAX OCTET STRING
        ACCESS read-write
        STATUS mandatory
        DESCRIPTION
                "The socket of this static service."
        ::= { wfIpxUserStaticServEntry 9 }

    wfIpxUserStaticServHopCount OBJECT-TYPE
        SYNTAX INTEGER
        ACCESS read-write
        STATUS mandatory
        DESCRIPTION
                "The hop count of this static service."
        DEFVAL { 1 }
        ::= { wfIpxUserStaticServEntry 10 }

    wfIpxAutoStaticServEntryTable OBJECT-TYPE
        SYNTAX SEQUENCE OF WfIpxAutoStaticServEntry
        ACCESS not-accessible
        STATUS mandatory
        DESCRIPTION
                "Wellfleet IPX Auto Static Service Table"
        ::= { wfIpxGroup 24 }

    wfIpxAutoStaticServEntry OBJECT-TYPE
        SYNTAX WfIpxAutoStaticServEntry
        ACCESS not-accessible
        STATUS mandatory
        DESCRIPTION
                "The Static Servs table contains information about all
                destinations reached via Auto statically configured Servs.
                NOTE: In the instance id wfIpxAutoStaticServName is
                      prefixed by the service name's length."
        INDEX  { wfIpxAutoStaticServSysInstance,
           wfIpxAutoStaticServCircIndex,
           wfIpxAutoStaticServName,
           wfIpxAutoStaticServType }
        ::= { wfIpxAutoStaticServEntryTable 1 }

    WfIpxAutoStaticServEntry ::= SEQUENCE {
          wfIpxAutoStaticServDelete
         INTEGER,
          wfIpxAutoStaticServDisable
         INTEGER,
          wfIpxAutoStaticServSysInstance
         INTEGER,
          wfIpxAutoStaticServCircIndex
         INTEGER,
          wfIpxAutoStaticServName
         DisplayString,
          wfIpxAutoStaticServType
         OCTET STRING,
          wfIpxAutoStaticServNetNum
         OCTET STRING,
          wfIpxAutoStaticServHostAddress
         OCTET STRING,
          wfIpxAutoStaticServSocket
         OCTET STRING,
          wfIpxAutoStaticServHopCount
         INTEGER
        }

    wfIpxAutoStaticServDelete OBJECT-TYPE
        SYNTAX INTEGER {
             created(1),
             deleted(2)
         }
        ACCESS read-write
        STATUS mandatory
        DESCRIPTION
                "Create/Delete parameter. Default is created.
                Autos perform an SNMP SET operation on this
                object in order to create/delete this entry."
        DEFVAL { created }
        ::= { wfIpxAutoStaticServEntry 1 }

    wfIpxAutoStaticServDisable OBJECT-TYPE
        SYNTAX INTEGER {
             enabled(1),
             disabled(2)
         }
        ACCESS read-write
        STATUS mandatory
        DESCRIPTION
                "Enable/Disable parameter. Default is enabled.
                Autos perform an SNMP SET operation on this
                object in order to enable/disable an entry."
        DEFVAL { enabled }
        ::= { wfIpxAutoStaticServEntry 2 }

    wfIpxAutoStaticServSysInstance OBJECT-TYPE
        SYNTAX INTEGER
        ACCESS read-only
        STATUS mandatory
        DESCRIPTION
                "The unique identifier of the instance of IPX
                to which this entry corresponds."
        ::= { wfIpxAutoStaticServEntry 3 }

    wfIpxAutoStaticServCircIndex OBJECT-TYPE
        SYNTAX INTEGER
        ACCESS read-only
        STATUS mandatory
        DESCRIPTION
                "The identifier of this circuit, unique within the
                instance of RIP. This value corresponds to the IPX circuit
                identifier found in wfIpxCircIndex."
        ::= { wfIpxAutoStaticServEntry 4 }

    wfIpxAutoStaticServName OBJECT-TYPE
        SYNTAX DisplayString
        ACCESS read-only
        STATUS mandatory
        DESCRIPTION
                "The service name.
                NOTE: This is a variable length field, 2-47 chars."
        ::= { wfIpxAutoStaticServEntry 5 }

    wfIpxAutoStaticServType OBJECT-TYPE
        SYNTAX OCTET STRING
        ACCESS read-only
        STATUS mandatory
        DESCRIPTION
                "The service type."
        ::= { wfIpxAutoStaticServEntry 6 }

    wfIpxAutoStaticServNetNum OBJECT-TYPE
        SYNTAX OCTET STRING
        ACCESS read-only
        STATUS mandatory
        DESCRIPTION
                "The network number of this static service."
        ::= { wfIpxAutoStaticServEntry 7 }

    wfIpxAutoStaticServHostAddress OBJECT-TYPE
        SYNTAX OCTET STRING
        ACCESS read-only
        STATUS mandatory
        DESCRIPTION
                "The host address of this static service."
        ::= { wfIpxAutoStaticServEntry 8 }

    wfIpxAutoStaticServSocket OBJECT-TYPE
        SYNTAX OCTET STRING
        ACCESS read-only
        STATUS mandatory
        DESCRIPTION
                "The socket of this static service."
        ::= { wfIpxAutoStaticServEntry 9 }

    wfIpxAutoStaticServHopCount OBJECT-TYPE
        SYNTAX INTEGER
        ACCESS read-only
        STATUS mandatory
        DESCRIPTION
                "The hop count of this static service."
        DEFVAL { 1 }
        ::= { wfIpxAutoStaticServEntry 10 }

    wfIpxStaticServMaskEntryTable OBJECT-TYPE
        SYNTAX SEQUENCE OF WfIpxStaticServMaskEntry
        ACCESS not-accessible
        STATUS mandatory
        DESCRIPTION
                "Wellfleet IPX Static Service Mask Table"
        ::= { wfIpxGroup 25 }

    wfIpxStaticServMaskEntry OBJECT-TYPE
        SYNTAX WfIpxStaticServMaskEntry
        ACCESS not-accessible
        STATUS mandatory
        DESCRIPTION
                "The Static Servs table contains information about all
                destinations reached via Auto statically configured Servs."
        INDEX  { wfIpxStaticServMaskSysInstance,
           wfIpxStaticServMaskCircIndex,
           wfIpxStaticServMaskNetwork,
           wfIpxStaticServMaskNetworkMask }
        ::= { wfIpxStaticServMaskEntryTable 1 }

    WfIpxStaticServMaskEntry ::= SEQUENCE {
          wfIpxStaticServMaskDelete
         INTEGER,
          wfIpxStaticServMaskDisable
         INTEGER,
          wfIpxStaticServMaskSysInstance
         INTEGER,
          wfIpxStaticServMaskCircIndex
         INTEGER,
          wfIpxStaticServMaskNetwork
         OCTET STRING,
          wfIpxStaticServMaskNetworkMask
         OCTET STRING
        }

    wfIpxStaticServMaskDelete OBJECT-TYPE
        SYNTAX INTEGER {
             created(1),
             deleted(2)
         }
        ACCESS read-write
        STATUS mandatory
        DESCRIPTION
                "Create/Delete parameter. Default is created.
                Users perform an SNMP SET operation on this
                object in order to create/delete this entry."
        DEFVAL { created }
        ::= { wfIpxStaticServMaskEntry 1 }

    wfIpxStaticServMaskDisable OBJECT-TYPE
        SYNTAX INTEGER {
             enabled(1),
             disabled(2)
         }
        ACCESS read-write
        STATUS mandatory
        DESCRIPTION
                "Enable/Disable parameter. Default is enabled.
                Users perform an SNMP SET operation on this
                object in order to enable/disable an entry."
        DEFVAL { enabled }
        ::= { wfIpxStaticServMaskEntry 2 }

    wfIpxStaticServMaskSysInstance OBJECT-TYPE
        SYNTAX INTEGER
        ACCESS read-only
        STATUS mandatory
        DESCRIPTION
                "The unique identifier of the instance of IPX
                to which this entry corresponds."
        ::= { wfIpxStaticServMaskEntry 3 }

    wfIpxStaticServMaskCircIndex OBJECT-TYPE
        SYNTAX INTEGER
        ACCESS read-only
        STATUS mandatory
        DESCRIPTION
                "The identifier of this circuit, unique within the
                instance of RIP. This value corresponds to the IPX circuit
                identifier found in wfIpxCircIndex."
        ::= { wfIpxStaticServMaskEntry 4 }

    wfIpxStaticServMaskNetwork OBJECT-TYPE
        SYNTAX OCTET STRING (SIZE (4))
        ACCESS read-only
        STATUS mandatory
        DESCRIPTION
                "The network"
        ::= { wfIpxStaticServMaskEntry 5 }

    wfIpxStaticServMaskNetworkMask OBJECT-TYPE
        SYNTAX OCTET STRING (SIZE (4))
        ACCESS read-only
        STATUS mandatory
        DESCRIPTION
                "The network mask."
        ::= { wfIpxStaticServMaskEntry 6 }

    wfIpxStaticHostEntryTable OBJECT-TYPE
        SYNTAX SEQUENCE OF WfIpxStaticHostEntry
        ACCESS not-accessible
        STATUS mandatory
        DESCRIPTION
                "Wellfleet IPX Static Host Table"
        ::= { wfIpxGroup 26 }

    wfIpxStaticHostEntry OBJECT-TYPE
        SYNTAX WfIpxStaticHostEntry
        ACCESS not-accessible
        STATUS mandatory
        DESCRIPTION
                "The static host entries define mappings from circindex
                and host address to wan physical layer address."
        INDEX  { wfIpxStaticHostSysInstance,
           wfIpxStaticHostCircIndex,
           wfIpxStaticHostAddress }
        ::= { wfIpxStaticHostEntryTable 1 }

    WfIpxStaticHostEntry ::= SEQUENCE {
          wfIpxStaticHostDelete
         INTEGER,
          wfIpxStaticHostDisable
         INTEGER,
          wfIpxStaticHostSysInstance
         INTEGER,
          wfIpxStaticHostCircIndex
         INTEGER,
          wfIpxStaticHostAddress
         OCTET STRING,
          wfIpxStaticHostWanAddress
         OCTET STRING,
          wfIpxStaticHostSubaddress
         DisplayString,
          wfIpxStaticHostTypeOfNumber
         INTEGER,
          wfIpxStaticHostType
         INTEGER,
          wfIpxStaticHostGreConnName
         DisplayString
        }

    wfIpxStaticHostDelete OBJECT-TYPE
        SYNTAX INTEGER {
             created(1),
             deleted(2)
         }
        ACCESS read-write
        STATUS mandatory
        DESCRIPTION
                "Create/Delete parameter. Default is created.
                Users perform an SNMP SET operation on this
                object in order to create/delete this entry."
        DEFVAL { created }
        ::= { wfIpxStaticHostEntry 1 }

    wfIpxStaticHostDisable OBJECT-TYPE
        SYNTAX INTEGER {
             enabled(1),
             disabled(2)
         }
        ACCESS read-write
        STATUS mandatory
        DESCRIPTION
                "Enable/Disable parameter. Default is enabled.
                Users perform an SNMP SET operation on this
                object in order to enable/disable an entry."
        DEFVAL { enabled }
        ::= { wfIpxStaticHostEntry 2 }

    wfIpxStaticHostSysInstance OBJECT-TYPE
        SYNTAX INTEGER
        ACCESS read-only
        STATUS mandatory
        DESCRIPTION
                "The unique identifier of the instance of IPX
                to which this entry corresponds."
        ::= { wfIpxStaticHostEntry 3 }

    wfIpxStaticHostCircIndex OBJECT-TYPE
        SYNTAX INTEGER
        ACCESS read-only
        STATUS mandatory
        DESCRIPTION
                "The identifier of this circuit, unique within the
                instance of RIP. This value corresponds to the IPX circuit
                identifier found in wfIpxCircIndex."
        ::= { wfIpxStaticHostEntry 4 }

    wfIpxStaticHostAddress OBJECT-TYPE
        SYNTAX OCTET STRING (SIZE (6))
        ACCESS read-only
        STATUS mandatory
        DESCRIPTION
                "The host address of this static host."
        ::= { wfIpxStaticHostEntry 5 }

    wfIpxStaticHostWanAddress OBJECT-TYPE
        SYNTAX OCTET STRING
        ACCESS read-write
        STATUS mandatory
        DESCRIPTION
                "The wan address of this host."
        ::= { wfIpxStaticHostEntry 6 }

    wfIpxStaticHostSubaddress OBJECT-TYPE
        SYNTAX DisplayString
        ACCESS read-write
        STATUS mandatory
        DESCRIPTION
                "The subaddress used to establish an SVC to the adjacent host."
        ::= { wfIpxStaticHostEntry 7 }

    wfIpxStaticHostTypeOfNumber OBJECT-TYPE
        SYNTAX INTEGER {
             unknown(1),
             international(2)
         }
        ACCESS read-write
        STATUS mandatory
        DESCRIPTION
                "The type of number used to establish an SVC to the adjacent
                 host."
        DEFVAL { international }
        ::= { wfIpxStaticHostEntry 8 }

    wfIpxStaticHostType OBJECT-TYPE
        SYNTAX INTEGER {
                    fre164(1),
                    default(2),
                    frx121(3),
                    frdlci(4),
                    gre(5),
                    atmsvc(6)
    		}
        ACCESS	read-write
        STATUS	mandatory
        DESCRIPTION
                "The type of static host."
        DEFVAL	{ default }
        ::= { wfIpxStaticHostEntry 9 }

    wfIpxStaticHostGreConnName OBJECT-TYPE
        SYNTAX  DisplayString
        ACCESS	read-write
        STATUS	mandatory
        DESCRIPTION
                "The name of the remote GRE connection to which a static host is configured."
        ::= { wfIpxStaticHostEntry 10 }

    wfIpxUserStaticNETBIOSTable OBJECT-TYPE
        SYNTAX	SEQUENCE OF WfIpxUserStaticNETBIOSEntry
        ACCESS	not-accessible
        STATUS	mandatory
        DESCRIPTION
                "Wellfleet IPX User Static NetBIOS Route Table"
        ::= { wfIpxGroup 27 }

    wfIpxUserStaticNETBIOSEntry OBJECT-TYPE
        SYNTAX	WfIpxUserStaticNETBIOSEntry
        ACCESS	not-accessible
        STATUS	mandatory
        DESCRIPTION
                "Contains entries that map NetBIOS names to destination addresses."
        INDEX	{ wfIpxUserStaticNETBIOSSysInstance,
    		  wfIpxUserStaticNETBIOSName }
        ::= { wfIpxUserStaticNETBIOSTable 1 }

    WfIpxUserStaticNETBIOSEntry ::= SEQUENCE {
    	    wfIpxUserStaticNETBIOSDelete
    		INTEGER,
    	    wfIpxUserStaticNETBIOSDisable
    		INTEGER,
    	    wfIpxUserStaticNETBIOSSysInstance
    		INTEGER,
    	    wfIpxUserStaticNETBIOSName
    		DisplayString,
    	    wfIpxUserStaticNETBIOSDestNetwork
    		OCTET STRING
        }

    wfIpxUserStaticNETBIOSDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete this entry."
        DEFVAL	{ created }
        ::= { wfIpxUserStaticNETBIOSEntry 1 }

    wfIpxUserStaticNETBIOSDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an entry."
        DEFVAL	{ enabled }
        ::= { wfIpxUserStaticNETBIOSEntry 2 }

    wfIpxUserStaticNETBIOSSysInstance OBJECT-TYPE
        SYNTAX	INTEGER
        ACCESS	read-only
        STATUS	mandatory
        DESCRIPTION
                "The unique identifier of the instance of IPX
                to which this entry corresponds."
        ::= { wfIpxUserStaticNETBIOSEntry 3 }

    wfIpxUserStaticNETBIOSName OBJECT-TYPE
        SYNTAX	DisplayString
        ACCESS	read-only
        STATUS	mandatory
        DESCRIPTION
                "The destination name for this NetBIOS static route."
        ::= { wfIpxUserStaticNETBIOSEntry 4 }

    wfIpxUserStaticNETBIOSDestNetwork OBJECT-TYPE
        SYNTAX	OCTET STRING
        ACCESS	read-write
        STATUS	mandatory
        DESCRIPTION
                "The destination network for this NetBIOS static route."
        ::= { wfIpxUserStaticNETBIOSEntry 5 }

    wfIpxAutoStaticNETBIOSTable OBJECT-TYPE
        SYNTAX	SEQUENCE OF WfIpxAutoStaticNETBIOSEntry
        ACCESS	not-accessible
        STATUS	mandatory
        DESCRIPTION
                "Wellfleet IPX Auto Static NetBIOS Route Table"
        ::= { wfIpxGroup 28 }

    wfIpxAutoStaticNETBIOSEntry OBJECT-TYPE
        SYNTAX	WfIpxAutoStaticNETBIOSEntry
        ACCESS	not-accessible
        STATUS	mandatory
        DESCRIPTION
                "Contains entries that map NetBIOS names to destination addresses."
        INDEX	{ wfIpxAutoStaticNETBIOSSysInstance,
    		  wfIpxAutoStaticNETBIOSDestNetwork }
        ::= { wfIpxAutoStaticNETBIOSTable 1 }

    WfIpxAutoStaticNETBIOSEntry ::= SEQUENCE {
    	    wfIpxAutoStaticNETBIOSDelete
    		INTEGER,
    	    wfIpxAutoStaticNETBIOSDisable
    		INTEGER,
    	    wfIpxAutoStaticNETBIOSSysInstance
    		INTEGER,
    	    wfIpxAutoStaticNETBIOSDestNetwork
    		OCTET STRING,
    	    wfIpxAutoStaticNETBIOSName
    		DisplayString
        }

    wfIpxAutoStaticNETBIOSDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete this entry."
        DEFVAL	{ created }
        ::= { wfIpxAutoStaticNETBIOSEntry 1 }

    wfIpxAutoStaticNETBIOSDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an entry."
        DEFVAL	{ enabled }
        ::= { wfIpxAutoStaticNETBIOSEntry 2 }

    wfIpxAutoStaticNETBIOSSysInstance OBJECT-TYPE
        SYNTAX	INTEGER
        ACCESS	read-only
        STATUS	mandatory
        DESCRIPTION
                "The unique identifier of the instance of IPX
                to which this entry corresponds."
        ::= { wfIpxAutoStaticNETBIOSEntry 3 }

    wfIpxAutoStaticNETBIOSDestNetwork OBJECT-TYPE
        SYNTAX	OCTET STRING (SIZE (4))
        ACCESS	read-only
        STATUS	mandatory
        DESCRIPTION
                "The destination network for this NetBIOS static route."
        ::= { wfIpxAutoStaticNETBIOSEntry 4 }

    wfIpxAutoStaticNETBIOSName OBJECT-TYPE
        SYNTAX	DisplayString
        ACCESS	read-only
        STATUS	mandatory
        DESCRIPTION
                "The destination name for this NetBIOS static route."
        ::= { wfIpxAutoStaticNETBIOSEntry 5 }

    wfIpxRouteFilterTable OBJECT-TYPE
        SYNTAX	SEQUENCE OF WfIpxRouteFilterEntry
        ACCESS	not-accessible
        STATUS	mandatory
        DESCRIPTION
                "Wellfleet IPX Route Filter Table"
        ::= { wfIpxGroup 29 }

    wfIpxRouteFilterEntry OBJECT-TYPE
        SYNTAX	WfIpxRouteFilterEntry
        ACCESS	not-accessible
        STATUS	mandatory
        DESCRIPTION
                "Each entry corresponds to one filter."
        INDEX	{ wfIpxRouteFilterSysInstance,
    		  wfIpxRouteFilterCircIndex,
    		  wfIpxRouteFilterRuleNumber }
        ::= { wfIpxRouteFilterTable 1 }

    WfIpxRouteFilterEntry ::= SEQUENCE {
    	    wfIpxRouteFilterDelete
    		INTEGER,
    	    wfIpxRouteFilterDisable
    		INTEGER,
    	    wfIpxRouteFilterSysInstance
    		INTEGER,
    	    wfIpxRouteFilterCircIndex
    		INTEGER,
    	    wfIpxRouteFilterRuleNumber
    		INTEGER,
    	    wfIpxRouteFilterNetwork
    		OCTET STRING,
    	    wfIpxRouteFilterNetworkMask
    		OCTET STRING,
    	    wfIpxRouteFilterMode
    		INTEGER,
    	    wfIpxRouteFilterAction
    		INTEGER,
    	    wfIpxRouteFilterProtocol
    		INTEGER,
    	    wfIpxRouteFilterCost
    		INTEGER,
    	    wfIpxRouteFilterCounter
    		Counter,
    	    wfIpxRouteFilterPriority
    		INTEGER
        }

    wfIpxRouteFilterDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete this entry."
        DEFVAL	{ created }
        ::= { wfIpxRouteFilterEntry 1 }

    wfIpxRouteFilterDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an entry."
        DEFVAL	{ enabled }
        ::= { wfIpxRouteFilterEntry 2 }

    wfIpxRouteFilterSysInstance OBJECT-TYPE
        SYNTAX	INTEGER
        ACCESS	read-only
        STATUS	mandatory
        DESCRIPTION
                "The unique identifier of the instance of IPX
                to which this entry corresponds."
        ::= { wfIpxRouteFilterEntry 3 }

    wfIpxRouteFilterCircIndex OBJECT-TYPE
        SYNTAX	INTEGER
        ACCESS	read-only
        STATUS	mandatory
        DESCRIPTION
                "The identifier of this circuit, unique within the
                instance of IPX. This value corresponds to the IPX circuit
                identifier found in wfIpxCircIndex."
        ::= { wfIpxRouteFilterEntry 4 }

    wfIpxRouteFilterRuleNumber OBJECT-TYPE
        SYNTAX	INTEGER
        ACCESS	read-only
        STATUS	mandatory
        DESCRIPTION
                "The identifier of the filter, unique within the
                IPX circuit."
        ::= { wfIpxRouteFilterEntry 5 }

    wfIpxRouteFilterNetwork OBJECT-TYPE
        SYNTAX	OCTET STRING
        ACCESS	read-write
        STATUS	mandatory
        DESCRIPTION
                "The network"
        ::= { wfIpxRouteFilterEntry 6 }

    wfIpxRouteFilterNetworkMask OBJECT-TYPE
        SYNTAX	OCTET STRING
        ACCESS	read-write
        STATUS	mandatory
        DESCRIPTION
                "The network mask"
        ::= { wfIpxRouteFilterEntry 7 }

    wfIpxRouteFilterMode OBJECT-TYPE
        SYNTAX	INTEGER {
    		    outbound(1),
    		    inbound(2),
    		    both(3)
    		}
        ACCESS	read-write
        STATUS	mandatory
        DESCRIPTION
                "The mode for filtering, Inbound, Outbound, or Both."
        DEFVAL	{ outbound }
        ::= { wfIpxRouteFilterEntry 8 }

    wfIpxRouteFilterAction OBJECT-TYPE
        SYNTAX	INTEGER {
    		    advertise(1),
    		    suppress(2)
    		}
        ACCESS	read-write
        STATUS	mandatory
        DESCRIPTION
                "The action for the filter."
        DEFVAL	{ advertise }
        ::= { wfIpxRouteFilterEntry 9 }

    wfIpxRouteFilterProtocol OBJECT-TYPE
        SYNTAX	INTEGER {
    		    any(1),
    		    local(2),
    		    rip(3),
    		    nlsp(4),
    		    static(5)
    		}
        ACCESS	read-write
        STATUS	mandatory
        DESCRIPTION
                "Apply this filter only to routes learned on protocol X when
                sending RIP updates. Does not apply to Inbound routes. A value
                of 1 (default) represents any protocol."
        DEFVAL	{ any }
        ::= { wfIpxRouteFilterEntry 10 }

    wfIpxRouteFilterCost OBJECT-TYPE
        SYNTAX	INTEGER
        ACCESS	read-write
        STATUS	mandatory
        DESCRIPTION
                "Cost for routes matching this filter. A Zero cost indicates
                that the route's actual cost should be used. Value only used
                when action is Advertise."
        ::= { wfIpxRouteFilterEntry 11 }

    wfIpxRouteFilterCounter OBJECT-TYPE
        SYNTAX	Counter
        ACCESS	read-only
        STATUS	mandatory
        DESCRIPTION
                "The number of packets matching this filter."
        ::= { wfIpxRouteFilterEntry 12 }

    wfIpxRouteFilterPriority OBJECT-TYPE
        SYNTAX	INTEGER
        ACCESS	read-write
        STATUS	mandatory
        DESCRIPTION
                "Priority of this filter in relation to other filters of the
                same type."
        ::= { wfIpxRouteFilterEntry 13 }

    wfIpxServNetFilterTable OBJECT-TYPE
        SYNTAX	SEQUENCE OF WfIpxServNetFilterEntry
        ACCESS	not-accessible
        STATUS	mandatory
        DESCRIPTION
                "Wellfleet IPX Service Net Filter Table"
        ::= { wfIpxGroup 30 }

    wfIpxServNetFilterEntry OBJECT-TYPE
        SYNTAX	WfIpxServNetFilterEntry
        ACCESS	not-accessible
        STATUS	mandatory
        DESCRIPTION
                "Each entry corresponds to one service filter."
        INDEX	{ wfIpxServNetFilterSysInstance,
    		  wfIpxServNetFilterCircIndex,
    		  wfIpxServNetFilterRuleNumber }
        ::= { wfIpxServNetFilterTable 1 }

    WfIpxServNetFilterEntry ::= SEQUENCE {
    	    wfIpxServNetFilterDelete
    		INTEGER,
    	    wfIpxServNetFilterDisable
    		INTEGER,
    	    wfIpxServNetFilterSysInstance
    		INTEGER,
    	    wfIpxServNetFilterCircIndex
    		INTEGER,
    	    wfIpxServNetFilterRuleNumber
    		INTEGER,
    	    wfIpxServNetFilterNetwork
    		OCTET STRING,
    	    wfIpxServNetFilterNetworkMask
    		OCTET STRING,
    	    wfIpxServNetFilterType
    		OCTET STRING,
    	    wfIpxServNetFilterMode
    		INTEGER,
    	    wfIpxServNetFilterAction
    		INTEGER,
    	    wfIpxServNetFilterProtocol
    		INTEGER,
    	    wfIpxServNetFilterCost
    		INTEGER,
    	    wfIpxServNetFilterCounter
    		Counter,
    	    wfIpxServNetFilterPriority
    		INTEGER
        }

    wfIpxServNetFilterDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete this entry."
        DEFVAL	{ created }
        ::= { wfIpxServNetFilterEntry 1 }

    wfIpxServNetFilterDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an entry."
        DEFVAL	{ enabled }
        ::= { wfIpxServNetFilterEntry 2 }

    wfIpxServNetFilterSysInstance OBJECT-TYPE
        SYNTAX	INTEGER
        ACCESS	read-only
        STATUS	mandatory
        DESCRIPTION
                "The unique identifier of the instance of IPX
                to which this entry corresponds."
        ::= { wfIpxServNetFilterEntry 3 }

    wfIpxServNetFilterCircIndex OBJECT-TYPE
        SYNTAX	INTEGER
        ACCESS	read-only
        STATUS	mandatory
        DESCRIPTION
                "The identifier of this circuit, unique within the
                instance of RIP. This value corresponds to the IPX circuit
                identifier found in wfIpxCircIndex."
        ::= { wfIpxServNetFilterEntry 4 }

    wfIpxServNetFilterRuleNumber OBJECT-TYPE
        SYNTAX	INTEGER
        ACCESS	read-only
        STATUS	mandatory
        DESCRIPTION
                "The identifier of the filter, unique within the
                IPX circuit."
        ::= { wfIpxServNetFilterEntry 5 }

    wfIpxServNetFilterNetwork OBJECT-TYPE
        SYNTAX	OCTET STRING
        ACCESS	read-write
        STATUS	mandatory
        DESCRIPTION
                "The network."
        ::= { wfIpxServNetFilterEntry 6 }

    wfIpxServNetFilterNetworkMask OBJECT-TYPE
        SYNTAX	OCTET STRING
        ACCESS	read-write
        STATUS	mandatory
        DESCRIPTION
                "The network mask."
        ::= { wfIpxServNetFilterEntry 7 }

    wfIpxServNetFilterType OBJECT-TYPE
        SYNTAX	OCTET STRING
        ACCESS	read-write
        STATUS	mandatory
        DESCRIPTION
                "The service type."
        ::= { wfIpxServNetFilterEntry 8 }

    wfIpxServNetFilterMode OBJECT-TYPE
        SYNTAX	INTEGER {
    		    outbound(1),
    		    inbound(2),
    		    both(3)
    		}
        ACCESS	read-write
        STATUS	mandatory
        DESCRIPTION
                "The mode for filtering, Inbound, Outbound, or Both."
        DEFVAL	{ outbound }
        ::= { wfIpxServNetFilterEntry 9 }

    wfIpxServNetFilterAction OBJECT-TYPE
        SYNTAX	INTEGER {
    		    advertise(1),
    		    suppress(2)
    		}
        ACCESS	read-write
        STATUS	mandatory
        DESCRIPTION
                "The action for the filter."
        DEFVAL	{ advertise }
        ::= { wfIpxServNetFilterEntry 10 }

    wfIpxServNetFilterProtocol OBJECT-TYPE
        SYNTAX	INTEGER {
    		    any(1),
    		    local(2),
    		    nlsp(4),
    		    static(5),
    		    sap(6)
    		}
        ACCESS	read-write
        STATUS	mandatory
        DESCRIPTION
                "Apply this filter only to services learned on protocol X when
                sending SAP updates. Does not apply to Inbound services. A value
                of 1 (default) represents any protocol."
        DEFVAL	{ any }
        ::= { wfIpxServNetFilterEntry 11 }

    wfIpxServNetFilterCost OBJECT-TYPE
        SYNTAX	INTEGER
        ACCESS	read-write
        STATUS	mandatory
        DESCRIPTION
                "Cost for services matching this filter. A Zero cost indicates
                that the service's actual cost should be used. Value only used
                when action is Advertise."
        ::= { wfIpxServNetFilterEntry 12 }

    wfIpxServNetFilterCounter OBJECT-TYPE
        SYNTAX	Counter
        ACCESS	read-only
        STATUS	mandatory
        DESCRIPTION
                "The number of packets matching this filter."
        ::= { wfIpxServNetFilterEntry 13 }

    wfIpxServNetFilterPriority OBJECT-TYPE
        SYNTAX	INTEGER
        ACCESS	read-write
        STATUS	mandatory
        DESCRIPTION
                "Priority of this filter in relation to other filters of the
                same type."
        ::= { wfIpxServNetFilterEntry 14 }

    wfIpxServNameFilterTable OBJECT-TYPE
        SYNTAX	SEQUENCE OF WfIpxServNameFilterEntry
        ACCESS	not-accessible
        STATUS	mandatory
        DESCRIPTION
                "Wellfleet IPX Service Name Filter Table"
        ::= { wfIpxGroup 31 }

    wfIpxServNameFilterEntry OBJECT-TYPE
        SYNTAX	WfIpxServNameFilterEntry
        ACCESS	not-accessible
        STATUS	mandatory
        DESCRIPTION
                "Each entry corresponds to one service filter.
                NOTE: In the instance id wfIpxServNameFilterName is
                      prefixed by the service name's length."
        INDEX	{ wfIpxServNameFilterSysInstance,
    		  wfIpxServNameFilterCircIndex,
    		  wfIpxServNameFilterRuleNumber }
        ::= { wfIpxServNameFilterTable 1 }

    WfIpxServNameFilterEntry ::= SEQUENCE {
    	    wfIpxServNameFilterDelete
    		INTEGER,
    	    wfIpxServNameFilterDisable
    		INTEGER,
    	    wfIpxServNameFilterSysInstance
    		INTEGER,
    	    wfIpxServNameFilterCircIndex
    		INTEGER,
    	    wfIpxServNameFilterRuleNumber
    		INTEGER,
    	    wfIpxServNameFilterName
    		DisplayString,
    	    wfIpxServNameFilterType
    		OCTET STRING,
    	    wfIpxServNameFilterMode
    		INTEGER,
    	    wfIpxServNameFilterAction
    		INTEGER,
    	    wfIpxServNameFilterProtocol
    		INTEGER,
    	    wfIpxServNameFilterCost
    		INTEGER,
    	    wfIpxServNameFilterCounter
    		Counter,
    	    wfIpxServNameFilterPriority
    		INTEGER
        }

    wfIpxServNameFilterDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete this entry."
        DEFVAL	{ created }
        ::= { wfIpxServNameFilterEntry 1 }

    wfIpxServNameFilterDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an entry."
        DEFVAL	{ enabled }
        ::= { wfIpxServNameFilterEntry 2 }

    wfIpxServNameFilterSysInstance OBJECT-TYPE
        SYNTAX	INTEGER
        ACCESS	read-only
        STATUS	mandatory
        DESCRIPTION
                "The unique identifier of the instance of IPX
                to which this entry corresponds."
        ::= { wfIpxServNameFilterEntry 3 }

    wfIpxServNameFilterCircIndex OBJECT-TYPE
        SYNTAX	INTEGER
        ACCESS	read-only
        STATUS	mandatory
        DESCRIPTION
                "The identifier of this circuit, unique within the
                instance of RIP. This value corresponds to the IPX circuit
                identifier found in wfIpxCircIndex."
        ::= { wfIpxServNameFilterEntry 4 }

    wfIpxServNameFilterRuleNumber OBJECT-TYPE
        SYNTAX	INTEGER
        ACCESS	read-only
        STATUS	mandatory
        DESCRIPTION
                "The identifier of the filter, unique within the
                IPX circuit."
        ::= { wfIpxServNameFilterEntry 5 }

    wfIpxServNameFilterName OBJECT-TYPE
        SYNTAX	DisplayString
        ACCESS	read-write
        STATUS	mandatory
        DESCRIPTION
                "The name of the service to be filtered.
                NOTE: This is a variable length field, 2-47 chars.
                      This field may be a regex matching pattern."
        ::= { wfIpxServNameFilterEntry 6 }

    wfIpxServNameFilterType OBJECT-TYPE
        SYNTAX	OCTET STRING
        ACCESS	read-write
        STATUS	mandatory
        DESCRIPTION
                "The type of the service to be filtered."
        ::= { wfIpxServNameFilterEntry 7 }

    wfIpxServNameFilterMode OBJECT-TYPE
        SYNTAX	INTEGER {
    		    outbound(1),
    		    inbound(2),
    		    both(3)
    		}
        ACCESS	read-write
        STATUS	mandatory
        DESCRIPTION
                "The mode for filtering, Inbound, Outbound, or Both."
        DEFVAL	{ outbound }
        ::= { wfIpxServNameFilterEntry 8 }

    wfIpxServNameFilterAction OBJECT-TYPE
        SYNTAX	INTEGER {
    		    advertise(1),
    		    suppress(2)
    		}
        ACCESS	read-write
        STATUS	mandatory
        DESCRIPTION
                "The action for the filter."
        DEFVAL	{ advertise }
        ::= { wfIpxServNameFilterEntry 9 }

    wfIpxServNameFilterProtocol OBJECT-TYPE
        SYNTAX	INTEGER {
    		    any(1),
    		    local(2),
    		    nlsp(4),
    		    static(5),
    		    sap(6)
    		}
        ACCESS	read-write
        STATUS	mandatory
        DESCRIPTION
                "Apply this filter only to services learned on protocol X when
                sending SAP updates. Does not apply to Inbound services. A value
                of 1 (default) represents any protocol."
        DEFVAL	{ any }
        ::= { wfIpxServNameFilterEntry 10 }

    wfIpxServNameFilterCost OBJECT-TYPE
        SYNTAX	INTEGER
        ACCESS	read-write
        STATUS	mandatory
        DESCRIPTION
                "Cost for services matching this filter. A Zero cost indicates
                that the service's actual cost should be used. Value only used
                when action is Advertise."
        ::= { wfIpxServNameFilterEntry 11 }

    wfIpxServNameFilterCounter OBJECT-TYPE
        SYNTAX	Counter
        ACCESS	read-only
        STATUS	mandatory
        DESCRIPTION
                "The number of packets matching this filter."
        ::= { wfIpxServNameFilterEntry 12 }

    wfIpxServNameFilterPriority OBJECT-TYPE
        SYNTAX	INTEGER
        ACCESS	read-write
        STATUS	mandatory
        DESCRIPTION
                "Priority of this filter in relation to other filters of the
                same type."
        ::= { wfIpxServNameFilterEntry 13 }

    wfIpxRipCircTable OBJECT-TYPE
        SYNTAX	SEQUENCE OF WfIpxRipCircEntry
        ACCESS	not-accessible
        STATUS	mandatory
        DESCRIPTION
                "IPX RIP Circuit MIB"
        ::= { wfIpxGroup 32 }

    wfIpxRipCircEntry OBJECT-TYPE
        SYNTAX	WfIpxRipCircEntry
        ACCESS	not-accessible
        STATUS	mandatory
        DESCRIPTION
                "An entry in the IPX RIP circuit table"
        INDEX	{ wfIpxRipCircSysInstance,
    		  wfIpxRipCircIndex }
        ::= { wfIpxRipCircTable 1 }

    WfIpxRipCircEntry ::= SEQUENCE {
    	    wfIpxRipCircDelete
    		INTEGER,
    	    wfIpxRipCircDisable
    		INTEGER,
    	    wfIpxRipCircState
    		INTEGER,
    	    wfIpxRipCircSysInstance
    		INTEGER,
    	    wfIpxRipCircIndex
    		INTEGER,
    	    wfIpxRipCircMode
    		INTEGER,
    	    wfIpxRipCircPace
    		INTEGER,
    	    wfIpxRipCircUpdate
    		INTEGER,
    	    wfIpxRipCircAgeMultiplier
    		INTEGER,
    	    wfIpxRipCircPacketSize
    		INTEGER,
    	    wfIpxRipCircOutPackets
    		Counter,
    	    wfIpxRipCircInPackets
    		Counter,
    	    wfIpxRipCircBadPackets
    		Counter,
    	    wfIpxRipCircUseMulticast
    		INTEGER,
    	    wfIpxRipCircSplitHorizon
    		INTEGER,
    	    wfIpxRipCircGenAutoStaticRoutes
    		INTEGER,
    	    wfIpxRipCircImmedUpdate
    		INTEGER,
    	    wfIpxRipCircDefaultRouteSupply
    		INTEGER,
    	    wfIpxRipCircDefaultRouteListen
    		INTEGER,
    	    wfIpxRipCircLostRouteDisable
    		INTEGER
        }

    wfIpxRipCircDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete this entry."
        DEFVAL	{ created }
        ::= { wfIpxRipCircEntry 1 }

    wfIpxRipCircDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an entry."
        DEFVAL	{ enabled }
        ::= { wfIpxRipCircEntry 2 }

    wfIpxRipCircState OBJECT-TYPE
        SYNTAX	INTEGER {
    		    up(1),
    		    down(2),
    		    init(3),
    		    notpresent(4)
    		}
        ACCESS	read-only
        STATUS	mandatory
        DESCRIPTION
                "The current state of this entry"
        DEFVAL	{ notpresent }
        ::= { wfIpxRipCircEntry 3 }

    wfIpxRipCircSysInstance OBJECT-TYPE
        SYNTAX	INTEGER
        ACCESS	read-only
        STATUS	mandatory
        DESCRIPTION
                "The unique identifier of the instance of IPX
                to which this entry corresponds."
        ::= { wfIpxRipCircEntry 4 }

    wfIpxRipCircIndex OBJECT-TYPE
        SYNTAX	INTEGER
        ACCESS	read-only
        STATUS	mandatory
        DESCRIPTION
                "The identifier of this circuit, unique within the
                instance of RIP. This value corresponds to the IPX circuit
                identifier found in wfIpxCircIndex."
        ::= { wfIpxRipCircEntry 5 }

    wfIpxRipCircMode OBJECT-TYPE
        SYNTAX	INTEGER {
    		    standard(1),
    		    listen(2),
    		    supply(3),
    		    auto(4)
    		}
        ACCESS	read-write
        STATUS	mandatory
        DESCRIPTION
                "Whether this RIP entry is in mode."
        DEFVAL	{ standard }
        ::= { wfIpxRipCircEntry 6 }

    wfIpxRipCircPace OBJECT-TYPE
        SYNTAX	INTEGER
        ACCESS	read-write
        STATUS	mandatory
        DESCRIPTION
                "The maximum pace, in packets/second, at which RIP
                packets may be sent on this circuit."
        DEFVAL	{ 18 }
        ::= { wfIpxRipCircEntry 7 }

    wfIpxRipCircUpdate OBJECT-TYPE
        SYNTAX	INTEGER
        ACCESS	read-write
        STATUS	mandatory
        DESCRIPTION
                "The RIP periodic update interval, in seconds"
        DEFVAL	{ 60 }
        ::= { wfIpxRipCircEntry 8 }

    wfIpxRipCircAgeMultiplier OBJECT-TYPE
        SYNTAX	INTEGER
        ACCESS	read-write
        STATUS	mandatory
        DESCRIPTION
                "The holding multiplier for information received in
                RIP periodic updates."
        DEFVAL	{ 3 }
        ::= { wfIpxRipCircEntry 9 }

    wfIpxRipCircPacketSize OBJECT-TYPE
        SYNTAX	INTEGER
        ACCESS	read-write
        STATUS	mandatory
        DESCRIPTION
                "The Maximum RIP packet size used on this circuit"
        DEFVAL	{ 432 }
        ::= { wfIpxRipCircEntry 10 }

    wfIpxRipCircOutPackets OBJECT-TYPE
        SYNTAX	Counter
        ACCESS	read-only
        STATUS	mandatory
        DESCRIPTION
                "The number of locally created RIP packets sent out
                this IPX RIP circuit."
        ::= { wfIpxRipCircEntry 11 }

    wfIpxRipCircInPackets OBJECT-TYPE
        SYNTAX	Counter
        ACCESS	read-only
        STATUS	mandatory
        DESCRIPTION
                "The number of RIP packets received on this IPX circuit,
                destined locally."
        ::= { wfIpxRipCircEntry 12 }

    wfIpxRipCircBadPackets OBJECT-TYPE
        SYNTAX	Counter
        ACCESS	read-only
        STATUS	mandatory
        DESCRIPTION
                "The number of bad RIP packets received on this
                IPX circuit."
        ::= { wfIpxRipCircEntry 13 }

    wfIpxRipCircUseMulticast OBJECT-TYPE
        SYNTAX	INTEGER {
    		    enabled(1),
    		    disabled(2)
    		}
        ACCESS	read-write
        STATUS	mandatory
        DESCRIPTION
                "Use multicast address to send RIP packets."
        DEFVAL	{ enabled }
        ::= { wfIpxRipCircEntry 14 }

    wfIpxRipCircSplitHorizon OBJECT-TYPE
        SYNTAX	INTEGER {
    		    enabled(1),
    		    disabled(2)
    		}
        ACCESS	read-write
        STATUS	mandatory
        DESCRIPTION
                "Enable/Disable split horizon on this RIP circuit."
        DEFVAL	{ enabled }
        ::= { wfIpxRipCircEntry 15 }

    wfIpxRipCircGenAutoStaticRoutes OBJECT-TYPE
        SYNTAX	INTEGER {
    		    enabled(1),
    		    disabled(2)
    		}
        ACCESS	read-write
        STATUS	mandatory
        DESCRIPTION
                "Tell IPX to generate entries in the wfIpxAutoStaticRouteTable."
        DEFVAL	{ disabled }
        ::= { wfIpxRipCircEntry 16 }

    wfIpxRipCircImmedUpdate OBJECT-TYPE
        SYNTAX	INTEGER {
    		    enabled(1),
    		    disabled(2),
                    useglobal(3)
    		}
        ACCESS	read-write
        STATUS	mandatory
        DESCRIPTION
                "Enable/Disable parameter. Users perform an
                SNMP SET operation on this object in order to
                enable/disable RIP immediate update on this
                particular circuit. The 'useglobal(3)' means
                the value of the global parameter
                wfIpxAdvSysGlobalTrigUpdate will be used on the
                circuit for this attribute. Default is useglobal."
        DEFVAL  { useglobal }
        ::= { wfIpxRipCircEntry 17 }

    wfIpxRipCircDefaultRouteSupply OBJECT-TYPE
        SYNTAX	INTEGER {
    		    enabled(1),
    		    disabled(2)
    		}
        ACCESS	read-write
        STATUS	mandatory
        DESCRIPTION
                "Advertise the default route, 0xFFFFFFFE, in RIP packets."
        DEFVAL	{ disabled }
        ::= { wfIpxRipCircEntry 18 }

    wfIpxRipCircDefaultRouteListen OBJECT-TYPE
        SYNTAX	INTEGER {
    		    enabled(1),
    		    disabled(2)
    		}
        ACCESS	read-write
        STATUS	mandatory
        DESCRIPTION
                "Accept the default route, 0xFFFFFFFE, in RIP packets."
        DEFVAL	{ disabled }
        ::= { wfIpxRipCircEntry 19 }

    wfIpxRipCircLostRouteDisable OBJECT-TYPE
        SYNTAX	INTEGER {
    		    enable(1),
    		    disable(2)
    		}
        ACCESS	read-write
        STATUS	mandatory
        DESCRIPTION
                "Disable lost route on RIP circuit"
        DEFVAL	{ enable }
        ::= { wfIpxRipCircEntry 20 }

    wfIpxSapCircTable OBJECT-TYPE
        SYNTAX	SEQUENCE OF WfIpxSapCircEntry
        ACCESS	not-accessible
        STATUS	mandatory
        DESCRIPTION
                "IPX SAP Circuit MIB"
        ::= { wfIpxGroup 33 }

    wfIpxSapCircEntry OBJECT-TYPE
        SYNTAX	WfIpxSapCircEntry
        ACCESS	not-accessible
        STATUS	mandatory
        DESCRIPTION
                "An entry in the IPX SAP circuit table"
        INDEX	{ wfIpxSapCircSysInstance,
    		  wfIpxSapCircIndex }
        ::= { wfIpxSapCircTable 1 }

    WfIpxSapCircEntry ::= SEQUENCE {
    	    wfIpxSapCircDelete
    		INTEGER,
    	    wfIpxSapCircDisable
    		INTEGER,
    	    wfIpxSapCircState
    		INTEGER,
    	    wfIpxSapCircSysInstance
    		INTEGER,
    	    wfIpxSapCircIndex
    		INTEGER,
    	    wfIpxSapCircMode
    		INTEGER,
    	    wfIpxSapCircPace
    		INTEGER,
    	    wfIpxSapCircUpdate
    		INTEGER,
    	    wfIpxSapCircAgeMultiplier
    		INTEGER,
    	    wfIpxSapCircPacketSize
    		INTEGER,
    	    wfIpxSapCircGetNearestServerReply
    		INTEGER,
    	    wfIpxSapCircNSQAlphabetical
    		INTEGER,
    	    wfIpxSapCircOutPackets
    		Counter,
    	    wfIpxSapCircInPackets
    		Counter,
    	    wfIpxSapCircBadPackets
    		Counter,
    	    wfIpxSapCircUseMulticast
    		INTEGER,
    	    wfIpxSapCircSplitHorizon
    		INTEGER,
    	    wfIpxSapCircGenAutoStaticServices
    		INTEGER,
    	    wfIpxSapCircImmedUpdate
    		INTEGER,
    	    wfIpxSapCircSaveFullName
    		INTEGER
        }

    wfIpxSapCircDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete this entry."
        DEFVAL	{ created }
        ::= { wfIpxSapCircEntry 1 }

    wfIpxSapCircDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an entry."
        DEFVAL	{ enabled }
        ::= { wfIpxSapCircEntry 2 }

    wfIpxSapCircState OBJECT-TYPE
        SYNTAX	INTEGER {
    		    up(1),
    		    down(2),
    		    init(3),
    		    notpresent(4)
    		}
        ACCESS	read-only
        STATUS	mandatory
        DESCRIPTION
                "The current state of this entry"
        DEFVAL	{ notpresent }
        ::= { wfIpxSapCircEntry 3 }

    wfIpxSapCircSysInstance OBJECT-TYPE
        SYNTAX	INTEGER
        ACCESS	read-only
        STATUS	mandatory
        DESCRIPTION
                "The unique identifier of the instance of IPX
                to which this entry corresponds."
        ::= { wfIpxSapCircEntry 4 }

    wfIpxSapCircIndex OBJECT-TYPE
        SYNTAX	INTEGER
        ACCESS	read-only
        STATUS	mandatory
        DESCRIPTION
                "The identifier of this circuit, unique within the
                instance of SAP. This value corresponds to the IPX circuit
                identifier found in wfIpxCircIndex."
        ::= { wfIpxSapCircEntry 5 }

    wfIpxSapCircMode OBJECT-TYPE
        SYNTAX	INTEGER {
    		    standard(1),
    		    listen(2),
    		    supply(3),
    		    auto(4)
    		}
        ACCESS	read-write
        STATUS	mandatory
        DESCRIPTION
                "Whether this SAP entry is in mode."
        DEFVAL	{ standard }
        ::= { wfIpxSapCircEntry 6 }

    wfIpxSapCircPace OBJECT-TYPE
        SYNTAX	INTEGER
        ACCESS	read-write
        STATUS	mandatory
        DESCRIPTION
                "The maximum pace, in packets/second, at which SAP
                packets may be sent on this circuit."
        DEFVAL	{ 18 }
        ::= { wfIpxSapCircEntry 7 }

    wfIpxSapCircUpdate OBJECT-TYPE
        SYNTAX	INTEGER
        ACCESS	read-write
        STATUS	mandatory
        DESCRIPTION
                "The SAP periodic update interval, in seconds"
        DEFVAL	{ 60 }
        ::= { wfIpxSapCircEntry 8 }

    wfIpxSapCircAgeMultiplier OBJECT-TYPE
        SYNTAX	INTEGER
        ACCESS	read-write
        STATUS	mandatory
        DESCRIPTION
                "The holding multiplier for information received in
                SAP periodic updates."
        DEFVAL	{ 3 }
        ::= { wfIpxSapCircEntry 9 }

    wfIpxSapCircPacketSize OBJECT-TYPE
        SYNTAX	INTEGER
        ACCESS	read-write
        STATUS	mandatory
        DESCRIPTION
                "The Maximum SAP packet size used on this circuit"
        DEFVAL	{ 480 }
        ::= { wfIpxSapCircEntry 10 }

    wfIpxSapCircGetNearestServerReply OBJECT-TYPE
        SYNTAX	INTEGER {
    		    enabled(1),
    		    disabled(2)
    		}
        ACCESS	read-write
        STATUS	mandatory
        DESCRIPTION
                "Enable/Disable responding to GNS requests on this circuit."
        DEFVAL	{ enabled }
        ::= { wfIpxSapCircEntry 11 }

    wfIpxSapCircNSQAlphabetical OBJECT-TYPE
        SYNTAX	INTEGER {
    		    enabled(1),
    		    disabled(2)
    		}
        ACCESS	read-write
        STATUS	mandatory
        DESCRIPTION
                "Respond to NSQ in Alphabetical order, ie. first-best server."
        DEFVAL	{ enabled }
        ::= { wfIpxSapCircEntry 12 }

    wfIpxSapCircOutPackets OBJECT-TYPE
        SYNTAX	Counter
        ACCESS	read-only
        STATUS	mandatory
        DESCRIPTION
                "The number of locally created SAP packets sent out
                this IPX SAP circuit."
        ::= { wfIpxSapCircEntry 13 }

    wfIpxSapCircInPackets OBJECT-TYPE
        SYNTAX	Counter
        ACCESS	read-only
        STATUS	mandatory
        DESCRIPTION
                "The number of SAP packets received on this IPX circuit,
                destined locally."
        ::= { wfIpxSapCircEntry 14 }

    wfIpxSapCircBadPackets OBJECT-TYPE
        SYNTAX	Counter
        ACCESS	read-only
        STATUS	mandatory
        DESCRIPTION
                "The number of bad SAP packets received on this
                IPX circuit."
        ::= { wfIpxSapCircEntry 15 }

    wfIpxSapCircUseMulticast OBJECT-TYPE
        SYNTAX	INTEGER {
    		    enabled(1),
    		    disabled(2)
    		}
        ACCESS	read-write
        STATUS	mandatory
        DESCRIPTION
                "Use multicast address to send SAP packets."
        DEFVAL	{ enabled }
        ::= { wfIpxSapCircEntry 16 }

    wfIpxSapCircSplitHorizon OBJECT-TYPE
        SYNTAX	INTEGER {
    		    enabled(1),
    		    disabled(2)
    		}
        ACCESS	read-write
        STATUS	mandatory
        DESCRIPTION
                "Enable/Disable split horizon on this SAP circuit."
        DEFVAL	{ enabled }
        ::= { wfIpxSapCircEntry 17 }

    wfIpxSapCircGenAutoStaticServices OBJECT-TYPE
        SYNTAX	INTEGER {
    		    enabled(1),
    		    disabled(2)
    		}
        ACCESS	read-write
        STATUS	mandatory
        DESCRIPTION
                "Tell IPX to generate entries in the wfIpxAutoStaticServTable."
        DEFVAL	{ disabled }
        ::= { wfIpxSapCircEntry 18 }

    wfIpxSapCircImmedUpdate OBJECT-TYPE
        SYNTAX	INTEGER {
    		    enabled(1),
    		    disabled(2),
                    useglobal(3)
    		}
        ACCESS	read-write
        STATUS	mandatory
        DESCRIPTION
                "Enable/Disable parameter. Users perform an
                SNMP SET operation on this object in order to
                enable/disable RIP immediate update on this
                particular circuit. The 'useglobal(3)' means
                the value of the global parameter
                wfIpxAdvSysGlobalTrigUpdate will be used on the
                circuit for this attribute. Default is useglobal."
        DEFVAL  { useglobal }
        ::= { wfIpxSapCircEntry 19 }

    wfIpxSapCircSaveFullName OBJECT-TYPE
        SYNTAX	INTEGER {
    		    enabled(1),
    		    disabled(2)
    		}
        ACCESS	read-write
        STATUS	mandatory
        DESCRIPTION
                "This allows the Router to ignore all characters following the
								 NULL character in the service name field of SAP packets. It
								 is intended to be a memory and cpu saving option."
        DEFVAL	{ enabled }
        ::= { wfIpxSapCircEntry 20 }

    wfIpxHostEntryTable OBJECT-TYPE
        SYNTAX	SEQUENCE OF WfIpxHostEntry
        ACCESS	not-accessible
        STATUS	mandatory
        DESCRIPTION
                "IPX Host table, contains information about all known hosts."
        ::= { wfIpxGroup 34 }

    wfIpxHostEntry OBJECT-TYPE
        SYNTAX	WfIpxHostEntry
        ACCESS	not-accessible
        STATUS	mandatory
        DESCRIPTION
                "Host table contains information about all known hosts."
        INDEX	{ wfIpxHostSysInstance,
    		  wfIpxHostNextHopCircIndex,
    		  wfIpxHostHostAddress }
        ::= { wfIpxHostEntryTable 1 }

    WfIpxHostEntry ::= SEQUENCE {
    	    wfIpxHostSysInstance
    		INTEGER,
    	    wfIpxHostNextHopCircIndex
    		INTEGER,
    	    wfIpxHostHostAddress
    		OCTET STRING,
    	    wfIpxHostNetNum
    		OCTET STRING,
    	    wfIpxHostWanAddress
    		OCTET STRING,
    	    wfIpxHostProtocol
    		INTEGER,
    	    wfIpxHostAge
    		INTEGER
        }

    wfIpxHostSysInstance OBJECT-TYPE
        SYNTAX	INTEGER
        ACCESS	read-only
        STATUS	mandatory
        DESCRIPTION
                "The unique identifier of the instance of IPX
                to which this entry corresponds."
        ::= { wfIpxHostEntry 1 }

    wfIpxHostNextHopCircIndex OBJECT-TYPE
        SYNTAX	INTEGER
        ACCESS	read-only
        STATUS	mandatory
        DESCRIPTION
                "The unique identifier of the IPX circuit used to reach
                the host."
        ::= { wfIpxHostEntry 2 }

    wfIpxHostHostAddress OBJECT-TYPE
        SYNTAX	OCTET STRING (SIZE (6))
        ACCESS	read-only
        STATUS	mandatory
        DESCRIPTION
                "The Host address of the Host."
        ::= { wfIpxHostEntry 3 }

    wfIpxHostNetNum OBJECT-TYPE
        SYNTAX	OCTET STRING
        ACCESS	read-only
        STATUS	mandatory
        DESCRIPTION
                "The network number of this host."
        ::= { wfIpxHostEntry 4 }

    wfIpxHostWanAddress OBJECT-TYPE
        SYNTAX	OCTET STRING
        ACCESS	read-only
        STATUS	mandatory
        DESCRIPTION
                "The Wan Physical address of this Host.
                NOTE: Only valid on WAN media where there is no
                      one-to-one mapping of host address to physical
                      address."
        ::= { wfIpxHostEntry 5 }

    wfIpxHostProtocol OBJECT-TYPE
        SYNTAX	INTEGER {
    		    other(1),
    		    local(2),
    		    dynamic(3),
    		    static(4)
    		}
        ACCESS	read-only
        STATUS	mandatory
        DESCRIPTION
                "The routing protocol from which knowledge of this
                host was obtained."
        DEFVAL	{ other }
        ::= { wfIpxHostEntry 6 }

    wfIpxHostAge OBJECT-TYPE
        SYNTAX	INTEGER
        ACCESS	read-only
        STATUS	mandatory
        DESCRIPTION
                "The current age of this entry, in seconds. Local and
                Static hosts are not aged."
        ::= { wfIpxHostEntry 7 }

    wfIpxForwardEntryTable OBJECT-TYPE
        SYNTAX	SEQUENCE OF WfIpxForwardEntry
        ACCESS	not-accessible
        STATUS	mandatory
        DESCRIPTION
                "IPX Forward table, contains information about
                all known forward entries."
        ::= { wfIpxGroup 35 }

    wfIpxForwardEntry OBJECT-TYPE
        SYNTAX	WfIpxForwardEntry
        ACCESS	not-accessible
        STATUS	mandatory
        DESCRIPTION
                "Forward table contains information about all
                known forward entries."
        INDEX	{ wfIpxForwardSysInstance,
    		  wfIpxForwardCircIndex,
    		  wfIpxForwardNetNum }
        ::= { wfIpxForwardEntryTable 1 }

    WfIpxForwardEntry ::= SEQUENCE {
    	    wfIpxForwardSysInstance
    		INTEGER,
    	    wfIpxForwardCircIndex
    		INTEGER,
    	    wfIpxForwardNetNum
    		OCTET STRING,
    	    wfIpxForwardType
    		INTEGER,
    	    wfIpxForwardProtocol
    		INTEGER,
    	    wfIpxForwardCount
    		Counter
        }

    wfIpxForwardSysInstance OBJECT-TYPE
        SYNTAX	INTEGER
        ACCESS	read-only
        STATUS	mandatory
        DESCRIPTION
                "The unique identifier of the instance of IPX
                to which this entry corresponds."
        ::= { wfIpxForwardEntry 1 }

    wfIpxForwardCircIndex OBJECT-TYPE
        SYNTAX	INTEGER
        ACCESS	read-only
        STATUS	mandatory
        DESCRIPTION
                "The unique identifier of the IPX circuit forward table
                in which this forward entry resides."
        ::= { wfIpxForwardEntry 2 }

    wfIpxForwardNetNum OBJECT-TYPE
        SYNTAX	OCTET STRING (SIZE (4))
        ACCESS	read-only
        STATUS	mandatory
        DESCRIPTION
                "The network number of this forward entry."
        ::= { wfIpxForwardEntry 3 }

    wfIpxForwardType OBJECT-TYPE
        SYNTAX	INTEGER {
    		    other(1),
    		    local(2),
    		    remote(3)
    		}
        ACCESS	read-only
        STATUS	mandatory
        DESCRIPTION
                "The type of this forward entry."
        DEFVAL	{ other }
        ::= { wfIpxForwardEntry 4 }

    wfIpxForwardProtocol OBJECT-TYPE
        SYNTAX	INTEGER {
    		    other(1),
    		    local(2),
    		    rip(3),
    		    nlsp(4),
    		    static(5)
    		}
        ACCESS	read-only
        STATUS	mandatory
        DESCRIPTION
                "The routing protocol from which knowledge of this
                forward was obtained."
        DEFVAL	{ other }
        ::= { wfIpxForwardEntry 5 }

    wfIpxForwardCount OBJECT-TYPE
        SYNTAX	Counter
        ACCESS	read-only
        STATUS	mandatory
        DESCRIPTION
                "The number of equal cost paths for this forward entry."
        ::= { wfIpxForwardEntry 6 }

    wfIpxTrafficFilter2Table OBJECT-TYPE
        SYNTAX	SEQUENCE OF WfIpxTrafficFilter2Entry
        ACCESS	not-accessible
        STATUS	mandatory
        DESCRIPTION
                "IPX Traffic Filters"
        ::= { wfIpxGroup 36 }

    wfIpxTrafficFilter2Entry OBJECT-TYPE
        SYNTAX	WfIpxTrafficFilter2Entry
        ACCESS	not-accessible
        STATUS	mandatory
        DESCRIPTION
                "A traffic filter definition"
        INDEX	{ wfIpxTrafficFilter2SysInstance,
    		  wfIpxTrafficFilter2CircIndex,
    		  wfIpxTrafficFilter2RuleNumber,
    		  wfIpxTrafficFilter2Fragment }
        ::= { wfIpxTrafficFilter2Table 1 }

    WfIpxTrafficFilter2Entry ::= SEQUENCE {
    	    wfIpxTrafficFilter2Create
    		INTEGER,
    	    wfIpxTrafficFilter2Enable
    		INTEGER,
    	    wfIpxTrafficFilter2Status
    		INTEGER,
    	    wfIpxTrafficFilter2Counter
    		Counter,
    	    wfIpxTrafficFilter2Definition
    		Opaque,
    	    wfIpxTrafficFilter2Reserved
    		INTEGER,
    	    wfIpxTrafficFilter2SysInstance
    		INTEGER,
    	    wfIpxTrafficFilter2CircIndex
    		INTEGER,
    	    wfIpxTrafficFilter2RuleNumber
    		INTEGER,
    	    wfIpxTrafficFilter2Fragment
    		INTEGER,
    	    wfIpxTrafficFilter2Name
    		DisplayString
        }

    wfIpxTrafficFilter2Create OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfIpxTrafficFilter2Entry 1 }

    wfIpxTrafficFilter2Enable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfIpxTrafficFilter2Entry 2 }

    wfIpxTrafficFilter2Status OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfIpxTrafficFilter2Entry 3 }

    wfIpxTrafficFilter2Counter OBJECT-TYPE
        SYNTAX	Counter
        ACCESS	read-only
        STATUS	mandatory
        DESCRIPTION
                "The number of received packets that have
                matched this rule."
        ::= { wfIpxTrafficFilter2Entry 4 }

    wfIpxTrafficFilter2Definition OBJECT-TYPE
        SYNTAX	Opaque
        ACCESS	read-write
        STATUS	mandatory
        DESCRIPTION
                "The filter rule definition."
        ::= { wfIpxTrafficFilter2Entry 5 }

    wfIpxTrafficFilter2Reserved OBJECT-TYPE
        SYNTAX	INTEGER
        ACCESS	read-only
        STATUS	mandatory
        DESCRIPTION
                "Reserved field."
        ::= { wfIpxTrafficFilter2Entry 6 }

    wfIpxTrafficFilter2SysInstance OBJECT-TYPE
        SYNTAX	INTEGER
        ACCESS	read-only
        STATUS	mandatory
        DESCRIPTION
                "The unique identifier for the instance of IPX."
        ::= { wfIpxTrafficFilter2Entry 7 }

    wfIpxTrafficFilter2CircIndex OBJECT-TYPE
        SYNTAX	INTEGER
        ACCESS	read-only
        STATUS	mandatory
        DESCRIPTION
                "The identifier of this IPX circuit. This
                value corresponds to the IPX circuit
                identifier found in wfIpxCircIndex."
        ::= { wfIpxTrafficFilter2Entry 8 }

    wfIpxTrafficFilter2RuleNumber OBJECT-TYPE
        SYNTAX	INTEGER
        ACCESS	read-only
        STATUS	mandatory
        DESCRIPTION
                "ID for the rule."
        ::= { wfIpxTrafficFilter2Entry 9 }

    wfIpxTrafficFilter2Fragment OBJECT-TYPE
        SYNTAX	INTEGER
        ACCESS	read-only
        STATUS	mandatory
        DESCRIPTION
                "Fragment number - for large rules."
        ::= { wfIpxTrafficFilter2Entry 10 }

    wfIpxTrafficFilter2Name OBJECT-TYPE
        SYNTAX	DisplayString
        ACCESS	read-write
        STATUS	mandatory
        DESCRIPTION
                "Name of the rule number."
        ::= { wfIpxTrafficFilter2Entry 11 }

    END  -- Wellfleet-IPXA-MIB
