NOKIA-ALCHEMYOS-CLUSTER-MIB DEFINITIONS ::= BEGIN

IMPORTS  alchemyOSModules, cryptoCluster, alchemyOSTraps
             FROM NOKIA-ALCHEMYOS-MIB
         OBJECT-IDENTITY, Integer32, MODULE-IDENTITY, OBJECT-TYPE, NOTIFICATION-TYPE, IpAddress
             FROM SNMPv2-SMI
         DisplayString
             FROM SNMPv2-TC;

nokiaAlchemyOSClusterMIB MODULE-IDENTITY
    LAST-UPDATED "200101180000Z"
    ORGANIZATION "Nokia Internet Communications."
    CONTACT-INFO 
		 "	Nokia, Inc.
			Customer Support

		  Postal: 100 Enterprise Way, Module B
			Scotts Valley, CA 95066
			USA
                  E-Mail: snmp-contact@cips.nokia.com"

    DESCRIPTION "Cluster MIB module."
    REVISION "200101180000Z"
    DESCRIPTION "Cleanup."
    ::= { alchemyOSModules 2 }

clusterInfoName OBJECT-TYPE
    SYNTAX      DisplayString
    MAX-ACCESS	read-only
    STATUS	current
    DESCRIPTION "The name of this cluster."
    ::= { cryptoCluster 1 }

clusterMemberInfoNumMembers OBJECT-TYPE
    SYNTAX      INTEGER (0..255)
    MAX-ACCESS	read-only
    STATUS	current
    DESCRIPTION "The number of members in this cluster."
    ::= { cryptoCluster 2 }

clusterAddrTable OBJECT-TYPE
        SYNTAX        SEQUENCE OF ClusterAddrEntry
	MAX-ACCESS    not-accessible
	STATUS	      current
        DESCRIPTION   "The list of IP addresses for this cluster."
	::= { cryptoCluster 3 }

clusterAddrEntry OBJECT-TYPE
	SYNTAX	      ClusterAddrEntry
        MAX-ACCESS    not-accessible
	STATUS	      current
        DESCRIPTION   "Cluster IP addresses."
	INDEX	      { clusterAddrIndex }
	::= { clusterAddrTable 1 }

ClusterAddrEntry ::= SEQUENCE {
		 clusterAddrIndex	INTEGER,
		 clusterInfoAddrs	IpAddress
		 }

clusterAddrIndex OBJECT-TYPE
        SYNTAX        INTEGER (0..255)
	MAX-ACCESS	      read-only
	STATUS	      current
        DESCRIPTION   "The index of the member list for this cluster."
	::= { clusterAddrEntry 1 }

clusterInfoAddrs OBJECT-TYPE
        SYNTAX        IpAddress
	MAX-ACCESS    read-only
	STATUS	      current
        DESCRIPTION   "The list of the cluster's IP addresses."
	::= { clusterAddrEntry 2 }

clusterMemberTable OBJECT-TYPE
    SYNTAX	SEQUENCE OF ClusterMemberEntry
    MAX-ACCESS	not-accessible
    STATUS	current
    DESCRIPTION "A list of information, one entry for each
                 member of the cluster."
    ::= { cryptoCluster 4 }

clusterMemberEntry OBJECT-TYPE
        SYNTAX        ClusterMemberEntry
        MAX-ACCESS    not-accessible
        STATUS        current
        DESCRIPTION   "A table entry containing information
                       about a member of the cluster."
        INDEX         { clusterMemberIndex }
        ::= { clusterMemberTable 1 }

ClusterMemberEntry ::= SEQUENCE {
	        clusterMemberIndex		INTEGER,
		clusterMemberPrimaryIPAddr	IpAddress,
		clusterMemberWorkload		INTEGER (0..255),
		clusterMemberMaster		INTEGER (0..255)
	     }

clusterMemberIndex OBJECT-TYPE
        SYNTAX        INTEGER (1..255)
        MAX-ACCESS    read-only
        STATUS        current
        DESCRIPTION   "A unique value for each member in the
                      cluster.  The value ranges between 1 and the value of
                      clusterMemberInfoNumMembers."
        ::= { clusterMemberEntry 1 }

clusterMemberPrimaryIPAddr OBJECT-TYPE
        SYNTAX        IpAddress
	MAX-ACCESS    read-only
	STATUS	      current
        DESCRIPTION   "The member's primary IP address."
	::= { clusterMemberEntry 2 }

clusterMemberWorkload OBJECT-TYPE
        SYNTAX        INTEGER  (0..255)
	MAX-ACCESS    read-only
	STATUS	      current
        DESCRIPTION   "The member's workload."
	::= { clusterMemberEntry 3 }

clusterMemberMaster OBJECT-TYPE
        SYNTAX        INTEGER { no(0), yes(1) }
	MAX-ACCESS    read-only
	STATUS	      current
        DESCRIPTION   "Is this member the master."
	::= { clusterMemberEntry 4 }

-- Each member of the cluster can have a list of secondary IP addresses...

clusterMemberSecondaryIPAddrTable OBJECT-TYPE
         SYNTAX	SEQUENCE OF ClusterMemberSecondaryIPAddrEntry
         MAX-ACCESS	not-accessible
         STATUS		current
         DESCRIPTION    "A table of secondary IP addresses
                         for this cluster member."
	 ::= { cryptoCluster 5 }

clusterMemberSecondaryIPAddrEntry OBJECT-TYPE
	SYNTAX        ClusterMemberSecondaryIPAddrEntry
        MAX-ACCESS    not-accessible
        STATUS        current
        DESCRIPTION   "List of the secondary (outside) addresses of the cluster
			    members.  This is only valid if this member is the
			    master node of the cluster."
        INDEX         { clusterMemberIndex, clusterMemberSecondaryIPAddrIndex }
        ::= { clusterMemberSecondaryIPAddrTable 1 }

ClusterMemberSecondaryIPAddrEntry ::= SEQUENCE {
		clusterMemberSecondaryIPAddr			IpAddress,
		clusterMemberSecondaryIPAddrIndex		Integer32
	     }

clusterMemberSecondaryIPAddr OBJECT-TYPE
        SYNTAX        IpAddress
	MAX-ACCESS    read-only
	STATUS	      current
        DESCRIPTION   "One member of the cluster's secondary IP address."
	::= { clusterMemberSecondaryIPAddrEntry 1 }

clusterMemberSecondaryIPAddrIndex OBJECT-TYPE
        SYNTAX       Integer32
        MAX-ACCESS   not-accessible
        STATUS       current
        DESCRIPTION "Second index for clusterMemberSecondaryIPAddrTable. The
		      first entry has index 1, the second 2, etc."
        ::= { clusterMemberSecondaryIPAddrEntry 2 }


-- Process table

processTable OBJECT-TYPE
    SYNTAX	SEQUENCE OF ProcessEntry
    MAX-ACCESS	not-accessible
    STATUS	current
    DESCRIPTION
	"A table containing information on running
	 processes/threads."
    ::= { cryptoCluster 6  }


processEntry OBJECT-TYPE
    SYNTAX	ProcessEntry
    MAX-ACCESS	not-accessible
    STATUS	current
    DESCRIPTION
        "An entry containing a process/thread name."
    INDEX	{ processIndex }
    ::= { processTable  1 }

ProcessEntry ::= SEQUENCE { 
    processIndex	INTEGER,
    processName		DisplayString
}

processIndex OBJECT-TYPE
    SYNTAX	INTEGER (1..65535)
    MAX-ACCESS	read-only
    STATUS	current
    DESCRIPTION
	"Reference Iindex for each process."
    ::= { processEntry 1 }

processName OBJECT-TYPE
    SYNTAX	DisplayString
    MAX-ACCESS	read-only
    STATUS	current
    DESCRIPTION
	"The process name."
    ::= { processEntry 2 }



-- The external IP address

externalIPAddress OBJECT-TYPE
        SYNTAX        IpAddress
	MAX-ACCESS    read-only
	STATUS	      current
        DESCRIPTION   "The external IP address."
	::= { cryptoCluster 7 }




-- Following are the various traps that can and will be sent.

alchemyOSTrap0 OBJECT-IDENTITY
    STATUS     current
    DESCRIPTION
        "Trap."
    ::= { alchemyOSTraps 0 }

clusterMemberJoin NOTIFICATION-TYPE
    STATUS     current
    DESCRIPTION
        "Signifies that a member node has joined the cluster."
    ::= { alchemyOSTrap0 1 }

clusterMemberLeft NOTIFICATION-TYPE
    STATUS     current
    DESCRIPTION
        "Signifies that a node has left the cluster."
    ::= { alchemyOSTrap0 2 }

clusterMemberBecameMaster NOTIFICATION-TYPE
    STATUS     current
    DESCRIPTION
        "Sent when a node has been made the master."
    ::= { alchemyOSTrap0 3 }

cpuUtilExceeded NOTIFICATION-TYPE
    STATUS     current
    DESCRIPTION
        "Sent when CPU utilisation exceeds defined limit."
    ::= { alchemyOSTrap0 4 }

ioLoadExceeded NOTIFICATION-TYPE
    STATUS     current
    DESCRIPTION
        "Sent when IO load exceeds defined limit."
    ::= { alchemyOSTrap0 5 }

droppedUdpPacketsExceeded NOTIFICATION-TYPE
    STATUS     current
    DESCRIPTION
        "Sent when UDP drop rate exceeds defined limit."
    ::= { alchemyOSTrap0 6 }

memUsageExceeded NOTIFICATION-TYPE
    STATUS     current
    DESCRIPTION
        "Sent when memory usage exceeds defined limit."
    ::= { alchemyOSTrap0 7 }


droppedIpPacketsExceeded NOTIFICATION-TYPE
    STATUS     current
    DESCRIPTION
        "Sent when IP packet drop rate exceeds defined limit."
    ::= { alchemyOSTrap0 8 }


gatedConfigError NOTIFICATION-TYPE
    STATUS     current
    DESCRIPTION
        "Sent when GATED detects errors in configuration and cannot proceed."
    ::= { alchemyOSTrap0 9 }


informAddress NOTIFICATION-TYPE
    OBJECTS { externalIPAddress }   
    STATUS     current
    DESCRIPTION
        "Sent to inform dynamic external interface address."
    ::= { alchemyOSTrap0 10 }


END
