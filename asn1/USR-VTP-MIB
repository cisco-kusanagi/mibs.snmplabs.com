USR-VTP-MIB DEFINITIONS ::= BEGIN
   IMPORTS
           	Integer32, Counter32, OBJECT-TYPE, OBJECT-IDENTITY,
                NOTIFICATION-TYPE, IpAddress, MODULE-IDENTITY
 			FROM SNMPv2-SMI
           	RowStatus,TimeStamp, DisplayString
                        FROM SNMPv2-TC
           	common, usrGre 
                        FROM USR-DEFINITIONS-MIB;
    usrVTP MODULE-IDENTITY
         LAST-UPDATED "200202202020Z"
         ORGANIZATION "CommWorks Corporation, a 3Com Company"
         CONTACT-INFO "Customer Support"
         DESCRIPTION
                 "The commWorks enterprise defined MIB objects for VTP"
         ::= { common 70 }
--       REVISION "200202202020Z"
--       DESCRIPTION " Converted trap to SNMPv2"         
--       REVISION "200205141520Z"
--       DESCRIPTION "Add structured trap comments"
	-- Textual Conventions       
        IpxNetwork ::= OCTET STRING (SIZE(4))
	usrVtpControl		OBJECT IDENTIFIER ::= { usrVTP 1 }
	usrVtpStatistics	OBJECT IDENTIFIER ::= { usrVTP 2 }
	usrVtpCca			OBJECT IDENTIFIER ::= { usrVTP 3 }
	usrVtpCcaTunnel		OBJECT IDENTIFIER ::= { usrVtpCca 1 }
	usrVtpCcaSession	OBJECT IDENTIFIER ::= { usrVtpCca 2 }
	usrVtpTraps         OBJECT IDENTIFIER ::= { usrVTP 6 }
	 usrGreControl           OBJECT IDENTIFIER       ::= { usrGre 1 }
     usrGreStatistics        OBJECT IDENTIFIER       ::= { usrGre 2 }
    --
    --  VTP (Process & Protocol) Control Group
    --
	usrVtpTimecheck	OBJECT-TYPE
		SYNTAX		INTEGER { enabled(1),disabled(2) }
		MAX-ACCESS	read-write
		STATUS		current
		DESCRIPTION	
			"This variable allows enabling/disabling of the timestamp 
			 check performed by VTP on received messages. If there are 
			 problems with the NTP server and/or clock synchronization,
			 it should be set to disabled."
		--CONFIGURABLE
	::= { usrVtpControl 1 }
--
--	VTP Statistics Group
--
	usrVtpRegistrationRequestsIn   OBJECT-TYPE
       SYNTAX   Counter32
       MAX-ACCESS   read-only
       STATUS   current
       DESCRIPTION
        "A table containing all the counters."
       ::= { usrVtpStatistics 1 }
     usrVtpRegistrationRequestsOut  OBJECT-TYPE
      SYNTAX    Counter32
      MAX-ACCESS    read-only
      STATUS    current
      DESCRIPTION
        "Registration requests sent counter"
      ::= { usrVtpStatistics 2 }
     usrVtpRegistrationResponsesIn  OBJECT-TYPE
      SYNTAX    Counter32
      MAX-ACCESS    read-only
      STATUS    current
      DESCRIPTION
        "Registration responses recvd"
      ::= { usrVtpStatistics 3 }
     usrVtpRegistrationResponsesOut OBJECT-TYPE
      SYNTAX    Counter32
      MAX-ACCESS    read-only
      STATUS    current
      DESCRIPTION
        "Registration responses sent"
      ::= { usrVtpStatistics 4 }
     usrVtpRefreshRequestsIn    OBJECT-TYPE
      SYNTAX    Counter32
      MAX-ACCESS    read-only
      STATUS    current
      DESCRIPTION
        "Refresh requests received."
      ::= { usrVtpStatistics 5 }
     usrVtpRefreshRequestsOut   OBJECT-TYPE
      SYNTAX    Counter32
      MAX-ACCESS    read-only
      STATUS    current
      DESCRIPTION
        "Refresh requests sent"
      ::= { usrVtpStatistics 6 }
     usrVtpRefreshResponsesIn   OBJECT-TYPE
      SYNTAX    Counter32
      MAX-ACCESS    read-only
      STATUS    current
      DESCRIPTION
        "Refresh responses received."
      ::= { usrVtpStatistics 7 }
     usrVtpRefreshResponsesOut  OBJECT-TYPE
      SYNTAX    Counter32
      MAX-ACCESS    read-only
      STATUS    current
      DESCRIPTION
        "Refresh responses sent"
      ::= { usrVtpStatistics 8 }
     usrVtpDeregistrationRequestsIn OBJECT-TYPE
      SYNTAX    Counter32
      MAX-ACCESS    read-only
      STATUS    current
      DESCRIPTION
        "De registration requests received"
      ::= { usrVtpStatistics 9 }
     usrVtpDeregistrationRequestsOut OBJECT-TYPE
      SYNTAX    Counter32
      MAX-ACCESS    read-only
      STATUS    current
      DESCRIPTION
        "De registration requests received"
      ::= { usrVtpStatistics 10 }
	usrVtpDeregistrationResponsesIn   OBJECT-TYPE
          SYNTAX        Counter32
          MAX-ACCESS    read-only
          STATUS        current
          DESCRIPTION
                "De registration responses sent"
          ::= { usrVtpStatistics 11 }
	usrVtpDeregistrationResponsesOut   OBJECT-TYPE
          SYNTAX        Counter32
          MAX-ACCESS    read-only
          STATUS        current
          DESCRIPTION
                "De registration responses sent"
          ::= { usrVtpStatistics 12 }
     usrVtpPDUAuthenticationFailures    OBJECT-TYPE
          SYNTAX        Counter32
          MAX-ACCESS    read-only
          STATUS        current
          DESCRIPTION
                "PDU authentication failures"
          ::= { usrVtpStatistics 13 }
     usrVtpVPNValidationFailures    OBJECT-TYPE
          SYNTAX        Counter32
          MAX-ACCESS    read-only
          STATUS        current
          DESCRIPTION
                "VPN validation failures"
          ::= { usrVtpStatistics 14 }
	 usrVtpTimeCheckFailures OBJECT-TYPE
        SYNTAX      Counter32
        MAX-ACCESS  read-only
        STATUS      current
        DESCRIPTION
            "The number of VTP messages which failed the
            timestamp check."
          ::= { usrVtpStatistics 15 }
--	
--	VTP CCA  Tunnel Group
--
	usrCcaTunnelTable OBJECT-TYPE
		SYNTAX		SEQUENCE OF UsrCcaTunnelEntry
		MAX-ACCESS	not-accessible
		STATUS		current
		DESCRIPTION
			"A table of CCA VTP tunnels"
	::= { usrVtpCcaTunnel 1 }
	usrCcaTunnelEntry 	OBJECT-TYPE
		SYNTAX		UsrCcaTunnelEntry
		MAX-ACCESS	not-accessible
		STATUS		current
		DESCRIPTION
			"An entry in the CCA VTP Tunnel table"
		INDEX { usrCcaTunnelTunnelIdx }
	::= { usrCcaTunnelTable 1 }
	UsrCcaTunnelEntry ::= SEQUENCE {
		usrCcaTunnelTunnelIdx			Integer32,
		usrCcaTunnelVPNName				DisplayString,
		usrCcaTunnelInterfaceName		DisplayString,
		usrCcaTunnelEstabTime			TimeStamp,
		usrCcaTunnelVPNId				Integer32,
		usrCcaTunnelGatewayAddr			IpAddress,
		usrCcaTunnelNasAddr				IpAddress,
		usrCcaTunnelSessionCount		Integer32,
		usrCcaTunnelStatus				RowStatus
	}
	usrCcaTunnelTunnelIdx	OBJECT-TYPE
		SYNTAX      Integer32
        MAX-ACCESS  read-only
        STATUS      current
        DESCRIPTION
            ""
    ::= { usrCcaTunnelEntry 1 }
	usrCcaTunnelVPNName OBJECT-TYPE
		SYNTAX		DisplayString
		MAX-ACCESS	read-only
		STATUS		current
		DESCRIPTION
			""
	::= { usrCcaTunnelEntry 2 }
	usrCcaTunnelInterfaceName 	OBJECT-TYPE
		SYNTAX		DisplayString
		MAX-ACCESS  read-only
		STATUS      current
        DESCRIPTION
            ""
    ::= { usrCcaTunnelEntry 3 }
	usrCcaTunnelEstabTime	OBJECT-TYPE
		SYNTAX      TimeStamp
        MAX-ACCESS  read-only
        STATUS      current
        DESCRIPTION
            ""
    ::= { usrCcaTunnelEntry 4 }
	usrCcaTunnelVPNId	OBJECT-TYPE
		SYNTAX      Integer32      
        MAX-ACCESS  read-only
        STATUS      current
        DESCRIPTION
            ""
    ::= { usrCcaTunnelEntry 5 }
	usrCcaTunnelGatewayAddr	OBJECT-TYPE
		SYNTAX      IpAddress      
        MAX-ACCESS  read-only
        STATUS      current
        DESCRIPTION
            ""
    ::= { usrCcaTunnelEntry 6 }
	usrCcaTunnelNasAddr	OBJECT-TYPE
		SYNTAX      IpAddress
        MAX-ACCESS  read-only
        STATUS      current
        DESCRIPTION
            ""
    ::= { usrCcaTunnelEntry 7 }
	usrCcaTunnelSessionCount	OBJECT-TYPE
		SYNTAX      Integer32
        MAX-ACCESS  read-only
        STATUS      current
        DESCRIPTION
            ""
    ::= { usrCcaTunnelEntry 8 }
	usrCcaTunnelStatus	OBJECT-TYPE
		SYNTAX      RowStatus
        MAX-ACCESS  read-write
        STATUS      current
        DESCRIPTION
            ""
    ::= { usrCcaTunnelEntry 9 }
	--
    --  VTP CCA Session Group
    --
    usrCcaSessionTable OBJECT-TYPE
        SYNTAX SEQUENCE OF UsrCcaSessionEntry
        MAX-ACCESS  not-accessible
        STATUS      current
        DESCRIPTION
            "A table of client sessions within a tunnel."
        ::= { usrVtpCcaSession 1 }
    usrCcaSessionEntry OBJECT-TYPE
        SYNTAX  UsrCcaSessionEntry
        MAX-ACCESS  not-accessible
        STATUS  current
        DESCRIPTION
            "An entry in the tunnel client session table."
        INDEX {usrCcaSessionTunnelId, usrCcaSessionSPI }
        ::= {usrCcaSessionTable 1 }
	UsrCcaSessionEntry ::= SEQUENCE {
        usrCcaSessionTunnelId       Integer32,
        usrCcaSessionSPI        Integer32,
        usrCcaSessionVPNId      Integer32,
        usrCcaSessionUserName       DisplayString,
        usrCcaSessionIPregistration INTEGER,
        usrCcaSessionIProuting      INTEGER,
        usrCcaSessionIProutingProto INTEGER,
        usrCcaSessionIPlocalAddress IpAddress,
        usrCcaSessionIPlocalMask    IpAddress,
        usrCcaSessionIPclientAddress    IpAddress,
        usrCcaSessionIPclientMask   IpAddress,
        usrCcaSessionIPXregistration    INTEGER,
        usrCcaSessionIPXrouting     INTEGER,
        usrCcaSessionIPXroutingProto    INTEGER,
        usrCcaSessionIPXlocalNetwork    IpxNetwork,
        usrCcaSessionIPXlocalNode   OCTET STRING,
        usrCcaSessionIPXclientNetwork   IpxNetwork,
        usrCcaSessionIPXclientNode  OCTET STRING,
        usrCcaSessionStatus     RowStatus
    }
    usrCcaSessionTunnelId OBJECT-TYPE
            SYNTAX      Integer32
            MAX-ACCESS      read-only
            STATUS          current
            DESCRIPTION
                        "The value used by VTP to uniquely identify this
                        tunnel by both the VPN Gateway and the NAS. This value
                        is also used in the GRE encapsulated packets to
                        identify which tunnel a given packet is on "
                ::= { usrCcaSessionEntry 1 }
	usrCcaSessionSPI OBJECT-TYPE
        SYNTAX      Integer32
        MAX-ACCESS  read-only
        STATUS      current
        DESCRIPTION
            "The session's Security Parameter Index. Used to
            identify a given session."
        ::= { usrCcaSessionEntry 2 }
    usrCcaSessionVPNId OBJECT-TYPE
        SYNTAX      Integer32
        MAX-ACCESS  read-only
        STATUS      current
        DESCRIPTION
            "The VPN Identifier for the VPN that this session's
            tunnel is a member of "
        ::= { usrCcaSessionEntry 3 }
    usrCcaSessionUserName OBJECT-TYPE
        SYNTAX      DisplayString (SIZE(1..80))
        MAX-ACCESS  read-only
        STATUS      current
        DESCRIPTION
            "The user login string as authenticated by the
            originating NAS."
        ::= { usrCcaSessionEntry 4 }
    usrCcaSessionIPregistration OBJECT-TYPE
        SYNTAX  INTEGER {
            enabled(1),
            disabled(2)
        }
        MAX-ACCESS  read-only
        STATUS      current
        DESCRIPTION
            "Indicates if IP is or is not registered for this
            session."
        ::= { usrCcaSessionEntry 5 }
	usrCcaSessionIProuting OBJECT-TYPE
        SYNTAX  INTEGER {
            none(0),
            broadcast(1),
            listen(2),
            broadcast-listen(3)
        }
        MAX-ACCESS  read-only
        STATUS      current
        DESCRIPTION
            "Indicates state of IP routing for this session."
        ::= { usrCcaSessionEntry 6 }
    usrCcaSessionIProutingProto OBJECT-TYPE
        SYNTAX  INTEGER {
            rip-I(1),
            rip-II(2),
            ospf(3)
        }
        MAX-ACCESS  read-only
        STATUS      current
        DESCRIPTION
            "If IP routing is enabled, indicates which routing
            protocol is used for this session."
        ::= { usrCcaSessionEntry 7 }
    usrCcaSessionIPlocalAddress OBJECT-TYPE
        SYNTAX      IpAddress
        MAX-ACCESS  read-only
        STATUS      current
        DESCRIPTION
            "The IP address the VPN Gateway's virtual router is
            using for this link."
        ::= { usrCcaSessionEntry 8 }
	usrCcaSessionIPlocalMask OBJECT-TYPE
        SYNTAX      IpAddress
        MAX-ACCESS  read-only
        STATUS      current
        DESCRIPTION
            "The IP subnet mask the VPN Gateway's virtual router
            is using for this link."
        ::= { usrCcaSessionEntry 9 }
    usrCcaSessionIPclientAddress OBJECT-TYPE
        SYNTAX      IpAddress
        MAX-ACCESS  read-only
        STATUS      current
        DESCRIPTION
            "The IP address of the NAS's dial-in client, which is
            the remote end of this link."
        ::= { usrCcaSessionEntry 10 }
    usrCcaSessionIPclientMask OBJECT-TYPE
        SYNTAX      IpAddress
        MAX-ACCESS  read-only
        STATUS      current
        DESCRIPTION
            "The IP subnet mask of the NAS's dial-in client, which
            is the remote end of this link."
        ::= { usrCcaSessionEntry 11 }
    usrCcaSessionIPXregistration OBJECT-TYPE
        SYNTAX  INTEGER {
            enabled(1),
            disabled(2)
        }
        MAX-ACCESS  read-only
        STATUS      current
        DESCRIPTION
            "Indicates if IPX is or is not registered for this
            session "
        ::= { usrCcaSessionEntry 12 }
	usrCcaSessionIPXrouting OBJECT-TYPE
        SYNTAX  INTEGER {
            none(0),
            send(1),
            listen(2),
            respond(3),
            all(4)
        }
        MAX-ACCESS  read-only
        STATUS      current
        DESCRIPTION
            "Indicates state of IPX routing for this session "
        ::= { usrCcaSessionEntry 13}
    usrCcaSessionIPXroutingProto OBJECT-TYPE
        SYNTAX  INTEGER {
            rip(1),
            nlsp(2)
        }
        MAX-ACCESS  read-only
        STATUS      current
        DESCRIPTION
            "If IPX routing is enabled, indicates which routing
            protocol is used for this session "
        ::= { usrCcaSessionEntry 14 }
    usrCcaSessionIPXlocalNetwork OBJECT-TYPE
        SYNTAX      IpxNetwork
        MAX-ACCESS  read-only
        STATUS      current
        DESCRIPTION
            "The IPX Network number the VPN Gateway's virtual
            router is using for this link."
        ::= { usrCcaSessionEntry 15 }
	usrCcaSessionIPXlocalNode OBJECT-TYPE
        SYNTAX      OCTET STRING (SIZE(6))
        MAX-ACCESS  read-only
        STATUS      current
        DESCRIPTION
            "The IPX Node address the VPN Gateway's virtual router
            is using for this link."
        ::= { usrCcaSessionEntry 16 }
    usrCcaSessionIPXclientNetwork OBJECT-TYPE
        SYNTAX      IpxNetwork
        MAX-ACCESS  read-only
        STATUS      current
        DESCRIPTION
            "The IPX Network number of the NAS's dial-in client,
            which is the remote end of this link "
        ::= { usrCcaSessionEntry 17 }
    usrCcaSessionIPXclientNode OBJECT-TYPE
        SYNTAX      OCTET STRING (SIZE(6))
        MAX-ACCESS  read-only
        STATUS      current
        DESCRIPTION
            "The IPX Node address of the NAS's dial-in client,
            which is the remote end of this link "
        ::= { usrCcaSessionEntry 18 }
    usrCcaSessionStatus OBJECT-TYPE
        SYNTAX      RowStatus
        MAX-ACCESS  read-write
        STATUS      current
        DESCRIPTION
            "The status of this entry."
        ::= { usrCcaSessionEntry 19 }
	        --
        --      GRE Control Group
        --
        usrGreState OBJECT-TYPE
                SYNTAX  INTEGER {
                        enabled(1),
                        disabled(2)
                }
                MAX-ACCESS      read-only
                STATUS          current
                DESCRIPTION
                        "Indicates if GRE is enabled or disabled. If the VTP
                        process is running, the state will always be enabled."
                ::= { usrGreControl 1 }
        --
        --      GRE Statistics Group
        --
        usrGreNetPktsIn OBJECT-TYPE
                SYNTAX          Counter32
                MAX-ACCESS      read-only
                STATUS          current
                DESCRIPTION
                        "Count of GRE encapsulated packets received from IP."
                ::= { usrGreStatistics 1 }
        usrGreNetPktsInDelivered OBJECT-TYPE
                SYNTAX          Counter32
                MAX-ACCESS      read-only
                STATUS          current
                DESCRIPTION
                        "Count of de-encapsulated GRE payloads delivered to
                        GRE clients."
                ::= { usrGreStatistics 2 }
		usrGreNetPktsInDiscarded OBJECT-TYPE
                SYNTAX          Counter32
                MAX-ACCESS      read-only
                STATUS          current
                DESCRIPTION
                        "Total count of de-encapsulated GRE payloads
                        discarded."
                ::= { usrGreStatistics 3 }
        usrGreNetPktsInHdrErrs OBJECT-TYPE
                SYNTAX          Counter32
                MAX-ACCESS      read-only
                STATUS          current
                DESCRIPTION
                        "Count of GRE packets discarded due to malformed
                        headers."
                ::= { usrGreStatistics 4 }
        usrGreNetPktsInNoClients OBJECT-TYPE
                SYNTAX          Counter32
                MAX-ACCESS      read-only
                STATUS          current
                DESCRIPTION
                        "Count of de-encapsulated GRE payloads discarded due
                        to no client."
                ::= { usrGreStatistics 5 }
        usrGreClientPktsIn OBJECT-TYPE
                SYNTAX          Counter32
                MAX-ACCESS      read-only
                STATUS          current
                DESCRIPTION
                        "Count of packets handed to GRE for encapsulation and
                        subsequent transmission."
                ::= { usrGreStatistics 6 }
		usrGreClientPktsEncapsulated OBJECT-TYPE
                SYNTAX          Counter32
                MAX-ACCESS      read-only
                STATUS          current
                DESCRIPTION
                        "Count of packets handed to GRE for encapsulation
                        which were actually encapsulated."
                ::= { usrGreStatistics 7 }
        usrGreClientPktsDiscarded OBJECT-TYPE
                SYNTAX          Counter32
                MAX-ACCESS      read-only
                STATUS          current
                DESCRIPTION
                        "Count of packets handed to GRE for encapsulation
                        which were discarded for some reason."
                ::= { usrGreStatistics 8 }
        usrGreClientPktToIP OBJECT-TYPE
                SYNTAX          Counter32
                MAX-ACCESS      read-only
                STATUS          current
                DESCRIPTION
                        "Count of GRE encapsulated payloads which were passed
                        to IP for transmission."
                ::= { usrGreStatistics 9 }
        usrVtpTrapsV2   OBJECT-IDENTITY
                STATUS  current    
                DESCRIPTION
                        "Events for VTP"
                ::= { usrVtpTraps 0 }
	usrVtpTunnelEstablishmentFailure NOTIFICATION-TYPE
                OBJECTS   {
                           usrCcaTunnelVPNId,
                           usrCcaTunnelGatewayAddr
                           }
                STATUS  current
                DESCRIPTION     "This trap is generated for tunnel
                                establishment failure."
                --#TYPE     "Tunnel establishment failure"
                --#SUMMARY  "Tunnel establishment failed for VPNId %d, gateway %d"
                --#ARGUMENTS { 0 1 }
                --#SEVERITY MAJOR
                --#STATE    OPERATIONAL
                --#PROBABLECAUSE "registrationErrorOrNoGatewayAvailable"
                ::= { usrVtpTrapsV2 1 }
	END -- End of USR-VTP-MIB DEFINITIONS
