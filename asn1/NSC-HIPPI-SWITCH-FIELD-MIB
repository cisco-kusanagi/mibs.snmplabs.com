-- Network Systems Corporation Enterprise MIB for Switch Management
-- Implementation of Field Structured Commands
-- Nov 3 1993
-- B. May

-- This MIB is to be used in conjunction with the NSC standard MIB to
-- define Switch specific information.  This MIB is common across all
-- NSC HIPPI switches.

	-- nscProducts, nscDevices, nscObj
	-- FROM NSC-MIB;

		NSC-HIPPI-SWITCH-FIELD-MIB DEFINITIONS ::= BEGIN

		IMPORTS
			OBJECT-TYPE, enterprises
			   FROM RFC1155-SMI
			DisplayString, PhysAddress
			   FROM RFC1213-MIB
			nsc, nscMib, nscProducts, nscHippiSwitch
			   FROM NSC-MIB;


    --  textual conventions

		-- For ease of lookup, the following are actually defined
		-- in the NSC MIB but are supplied here as comments.
		-- The content of this MIB definition is to define the
		-- objects under the nscHippiSwitch node.

		-- nsc			OBJECT IDENTIFIER ::= { enterprises 10 }
		-- nscMib		OBJECT IDENTIFIER ::= { nsc 2 }
		-- nscProducts		OBJECT IDENTIFIER ::= { nscMib 1 }
		--   nscDevices		OBJECT IDENTIFIER ::= { nscProducts 1 }
		--     nscObj		OBJECT IDENTIFIER ::= { nscDevices 1 }
		--   nscHippiSwitch	OBJECT IDENTIFIER ::= { nscProducts 4 }

		--
		-- The list immediately following (based upon ps32FieldDir)
		-- is the actual set of objects that may be operated upon
		-- for access to the Hippi Switch.  The syntax for access
		-- and the expected results are documented in the SMS 2.0 
		-- Installation and Reference Manual.
		--
		ps32FieldDir	OBJECT IDENTIFIER ::= { nscHippiSwitch 7 }

	     -- ps32BistAPort	OBJECT IDENTIFIER ::= { ps32FieldDir 1 }
		ps32Clear	OBJECT IDENTIFIER ::= { ps32FieldDir 2 }
		ps32Disable	OBJECT IDENTIFIER ::= { ps32FieldDir 3 }
		ps32Display	OBJECT IDENTIFIER ::= { ps32FieldDir 4 }
		ps32Enable	OBJECT IDENTIFIER ::= { ps32FieldDir 5 }
	     -- ps32ResetSwitch OBJECT-TYPE 	  ::= { ps32FieldDir 6 }
		ps32Restore	OBJECT IDENTIFIER ::= { ps32FieldDir 7 }
		ps32Save	OBJECT IDENTIFIER ::= { ps32FieldDir 8 }
		ps32Set		OBJECT IDENTIFIER ::= { ps32FieldDir 9 }

		ps32BistAPort OBJECT-TYPE
		   SYNTAX   DisplayString (SIZE (0..255))
		   ACCESS   read-write
		   STATUS   mandatory
		   DESCRIPTION
		       "The command to BIST (Built In Self Test) a single
		       port in the Hippi Switch.  The variable is set to
		       the port number of a valid installed port and a GET
		       results in a status text line based upon the latest
		       execution."
		::= { ps32FieldDir 1 }

		ps32ClearAll OBJECT-TYPE
		   SYNTAX   DisplayString (SIZE (0..255))
		   ACCESS   read-write
		   STATUS   mandatory
		   DESCRIPTION
		       "This object is a string which causes all errors, 
		       statistics, and pathways for all ports in the switch
		       to be cleared.  It is equivalent to setting the
		       ps32ClearErrorsAll, ps32ClearStatsAll, and 
		       ps32ClearPathAll variables.  The variable is not
		       actually used by the agent.  This variable returns
		       a status text line when a GET is issued."
		::= { ps32Clear 1 }

		ps32ClearErrorsAll OBJECT-TYPE
		   SYNTAX   DisplayString (SIZE (0..255))
		   ACCESS   read-write
		   STATUS   mandatory
		   DESCRIPTION
		       "This object is a dummy that asks the agent to clear
		       parity errors on all port in the switch.  The object
		       is not used by the agent.  This variable returns a 
		       status text line when a GET is issued."
		::= { ps32Clear 2 }

		ps32ClearErrorsInPort OBJECT-TYPE
		   SYNTAX   DisplayString (SIZE (0..255))
		   ACCESS   read-write
		   STATUS   mandatory
		   DESCRIPTION
		       "This object is a dummy that requests the agent to
		       clear parity errors for the port passed.  The var-
		       iable is used as the port number.  This variable 
		       returns a status text line when a GET is issued."
		::= { ps32Clear 3 }

		ps32ClearPathAll OBJECT-TYPE
		   SYNTAX   DisplayString (SIZE (0..255))
		   ACCESS   read-write
		   STATUS   mandatory
		   DESCRIPTION
		       "This object requests that all pathways for all
		       ports in the switch be cleared.  The variable is
		       not actually used by the agent code.  This variable 
		       returns a status text line when a GET is issued."
		::= { ps32Clear 4 }

		ps32ClearPathInPort OBJECT-TYPE
		   SYNTAX   DisplayString (SIZE (0..255))
		   ACCESS   read-write
		   STATUS   mandatory
		   DESCRIPTION
		       "This object requests that all pathways for a single
		       port in the switch be cleared.  The variable is
		       used by the agent code to determine the port to be
		       cleared.  This variable returns a status text line 
		       when a GET is issued."
		::= { ps32Clear 5 }

		ps32ClearPathDest OBJECT-TYPE
		   SYNTAX   DisplayString (SIZE (0..255))
		   ACCESS   read-write
		   STATUS   mandatory
		   DESCRIPTION
		       "This object requests that a single pathway for a 
		       single port in the switch be cleared.  The variable 
		       is used by the agent code to determine the port and
		       the Hippi Destination Address (which determines the
		       pathway) to be cleared.  This variable returns a 
		       status text line when a GET is issued."
		::= { ps32Clear 6 }

		ps32ClearPathForce OBJECT-TYPE
		   SYNTAX   DisplayString (SIZE (0..255))
		   ACCESS   read-write
		   STATUS   mandatory
		   DESCRIPTION
		       "This object requests that the forced pathway (if 
		       any) for a single port in the switch be cleared. 
		       The variable is used by the agent code to determine 
		       the port to be cleared.  This variable returns a 
		       status text line when a GET is issued."
		::= { ps32Clear 7 }

		ps32ClearStatsAll OBJECT-TYPE
		   SYNTAX   DisplayString (SIZE (0..255))
		   ACCESS   read-write
		   STATUS   mandatory
		   DESCRIPTION
		       "This object requests that the port statistics for 
		       all ports in the switch be cleared.  The variable 
		       is not used by the agent code. This variable returns
		       a status text line when a GET is issued."
		::= { ps32Clear 8 }

		ps32ClearStatsInPort OBJECT-TYPE
		   SYNTAX   DisplayString (SIZE (0..255))
		   ACCESS   read-write
		   STATUS   mandatory
		   DESCRIPTION
		       "This object requests that the port statistics for a 
		       single port in the switch be cleared.  The variable 
		       is used by the agent code to determine the port to be
		       cleared.  This variable returns a status text line 
		       when a GET is issued."
		::= { ps32Clear 9 }

		ps32Disable2	OBJECT IDENTIFIER ::= { ps32FieldDir 3 }

		ps32DisablePortAll OBJECT-TYPE
		   SYNTAX   DisplayString (SIZE (0..255))
		   ACCESS   read-write
		   STATUS   mandatory
		   DESCRIPTION
		       "This object, when set, causes the agent to disable
		       all ports in the switch.  The variable is not used
		       by the agent.  This variable returns a status text 
		       line when a GET is issued."
		::= { ps32Disable 1 }

		ps32DisablePortInPort OBJECT-TYPE
		   SYNTAX   DisplayString (SIZE (0..255))
		   ACCESS   read-write
		   STATUS   mandatory
		   DESCRIPTION
		       "This object, when set, causes the agent to disable
		       the requested port in the switch.  The variable is 
		       used by the agent to determine the port to be
		       disabled.  This variable returns a status text 
		       line when a GET is issued."
		::= { ps32Disable 2 }

		ps32Display2	OBJECT IDENTIFIER ::= { ps32FieldDir 4 }

		ps32Config	OBJECT IDENTIFIER ::= { ps32Display 1 }
		ps32PathList	OBJECT IDENTIFIER ::= { ps32Display 2 }
		ps32Status	OBJECT IDENTIFIER ::= { ps32Display 3 }
		-- ps32Version	OBJECT IDENTIFIER ::= { ps32Display 4 }
		ps32AllStatus	OBJECT IDENTIFIER ::= { ps32Status 1 }
		ps32IPStatus	OBJECT IDENTIFIER ::= { ps32Status 2 }
		ps32MiscStatus	OBJECT IDENTIFIER ::= { ps32Status 3 }


		ps32DCTitle OBJECT-TYPE
		   SYNTAX   DisplayString
		   ACCESS   read-only
		   STATUS   mandatory
		   DESCRIPTION
		       "Display Config Title Line"
		::= { ps32Config 1 }

		ps32DCTable OBJECT-TYPE
		   SYNTAX   SEQUENCE OF PS32DCEntry
		   ACCESS   not-accessible
		   STATUS   mandatory
		   DESCRIPTION
			"A table of status lines."
		   --DEFAULT test-function test-ps32DC
		   --DEFAULT next-function next-ps32DC
		::= { ps32Config 2 }

		ps32DCEntry OBJECT-TYPE
		   SYNTAX   PS32DCEntry
		   ACCESS   not-accessible
		   STATUS   mandatory
		   DESCRIPTION
		       "An individual config line."
		::= { ps32DCTable 1 }

		PS32DCEntry ::=
		    SEQUENCE {
        		ps32DCLine
			    DisplayString
		    }

		ps32DCLine OBJECT-TYPE
		   SYNTAX   DisplayString
		   ACCESS   read-only
		   STATUS   mandatory
		   DESCRIPTION
		       "An individual config line."
		::= { ps32DCEntry 1 }

		ps32DSATitle OBJECT-TYPE
		   SYNTAX   DisplayString
		   ACCESS   read-only
		   STATUS   mandatory
		   DESCRIPTION
		       "Status All Title Line 1"
		::= { ps32AllStatus 1 }

		ps32DSATable OBJECT-TYPE
		   SYNTAX   SEQUENCE OF PS32DSAEntry
		   ACCESS   not-accessible
		   STATUS   mandatory
		   DESCRIPTION
			"A table of status lines."
		   --DEFAULT test-function test-ps32DSA
		   --DEFAULT next-function next-ps32DSA
		::= { ps32AllStatus 2 }

		ps32DSAEntry OBJECT-TYPE
		   SYNTAX   PS32DSAEntry
		   ACCESS   not-accessible
		   STATUS   mandatory
		   DESCRIPTION
		       "An individual status line."
		::= { ps32DSATable 1 }

		PS32DSAEntry ::=
		    SEQUENCE {
        		ps32DSALine
			    DisplayString
		    }

		ps32DSALine OBJECT-TYPE
		   SYNTAX   DisplayString
		   ACCESS   read-only
		   STATUS   mandatory
		   DESCRIPTION
		       "An individual status line."
		::= { ps32DSAEntry 1 }


		ps32DSITable OBJECT-TYPE
		   SYNTAX   SEQUENCE OF PS32DSIEntry
		   ACCESS   not-accessible
		   STATUS   mandatory
		   DESCRIPTION
			"A table of status lines."
		   --DEFAULT get-function  get-ps32DSILine
		   --DEFAULT test-function test-ps32DSI
		   --DEFAULT next-function next-ps32DSI
		::= { ps32IPStatus 1 }

		ps32DSIEntry OBJECT-TYPE
		   SYNTAX   PS32DSIEntry
		   ACCESS   not-accessible
		   STATUS   mandatory
		   DESCRIPTION
		       "An individual status line."
		   INDEX { ps32PortNumber }
		::= { ps32DSITable 1 }

		PS32DSIEntry ::=
		    SEQUENCE {
        		ps32DSILine1
			    DisplayString,
        		ps32DSILine2
			    DisplayString,
        		ps32DSILine3
			    DisplayString,
        		ps32DSILine4
			    DisplayString,
        		ps32DSILine5
			    DisplayString,
        		ps32DSILine6
			    DisplayString,
        		ps32DSILine7
			    DisplayString,
        		ps32DSILine8
			    DisplayString,
        		ps32DSILine9
			    DisplayString
		    }

		ps32DSILine1 OBJECT-TYPE
		   SYNTAX   DisplayString
		   ACCESS   read-only
		   STATUS   mandatory
		   DESCRIPTION
		       "An individual status line."
		::= { ps32DSIEntry 1 }

		ps32DSILine2 OBJECT-TYPE
		   SYNTAX   DisplayString
		   ACCESS   read-only
		   STATUS   mandatory
		   DESCRIPTION
		       "An individual status line."
		::= { ps32DSIEntry 2 }

		ps32DSILine3 OBJECT-TYPE
		   SYNTAX   DisplayString
		   ACCESS   read-only
		   STATUS   mandatory
		   DESCRIPTION
		       "An individual status line."
		::= { ps32DSIEntry 3 }

		ps32DSILine4 OBJECT-TYPE
		   SYNTAX   DisplayString
		   ACCESS   read-only
		   STATUS   mandatory
		   DESCRIPTION
		       "An individual status line."
		::= { ps32DSIEntry 4 }

		ps32DSILine5 OBJECT-TYPE
		   SYNTAX   DisplayString
		   ACCESS   read-only
		   STATUS   mandatory
		   DESCRIPTION
		       "An individual status line."
		::= { ps32DSIEntry 5 }

		ps32DSILine6 OBJECT-TYPE
		   SYNTAX   DisplayString
		   ACCESS   read-only
		   STATUS   mandatory
		   DESCRIPTION
		       "An individual status line."
		::= { ps32DSIEntry 6 }

		ps32DSILine7 OBJECT-TYPE
		   SYNTAX   DisplayString
		   ACCESS   read-only
		   STATUS   mandatory
		   DESCRIPTION
		       "An individual status line."
		::= { ps32DSIEntry 7 }

		ps32DSILine8 OBJECT-TYPE
		   SYNTAX   DisplayString
		   ACCESS   read-only
		   STATUS   mandatory
		   DESCRIPTION
		       "An individual status line."
		::= { ps32DSIEntry 8 }

		ps32DSILine9 OBJECT-TYPE
		   SYNTAX   DisplayString
		   ACCESS   read-only
		   STATUS   mandatory
		   DESCRIPTION
		       "An individual status line."
		::= { ps32DSIEntry 9 }


		ps32DSMTable OBJECT-TYPE
		   SYNTAX   SEQUENCE OF PS32DSMEntry
		   ACCESS   not-accessible
		   STATUS   mandatory
		   DESCRIPTION
			"A table of status lines."
		   --DEFAULT get-function  get-ps32DSMLine
		   --DEFAULT test-function test-ps32DSM
		   --DEFAULT next-function next-ps32DSM
		::= { ps32MiscStatus 1 }

		ps32DSMEntry OBJECT-TYPE
		   SYNTAX   PS32DSMEntry
		   ACCESS   not-accessible
		   STATUS   mandatory
		   DESCRIPTION
		       "An individual status line."
		::= { ps32DSMTable 1 }

		PS32DSMEntry ::=
		    SEQUENCE {
        		ps32DSMLine
			    DisplayString
		    }

		ps32DSMLine OBJECT-TYPE
		   SYNTAX   DisplayString
		   ACCESS   read-only
		   STATUS   mandatory
		   DESCRIPTION
		       "An individual status line."
		::= { ps32DSMEntry 1 }

		ps32DSPTable OBJECT-TYPE
		   SYNTAX   DisplayString
		   ACCESS   read-only
		   STATUS   mandatory
		   DESCRIPTION
		       "Display Pathways Title Line 1"
		::= { ps32PathList 1 }

		ps32DSPPathwayTable OBJECT-TYPE
		   SYNTAX   SEQUENCE OF PS32DSPPathwayEntry
		   ACCESS   not-accessible
		   STATUS   mandatory
		   DESCRIPTION
		       "A sparsely populated table that can be used to
		       determine pathway information for a given port."
		   --DEFAULT test-function test-fieldPathway
		   --DEFAULT next-function next-fieldPathway
		::= { ps32DSPTable 1 }

		ps32DSPPathwayEntry OBJECT-TYPE
		   SYNTAX   PS32DSPPathwayEntry
		   ACCESS   not-accessible
		   STATUS   mandatory
		   DESCRIPTION
		       "An individual hippi switch pathway entry."
		   INDEX { ps32PortNumber, ps32PathwayHDA }
		::= { ps32DSPPathwayTable 1 }

		PS32DSPPathwayEntry ::=
		   SEQUENCE {
        		ps32DSPLine
			   DisplayString
		   }

		ps32DSPLine OBJECT-TYPE
		   SYNTAX   DisplayString
		   ACCESS   read-only
		   STATUS   mandatory
		   DESCRIPTION
		       "This is a list of output port numbers that can
		       supply a path or a portion of the path to the
		       specified HDA.  The number of output ports and
		       the number of ports that can be defined are switch
		       specific.  ie: the  can accept up to four
		       output ports with values of 0 to 31.

		       The port list contains decimal numbers and are
		       separated by spaces.  Specifying a new string
		       replaces any previous definitions including a
		       NULL string removing all definitions."
		::= { ps32DSPPathwayEntry 1 }

		ps32DSPDPathwayTable OBJECT-TYPE
		   SYNTAX   SEQUENCE OF PS32DSPDPathwayEntry
		   ACCESS   not-accessible
		   STATUS   mandatory
		   DESCRIPTION
		       "A sparsely populated table that can be used to
		       determine pathway information for a given port."
		   --DEFAULT test-function test-fieldPathway
		   --DEFAULT next-function next-fieldPathway
		::= { ps32PathList 2 }

		ps32DSPDPathwayEntry OBJECT-TYPE
		   SYNTAX   PS32DSPDPathwayEntry
		   ACCESS   not-accessible
		   STATUS   mandatory
		   DESCRIPTION
		       "An individual hippi switch pathway entry."
		   INDEX { ps32PortNumber, ps32PathwayHDA }
		::= { ps32DSPDPathwayTable 1 }

		PS32DSPDPathwayEntry ::=
		   SEQUENCE {
        		ps32DSPDLine
			   DisplayString
		   }

		ps32DSPDLine OBJECT-TYPE
		   SYNTAX   DisplayString
		   ACCESS   read-only
		   STATUS   mandatory
		   DESCRIPTION
		       "This is a list of output port numbers that can
		       supply a path or a portion of the path to the
		       specified HDA.  The number of output ports and
		       the number of ports that can be defined are switch
		       specific.  ie: the  can accept up to four
		       output ports with values of 0 to 31.

		       The port list contains decimal numbers and are
		       separated by spaces.  Specifying a new string
		       replaces any previous definitions including a
		       NULL string removing all definitions."
		::= { ps32DSPDPathwayEntry 1 }

		ps32DSPIPathwayTable OBJECT-TYPE
		   SYNTAX   SEQUENCE OF PS32DSPIPathwayEntry
		   ACCESS   not-accessible
		   STATUS   mandatory
		   DESCRIPTION
		       "A sparsely populated table that can be used to
		       determine pathway information for a given port."
		   --DEFAULT test-function test-fieldPathway
		   --DEFAULT next-function next-fieldPathway
		::= { ps32PathList 3 }

		ps32DSPIPathwayEntry OBJECT-TYPE
		   SYNTAX   PS32DSPIPathwayEntry
		   ACCESS   not-accessible
		   STATUS   mandatory
		   DESCRIPTION
		       "An individual hippi switch pathway entry."
		   INDEX { ps32PortNumber, ps32PathwayHDA }
		::= { ps32DSPIPathwayTable 1 }

		PS32DSPIPathwayEntry ::=
		   SEQUENCE {
        		ps32DSPILine
			   DisplayString
		   }

		ps32DSPILine OBJECT-TYPE
		   SYNTAX   DisplayString
		   ACCESS   read-only
		   STATUS   mandatory
		   DESCRIPTION
		       "This is a list of output port numbers that can
		       supply a path or a portion of the path to the
		       specified HDA.  The number of output ports and
		       the number of ports that can be defined are switch
		       specific.  ie: the  can accept up to four
		       output ports with values of 0 to 31.

		       The port list contains decimal numbers and are
		       separated by spaces.  Specifying a new string
		       replaces any previous definitions including a
		       NULL string removing all definitions."
		::= { ps32DSPIPathwayEntry 1 }

		ps32Version OBJECT-TYPE
		   SYNTAX   DisplayString
		   ACCESS   read-only
		   STATUS   mandatory
		   DESCRIPTION
		       "SMS Version String"
		::= { ps32Display 4 }


		ps32Enable2	OBJECT IDENTIFIER ::= { ps32FieldDir 5 }

		ps32EnablePortAll OBJECT-TYPE
		   SYNTAX   DisplayString (SIZE (0..255))
		   ACCESS   read-write
		   STATUS   mandatory
		   DESCRIPTION
		       "This object, when set, causes the agent to enable
		       all ports in the switch.  The variable is not used
		       by the agent.  This variable returns a status text 
		       line when a GET is issued."
		::= { ps32Enable 1 }

		ps32EnablePortInPort OBJECT-TYPE
		   SYNTAX   DisplayString (SIZE (0..255))
		   ACCESS   read-write
		   STATUS   mandatory
		   DESCRIPTION
		       "This object, when set, causes the agent to enable
		       the requested port in the switch.  The variable is 
		       used by the agent to determine the port to be
		       enabled.  This variable returns a status text 
		       line when a GET is issued."
		::= { ps32Enable 2 }

		ps32ResetSwitch OBJECT-TYPE
		   SYNTAX   DisplayString (SIZE (0..255))
		   ACCESS   read-write
		   STATUS   mandatory
		   DESCRIPTION
		       "This object is a dummy variable to allow the switch 
		       to be reset.  This procedure is NOT RECOMMENDED.  In
		       the current implementation this feature is not actu-
		       ally supported, but does the equivalent of CLEAR ALL.
		       This variable returns a status text line when a GET 
		       is issued."
		::= { ps32FieldDir 6 }

		ps32Restore2	OBJECT IDENTIFIER ::= { ps32FieldDir 7 }

		ps32RestorePathAll OBJECT-TYPE
		   SYNTAX   DisplayString (SIZE (0..255))
		   ACCESS   read-write
		   STATUS   mandatory
		   DESCRIPTION
		       "This object, when set, causes the agent to restore
		       all pathways in the switch.  The variable is not used
		       by the agent.  This variable returns a status text 
		       line when a GET is issued."
		::= { ps32Restore 1 }

		ps32RestorePathInPort OBJECT-TYPE
		   SYNTAX   DisplayString (SIZE (0..255))
		   ACCESS   read-write
		   STATUS   mandatory
		   DESCRIPTION
		       "This object, when set, causes the agent to restore
		       all pathways owned by the requested port.  The var-
		       iable is used by the agent to determine the port to 
		       be restored.  This variable returns a status text 
		       line when a GET is issued."
		::= { ps32Restore 2 }

		ps32Save2	OBJECT IDENTIFIER ::= { ps32FieldDir 8 }

		ps32SaveAll OBJECT-TYPE
		   SYNTAX   DisplayString (SIZE (0..255))
		   ACCESS   read-write
		   STATUS   mandatory
		   DESCRIPTION
		       "This object, when set, causes the agent to save the
		       current configuration and all pathways for all ports
		       in the switch.  This is the equivalent of issuing a
		       saveConfig followed by a savePathAll.  The variable 
		       is not used by the agent.  This variable returns a 
		       status text line when a GET is issued."
		::= { ps32Save 1 }

		ps32SaveConfig OBJECT-TYPE
		   SYNTAX   DisplayString (SIZE (0..255))
		   ACCESS   read-write
		   STATUS   mandatory
		   DESCRIPTION
		       "This object, when set, requests that the agent save
		       the current configuration into EEPROM.  The variable
		       is not used by the agent code.  This variable returns
		       a status text line when a GET is issued."
		::= { ps32Save 2 }

		ps32SavePathAll OBJECT-TYPE
		   SYNTAX   DisplayString (SIZE (0..255))
		   ACCESS   read-write
		   STATUS   mandatory
		   DESCRIPTION
		       "This object, when set, causes the agent to save all
		       pathways for all ports in the switch.  The variable 
		       is not used by the agent.  This variable returns a 
		       status text line when a GET is issued."
		::= { ps32Save 3 }

		ps32SavePathInPort OBJECT-TYPE
		   SYNTAX   DisplayString (SIZE (0..255))
		   ACCESS   read-write
		   STATUS   mandatory
		   DESCRIPTION
		       "This object, when set, causes the agent to save all
		       pathways for the requested port in the switch.  The
		       variable is used by the agent to determine the port
		       for which to save the pathways.  This object returns
		       a status text line when a GET is issued."
		::= { ps32Save 4 }

		ps32Set2		OBJECT IDENTIFIER ::= { ps32FieldDir 9 }

		ps32SetPathAll OBJECT-TYPE
		   SYNTAX   DisplayString (SIZE (0..255))
		   ACCESS   read-write
		   STATUS   mandatory
		   DESCRIPTION
		       "This object allows the user to request that for
		       every port in the switch, for a given Hippi Destin-
		       ation Address (HDA), a list of output ports (up to 4)
		       be set.  The variable is used to enter the HDA and
		       output ports as follows: HDA - 3 hex digits (0-fff);
		       ports - 2 decimal digits (0-31).  Thus, a request
		       could be formatted as 'f72 1 31 7 23'.  This variable
		       returns a status text line when a GET is issued."
		::= { ps32Set 1 }

		ps32SetPathDest OBJECT-TYPE
		   SYNTAX   DisplayString (SIZE (0..255))
		   ACCESS   read-write
		   STATUS   mandatory
		   DESCRIPTION
		       "This object allows the user to request that for
		       a given port in the switch, for a given Hippi Destin-
		       ation Address (HDA), a list of output ports (up to 4)
		       be set. The variable is used to enter the input port,
		       the HDA and output ports as follows: HDA - 3 hex 
		       digits (0-fff); ports - 2 decimal digits (0-31).
		       Thus, a request may be formatted as '23 f72 1 31 7'.
		       This variable returns a status text line when a GET
		       is issued."
		::= { ps32Set 2 }

		ps32SetPathForce OBJECT-TYPE
		   SYNTAX   DisplayString (SIZE (0..255))
		   ACCESS   read-write
		   STATUS   mandatory
		   DESCRIPTION
		       "This object allows the user to request that input 
		       for a given port in the switch be forced to the 
		       stated destination port.  The variable is used to 
		       enter the input port and output port as follows: 
		       ports - 1 or 2 decimal digits (0-31).  All requests
		       are formatted as '23 7' where 23 is the input port
		       and 7 is the output port.  This variable returns a 
		       status text line when a GET is issued."
		::= { ps32Set 3 }

		END
