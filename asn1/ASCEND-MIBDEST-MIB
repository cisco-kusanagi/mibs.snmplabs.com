--			Ascend mibdest MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDEST-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibdestProfile  OBJECT IDENTIFIER ::= { configuration 73}

	-- The mibdestProfile table
	--
	-- This table contains parameters for the mibdestProfile profile
	--

    mibdestProfileTable	OBJECT-TYPE
	SYNTAX		SEQUENCE OF MibdestProfileEntry
	ACCESS		not-accessible
	STATUS		mandatory
	DESCRIPTION	"A list of mibdestProfile profile entries."
	::= { mibdestProfile 1 }

    mibdestProfileEntry	OBJECT-TYPE
	SYNTAX		MibdestProfileEntry
	ACCESS		not-accessible
	STATUS		mandatory
	DESCRIPTION	"A mibdestProfile entry containing objects that
			 maps to the parameters of mibdestProfile profile."
	INDEX		{ destProfile-PlanNumber }
	::= { mibdestProfileTable 1 }

    MibdestProfileEntry ::=
	SEQUENCE {
	    destProfile-PlanNumber
		INTEGER,
	    destProfile-Name
		DisplayString,
	    destProfile-NumberOption
		INTEGER,
	    destProfile-Action-o
		INTEGER
	}

    destProfile-PlanNumber	OBJECT-TYPE
	SYNTAX	INTEGER
	ACCESS	read-only
	STATUS	mandatory
	DESCRIPTION	""
	::= { mibdestProfileEntry 1 }

    destProfile-Name	OBJECT-TYPE
	SYNTAX	DisplayString
	ACCESS	read-write
	STATUS	mandatory
	DESCRIPTION	""
	::= { mibdestProfileEntry 2 }

    destProfile-NumberOption	OBJECT-TYPE
	SYNTAX	INTEGER {
		    destSelFirstAvail (1),
		    destSelFirstActive (2),
		    destSelAnyAvail (3),
		    numberOfDestSel (4)
		}
	ACCESS	read-write
	STATUS	mandatory
	DESCRIPTION	""
	::= { mibdestProfileEntry 3 }

    destProfile-Action-o	OBJECT-TYPE
	SYNTAX	INTEGER {
		    noAction (1),
		    createProfile (2),
		    deleteProfile (3)
		}
	ACCESS	read-write
	STATUS	mandatory
	DESCRIPTION	""
	::= { mibdestProfileEntry 4 }


	-- The mibdestProfile__dest_number table
	--
	-- This table contains parameters for the mibdestProfile__dest_number profile
	--

    mibdestProfile-DestNumberTable	OBJECT-TYPE
	SYNTAX		SEQUENCE OF MibdestProfile-DestNumberEntry
	ACCESS		not-accessible
	STATUS		mandatory
	DESCRIPTION	"A list of mibdestProfile__dest_number profile entries."
	::= { mibdestProfile 2 }

    mibdestProfile-DestNumberEntry	OBJECT-TYPE
	SYNTAX		MibdestProfile-DestNumberEntry
	ACCESS		not-accessible
	STATUS		mandatory
	DESCRIPTION	"A mibdestProfile__dest_number entry containing objects that
			 maps to the parameters of mibdestProfile__dest_number profile."
	INDEX		{ destProfile-DestNumber-PlanNumber, destProfile-DestNumber-Index-o }
	::= { mibdestProfile-DestNumberTable 1 }

    MibdestProfile-DestNumberEntry ::=
	SEQUENCE {
	    destProfile-DestNumber-PlanNumber
		INTEGER,
	    destProfile-DestNumber-Index-o
		INTEGER,
	    destProfile-DestNumber-PhoneNumber
		DisplayString,
	    destProfile-DestNumber-CallByCallId
		INTEGER
	}

    destProfile-DestNumber-PlanNumber	OBJECT-TYPE
	SYNTAX	INTEGER
	ACCESS	read-only
	STATUS	mandatory
	DESCRIPTION	""
	::= { mibdestProfile-DestNumberEntry 1 }

    destProfile-DestNumber-Index-o	OBJECT-TYPE
	SYNTAX	INTEGER
	ACCESS	read-only
	STATUS	mandatory
	DESCRIPTION	""
	::= { mibdestProfile-DestNumberEntry 2 }

    destProfile-DestNumber-PhoneNumber	OBJECT-TYPE
	SYNTAX	DisplayString
	ACCESS	read-write
	STATUS	mandatory
	DESCRIPTION	""
	::= { mibdestProfile-DestNumberEntry 3 }

    destProfile-DestNumber-CallByCallId	OBJECT-TYPE
	SYNTAX	INTEGER
	ACCESS	read-write
	STATUS	mandatory
	DESCRIPTION	""
	::= { mibdestProfile-DestNumberEntry 4 }

END
