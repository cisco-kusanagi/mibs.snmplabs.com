-- Version 2.15.1.2, modified  2002-01-14 10:35:47-05 

        VPMT-OPT-MIB DEFINITIONS ::= BEGIN

        IMPORTS
				enterprises FROM RFC1155-SMI
            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }


        -- Textual Conventions

        DisplayString ::= OCTET STRING

        -- VPMT Configuration objects    
        
        cdx6500VPMTCfgTable OBJECT-TYPE
            SYNTAX SEQUENCE OF Cdx6500VPMTCfgEntry
            ACCESS not-accessible
            STATUS mandatory
            DESCRIPTION
                "An VPMT Configuration Table."
        ::= { cdx6500CfgGeneralGroup 26 }
        

        cdx6500VPMTCfgEntry OBJECT-TYPE
            SYNTAX Cdx6500VPMTCfgEntry
            ACCESS not-accessible
            STATUS mandatory
            DESCRIPTION
                "Entry in the VPMT Configuration Table.
                 Each entry contains an index(cdx6500VPMTCfgEntryNum),
                 and other configuration parameters fot a 
                 single VPMT table"
            INDEX { cdx6500VPMTCfgEntryNum }
        ::= { cdx6500VPMTCfgTable 1 }

        Cdx6500VPMTCfgEntry ::=
            SEQUENCE {                                                             
                cdx6500VPMTCfgEntryNum
                    INTEGER,              
                cdx6500VPMTCfgvpType
                    INTEGER,
                cdx6500VPMTCfgvpNum
                    INTEGER,
                cdx6500VPMTCfgdslNum
                    INTEGER,
                cdx6500VPMTCfgds0Rate
                    INTEGER,
                cdx6500VPMTCfgsrcTimeSlot
                    INTEGER,
                cdx6500VPMTCfgdestTimeSlot
                    INTEGER,
                cdx6500VPMTCfglocalDialNum
                    DisplayString,
                cdx6500VPMTCfgsubAddress
                    DisplayString,
                cdx6500VPMTCfgcallPermission
                    INTEGER,
                cdx6500VPMTCfgnum-ccs-bypass-connections
                    INTEGER,
                cdx6500VPMTCfgPhysical-Port 
                    INTEGER
                }

        cdx6500VPMTCfgEntryNum OBJECT-TYPE
            SYNTAX INTEGER
            ACCESS read-only
            STATUS mandatory
            DESCRIPTION
                "This indicate the VPMT Entry Number"
        ::= { cdx6500VPMTCfgEntry 1 }

        cdx6500VPMTCfgvpType OBJECT-TYPE
            SYNTAX INTEGER {
                    vpmt-ptype-null (1),
                    vpmt-ptype-voice (2),
                    vpmt-ptype-pri-voice (3),
                    vpmt-ptype-bypass-voice (4),
                    vpmt-ptype-tdm-data (5),
                    vpmt-ptype-pri-data (6),
                    vpmt-ptype-bypass-data (7),
                    vpmt-ptype-trans-ccs-voice (8),
                    vpmt-ptype-ccs-bypass (9),
                    vpmt-ptype-bri-voice (10),
                    vpmt-ptype-aam (11),
                    vpmt-ptype-num (12)
                    }
            ACCESS read-only
            STATUS mandatory
            DESCRIPTION
                "Specify the type of Virtual Port:
                   NULL         : No Configuration
                   TDM-VOICE    : Voice port operates on a configured DS0
                   PRI-VOICE    : Voice port operates on a DS0 determined by the
                                  ISDN/QSIG D-Channel
                   Transparent-CCS-VOICE : Voice port associated with a TBOP signaling
                                           channel
                   BYPASS-VOICE : Voice and signaling transparently switched
                                  between configured DS0's
                   TDM-DATA     : Data port operates on a configured DS0
                   PRI-DATA     : Data port operates on a DS0 determined by the
                                  ISDN/QSIG D-Channel
                   BYPASS-DATA  : Data transparently switched between configured DS0's
                   CCS-BYPASS   : Data or Voice switched between two ISDN/QSIG D-channel"
        ::= { cdx6500VPMTCfgEntry 2 }

        cdx6500VPMTCfgvpNum OBJECT-TYPE
            SYNTAX INTEGER (100..254)
            ACCESS read-only
            STATUS mandatory
            DESCRIPTION
                "Specify the Virtual Port Number, 100-254."
        ::= { cdx6500VPMTCfgEntry 3 }

        cdx6500VPMTCfgdslNum OBJECT-TYPE
            SYNTAX INTEGER (4..7)
            ACCESS read-only
            STATUS mandatory
            DESCRIPTION
                "Specify the Interface Number associated with this Virtual Port, 4-7 (1 based).
                 Interface Number 1 supports TDM or PRI Data Ports only,
                 Interface Number 2 and 3 not supported"
        ::= { cdx6500VPMTCfgEntry 4 }

        cdx6500VPMTCfgds0Rate OBJECT-TYPE
            SYNTAX INTEGER {
                    vpmt-rate-56k (1),
                    vpmt-rate-64k (2),
                    vpmt-rate-num (3)
                    }
            ACCESS read-only
            STATUS mandatory
            DESCRIPTION
                 "Specify the DS0 Rate.
                  For TDM-DATA this parameter controls the speed of the port.
                  For PRI-DATA this parameter controls the speed of the port only for
                  outbound calls from this node. 
                  The speed for an inbound call is determined by the incoming Call Request."
        ::= { cdx6500VPMTCfgEntry 5 }

        cdx6500VPMTCfgsrcTimeSlot OBJECT-TYPE
            SYNTAX INTEGER
            ACCESS read-only
            STATUS mandatory
            DESCRIPTION
                 "Specify the Time Slot assignments
                  No of DS0/B-channel 1-24 for T1
                  No of DS0/B-channel 1-31 for E1 - TDM-DATA
                  No of DS0/B-channel 1-15,17-31 for E1 - TDM-VOICE
                  Note: Only TDM-DATA virtual port type can use more than 1 time slot.
                        INT. 1 Supports max. 31 data ports.
                        INT. 4 & 5 Supports max 31 data ports and 30 voice ports
                        INT. 6 & 7 Supports max 31 data ports and 30 voice ports "
        ::= { cdx6500VPMTCfgEntry 6 }

        cdx6500VPMTCfgdestTimeSlot OBJECT-TYPE
            SYNTAX INTEGER
            ACCESS read-only
            STATUS mandatory
            DESCRIPTION
                 "Specify the number of Time Slot on the Destination interface:
                       1-24  for T1
                       1-31  for E1"
        ::= { cdx6500VPMTCfgEntry 7 }

        cdx6500VPMTCfglocalDialNum OBJECT-TYPE
            SYNTAX DisplayString (SIZE(0..17))
            ACCESS read-only
            STATUS mandatory
            DESCRIPTION
                 "Enter the Local Subscriber Address (ISDN number) for this
                  virtual port/CCS Bypass connection.
                  Use the space bar to blank the parameter. 1 to 20 characters
                  For Outgoing Call:
                    For Data Calls  - This will be passed as the outgoing Calling Party
                                      number. Only valid characters are 0 - 9.
                    For Voice Calls - This will be passed as the outgoing Calling Party
                                      number if the 'Calling Address Replacement' parameter
                                      is configured in the T1/E1 port record. Only valid
                                      characters are 0 - 9.
                                      For CCS Bypass  - This parameter is not applicable.
                  For Incoming Call:
                    For Data Calls  - The Called Party number received by the aggregate
                                      interface is compared to this parameter.
                                      Enter a trailing asterisk(*) as a wild-card.
                    For Voice Calls - This will be passed as the ingoing Calling Party
                                      number if the 'Calling Address Replacement' parameter
                                      is configured in the T1/E1 port record. Only valid
                                      characters are 0 - 9.
                    For CCS Bypass  - The Called Party Number received by the aggregate
                                      interface is compared to this parameter.
                                      If a match is found, the ISDN/QSIG call will be
                                      forwarded to the adjacent T1/E1 port.
                                      If the first character is a '!' the call will be
                                      BYPASS if the remaining number does not match
                                      the Called Party Number.
                                      If the first character is a '@' the call will be
                                      will not be BYPASS if the remaining number matches
                                      the Called Party Number and the search for BYPASS
                                      match will be aborted"
        ::= { cdx6500VPMTCfgEntry 8 }

        cdx6500VPMTCfgsubAddress OBJECT-TYPE
            SYNTAX DisplayString (SIZE(0..17))
            ACCESS read-only
            STATUS mandatory
            DESCRIPTION
                 "Outgoing Call:
                       This subaddress will be sent in the Call Setup Message.
                  Incomin Call:
                       This subaddress will be used for call verification if provided"
        ::= { cdx6500VPMTCfgEntry 9 }

        cdx6500VPMTCfgcallPermission OBJECT-TYPE
            SYNTAX INTEGER {
			out (1),
			inc (2)
                        }
            ACCESS read-only
            STATUS mandatory
            DESCRIPTION
                 "Clear Circuit Mode call permission criteria. This defines the
                  types of call handling criteria for the ISDN line.
                       OUT      - Initiates call only; does not accept call.
                       INC      - Accepts call only; does not send call to the network."
        ::= { cdx6500VPMTCfgEntry 10 }

        cdx6500VPMTCfgnum-ccs-bypass-connections OBJECT-TYPE
            SYNTAX INTEGER
            ACCESS read-only
            STATUS mandatory
            DESCRIPTION
                 "Specifies the maximum number of simultaneous CCS Bypass connections
                  allowed to the called number."
        ::= { cdx6500VPMTCfgEntry 11 }

        cdx6500VPMTCfgPhysical-Port OBJECT-TYPE
            SYNTAX INTEGER
            ACCESS read-only
            STATUS mandatory
            DESCRIPTION
                 "Specify the Physical Port Number."
        ::= { cdx6500VPMTCfgEntry 12 }

        END
