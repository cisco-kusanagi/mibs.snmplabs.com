Wellfleet-SR-MIB DEFINITIONS ::= BEGIN

-- Created by mdl2asn version 3.1
-- Creation date: Wed Aug 30 16:47:54 EDT 1995


    IMPORTS

      IpAddress, Counter
        FROM RFC1155-SMI
      OBJECT-TYPE
        FROM RFC-1212
      DisplayString
        FROM RFC1213-MIB
      wfBridgeGroup
        FROM Wellfleet-COMMON-MIB;

    wfBrSourceRouting	OBJECT IDENTIFIER ::= { wfBridgeGroup 2 }

    wfBrSr		OBJECT IDENTIFIER ::= { wfBrSourceRouting 1 }

    wfBrSrBaseDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the bridge."
        DEFVAL	{ created }
        ::= { wfBrSr 1 }

    wfBrSrBaseDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable the bridge."
        DEFVAL	{ enabled }
        ::= { wfBrSr 2 }

    wfBrSrBaseState OBJECT-TYPE
        SYNTAX	INTEGER {
    		    up(1),
    		    down(2),
    		    init(3),
    		    notpresent(4)
    		}
        ACCESS	read-only
        STATUS	mandatory
        DESCRIPTION
                "The current state of the SR bridge."
        DEFVAL	{ down }
        ::= { wfBrSr 3 }

    wfBrSrBaseInternalLanId OBJECT-TYPE
        SYNTAX	INTEGER
        ACCESS	read-write
        STATUS	mandatory
        DESCRIPTION
                "The SR bridge internal LAN ID"
        ::= { wfBrSr 4 }

    wfBrSrBaseBridgeId OBJECT-TYPE
        SYNTAX	INTEGER
        ACCESS	read-write
        STATUS	mandatory
        DESCRIPTION
                "The SR bridge Id"
        ::= { wfBrSr 5 }

    wfBrSrBaseGroupLanId OBJECT-TYPE
        SYNTAX	INTEGER
        ACCESS	read-write
        STATUS	mandatory
        DESCRIPTION
                "The SR bridge Group LAN ID"
        DEFVAL	{ 4095 }
        ::= { wfBrSr 6 }

    wfBrSrBaseIpEncapsDisable OBJECT-TYPE
        SYNTAX	INTEGER {
    		    enabled(1),
    		    disabled(2)
    		}
        ACCESS	read-write
        STATUS	mandatory
        DESCRIPTION
                "IP Encapsulation Enable/Disable"
        DEFVAL	{ disabled }
        ::= { wfBrSr 7 }

    wfBrSrBaseIpNetworkRingId OBJECT-TYPE
        SYNTAX	INTEGER
        ACCESS	read-write
        STATUS	mandatory
        DESCRIPTION
                "The ring number of a connected IP network"
        ::= { wfBrSr 8 }

    wfBrSrBaseIpInReceives OBJECT-TYPE
        SYNTAX	Counter
        ACCESS	read-only
        STATUS	mandatory
        DESCRIPTION
                "The number IP frames received by the network"
        ::= { wfBrSr 9 }

    wfBrSrBaseIpSeqErrors OBJECT-TYPE
        SYNTAX	Counter
        ACCESS	read-only
        STATUS	mandatory
        DESCRIPTION
                "The number IP frames received by the network"
        ::= { wfBrSr 10 }

    wfBrSrBaseIpMtuSize OBJECT-TYPE
        SYNTAX	INTEGER
        ACCESS	read-write
        STATUS	mandatory
        DESCRIPTION
                "The mtu size in bytes to be negotiated for
                the IP network.  This size will be converted
                to the LF code in the Route Control field"
        DEFVAL	{ 4562 }
        ::= { wfBrSr 11 }

    wfBrSrBaseNbServerRifCacheDisable OBJECT-TYPE
        SYNTAX	INTEGER {
    		    enabled(1),
    		    disabled(2)
    		}
        ACCESS	read-write
        STATUS	mandatory
        DESCRIPTION
                "Enable/Disable parameter for the NetBIOS Server rif cache"
        DEFVAL	{ disabled }
        ::= { wfBrSr 12 }

    wfBrSrBaseNbClientRifCacheDisable OBJECT-TYPE
        SYNTAX	INTEGER {
    		    enabled(1),
    		    disabled(2)
    		}
        ACCESS	read-write
        STATUS	mandatory
        DESCRIPTION
                "Enable/Disable parameter for the NetBIOS Client rif cache"
        DEFVAL	{ disabled }
        ::= { wfBrSr 13 }

    wfBrSrBaseNbDatagramRifCacheDisable OBJECT-TYPE
        SYNTAX	INTEGER {
    		    enabled(1),
    		    disabled(2)
    		}
        ACCESS	read-write
        STATUS	mandatory
        DESCRIPTION
                "Enable/Disable parameter for the NetBIOS Datagram rif cache"
        DEFVAL	{ disabled }
        ::= { wfBrSr 14 }

    wfBrSrBaseNb15CharacterDisable OBJECT-TYPE
        SYNTAX	INTEGER {
    		    enabled(1),
    		    disabled(2)
    		}
        ACCESS	read-write
        STATUS	mandatory
        DESCRIPTION
                "Enable/Disable parameter for 15-character NetBIOS name caching"
        DEFVAL	{ disabled }
        ::= { wfBrSr 15 }

    wfBrSrBaseNbRifMibDisable OBJECT-TYPE
        SYNTAX	INTEGER {
    		    enabled(1),
    		    disabled(2)
    		}
        ACCESS	read-write
        STATUS	mandatory
        DESCRIPTION
                "Enable/Disable creation of MIB instances for each cached name"
        DEFVAL	{ enabled }
        ::= { wfBrSr 16 }

    wfBrSrBaseNbMaximumRifEntries OBJECT-TYPE
        SYNTAX	INTEGER
        ACCESS	read-write
        STATUS	mandatory
        DESCRIPTION
                "The maximum number of entries allowed in the NetBIOS server/client rif cache"
        DEFVAL	{ 100 }
        ::= { wfBrSr 17 }

    wfBrSrBaseNbCurrentRifEntries OBJECT-TYPE
        SYNTAX	INTEGER
        ACCESS	read-only
        STATUS	mandatory
        DESCRIPTION
                "The number of entries currently in the NetBIOS server/client cache"
        ::= { wfBrSr 18 }

    wfBrSrBaseNbRifAgeTime OBJECT-TYPE
        SYNTAX	INTEGER
        ACCESS	read-write
        STATUS	mandatory
        DESCRIPTION
                "The age in seconds when inactive NetBIOS names will be aged out of the rif cache"
        DEFVAL	{ 300 }
        ::= { wfBrSr 19 }

    wfBrSrBaseNbRifHashEntries OBJECT-TYPE
        SYNTAX	INTEGER(253..2147483647)
        ACCESS	read-write
        STATUS	mandatory
        DESCRIPTION
                "The number of entries in the RIF hash table"
        DEFVAL	{ 253 }
        ::= { wfBrSr 20 }

    wfBrSrBaseNbRifCacheHits OBJECT-TYPE
        SYNTAX	Counter
        ACCESS	read-only
        STATUS	mandatory
        DESCRIPTION
                "The number of times the NetBIOS rif cache has been used"
        ::= { wfBrSr 21 }

    wfBrSrBaseNbRifCacheMisses OBJECT-TYPE
        SYNTAX	Counter
        ACCESS	read-only
        STATUS	mandatory
        DESCRIPTION
                "The number of failed lookups on the NetBIOS rif cache"
        ::= { wfBrSr 22 }

    wfBrSrBaseNbRifDroppedFrames OBJECT-TYPE
        SYNTAX	Counter
        ACCESS	read-only
        STATUS	mandatory
        DESCRIPTION
                "The number of NB frames dropped because the rif stored in the rif cache
                indicated that this frame traveled a sub-optimal route"
        ::= { wfBrSr 23 }

    wfBrSrBaseNbQueryCacheDisable OBJECT-TYPE
        SYNTAX	INTEGER {
    		    enabled(1),
    		    disabled(2)
    		}
        ACCESS	read-write
        STATUS	mandatory
        DESCRIPTION
                "Enable/Disable parameter for the NetBIOS Query cache"
        DEFVAL	{ disabled }
        ::= { wfBrSr 24 }

    wfBrSrBaseNbQueryMibDisable OBJECT-TYPE
        SYNTAX	INTEGER {
    		    enabled(1),
    		    disabled(2)
    		}
        ACCESS	read-write
        STATUS	mandatory
        DESCRIPTION
                "Enable/Disable creation of MIB instances for each cached query"
        DEFVAL	{ enabled }
        ::= { wfBrSr 25 }

    wfBrSrBaseNbMaximumQueryEntries OBJECT-TYPE
        SYNTAX	INTEGER
        ACCESS	read-write
        STATUS	mandatory
        DESCRIPTION
                "The maximum number of entries allowed in the NetBIOS query cache"
        DEFVAL	{ 100 }
        ::= { wfBrSr 26 }

    wfBrSrBaseNbCurrentQueryEntries OBJECT-TYPE
        SYNTAX	INTEGER
        ACCESS	read-only
        STATUS	mandatory
        DESCRIPTION
                "The number of entries currently in the NetBIOS query cache"
        ::= { wfBrSr 27 }

    wfBrSrBaseNbQueryAgeTime OBJECT-TYPE
        SYNTAX	INTEGER
        ACCESS	read-write
        STATUS	mandatory
        DESCRIPTION
                "The age in seconds when NetBIOS queries will be aged out of the query cache"
        DEFVAL	{ 15 }
        ::= { wfBrSr 28 }

    wfBrSrBaseNbQueryFilteredFrames OBJECT-TYPE
        SYNTAX	Counter
        ACCESS	read-only
        STATUS	mandatory
        DESCRIPTION
                "The number of duplicate NetBIOS queries filtered"
        ::= { wfBrSr 29 }

    wfBrSrBaseStpEnable OBJECT-TYPE
        SYNTAX	INTEGER {
    		    enabled(1),
    		    disabled(2)
    		}
        ACCESS	read-write
        STATUS	mandatory
        DESCRIPTION
                "Spanning Tree Enable/Disable"
        DEFVAL	{ disabled }
        ::= { wfBrSr 30 }

    wfBrSrBaseStpState OBJECT-TYPE
        SYNTAX	INTEGER {
    		    up(1),
    		    down(2),
    		    init(3),
    		    notpresent(4)
    		}
        ACCESS	read-only
        STATUS	mandatory
        DESCRIPTION
                "Spanning Tree State"
        DEFVAL	{ down }
        ::= { wfBrSr 31 }

    wfBrSrBaseStpProtocolSpecification OBJECT-TYPE
        SYNTAX	INTEGER {
    		    unknown(1),
    		    declb100(2),
    		    ieee8021d(3)
    		}
        ACCESS	read-write
        STATUS	mandatory
        DESCRIPTION
                "The version of the Spanning Tree protocol being run"
        DEFVAL	{ ieee8021d }
        ::= { wfBrSr 32 }

    wfBrSrBaseStpBridgeID OBJECT-TYPE
        SYNTAX	OCTET STRING
        ACCESS	read-write
        STATUS	mandatory
        DESCRIPTION
                "The Spanning Tree Bridge ID assigned to this
                bridge. It is a 8-octet string. The first two
                octets make up the bridge priority, and the last
                six are the MAC address of this bridge, which
                is commonly the MAC address of the first port
                on the bridge."
        ::= { wfBrSr 33 }

    wfBrSrBaseStpTimeSinceTopologyChange OBJECT-TYPE
        SYNTAX	Counter
        ACCESS	read-only
        STATUS	mandatory
        DESCRIPTION
                "The time (in hundredths of a second) since the last
                topology change was detected by the bridge."
        ::= { wfBrSr 34 }

    wfBrSrBaseStpTopChanges OBJECT-TYPE
        SYNTAX	Counter
        ACCESS	read-only
        STATUS	mandatory
        DESCRIPTION
                "The total number of topology changes detected by
                this bridge since it was last reset or initialized"
        ::= { wfBrSr 35 }

    wfBrSrBaseStpDesignatedRoot OBJECT-TYPE
        SYNTAX	OCTET STRING
        ACCESS	read-only
        STATUS	mandatory
        DESCRIPTION
                "The bridge ID of the root of the Spanning Tree as
                determined by the Spanning Tree Protocol as
                executed by the bridge. This value is used as
                the Root Identifier parameter in all Configuration
                Bridge PDUs originated by this node. It is a 8-octet
                string. The first two octets make up the priority,
                and the last six are the MAC address of the designated
                root bridge."
        ::= { wfBrSr 36 }

    wfBrSrBaseStpRootCost OBJECT-TYPE
        SYNTAX	INTEGER
        ACCESS	read-only
        STATUS	mandatory
        DESCRIPTION
                "The cost of the path to the root as seen from this
                bridge."
        ::= { wfBrSr 37 }

    wfBrSrBaseStpRootPort OBJECT-TYPE
        SYNTAX	INTEGER
        ACCESS	read-only
        STATUS	mandatory
        DESCRIPTION
                "The port identifier of the port which offers the
                lowest cost path from this bridge to the root bridge."
        ::= { wfBrSr 38 }

    wfBrSrBaseStpMaxAge OBJECT-TYPE
        SYNTAX	INTEGER
        ACCESS	read-only
        STATUS	mandatory
        DESCRIPTION
                "The maximum age of the Spanning Tree Protocol
                information learned from the network on any port
                before it is discarded, in hundredths of a second.
                This represents the value actually in use by the
                bridge."
        ::= { wfBrSr 39 }

    wfBrSrBaseStpHelloTime OBJECT-TYPE
        SYNTAX	INTEGER
        ACCESS	read-only
        STATUS	mandatory
        DESCRIPTION
                "The amount of time between transmission of
                configuration BPDUs by this bridge on any port,
                when it is the root of the Spanning Tree or
                trying to become so, in hundreths of a second.
                This represents the value actually in use by the bridge."
        ::= { wfBrSr 40 }

    wfBrSrBaseStpHoldTime OBJECT-TYPE
        SYNTAX	INTEGER {
    		    time(100)
    		}
        ACCESS	read-only
        STATUS	mandatory
        DESCRIPTION
                "The value that determines the interval length during
                which no more than two configuration BPDUs shall be
                transmitted by this bridge, in hundredths of a second."
        DEFVAL	{ time }
        ::= { wfBrSr 41 }

    wfBrSrBaseStpForwardDelay OBJECT-TYPE
        SYNTAX	INTEGER
        ACCESS	read-only
        STATUS	mandatory
        DESCRIPTION
                "The time, in hundredths of a second, that a port
                on this bridge will stay in a transitional state
                (e.g. LISTENING) before moving to the next state
                (e.g. LEARNING). This value is also used to age
                all dynamic entries in the Forwarding Database
                when a topology changed has been detected and is
                underway. This represents the value actually in
                use by the bridge."
        ::= { wfBrSr 42 }

    wfBrSrBaseStpBridgeMaxAge OBJECT-TYPE
        SYNTAX	INTEGER(600..4000)
        ACCESS	read-write
        STATUS	mandatory
        DESCRIPTION
                "The value that all bridges use for MaxAge when
                this bridge acting as the root."
        DEFVAL	{ 2000 }
        ::= { wfBrSr 43 }

    wfBrSrBaseStpBridgeHelloTime OBJECT-TYPE
        SYNTAX	INTEGER(100..1000)
        ACCESS	read-write
        STATUS	mandatory
        DESCRIPTION
                "The value that all bridges use for HelloTime when
                this bridge acting as the root."
        DEFVAL	{ 200 }
        ::= { wfBrSr 44 }

    wfBrSrBaseStpBridgeForwardDelay OBJECT-TYPE
        SYNTAX	INTEGER(400..3000)
        ACCESS	read-write
        STATUS	mandatory
        DESCRIPTION
                "The value that all bridges use for Forward Delay when
                this bridge acting as the root."
        DEFVAL	{ 1500 }
        ::= { wfBrSr 45 }

    wfBrSrBaseNbNameQueryCacheDisable OBJECT-TYPE
        SYNTAX	INTEGER {
    		    enabled(1),
    		    disabled(2)
    		}
        ACCESS	read-write
        STATUS	mandatory
        DESCRIPTION
                "Enable/Disable parameter for the NetBIOS Name Query cache"
        DEFVAL	{ disabled }
        ::= { wfBrSr 46 }

    wfBrSrBaseAreHopCntLimit OBJECT-TYPE
        SYNTAX  INTEGER {
                    areonly(1),
                    areste(2)
                }
        ACCESS  read-write
        STATUS  mandatory
        DESCRIPTION
                "Based on hop count limit restrict AREs only(STEs still travel
                7 hops) or restrict both AREs and STEs."
        DEFVAL  { areonly }
        ::= { wfBrSr 47 }

    wfBrSrInterfaceTable OBJECT-TYPE
        SYNTAX	SEQUENCE OF WfBrSrInterfaceEntry
        ACCESS	not-accessible
        STATUS	mandatory
        DESCRIPTION
                "A table that contains information about every
                interface that is associated with this
                source routing bridge.
                inst_id[1] = wfBrSrInterfaceCircuit"
        ::= { wfBrSourceRouting 2 }

    wfBrSrInterfaceEntry OBJECT-TYPE
        SYNTAX	WfBrSrInterfaceEntry
        ACCESS	not-accessible
        STATUS	mandatory
        DESCRIPTION
                "An entry in wfBrSrInterface."
        INDEX	{ wfBrSrInterfaceCircuit }
        ::= { wfBrSrInterfaceTable 1 }

    WfBrSrInterfaceEntry ::= SEQUENCE {
    	    wfBrSrInterfaceDelete
    		INTEGER,
    	    wfBrSrInterfaceDisable
    		INTEGER,
    	    wfBrSrInterfaceState
    		INTEGER,
    	    wfBrSrInterfaceCircuit
    		INTEGER,
    	    wfBrSrInterfaceMaxRds
    		INTEGER,
    	    wfBrSrInterfaceRing
    		INTEGER,
    	    wfBrSrInterfaceBlockOutSte
    		INTEGER,
    	    wfBrSrInterfaceBlockInSte
    		INTEGER,
    	    wfBrSrInterfaceBlockIp
    		INTEGER,
    	    wfBrSrInterfaceIpAddress
    		IpAddress,
    	    wfBrSrInterfaceInFrames
    		Counter,
    	    wfBrSrInterfaceOutFrames
    		Counter,
    	    wfBrSrInterfaceOutIpFrames
    		Counter,
    	    wfBrSrInterfaceDropInvalidRcs
    		Counter,
    	    wfBrSrInterfaceDropInvalidRings
    		Counter,
    	    wfBrSrInterfaceDropSrfs
    		Counter,
    	    wfBrSrInterfaceNbServerRifCacheDisable
    		INTEGER,
    	    wfBrSrInterfaceNbClientRifCacheDisable
    		INTEGER,
    	    wfBrSrInterfaceNbDatagramRifCacheDisable
    		INTEGER,
    	    wfBrSrInterfaceNbQueryCacheDisable
    		INTEGER,
    	    wfBrSrInterfaceXbInFrames
    		Counter,
    	    wfBrSrInterfaceXbDropFrames
    		Counter,
    	    wfBrSrInterfaceFrBcastDlci
    		INTEGER,
    	    wfBrSrInterfaceEncapsFormat
    		INTEGER,
    	    wfBrSrInterfaceStpEnable
    		INTEGER,
    	    wfBrSrInterfaceStpState
    		INTEGER,
    	    wfBrSrInterfaceStpMultiCastAddr
    		OCTET STRING,
    	    wfBrSrInterfaceStpPathCost
    		INTEGER,
    	    wfBrSrInterfaceStpDesignatedRoot
    		OCTET STRING,
    	    wfBrSrInterfaceStpDesignatedCost
    		INTEGER,
    	    wfBrSrInterfaceStpDesignatedBridge
    		OCTET STRING,
    	    wfBrSrInterfaceStpDesignatedPort
    		INTEGER,
    	    wfBrSrInterfaceStpForwardTransitions
    		Counter,
    	    wfBrSrInterfaceStpPktsXmitd
    		Counter,
    	    wfBrSrInterfaceStpPktsRcvd
    		Counter,
    	    wfBrSrInterfaceStpTranslationDisable
    		INTEGER,
    	    wfBrSrInterfaceMaxLfField
    		INTEGER,
	    wfBrSrInterfaceFilterAddress
                INTEGER
        }

    wfBrSrInterfaceDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete an interface."
        DEFVAL	{ created }
        ::= { wfBrSrInterfaceEntry 1 }

    wfBrSrInterfaceDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an interface."
        DEFVAL	{ enabled }
        ::= { wfBrSrInterfaceEntry 2 }

    wfBrSrInterfaceState OBJECT-TYPE
        SYNTAX	INTEGER {
    		    up(1),
    		    down(2),
    		    init(3),
    		    notpresent(4)
    		}
        ACCESS	read-only
        STATUS	mandatory
        DESCRIPTION
                "The current state of the interface."
        DEFVAL	{ down }
        ::= { wfBrSrInterfaceEntry 3 }

    wfBrSrInterfaceCircuit OBJECT-TYPE
        SYNTAX	INTEGER
        ACCESS	read-only
        STATUS	mandatory
        DESCRIPTION
                "The circuit that this interface runs over."
        ::= { wfBrSrInterfaceEntry 4 }

    wfBrSrInterfaceMaxRds OBJECT-TYPE
        SYNTAX	INTEGER(1..7)
        ACCESS	read-write
        STATUS	mandatory
        DESCRIPTION
                "The maximum number of RDs permitted in incoming
                explorer frames"
        DEFVAL	{ 7 }
        ::= { wfBrSrInterfaceEntry 5 }

    wfBrSrInterfaceRing OBJECT-TYPE
        SYNTAX	INTEGER
        ACCESS	read-write
        STATUS	mandatory
        DESCRIPTION
                "The ring number of the source routing circuit.
                Even non-ring circuit need a ring number if
                it is to do source routing"
        ::= { wfBrSrInterfaceEntry 6 }

    wfBrSrInterfaceBlockOutSte OBJECT-TYPE
        SYNTAX	INTEGER {
    		    block(1),
    		    accept(2)
    		}
        ACCESS	read-write
        STATUS	mandatory
        DESCRIPTION
                "Enables blocking of outbound STEs"
        DEFVAL	{ accept }
        ::= { wfBrSrInterfaceEntry 7 }

    wfBrSrInterfaceBlockInSte OBJECT-TYPE
        SYNTAX	INTEGER {
    		    block(1),
    		    accept(2)
    		}
        ACCESS	read-write
        STATUS	mandatory
        DESCRIPTION
                "Enables blocking of inbound STEs"
        DEFVAL	{ accept }
        ::= { wfBrSrInterfaceEntry 8 }

    wfBrSrInterfaceBlockIp OBJECT-TYPE
        SYNTAX	INTEGER {
    		    block(1),
    		    accept(2)
    		}
        ACCESS	read-write
        STATUS	mandatory
        DESCRIPTION
                "Enables blocking of inbound explorers that have
                have already been through the IP network"
        DEFVAL	{ accept }
        ::= { wfBrSrInterfaceEntry 9 }

    wfBrSrInterfaceIpAddress OBJECT-TYPE
        SYNTAX	IpAddress
        ACCESS	read-write
        STATUS	mandatory
        DESCRIPTION
                "Ip address for this ring. This should match the
                the IP address in the IP MIB"
        ::= { wfBrSrInterfaceEntry 10 }

    wfBrSrInterfaceInFrames OBJECT-TYPE
        SYNTAX	Counter
        ACCESS	read-only
        STATUS	mandatory
        DESCRIPTION
                "The number of frames that have been received by
                this interface from its circuit."
        ::= { wfBrSrInterfaceEntry 11 }

    wfBrSrInterfaceOutFrames OBJECT-TYPE
        SYNTAX	Counter
        ACCESS	read-only
        STATUS	mandatory
        DESCRIPTION
                "The number of frames that have been transmitted
                by this interface"
        ::= { wfBrSrInterfaceEntry 12 }

    wfBrSrInterfaceOutIpFrames OBJECT-TYPE
        SYNTAX	Counter
        ACCESS	read-only
        STATUS	mandatory
        DESCRIPTION
                "The number of frames that have been transmitted
                by this interface to the IP network"
        ::= { wfBrSrInterfaceEntry 13 }

    wfBrSrInterfaceDropInvalidRcs OBJECT-TYPE
        SYNTAX	Counter
        ACCESS	read-only
        STATUS	mandatory
        DESCRIPTION
                "Count of frames received which were
                discarded because of a bad Route Control field"
        ::= { wfBrSrInterfaceEntry 14 }

    wfBrSrInterfaceDropInvalidRings OBJECT-TYPE
        SYNTAX	Counter
        ACCESS	read-only
        STATUS	mandatory
        DESCRIPTION
                "Count of frames received which were
                discarded because of a invalid incoming ring"
        ::= { wfBrSrInterfaceEntry 15 }

    wfBrSrInterfaceDropSrfs OBJECT-TYPE
        SYNTAX	Counter
        ACCESS	read-only
        STATUS	mandatory
        DESCRIPTION
                "Count of specifically routed frames received which were
                discarded due to filtering or no next circuit"
        ::= { wfBrSrInterfaceEntry 16 }

    wfBrSrInterfaceNbServerRifCacheDisable OBJECT-TYPE
        SYNTAX	INTEGER {
    		    enabled(1),
    		    disabled(2)
    		}
        ACCESS	read-write
        STATUS	mandatory
        DESCRIPTION
                "Enable/Disable parameter for the NetBIOS Server cache"
        DEFVAL	{ enabled }
        ::= { wfBrSrInterfaceEntry 17 }

    wfBrSrInterfaceNbClientRifCacheDisable OBJECT-TYPE
        SYNTAX	INTEGER {
    		    enabled(1),
    		    disabled(2)
    		}
        ACCESS	read-write
        STATUS	mandatory
        DESCRIPTION
                "Enable/Disable parameter for the NetBIOS Client cache"
        DEFVAL	{ enabled }
        ::= { wfBrSrInterfaceEntry 18 }

    wfBrSrInterfaceNbDatagramRifCacheDisable OBJECT-TYPE
        SYNTAX	INTEGER {
    		    enabled(1),
    		    disabled(2)
    		}
        ACCESS	read-write
        STATUS	mandatory
        DESCRIPTION
                "Enable/Disable parameter for the NetBIOS Datagram cache"
        DEFVAL	{ enabled }
        ::= { wfBrSrInterfaceEntry 19 }

    wfBrSrInterfaceNbQueryCacheDisable OBJECT-TYPE
        SYNTAX	INTEGER {
    		    enabled(1),
    		    disabled(2)
    		}
        ACCESS	read-write
        STATUS	mandatory
        DESCRIPTION
                "Enable/Disable parameter for the NetBIOS Query cache"
        DEFVAL	{ enabled }
        ::= { wfBrSrInterfaceEntry 20 }

    wfBrSrInterfaceXbInFrames OBJECT-TYPE
        SYNTAX	Counter
        ACCESS	read-only
        STATUS	mandatory
        DESCRIPTION
                "The number of frames that have been received
                by this interface"
        ::= { wfBrSrInterfaceEntry 21 }

    wfBrSrInterfaceXbDropFrames OBJECT-TYPE
        SYNTAX	Counter
        ACCESS	read-only
        STATUS	mandatory
        DESCRIPTION
                "The number of frames that were dropped because they
                were too large"
        ::= { wfBrSrInterfaceEntry 22 }

    wfBrSrInterfaceFrBcastDlci OBJECT-TYPE
        SYNTAX	INTEGER
        ACCESS	read-write
        STATUS	mandatory
        DESCRIPTION
                "The Frame Relay broadcast dlci"
        DEFVAL	{ 2147483647 }
        ::= { wfBrSrInterfaceEntry 23 }

    wfBrSrInterfaceEncapsFormat OBJECT-TYPE
        SYNTAX	INTEGER {
    		    proprietary(1),
    		    standard(2)
    		}
        ACCESS	read-write
        STATUS	mandatory
        DESCRIPTION
                "Non-Token Ring encapsulation format"
        DEFVAL	{ proprietary }
        ::= { wfBrSrInterfaceEntry 24 }

    wfBrSrInterfaceStpEnable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an interface
                for the Spanning Tree."
        DEFVAL	{ disabled }
        ::= { wfBrSrInterfaceEntry 25 }

    wfBrSrInterfaceStpState OBJECT-TYPE
        SYNTAX	INTEGER {
    		    disabled(1),
    		    blocking(2),
    		    listening(3),
    		    learning(4),
    		    forwarding(5),
    		    broken(6)
    		}
        ACCESS	read-only
        STATUS	mandatory
        DESCRIPTION
                "The current state of the port as defined by the
                application of the Spanning Tree Protocol."
        DEFVAL	{ disabled }
        ::= { wfBrSrInterfaceEntry 26 }

    wfBrSrInterfaceStpMultiCastAddr OBJECT-TYPE
        SYNTAX	OCTET STRING
        ACCESS	read-only
        STATUS	mandatory
        DESCRIPTION
                "The MAC address used as the destination for all
                BPDU packets generated out this port."
        ::= { wfBrSrInterfaceEntry 27 }

    wfBrSrInterfaceStpPathCost OBJECT-TYPE
        SYNTAX	INTEGER(1..65535)
        ACCESS	read-write
        STATUS	mandatory
        DESCRIPTION
                "The contribution of this port the root
                path cost of paths toward the Spanning Tree
                root which include this port."
        DEFVAL	{ 1 }
        ::= { wfBrSrInterfaceEntry 28 }

    wfBrSrInterfaceStpDesignatedRoot OBJECT-TYPE
        SYNTAX	OCTET STRING
        ACCESS	read-only
        STATUS	mandatory
        DESCRIPTION
                "The unique Bridge Identifier of the Bridge recorded
                as the Root in the Configuration BPDUs transmitted
                by the Designated Bridge for the segment to which this
                port is attached. Bridge IDs are made up of a
                2-byte priority field, and a 6-byte MAC address."
        ::= { wfBrSrInterfaceEntry 29 }

    wfBrSrInterfaceStpDesignatedCost OBJECT-TYPE
        SYNTAX	INTEGER
        ACCESS	read-only
        STATUS	mandatory
        DESCRIPTION
                "The path cost of the Designated Port of the
                segment connected to this port. This value
                is compared to the Root Path Cost field in
                received bridge PDUs."
        ::= { wfBrSrInterfaceEntry 30 }

    wfBrSrInterfaceStpDesignatedBridge OBJECT-TYPE
        SYNTAX	OCTET STRING
        ACCESS	read-only
        STATUS	mandatory
        DESCRIPTION
                "The Bridge Identifier of the bridge which this
                port considers to be the Designated Bridge for
                this port's segment."
        ::= { wfBrSrInterfaceEntry 31 }

    wfBrSrInterfaceStpDesignatedPort OBJECT-TYPE
        SYNTAX	INTEGER
        ACCESS	read-only
        STATUS	mandatory
        DESCRIPTION
                "The Port Identifier of the port on the Designated
                Bridge for this port's segment."
        ::= { wfBrSrInterfaceEntry 32 }

    wfBrSrInterfaceStpForwardTransitions OBJECT-TYPE
        SYNTAX	Counter
        ACCESS	read-only
        STATUS	mandatory
        DESCRIPTION
                "The number of times this port has transitioned
                from the Learning State to the Forwarding state."
        ::= { wfBrSrInterfaceEntry 33 }

    wfBrSrInterfaceStpPktsXmitd OBJECT-TYPE
        SYNTAX	Counter
        ACCESS	read-only
        STATUS	mandatory
        DESCRIPTION
                "The number of BPDU packets transmitted out this port"
        ::= { wfBrSrInterfaceEntry 34 }

    wfBrSrInterfaceStpPktsRcvd OBJECT-TYPE
        SYNTAX	Counter
        ACCESS	read-only
        STATUS	mandatory
        DESCRIPTION
                "The number of BPDU packets transmitted out this port"
        ::= { wfBrSrInterfaceEntry 35 }

    wfBrSrInterfaceStpTranslationDisable OBJECT-TYPE
        SYNTAX	INTEGER {
    		    enabled(1),
    		    disabled(2)
    		}
        ACCESS	read-write
        STATUS	mandatory
        DESCRIPTION
                "Enable/Disable translation bridging parameter. Default is disabled."
        DEFVAL	{ disabled }
        ::= { wfBrSrInterfaceEntry 36 }

    wfBrSrInterfaceMaxLfField OBJECT-TYPE
        SYNTAX	INTEGER {
    		    sr1500(1),
    		    sr2052(2),
    		    sr4472(3)
    		}
        ACCESS	read-write
        STATUS	mandatory
        DESCRIPTION
                "The maximum size of the Lf Field. This was added to restrict
                the packet size when using FDDI.

                  Note: The BR_SR_INTERFACE_SR4472 setting is for IBM use only.
                    This packet size is not normally supported on the FDDI.
                    The default setting is for IBM. This will need to be set
                    to 1 or 2 for all other vendors."
        DEFVAL	{ sr4472 }
        ::= { wfBrSrInterfaceEntry 37 }

    wfBrSrInterfaceFilterAddress OBJECT-TYPE
        SYNTAX  INTEGER {
                    groupaddress(1),
                    destinationaddress(2)
                 }
        ACCESS  read-write
        STATUS  mandatory
        DESCRIPTION
                "Selection of Filter Address type when filtering SRF's.
                 Filtering can be performed on the Wellfleet Group
                 Address or on the Destination Address in the frame."
        DEFVAL  { groupaddress }
        ::= { wfBrSrInterfaceEntry 38 }

    wfBrSrBridgeTable OBJECT-TYPE
        SYNTAX	SEQUENCE OF WfBrSrBridgeEntry
        ACCESS	not-accessible
        STATUS	mandatory
        DESCRIPTION
                "A table that contains the bridge numbers used
                by Wellfleet bridges in a source routing network
                inst_id[2] = wfBrSrBridgeId"
        ::= { wfBrSourceRouting 3 }

    wfBrSrBridgeEntry OBJECT-TYPE
        SYNTAX	WfBrSrBridgeEntry
        ACCESS	not-accessible
        STATUS	mandatory
        DESCRIPTION
                "An entry in wfBrSrBridge."
        INDEX	{ wfBrSrBridgeId }
        ::= { wfBrSrBridgeTable 1 }

    WfBrSrBridgeEntry ::= SEQUENCE {
    	    wfBrSrBridgeDelete
    		INTEGER,
    	    wfBrSrBridgeId
    		INTEGER
        }

    wfBrSrBridgeDelete OBJECT-TYPE
        SYNTAX	INTEGER {
    		    created(1),
    		    deleted(2)
    		}
        ACCESS	read-write
        STATUS	mandatory
        DESCRIPTION
                "Create/Delete parameter. Default is created.
                Users perform an SNMP SET operation on this object in
                order to create/delete an IP encapsulation peer record."
        DEFVAL	{ created }
        ::= { wfBrSrBridgeEntry 1 }

    wfBrSrBridgeId OBJECT-TYPE
        SYNTAX	INTEGER
        ACCESS	read-only
        STATUS	mandatory
        DESCRIPTION
                "The Bridge Id reserved for Wellfleet bridges"
        ::= { wfBrSrBridgeEntry 2 }

    wfBrSrIpExplorerTable OBJECT-TYPE
        SYNTAX	SEQUENCE OF WfBrSrIpExplorerEntry
        ACCESS	not-accessible
        STATUS	mandatory
        DESCRIPTION
                "A table that contains the table of IP addresses
                to which source routing explorers should be sent
                inst_id[2] = wfBrSrIpExplorerAddress"
        ::= { wfBrSourceRouting 4 }

    wfBrSrIpExplorerEntry OBJECT-TYPE
        SYNTAX	WfBrSrIpExplorerEntry
        ACCESS	not-accessible
        STATUS	mandatory
        DESCRIPTION
                "An entry in wfBrSrIpExplorer."
        INDEX	{ wfBrSrIpExplorerAddr }
        ::= { wfBrSrIpExplorerTable 1 }

    WfBrSrIpExplorerEntry ::= SEQUENCE {
    	    wfBrSrIpExplorerDelete
    		INTEGER,
    	    wfBrSrIpExplorerAddr
    		IpAddress,
            wfBrSrIpExplorerProtocol
                INTEGER
        }

    wfBrSrIpExplorerDelete OBJECT-TYPE
        SYNTAX	INTEGER {
    		    created(1),
    		    deleted(2)
    		}
        ACCESS	read-write
        STATUS	mandatory
        DESCRIPTION
                "Create/Delete parameter. Default is created.
                Users perform an SNMP SET operation on this object in
                order to create/delete an IP encapsulation peer record."
        DEFVAL	{ created }
        ::= { wfBrSrIpExplorerEntry 1 }

    wfBrSrIpExplorerAddr OBJECT-TYPE
        SYNTAX	IpAddress
        ACCESS	read-only
        STATUS	mandatory
        DESCRIPTION
                "The IP address of this encapsulation peer."
        ::= { wfBrSrIpExplorerEntry 2 }

    wfBrSrIpExplorerProtocol  OBJECT-TYPE
        SYNTAX  INTEGER
        ACCESS  read-write
        STATUS  obsolete
        DESCRIPTION
                "Which IP Encaps protocols to use, 0 = old, 1 = new.
                 The value 1 = new is no longer valid."
        ::= { wfBrSrIpExplorerEntry 3 }

    wfBrSrIpEncapsTable OBJECT-TYPE
        SYNTAX	SEQUENCE OF WfBrSrIpEncapsEntry
        ACCESS	not-accessible
        STATUS	obsolete
        DESCRIPTION
                "A table that contains information about IP
                Encapsulation ring-to-IP Address mappings.
                This information is used to make the 'next
                ring' IP Address decision.
                inst = wfBrSrIpEncapsRing"
        ::= { wfBrSourceRouting 5 }

    wfBrSrIpEncapsEntry OBJECT-TYPE
        SYNTAX	WfBrSrIpEncapsEntry
        ACCESS	not-accessible
        STATUS	obsolete
        DESCRIPTION
                "An entry in the wfBrSrIpEncapsTable."
        INDEX	{ wfBrSrIpEncapsRing }
        ::= { wfBrSrIpEncapsTable 1 }

    WfBrSrIpEncapsEntry ::= SEQUENCE {
    	    wfBrSrIpEncapsRing
    		INTEGER,
    	    wfBrSrIpEncapsIpAddress
    		IpAddress,
    	    wfBrSrIpEncapsStatus
    		INTEGER
        }

    wfBrSrIpEncapsRing OBJECT-TYPE
        SYNTAX	INTEGER
        ACCESS	read-only
        STATUS	obsolete
        DESCRIPTION
                "The remote ring number for which we have a ring to
                IP Address mapping."
        ::= { wfBrSrIpEncapsEntry 1 }

    wfBrSrIpEncapsIpAddress OBJECT-TYPE
        SYNTAX	IpAddress
        ACCESS	read-only
        STATUS	obsolete
        DESCRIPTION
                "The IP Address of the Wellfleet IP Encapsulation
                peer to which this ring is connected."
        ::= { wfBrSrIpEncapsEntry 2 }

    wfBrSrIpEncapsStatus OBJECT-TYPE
        SYNTAX	INTEGER {
    		    learned(3)
    		}
        ACCESS	read-only
        STATUS	obsolete
        DESCRIPTION
                "The status of this entry. The meanings of the
                values are:
                  learned(3) : the value of the corresponding
                              instance of wfBrSrIpEncapsRing was
                              learned, and is being used."
        DEFVAL	{ learned }
        ::= { wfBrSrIpEncapsEntry 3 }

    wfBrSrTrafficFilterTable OBJECT-TYPE
        SYNTAX	SEQUENCE OF WfBrSrTrafficFilterEntry
        ACCESS	not-accessible
        STATUS	mandatory
        DESCRIPTION
                "SR Bridge Traffic Filters"
        ::= { wfBrSourceRouting 6 }

    wfBrSrTrafficFilterEntry OBJECT-TYPE
        SYNTAX	WfBrSrTrafficFilterEntry
        ACCESS	not-accessible
        STATUS	mandatory
        DESCRIPTION
                "An entry in WfBrSrTrafficFilterTable."
        INDEX	{ wfBrSrTrafficFilterCircuit,
    		  wfBrSrTrafficFilterRuleNumber,
    		  wfBrSrTrafficFilterFragment }
        ::= { wfBrSrTrafficFilterTable 1 }

    WfBrSrTrafficFilterEntry ::= SEQUENCE {
    	    wfBrSrTrafficFilterCreate
    		INTEGER,
    	    wfBrSrTrafficFilterEnable
    		INTEGER,
    	    wfBrSrTrafficFilterStatus
    		INTEGER,
    	    wfBrSrTrafficFilterCounter
    		Counter,
    	    wfBrSrTrafficFilterDefinition
    		OCTET STRING,
    	    wfBrSrTrafficFilterReserved
    		INTEGER,
    	    wfBrSrTrafficFilterCircuit
    		INTEGER,
    	    wfBrSrTrafficFilterRuleNumber
    		INTEGER,
    	    wfBrSrTrafficFilterFragment
    		INTEGER,
    	    wfBrSrTrafficFilterName
    		DisplayString
        }

    wfBrSrTrafficFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfBrSrTrafficFilterEntry 1 }

    wfBrSrTrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfBrSrTrafficFilterEntry 2 }

    wfBrSrTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfBrSrTrafficFilterEntry 3 }

    wfBrSrTrafficFilterCounter OBJECT-TYPE
        SYNTAX	Counter
        ACCESS	read-only
        STATUS	mandatory
        DESCRIPTION
                "The number of received packets that have
                matched this rule."
        ::= { wfBrSrTrafficFilterEntry 4 }

    wfBrSrTrafficFilterDefinition OBJECT-TYPE
        SYNTAX	OCTET STRING
        ACCESS	read-write
        STATUS	mandatory
        DESCRIPTION
                "The filter rule definition."
        ::= { wfBrSrTrafficFilterEntry 5 }

    wfBrSrTrafficFilterReserved OBJECT-TYPE
        SYNTAX	INTEGER
        ACCESS	read-only
        STATUS	mandatory
        DESCRIPTION
                "Reserved field."
        ::= { wfBrSrTrafficFilterEntry 6 }

    wfBrSrTrafficFilterCircuit OBJECT-TYPE
        SYNTAX	INTEGER
        ACCESS	read-only
        STATUS	mandatory
        DESCRIPTION
                "The ID of the Bridge Circuit to which the
                filter is applied."
        ::= { wfBrSrTrafficFilterEntry 7 }

    wfBrSrTrafficFilterRuleNumber OBJECT-TYPE
        SYNTAX	INTEGER
        ACCESS	read-only
        STATUS	mandatory
        DESCRIPTION
                "ID for the rule."
        ::= { wfBrSrTrafficFilterEntry 8 }

    wfBrSrTrafficFilterFragment OBJECT-TYPE
        SYNTAX	INTEGER
        ACCESS	read-only
        STATUS	mandatory
        DESCRIPTION
                "Fragment number - for large rules."
        ::= { wfBrSrTrafficFilterEntry 9 }

    wfBrSrTrafficFilterName OBJECT-TYPE
        SYNTAX	DisplayString
        ACCESS	read-write
        STATUS	mandatory
        DESCRIPTION
                "name of the rule number"
        ::= { wfBrSrTrafficFilterEntry 10 }

    wfBrSrEsRifTable OBJECT-TYPE
        SYNTAX	SEQUENCE OF WfBrSrEsRifEntry
        ACCESS	not-accessible
        STATUS	mandatory
        DESCRIPTION
                "A table that contains the currently active
                RIFs in use by Router End Station Support
                inst_id[9] = wfBrSrIpExplorerAddress"
        ::= { wfBrSourceRouting 7 }

    wfBrSrEsRifEntry OBJECT-TYPE
        SYNTAX	WfBrSrEsRifEntry
        ACCESS	not-accessible
        STATUS	mandatory
        DESCRIPTION
                "An entry in wfBrSrEsRif."
        INDEX	{ wfBrSrEsRifCircuit,
    		  wfBrSrEsRifProtocol,
    		  wfBrSrEsRifMacAddr }
        ::= { wfBrSrEsRifTable 1 }

    WfBrSrEsRifEntry ::= SEQUENCE {
    	    wfBrSrEsRifCircuit
    		INTEGER,
    	    wfBrSrEsRifProtocol
    		OCTET STRING,
    	    wfBrSrEsRifMacAddr
    		OCTET STRING,
    	    wfBrSrEsRifRoute
    		OCTET STRING
        }

    wfBrSrEsRifCircuit OBJECT-TYPE
        SYNTAX	INTEGER
        ACCESS	read-only
        STATUS	mandatory
        DESCRIPTION
                "The circuit on which this entry was learned"
        ::= { wfBrSrEsRifEntry 1 }

    wfBrSrEsRifProtocol OBJECT-TYPE
        SYNTAX	OCTET STRING (SIZE (4))
        ACCESS	read-only
        STATUS	mandatory
        DESCRIPTION
                "The protocol in use at end station corresponding
                to this RIF.  If the protocol uses LLC encapsulation
                this field will contain the DSAP/SSAP pair.  If a
                SNAP encapsulation is used, it will contain the
                protocol type."
        ::= { wfBrSrEsRifEntry 2 }

    wfBrSrEsRifMacAddr OBJECT-TYPE
        SYNTAX	OCTET STRING (SIZE (4))
        ACCESS	read-only
        STATUS	mandatory
        DESCRIPTION
                "The Mac address of the end station corresponding
                to this RIF."
        ::= { wfBrSrEsRifEntry 3 }

    wfBrSrEsRifRoute OBJECT-TYPE
        SYNTAX	OCTET STRING
        ACCESS	read-only
        STATUS	mandatory
        DESCRIPTION
                "The route contained in the RIF field"
        ::= { wfBrSrEsRifEntry 4 }

    wfBrSrNbRifTable OBJECT-TYPE
        SYNTAX	SEQUENCE OF WfBrSrNbRifEntry
        ACCESS	not-accessible
        STATUS	mandatory
        DESCRIPTION
                "The NetBIOS server/client rif cache table"
        ::= { wfBrSourceRouting 8 }

    wfBrSrNbRifEntry OBJECT-TYPE
        SYNTAX	WfBrSrNbRifEntry
        ACCESS	not-accessible
        STATUS	mandatory
        DESCRIPTION
                "An entry in the NetBIOS rif cache table"
        INDEX	{ wfBrSrNbName }
        ::= { wfBrSrNbRifTable 1 }

    WfBrSrNbRifEntry ::= SEQUENCE {
    	    wfBrSrNbName
    		OCTET STRING,
    	    wfBrSrNbMacAddress
    		OCTET STRING,
    	    wfBrSrNbStatic
    		INTEGER,
    	    wfBrSrNbRif
    		OCTET STRING,
    	    wfBrSrNbRifCacheHits
    		Counter
        }

    wfBrSrNbName OBJECT-TYPE
        SYNTAX	OCTET STRING (SIZE (16))
        ACCESS	read-only
        STATUS	mandatory
        DESCRIPTION
                "The NetBIOS name of this station. It is a maximum of 16 characters.
                Names that are shorter are padded with ASCII spaces - 0x20"
        ::= { wfBrSrNbRifEntry 1 }

    wfBrSrNbMacAddress OBJECT-TYPE
        SYNTAX	OCTET STRING
        ACCESS	read-only
        STATUS	mandatory
        DESCRIPTION
                "The Mac Address of the NetBIOS station"
        ::= { wfBrSrNbRifEntry 2 }

    wfBrSrNbStatic OBJECT-TYPE
        SYNTAX	INTEGER {
    		    static(1),
    		    learned(2)
    		}
        ACCESS	read-only
        STATUS	mandatory
        DESCRIPTION
                "Indicates whether this entry is a static or learned entry"
        ::= { wfBrSrNbRifEntry 3 }

    wfBrSrNbRif OBJECT-TYPE
        SYNTAX	OCTET STRING
        ACCESS	read-only
        STATUS	mandatory
        DESCRIPTION
                "Cached RIF to get to this station"
        ::= { wfBrSrNbRifEntry 4 }

    wfBrSrNbRifCacheHits OBJECT-TYPE
        SYNTAX	Counter
        ACCESS	read-only
        STATUS	mandatory
        DESCRIPTION
                "The number of AREs that have been converted by this station"
        ::= { wfBrSrNbRifEntry 5 }

    wfBrSrNbQueryTable OBJECT-TYPE
        SYNTAX	SEQUENCE OF WfBrSrNbQueryEntry
        ACCESS	not-accessible
        STATUS	mandatory
        DESCRIPTION
                "The NetBIOS Query cache table"
        ::= { wfBrSourceRouting 9 }

    wfBrSrNbQueryEntry OBJECT-TYPE
        SYNTAX	WfBrSrNbQueryEntry
        ACCESS	not-accessible
        STATUS	mandatory
        DESCRIPTION
                "An entry in the NetBIOS Query cache table"
        INDEX	{ wfBrSrNbQueryMacAddress,
    		  wfBrSrNbRspCorrelator }
        ::= { wfBrSrNbQueryTable 1 }

    WfBrSrNbQueryEntry ::= SEQUENCE {
    	    wfBrSrNbQueryMacAddress
    		OCTET STRING,
    	    wfBrSrNbRspCorrelator
    		INTEGER,
    	    wfBrSrNbQuery
    		OCTET STRING,
    	    wfBrSrNbQueryFilteredFrames
    		Counter
        }

    wfBrSrNbQueryMacAddress OBJECT-TYPE
        SYNTAX	OCTET STRING (SIZE (6))
        ACCESS	read-only
        STATUS	mandatory
        DESCRIPTION
                "The MAC Address of the NetBIOS station"
        ::= { wfBrSrNbQueryEntry 1 }

    wfBrSrNbRspCorrelator OBJECT-TYPE
        SYNTAX	INTEGER
        ACCESS	read-only
        STATUS	mandatory
        DESCRIPTION
                "NetBIOS query sequence number"
        ::= { wfBrSrNbQueryEntry 2 }

    wfBrSrNbQuery OBJECT-TYPE
        SYNTAX	OCTET STRING
        ACCESS	read-only
        STATUS	mandatory
        DESCRIPTION
                "Cached NetBIOS query"
        ::= { wfBrSrNbQueryEntry 3 }

    wfBrSrNbQueryFilteredFrames OBJECT-TYPE
        SYNTAX	Counter
        ACCESS	read-only
        STATUS	mandatory
        DESCRIPTION
                "The number of identical Queries which have been filtered"
        ::= { wfBrSrNbQueryEntry 4 }

    wfBrSrNbStaticTable OBJECT-TYPE
        SYNTAX	SEQUENCE OF WfBrSrNbStaticEntry
        ACCESS	not-accessible
        STATUS	mandatory
        DESCRIPTION
                "The NetBIOS static server/client entry table"
        ::= { wfBrSourceRouting 10 }

    wfBrSrNbStaticEntry OBJECT-TYPE
        SYNTAX	WfBrSrNbStaticEntry
        ACCESS	not-accessible
        STATUS	mandatory
        DESCRIPTION
                "An entry in the NetBIOS static entry table"
        INDEX	{ wfBrSrNbStaticName }
        ::= { wfBrSrNbStaticTable 1 }

    WfBrSrNbStaticEntry ::= SEQUENCE {
    	    wfBrSrNbStaticDelete
    		INTEGER,
    	    wfBrSrNbStaticDisable
    		INTEGER,
    	    wfBrSrNbStaticState
    		INTEGER,
    	    wfBrSrNbStaticName
    		OCTET STRING,
    	    wfBrSrNbStaticMacAddress
    		OCTET STRING,
    	    wfBrSrNbStaticRif
    		OCTET STRING
        }

    wfBrSrNbStaticDelete OBJECT-TYPE
        SYNTAX	INTEGER {
    		    created(1),
    		    deleted(2)
    		}
        ACCESS	read-write
        STATUS	mandatory
        DESCRIPTION
                "Create/Delete parameter for the NetBIOS static entry"
        DEFVAL	{ created }
        ::= { wfBrSrNbStaticEntry 1 }

    wfBrSrNbStaticDisable OBJECT-TYPE
        SYNTAX	INTEGER {
    		    enabled(1),
    		    disabled(2)
    		}
        ACCESS	read-write
        STATUS	mandatory
        DESCRIPTION
                "Enable/Disable parameter for the NetBIOS static entry"
        DEFVAL	{ enabled }
        ::= { wfBrSrNbStaticEntry 2 }

    wfBrSrNbStaticState OBJECT-TYPE
        SYNTAX	INTEGER {
    		    valid(1),
    		    invalid(2)
    		}
        ACCESS	read-only
        STATUS	mandatory
        DESCRIPTION
                "The state of this NetBIOS static entry"
        DEFVAL	{ invalid }
        ::= { wfBrSrNbStaticEntry 3 }

    wfBrSrNbStaticName OBJECT-TYPE
        SYNTAX	OCTET STRING (SIZE (16))
        ACCESS	read-only
        STATUS	mandatory
        DESCRIPTION
                "The NetBIOS name of this station. It is a maximum of 16 characters.
                Names that are shorter are padded with ASCII spaces - 0x20"
        ::= { wfBrSrNbStaticEntry 4 }

    wfBrSrNbStaticMacAddress OBJECT-TYPE
        SYNTAX	OCTET STRING
        ACCESS	read-write
        STATUS	mandatory
        DESCRIPTION
                "The Mac Address of the NetBIOS station"
        ::= { wfBrSrNbStaticEntry 5 }

    wfBrSrNbStaticRif OBJECT-TYPE
        SYNTAX	OCTET STRING
        ACCESS	read-write
        STATUS	mandatory
        DESCRIPTION
                "The RIF to get to this station"
        ::= { wfBrSrNbStaticEntry 6 }

    wfBrXb		OBJECT IDENTIFIER ::= { wfBrSourceRouting 11 }

    wfBrXbBaseDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the bridge."
        DEFVAL	{ created }
        ::= { wfBrXb 1 }

    wfBrXbBaseDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable the bridge."
        DEFVAL	{ enabled }
        ::= { wfBrXb 2 }

    wfBrXbBaseEthernetLanId OBJECT-TYPE
        SYNTAX	INTEGER(1..4095)
        ACCESS	read-write
        STATUS	mandatory
        DESCRIPTION
                "Ethernet pseudo 'Ring' number"
        ::= { wfBrXb 3 }

    wfBrXbBaseMaxRifEntries OBJECT-TYPE
        SYNTAX	INTEGER
        ACCESS	read-write
        STATUS	mandatory
        DESCRIPTION
                "Maximum number of entries in the token-ring station address/RIF database"
        DEFVAL	{ 255 }
        ::= { wfBrXb 4 }

    wfBrXbBaseCurrentRifEntries OBJECT-TYPE
        SYNTAX	INTEGER
        ACCESS	read-only
        STATUS	mandatory
        DESCRIPTION
                "Current number of entries in the token-ring station address/RIF database"
        ::= { wfBrXb 5 }

    wfBrXbBaseAgeTime OBJECT-TYPE
        SYNTAX	INTEGER
        ACCESS	read-write
        STATUS	mandatory
        DESCRIPTION
                "Aging values for token-ring and Ethernet/802.3 MAC address databases"
        DEFVAL	{ 300 }
        ::= { wfBrXb 6 }

    wfBrXbBaseBcastAddressConversionDisable OBJECT-TYPE
        SYNTAX	INTEGER {
    		    enabled(1),
    		    disabled(2)
    		}
        ACCESS	read-write
        STATUS	mandatory
        DESCRIPTION
                "Enable/disable conversion from Ethernet Broadcast address to Token-ring
                broadcast address"
        DEFVAL	{ enabled }
        ::= { wfBrXb 7 }

    wfBrXbBaseDefaultMode OBJECT-TYPE
        SYNTAX	INTEGER {
    		    ethernet(1),
    		    ieee8023(2)
    		}
        ACCESS	read-write
        STATUS	mandatory
        DESCRIPTION
                "default mode indicates whether nodes should be assumed to be Ethernet version 2 or 802.3 nodes,
                if no other information is available. This parameter applies to Ethernet/802.3 interfaces only."
        DEFVAL	{ ethernet }
        ::= { wfBrXb 8 }

    wfBrXbBaseBcastMode OBJECT-TYPE
        SYNTAX	INTEGER {
    		    are(1),
    		    ste(2)
    		}
        ACCESS	read-write
        STATUS	mandatory
        DESCRIPTION
                "this parameter governs whether frames to be broadcast on the token-ring interface (because the destination address was not recognized) should go out as All-routes-explorers or as Spanning-tree-explorers. This parameter applies to token-ring interfaces only."
        DEFVAL	{ ste }
        ::= { wfBrXb 9 }

    wfBrXbBaseSaps OBJECT-TYPE
        SYNTAX	OCTET STRING
        ACCESS	read-write
        STATUS	mandatory
        DESCRIPTION
                "this parameter is the list of SAPS to bridge"
        ::= { wfBrXb 10 }

    wfBrXbFddiBridge OBJECT-TYPE
	SYNTAX  INTEGER {
		    enabled(1),
		    disabled(2)
		}
	ACCESS  read-write
	STATUS  mandatory
	DESCRIPTION
	         "Enable/disable larger size packets (FDDI and TokenRing) to
	         pass through the bridge if no ethernet or sync ports are
	         configured for XB."
	DEFVAL  { disabled }
	::= { wfBrXb 11 }

    wfBrXbAddressMapTable OBJECT-TYPE
        SYNTAX	SEQUENCE OF WfBrXbAddressMapEntry
        ACCESS	not-accessible
        STATUS	mandatory
        DESCRIPTION
                "users may configure specific Functional<->Multicast address conversions
                or specific MAC address conversions to be performed. This table keeps
                these mappings (on a per-system basis)."
        ::= { wfBrSourceRouting 12 }

    wfBrXbAddressMapEntry OBJECT-TYPE
        SYNTAX	WfBrXbAddressMapEntry
        ACCESS	not-accessible
        STATUS	mandatory
        DESCRIPTION
                "An entry in the MAC address mapping table"
        INDEX	{ wfBrXbAddressMapEthernetAddress }
        ::= { wfBrXbAddressMapTable 1 }

    WfBrXbAddressMapEntry ::= SEQUENCE {
    	    wfBrXbAddressMapDelete
    		INTEGER,
    	    wfBrXbAddressMapEthernetAddress
    		OCTET STRING,
    	    wfBrXbAddressMapTokenRingAddress
    		OCTET STRING
        }

    wfBrXbAddressMapDelete OBJECT-TYPE
        SYNTAX	INTEGER {
    		    created(1),
    		    deleted(2)
    		}
        ACCESS	read-write
        STATUS	mandatory
        DESCRIPTION
                "Create/Delete parameter for the station type static entry"
        DEFVAL	{ created }
        ::= { wfBrXbAddressMapEntry 1 }

    wfBrXbAddressMapEthernetAddress OBJECT-TYPE
        SYNTAX	OCTET STRING (SIZE (6))
        ACCESS	read-only
        STATUS	mandatory
        DESCRIPTION
                "The ethernet MAC Address of the station"
        ::= { wfBrXbAddressMapEntry 2 }

    wfBrXbAddressMapTokenRingAddress OBJECT-TYPE
        SYNTAX	OCTET STRING
        ACCESS	read-write
        STATUS	mandatory
        DESCRIPTION
                "The token-ring MAC Address of the station"
        ::= { wfBrXbAddressMapEntry 3 }

    wfBrXbRifTable OBJECT-TYPE
        SYNTAX	SEQUENCE OF WfBrXbRifEntry
        ACCESS	not-accessible
        STATUS	mandatory
        DESCRIPTION
                "The token-ring RIF cache table"
        ::= { wfBrSourceRouting 13 }

    wfBrXbRifEntry OBJECT-TYPE
        SYNTAX	WfBrXbRifEntry
        ACCESS	not-accessible
        STATUS	mandatory
        DESCRIPTION
                "An entry in the token-ring RIF cache table"
        INDEX	{ wfBrXbRifMacAddress }
        ::= { wfBrXbRifTable 1 }

    WfBrXbRifEntry ::= SEQUENCE {
    	    wfBrXbRifMacAddress
    		OCTET STRING,
    	    wfBrXbRifField
    		OCTET STRING
        }

    wfBrXbRifMacAddress OBJECT-TYPE
        SYNTAX	OCTET STRING (SIZE (6))
        ACCESS	read-only
        STATUS	mandatory
        DESCRIPTION
                "The Mac Address of the token-ring station"
        ::= { wfBrXbRifEntry 1 }

    wfBrXbRifField OBJECT-TYPE
        SYNTAX	OCTET STRING
        ACCESS	read-only
        STATUS	mandatory
        DESCRIPTION
                "The RIF to get to this station"
        ::= { wfBrXbRifEntry 2 }

    wfBrXbStationTypeTable OBJECT-TYPE
        SYNTAX	SEQUENCE OF WfBrXbStationTypeEntry
        ACCESS	not-accessible
        STATUS	mandatory
        DESCRIPTION
                "The station type (Ethernet or 802.3) static entry table"
        ::= { wfBrSourceRouting 14 }

    wfBrXbStationTypeEntry OBJECT-TYPE
        SYNTAX	WfBrXbStationTypeEntry
        ACCESS	not-accessible
        STATUS	mandatory
        DESCRIPTION
                "An entry in the station type static entry table"
        INDEX	{ wfBrXbStationTypeEthernetAddress }
        ::= { wfBrXbStationTypeTable 1 }

    WfBrXbStationTypeEntry ::= SEQUENCE {
    	    wfBrXbStationTypeDelete
    		INTEGER,
    	    wfBrXbStationTypeEthernetAddress
    		OCTET STRING,
    	    wfBrXbStationTypeIndicator
    		INTEGER
        }

    wfBrXbStationTypeDelete OBJECT-TYPE
        SYNTAX	INTEGER {
    		    created(1),
    		    deleted(2)
    		}
        ACCESS	read-write
        STATUS	mandatory
        DESCRIPTION
                "Create/Delete parameter for the station type static entry"
        DEFVAL	{ created }
        ::= { wfBrXbStationTypeEntry 1 }

    wfBrXbStationTypeEthernetAddress OBJECT-TYPE
        SYNTAX	OCTET STRING (SIZE (6))
        ACCESS	read-only
        STATUS	mandatory
        DESCRIPTION
                "The Mac Address of the station"
        ::= { wfBrXbStationTypeEntry 2 }

    wfBrXbStationTypeIndicator OBJECT-TYPE
        SYNTAX	INTEGER {
    		    ethernet(1),
    		    ieee8023(2)
    		}
        ACCESS	read-write
        STATUS	mandatory
        DESCRIPTION
                "The station type (Ethernet or 802.3)"
        ::= { wfBrXbStationTypeEntry 3 }

    wfBrSrIpEncapsRBTable OBJECT-TYPE
        SYNTAX	SEQUENCE OF WfBrSrIpEncapsRBEntry
        ACCESS	not-accessible
        STATUS	mandatory
        DESCRIPTION
                "A table that contains information about IP
                Encapsulation ring/bridge-to-IP Address mappings.
                This information is used to make the 'next
                ring/bridge' IP Address decision.
                inst = wfBrSrIpEncapsRing.wfBrSrIpEncapsBridge"
        ::= { wfBrSourceRouting 15 }

    wfBrSrIpEncapsRBEntry OBJECT-TYPE
        SYNTAX	WfBrSrIpEncapsRBEntry
        ACCESS	not-accessible
        STATUS	mandatory
        DESCRIPTION
                "An entry in the wfBrSrIpEncapsRBTable."
        INDEX	{ wfBrSrIpEncapsRBRing,
    		  wfBrSrIpEncapsRBBridge }
        ::= { wfBrSrIpEncapsRBTable 1 }

    WfBrSrIpEncapsRBEntry ::= SEQUENCE {
    	    wfBrSrIpEncapsRBRing
    		INTEGER,
    	    wfBrSrIpEncapsRBBridge
    		INTEGER,
    	    wfBrSrIpEncapsRBIpAddress
    		IpAddress,
    	    wfBrSrIpEncapsRBStatus
    		INTEGER
        }

    wfBrSrIpEncapsRBRing OBJECT-TYPE
        SYNTAX	INTEGER
        ACCESS	read-only
        STATUS	mandatory
        DESCRIPTION
                "The remote ring number for which we have a ring-bridge to
                IP Address mapping."
        ::= { wfBrSrIpEncapsRBEntry 1 }

    wfBrSrIpEncapsRBBridge OBJECT-TYPE
        SYNTAX	INTEGER
        ACCESS	read-only
        STATUS	mandatory
        DESCRIPTION
                "The Bridge ID for which we have a ring-bridge to
                IP Address mapping."
        ::= { wfBrSrIpEncapsRBEntry 2 }

    wfBrSrIpEncapsRBIpAddress OBJECT-TYPE
        SYNTAX	IpAddress
        ACCESS	read-only
        STATUS	mandatory
        DESCRIPTION
                "The IP Address of the Wellfleet IP Encapsulation
                peer to which this ring-bridge is connected."
        ::= { wfBrSrIpEncapsRBEntry 3 }

    wfBrSrIpEncapsRBStatus OBJECT-TYPE
        SYNTAX	INTEGER {
    		    learned(3)
    		}
        ACCESS	read-only
        STATUS	mandatory
        DESCRIPTION
                "The status of this entry. The meanings of the
                values are:
                  learned(3) : the value of the corresponding
                              instance of wfBrSrIpEncapsRing and
                              wfBrSrIpEncapsBridge was
                              learned, and is being used."
        DEFVAL	{ learned }
        ::= { wfBrSrIpEncapsRBEntry 4 }

    END  -- Wellfleet-SR-MIB
