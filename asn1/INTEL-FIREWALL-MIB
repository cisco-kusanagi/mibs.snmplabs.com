INTEL-FIREWALL-MIB DEFINITIONS ::= BEGIN

-- Copyright (C) 1997 Intel Corporation. All rights reserved.
--
-- firewall MIB, 1998-11-30
--
-- Proprietary MIB containing information about the Firewall System.
--
-- Change History:
-- 1998-11-30 Initial version
--

IMPORTS
    Counter FROM RFC1155-SMI
	 mib2ext                    FROM INTEL-GEN-MIB
    OBJECT-TYPE                FROM RFC-1212
	 IpAddress FROM RFC1155-SMI;

    firewall                OBJECT IDENTIFIER ::= { mib2ext 54 }
    firewallInfo            OBJECT IDENTIFIER ::= { firewall 1 }

firewallSessionTable OBJECT-TYPE
    SYNTAX SEQUENCE OF FirewallSessionEntry
    ACCESS not-accessible
    STATUS mandatory
    DESCRIPTION ""
    ::= { firewallInfo 1 }

firewallSessionEntry OBJECT-TYPE
    SYNTAX FirewallSessionEntry
    ACCESS not-accessible
    STATUS mandatory
    DESCRIPTION ""
    INDEX { firewallSessionIpIfIndex, firewallSessionDirection, firewallSessionNumber }
    ::= { firewallSessionTable 1 }

FirewallSessionEntry ::= SEQUENCE {
                        firewallSessionIpIfIndex
                           INTEGER,
                        firewallSessionDirection
                           INTEGER,
                        firewallSessionNumber
                           INTEGER,
                        firewallSessionSourceAddr
                           IpAddress,
                        firewallSessionSourcePortOrSeq
                           Counter,
                        firewallSessionDestAddr
                           IpAddress,
                        firewallSessionDestPortOrSeq
                           Counter,
                        firewallSessionProtocol
                           INTEGER,
                        firewallSessionState
                           INTEGER,
                        firewallSessionLastUpdate
                           INTEGER,
                        firewallSessionPacked1
                           OCTET STRING
                        }

firewallSessionIpIfIndex OBJECT-TYPE
    SYNTAX INTEGER
    ACCESS read-only
    STATUS mandatory
    DESCRIPTION ""
    ::= { firewallSessionEntry 1 }

firewallSessionDirection OBJECT-TYPE
    SYNTAX INTEGER {
              in(1),
              out(2)
             }
    ACCESS read-only
    STATUS mandatory
    DESCRIPTION ""
    ::= { firewallSessionEntry 2 }

firewallSessionNumber OBJECT-TYPE
    SYNTAX INTEGER
    ACCESS read-only
    STATUS mandatory
    DESCRIPTION ""
    ::= { firewallSessionEntry 3 }

firewallSessionSourceAddr OBJECT-TYPE
    SYNTAX IpAddress
    ACCESS read-only
    STATUS mandatory
    DESCRIPTION ""
    ::= { firewallSessionEntry 4 }

firewallSessionSourcePortOrSeq OBJECT-TYPE
    SYNTAX Counter
    ACCESS read-only
    STATUS mandatory
    DESCRIPTION ""
    ::= { firewallSessionEntry 5 }

firewallSessionDestAddr OBJECT-TYPE
    SYNTAX IpAddress
    ACCESS read-only
    STATUS mandatory
    DESCRIPTION ""
    ::= { firewallSessionEntry 6 }

firewallSessionDestPortOrSeq OBJECT-TYPE
    SYNTAX Counter
    ACCESS read-only
    STATUS mandatory
    DESCRIPTION ""
    ::= { firewallSessionEntry 7 }

firewallSessionProtocol OBJECT-TYPE
    SYNTAX INTEGER {
              icmp(1),
              tcp(6),
              udp(17)
             }
    ACCESS read-only
    STATUS mandatory
    DESCRIPTION ""
    ::= { firewallSessionEntry 8 }

firewallSessionState OBJECT-TYPE
    SYNTAX INTEGER {
	      established(1),
	      synreceived(2),
	      sendsyninsidewaitforacksyn(3),
	      finwaitone(4),
	      finwaittwo(5),
	      closewait(6),
	      terminated(7),
	      cantbeadded(8),
	      reused(9),
	      timedout(10),
	      denied(11),
	      portterminated(16)
             }
    ACCESS read-only
    STATUS mandatory
    DESCRIPTION ""
    ::= { firewallSessionEntry 9 }

firewallSessionLastUpdate OBJECT-TYPE
    SYNTAX INTEGER
    ACCESS read-only
    STATUS mandatory
    DESCRIPTION ""
    ::= { firewallSessionEntry 10 }

firewallSessionPacked1 OBJECT-TYPE
    SYNTAX OCTET STRING (SIZE(100))
    ACCESS read-only
    STATUS mandatory
    DESCRIPTION "SourceAddr 4
                 SourcePortOrSeq 4
                 DestAddr 4
                 DestPortOrSeq 4
                 Protocol 4
                 State 4
                 LastUpdate 4
                 (All numbers are stored in bigendian format)
                 "
    ::= { firewallSessionEntry 11 }

END
