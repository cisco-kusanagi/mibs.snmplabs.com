--
    --    OpenROUTE MIB
    --            This MIB defines the system-wide net management
    --            functionality available on Proteon devices.
    --
    --            Compatible with OpenROUTE s/w release V 2.1a and higher.
    --
    --    Version 3.2.0
    --
    --    Last Modified:
    --            August 5, 1998
    --
    --    Contact Information:
    --            Customer Service
    --            OpenROUTE Networks, Inc.
    --            9 Technology Drive
    --            Westborough, MA 01581
    --            
    --            phone:    508-898-3100
    --            email:    prohelp-cs@openroute.com
    --         web site:    http://www.openroute.com
    --

    
    OpenROUTE-MIB DEFINITIONS ::= BEGIN

    IMPORTS
        enterprises, Counter, TimeTicks, IpAddress 
                FROM RFC1155-SMI
        ifIndex, DisplayString        
                 FROM RFC1213-MIB
        OBJECT-TYPE     
                FROM RFC-1212
        TRAP-TYPE     
                FROM RFC-1215
			proElsTrapSeqs, proElsTrapSubSystem, proElsTrapEvent
				FROM PROTEON-MIB;


    proteon             OBJECT IDENTIFIER ::= { enterprises 1 }
    proAdmin            OBJECT IDENTIFIER ::= { proteon 1 }
    proSystem           OBJECT IDENTIFIER ::= { proteon 6 }

    -- Admin groups

    proSysObjId         OBJECT IDENTIFIER ::= { proAdmin 1 }
    proStatus           OBJECT IDENTIFIER ::= { proAdmin 2 }
    proPriv             OBJECT IDENTIFIER ::= { proAdmin 5 }

    -- System groups

    proResource         OBJECT IDENTIFIER ::= { proSystem 1 }
    proEls              OBJECT IDENTIFIER ::= { proSystem 2 }
    proTemp             OBJECT IDENTIFIER ::= { proSystem 3 }
    proConfig           OBJECT IDENTIFIER ::= { proSystem 4 }

    -- Resource groups

    proResMemory        OBJECT IDENTIFIER ::= { proResource 1 }
    proResBuffers       OBJECT IDENTIFIER ::= { proResource 2 }
    proResMemHeap       OBJECT IDENTIFIER ::= { proResMemory 1 }
    proResMemBuf        OBJECT IDENTIFIER ::= { proResMemory 2 }
    proResBufGlobal     OBJECT IDENTIFIER ::= { proResBuffers 1 }

    -- ELS trap objects

    -- The following objects were used when generating an elsTrap
    -- in the old format.  These are obsolete: proSysObjId 1, 2, and 3  
    -- 

    proElsTrapVar1        OBJECT IDENTIFIER ::= { proSysObjId 5 }
    proElsTrapVar2        OBJECT IDENTIFIER ::= { proSysObjId 6 }
    proElsTrapVar3        OBJECT IDENTIFIER ::= { proSysObjId 7 }
    proElsTrapVar4        OBJECT IDENTIFIER ::= { proSysObjId 8 }
    proElsTrapVar5        OBJECT IDENTIFIER ::= { proSysObjId 9 }
    proElsTrapVar6        OBJECT IDENTIFIER ::= { proSysObjId 10 }
    proElsTrapVar7        OBJECT IDENTIFIER ::= { proSysObjId 11 }
    proElsTrapVar8        OBJECT IDENTIFIER ::= { proSysObjId 12 }
    proElsTrapVar9        OBJECT IDENTIFIER ::= { proSysObjId 13 }


    -- ELS groups

    proElsGeneric       OBJECT IDENTIFIER ::= { proEls 1 }


    -- Textual conventions
    -- 
    -- Each ELS log message is classified by a log-level. This allows 
    -- the user to configure logging of a class of messages. The
    -- following are the possible values for the log levels.

    ProElsMsgLogLevel ::= INTEGER {
        other(1),
        proMsgLevelUIError(2),
        proMsgLevelCIError(3),
        proMsgLevelUEError(4),
        proMsgLevelCEError(5),
        proMsgLevelError(6),
        proMsgLevelUInfo(7),
        proMsgLevelCInfo(8),
        proMsgLevelInfo(9),
        proMsgLevelPTrace(10),
        proMsgLevelUTrace(11),
        proMsgLevelCTrace(12),
        proMsgLevelTrace(13),
        proMsgLevelAlways(14),
        proMsgLevelStandard(15),                    -- default
        proMsgLevelAll(16)
    }

    --
    -- The following values are used to indicate if logging is disabled
    -- or enabled for a particular subsystem or an event.

    ProElsLogStatus ::= INTEGER {
        proElsLogDisabled(1),
        proElsLogEnabled(2)
    }

    --
    -- sysObjectID values
    --
    -- The following are the sysObjectID values for the various 
    -- devices.

    proSysObjIdP4100         OBJECT IDENTIFIER ::= { proSysObjId 41 }
    proSysObjIdP4200         OBJECT IDENTIFIER ::= { proSysObjId 42 }
    proSysObjIdDNX300        OBJECT IDENTIFIER ::= { proSysObjId 43 }
    proSysObjIdCNX400        OBJECT IDENTIFIER ::= { proSysObjId 44 }
    proSysObjIdCNX600        OBJECT IDENTIFIER ::= { proSysObjId 46 }
    proSysObjIdRBX200        OBJECT IDENTIFIER ::= { proSysObjId 47 }
    proSysObjIdCNX500        OBJECT IDENTIFIER ::= { proSysObjId 49 }
    proSysObjIdRBX250        OBJECT IDENTIFIER ::= { proSysObjId 50 }        
    proSysObjIdBOSS3Slot     OBJECT IDENTIFIER ::= { proSysObjId 53 }
    proSysObjIdBOSSs90       OBJECT IDENTIFIER ::= { proSysObjId 54 }
    proSysObjIdGT60          OBJECT IDENTIFIER ::= { proSysObjId 55 }
    proSysObjIdGT62          OBJECT IDENTIFIER ::= { proSysObjId 56 }
    proSysObjIdGT100         OBJECT IDENTIFIER ::= { proSysObjId 57 }
    proSysObjIdGTAM          OBJECT IDENTIFIER ::= { proSysObjId 58 }
    proSysObjIdGT70          OBJECT IDENTIFIER ::= { proSysObjId 59 }
    proSysObjIdGT72          OBJECT IDENTIFIER ::= { proSysObjId 60 }
    proSysObjIdGT60-SEC      OBJECT IDENTIFIER ::= { proSysObjId 61 }
    proSysObjIdGT70-SEC      OBJECT IDENTIFIER ::= { proSysObjId 62 }
    proSysObjIdGT65          OBJECT IDENTIFIER ::= { proSysObjId 63 }
    proSysObjIdGT75          OBJECT IDENTIFIER ::= { proSysObjId 64 }
    proSysObjIdCSX900ER      OBJECT IDENTIFIER ::= { proSysObjId 65 }
    proSysObjIdGTX-1000      OBJECT IDENTIFIER ::= { proSysObjId 66 }
    proSysObjIdDRAGON        OBJECT IDENTIFIER ::= { proSysObjId 67 }
    proSysObjIdDRAGONPRO     OBJECT IDENTIFIER ::= { proSysObjId 68 }
    proSysObjIdGTE2          OBJECT IDENTIFIER ::= { proSysObjId 69 }
    proSysObjIdGT50          OBJECT IDENTIFIER ::= { proSysObjId 70 }


    --
    -- Reset action object
    --

    proActionReset OBJECT-TYPE
        SYNTAX  INTEGER
        ACCESS  read-write
        STATUS  mandatory
        DESCRIPTION
            "This object, when read, returns a value of zero.
            A set of this object causes the router to be reset. The
            value represents the delay (in seconds) before the reset
            will take affect." 
        ::= { proPriv 2 }

    --
    -- SYSLOG Server object
    --

    proSyslogServer OBJECT-TYPE
        SYNTAX  IpAddress
        ACCESS  read-write
        STATUS  mandatory
        DESCRIPTION
            "The IP Address of the SYSLOG server to which all router
	    SYSLOG messages (to UDP port 514) are transmitted."
        ::= { proPriv 5 }

    --
    -- Status group
    --
    -- This group provides general status info on the device.

    proStatusReloadTime OBJECT-TYPE
        SYNTAX  TimeTicks
        ACCESS  read-only
        STATUS  mandatory
        DESCRIPTION
            "The time (in hundredths of a second) since the last
            time the router software was reloaded."
        ::= { proStatus 1 }

    proStatusStarts OBJECT-TYPE
        SYNTAX  Counter
        ACCESS  read-only
        STATUS  mandatory
        DESCRIPTION
            "The number of times the router has started since
            the last reload."
        ::= { proStatus 2 }

    proStatusCrashes OBJECT-TYPE
        SYNTAX  Counter
        ACCESS  read-only
        STATUS  mandatory
        DESCRIPTION
            "The number of times the router has crashed since
            the last reload. Only those crashes that caused
            the router to deliberately restart due to a
            software error are counted by this object."
            ::= { proStatus 3 }

    proStatusCrashMsg OBJECT-TYPE
        SYNTAX  DisplayString
        ACCESS  read-only
        STATUS  mandatory
        DESCRIPTION
            "The last crash message. The message will indicate
            if the router has not crashed since the last reload."
        ::= { proStatus 4 }

    --
    -- Resource group
    --

    -- Memory group (Heap)
    --
    -- Heap memory is the memory used to dynamically allocate 
    -- data structures.
    -- This group provides heap memory statistics.

    proResMemHeapTotal OBJECT-TYPE
        SYNTAX  INTEGER
        ACCESS  read-only
        STATUS  mandatory
        DESCRIPTION
            "The total number of bytes of heap memory available
            for allocation."
        ::= { proResMemHeap 1 }

    proResMemHeapReserve OBJECT-TYPE
        SYNTAX  INTEGER
        ACCESS  read-only
        STATUS  mandatory
        DESCRIPTION
            "The minimum amount of memory needed by the currently
            configured protocols and features."
        ::= { proResMemHeap 2 }

    proResMemHeapNeverAlloc OBJECT-TYPE
        SYNTAX  INTEGER
        ACCESS  read-only
        STATUS  mandatory
        DESCRIPTION
             "The memory that has never been allocated."
        ::= { proResMemHeap 3 }

    proResMemHeapPermAlloc OBJECT-TYPE
        SYNTAX  INTEGER
        ACCESS  read-only
        STATUS  mandatory
        DESCRIPTION
            "The memory that is permanently allocated to router tasks."
        ::= { proResMemHeap 4 }

    proResMemHeapTempAlloc OBJECT-TYPE
        SYNTAX  INTEGER
        ACCESS  read-only
        STATUS  mandatory
        DESCRIPTION
            "The memory that is temporarily allocated to router tasks."
         ::= { proResMemHeap 5 }

    proResMemHeapPrevAlloc OBJECT-TYPE
        SYNTAX  INTEGER
        ACCESS  read-only
        STATUS  mandatory
        DESCRIPTION
            "The memory that was temporarily allocated and returned to
            the free pool."
        ::= { proResMemHeap 6 }


    -- Memory group (Buffer)
    --
    -- Buffer memory is the memory used to dynamically allocate 
    -- data buffers.
    -- This group provides buffer memory statistics.

    proResMemBufTotal OBJECT-TYPE
        SYNTAX  INTEGER
        ACCESS  read-only
        STATUS  mandatory
        DESCRIPTION
            "The total number of bytes of buffer memory available
            for allocation."
        ::= { proResMemBuf 1 }

    proResMemBufReserve OBJECT-TYPE
        SYNTAX  INTEGER
        ACCESS  read-only
        STATUS  mandatory
        DESCRIPTION
            "The minimum amount of memory needed by the currently
             configured protocols and features."
        ::= { proResMemBuf 2 }

    proResMemBufNeverAlloc OBJECT-TYPE
        SYNTAX  INTEGER
        ACCESS  read-only
        STATUS  mandatory
        DESCRIPTION
             "The memory that has never been allocated."
        ::= { proResMemBuf 3 }

    proResMemBufPermAlloc OBJECT-TYPE
        SYNTAX  INTEGER
        ACCESS  read-only
        STATUS  mandatory
        DESCRIPTION
            "The memory that is permanently allocated to router tasks."
        ::= { proResMemBuf 4 }


    -- Buffer group (Global)
    --
    -- This group provides statistics on global buffers available
    -- in the configured system.

    proResBufGlobalTotal OBJECT-TYPE
        SYNTAX  INTEGER
        ACCESS  read-only
        STATUS  mandatory
        DESCRIPTION
            "The total number of global buffers in the system."
        ::= { proResBufGlobal 1 }

    proResBufGlobalFree OBJECT-TYPE
        SYNTAX  INTEGER
        ACCESS  read-only
        STATUS  mandatory
        DESCRIPTION
            "The total number of free buffers in the system."
        ::= { proResBufGlobal 2 }

    proResBufGlobalFair OBJECT-TYPE
        SYNTAX  INTEGER
        ACCESS  read-only
        STATUS  mandatory
        DESCRIPTION
            "The 'fair' number of buffers for each interface."
        ::= { proResBufGlobal 3 }

    proResBufGlobalLow OBJECT-TYPE
        SYNTAX  INTEGER
        ACCESS  read-only
        STATUS  mandatory
        DESCRIPTION
            "The low mark for free buffers. If the value of 
            proResBufGlobalFree is less than this object then freed
            buffers will not be placed on any queue that has more than
            the 'fair' number of buffers on it."
        ::= { proResBufGlobal 4 }


    -- Buffer Table
    --
    -- This group provides statistics on packet buffers assigned
    -- to each interface.

    proResBufTable OBJECT-TYPE
        SYNTAX  SEQUENCE OF ProResBufTableEntry
        ACCESS  not-accessible
        STATUS  mandatory
        DESCRIPTION
            "The per-port buffer table."
        ::= { proResBuffers 2 }

    proResBufTableEntry OBJECT-TYPE
        SYNTAX  ProResBufTableEntry
        ACCESS  not-accessible
        STATUS  mandatory
        DESCRIPTION
            "An entry indicating the buffers allocated per interface."
        INDEX   { ifIndex }
        ::= { proResBufTable 1 }

    ProResBufTableEntry ::= 
        SEQUENCE {
            proResInputBufsReq
                INTEGER,
            proResInputBufsAlloc
                INTEGER,
            proResInputBufsLow
                INTEGER,
            proResInputBufsCurrent
                INTEGER,
            proResInputBufsSize
                INTEGER,
            proResInputBufsTotalBytes
                INTEGER
        }

    proResInputBufsReq OBJECT-TYPE
        SYNTAX  INTEGER
        ACCESS  read-only
        STATUS  mandatory
        DESCRIPTION
            "The number of buffers requested for this interface."
        ::= { proResBufTableEntry 1 }

    proResInputBufsAlloc OBJECT-TYPE
        SYNTAX  INTEGER
        ACCESS  read-only
        STATUS  mandatory
        DESCRIPTION
            "The number of buffers allocated for this interface."
        ::= { proResBufTableEntry 2 }

    proResInputBufsLow OBJECT-TYPE
        SYNTAX  INTEGER
        ACCESS  read-only
        STATUS  mandatory
        DESCRIPTION
            "The low water mark for number of buffers."
        ::= { proResBufTableEntry 3 }

    proResInputBufsCurrent OBJECT-TYPE
        SYNTAX  INTEGER
        ACCESS  read-only
        STATUS  mandatory
        DESCRIPTION
            "The current number of buffers for this device.
            A value of zero indicates that the device is disabled.
            If, on receipt of a packet, the value of this object
            is less than proResInputBufsLow than the packet is 
            eligible for flow control."
        ::= { proResBufTableEntry 4 }

    proResInputBufsSize OBJECT-TYPE
        SYNTAX  INTEGER
        ACCESS  read-only
        STATUS  mandatory
        DESCRIPTION
            "The size, in bytes, of each buffer allocated to this
            interface."
        ::= { proResBufTableEntry 5 }

    proResInputBufsTotalBytes OBJECT-TYPE
        SYNTAX  INTEGER
        ACCESS  read-only
        STATUS  mandatory
        DESCRIPTION
            "The total number of bytes allocated to this interface.
            This is obtained by multiplying proResInputBufsAlloc by
            proResInputBufsSize."
        ::= { proResBufTableEntry 6 }


    --
    -- Event Logging System (ELS) groups
    --
    -- The following groups export the ELS subsystem functionality.
    --

    -- ELS generic group
    --
    -- The ELS system-wide objects

    proElsPin OBJECT-TYPE
        SYNTAX  INTEGER
        ACCESS  read-write
        STATUS  mandatory
        DESCRIPTION
            "The number of ELS enterprise specific traps which may be 
            generated per second. A value of zero indicates no limit."
        ::= { proElsGeneric 1 }

    proElsDroppeds OBJECT-TYPE
        SYNTAX  Counter
        ACCESS  read-only
        STATUS  mandatory
        DESCRIPTION
            "The number of ELS enterprise specific traps which were 
            dropped because the pin had been reached."
        ::= { proElsGeneric 2 }

    proElsTimestamp OBJECT-TYPE
        SYNTAX    INTEGER {
                    proTSOff(1),
                    proTSSysUpTime(2),
                    proTSTimeOfDay(3)
                }
        ACCESS  read-write
        STATUS  mandatory
        DESCRIPTION
            "This object indicates whether ELS messages should be
            timestamped and, if yes, the timebase to use.

            Setting the object to proTSOff(1) disables timestamping.

            Setting the object to proTSSysUpTime(2) uses the 
            sysUpTime value as the timestamp.

            Setting the object to proTSTimeOfDay(3) uses the 
            real-time clock value as the timestamp."
        ::= { proElsGeneric 3 }

    proElsAction OBJECT-TYPE
        SYNTAX    INTEGER {
                    other(1),
                    proElsActionClear(2),
                    proElsActionDefault(3)
                }
        ACCESS  read-write
        STATUS  mandatory
        DESCRIPTION
            "A read of this object always returns the value other(1).

            Setting the object to elsActionClear(2) clears all ELS
            configuration. Specifically, this clear all ELS related 
            sram records. This action is the same as entering the
             command at the ELS config menu in the gateway
            console.

            Setting the object to proElsActionDefault(3) turns off
            logging of ELS events to both the console and SNMP traps
            for all configured subsystems. This action is the same as
            entering the commands:
                default disp sub all  
                default trap sub all
            at the ELS config menu in the gateway console."
        ::= { proElsGeneric 4 }

    proElsTrapVersion OBJECT-TYPE
        SYNTAX  INTEGER {
                    proElsTrapVersionV1(1),        
                    proElsTrapVersionV2(2)           -- default
                }
        ACCESS  read-write
        STATUS  mandatory
        DESCRIPTION
            "The new ELS trap format is used by default. The ability
            to select the old proElsTrapVersionV1 format is only provided 
            for backward compatibility. It is strongly recommended that 
            net managers use the new and improved proElsTrapVersionV2 
            format.

            This object reverts to its default value after a cold start
            (reload)."
        ::= { proElsGeneric 5 }

    -- ELS Subsystem group
    --
    -- This group describes each configured subsystem.
    
    proElsSubSysTable OBJECT-TYPE
        SYNTAX  SEQUENCE OF ProElsSubSysTableEntry
        ACCESS  not-accessible
        STATUS  mandatory
        DESCRIPTION
            "The ELS sub-system table."
        ::= { proEls 2 }

    proElsSubSysTableEntry OBJECT-TYPE
        SYNTAX  ProElsSubSysTableEntry
        ACCESS  not-accessible
        STATUS  mandatory
        DESCRIPTION
            "An entry corresponding to a specific subsystem."
        INDEX   { proElsSubSysIndex }
        ::= { proElsSubSysTable 1 }

    ProElsSubSysTableEntry ::= 
        SEQUENCE {
            proElsSubSysIndex
                INTEGER,
            proElsSubSysDescr
                DisplayString,
            proElsSubSysNumEvents
                INTEGER,
            proElsSubSysDisplayEnable
                ProElsMsgLogLevel,
            proElsSubSysDisplayDisable
                ProElsMsgLogLevel,
            proElsSubSysTrapEnable
                ProElsMsgLogLevel,
            proElsSubSysTrapDisable
                ProElsMsgLogLevel,
            proElsSubSysCurrDisplayLevel
                INTEGER,
            proElsSubSysCurrTrapLevel
                INTEGER
        }

    proElsSubSysIndex OBJECT-TYPE
        SYNTAX  INTEGER {
                    proElsSubSysIndexGw(1),     -- GW
                    proElsSubSysIndexArp(5),    -- ARP
                    proElsSubSysIndexIp(10),    -- IP
                    proElsSubSysIndexIcmp(11),  -- ICMP
                    proElsSubSysIndexTcp(12),   -- TCP
                    proElsSubSysIndexUdp(13),   -- UDP
                    proElsSubSysIndexBtp(14),   -- BTP
                    proElsSubSysIndexRip(15),   -- RIP
                    proElsSubSysIndexEgp(16),   -- EGP
                    proElsSubSysIndexSpf(17),   -- SPF
                    proElsSubSysIndexMspf(18),  -- MSPF
                    proElsSubSysIndexTftp(19),  -- TFTP
                    proElsSubSysIndexTn(20),    -- TN
                    proElsSubSysIndexSnmp(21),  -- SNMP
                    proElsSubSysIndexDn(25),    -- DN
                    proElsSubSysIndexXn(30),    -- XN
                    proElsSubSysIndexXns(31),   -- XNS
                    proElsSubSysIndexIpx(35),   -- IPX
                    proElsSubSysIndexIso(40),   -- ISO
                    proElsSubSysIndexEsis(41),  -- ESIS
                    proElsSubSysIndexIsis(42),  -- ISIS
                    proElsSubSysIndexDnav(43),  -- DNAV
                    proElsSubSysIndexApl(50),   -- APL
                    proElsSubSysIndexZip(51),   -- ZIP
                    proElsSubSysIndexRtmp(52),  -- RTMP
                    proElsSubSysIndexAp2(53),   -- AP2
                    proElsSubSysIndexZip2(54),  -- ZIP2
                    proElsSubSysIndexDds(55),   -- DDS
                    proElsSubSysIndexR2mp(56),  -- R2MP
                    proElsSubSysIndexVn(60),    -- VN
                    proElsSubSysIndexSrb(70),   -- SRB
                    proElsSubSysIndexStb(71),   -- STB
                    proElsSubSysIndexSrt(72),   -- SRT
                    proElsSubSysIndexStp(73),   -- STP
                    proElsSubSysIndexBr(74),    -- BR
                    proElsSubSysIndexSdlc(75),  -- SDLC
                    proElsSubSysIndexArpa(80),  -- ARPA
                    proElsSubSysIndexEth(81),   -- ETH
                    proElsSubSysIndexPn(82),    -- PN
                    proElsSubSysIndexSl(83),    -- SL
                    proElsSubSysIndexTkr(84),   -- TKR
                    proElsSubSysIndexX25(85),   -- X25
                    proElsSubSysIndexMan(87),   -- MAN
                    proElsSubSysIndexFddi(88),  -- FDDI
                    proElsSubSysIndexAtr(89),   -- ATR
                    proElsSubSysIndexSrly(90),  -- SRLY
                    proElsSubSysIndexFr(92),    -- FR
                    proElsSubSysIndexPpp(95),   -- PPP
                    proElsSubSysIndexX251(96),  -- X251
                    proElsSubSysIndexX252(97),  -- X252
                    proElsSubSysIndexX253(98),  -- X253
                    proElsSubSysIndexIppn(100), -- IPPN
                    proElsSubSysIndexWrs(101),  -- WRS
                    proElsSubSysIndexLnm(102),  -- LNM
                    proElsSubSysIndexLlc(103),  -- LLC
                    proElsSubSysIndexBgp(104),  -- BGP
                    proElsSubSysIndexMcf(105),  -- MCF
                    proElsSubSysIndexBoss(106), -- BOSS
                    proElsSubSysIndexDls(107),  -- DLS
                    proElsSubSysIndexV25b(108)  -- V25B
                }
        ACCESS  read-only
        STATUS  mandatory
        DESCRIPTION
            "This object is used to identify a specific subsystem."
        ::= { proElsSubSysTableEntry 1 }

    proElsSubSysDescr OBJECT-TYPE
        SYNTAX  DisplayString (SIZE (0..16))
        ACCESS  read-only
        STATUS  mandatory
        DESCRIPTION
            "This is a textual string indicating the name of the
            subsystem."
        ::= { proElsSubSysTableEntry 2 }

    proElsSubSysNumEvents OBJECT-TYPE
        SYNTAX  INTEGER
        ACCESS  read-only
        STATUS  mandatory
        DESCRIPTION
            "The number of events defined for this subsystem."
        ::= { proElsSubSysTableEntry 3 }

    proElsSubSysDisplayEnable OBJECT-TYPE
        SYNTAX  ProElsMsgLogLevel
        ACCESS  read-write
        STATUS  mandatory
        DESCRIPTION
            "A read of this object always returns the value other(1).

            Setting this object to one of the other enumerated values
            has the effect of enabling ELS events of the specified
            level to the console."
        ::= { proElsSubSysTableEntry 4 }

    proElsSubSysDisplayDisable OBJECT-TYPE
        SYNTAX  ProElsMsgLogLevel
        ACCESS  read-write
        STATUS  mandatory
        DESCRIPTION
            "A read of this object always returns the value other(1).

            Setting this object to one of the other enumerated values
            has the effect of disabling ELS events of the specified
            level to the console."
        ::= { proElsSubSysTableEntry 5 }

    proElsSubSysTrapEnable OBJECT-TYPE
        SYNTAX  ProElsMsgLogLevel
        ACCESS  read-write
        STATUS  mandatory
        DESCRIPTION
            "A read of this object always returns the value other(1).

            Setting this object to one of the other enumerated values
            has the effect of enabling ELS events of the specified
            level to a NMS via SNMP trap."
        ::= { proElsSubSysTableEntry 6 }

    proElsSubSysTrapDisable OBJECT-TYPE
        SYNTAX  ProElsMsgLogLevel
        ACCESS  read-write
        STATUS  mandatory
        DESCRIPTION
            "A read of this object always returns the value other(1).

            Setting this object to one of the other enumerated values
            has the effect of disabling ELS events of the specified
            level to a NMS via SNMP trap."
        ::= { proElsSubSysTableEntry 7 }

    proElsSubSysCurrDisplayLevel OBJECT-TYPE
        SYNTAX  INTEGER
        ACCESS  read-only
        STATUS  mandatory
        DESCRIPTION
            "The current event log levels that are enabled for display
            to console. Note that the value represents a bit string,
            a bit for each value defined in ProElsMsgLogLevel (excluding
            the other(1)) value. For example:
                proMsgLevelUIError,  bit 1
                proMsgLevelCIError,  bit 2
                etc.
            Note also that the levels:
                proMsgLevelError
                proMsgLevelInfo
                proMsgLevelTrace
                proMsgLevelStandard
                proMsgLevelAll
            are aggregates of other logging levels. So, for example, 
            turning on proMsgLogLevelError(6) will turn on (set the 
            bits) for all sub-levels in this category (i.e values 
            2,3,4 and 5)."
        ::= { proElsSubSysTableEntry 8 }

    proElsSubSysCurrTrapLevel OBJECT-TYPE
        SYNTAX  INTEGER
        ACCESS  read-only
        STATUS  mandatory
        DESCRIPTION
            "The current event log levels that are enabled for logging
            via SNMP trap. Note that the value represents a bit string,
            a bit for each value defined in ProElsMsgLogLevel (excluding
            the other(1)) value. For example:
                proMsgLevelUIError,  bit 1
                proMsgLevelCIError,  bit 2
                etc.
            Note also that the levels:
                proMsgLevelError
                proMsgLevelInfo
                proMsgLevelTrace
                proMsgLevelStandard
                proMsgLevelAll
            are aggregates of other logging levels. So, for example, 
            turning on proMsgLogLevelError(6) will turn on (set the 
            bits) for all sub-levels in this category (i.e values 
            2,3,4 and 5)."
        ::= { proElsSubSysTableEntry 9 }


    -- ELS Subsystem Events group
    --
    -- This group describes each event for each configured subsystem.

    proElsSubSysEventTable OBJECT-TYPE
        SYNTAX  SEQUENCE OF ProElsSubSysEventTableEntry
        ACCESS  not-accessible
        STATUS  mandatory
        DESCRIPTION
            "The ELS Sub system event table."
        ::= { proEls 3 }

    proElsSubSysEventTableEntry OBJECT-TYPE
        SYNTAX  ProElsSubSysEventTableEntry
        ACCESS  not-accessible
        STATUS  mandatory
        DESCRIPTION
            "An entry corresponding to a specific event in the 
            particular subsystem."
        INDEX   { proElsSubSysIndex, proElsSubSysEventIndex }
        ::= { proElsSubSysEventTable 1 }


    ProElsSubSysEventTableEntry ::= 
        SEQUENCE {
            proElsSubSysEventIndex
                INTEGER,
            proElsSubSysEventMsg
                DisplayString,
            proElsSubSysEventCount
                INTEGER,
            proElsSubSysEventLogLevel
                ProElsMsgLogLevel,
            proElsSubSysEventLogToConsole
                ProElsLogStatus,
            proElsSubSysEventLogToTrap
                ProElsLogStatus
        }

    proElsSubSysEventIndex OBJECT-TYPE
        SYNTAX  INTEGER
        ACCESS  read-only
        STATUS  mandatory
        DESCRIPTION
            "The specific message to which this entry refers."
        ::= { proElsSubSysEventTableEntry 1 }

    proElsSubSysEventMsg OBJECT-TYPE
        SYNTAX  DisplayString
        ACCESS  read-only
        STATUS  mandatory
        DESCRIPTION
               "The textual description for the message.  If timestamping
                 is turned on (proElsTimestamp is set to 2 or 3), the
                 8-byte timestamp and a blank will precede the ELS
                 message.  In all cases proElsSubSysEventMsg provides
                 the same ELS data as would be displayed on the console."
        ::= { proElsSubSysEventTableEntry 2 }

    proElsSubSysEventCount OBJECT-TYPE
        SYNTAX  INTEGER
        ACCESS  read-only
        STATUS  mandatory
        DESCRIPTION
            "The number of times this event has occurred."
        ::= { proElsSubSysEventTableEntry 3 }

    proElsSubSysEventLogLevel OBJECT-TYPE
        SYNTAX  ProElsMsgLogLevel
        ACCESS  read-only
        STATUS  mandatory
        DESCRIPTION
            "The pre-defined setting that classifies this message." 
        ::= { proElsSubSysEventTableEntry 4 }

    proElsSubSysEventLogToConsole OBJECT-TYPE
        SYNTAX  ProElsLogStatus
        ACCESS  read-write
        STATUS  mandatory
        DESCRIPTION
            "This object indicates whether this event should be logged
             to the console."
        ::= { proElsSubSysEventTableEntry 5 }

    proElsSubSysEventLogToTrap OBJECT-TYPE
        SYNTAX  ProElsLogStatus
        ACCESS  read-write
        STATUS  mandatory
        DESCRIPTION
            "This object indicates whether this event should be logged
             to SNMP trap."
        ::= { proElsSubSysEventTableEntry 6 }


    -- Traps

    -- ELS Trap
    --
    -- The following trap is generated when an ELS event occurs
    -- and the corresponding event is enabled for trap generation.

    proElsTrapV1 TRAP-TYPE
        ENTERPRISE   proteon
        VARIABLES    { proElsTrapSeqs, proElsTrapSubSystem, proElsTrapEvent }
        DESCRIPTION
            "An ELS trap event."
        ::= 1

    proElsTrapV2 TRAP-TYPE
        ENTERPRISE   proteon
        VARIABLES    { proElsSubSysEventMsg }
        DESCRIPTION
            "An ELS trap event. proElsSubSysEventMsg provides a 
            textual description of the event."
        ::= 2

 
    --- Proteon Temperature Group
    ---
    --- The Temperature Group is optional.  This group will be made
    --- available only on those routers that have thermometer capability.
    --- This group will not be exported on routers that do not have
    --- thermometer support.

    proTempScale    OBJECT-TYPE
        SYNTAX  INTEGER { 
            celsius(1), 
            fahrenheit(2) 
        }
        ACCESS  read-only
        STATUS  mandatory
        DESCRIPTION
            "Indicates the scale used when reporting temperature values.
            If Celsius(1), all temperature values are in degrees Celsius.
            If Fahrenheit(2), all temperature values are in degrees 
            Fahrenheit."
        ::= {proTemp 1}
    
    proMaxHwTemp    OBJECT-TYPE
        SYNTAX  INTEGER
        ACCESS  read-only
        STATUS  mandatory
        DESCRIPTION
            "This attribute indicates the maximum temperature that the
            thermometer system can record.  This attribute is used as
            an upper bound for all temperature ranges."
        ::= {proTemp 2}
            
    proMinHwTemp    OBJECT-TYPE
        SYNTAX  INTEGER
        ACCESS  read-only
        STATUS  mandatory
        DESCRIPTION
            "This attribute indicates the minimum temperature that the
            thermometer system can record.  This attribute is used as
            a lower bound for all temperature ranges."
        ::= {proTemp 3}
                
    
    proTempPollPeriod   OBJECT-TYPE
        SYNTAX  INTEGER( 10..600 )
        ACCESS  read-only
        STATUS  mandatory
        DESCRIPTION
            "This attribute determines how often the thermometer 
            system will recalculate the current temperature and
            any temperature range checks.  This value represents
            time in seconds between temperature recalculations."
        DEFVAL  {60}
        ::= {proTemp 4}
    
    proCurrentTemp  OBJECT-TYPE
        SYNTAX  INTEGER
        ACCESS  read-only
        STATUS  mandatory
        DESCRIPTION
            "The current ambient temperature of the system.  This value 
            is recalculated by the system once per proTempPollPeriod."
        ::= { proTemp 5}
    
    
    proLowTempThreshold OBJECT-TYPE
        SYNTAX  INTEGER
        ACCESS  read-only
        STATUS  mandatory
        DESCRIPTION
            "The temperature that will cause a Low Temperature 
            Condition to become true.  The Low Temperature Condition will 
            become true when:
    
                proCurrentTemp <= proLowTempThreshold.  
    
            The low temperature condition will reset when:
    
                proCurrentTemp > (proLowTempThreshold + proTempHysteresis).
    
            This range is checked one per proTempPollPeriod."
        ::= {proTemp 6}
    
    proHighTempThreshold    OBJECT-TYPE
        SYNTAX  INTEGER
        ACCESS  read-only
        STATUS  mandatory
        DESCRIPTION
            "The temperature that will cause a High Temperature 
            Condition to become true.  The High Temperature Condition will 
            become true when:
    
                proCurrentTemp >= proHighTempThreshold.
    
            The high temperature condition will reset when:
    
                proCurrentTemp < (proHighTempThreshold - proTempHysteresis).
    
            This range is checked one per proTempPollPeriod."
        ::= {proTemp 7}
    
    
    proTempHysteresis   OBJECT-TYPE
        SYNTAX  INTEGER
        ACCESS  read-only
        STATUS  mandatory
        DESCRIPTION
            "The number of degrees that the current ambient temperature
            must drop below proHighTempThreshold or above proLowTempTheshold
            before the threshold's condition is deactivated."
        DEFVAL {5}
        ::= {proTemp 8}
    
    
    proHighTempCondition OBJECT-TYPE
        SYNTAX  INTEGER {
                    off(1),
                    on(2)
                }
        ACCESS  read-only
        STATUS  mandatory
        DESCRIPTION
            "Indicates whether a High Temperature Condition is active.  
            This attribute will be set ON(2) if a High Temperature Condition 
            is active."
        ::= {proTemp 9}
    
    
    proLowTempCondition  OBJECT-TYPE
        SYNTAX  INTEGER {
                    off(1),
                    on(2)
                }
        ACCESS  read-only
        STATUS  mandatory
        DESCRIPTION
            "Indicates whether a Low Temperature Condition is active.  
            This attribute will be set ON(2) if a Low Temperature Condition 
            is active."
        ::= {proTemp 10}
    
    proHighestTemp  OBJECT-TYPE
        SYNTAX  INTEGER
        ACCESS  read-only
        STATUS  mandatory
        DESCRIPTION
            "This is the highest temperature recorded by the router since
            last reset."
        ::= {proTemp 11}
    
    proHighTempTime OBJECT-TYPE
        SYNTAX  TimeTicks
        ACCESS  read-only
        STATUS  mandatory
        DESCRIPTION
            "This is the time (in hundreds of seconds) that has elapsed
            since proHighestTemp was last recorded."
        ::= {proTemp 12} 
    
    proLowestTemp  OBJECT-TYPE
        SYNTAX  INTEGER
        ACCESS  read-only
        STATUS  mandatory
        DESCRIPTION
            "This is the lowest temperature recorded by the router since
            last reset."
        ::= {proTemp 13}
    
    proLowTempTime OBJECT-TYPE
        SYNTAX  TimeTicks
        ACCESS  read-only
        STATUS  mandatory
        DESCRIPTION
            "This is the time (in hundreds of seconds) that has elapsed
            since proLowestTemp was last recorded."
        ::= {proTemp 14} 


    -- Config groups

    proCfgLoad          OBJECT IDENTIFIER ::= { proConfig 1 }


    --- Proteon Load Configuration Group
    ---
    --- This group describes the contents of the particular load
    --- the router is running.  This information can be used to
    --- determine which subsystems are able to be configured.

    proCfgProtocols     OBJECT-TYPE
        SYNTAX  DisplayString (SIZE(0..255))
        ACCESS  read-only
        STATUS  mandatory
        DESCRIPTION
            "This object returns an ASCII string containing the short 
             names of all protocol types supported in the current load."
        ::= { proCfgLoad 1 }

    proCfgDatalinks     OBJECT-TYPE
        SYNTAX  DisplayString (SIZE(0..255))
        ACCESS  read-only
        STATUS  mandatory
        DESCRIPTION
            "This object returns an ASCII string containing the short 
             names of all datalink/MAC types supported in the current load."
        ::= { proCfgLoad 2 }

    proCfgFeatures      OBJECT-TYPE
        SYNTAX  DisplayString (SIZE(0..255))
        ACCESS  read-only
        STATUS  mandatory
        DESCRIPTION
            "This object returns an ASCII string containing the short 
             names of all router features supported in the current load."
        ::= { proCfgLoad 3 }

    END
