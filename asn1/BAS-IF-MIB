BAS-IF-MIB DEFINITIONS ::= BEGIN

IMPORTS
    MODULE-IDENTITY, OBJECT-TYPE, IpAddress             FROM SNMPv2-SMI
    InterfaceIndex, ifEntry                             FROM IF-MIB
    basExtIf, BasChassisId, BasSlotId, BasInterfaceId,
    BasLogicalPortId                                    FROM BAS-MIB;

basIfMIB MODULE-IDENTITY
    LAST-UPDATED "9811061430Z"
    ORGANIZATION "Broadband Access Systems, Inc."
    CONTACT-INFO
        " Tech Support
          Broadband Access Systems, Inc.
          201 Forest Street
          Marlborough, MA 01752
          USA

          508-485-8200
          support@basystems.com"
    DESCRIPTION
        "The MIB module defines the configuration MIB objects
         for Broadband Access Systems, Inc. interfaces
         extensions."
    ::= { basExtIf 1 }


-- the BAS Interfaces table

-- The BAS Interfaces table contains BAS proprietaryinformation on
-- the entity's interfaces.

basIfTable OBJECT-TYPE
    SYNTAX      SEQUENCE OF BasIfEntry
    MAX-ACCESS  not-accessible
    STATUS      current
    DESCRIPTION
        "A list of interface entries.  The number of entries
        is given by the value of ifNumber."
    ::= { basIfMIB 2 }

basIfEntry OBJECT-TYPE
    SYNTAX      BasIfEntry
    MAX-ACCESS  not-accessible
    STATUS      current
    DESCRIPTION
        "An entry containing management information applicable
        to a particular interface."
    AUGMENTS { ifEntry }
    ::= { basIfTable 1 }

BasIfEntry ::=
    SEQUENCE {
        basIfChassis            BasChassisId,
        basIfSlot               BasSlotId,
        basIfInterface          BasInterfaceId,
        basIfLPort              BasLogicalPortId,
        basIfClass              INTEGER,
        basIfSimpleProxyArp     INTEGER,
        basIfDhcpCmSubnet       IpAddress,
        basIfDhcpHostSubnet     IpAddress,
        basIfArpAgingDisable    INTEGER,
        basIfSecurityFilter     INTEGER
    }

basIfChassis OBJECT-TYPE
    SYNTAX      BasChassisId
    MAX-ACCESS  read-only
    STATUS      current
    DESCRIPTION
        "The BAS Chassis ID of this card."
    ::= { basIfEntry 1 }

basIfSlot OBJECT-TYPE
    SYNTAX      BasSlotId
    MAX-ACCESS  read-only
    STATUS      current
    DESCRIPTION
        "The BAS Slot ID of this card."
    ::= { basIfEntry 2 }

basIfInterface OBJECT-TYPE
    SYNTAX      BasInterfaceId
    MAX-ACCESS  read-only
    STATUS      current
    DESCRIPTION
        "The BAS interface ID of this card."
    ::= { basIfEntry 3 }

basIfLPort OBJECT-TYPE
    SYNTAX      BasLogicalPortId
    MAX-ACCESS  read-only
    STATUS      current
    DESCRIPTION
        "The BAS logical port ID of this card."
    ::= { basIfEntry 4 }

basIfClass OBJECT-TYPE
    SYNTAX      INTEGER {
                        icl(1),
                        ccl(2),
                        egress(3)
                }
    MAX-ACCESS  read-only
    STATUS      current
    DESCRIPTION
        "The BAS class of this interface."
    ::= { basIfEntry 5 }

basIfSimpleProxyArp OBJECT-TYPE
    SYNTAX      INTEGER {
                        enable(1),
                        disable(2)
                }
    MAX-ACCESS  read-write
    STATUS      current
    DESCRIPTION
        "Enable or disable simple proxy ARP so CMTS
        hosts can communicate with one another."
    ::= { basIfEntry 6 }

basIfDhcpCmSubnet OBJECT-TYPE
    SYNTAX      IpAddress
    MAX-ACCESS  read-write
    STATUS      current
    DESCRIPTION
        "Subnet to use for giaddr for cable modem DHCP requests."
    ::= { basIfEntry 7 }

basIfDhcpHostSubnet OBJECT-TYPE
    SYNTAX      IpAddress
    MAX-ACCESS  read-write
    STATUS      current
    DESCRIPTION
        "Subnet to use for giaddr for host DHCP requests."
    ::= { basIfEntry 8 }

basIfArpAgingDisable OBJECT-TYPE
    SYNTAX      INTEGER {
                        enable(1),
                        disable(2)
                }
    MAX-ACCESS  read-write
    STATUS      current
    DESCRIPTION
        "Enable or disable timing out ARP enties on this interface."
    ::= { basIfEntry 9 }

basIfSecurityFilter OBJECT-TYPE
    SYNTAX      INTEGER {
                        enable(1),
                        disable(2)
                }
    MAX-ACCESS  read-write
    STATUS      current
    DESCRIPTION
        "Enable or disable security filtering on this interface.
	If this filter is enabled all packets sent to 10.x.13.x
	from a CM other than SNMP,DHCP,ICMP,TOD,SYSLOG,
	and TFTP will be dropped and all packets from CPE other
	than ICMP and DHCP will be dropped."
    ::= { basIfEntry 10 }

END
