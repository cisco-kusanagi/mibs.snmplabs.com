Wellfleet-SYS-SVC-MIB DEFINITIONS ::= BEGIN
 
-- Created by mdl2asn version 3.1
-- Creation date: Wed Aug 30 16:49:00 EDT 1995


    IMPORTS

      IpAddress
        FROM RFC1155-SMI
      OBJECT-TYPE
        FROM RFC-1212
      DisplayString
        FROM RFC1213-MIB
      wfNetBootGroup
        FROM Wellfleet-COMMON-MIB;


    wfNetbootCfgGroup	OBJECT IDENTIFIER ::= { wfNetBootGroup 1 }

    wfNetbootImage OBJECT-TYPE
        SYNTAX	INTEGER {
    		    imageoff(1),
    		    imageon(2)
    		}
        ACCESS	read-write
        STATUS	mandatory
        DESCRIPTION
                "Enables booting of an executable image over the network. If
                disabled, then the image will be read from a local file system."
        DEFVAL	{ imageon }
        ::= { wfNetbootCfgGroup 1 }

    wfNetbootConfig OBJECT-TYPE
        SYNTAX	INTEGER {
    		    configoff(1),
    		    configon(2)
    		}
        ACCESS	read-write
        STATUS	mandatory
        DESCRIPTION
                "Enables booting of a configuration file over the network. If
                disabled, then the config will be read from a local file system."
        DEFVAL	{ configon }
        ::= { wfNetbootCfgGroup 2 }

    wfNetbootServerAddress OBJECT-TYPE
        SYNTAX	IpAddress
        ACCESS	read-write
        STATUS	mandatory
        DESCRIPTION
                "IP address of remote server."
        ::= { wfNetbootCfgGroup 3 }

    wfNetbootImageName OBJECT-TYPE
        SYNTAX	DisplayString
        ACCESS	read-write
        STATUS	mandatory
        DESCRIPTION
                "Pathname of image file on remote server."
        ::= { wfNetbootCfgGroup 4 }

    wfNetbootConfigName OBJECT-TYPE
        SYNTAX	DisplayString
        ACCESS	read-write
        STATUS	mandatory
        DESCRIPTION
                "Pathname of configuration file on remote server."
        ::= { wfNetbootCfgGroup 5 }

    wfNetbootCfgDelete OBJECT-TYPE
        SYNTAX	INTEGER {
    		    create(1),
    		    delete(2)
    		}
        ACCESS	read-write
        STATUS	mandatory
        DESCRIPTION
                "create/delete parameter, dflt = created"
        DEFVAL	{ create }
        ::= { wfNetbootCfgGroup 6 }

    wfNetbootCurrGroup	OBJECT IDENTIFIER ::= { wfNetBootGroup 2 }

    wfNetbootImageCurr OBJECT-TYPE
        SYNTAX	INTEGER {
    		    imagecurroff(1),
    		    imagecurron(2)
    		}
        ACCESS	read-only
        STATUS	mandatory
        DESCRIPTION
                "Current value of Netboot image flag in Non-Volatile RAM."
        DEFVAL	{ imagecurron }
        ::= { wfNetbootCurrGroup 1 }

    wfNetbootConfigCurr OBJECT-TYPE
        SYNTAX	INTEGER {
    		    configcurroff(1),
    		    configcurron(2)
    		}
        ACCESS	read-only
        STATUS	mandatory
        DESCRIPTION
                "Current value of Netboot config flag in Non-Volatile RAM."
        DEFVAL	{ configcurron }
        ::= { wfNetbootCurrGroup 2 }

    wfNetbootServerAddressCurr OBJECT-TYPE
        SYNTAX	IpAddress
        ACCESS	read-only
        STATUS	mandatory
        DESCRIPTION
                "IP address of remote server."
        ::= { wfNetbootCurrGroup 3 }

    wfNetbootImageNameCurr OBJECT-TYPE
        SYNTAX	DisplayString
        ACCESS	read-only
        STATUS	mandatory
        DESCRIPTION
                "Pathname of image file on remote server."
        ::= { wfNetbootCurrGroup 4 }

    wfNetbootConfigNameCurr OBJECT-TYPE
        SYNTAX	DisplayString
        ACCESS	read-only
        STATUS	mandatory
        DESCRIPTION
                "Pathname of configuration file on remote server."
        ::= { wfNetbootCurrGroup 5 }

    wfNetbootCfgTable OBJECT-TYPE
        SYNTAX	SEQUENCE OF WfNetbootCfgEntry
        ACCESS	not-accessible
        STATUS	mandatory
        DESCRIPTION
                "A Table of Interface-specific Netboot Configuration Parameters"
        ::= { wfNetBootGroup 3 }

    wfNetbootCfgEntry OBJECT-TYPE
        SYNTAX	WfNetbootCfgEntry
        ACCESS	not-accessible
        STATUS	mandatory
        DESCRIPTION
                "Values of a particular interface's configuration parameters."
        INDEX	{ wfNetbootSlot,
    		  wfNetbootConnector }
        ::= { wfNetbootCfgTable 1 }

    WfNetbootCfgEntry ::= SEQUENCE {
    	    wfNetbootDelete
    		INTEGER,
    	    wfNetbootSlot
    		INTEGER,
    	    wfNetbootConnector
    		INTEGER,
    	    wfNetbootIpAddr
    		IpAddress,
    	    wfNetbootIpMask
    		IpAddress,
    	    wfNetbootNextHop
    		IpAddress,
    	    wfNetbootProtoMask
    		INTEGER,
    	    wfNetbootDisable
    		INTEGER,
    	    wfNetbootConnName
    		DisplayString,
    	    wfNetbootTokenRingSpeed
    		INTEGER,
    	    wfNetbootBchanRate
    		INTEGER,
            wfNetbootDsuCsuOpMode
                INTEGER
        }

    wfNetbootDelete OBJECT-TYPE
        SYNTAX	INTEGER {
    		    create(1),
    		    delete(2)
    		}
        ACCESS	read-write
        STATUS	mandatory
        DESCRIPTION
                "create/delete parameter, dflt = created
                Deleteing this instance will set the corresponding NOVRAM
                values to the default settings."
        DEFVAL	{ create }
        ::= { wfNetbootCfgEntry 1 }

    wfNetbootSlot OBJECT-TYPE
        SYNTAX	INTEGER(1..14)
        ACCESS	read-only
        STATUS	mandatory
        DESCRIPTION
                "instance ID Slot, filled in by driver"
        ::= { wfNetbootCfgEntry 2 }

    wfNetbootConnector OBJECT-TYPE
        SYNTAX	INTEGER {
    		    xcvr1(1),
    		    com1(2),
    		    com2(3),
    		    com3(4),
    		    xcvr11(5),
    		    xcvr12(6),
    		    com11(7),
    		    com12(8),
    		    xcvr21(9),
    		    xcvr22(10),
    		    com21(11),
    		    com22(12),
    		    xcvr31(13),
    		    xcvr32(14),
    		    com31(15),
    		    com32(16),
    		    xcvr41(17),
    		    xcvr42(18),
    		    com41(19),
    		    com42(20),
    		    xcvr2(21),
		    xcvr33(22),
		    xcvr34(23),
		    arnxcvr1(24),
		    arnxcvr2(25),
		    arncom1(26),
		    arncom2(27),
		    arncom3(28),
		    arncom4(29),
		    arncom5(30),
		    arnmau1(31),
		    arnmau2(32),
    		    com13(33),
    		    com14(34),
    		    com23(35),
    		    com24(36),
    		    com33(37),
    		    com34(38),
    		    com43(39),
    		    com44(40)
    		}
        ACCESS	read-only
        STATUS	mandatory
        DESCRIPTION
                "Unique number which identifies the interface for which the
                following parameters are configured."
        ::= { wfNetbootCfgEntry 3 }

    wfNetbootIpAddr OBJECT-TYPE
        SYNTAX	IpAddress
        ACCESS	read-write
        STATUS	mandatory
        DESCRIPTION
                "IP address to use on this interface"
        ::= { wfNetbootCfgEntry 4 }

    wfNetbootIpMask OBJECT-TYPE
        SYNTAX	IpAddress
        ACCESS	read-write
        STATUS	mandatory
        DESCRIPTION
                "IP address mask to use on this interface"
        ::= { wfNetbootCfgEntry 5 }

    wfNetbootNextHop OBJECT-TYPE
        SYNTAX	IpAddress
        ACCESS	read-write
        STATUS	mandatory
        DESCRIPTION
                "IP address of the next hop router connected to this interface.
                This value is used to auto-configure a static route for
                Network Boot."
        ::= { wfNetbootCfgEntry 6 }

    wfNetbootProtoMask OBJECT-TYPE
        SYNTAX	INTEGER {
    		    fron(1),
    		    x25on(2),
    		    intrnclkon(3),
    		    noton(4),
    		    annexaon(5),
    		    lmion(6),
				ppp(7)
    		}
        ACCESS	read-write
        STATUS	mandatory
        DESCRIPTION
                "Bit Mask indicating a non-default protocol is being used on
                this interface."
        DEFVAL	{ noton }
        ::= { wfNetbootCfgEntry 7 }

    wfNetbootDisable OBJECT-TYPE
        SYNTAX	INTEGER {
    		    enable(1),
    		    disable(2)
    		}
        ACCESS	read-write
        STATUS	mandatory
        DESCRIPTION
                "Enable or disable the interface for Netbooting."
        DEFVAL	{ enable }
        ::= { wfNetbootCfgEntry 8 }

    wfNetbootConnName OBJECT-TYPE
        SYNTAX	DisplayString
        ACCESS	read-only
        STATUS	mandatory
        DESCRIPTION
                "Connector name."
        ::= { wfNetbootCfgEntry 9 }

    wfNetbootTokenRingSpeed OBJECT-TYPE
        SYNTAX	INTEGER {
    		    mbps4(4),
    		    mbps16(16)
    		}
        ACCESS	read-write
        STATUS	mandatory
        DESCRIPTION
                "Speed of the Token Ring interface for Netbooting."
        DEFVAL	{ mbps16 }
        ::= { wfNetbootCfgEntry 10 }

    wfNetbootBchanRate OBJECT-TYPE
        SYNTAX	INTEGER {
    		    rate64k(64),
    		    rate128k(128)
    		}
        ACCESS	read-write
        STATUS	mandatory
        DESCRIPTION
                "Speed B Channel for Netbooting. AN 200 Only"
        DEFVAL	{ rate64k }
        ::= { wfNetbootCfgEntry 11 }

     wfNetbootDsuCsuOpMode OBJECT-TYPE
        SYNTAX INTEGER {
                   rate56k(56),
                   rate64k(64)
               }
        ACCESS read-write
        STATUS mandatory
        DESCRIPTION
               "Dsu/Csu interface speed for Netbooting"
        DEFVAL { rate56k }
        ::= { wfNetbootCfgEntry 12 }


    wfNetbootCurrTable OBJECT-TYPE
        SYNTAX	SEQUENCE OF WfNetbootCurrEntry
        ACCESS	not-accessible
        STATUS	mandatory
        DESCRIPTION
                "A Table of current values for Interface-specific Netboot Parameters"
        ::= { wfNetBootGroup 4 }

    wfNetbootCurrEntry OBJECT-TYPE
        SYNTAX	WfNetbootCurrEntry
        ACCESS	not-accessible
        STATUS	mandatory
        DESCRIPTION
                "Values of a particular interface's current configuration parameters."
        INDEX	{ wfNetbootCurrSlot,
    		  wfNetbootCurrConnector }
        ::= { wfNetbootCurrTable 1 }

    WfNetbootCurrEntry ::= SEQUENCE {
    	    wfNetbootCurrSlot
    		INTEGER,
    	    wfNetbootCurrConnector
    		INTEGER,
    	    wfNetbootCurrIpAddr
    		IpAddress,
    	    wfNetbootCurrIpMask
    		IpAddress,
    	    wfNetbootCurrNextHop
    		IpAddress,
    	    wfNetbootCurrProtoMask
    		INTEGER,
    	    wfNetbootCurrDisable
    		INTEGER,
    	    wfNetbootCurrConnName
    		DisplayString,
    	    wfNetbootCurrTokenRingSpeed
    		INTEGER,
            wfNetbootCurrBchanRate
	        INTEGER,
            wfNetbootCurrDsuCsuOpMode
                INTEGER
        }

    wfNetbootCurrSlot OBJECT-TYPE
        SYNTAX	INTEGER(1..14)
        ACCESS	read-only
        STATUS	mandatory
        DESCRIPTION
                "instance ID Slot, filled in by driver"
        ::= { wfNetbootCurrEntry 1 }

    wfNetbootCurrConnector OBJECT-TYPE
        SYNTAX	INTEGER {
    		    currxcvr1(1),
    		    currcom1(2),
    		    currcom2(3),
    		    currcom3(4),
    		    currxcvr11(5),
    		    currxcvr12(6),
    		    currcom11(7),
    		    currcom12(8),
    		    currxcvr21(9),
    		    currxcvr22(10),
    		    currcom21(11),
    		    currcom22(12),
    		    currxcvr31(13),
    		    currxcvr32(14),
    		    currcom31(15),
    		    currcom32(16),
    		    currxcvr41(17),
    		    currxcvr42(18),
    		    currcom41(19),
    		    currcom42(20),
    		    currxcvr2(21),
		    currxcvr33(22),
		    currxcvr34(23),
		    currarnxcvr1(24),
		    currarnxcvr2(25),
		    currarncom1(26),
		    currarncom2(27),
		    currarncom3(28),
		    currarncom4(29),
		    currarncom5(30),
		    currarnmau1(31),
		    currarnmau2(32),
    		    currcom13(33),
    		    currcom14(34),
    		    currcom23(35),
    		    currcom24(36),
    		    currcom33(37),
    		    currcom34(38),
    		    currcom43(39),
    		    currcom44(40)
    		}
        ACCESS	read-only
        STATUS	mandatory
        DESCRIPTION
                "Unique number which identifies the interface for which the
                following parameters are configured."
        ::= { wfNetbootCurrEntry 2 }

    wfNetbootCurrIpAddr OBJECT-TYPE
        SYNTAX	IpAddress
        ACCESS	read-only
        STATUS	mandatory
        DESCRIPTION
                "IP address to use on this interface"
        ::= { wfNetbootCurrEntry 3 }

    wfNetbootCurrIpMask OBJECT-TYPE
        SYNTAX	IpAddress
        ACCESS	read-only
        STATUS	mandatory
        DESCRIPTION
                "IP address mask to use on this interface"
        ::= { wfNetbootCurrEntry 4 }

    wfNetbootCurrNextHop OBJECT-TYPE
        SYNTAX	IpAddress
        ACCESS	read-only
        STATUS	mandatory
        DESCRIPTION
                "IP address of the next hop router connected to this interface.
                This value is used to auto-configure a static route for
                Network Boot."
        ::= { wfNetbootCurrEntry 5 }

    wfNetbootCurrProtoMask OBJECT-TYPE
        SYNTAX	INTEGER {
    		    frcurron(1),
    		    x25curron(2),
    		    intrnclkcurron(3),
    		    notcurron(4),
    		    annexaon(5),
    		    lmion(6),
				ppp(7)
    		}
        ACCESS	read-only
        STATUS	mandatory
        DESCRIPTION
                "Bit Mask indicating a non-default protocol is being used on
                this interface."
        DEFVAL	{ notcurron }
        ::= { wfNetbootCurrEntry 6 }

    wfNetbootCurrDisable OBJECT-TYPE
        SYNTAX	INTEGER {
    		    enable(1),
    		    disable(2)
    		}
        ACCESS	read-only
        STATUS	mandatory
        DESCRIPTION
                "Enable or disable the interface for Netbooting."
        DEFVAL	{ enable }
        ::= { wfNetbootCurrEntry 7 }

    wfNetbootCurrConnName OBJECT-TYPE
        SYNTAX	DisplayString
        ACCESS	read-only
        STATUS	mandatory
        DESCRIPTION
                "Connector name."
        ::= { wfNetbootCurrEntry 8 }

    wfNetbootCurrTokenRingSpeed OBJECT-TYPE
        SYNTAX	INTEGER {
    		    mbps4(4),
    		    mbps16(16)
    		}
        ACCESS	read-only
        STATUS	mandatory
        DESCRIPTION
                "Speed of the Token Ring interface for Netbooting."
        DEFVAL	{ mbps16 }
        ::= { wfNetbootCurrEntry 9 }

    wfNetbootCurrBchanRate OBJECT-TYPE
        SYNTAX	INTEGER {
    		    rate64k(64),
    		    rate128k(128)
    		}
        ACCESS	read-write
        STATUS	mandatory
        DESCRIPTION
                "Speed B Channel for Netbooting. AN 200 Only"
        DEFVAL	{ rate64k }
        ::= { wfNetbootCurrEntry 10 }

    wfNetbootCurrDsuCsuOpMode OBJECT-TYPE
        SYNTAX  INTEGER {
                    rate56k(56),
                    rate64k(64)
                }
        ACCESS  read-write
        STATUS  mandatory
        DESCRIPTION
                "Dsu/Csu interface speed for Netbooting"
        DEFVAL  { rate56k }
       ::= { wfNetbootCurrEntry 11 }
      
    END  -- Wellfleet-SYS-SVC-MIB
