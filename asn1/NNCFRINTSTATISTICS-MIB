-------------------------------------------------------------------------------
-- file: FrameRelayIntervalStatistics.mib 
--
-- description:
--    This file contains the SNMP definitions for the Frame Relay Interval
--    Statistics area.
--
-- history:
--    31A0630 / 96.02.06 / Sriram Darbha / Creation from MIBTemplate.mib V1.0 
--    31A0630 / 96.02.27 / Sriram Darbha / Changes after review
--
-- %%history-start%%
-- 96.12.12 tkuhl 31A0691: Added Stream BERT stuff 
-- 96.12.13 mhong 31A0691: Checkin the correct file 
-- 97.08.28 derrickn 31A1054: Added endpoint statistic for frames converted 
--   to DE 
-- 97.10.06 derrickn P.217923: Changed policed to DE stat to show as an 
--   ingress not egress. 
-- 97.10.08 derrickn P.217923: Fix the description to go along with the name 
--   change. 
-- 98.01.28 derrickn 31A1155: fraps.3.1 trib merge. 
-- 98.05.01 derrickn P.228886: use more appropriate types for the variables 
-- %%history-end%%
--
-- Copyright 1996-1998 Newbridge Networks Corporation.  All Rights Reserved
-------------------------------------------------------------------------------
NNCFRINTSTATISTICS-MIB DEFINITIONS ::= BEGIN

    IMPORTS
        MODULE-IDENTITY, OBJECT-TYPE, OBJECT-IDENTITY,
            Integer32, Gauge32, Counter32
            FROM SNMPv2-SMI
        NncExtIntvlStateType
            FROM NNC-INTERVAL-STATISTICS-TC-MIB
        MODULE-COMPLIANCE, OBJECT-GROUP
            FROM SNMPv2-CONF
        ifIndex
            FROM IF-MIB
        nncExtensions, NncExtCounter64
            FROM NNCGNI0001-SMI;
            
    nncFrIntStatistics MODULE-IDENTITY
        LAST-UPDATED     "9803031200Z" 
        ORGANIZATION     "Newbridge Networks Corporation"
        CONTACT-INFO
                        "Newbridge Networks Corporation
                         Postal: 600 March Road
                             Kanata, Ontario
                             Canada K2K 2E6

                         Phone:  +1 613 591 3600
                         Fax:    +1 613 591 3680"
        
        DESCRIPTION  "This module contains definitions for
                 performance monitoring of Frame Relay Streams"
    
    ::= { nncExtensions 30 }


    nncFrIntStatisticsObjects OBJECT IDENTIFIER ::= { nncFrIntStatistics 1 }
    nncFrIntStatisticsTraps OBJECT IDENTIFIER ::= { nncFrIntStatistics 2 }
    nncFrIntStatisticsGroups OBJECT IDENTIFIER ::= { nncFrIntStatistics 3 }
    nncFrIntStatisticsCompliances OBJECT IDENTIFIER ::= { nncFrIntStatistics 4 }

--------------------------------------------------------------------------------
-- nncFrIntStatisticsObjects - Object Definitions
--
-- This MIB module contains the following objects:
--  1. FR Stream Stats Current Table
--  2. FR Stream Stats Interval Table
--  3. FR PVC Endpoint Stats Current Table
--  4. FR PVC Endpoint Stats Interval Table
--  5. nncFrDepthOfHistoricalStrata - depth of historical intervals
--  6. FR Stream BERT statistics Table
--
-- NOTE:
-- 1. For interval statistics tables, statistics are collected for 'M' intervals
-- of 1 hour each.  Presently, resource limitations on the card limit support
-- to the case M = 1.
--------------------------------------------------------------------------------

--------------------------------------------------------------------------------
-- nncFrIntStatisticsObject 1: Streams Stats Current Table
--------------------------------------------------------------------------------

  nncFrStrStatCurrentTable            OBJECT-TYPE
    SYNTAX        SEQUENCE OF NncFrStrStatCurrentEntry
    MAX-ACCESS    not-accessible
    STATUS        current
    DESCRIPTION  "The nncFrStrStatCurrentTable contains objects for
            monitoring the performance of a frame relay stream during
            the current 1hr interval."
  ::= { nncFrIntStatisticsObjects 1 }


  nncFrStrStatCurrentEntry            OBJECT-TYPE
    SYNTAX        NncFrStrStatCurrentEntry
    MAX-ACCESS    not-accessible
    STATUS        current
    DESCRIPTION  "An entry in the 1hr current statistics table.  Each
            conceptual row contains current interval statistics for
            a particular frame relay stream."
    INDEX        { ifIndex }
  ::= { nncFrStrStatCurrentTable 1 }


  NncFrStrStatCurrentEntry ::=
    SEQUENCE {
        nncFrStrStatCurrentState                       NncExtIntvlStateType,
        nncFrStrStatCurrentAbsoluteIntervalNumber      INTEGER,
        nncFrStrStatCurrentInOctets                    NncExtCounter64,
        nncFrStrStatCurrentOutOctets                   NncExtCounter64,
        nncFrStrStatCurrentInUCastPackets              NncExtCounter64,
        nncFrStrStatCurrentOutUCastPackets             NncExtCounter64,
        nncFrStrStatCurrentInDiscards                  NncExtCounter64,
        nncFrStrStatCurrentOutDiscards                 NncExtCounter64,
        nncFrStrStatCurrentInErrors                    NncExtCounter64,
        nncFrStrStatCurrentOutErrors                   NncExtCounter64,
        nncFrStrStatCurrentSigUserProtErrors           NncExtCounter64,
        nncFrStrStatCurrentSigNetProtErrors            NncExtCounter64,
        nncFrStrStatCurrentSigUserLinkRelErrors        NncExtCounter64,
        nncFrStrStatCurrentSigNetLinkRelErrors         NncExtCounter64,
        nncFrStrStatCurrentSigUserChanInactive         NncExtCounter64,
        nncFrStrStatCurrentSigNetChanInactive          NncExtCounter64,
        nncFrStrStatCurrentStSCAlarms                  Counter32,
        nncFrStrStatCurrentStTimeSC                    Gauge32,
        nncFrStrStatCurrentStMaxDurationRED            Counter32,
        nncFrStrStatCurrentStMCAlarms                  Counter32,
        nncFrStrStatCurrentStTimeMC                    Gauge32,
        nncFrStrStatCurrentOutLinkUtilization          Gauge32(0..100),
        nncFrStrStatCurrentInLinkUtilization           Gauge32(0..100),
        nncFrStrStatCurrentInInvdLength                NncExtCounter64,
        nncFrStrStatCurrentStLastErroredDLCI           Integer32(0..8388607),
        nncFrStrStatCurrentInDiscdOctetsCOS            NncExtCounter64,
        nncFrStrStatCurrentInDiscdCOSDESet             NncExtCounter64,
        nncFrStrStatCurrentInDiscdCOSDEClr             NncExtCounter64,
        nncFrStrStatCurrentInDiscdBadEncaps            NncExtCounter64,
        nncFrStrStatCurrentOutDiscdBadEncaps           NncExtCounter64,
        nncFrStrStatCurrentInDiscdUnsupEncaps          NncExtCounter64,
        nncFrStrStatCurrentOutDiscdUnsupEncaps         NncExtCounter64,
        nncFrStrStatCurrentOutDiscdDESet               NncExtCounter64,
        nncFrStrStatCurrentOutDiscdDEClr               NncExtCounter64,
        nncFrStrStatCurrentInDiscdDESet                NncExtCounter64,
        nncFrStrStatCurrentInDiscdDEClr                NncExtCounter64,
        nncFrStrStatCurrentStLMSigInvldField           NncExtCounter64,
        nncFrStrStatCurrentStLMSigUnsupMsgType         NncExtCounter64,
        nncFrStrStatCurrentStLMSigInvldEID             NncExtCounter64,
        nncFrStrStatCurrentStLMSigInvldIELen           NncExtCounter64,
        nncFrStrStatCurrentStLMSigInvldRepType         NncExtCounter64,
        nncFrStrStatCurrentStLMSigFrmWithNoIEs         NncExtCounter64,
        nncFrStrStatCurrentStUserSequenceErrs          NncExtCounter64,
        nncFrStrStatCurrentStNetSequenceErrs           NncExtCounter64,
        nncFrStrStatCurrentStLMUTimeoutsnT1            NncExtCounter64,
        nncFrStrStatCurrentStLMUStatusMsgsRcvd         NncExtCounter64,
        nncFrStrStatCurrentStLMUStatusENQMsgsSent      NncExtCounter64,
        nncFrStrStatCurrentStLMUAsyncStatusRcvd        NncExtCounter64,
        nncFrStrStatCurrentStLMNTimeoutsnT2            NncExtCounter64,
        nncFrStrStatCurrentStLMNStatusMsgsSent         NncExtCounter64,
        nncFrStrStatCurrentStLMNStatusENQMsgsRcvd      NncExtCounter64,
        nncFrStrStatCurrentStLMNAsyncStatusSent        NncExtCounter64,
        nncFrStrStatCurrentInCRCErrors                 NncExtCounter64,
        nncFrStrStatCurrentInNonIntegral               NncExtCounter64,
        nncFrStrStatCurrentInReservedDLCI              NncExtCounter64,
        nncFrStrStatCurrentInInvldEA                   NncExtCounter64,
        nncFrStrStatCurrentStFrmTooSmall               NncExtCounter64,
        nncFrStrStatCurrentInAborts                    NncExtCounter64,
        nncFrStrStatCurrentInSumOfDisagremnts          NncExtCounter64,
        nncFrStrStatCurrentInOverRuns                  NncExtCounter64,
        nncFrStrStatCurrentOutUnderRuns                NncExtCounter64,
        nncFrStrStatCurrentStIntervalDuration          Integer32,
        nncFrStrStatCurrentBestEffortPeakDelay         Gauge32(1..60000),
        nncFrStrStatCurrentCommittedPeakDelay          Gauge32(1..60000),
        nncFrStrStatCurrentLowDelayPeakDelay           Gauge32(1..60000),
        nncFrStrStatCurrentRealTimePeakDelay           Gauge32(1..60000),
        nncFrStrStatCurrentBestEffortAccDelay          NncExtCounter64,
        nncFrStrStatCurrentCommittedAccDelay           NncExtCounter64,
        nncFrStrStatCurrentLowDelayAccDelay            NncExtCounter64,
        nncFrStrStatCurrentRealTimeAccDelay            NncExtCounter64,
        nncFrStrStatCurrentBestEffortOutUCastPackets   NncExtCounter64,
        nncFrStrStatCurrentCommittedOutUCastPackets    NncExtCounter64,
        nncFrStrStatCurrentLowDelayOutUCastPackets     NncExtCounter64,
        nncFrStrStatCurrentRealTimeOutUCastPackets     NncExtCounter64,
        nncFrStrStatCurrentBestEffortUCastPacketsDEClr NncExtCounter64,
        nncFrStrStatCurrentCommittedUCastPacketsDEClr  NncExtCounter64,
        nncFrStrStatCurrentLowDelayUCastPacketsDEClr   NncExtCounter64,
        nncFrStrStatCurrentRealTimeUCastPacketsDEClr   NncExtCounter64,
        nncFrStrStatCurrentBestEffortDiscdDEClr        NncExtCounter64,
        nncFrStrStatCurrentCommittedDiscdDEClr         NncExtCounter64,
        nncFrStrStatCurrentLowDelayDiscdDEClr          NncExtCounter64,
        nncFrStrStatCurrentRealTimeDiscdDEClr          NncExtCounter64
    }


  nncFrStrStatCurrentState            OBJECT-TYPE
    SYNTAX        NncExtIntvlStateType
    MAX-ACCESS    read-only
    STATUS        current
    DESCRIPTION  "The state of the current interval. The object provides
            a status for those entries which have been reset by the
            user or have been subject to a wall-clock time change."
  ::= { nncFrStrStatCurrentEntry 1 }

  nncFrStrStatCurrentAbsoluteIntervalNumber    OBJECT-TYPE
    SYNTAX        INTEGER (0..96)
    MAX-ACCESS    read-only
    STATUS        current
    DESCRIPTION  "The absolute interval number of this interval."
  ::= { nncFrStrStatCurrentEntry 2 }

  nncFrStrStatCurrentInOctets            OBJECT-TYPE
    SYNTAX        NncExtCounter64
    MAX-ACCESS    read-only
    STATUS        current
    DESCRIPTION  "Number of bytes received on this stream."
  ::= { nncFrStrStatCurrentEntry 3 }


  nncFrStrStatCurrentOutOctets            OBJECT-TYPE
    SYNTAX        NncExtCounter64
    MAX-ACCESS    read-only
    STATUS        current
    DESCRIPTION  "Number of bytes transmitted on this stream."
  ::= { nncFrStrStatCurrentEntry 4 }


  nncFrStrStatCurrentInUCastPackets        OBJECT-TYPE
    SYNTAX        NncExtCounter64
    MAX-ACCESS    read-only
    STATUS        current
    DESCRIPTION  "Number of unerrored, unicast frames received." 
  ::= { nncFrStrStatCurrentEntry 5 }


  nncFrStrStatCurrentOutUCastPackets        OBJECT-TYPE
    SYNTAX        NncExtCounter64
    MAX-ACCESS    read-only
    STATUS        current
    DESCRIPTION  "Number of unerrored, unicast frames transmitted."
  ::= { nncFrStrStatCurrentEntry 6 }


  nncFrStrStatCurrentInDiscards            OBJECT-TYPE
    SYNTAX        NncExtCounter64
    MAX-ACCESS    read-only
    STATUS        current
    DESCRIPTION  "Number of incoming frames discarded due to these
            reasons: policing, congestion."
  ::= { nncFrStrStatCurrentEntry 7 }


  nncFrStrStatCurrentOutDiscards        OBJECT-TYPE
    SYNTAX        NncExtCounter64
    MAX-ACCESS    read-only
    STATUS        current
    DESCRIPTION  "Number of outgoing frames discarded due to these
            reasons: policing, congestion."
  ::= { nncFrStrStatCurrentEntry 8 }


  nncFrStrStatCurrentInErrors            OBJECT-TYPE
    SYNTAX        NncExtCounter64
    MAX-ACCESS    read-only
    STATUS        current
    DESCRIPTION  "Number of incoming frames discarded due to errors:
            invalid lengths, non-integral bytes, CRC errors, 
            bad encapsulation, invalid EA, reserved DLCI"
  ::= { nncFrStrStatCurrentEntry 9 }


  nncFrStrStatCurrentOutErrors            OBJECT-TYPE
    SYNTAX        NncExtCounter64
    MAX-ACCESS    read-only
    STATUS        current
    DESCRIPTION  "Number of outgoing frames discarded due to errors:
            eg. bad encapsulation."
  ::= { nncFrStrStatCurrentEntry 10 }


  nncFrStrStatCurrentSigUserProtErrors        OBJECT-TYPE
    SYNTAX        NncExtCounter64
    MAX-ACCESS    read-only
    STATUS        current
    DESCRIPTION  "Number of user-side local in-channel signalling
            protocol errors (protocol discriminator, message type,
            call reference & mandatory information eleement errors)
            for this uni/nni stream.  If the stream is not perfor-
            ming user-side procedures, this value is equal to
            noSuchName."
  ::= { nncFrStrStatCurrentEntry 11 }


  nncFrStrStatCurrentSigNetProtErrors        OBJECT-TYPE
    SYNTAX        NncExtCounter64
    MAX-ACCESS    read-only
    STATUS        current
    DESCRIPTION  "Number of network-side local in-channel signalling
            protocol errors (protocol discriminator, message type,
            call reference & mandatory information eleement errors)
            for this uni/nni stream.  If the stream is not perfor-
            ming network-side procedures, this value is equal to
            noSuchName."
  ::= { nncFrStrStatCurrentEntry 12 }


  nncFrStrStatCurrentSigUserLinkRelErrors    OBJECT-TYPE
    SYNTAX        NncExtCounter64
    MAX-ACCESS    read-only
    STATUS        current
    DESCRIPTION  "Number of user-side local in-channel signalling link
            reliability errors (non receipt of Enq/Status messages
            or invalid sequence numbers in a link integrity verifi-
            cation information element) for this stream.  If the
            stream is not performing user-side procedures, this
            value is equal to noSuchName."
  ::= { nncFrStrStatCurrentEntry 13 }


  nncFrStrStatCurrentSigNetLinkRelErrors    OBJECT-TYPE
    SYNTAX        NncExtCounter64
    MAX-ACCESS    read-only
    STATUS        current
    DESCRIPTION  "Number of network-side local in-channel signalling
            link reliability errors (non receipt of Enq/Status
            messages or invalid sequence numbers in a link integrity
            verification information element) for this stream.  If
            the stream is not performing network-side procedures,
            this value is equal to noSuchName."
  ::= { nncFrStrStatCurrentEntry 14 }


  nncFrStrStatCurrentSigUserChanInactive    OBJECT-TYPE
    SYNTAX        NncExtCounter64
    MAX-ACCESS    read-only
    STATUS        current
    DESCRIPTION  "Number of times the user-side channel was declared
            inactive (N2 errors in N3 events) for this stream.  If
            the stream is not performing user-side procedures, this
            value is equal to noSuchName."
  ::= { nncFrStrStatCurrentEntry 15 }


  nncFrStrStatCurrentSigNetChanInactive        OBJECT-TYPE
    SYNTAX        NncExtCounter64
    MAX-ACCESS    read-only
    STATUS        current
    DESCRIPTION  "Number of times the network-side channel was declared
            inactive (N2 errors in N3 events) for this stream.
            If the stream is not performing network-side procedures,
            this value is equal to noSuchName."
  ::= { nncFrStrStatCurrentEntry 16 }


  nncFrStrStatCurrentStSCAlarms OBJECT-TYPE
    SYNTAX        Counter32
    MAX-ACCESS    read-only
    STATUS        current
    DESCRIPTION  "Number of one second intervals for which the stream
            entered the severely congested state."
  ::= { nncFrStrStatCurrentEntry 17 }


  nncFrStrStatCurrentStTimeSC OBJECT-TYPE
    SYNTAX        Gauge32
    MAX-ACCESS    read-only
    STATUS        current
    DESCRIPTION  "Period of time the stream was in the severely congested state
            during the current interval (expressed in 10's of milliseconds).
            Divide into the entire length of the interval to get a ratio."
  ::= { nncFrStrStatCurrentEntry 18 }


  nncFrStrStatCurrentStMaxDurationRED OBJECT-TYPE
    SYNTAX        Counter32
    MAX-ACCESS    read-only
    STATUS        current
    DESCRIPTION  "Longest period of time the stream spent in the Red (severely
            congested) state, expressed in seconds."
  ::= { nncFrStrStatCurrentEntry 19 }


  nncFrStrStatCurrentStMCAlarms OBJECT-TYPE
    SYNTAX        Counter32
    MAX-ACCESS    read-only
    STATUS        current
    DESCRIPTION  "Number of one second intervals for which the stream
            entered the mildly congested state."
  ::= { nncFrStrStatCurrentEntry 20 }


  nncFrStrStatCurrentStTimeMC OBJECT-TYPE
    SYNTAX        Gauge32
    MAX-ACCESS    read-only
    STATUS        current
    DESCRIPTION  "Period of time the stream was in the mildly congested state
            during the current interval (expressed in 10's of milliseconds).
            Divide into the entire length of the interval to get a ratio."
  ::= { nncFrStrStatCurrentEntry 21 }


  nncFrStrStatCurrentOutLinkUtilization        OBJECT-TYPE
    SYNTAX        Gauge32(0..100)
    MAX-ACCESS    read-only
    STATUS        current
    DESCRIPTION  "The percentage utilization on the outgoing link
            during the current interval."
  ::= { nncFrStrStatCurrentEntry 22 }


  nncFrStrStatCurrentInLinkUtilization        OBJECT-TYPE
    SYNTAX        Gauge32(0..100)
    MAX-ACCESS    read-only
    STATUS        current
    DESCRIPTION  "The percentage utilization on the incoming link
            during the current interval."
  ::= { nncFrStrStatCurrentEntry 23 }


  nncFrStrStatCurrentInInvdLength OBJECT-TYPE
    SYNTAX        NncExtCounter64
    MAX-ACCESS    read-only
    STATUS        current
    DESCRIPTION  "Number of frames discarded because there was no data in
            the frame, or because the frame exceeded the maximum allowed
            length."
  ::= { nncFrStrStatCurrentEntry 24 }


  nncFrStrStatCurrentStLastErroredDLCI OBJECT-TYPE
    SYNTAX        Integer32(0..8388607)
    MAX-ACCESS    read-only
    STATUS        current
    DESCRIPTION  "DLCI of the most recent DLC to receive invalid frames
                 on this frame stream."
  ::= { nncFrStrStatCurrentEntry 25 }


  nncFrStrStatCurrentInDiscdOctetsCOS OBJECT-TYPE
    SYNTAX        NncExtCounter64
    MAX-ACCESS    read-only
    STATUS        current
    DESCRIPTION  "Number of ingress bytes discarded due to receive
            Class-of-Service procedures."
  ::= { nncFrStrStatCurrentEntry 26 }


  nncFrStrStatCurrentInDiscdCOSDESet OBJECT-TYPE
    SYNTAX        NncExtCounter64
    MAX-ACCESS    read-only
    STATUS        current
    DESCRIPTION  "Number of ingress frames discarded due to receive
            Class-of-Service procedures, in which the DE bit was set."
  ::= { nncFrStrStatCurrentEntry 27 }


  nncFrStrStatCurrentInDiscdCOSDEClr OBJECT-TYPE
    SYNTAX        NncExtCounter64
    MAX-ACCESS    read-only
    STATUS        current
    DESCRIPTION  "Number of ingress frames discarded due to receive
            Class-of-Service procedures, in which the DE bit was not set."
  ::= { nncFrStrStatCurrentEntry 28 }


  nncFrStrStatCurrentInDiscdBadEncaps        OBJECT-TYPE
    SYNTAX        NncExtCounter64
    MAX-ACCESS    read-only
    STATUS        current
    DESCRIPTION  "Number of ingress frames discarded due to having a bad
            RFC1490 encapsulation header."
  ::= { nncFrStrStatCurrentEntry 29 }


  nncFrStrStatCurrentOutDiscdBadEncaps        OBJECT-TYPE
    SYNTAX        NncExtCounter64
    MAX-ACCESS    read-only
    STATUS        current
    DESCRIPTION  "Number of egress frames discarded due to having a bad
            RFC1483 encapsulation header."
  ::= { nncFrStrStatCurrentEntry 30 }


  nncFrStrStatCurrentInDiscdUnsupEncaps        OBJECT-TYPE
    SYNTAX        NncExtCounter64
    MAX-ACCESS    read-only
    STATUS        current
    DESCRIPTION  "Number of ingress frames discarded due to having an
            unsupported RFC1490 encapsulation header."
  ::= { nncFrStrStatCurrentEntry 31 }


  nncFrStrStatCurrentOutDiscdUnsupEncaps        OBJECT-TYPE
    SYNTAX        NncExtCounter64
    MAX-ACCESS    read-only
    STATUS        current
    DESCRIPTION  "Number of egress frames discarded due to having an
            unsupported RFC1483 encapsulation header."
  ::= { nncFrStrStatCurrentEntry 32 }


  nncFrStrStatCurrentOutDiscdDESet OBJECT-TYPE
    SYNTAX        NncExtCounter64
    MAX-ACCESS    read-only
    STATUS        current
    DESCRIPTION  "Number of egress frames discarded due to transmit
            congestion procedures, in which the DE bit was set."
  ::= { nncFrStrStatCurrentEntry 33 }


  nncFrStrStatCurrentOutDiscdDEClr OBJECT-TYPE
    SYNTAX        NncExtCounter64
    MAX-ACCESS    read-only
    STATUS        current
    DESCRIPTION  "Number of egress frames discarded due to transmit
            congestion procedures, in which the DE bit was not set."
  ::= { nncFrStrStatCurrentEntry 34 }


  nncFrStrStatCurrentInDiscdDESet OBJECT-TYPE
    SYNTAX        NncExtCounter64
    MAX-ACCESS    read-only
    STATUS        current
    DESCRIPTION  "Number of ingress frames discarded due to receive
            congestion procedures, in which the DE bit was set."
  ::= { nncFrStrStatCurrentEntry 35 }


  nncFrStrStatCurrentInDiscdDEClr OBJECT-TYPE
    SYNTAX        NncExtCounter64
    MAX-ACCESS    read-only
    STATUS        current
    DESCRIPTION  "Number of ingress frames discarded due to receive
            congestion procedures, in which the DE bit was not set."
  ::= { nncFrStrStatCurrentEntry 36 }


  nncFrStrStatCurrentStLMSigInvldField        OBJECT-TYPE
    SYNTAX        NncExtCounter64
    MAX-ACCESS    read-only
    STATUS        current
    DESCRIPTION  "Number of Status signalling frames with incorrect values
            for the Unnumbered Information Frame field, Protocol
            Discrimator field, or Call Reference Field."
  ::= { nncFrStrStatCurrentEntry 37 }


  nncFrStrStatCurrentStLMSigUnsupMsgType        OBJECT-TYPE
    SYNTAX        NncExtCounter64
    MAX-ACCESS    read-only
    STATUS        current
    DESCRIPTION  "Number of Status signalling frames that are not a Status
            or Status Enquiry messsage (Unsupported message type)."
  ::= { nncFrStrStatCurrentEntry 38 }


  nncFrStrStatCurrentStLMSigInvldEID        OBJECT-TYPE
    SYNTAX        NncExtCounter64
    MAX-ACCESS    read-only
    STATUS        current
    DESCRIPTION  "Number of Status signalling frames with an IEID that is
            not a Report Type IEID, Keep Alive Sequence IEID, or a PVC
            Status IEID."
  ::= { nncFrStrStatCurrentEntry 39 }


  nncFrStrStatCurrentStLMSigInvldIELen        OBJECT-TYPE
    SYNTAX        NncExtCounter64
    MAX-ACCESS    read-only
    STATUS        current
    DESCRIPTION  "Number of Status signalling frames with an IE length
            field size that does not conform with the Frame Relay status
            signalling protocol."
  ::= { nncFrStrStatCurrentEntry 40 }


  nncFrStrStatCurrentStLMSigInvldRepType        OBJECT-TYPE
    SYNTAX        NncExtCounter64
    MAX-ACCESS    read-only
    STATUS        current
    DESCRIPTION  "Number of Status signalling frames with a Report Type IE
            that were not a Full Report Type or a Keep Alive Confirmation."
  ::= { nncFrStrStatCurrentEntry 41 }


  nncFrStrStatCurrentStLMSigFrmWithNoIEs        OBJECT-TYPE
    SYNTAX        NncExtCounter64
    MAX-ACCESS    read-only
    STATUS        current
    DESCRIPTION  "Number of Status signalling frames that terminate before
            the IE appears."
  ::= { nncFrStrStatCurrentEntry 42 }


  nncFrStrStatCurrentStUserSequenceErrs        OBJECT-TYPE
    SYNTAX        NncExtCounter64
    MAX-ACCESS    read-only
    STATUS        current
    DESCRIPTION  "Number of status signalling frames received with a Last
            Received Sequence number that is inconsistent with the expected
            value, the last transmitted Current Sequence Number.
            If the stream is not performing user-side procedures,
            this value is equal to noSuchName."
  ::= { nncFrStrStatCurrentEntry 43 }


  nncFrStrStatCurrentStNetSequenceErrs        OBJECT-TYPE
    SYNTAX        NncExtCounter64
    MAX-ACCESS    read-only
    STATUS        current
    DESCRIPTION  "Number of status signalling frames received with a
            Last Received Sequence number that is inconsistent with the
            expected value, the last transmitted Current Sequence Number.
            If the stream is not performing network-side procedures,
            this value is equal to noSuchName."
  ::= { nncFrStrStatCurrentEntry 44 }


  nncFrStrStatCurrentStLMUTimeoutsnT1 OBJECT-TYPE
    SYNTAX        NncExtCounter64
    MAX-ACCESS    read-only
    STATUS        current
    DESCRIPTION  "Number of times the link integrity verification interval
            has been exceeded without receiving a Status message.
            If the stream is not performing user-side procedures,
            this value is equal to noSuchName."
  ::= { nncFrStrStatCurrentEntry 45 }


  nncFrStrStatCurrentStLMUStatusMsgsRcvd OBJECT-TYPE
    SYNTAX        NncExtCounter64
    MAX-ACCESS    read-only
    STATUS        current
    DESCRIPTION  "Number of Status messages received.
            If the stream is not performing user-side procedures,
            this value is equal to noSuchName."
  ::= { nncFrStrStatCurrentEntry 46 }


  nncFrStrStatCurrentStLMUStatusENQMsgsSent OBJECT-TYPE
    SYNTAX        NncExtCounter64
    MAX-ACCESS    read-only
    STATUS        current
    DESCRIPTION  "Number of Status Enquiry messages sent.
            If the stream is not performing user-side procedures,
            this value is equal to noSuchName."
  ::= { nncFrStrStatCurrentEntry 47 }


  nncFrStrStatCurrentStLMUAsyncStatusRcvd OBJECT-TYPE
    SYNTAX        NncExtCounter64
    MAX-ACCESS    read-only
    STATUS        current
    DESCRIPTION  "Number of asynchronous Update Status messages received.
            If the stream is not performing user-side procedures,
            this value is equal to noSuchName."
  ::= { nncFrStrStatCurrentEntry 48 }


  nncFrStrStatCurrentStLMNTimeoutsnT2 OBJECT-TYPE
    SYNTAX        NncExtCounter64
    MAX-ACCESS    read-only
    STATUS        current
    DESCRIPTION  "Number of times the polling verification interval
            was exceeded without receivung a Keep Alive Sequence.
            If the stream is not performing network-side procedures,
            this value is equal to noSuchName."
  ::= { nncFrStrStatCurrentEntry 49 }


  nncFrStrStatCurrentStLMNStatusMsgsSent OBJECT-TYPE
    SYNTAX        NncExtCounter64
    MAX-ACCESS    read-only
    STATUS        current
    DESCRIPTION  "Number of Status messages sent.
            If the stream is not performing network-side procedures,
            this value is equal to noSuchName."
  ::= { nncFrStrStatCurrentEntry 50 }


  nncFrStrStatCurrentStLMNStatusENQMsgsRcvd OBJECT-TYPE
    SYNTAX        NncExtCounter64
    MAX-ACCESS    read-only
    STATUS        current
    DESCRIPTION  "Number of Status Enquiry messages received.
            If the stream is not performing network-side procedures,
            this value is equal to noSuchName."
  ::= { nncFrStrStatCurrentEntry 51 }


  nncFrStrStatCurrentStLMNAsyncStatusSent OBJECT-TYPE
    SYNTAX        NncExtCounter64
    MAX-ACCESS    read-only
    STATUS        current
    DESCRIPTION  "Number of asynchronous Update Status messages transmitted.
            If the stream is not performing network-side procedures,
            this value is equal to noSuchName."
  ::= { nncFrStrStatCurrentEntry 52 }


  nncFrStrStatCurrentInCRCErrors OBJECT-TYPE
    SYNTAX        NncExtCounter64
    MAX-ACCESS    read-only
    STATUS        current
    DESCRIPTION  "Number of frames with an incorrect CRC-16 value."
  ::= { nncFrStrStatCurrentEntry 53 }


  nncFrStrStatCurrentInNonIntegral        OBJECT-TYPE
    SYNTAX        NncExtCounter64
    MAX-ACCESS    read-only
    STATUS        current
    DESCRIPTION  "Number of frames with a non-integral number of
            octets between the delimiting HDLC flags."
  ::= { nncFrStrStatCurrentEntry 54 }


  nncFrStrStatCurrentInReservedDLCI        OBJECT-TYPE
    SYNTAX        NncExtCounter64
    MAX-ACCESS    read-only
    STATUS        current
    DESCRIPTION  "Number of frames with a DLCI that cannot be assigned
            to user connections."
  ::= { nncFrStrStatCurrentEntry 55 }


  nncFrStrStatCurrentInInvldEA        OBJECT-TYPE
    SYNTAX        NncExtCounter64
    MAX-ACCESS    read-only
    STATUS        current
    DESCRIPTION  "Number of frames with the EA (extended address) bit
            incorrectly set."
  ::= { nncFrStrStatCurrentEntry 56 }


  nncFrStrStatCurrentStFrmTooSmall        OBJECT-TYPE
    SYNTAX        NncExtCounter64
    MAX-ACCESS    read-only
    STATUS        current
    DESCRIPTION  "Number of frames that are smaller than the allowed
            minimum size."
  ::= { nncFrStrStatCurrentEntry 57 }


  nncFrStrStatCurrentInAborts        OBJECT-TYPE
    SYNTAX        NncExtCounter64
    MAX-ACCESS    read-only
    STATUS        current
    DESCRIPTION  "Number of aborted frames."
  ::= { nncFrStrStatCurrentEntry 58 }


  nncFrStrStatCurrentInSumOfDisagremnts        OBJECT-TYPE
    SYNTAX        NncExtCounter64
    MAX-ACCESS    read-only
    STATUS        current
    DESCRIPTION  "Total number of frames discarded because: the
            frame relay UNI or ICI was unavailable to accept frame
            traffic, the frame had a DLCI not available for end-user
            connections, the DLCI was inactive, the frame exceeded
            the maximum configured frame length (but its length was
            legal within the frame relay protocol), the frame violated
            the configured address field size (but had a legal address
            field size with the frame relay protocol), or was an
            unexpected status signalling frame."
  ::= { nncFrStrStatCurrentEntry 59 }


  nncFrStrStatCurrentInOverRuns        OBJECT-TYPE
    SYNTAX        NncExtCounter64
    MAX-ACCESS    read-only
    STATUS        current
    DESCRIPTION  "Number of times the receiver was forced to overrun."
  ::= { nncFrStrStatCurrentEntry 60 }


  nncFrStrStatCurrentOutUnderRuns        OBJECT-TYPE
    SYNTAX        NncExtCounter64
    MAX-ACCESS    read-only
    STATUS        current
    DESCRIPTION  "Number of times the transmitter was forced to underrun."
  ::= { nncFrStrStatCurrentEntry 61 }


  nncFrStrStatCurrentStIntervalDuration OBJECT-TYPE
    SYNTAX        Integer32
    MAX-ACCESS    read-only
    STATUS        current
    DESCRIPTION  "Duration of the statistics accumulation interval."
  ::= { nncFrStrStatCurrentEntry 62 }


  nncFrStrStatCurrentBestEffortPeakDelay OBJECT-TYPE
    SYNTAX        Gauge32(1..60000)
    MAX-ACCESS    read-only
    STATUS        current
    DESCRIPTION  "The largest delay experienced by any frame that was
            transmitted on the stream in service category Best Effort."
  ::= { nncFrStrStatCurrentEntry 63 }


  nncFrStrStatCurrentCommittedPeakDelay OBJECT-TYPE
    SYNTAX        Gauge32(1..60000)
    MAX-ACCESS    read-only
    STATUS        current
    DESCRIPTION  "The largest delay experienced by any frame that was
            transmitted on the stream in service category: Committed
            Throughptut."
  ::= { nncFrStrStatCurrentEntry 64 }


  nncFrStrStatCurrentLowDelayPeakDelay OBJECT-TYPE
    SYNTAX        Gauge32(1..60000)
    MAX-ACCESS    read-only
    STATUS        current
    DESCRIPTION  "The largest delay experienced by any frame that was
            transmitted on the stream in service category: Low Delay."
  ::= { nncFrStrStatCurrentEntry 65 }


  nncFrStrStatCurrentRealTimePeakDelay OBJECT-TYPE
    SYNTAX        Gauge32(1..60000)
    MAX-ACCESS    read-only
    STATUS        current
    DESCRIPTION  "The largest delay experienced by any frame that was
            transmitted on the stream in service category Real Time."
  ::= { nncFrStrStatCurrentEntry 66 }


  nncFrStrStatCurrentBestEffortAccDelay OBJECT-TYPE
    SYNTAX        NncExtCounter64
    MAX-ACCESS    read-only
    STATUS        current
    DESCRIPTION  "The accumulated delay experienced by all frames in a
            stream transmitted in service category Best Effort.  Combined
            with the Out Ucast Packets for service category Best Effort,
            the average delay per frame can be calculated."
  ::= { nncFrStrStatCurrentEntry 67 }


  nncFrStrStatCurrentCommittedAccDelay OBJECT-TYPE
    SYNTAX        NncExtCounter64
    MAX-ACCESS    read-only
    STATUS        current
    DESCRIPTION  "The accumulated delay experienced by all frames in a
            stream transmitted in service category Committed Throughput.
            Combined with the Out Ucast Packets for service category
            Committed Throughput, the average delay per frame can be
            calculated."
  ::= { nncFrStrStatCurrentEntry 68 }

  nncFrStrStatCurrentLowDelayAccDelay OBJECT-TYPE
    SYNTAX        NncExtCounter64
    MAX-ACCESS    read-only
    STATUS        current
    DESCRIPTION  "The accumulated delay experienced by all frames in a
            stream transmitted in service category Low Delay.
            Combined with the Out Ucast Packets for service category
            Low Delay, the average delay per frame can be calculated."
  ::= { nncFrStrStatCurrentEntry 69 }

  nncFrStrStatCurrentRealTimeAccDelay OBJECT-TYPE
    SYNTAX        NncExtCounter64
    MAX-ACCESS    read-only
    STATUS        current
    DESCRIPTION  "The accumulated delay experienced by all frames in a
            stream transmitted in service category Real Time.
            Combined with the Out Ucast Packets for service category
            Real Time, the average delay per frame can be calculated."
  ::= { nncFrStrStatCurrentEntry 70 }

  nncFrStrStatCurrentBestEffortOutUCastPackets OBJECT-TYPE
    SYNTAX        NncExtCounter64
    MAX-ACCESS    read-only
    STATUS        current
    DESCRIPTION  "Number of unerrored, unicast frames transmitted in
            service category Best Effort."
  ::= { nncFrStrStatCurrentEntry 71 }


  nncFrStrStatCurrentCommittedOutUCastPackets OBJECT-TYPE
    SYNTAX        NncExtCounter64
    MAX-ACCESS    read-only
    STATUS        current
    DESCRIPTION  "Number of unerrored, unicast frames transmitted in
            service category Committed Throughput."
  ::= { nncFrStrStatCurrentEntry 72 }


  nncFrStrStatCurrentLowDelayOutUCastPackets OBJECT-TYPE
    SYNTAX        NncExtCounter64
    MAX-ACCESS    read-only
    STATUS        current
    DESCRIPTION  "Number of unerrored, unicast frames transmitted in
            service category Low Delay."
  ::= { nncFrStrStatCurrentEntry 73 }


  nncFrStrStatCurrentRealTimeOutUCastPackets OBJECT-TYPE
    SYNTAX        NncExtCounter64
    MAX-ACCESS    read-only
    STATUS        current
    DESCRIPTION  "Number of unerrored, unicast frames transmitted in
            service category Real Time."
  ::= { nncFrStrStatCurrentEntry 74 }


  nncFrStrStatCurrentBestEffortUCastPacketsDEClr OBJECT-TYPE
    SYNTAX        NncExtCounter64
    MAX-ACCESS    read-only
    STATUS        current
    DESCRIPTION  "Number of unerrored, unicast frames with the DE
            bit not set transmitted in service category Best Effort."
  ::= { nncFrStrStatCurrentEntry 75 }


  nncFrStrStatCurrentCommittedUCastPacketsDEClr OBJECT-TYPE
    SYNTAX        NncExtCounter64
    MAX-ACCESS    read-only
    STATUS        current
    DESCRIPTION  "Number of unerrored, unicast frames with the DE
            bit not set transmitted in service category Committed
            Throughput."
  ::= { nncFrStrStatCurrentEntry 76 }


  nncFrStrStatCurrentLowDelayUCastPacketsDEClr OBJECT-TYPE
    SYNTAX        NncExtCounter64
    MAX-ACCESS    read-only
    STATUS        current
    DESCRIPTION  "Number of unerrored, unicast frames with the DE
            bit not set transmitted in service category Low Delay."
  ::= { nncFrStrStatCurrentEntry 77 }


  nncFrStrStatCurrentRealTimeUCastPacketsDEClr OBJECT-TYPE
    SYNTAX        NncExtCounter64
    MAX-ACCESS    read-only
    STATUS        current
    DESCRIPTION  "Number of unerrored, unicast frames with the DE
            bit not set, transmitted in service category Real Time."
  ::= { nncFrStrStatCurrentEntry 78 }


  nncFrStrStatCurrentBestEffortDiscdDEClr OBJECT-TYPE
    SYNTAX        NncExtCounter64
    MAX-ACCESS    read-only
    STATUS        current
    DESCRIPTION  "Number of unerrored, unicast frames with the DE bit
            not set, discarded by QoS procedures in service category
            Best Effort."
  ::= { nncFrStrStatCurrentEntry 79 }

  nncFrStrStatCurrentCommittedDiscdDEClr OBJECT-TYPE
    SYNTAX        NncExtCounter64
    MAX-ACCESS    read-only
    STATUS        current
    DESCRIPTION  "Number of unerrored, unicast frames with the DE bit
            not set, discarded by QoS procedures in service category
            Committed Throughput."
  ::= { nncFrStrStatCurrentEntry 80 }

  nncFrStrStatCurrentLowDelayDiscdDEClr OBJECT-TYPE
    SYNTAX        NncExtCounter64
    MAX-ACCESS    read-only
    STATUS        current
    DESCRIPTION  "Number of unerrored, unicast frames with the DE bit
            not set, discarded by QoS procedures in service category
            Low Delay."
  ::= { nncFrStrStatCurrentEntry 81 }

  nncFrStrStatCurrentRealTimeDiscdDEClr OBJECT-TYPE
    SYNTAX        NncExtCounter64
    MAX-ACCESS    read-only
    STATUS        current
    DESCRIPTION  "Number of unerrored, unicast frames with the DE bit
            not set, discarded by QoS procedures in service category
            Real Time."
  ::= { nncFrStrStatCurrentEntry 82 }



--------------------------------------------------------------------------------
-- nncFrIntStatisticsObject 2: Stream Stats Interval Table
--------------------------------------------------------------------------------

  nncFrStrStatIntervalTable            OBJECT-TYPE
    SYNTAX        SEQUENCE OF NncFrStrStatIntervalEntry
    MAX-ACCESS    not-accessible
    STATUS        current
    DESCRIPTION  "The nncFrStrStatIntervalTable contains objects for
            monitoring the performance of a frame relay stream over
            M historical intervals of 1hr each."
  ::= { nncFrIntStatisticsObjects 2 }


  nncFrStrStatIntervalEntry            OBJECT-TYPE
    SYNTAX        NncFrStrStatIntervalEntry
    MAX-ACCESS    not-accessible
    STATUS        current
    DESCRIPTION  "An entry in the 1hr interval statistics table.  Each
            conceptual row contains interval statistics for a par-
            ticular interval on a particular stream."
    INDEX        { ifIndex,
              nncFrStrStatIntervalNumber }
  ::= { nncFrStrStatIntervalTable 1 }


  NncFrStrStatIntervalEntry ::=
    SEQUENCE {
        nncFrStrStatIntervalNumber                      INTEGER,
        nncFrStrStatIntervalState                       NncExtIntvlStateType,
        nncFrStrStatIntervalAbsoluteIntervalNumber      INTEGER,
        nncFrStrStatIntervalInOctets                    NncExtCounter64,
        nncFrStrStatIntervalOutOctets                   NncExtCounter64,
        nncFrStrStatIntervalInUCastPackets              NncExtCounter64,
        nncFrStrStatIntervalOutUCastPackets             NncExtCounter64,
        nncFrStrStatIntervalInDiscards                  NncExtCounter64,
        nncFrStrStatIntervalOutDiscards                 NncExtCounter64,
        nncFrStrStatIntervalInErrors                    NncExtCounter64,
        nncFrStrStatIntervalOutErrors                   NncExtCounter64,
        nncFrStrStatIntervalSigUserProtErrors           NncExtCounter64,
        nncFrStrStatIntervalSigNetProtErrors            NncExtCounter64,
        nncFrStrStatIntervalSigUserLinkRelErrors        NncExtCounter64,
        nncFrStrStatIntervalSigNetLinkRelErrors         NncExtCounter64,
        nncFrStrStatIntervalSigUserChanInactive         NncExtCounter64,
        nncFrStrStatIntervalSigNetChanInactive          NncExtCounter64,
        nncFrStrStatIntervalStSCAlarms                  Counter32,
        nncFrStrStatIntervalStTimeSC                    Gauge32,
        nncFrStrStatIntervalStMaxDurationRED            Counter32,
        nncFrStrStatIntervalStMCAlarms                  Counter32,
        nncFrStrStatIntervalStTimeMC                    Gauge32,
        nncFrStrStatIntervalOutLinkUtilization          Gauge32(0..100),
        nncFrStrStatIntervalInLinkUtilization           Gauge32(0..100),
        nncFrStrStatIntervalInInvdLength                NncExtCounter64,
        nncFrStrStatIntervalStLastErroredDLCI           Integer32(0..8388607),
        nncFrStrStatIntervalInDiscdOctetsCOS            NncExtCounter64,
        nncFrStrStatIntervalInDiscdCOSDESet             NncExtCounter64,
        nncFrStrStatIntervalInDiscdCOSDEClr             NncExtCounter64,
        nncFrStrStatIntervalInDiscdBadEncaps            NncExtCounter64,
        nncFrStrStatIntervalOutDiscdBadEncaps           NncExtCounter64,
        nncFrStrStatIntervalInDiscdUnsupEncaps          NncExtCounter64,
        nncFrStrStatIntervalOutDiscdUnsupEncaps         NncExtCounter64,
        nncFrStrStatIntervalOutDiscdDESet               NncExtCounter64,
        nncFrStrStatIntervalOutDiscdDEClr               NncExtCounter64,
        nncFrStrStatIntervalInDiscdDESet                NncExtCounter64,
        nncFrStrStatIntervalInDiscdDEClr                NncExtCounter64,
        nncFrStrStatIntervalStLMSigInvldField           NncExtCounter64,
        nncFrStrStatIntervalStLMSigUnsupMsgType         NncExtCounter64,
        nncFrStrStatIntervalStLMSigInvldEID             NncExtCounter64,
        nncFrStrStatIntervalStLMSigInvldIELen           NncExtCounter64,
        nncFrStrStatIntervalStLMSigInvldRepType         NncExtCounter64,
        nncFrStrStatIntervalStLMSigFrmWithNoIEs         NncExtCounter64,
        nncFrStrStatIntervalStUserSequenceErrs          NncExtCounter64,
        nncFrStrStatIntervalStNetSequenceErrs           NncExtCounter64,
        nncFrStrStatIntervalStLMUTimeoutsnT1            NncExtCounter64,
        nncFrStrStatIntervalStLMUStatusMsgsRcvd         NncExtCounter64,
        nncFrStrStatIntervalStLMUStatusENQMsgsSent      NncExtCounter64,
        nncFrStrStatIntervalStLMUAsyncStatusRcvd        NncExtCounter64,
        nncFrStrStatIntervalStLMNTimeoutsnT2            NncExtCounter64,
        nncFrStrStatIntervalStLMNStatusMsgsSent         NncExtCounter64,
        nncFrStrStatIntervalStLMNStatusENQMsgsRcvd      NncExtCounter64,
        nncFrStrStatIntervalStLMNAsyncStatusSent        NncExtCounter64,
        nncFrStrStatIntervalInCRCErrors                 NncExtCounter64,
        nncFrStrStatIntervalInNonIntegral               NncExtCounter64,
        nncFrStrStatIntervalInReservedDLCI              NncExtCounter64,
        nncFrStrStatIntervalInInvldEA                   NncExtCounter64,
        nncFrStrStatIntervalStFrmTooSmall               NncExtCounter64,
        nncFrStrStatIntervalInAborts                    NncExtCounter64,
        nncFrStrStatIntervalInSumOfDisagremnts          NncExtCounter64,
        nncFrStrStatIntervalInOverRuns                  NncExtCounter64,
        nncFrStrStatIntervalOutUnderRuns                NncExtCounter64,
        nncFrStrStatIntervalStIntervalDuration          Integer32,
        nncFrStrStatIntervalBestEffortPeakDelay         Gauge32(1..60000),
        nncFrStrStatIntervalCommittedPeakDelay          Gauge32(1..60000),
        nncFrStrStatIntervalLowDelayPeakDelay           Gauge32(1..60000),
        nncFrStrStatIntervalRealTimePeakDelay           Gauge32(1..60000),
        nncFrStrStatIntervalBestEffortAccDelay          NncExtCounter64,
        nncFrStrStatIntervalCommittedAccDelay           NncExtCounter64,
        nncFrStrStatIntervalLowDelayAccDelay            NncExtCounter64,
        nncFrStrStatIntervalRealTimeAccDelay            NncExtCounter64,
        nncFrStrStatIntervalBestEffortOutUCastPackets   NncExtCounter64,
        nncFrStrStatIntervalCommittedOutUCastPackets    NncExtCounter64,
        nncFrStrStatIntervalLowDelayOutUCastPackets     NncExtCounter64,
        nncFrStrStatIntervalRealTimeOutUCastPackets     NncExtCounter64,
        nncFrStrStatIntervalBestEffortUCastPacketsDEClr NncExtCounter64,
        nncFrStrStatIntervalCommittedUCastPacketsDEClr  NncExtCounter64,
        nncFrStrStatIntervalLowDelayUCastPacketsDEClr   NncExtCounter64,
        nncFrStrStatIntervalRealTimeUCastPacketsDEClr   NncExtCounter64,
        nncFrStrStatIntervalBestEffortDiscdDEClr        NncExtCounter64,
        nncFrStrStatIntervalCommittedDiscdDEClr         NncExtCounter64,
        nncFrStrStatIntervalLowDelayDiscdDEClr          NncExtCounter64,
        nncFrStrStatIntervalRealTimeDiscdDEClr          NncExtCounter64
    }

  nncFrStrStatIntervalNumber            OBJECT-TYPE
    SYNTAX        INTEGER (1..96)
    MAX-ACCESS    not-accessible
    STATUS        current
    DESCRIPTION  "The interval number (N) of the statistics in this row."
  ::= { nncFrStrStatIntervalEntry 1 }


  nncFrStrStatIntervalState            OBJECT-TYPE
    SYNTAX        NncExtIntvlStateType
    MAX-ACCESS    read-only
    STATUS        current
    DESCRIPTION  "The state of the interval represented by this row. The
            object provides a status for those entries which have
            been reset by the user or subject to a wall-clock time
            change."
  ::= { nncFrStrStatIntervalEntry 2 }


  nncFrStrStatIntervalAbsoluteIntervalNumber    OBJECT-TYPE
    SYNTAX        INTEGER (0..96)
    MAX-ACCESS    not-accessible
    STATUS        current
    DESCRIPTION  "The absolute interval number of this interval."
  ::= { nncFrStrStatIntervalEntry 3 }


  nncFrStrStatIntervalInOctets            OBJECT-TYPE
    SYNTAX        NncExtCounter64
    MAX-ACCESS    read-only
    STATUS        current
    DESCRIPTION  "Number of bytes received on this stream."
  ::= { nncFrStrStatIntervalEntry 4 }


  nncFrStrStatIntervalOutOctets            OBJECT-TYPE
    SYNTAX        NncExtCounter64
    MAX-ACCESS    read-only
    STATUS        current
    DESCRIPTION  "Number of bytes transmitted on this stream."
  ::= { nncFrStrStatIntervalEntry 5 }


  nncFrStrStatIntervalInUCastPackets        OBJECT-TYPE
    SYNTAX        NncExtCounter64
    MAX-ACCESS    read-only
    STATUS        current
    DESCRIPTION  "Number of unerrored, unicast frames received." 
  ::= { nncFrStrStatIntervalEntry 6 }


  nncFrStrStatIntervalOutUCastPackets        OBJECT-TYPE
    SYNTAX        NncExtCounter64
    MAX-ACCESS    read-only
    STATUS        current
    DESCRIPTION  "Number of unerrored, unicast frames transmitted."
  ::= { nncFrStrStatIntervalEntry 7 }


  nncFrStrStatIntervalInDiscards        OBJECT-TYPE
    SYNTAX        NncExtCounter64
    MAX-ACCESS    read-only
    STATUS        current
    DESCRIPTION  "Number of incoming frames discarded due to these
            reasons: policing, congestion."
  ::= { nncFrStrStatIntervalEntry 8 }


  nncFrStrStatIntervalOutDiscards        OBJECT-TYPE
    SYNTAX        NncExtCounter64
    MAX-ACCESS    read-only
    STATUS        current
    DESCRIPTION  "Number of outgoing frames discarded due to these
            reasons: policing, congestion."
  ::= { nncFrStrStatIntervalEntry 9 }


  nncFrStrStatIntervalInErrors            OBJECT-TYPE
    SYNTAX        NncExtCounter64
    MAX-ACCESS    read-only
    STATUS        current
    DESCRIPTION  "Number of incoming frames discarded due to errors:
            eg. invalid lengths, non-integral bytes..."
  ::= { nncFrStrStatIntervalEntry 10 }


  nncFrStrStatIntervalOutErrors            OBJECT-TYPE
    SYNTAX        NncExtCounter64
    MAX-ACCESS    read-only
    STATUS        current
    DESCRIPTION  "Number of outgoing frames discarded due to errors:
            eg. bad encapsulation."
  ::= { nncFrStrStatIntervalEntry 11 }


  nncFrStrStatIntervalSigUserProtErrors        OBJECT-TYPE
    SYNTAX        NncExtCounter64
    MAX-ACCESS    read-only
    STATUS        current
    DESCRIPTION  "Number of user-side local in-channel signalling
            protocol errors (protocol discriminator, message type,
            call reference & mandatory information eleement errors)
            for this uni/nni stream.  If the stream is not perfor-
            ming user-side procedures, this value is equal to
            noSuchName."
  ::= { nncFrStrStatIntervalEntry 12 }


  nncFrStrStatIntervalSigNetProtErrors        OBJECT-TYPE
    SYNTAX        NncExtCounter64
    MAX-ACCESS    read-only
    STATUS        current
    DESCRIPTION  "Number of network-side local in-channel signalling
            protocol errors (protocol discriminator, message type,
            call reference & mandatory information eleement errors)
            for this uni/nni stream.  If the stream is not perfor-
            ming network-side procedures, this value is equal to
            noSuchName."
  ::= { nncFrStrStatIntervalEntry 13 }


  nncFrStrStatIntervalSigUserLinkRelErrors    OBJECT-TYPE
    SYNTAX        NncExtCounter64
    MAX-ACCESS    read-only
    STATUS        current
    DESCRIPTION  "Number of user-side local in-channel signalling link
            reliability errors (non receipt of Enq/Status messages
            or invalid sequence numbers in a link integrity verifi-
            cation information element) for this stream.  If the
            stream is not performing user-side procedures, this
            value is equal to noSuchName."
  ::= { nncFrStrStatIntervalEntry 14 }


  nncFrStrStatIntervalSigNetLinkRelErrors    OBJECT-TYPE
    SYNTAX        NncExtCounter64
    MAX-ACCESS    read-only
    STATUS        current
    DESCRIPTION  "Number of network-side local in-channel signalling
            link reliability errors (non receipt of Enq/Status
            messages or invalid sequence numbers in a link integrity
            verification information element) for this stream.  If
            the stream is not performing network-side procedures,
            this value is equal to noSuchName."
  ::= { nncFrStrStatIntervalEntry 15 }


  nncFrStrStatIntervalSigUserChanInactive    OBJECT-TYPE
    SYNTAX        NncExtCounter64
    MAX-ACCESS    read-only
    STATUS        current
    DESCRIPTION  "Number of times the user-side channel was declared
            inactive (N2 errors in N3 events) for this stream.  If
            the stream is not performing user-side procedures, this
            value is equal to noSuchName."
  ::= { nncFrStrStatIntervalEntry 16 }


  nncFrStrStatIntervalSigNetChanInactive    OBJECT-TYPE
    SYNTAX        NncExtCounter64
    MAX-ACCESS    read-only
    STATUS        current
    DESCRIPTION  "Number of times the network-side channel was declared
            inactive (N2 errors in N3 events) for this stream.  If
            the stream is not performing network-side procedures,
            this value is equal to noSuchName."
  ::= { nncFrStrStatIntervalEntry 17 }


  nncFrStrStatIntervalStSCAlarms OBJECT-TYPE
    SYNTAX        Counter32
    MAX-ACCESS    read-only
    STATUS        current
    DESCRIPTION  "Number of one second intervals for which the stream
            entered the severely congested state."
  ::= { nncFrStrStatIntervalEntry 18 }


  nncFrStrStatIntervalStTimeSC OBJECT-TYPE
    SYNTAX        Gauge32
    MAX-ACCESS    read-only
    STATUS        current
    DESCRIPTION  "Period of time the stream was in the severely congested state
            during the designated interval (expressed in 10's of milliseconds).
            Divide into the entire length of the interval to get a ratio."
  ::= { nncFrStrStatIntervalEntry 19 }


  nncFrStrStatIntervalStMaxDurationRED OBJECT-TYPE
    SYNTAX        Counter32
    MAX-ACCESS    read-only
    STATUS        current
    DESCRIPTION  "Longest period of time the stream spent in the Red (severely
            congested) state, expressed in seconds."
  ::= { nncFrStrStatIntervalEntry 20 }


  nncFrStrStatIntervalStMCAlarms OBJECT-TYPE
    SYNTAX        Counter32
    MAX-ACCESS    read-only
    STATUS        current
    DESCRIPTION  "Number of one second intervals for which the stream
            entered the mildly congested state."
  ::= { nncFrStrStatIntervalEntry 21 }


  nncFrStrStatIntervalStTimeMC OBJECT-TYPE
    SYNTAX        Gauge32
    MAX-ACCESS    read-only
    STATUS        current
    DESCRIPTION  "Period of time the stream was in the mildly congested state
            during the designated interval (expressed in 10's of milliseconds).
            Divide into the entire length of the interval to get a ratio."
  ::= { nncFrStrStatIntervalEntry 22 }


  nncFrStrStatIntervalOutLinkUtilization        OBJECT-TYPE
    SYNTAX        Gauge32(0..100)
    MAX-ACCESS    read-only
    STATUS        current
    DESCRIPTION  "The percentage utilization on the outgoing link
            during the designated interval."
  ::= { nncFrStrStatIntervalEntry 23 }


  nncFrStrStatIntervalInLinkUtilization        OBJECT-TYPE
    SYNTAX        Gauge32(0..100)
    MAX-ACCESS    read-only
    STATUS        current
    DESCRIPTION  "The percentage utilization on the incoming link
            during the designated interval."
  ::= { nncFrStrStatIntervalEntry 24 }


  nncFrStrStatIntervalInInvdLength OBJECT-TYPE
    SYNTAX        NncExtCounter64
    MAX-ACCESS    read-only
    STATUS        current
    DESCRIPTION  "Number of frames discarded because there was no data in
            the frame, or because the frame exceeded the maximum allowed
            length."
  ::= { nncFrStrStatIntervalEntry 25 }


  nncFrStrStatIntervalStLastErroredDLCI OBJECT-TYPE
    SYNTAX        Integer32(0..8388607)
    MAX-ACCESS    read-only
    STATUS        current
    DESCRIPTION  "DLCI of the most recent DLC to receive invalid frames
                 on this frame stream."
  ::= { nncFrStrStatIntervalEntry 26 }


  nncFrStrStatIntervalInDiscdOctetsCOS OBJECT-TYPE
    SYNTAX        NncExtCounter64
    MAX-ACCESS    read-only
    STATUS        current
    DESCRIPTION  "Number of ingress bytes discarded due to receive
            Class-of-Service procedures."
  ::= { nncFrStrStatIntervalEntry 27 }


  nncFrStrStatIntervalInDiscdCOSDESet OBJECT-TYPE
    SYNTAX        NncExtCounter64
    MAX-ACCESS    read-only
    STATUS        current
    DESCRIPTION  "Number of ingress frames discarded due to receive
            Class-of-Service procedures, in which the DE bit was set."
  ::= { nncFrStrStatIntervalEntry 28 }


  nncFrStrStatIntervalInDiscdCOSDEClr OBJECT-TYPE
    SYNTAX        NncExtCounter64
    MAX-ACCESS    read-only
    STATUS        current
    DESCRIPTION  "Number of ingress frames discarded due to receive
            Class-of-Service procedures, in which the DE bit was not set."
  ::= { nncFrStrStatIntervalEntry 29 }


  nncFrStrStatIntervalInDiscdBadEncaps        OBJECT-TYPE
    SYNTAX        NncExtCounter64
    MAX-ACCESS    read-only
    STATUS        current
    DESCRIPTION  "Number of ingress frames discarded due to having a bad
            RFC1490 encapsulation header."
  ::= { nncFrStrStatIntervalEntry 30 }


  nncFrStrStatIntervalOutDiscdBadEncaps        OBJECT-TYPE
    SYNTAX        NncExtCounter64
    MAX-ACCESS    read-only
    STATUS        current
    DESCRIPTION  "Number of egress frames discarded due to having a bad
            RFC1483 encapsulation header."
  ::= { nncFrStrStatIntervalEntry 31 }


  nncFrStrStatIntervalInDiscdUnsupEncaps        OBJECT-TYPE
    SYNTAX        NncExtCounter64
    MAX-ACCESS    read-only
    STATUS        current
    DESCRIPTION  "Number of ingress frames discarded due to having an
            unsupported RFC1490 encapsulation header."
  ::= { nncFrStrStatIntervalEntry 32 }


  nncFrStrStatIntervalOutDiscdUnsupEncaps        OBJECT-TYPE
    SYNTAX        NncExtCounter64
    MAX-ACCESS    read-only
    STATUS        current
    DESCRIPTION  "Number of egress frames discarded due to having an
            unsupported RFC1483 encapsulation header."
  ::= { nncFrStrStatIntervalEntry 33 }


  nncFrStrStatIntervalOutDiscdDESet OBJECT-TYPE
    SYNTAX        NncExtCounter64
    MAX-ACCESS    read-only
    STATUS        current
    DESCRIPTION  "Number of egress frames discarded due to transmit
            congestion procedures, in which the DE bit was set."
  ::= { nncFrStrStatIntervalEntry 34 }


  nncFrStrStatIntervalOutDiscdDEClr OBJECT-TYPE
    SYNTAX        NncExtCounter64
    MAX-ACCESS    read-only
    STATUS        current
    DESCRIPTION  "Number of egress frames discarded due to transmit
            congestion procedures, in which the DE bit was not set."
  ::= { nncFrStrStatIntervalEntry 35 }


  nncFrStrStatIntervalInDiscdDESet OBJECT-TYPE
    SYNTAX        NncExtCounter64
    MAX-ACCESS    read-only
    STATUS        current
    DESCRIPTION  "Number of ingress frames discarded due to receive
            congestion procedures, in which the DE bit was set."
  ::= { nncFrStrStatIntervalEntry 36 }


  nncFrStrStatIntervalInDiscdDEClr OBJECT-TYPE
    SYNTAX        NncExtCounter64
    MAX-ACCESS    read-only
    STATUS        current
    DESCRIPTION  "Number of ingress frames discarded due to receive
            congestion procedures, in which the DE bit was not set."
  ::= { nncFrStrStatIntervalEntry 37 }


  nncFrStrStatIntervalStLMSigInvldField        OBJECT-TYPE
    SYNTAX        NncExtCounter64
    MAX-ACCESS    read-only
    STATUS        current
    DESCRIPTION  "Number of Status signalling frames with incorrect values
            for the Unnumbered Information Frame field, Protocol Discriminator
            field, or Call Reference Field."
  ::= { nncFrStrStatIntervalEntry 38 }


  nncFrStrStatIntervalStLMSigUnsupMsgType        OBJECT-TYPE
    SYNTAX        NncExtCounter64
    MAX-ACCESS    read-only
    STATUS        current
    DESCRIPTION  "Number of Status signalling frames that are not a Status
            or Status Enquiry messsage (Unsupported message type)."
  ::= { nncFrStrStatIntervalEntry 39 }


  nncFrStrStatIntervalStLMSigInvldEID        OBJECT-TYPE
    SYNTAX        NncExtCounter64
    MAX-ACCESS    read-only
    STATUS        current
    DESCRIPTION  "Number of Status signalling frames with an IEID that is
            not a Report Type IEID, Keep Alive Sequence IEID, or a PVC
            Status IEID."
  ::= { nncFrStrStatIntervalEntry 40 }


  nncFrStrStatIntervalStLMSigInvldIELen        OBJECT-TYPE
    SYNTAX        NncExtCounter64
    MAX-ACCESS    read-only
    STATUS        current
    DESCRIPTION  "Number of Status signalling frames with an IE length
            field size that does not conform with the Frame Relay status
            signalling protocol."
  ::= { nncFrStrStatIntervalEntry 41 }


  nncFrStrStatIntervalStLMSigInvldRepType        OBJECT-TYPE
    SYNTAX        NncExtCounter64
    MAX-ACCESS    read-only
    STATUS        current
    DESCRIPTION  "Number of Status signalling frames with a Report Type
            IE that were not a Full Report Type or a Keep Alive Confirmation."
  ::= { nncFrStrStatIntervalEntry 42 }


  nncFrStrStatIntervalStLMSigFrmWithNoIEs        OBJECT-TYPE
    SYNTAX        NncExtCounter64
    MAX-ACCESS    read-only
    STATUS        current
    DESCRIPTION  "Number of Status signalling frames that terminate before
            the IE appears."
  ::= { nncFrStrStatIntervalEntry 43 }


  nncFrStrStatIntervalStUserSequenceErrs        OBJECT-TYPE
    SYNTAX        NncExtCounter64
    MAX-ACCESS    read-only
    STATUS        current
    DESCRIPTION  "Number of status signalling frames received with a Last
            Received Sequence number that is inconsistent with the expected
            value, the last transmitted Interval Sequence Number.
            If the stream is not performing user-side procedures,
            this value is equal to noSuchName."
  ::= { nncFrStrStatIntervalEntry 44 }


  nncFrStrStatIntervalStNetSequenceErrs        OBJECT-TYPE
    SYNTAX        NncExtCounter64
    MAX-ACCESS    read-only
    STATUS        current
    DESCRIPTION  "Number of status signalling frames received with a
            Last Received Sequence number that is inconsistent with the
            expected value, the last transmitted Interval Sequence Number.
            If the stream is not performing network-side procedures,
            this value is equal to noSuchName."
  ::= { nncFrStrStatIntervalEntry 45 }


  nncFrStrStatIntervalStLMUTimeoutsnT1 OBJECT-TYPE
    SYNTAX        NncExtCounter64
    MAX-ACCESS    read-only
    STATUS        current
    DESCRIPTION  "Number of times the link integrity verification interval
            has been exceeded without receiving a Status message.
            If the stream is not performing user-side procedures,
            this value is equal to noSuchName."
  ::= { nncFrStrStatIntervalEntry 46 }


  nncFrStrStatIntervalStLMUStatusMsgsRcvd OBJECT-TYPE
    SYNTAX        NncExtCounter64
    MAX-ACCESS    read-only
    STATUS        current
    DESCRIPTION  "Number of Status messages received.
            If the stream is not performing user-side procedures,
            this value is equal to noSuchName."
  ::= { nncFrStrStatIntervalEntry 47 }


  nncFrStrStatIntervalStLMUStatusENQMsgsSent OBJECT-TYPE
    SYNTAX        NncExtCounter64
    MAX-ACCESS    read-only
    STATUS        current
    DESCRIPTION  "Number of Status Enquiry messages sent.
            If the stream is not performing user-side procedures,
            this value is equal to noSuchName."
  ::= { nncFrStrStatIntervalEntry 48 }


  nncFrStrStatIntervalStLMUAsyncStatusRcvd OBJECT-TYPE
    SYNTAX        NncExtCounter64
    MAX-ACCESS    read-only
    STATUS        current
    DESCRIPTION  "Number of asynchronous Update Status messages received.
            If the stream is not performing user-side procedures,
            this value is equal to noSuchName."
  ::= { nncFrStrStatIntervalEntry 49 }


  nncFrStrStatIntervalStLMNTimeoutsnT2 OBJECT-TYPE
    SYNTAX        NncExtCounter64
    MAX-ACCESS    read-only
    STATUS        current
    DESCRIPTION  "Number of times the polling verification interval was
            exceeded without receivung a Keep Alive Sequence.
            If the stream is not performing network-side procedures,
            this value is equal to noSuchName."
  ::= { nncFrStrStatIntervalEntry 50 }


  nncFrStrStatIntervalStLMNStatusMsgsSent OBJECT-TYPE
    SYNTAX        NncExtCounter64
    MAX-ACCESS    read-only
    STATUS        current
    DESCRIPTION  "Number of Status messages sent.
            If the stream is not performing network-side procedures,
            this value is equal to noSuchName."
  ::= { nncFrStrStatIntervalEntry 51 }


  nncFrStrStatIntervalStLMNStatusENQMsgsRcvd OBJECT-TYPE
    SYNTAX        NncExtCounter64
    MAX-ACCESS    read-only
    STATUS        current
    DESCRIPTION  "Number of Status Enquiry messages received.
            If the stream is not performing network-side procedures,
            this value is equal to noSuchName."
  ::= { nncFrStrStatIntervalEntry 52 }


  nncFrStrStatIntervalStLMNAsyncStatusSent OBJECT-TYPE
    SYNTAX        NncExtCounter64
    MAX-ACCESS    read-only
    STATUS        current
    DESCRIPTION  "Number of asynchronous Update Status messages transmitted.
            If the stream is not performing network-side procedures,
            this value is equal to noSuchName."
  ::= { nncFrStrStatIntervalEntry 53 }


  nncFrStrStatIntervalInCRCErrors OBJECT-TYPE
    SYNTAX        NncExtCounter64
    MAX-ACCESS    read-only
    STATUS        current
    DESCRIPTION  "Number of frames with an incorrect CRC-16 value."
  ::= { nncFrStrStatIntervalEntry 54 }


  nncFrStrStatIntervalInNonIntegral        OBJECT-TYPE
    SYNTAX        NncExtCounter64
    MAX-ACCESS    read-only
    STATUS        current
    DESCRIPTION  "Number of frames with a non-integral number of
            octets between the delimiting HDLC flags."
  ::= { nncFrStrStatIntervalEntry 55 }


  nncFrStrStatIntervalInReservedDLCI        OBJECT-TYPE
    SYNTAX        NncExtCounter64
    MAX-ACCESS    read-only
    STATUS        current
    DESCRIPTION  "Number of frames with a DLCI that cannot be assigned
            to user connections."
  ::= { nncFrStrStatIntervalEntry 56 }


  nncFrStrStatIntervalInInvldEA        OBJECT-TYPE
    SYNTAX        NncExtCounter64
    MAX-ACCESS    read-only
    STATUS        current
    DESCRIPTION  "Number of frames with the EA (extended address) bit
            incorrectly set."
  ::= { nncFrStrStatIntervalEntry 57 }


  nncFrStrStatIntervalStFrmTooSmall        OBJECT-TYPE
    SYNTAX        NncExtCounter64
    MAX-ACCESS    read-only
    STATUS        current
    DESCRIPTION  "Number of frames that are smaller than the allowed
            minimum size."
  ::= { nncFrStrStatIntervalEntry 58 }


  nncFrStrStatIntervalInAborts        OBJECT-TYPE
    SYNTAX        NncExtCounter64
    MAX-ACCESS    read-only
    STATUS        current
    DESCRIPTION  "Number of aborted frames."
  ::= { nncFrStrStatIntervalEntry 59 }


  nncFrStrStatIntervalInSumOfDisagremnts        OBJECT-TYPE
    SYNTAX        NncExtCounter64
    MAX-ACCESS    read-only
    STATUS        current
    DESCRIPTION  "Total number of frames discarded because: the
            frame relay UNI or ICI was unavailable to accept frame
            traffic, the frame had a DLCI not available for end-user
            connections, the DLCI was inactive, the frame exceeded
            the maximum configured frame length (but its length was
            legal within the frame relay protocol), the frame violated
            the configured address field size (but had a legal address
            field size with the frame relay protocol), or was an
            unexpected status signalling frame."
  ::= { nncFrStrStatIntervalEntry 60 }


  nncFrStrStatIntervalInOverRuns        OBJECT-TYPE
    SYNTAX        NncExtCounter64
    MAX-ACCESS    read-only
    STATUS        current
    DESCRIPTION  "Number of times the receiver was forced to overrun."
  ::= { nncFrStrStatIntervalEntry 61 }


  nncFrStrStatIntervalOutUnderRuns        OBJECT-TYPE
    SYNTAX        NncExtCounter64
    MAX-ACCESS    read-only
    STATUS        current
    DESCRIPTION  "Number of times the transmitter was forced to underrun."
  ::= { nncFrStrStatIntervalEntry 62 }


  nncFrStrStatIntervalStIntervalDuration OBJECT-TYPE
    SYNTAX        Integer32
    MAX-ACCESS    read-only
    STATUS        current
    DESCRIPTION  "Duration of the statistics accumulation interval."
  ::= { nncFrStrStatIntervalEntry 63 }


  nncFrStrStatIntervalBestEffortPeakDelay OBJECT-TYPE
    SYNTAX        Gauge32(1..60000)
    MAX-ACCESS    read-only
    STATUS        current
    DESCRIPTION  "The largest delay experienced by any frame that was
            transmitted on the stream in service category Best Effort."
  ::= { nncFrStrStatIntervalEntry 64 }


  nncFrStrStatIntervalCommittedPeakDelay OBJECT-TYPE
    SYNTAX        Gauge32(1..60000)
    MAX-ACCESS    read-only
    STATUS        current
    DESCRIPTION  "The largest delay experienced by any frame that was
            transmitted on the stream in service category: Committed
            Throughptut."
  ::= { nncFrStrStatIntervalEntry 65 }


  nncFrStrStatIntervalLowDelayPeakDelay OBJECT-TYPE
    SYNTAX        Gauge32(1..60000)
    MAX-ACCESS    read-only
    STATUS        current
    DESCRIPTION  "The largest delay experienced by any frame that was
            transmitted on the stream in service category: Low Delay."
  ::= { nncFrStrStatIntervalEntry 66 }


  nncFrStrStatIntervalRealTimePeakDelay OBJECT-TYPE
    SYNTAX        Gauge32(1..60000)
    MAX-ACCESS    read-only
    STATUS        current
    DESCRIPTION  "The largest delay experienced by any frame that was
            transmitted on the stream in service category Real Time."
  ::= { nncFrStrStatIntervalEntry 67 }


  nncFrStrStatIntervalBestEffortAccDelay OBJECT-TYPE
    SYNTAX        NncExtCounter64
    MAX-ACCESS    read-only
    STATUS        current
    DESCRIPTION  "The accumulated delay experienced by all frames in a
            stream transmitted in service category Best Effort.  Combined
            with the Out Ucast Packets for service category Best Effort,
            the average delay per frame can be calculated."
  ::= { nncFrStrStatIntervalEntry 68 }


  nncFrStrStatIntervalCommittedAccDelay OBJECT-TYPE
    SYNTAX        NncExtCounter64
    MAX-ACCESS    read-only
    STATUS        current
    DESCRIPTION  "The accumulated delay experienced by all frames in a
            stream transmitted in service category Committed Throughput.
            Combined with the Out Ucast Packets for service category
            Committed Throughput, the average delay per frame can be
            calculated."
  ::= { nncFrStrStatIntervalEntry 69 }

  nncFrStrStatIntervalLowDelayAccDelay OBJECT-TYPE
    SYNTAX        NncExtCounter64
    MAX-ACCESS    read-only
    STATUS        current
    DESCRIPTION  "The accumulated delay experienced by all frames in a
            stream transmitted in service category Low Delay.
            Combined with the Out Ucast Packets for service category
            Low Delay, the average delay per frame can be calculated."
  ::= { nncFrStrStatIntervalEntry 70 }

  nncFrStrStatIntervalRealTimeAccDelay OBJECT-TYPE
    SYNTAX        NncExtCounter64
    MAX-ACCESS    read-only
    STATUS        current
    DESCRIPTION  "The accumulated delay experienced by all frames in a
            stream transmitted in service category Real Time.
            Combined with the Out Ucast Packets for service category
            Real Time, the average delay per frame can be calculated."
  ::= { nncFrStrStatIntervalEntry 71 }

  nncFrStrStatIntervalBestEffortOutUCastPackets OBJECT-TYPE
    SYNTAX        NncExtCounter64
    MAX-ACCESS    read-only
    STATUS        current
    DESCRIPTION  "Number of unerrored, unicast frames transmitted in
            service category Best Effort."
  ::= { nncFrStrStatIntervalEntry 72 }


  nncFrStrStatIntervalCommittedOutUCastPackets OBJECT-TYPE
    SYNTAX        NncExtCounter64
    MAX-ACCESS    read-only
    STATUS        current
    DESCRIPTION  "Number of unerrored, unicast frames transmitted in
            service category Committed Throughput."
  ::= { nncFrStrStatIntervalEntry 73 }


  nncFrStrStatIntervalLowDelayOutUCastPackets OBJECT-TYPE
    SYNTAX        NncExtCounter64
    MAX-ACCESS    read-only
    STATUS        current
    DESCRIPTION  "Number of unerrored, unicast frames transmitted in
            service category Low Delay."
  ::= { nncFrStrStatIntervalEntry 74 }


  nncFrStrStatIntervalRealTimeOutUCastPackets OBJECT-TYPE
    SYNTAX        NncExtCounter64
    MAX-ACCESS    read-only
    STATUS        current
    DESCRIPTION  "Number of unerrored, unicast frames transmitted in
            service category Real Time."
  ::= { nncFrStrStatIntervalEntry 75 }


  nncFrStrStatIntervalBestEffortUCastPacketsDEClr OBJECT-TYPE
    SYNTAX        NncExtCounter64
    MAX-ACCESS    read-only
    STATUS        current
    DESCRIPTION  "Number of unerrored, unicast frames with the DE
            bit not set transmitted in service category Best Effort."
  ::= { nncFrStrStatIntervalEntry 76 }


  nncFrStrStatIntervalCommittedUCastPacketsDEClr OBJECT-TYPE
    SYNTAX        NncExtCounter64
    MAX-ACCESS    read-only
    STATUS        current
    DESCRIPTION  "Number of unerrored, unicast frames with the DE
            bit not set transmitted in service category Committed
            Throughput."
  ::= { nncFrStrStatIntervalEntry 77 }


  nncFrStrStatIntervalLowDelayUCastPacketsDEClr OBJECT-TYPE
    SYNTAX        NncExtCounter64
    MAX-ACCESS    read-only
    STATUS        current
    DESCRIPTION  "Number of unerrored, unicast frames with the DE
            bit not set transmitted in service category Low Delay."
  ::= { nncFrStrStatIntervalEntry 78 }


  nncFrStrStatIntervalRealTimeUCastPacketsDEClr OBJECT-TYPE
    SYNTAX        NncExtCounter64
    MAX-ACCESS    read-only
    STATUS        current
    DESCRIPTION  "Number of unerrored, unicast frames with the DE
            bit not set, transmitted in service category Real Time."
  ::= { nncFrStrStatIntervalEntry 79 }


  nncFrStrStatIntervalBestEffortDiscdDEClr OBJECT-TYPE
    SYNTAX        NncExtCounter64
    MAX-ACCESS    read-only
    STATUS        current
    DESCRIPTION  "Number of unerrored, unicast frames with the DE bit
            not set, discarded by QoS procedures in service category
            Best Effort."
  ::= { nncFrStrStatIntervalEntry 80 }

  nncFrStrStatIntervalCommittedDiscdDEClr OBJECT-TYPE
    SYNTAX        NncExtCounter64
    MAX-ACCESS    read-only
    STATUS        current
    DESCRIPTION  "Number of unerrored, unicast frames with the DE bit
            not set, discarded by QoS procedures in service category
            Committed Throughput."
  ::= { nncFrStrStatIntervalEntry 81 }

  nncFrStrStatIntervalLowDelayDiscdDEClr OBJECT-TYPE
    SYNTAX        NncExtCounter64
    MAX-ACCESS    read-only
    STATUS        current
    DESCRIPTION  "Number of unerrored, unicast frames with the DE bit
            not set, discarded by QoS procedures in service category
            Low Delay."
  ::= { nncFrStrStatIntervalEntry 82 }

  nncFrStrStatIntervalRealTimeDiscdDEClr OBJECT-TYPE
    SYNTAX        NncExtCounter64
    MAX-ACCESS    read-only
    STATUS        current
    DESCRIPTION  "Number of unerrored, unicast frames with the DE bit
            not set, discarded by QoS procedures in service category
            Real Time."
  ::= { nncFrStrStatIntervalEntry 83 }



--------------------------------------------------------------------------------
-- nncFrIntStatisticsObject 3: Endpoint Stats Current Table
--------------------------------------------------------------------------------

  nncFrPVCEndptStatCurrentTable            OBJECT-TYPE
    SYNTAX        SEQUENCE OF NncFrPVCEndptStatCurrentEntry
    MAX-ACCESS    not-accessible
    STATUS        current
    DESCRIPTION  "The nncFrPVCEndptStatCurrentTable contains objects for
            monitoring performance of a frame relay endpoint during
            the current 1hr interval."
  ::= { nncFrIntStatisticsObjects 3 }


  nncFrPVCEndptStatCurrentEntry            OBJECT-TYPE
    SYNTAX        NncFrPVCEndptStatCurrentEntry
    MAX-ACCESS    not-accessible
    STATUS        current
    DESCRIPTION  "An entry in the 1hr current statistics table.  Each
            conceptual row contains current interval statistics for
            a particular PVC Endpoint."
    INDEX        { ifIndex,
              nncFrPVCEndptStatCurrentDLCINumber }
  ::= { nncFrPVCEndptStatCurrentTable 1 }


  NncFrPVCEndptStatCurrentEntry ::=
    SEQUENCE {
        nncFrPVCEndptStatCurrentDLCINumber               INTEGER,
        nncFrPVCEndptStatCurrentState                    NncExtIntvlStateType,
        nncFrPVCEndptStatCurrentAbsoluteIntervalNumber   INTEGER,
        nncFrPVCEndptStatCurrentInFrames                 NncExtCounter64,
        nncFrPVCEndptStatCurrentOutFrames                NncExtCounter64,
        nncFrPVCEndptStatCurrentInOctets                 NncExtCounter64,
        nncFrPVCEndptStatCurrentOutOctets                NncExtCounter64,
        nncFrPVCEndptStatCurrentInDiscards               NncExtCounter64,
        nncFrPVCEndptStatCurrentOutExcessFrames          NncExtCounter64,
        nncFrPVCEndptStatCurrentInDEFrames               NncExtCounter64,
        nncFrPVCEndptStatCurrentInCosTagDeFrames         NncExtCounter64,
        nncFrPVCEndptStatCurrentInOctetsDESet            NncExtCounter64,
        nncFrPVCEndptStatCurrentInFramesBECNSet          NncExtCounter64,
        nncFrPVCEndptStatCurrentInFramesFECNSet          NncExtCounter64,
        nncFrPVCEndptStatCurrentInInvdLength             NncExtCounter64,
        nncFrPVCEndptStatCurrentOutOctetsDESet           NncExtCounter64,
        nncFrPVCEndptStatCurrentOutFramesBECNSet         NncExtCounter64,
        nncFrPVCEndptStatCurrentOutFramesFECNSet         NncExtCounter64,
        nncFrPVCEndptStatCurrentOutFramesInRed           NncExtCounter64,
        nncFrPVCEndptStatCurrentInDiscdOctetsCOS         NncExtCounter64,
        nncFrPVCEndptStatCurrentInDiscdDESet             NncExtCounter64,
        nncFrPVCEndptStatCurrentInDiscdDEClr             NncExtCounter64,
        nncFrPVCEndptStatCurrentInDiscdBadEncaps         NncExtCounter64,
        nncFrPVCEndptStatCurrentInDiscdUnsupEncaps       NncExtCounter64,
        nncFrPVCEndptStatCurrentInDiscdCOSDESet          NncExtCounter64,
        nncFrPVCEndptStatCurrentInDiscdCOSDEClr          NncExtCounter64,
        nncFrPVCEndptStatCurrentOutDiscdDESet            NncExtCounter64,
        nncFrPVCEndptStatCurrentOutDiscdDEClr            NncExtCounter64,
        nncFrPVCEndptStatCurrentOutDiscdBadEncaps        NncExtCounter64,
        nncFrPVCEndptStatCurrentOutDiscdUnsupEncaps      NncExtCounter64,
        nncFrPVCEndptStatCurrentStReasDiscards           NncExtCounter64
    }


  nncFrPVCEndptStatCurrentDLCINumber        OBJECT-TYPE
    SYNTAX        INTEGER (0..1024)
    MAX-ACCESS    not-accessible
    STATUS        current
    DESCRIPTION  "The DLCI number of the stream to which statistics in
            this row belong."
  ::= { nncFrPVCEndptStatCurrentEntry 1 }


  nncFrPVCEndptStatCurrentState            OBJECT-TYPE
    SYNTAX        NncExtIntvlStateType
    MAX-ACCESS    read-only
    STATUS        current
    DESCRIPTION  "The state of the current interval. The object provides
            a status for those entries which have been reset by the
            user or have been subject to a wall-clock time change."
  ::= { nncFrPVCEndptStatCurrentEntry 2 }


  nncFrPVCEndptStatCurrentAbsoluteIntervalNumber    OBJECT-TYPE
    SYNTAX        INTEGER (0..96)
    MAX-ACCESS    not-accessible
    STATUS        current
    DESCRIPTION  "The absolute interval number of this interval."
  ::= { nncFrPVCEndptStatCurrentEntry 3 }


  nncFrPVCEndptStatCurrentInFrames        OBJECT-TYPE
    SYNTAX        NncExtCounter64
    MAX-ACCESS    read-only
    STATUS        current
    DESCRIPTION  "Number of frames received on this PVC Endpoint."
  ::= { nncFrPVCEndptStatCurrentEntry 4 }


  nncFrPVCEndptStatCurrentOutFrames        OBJECT-TYPE
    SYNTAX        NncExtCounter64
    MAX-ACCESS    read-only
    STATUS        current
    DESCRIPTION  "Number of frames transmitted on this PVC Endpoint."
  ::= { nncFrPVCEndptStatCurrentEntry 5 }


  nncFrPVCEndptStatCurrentInOctets        OBJECT-TYPE
    SYNTAX        NncExtCounter64
    MAX-ACCESS    read-only
    STATUS        current
    DESCRIPTION  "Number of bytes received on this PVC Endpoint."
  ::= { nncFrPVCEndptStatCurrentEntry 6 }


  nncFrPVCEndptStatCurrentOutOctets        OBJECT-TYPE
    SYNTAX        NncExtCounter64
    MAX-ACCESS    read-only
    STATUS        current
    DESCRIPTION  "Number of bytes transmitted on this PVC Endpoint."
  ::= { nncFrPVCEndptStatCurrentEntry 7 }


  nncFrPVCEndptStatCurrentInDiscards        OBJECT-TYPE
    SYNTAX        NncExtCounter64
    MAX-ACCESS    read-only
    STATUS        current
    DESCRIPTION  "Number of frames received by the network (ingress)
            that were discarded due to traffic enforcement for this
            PVC Endpoint." 
  ::= { nncFrPVCEndptStatCurrentEntry 8 }


  nncFrPVCEndptStatCurrentOutExcessFrames    OBJECT-TYPE
    SYNTAX        NncExtCounter64
    MAX-ACCESS    read-only
    STATUS        current
    DESCRIPTION  "Number of frames transmitted by the network (egress)
            for this PVC Endpoint that were treated as excess
            traffic (the DE bit may be set to one)."
  ::= { nncFrPVCEndptStatCurrentEntry 9 }


  nncFrPVCEndptStatCurrentInDEFrames        OBJECT-TYPE
    SYNTAX        NncExtCounter64
    MAX-ACCESS    read-only
    STATUS        current
    DESCRIPTION  "Number of frames received by the network (ingress)
            with the DE bit set to (1) for the PVC Endpoint."
  ::= { nncFrPVCEndptStatCurrentEntry 10 }


  nncFrPVCEndptStatCurrentInCosTagDeFrames OBJECT-TYPE
    SYNTAX      NncExtCounter64
    MAX-ACCESS  read-only
    STATUS      current
    DESCRIPTION "Number of frames received by the network (ingress)
            for this PVC Endpoint that were policed from normal
            to excess traffic (the DE bit was set to one) and transmitted."
  ::= { nncFrPVCEndptStatCurrentEntry 11 }


  nncFrPVCEndptStatCurrentInOctetsDESet OBJECT-TYPE
    SYNTAX      NncExtCounter64
    MAX-ACCESS  read-only
    STATUS      current
    DESCRIPTION  "Number of bytes received on this PVC Endpoint with the
            DE bit set."
  ::= { nncFrPVCEndptStatCurrentEntry 12 }


  nncFrPVCEndptStatCurrentInFramesBECNSet OBJECT-TYPE
    SYNTAX      NncExtCounter64
    MAX-ACCESS  read-only
    STATUS      current
    DESCRIPTION "Number of frames received by the network (ingress)
            for this PVC Endpoint that had the BECN bit set."
  ::= { nncFrPVCEndptStatCurrentEntry 13 }


  nncFrPVCEndptStatCurrentInFramesFECNSet OBJECT-TYPE
    SYNTAX      NncExtCounter64
    MAX-ACCESS  read-only
    STATUS      current
    DESCRIPTION "Number of frames received by the network (ingress)
            for this PVC Endpoint that had the FECN bit set."
  ::= { nncFrPVCEndptStatCurrentEntry 14 }


  nncFrPVCEndptStatCurrentInInvdLength OBJECT-TYPE
    SYNTAX      NncExtCounter64
    MAX-ACCESS  read-only
    STATUS      current
    DESCRIPTION "Number of frames received by the network (ingress)
            for this PVC Endpoint that were discarded because the frame
            had no data, or the data exceeded the maximum allowed length."
  ::= { nncFrPVCEndptStatCurrentEntry 15 }


  nncFrPVCEndptStatCurrentOutOctetsDESet OBJECT-TYPE
    SYNTAX      NncExtCounter64
    MAX-ACCESS  read-only
    STATUS      current
    DESCRIPTION  "Number of bytes transmitted on this PVC Endpoint with the
            DE bit set."
  ::= { nncFrPVCEndptStatCurrentEntry 16 }


  nncFrPVCEndptStatCurrentOutFramesBECNSet OBJECT-TYPE
    SYNTAX      NncExtCounter64
    MAX-ACCESS  read-only
    STATUS      current
    DESCRIPTION "Number of frames transmitted by the network (egress)
            for this PVC Endpoint that had the BECN bit set."
  ::= { nncFrPVCEndptStatCurrentEntry 17 }


  nncFrPVCEndptStatCurrentOutFramesFECNSet OBJECT-TYPE
    SYNTAX      NncExtCounter64
    MAX-ACCESS  read-only
    STATUS      current
    DESCRIPTION "Number of frames transmitted by the network (egress)
            for this PVC Endpoint that had the FECN bit set."
  ::= { nncFrPVCEndptStatCurrentEntry 18 }


  nncFrPVCEndptStatCurrentOutFramesInRed OBJECT-TYPE
    SYNTAX      NncExtCounter64
    MAX-ACCESS  read-only
    STATUS      current
    DESCRIPTION "Number of frames transmitted by the network (egress)
            for this PVC Endpoint when the frame stream was in Red State."
  ::= { nncFrPVCEndptStatCurrentEntry 19 }


  nncFrPVCEndptStatCurrentInDiscdOctetsCOS OBJECT-TYPE
    SYNTAX      NncExtCounter64
    MAX-ACCESS  read-only
    STATUS      current
    DESCRIPTION "Number of bytes discarded because of receive class-of-service
            enforcement on the PVC Endpoint."
  ::= { nncFrPVCEndptStatCurrentEntry 20 }


  nncFrPVCEndptStatCurrentInDiscdDESet OBJECT-TYPE
    SYNTAX      NncExtCounter64
    MAX-ACCESS  read-only
    STATUS      current
    DESCRIPTION "Number of frames discarded because of receive congestion
            procedures, in which the DE bit was set."
  ::= { nncFrPVCEndptStatCurrentEntry 21 }


  nncFrPVCEndptStatCurrentInDiscdDEClr OBJECT-TYPE
    SYNTAX      NncExtCounter64
    MAX-ACCESS  read-only
    STATUS      current
    DESCRIPTION "Number of frames discarded because of receive congestion
            procedures, in which the DE bit was not set."
  ::= { nncFrPVCEndptStatCurrentEntry 22 }


  nncFrPVCEndptStatCurrentInDiscdBadEncaps OBJECT-TYPE
    SYNTAX      NncExtCounter64
    MAX-ACCESS  read-only
    STATUS      current
    DESCRIPTION "Number of frames discarded on this PVC Endpoint because of 
            a bad receive RFC1490 encapsulation header."
  ::= { nncFrPVCEndptStatCurrentEntry 23 }


  nncFrPVCEndptStatCurrentInDiscdUnsupEncaps OBJECT-TYPE
    SYNTAX      NncExtCounter64
    MAX-ACCESS  read-only
    STATUS      current
    DESCRIPTION "Number of frames discarded on this PVC Endpoint because of 
            an unsupported receive RFC1490 encapsulation header."
  ::= { nncFrPVCEndptStatCurrentEntry 24 }


  nncFrPVCEndptStatCurrentInDiscdCOSDESet OBJECT-TYPE
    SYNTAX      NncExtCounter64
    MAX-ACCESS  read-only
    STATUS      current
    DESCRIPTION "Number of frames discarded due to receive class of service
            procedures, in which the DE bit was set."
  ::= { nncFrPVCEndptStatCurrentEntry 25 }


  nncFrPVCEndptStatCurrentInDiscdCOSDEClr OBJECT-TYPE
    SYNTAX      NncExtCounter64
    MAX-ACCESS  read-only
    STATUS      current
    DESCRIPTION "Number of frames discarded for the PVC Endpoint due to
            receive class of service procedures, in which the DE bit was
            not set."
  ::= { nncFrPVCEndptStatCurrentEntry 26 }


  nncFrPVCEndptStatCurrentOutDiscdDESet OBJECT-TYPE
    SYNTAX      NncExtCounter64
    MAX-ACCESS  read-only
    STATUS      current
    DESCRIPTION "Number of frames discarded for the PVC Endpoint due to
            transmit congestion procedures, in which the DE bit was set."
  ::= { nncFrPVCEndptStatCurrentEntry 27 }


  nncFrPVCEndptStatCurrentOutDiscdDEClr OBJECT-TYPE
    SYNTAX      NncExtCounter64
    MAX-ACCESS  read-only
    STATUS      current
    DESCRIPTION "Number of frames discarded for the PVC Endpoint due to
            transmit congestion procedures, in which the DE bit was not set."
  ::= { nncFrPVCEndptStatCurrentEntry 28 }


  nncFrPVCEndptStatCurrentOutDiscdBadEncaps OBJECT-TYPE
    SYNTAX      NncExtCounter64
    MAX-ACCESS  read-only
    STATUS      current
    DESCRIPTION "Number of frames discarded for the PVC Endpoint due to
            having a bad RFC1483 encapsulation header."
  ::= { nncFrPVCEndptStatCurrentEntry 29 }


  nncFrPVCEndptStatCurrentOutDiscdUnsupEncaps OBJECT-TYPE
    SYNTAX      NncExtCounter64
    MAX-ACCESS  read-only
    STATUS      current
    DESCRIPTION "Number of frames discarded for the PVC Endpoint due to
            having an unsupported RFC1483 encapsulation header."
  ::= { nncFrPVCEndptStatCurrentEntry 30 }


  nncFrPVCEndptStatCurrentStReasDiscards OBJECT-TYPE
    SYNTAX      NncExtCounter64
    MAX-ACCESS  read-only
    STATUS      current
    DESCRIPTION "Number of frames discarded for the PVC Endpoint due to
            any reassembly errors."
  ::= { nncFrPVCEndptStatCurrentEntry 31 }



--------------------------------------------------------------------------------
-- nncFrIntStatisticsObject 4: Endpoint Stats Interval Table
--------------------------------------------------------------------------------

  nncFrPVCEndptStatIntervalTable            OBJECT-TYPE
    SYNTAX        SEQUENCE OF NncFrPVCEndptStatIntervalEntry
    MAX-ACCESS    not-accessible
    STATUS        current
    DESCRIPTION  "The nncFrPVCEndptStatIntervalTable contains objects
            for monitoring performance of a frame relay endpoint
            over M 1hr historical intervals."
  ::= { nncFrIntStatisticsObjects 4 }


  nncFrPVCEndptStatIntervalEntry            OBJECT-TYPE
    SYNTAX        NncFrPVCEndptStatIntervalEntry
    MAX-ACCESS    not-accessible
    STATUS        current
    DESCRIPTION  "An entry in the 1hr interval statistics table.  Each
            conceptual row contains statistics for a particular PVC
            Endpoint and interval."
    INDEX        { ifIndex,
              nncFrPVCEndptStatIntervalDLCINumber,
              nncFrPVCEndptStatIntervalNumber }
  ::= { nncFrPVCEndptStatIntervalTable 1 }


  NncFrPVCEndptStatIntervalEntry ::=
    SEQUENCE {
        nncFrPVCEndptStatIntervalDLCINumber              INTEGER,
        nncFrPVCEndptStatIntervalNumber                  INTEGER,
        nncFrPVCEndptStatIntervalState                   NncExtIntvlStateType,
        nncFrPVCEndptStatIntervalAbsoluteIntervalNumber  INTEGER,
        nncFrPVCEndptStatIntervalInFrames                NncExtCounter64,
        nncFrPVCEndptStatIntervalOutFrames               NncExtCounter64,
        nncFrPVCEndptStatIntervalInOctets                NncExtCounter64,
        nncFrPVCEndptStatIntervalOutOctets               NncExtCounter64,
        nncFrPVCEndptStatIntervalInDiscards              NncExtCounter64,
        nncFrPVCEndptStatIntervalOutExcessFrames         NncExtCounter64,
        nncFrPVCEndptStatIntervalInDEFrames              NncExtCounter64,
        nncFrPVCEndptStatIntervalInCosTagDeFrames        NncExtCounter64,
        nncFrPVCEndptStatIntervalInOctetsDESet           NncExtCounter64,
        nncFrPVCEndptStatIntervalInFramesBECNSet         NncExtCounter64,
        nncFrPVCEndptStatIntervalInFramesFECNSet         NncExtCounter64,
        nncFrPVCEndptStatIntervalInInvdLength            NncExtCounter64,
        nncFrPVCEndptStatIntervalOutOctetsDESet          NncExtCounter64,
        nncFrPVCEndptStatIntervalOutFramesBECNSet        NncExtCounter64,
        nncFrPVCEndptStatIntervalOutFramesFECNSet        NncExtCounter64,
        nncFrPVCEndptStatIntervalOutFramesInRed          NncExtCounter64,
        nncFrPVCEndptStatIntervalInDiscdOctetsCOS        NncExtCounter64,
        nncFrPVCEndptStatIntervalInDiscdDESet            NncExtCounter64,
        nncFrPVCEndptStatIntervalInDiscdDEClr            NncExtCounter64,
        nncFrPVCEndptStatIntervalInDiscdBadEncaps        NncExtCounter64,
        nncFrPVCEndptStatIntervalInDiscdUnsupEncaps      NncExtCounter64,
        nncFrPVCEndptStatIntervalInDiscdCOSDESet         NncExtCounter64,
        nncFrPVCEndptStatIntervalInDiscdCOSDEClr         NncExtCounter64,
        nncFrPVCEndptStatIntervalOutDiscdDESet           NncExtCounter64,
        nncFrPVCEndptStatIntervalOutDiscdDEClr           NncExtCounter64,
        nncFrPVCEndptStatIntervalOutDiscdBadEncaps       NncExtCounter64,
        nncFrPVCEndptStatIntervalOutDiscdUnsupEncaps     NncExtCounter64,
        nncFrPVCEndptStatIntervalStReasDiscards          NncExtCounter64
    }


  nncFrPVCEndptStatIntervalDLCINumber            OBJECT-TYPE
    SYNTAX        INTEGER (0..1024)
    MAX-ACCESS    not-accessible
    STATUS        current
    DESCRIPTION  "The DLCI number of the stream to which statistics in
            this row belong."
  ::= { nncFrPVCEndptStatIntervalEntry 1 }

  nncFrPVCEndptStatIntervalNumber            OBJECT-TYPE
    SYNTAX        INTEGER (1..96)
    MAX-ACCESS    not-accessible
    STATUS        current
    DESCRIPTION  "The interval number (N) of the statistics in this row."
  ::= { nncFrPVCEndptStatIntervalEntry 2 }


  nncFrPVCEndptStatIntervalState            OBJECT-TYPE
    SYNTAX        NncExtIntvlStateType
    MAX-ACCESS    read-only
    STATUS        current
    DESCRIPTION  "The state of the interval represented by this row. The
            object provides a status for those entries which have
            been reset by the user or have been subject to a wall-
            clock time change."
  ::= { nncFrPVCEndptStatIntervalEntry 3 }


  nncFrPVCEndptStatIntervalAbsoluteIntervalNumber    OBJECT-TYPE
    SYNTAX        INTEGER (0..96)
    MAX-ACCESS    not-accessible
    STATUS        current
    DESCRIPTION  "The absolute interval number of this interval."
  ::= { nncFrPVCEndptStatIntervalEntry 4 }


  nncFrPVCEndptStatIntervalInFrames        OBJECT-TYPE
    SYNTAX        NncExtCounter64
    MAX-ACCESS    read-only
    STATUS        current
    DESCRIPTION  "Number of frames received on this PVC Endpoint."
  ::= { nncFrPVCEndptStatIntervalEntry 5 }


  nncFrPVCEndptStatIntervalOutFrames        OBJECT-TYPE
    SYNTAX        NncExtCounter64
    MAX-ACCESS    read-only
    STATUS        current
    DESCRIPTION  "Number of frames transmitted on this PVC Endpoint."
  ::= { nncFrPVCEndptStatIntervalEntry 6 }


  nncFrPVCEndptStatIntervalInOctets        OBJECT-TYPE
    SYNTAX        NncExtCounter64
    MAX-ACCESS    read-only
    STATUS        current
    DESCRIPTION  "Number of bytes received on this PVC Endpoint."
  ::= { nncFrPVCEndptStatIntervalEntry 7 }


  nncFrPVCEndptStatIntervalOutOctets        OBJECT-TYPE
    SYNTAX        NncExtCounter64
    MAX-ACCESS    read-only
    STATUS        current
    DESCRIPTION  "Number of bytes transmitted on this PVC Endpoint."
  ::= { nncFrPVCEndptStatIntervalEntry 8 }


  nncFrPVCEndptStatIntervalInDiscards        OBJECT-TYPE
    SYNTAX        NncExtCounter64
    MAX-ACCESS    read-only
    STATUS        current
    DESCRIPTION  "Number of frames received by the network (ingress)
            that were discarded due to traffic enforcement for this
            PVC Endpoint." 
  ::= { nncFrPVCEndptStatIntervalEntry 9 }


  nncFrPVCEndptStatIntervalOutExcessFrames    OBJECT-TYPE
    SYNTAX        NncExtCounter64
    MAX-ACCESS    read-only
    STATUS        current
    DESCRIPTION  "Number of frames transmitted by the network (egress)
            for this PVC Endpoint that were treated as excess
            traffic (the DE bit may be set to one)."
  ::= { nncFrPVCEndptStatIntervalEntry 10 }


  nncFrPVCEndptStatIntervalInDEFrames        OBJECT-TYPE
    SYNTAX        NncExtCounter64
    MAX-ACCESS    read-only
    STATUS        current
    DESCRIPTION  "Number of frames received by the network (ingress)
            with the DE bit set to (1) for the PVC Endpoint."
  ::= { nncFrPVCEndptStatIntervalEntry 11 }

 
  nncFrPVCEndptStatIntervalInCosTagDeFrames    OBJECT-TYPE
    SYNTAX      NncExtCounter64
    MAX-ACCESS  read-only
    STATUS      current
    DESCRIPTION "Number of frames received by the network (ingress)
            for this PVC Endpoint that were policed to be excess
            traffic (the DE bit was set to one) and transmitted."
  ::= { nncFrPVCEndptStatIntervalEntry 12 }


  nncFrPVCEndptStatIntervalInOctetsDESet OBJECT-TYPE
    SYNTAX      NncExtCounter64
    MAX-ACCESS  read-only
    STATUS      current
    DESCRIPTION  "Number of bytes received on this PVC Endpoint with the
            DE bit set."
  ::= { nncFrPVCEndptStatIntervalEntry 13 }


  nncFrPVCEndptStatIntervalInFramesBECNSet OBJECT-TYPE
    SYNTAX      NncExtCounter64
    MAX-ACCESS  read-only
    STATUS      current
    DESCRIPTION "Number of frames received by the network (ingress)
            for this PVC Endpoint that had the BECN bit set."
  ::= { nncFrPVCEndptStatIntervalEntry 14 }


  nncFrPVCEndptStatIntervalInFramesFECNSet OBJECT-TYPE
    SYNTAX      NncExtCounter64
    MAX-ACCESS  read-only
    STATUS      current
    DESCRIPTION "Number of frames received by the network (ingress)
            for this PVC Endpoint that had the FECN bit set."
  ::= { nncFrPVCEndptStatIntervalEntry 15 }


  nncFrPVCEndptStatIntervalInInvdLength OBJECT-TYPE
    SYNTAX      NncExtCounter64
    MAX-ACCESS  read-only
    STATUS      current
    DESCRIPTION "Number of frames received by the network (ingress)
            for this PVC Endpoint that were discarded because the frame
            had no data, or the data exceeded the maximum allowed length."
  ::= { nncFrPVCEndptStatIntervalEntry 16 }


  nncFrPVCEndptStatIntervalOutOctetsDESet OBJECT-TYPE
    SYNTAX      NncExtCounter64
    MAX-ACCESS  read-only
    STATUS      current
    DESCRIPTION  "Number of bytes transmitted on this PVC Endpoint with the
            DE bit set."
  ::= { nncFrPVCEndptStatIntervalEntry 17 }


  nncFrPVCEndptStatIntervalOutFramesBECNSet OBJECT-TYPE
    SYNTAX      NncExtCounter64
    MAX-ACCESS  read-only
    STATUS      current
    DESCRIPTION "Number of frames transmitted by the network (egress)
            for this PVC Endpoint that had the BECN bit set."
  ::= { nncFrPVCEndptStatIntervalEntry 18 }


  nncFrPVCEndptStatIntervalOutFramesFECNSet OBJECT-TYPE
    SYNTAX      NncExtCounter64
    MAX-ACCESS  read-only
    STATUS      current
    DESCRIPTION "Number of frames transmitted by the network (egress)
            for this PVC Endpoint that had the FECN bit set."
  ::= { nncFrPVCEndptStatIntervalEntry 19 }


  nncFrPVCEndptStatIntervalOutFramesInRed OBJECT-TYPE
    SYNTAX      NncExtCounter64
    MAX-ACCESS  read-only
    STATUS      current
    DESCRIPTION "Number of frames transmitted by the network (egress)
            for this PVC Endpoint when the frame stream was in Red State."
  ::= { nncFrPVCEndptStatIntervalEntry 20 }


  nncFrPVCEndptStatIntervalInDiscdOctetsCOS OBJECT-TYPE
    SYNTAX      NncExtCounter64
    MAX-ACCESS  read-only
    STATUS      current
    DESCRIPTION "Number of bytes discarded because of receive class-of-service
            enforcement on the PVC Endpoint."
  ::= { nncFrPVCEndptStatIntervalEntry 21 }


  nncFrPVCEndptStatIntervalInDiscdDESet OBJECT-TYPE
    SYNTAX      NncExtCounter64
    MAX-ACCESS  read-only
    STATUS      current
    DESCRIPTION "Number of frames discarded because of receive congestion
            procedures, in which the DE bit was set."
  ::= { nncFrPVCEndptStatIntervalEntry 22 }


  nncFrPVCEndptStatIntervalInDiscdDEClr OBJECT-TYPE
    SYNTAX      NncExtCounter64
    MAX-ACCESS  read-only
    STATUS      current
    DESCRIPTION "Number of frames discarded because of receive congestion
            procedures, in which the DE bit was not set."
  ::= { nncFrPVCEndptStatIntervalEntry 23 }


  nncFrPVCEndptStatIntervalInDiscdBadEncaps OBJECT-TYPE
    SYNTAX      NncExtCounter64
    MAX-ACCESS  read-only
    STATUS      current
    DESCRIPTION "Number of frames discarded on this PVC Endpoint because of 
            a bad receive RFC1490 encapsulation header."
  ::= { nncFrPVCEndptStatIntervalEntry 24 }


  nncFrPVCEndptStatIntervalInDiscdUnsupEncaps OBJECT-TYPE
    SYNTAX      NncExtCounter64
    MAX-ACCESS  read-only
    STATUS      current
    DESCRIPTION "Number of frames discarded on this PVC Endpoint because of 
            an unsupported receive RFC1490 encapsulation header."
  ::= { nncFrPVCEndptStatIntervalEntry 25 }


  nncFrPVCEndptStatIntervalInDiscdCOSDESet OBJECT-TYPE
    SYNTAX      NncExtCounter64
    MAX-ACCESS  read-only
    STATUS      current
    DESCRIPTION "Number of frames discarded due to receive class of service
            procedures, in which the DE bit was set."
  ::= { nncFrPVCEndptStatIntervalEntry 26 }


  nncFrPVCEndptStatIntervalInDiscdCOSDEClr OBJECT-TYPE
    SYNTAX      NncExtCounter64
    MAX-ACCESS  read-only
    STATUS      current
    DESCRIPTION "Number of frames discarded for the PVC Endpoint due to
            receive class of service procedures, in which the DE bit was
            not set."
  ::= { nncFrPVCEndptStatIntervalEntry 27 }


  nncFrPVCEndptStatIntervalOutDiscdDESet OBJECT-TYPE
    SYNTAX      NncExtCounter64
    MAX-ACCESS  read-only
    STATUS      current
    DESCRIPTION "Number of frames discarded for the PVC Endpoint due to
            transmit congestion procedures, in which the DE bit was set."
  ::= { nncFrPVCEndptStatIntervalEntry 28 }


  nncFrPVCEndptStatIntervalOutDiscdDEClr OBJECT-TYPE
    SYNTAX      NncExtCounter64
    MAX-ACCESS  read-only
    STATUS      current
    DESCRIPTION "Number of frames discarded for the PVC Endpoint due to
            transmit congestion procedures, in which the DE bit was not set."
  ::= { nncFrPVCEndptStatIntervalEntry 29 }


  nncFrPVCEndptStatIntervalOutDiscdBadEncaps OBJECT-TYPE
    SYNTAX      NncExtCounter64
    MAX-ACCESS  read-only
    STATUS      current
    DESCRIPTION "Number of frames discarded for the PVC Endpoint due to
            having a bad RFC1483 encapsulation header."
  ::= { nncFrPVCEndptStatIntervalEntry 30 }


  nncFrPVCEndptStatIntervalOutDiscdUnsupEncaps OBJECT-TYPE
    SYNTAX      NncExtCounter64
    MAX-ACCESS  read-only
    STATUS      current
    DESCRIPTION "Number of frames discarded for the PVC Endpoint due to
            having an unsupported RFC1483 encapsulation header."
  ::= { nncFrPVCEndptStatIntervalEntry 31 }


  nncFrPVCEndptStatIntervalStReasDiscards OBJECT-TYPE
    SYNTAX      NncExtCounter64
    MAX-ACCESS  read-only
    STATUS      current
    DESCRIPTION "Number of frames discarded for the PVC Endpoint due to
            any reassembly errors."
  ::= { nncFrPVCEndptStatIntervalEntry 32 }


--------------------------------------------------------------------------------
-- nncFrIntStatisticsObject 5: nncFrDepthOfHistoricalStrata
--------------------------------------------------------------------------------

  nncFrDepthOfHistoricalStrata             OBJECT-TYPE
    SYNTAX        INTEGER (1..96)
    MAX-ACCESS    read-only
    STATUS        current
    DESCRIPTION  "Depth of historical strata of FR interval statistics."
  ::= { nncFrIntStatisticsObjects 5 }

--------------------------------------------------------------------------------
-- nncFrIntStatisticsObject 6: Stream BERT Statistics
--------------------------------------------------------------------------------

  nncFrStrBertStatTable              OBJECT-TYPE
    SYNTAX      SEQUENCE OF NncFrStrBertStatEntry
    MAX-ACCESS  not-accessible
    STATUS        current
    DESCRIPTION  "The nncFrStrBertStatTable contains objects for reporting the
            current statistics of a BERT being performed on a frame relay
            stream. This feature is introduced in Rel 2.2 frame relay cards."
  ::= { nncFrIntStatisticsObjects 6 }


  nncFrStrBertStatEntry            OBJECT-TYPE
    SYNTAX        NncFrStrBertStatEntry
    MAX-ACCESS    not-accessible
    STATUS        current
    DESCRIPTION  "An entry in the BERT statistics table.  Each conceptual row
            contains statistics related to the BERT being performed
            on a specific DLCI within a particular frame relay stream." 
    INDEX        { ifIndex }
  ::= { nncFrStrBertStatTable 1 }


  NncFrStrBertStatEntry ::=
  SEQUENCE {
    nncFrStrBertDlci            Integer32,
    nncFrStrBertStatStatus      INTEGER,
    nncFrStrBertStatTxFrames    Gauge32,
    nncFrStrBertStatRxFrames    Gauge32,
    nncFrStrBertStatTxBytes     Gauge32,
    nncFrStrBertStatRxBytes     Gauge32,
    nncFrStrBertStatRxErrors    Gauge32,
    nncFrStrBertStatEstErrors   Gauge32
  }

  nncFrStrBertDlci            OBJECT-TYPE
SYNTAX      Integer32
MAX-ACCESS  read-only
STATUS      current
DESCRIPTION "This object indicates if there is a BERT active on the frame 
        relay stream, and when active on which DLCI the BERT is active 
        on. WHERE: 0 = BERT not active, non-zero = DLCI"
  ::= { nncFrStrBertStatEntry 1 }

  nncFrStrBertStatStatus        OBJECT-TYPE
    SYNTAX      INTEGER (0..1)
    MAX-ACCESS  read-only
    STATUS      current
    DESCRIPTION "The current status of the BERT when the BERT is
            activated: where 0 = Loss of pattern sync. 1 = Pattern Sync."
  ::= { nncFrStrBertStatEntry 2 }

  nncFrStrBertStatTxFrames            OBJECT-TYPE
    SYNTAX      Gauge32
    MAX-ACCESS  read-only
    STATUS      current
    DESCRIPTION "The  number of Frames transmitted onto the stream by
            BERT Task. Each BERT Frame is of a fixed size and contains a
            fixed pattern."
  ::= { nncFrStrBertStatEntry 3 }

  nncFrStrBertStatRxFrames            OBJECT-TYPE
    SYNTAX      Gauge32
    MAX-ACCESS  read-only
    STATUS      current
    DESCRIPTION  "The  number of Frames received while the BERT is in 
            pattern sync. The Rx Frame count will only be incremented when
            in pattern sync and the received packet is the correct size and
            contains the DLCI being BERTED."
  ::= { nncFrStrBertStatEntry 4 }

  nncFrStrBertStatRxBytes            OBJECT-TYPE
    SYNTAX      Gauge32
    MAX-ACCESS  read-only
    STATUS      current
    DESCRIPTION  "The  number of Bytes transmitted onto the stream by
            BERT Task. Each BERT packet is of a fixed size and contains a
            fixed pattern."
  ::= { nncFrStrBertStatEntry 5 }

  nncFrStrBertStatTxBytes            OBJECT-TYPE
    SYNTAX      Gauge32
    MAX-ACCESS  read-only
    STATUS      current
    DESCRIPTION  "The  number of Bytes transmitted while the BERT is in 
            pattern sync. The Tx Byte count will only be incremented when
            in pattern sync."
  ::= { nncFrStrBertStatEntry 6 }

  nncFrStrBertStatRxErrors            OBJECT-TYPE
    SYNTAX      Gauge32
    MAX-ACCESS  read-only
    STATUS      current
    DESCRIPTION  "The  number of errors detected in the received 
            packets while the BERT is in pattern sync. Packets flagged
            as having CRC errors that contain the DLCI being BERTED and
            the correct packet size being BERTED will be scanned for
            errors and the number of errors accumulated in this counter."
  ::= { nncFrStrBertStatEntry 7 }

  nncFrStrBertStatEstErrors            OBJECT-TYPE
    SYNTAX      Gauge32
    MAX-ACCESS  read-only
    STATUS      current
    DESCRIPTION  "The estimated number of errors encountered by the
            packets being transmitted while the BERT is in pattern sync
            based on the fact that the packets are not returned, and
            pattern sync is maintained."
  ::= { nncFrStrBertStatEntry 8 }



--------------------------------------------------------------------------------
-- Conformance Group Definitions
--------------------------------------------------------------------------------

    nncFrStrStatCurrentGroup    OBJECT-GROUP
        OBJECTS    {
            nncFrStrStatCurrentState,
            nncFrStrStatCurrentAbsoluteIntervalNumber,
            nncFrStrStatCurrentInOctets,
            nncFrStrStatCurrentOutOctets,
            nncFrStrStatCurrentInUCastPackets,
            nncFrStrStatCurrentOutUCastPackets,
            nncFrStrStatCurrentInDiscards,
            nncFrStrStatCurrentOutDiscards,
            nncFrStrStatCurrentInErrors,
            nncFrStrStatCurrentOutErrors,
            nncFrStrStatCurrentSigUserProtErrors,
            nncFrStrStatCurrentSigNetProtErrors,
            nncFrStrStatCurrentSigUserLinkRelErrors,
            nncFrStrStatCurrentSigNetLinkRelErrors,
            nncFrStrStatCurrentSigUserChanInactive,
            nncFrStrStatCurrentSigNetChanInactive,
            nncFrStrStatCurrentStSCAlarms,
            nncFrStrStatCurrentStTimeSC,
            nncFrStrStatCurrentStMaxDurationRED,
            nncFrStrStatCurrentStMCAlarms,
            nncFrStrStatCurrentStTimeMC,
            nncFrStrStatCurrentOutLinkUtilization,
            nncFrStrStatCurrentInLinkUtilization,
            nncFrStrStatCurrentInInvdLength,
            nncFrStrStatCurrentStLastErroredDLCI,
            nncFrStrStatCurrentInDiscdOctetsCOS,
            nncFrStrStatCurrentInDiscdCOSDESet,
            nncFrStrStatCurrentInDiscdCOSDEClr,
            nncFrStrStatCurrentInDiscdBadEncaps,
            nncFrStrStatCurrentOutDiscdBadEncaps,
            nncFrStrStatCurrentInDiscdUnsupEncaps,
            nncFrStrStatCurrentOutDiscdUnsupEncaps,
            nncFrStrStatCurrentOutDiscdDESet,
            nncFrStrStatCurrentOutDiscdDEClr,
            nncFrStrStatCurrentInDiscdDESet,
            nncFrStrStatCurrentInDiscdDEClr,
            nncFrStrStatCurrentStLMSigInvldField,
            nncFrStrStatCurrentStLMSigUnsupMsgType,
            nncFrStrStatCurrentStLMSigInvldEID,
            nncFrStrStatCurrentStLMSigInvldIELen,
            nncFrStrStatCurrentStLMSigInvldRepType,
            nncFrStrStatCurrentStLMSigFrmWithNoIEs,
            nncFrStrStatCurrentStUserSequenceErrs,
            nncFrStrStatCurrentStNetSequenceErrs,
            nncFrStrStatCurrentStLMUTimeoutsnT1,
            nncFrStrStatCurrentStLMUStatusMsgsRcvd,
            nncFrStrStatCurrentStLMUStatusENQMsgsSent,
            nncFrStrStatCurrentStLMUAsyncStatusRcvd,
            nncFrStrStatCurrentStLMNTimeoutsnT2,
            nncFrStrStatCurrentStLMNStatusMsgsSent,
            nncFrStrStatCurrentStLMNStatusENQMsgsRcvd,
            nncFrStrStatCurrentStLMNAsyncStatusSent,
            nncFrStrStatCurrentInCRCErrors,
            nncFrStrStatCurrentInNonIntegral,
            nncFrStrStatCurrentInReservedDLCI,
            nncFrStrStatCurrentInInvldEA,
            nncFrStrStatCurrentStFrmTooSmall,
            nncFrStrStatCurrentInAborts,
            nncFrStrStatCurrentInSumOfDisagremnts,
            nncFrStrStatCurrentInOverRuns,
            nncFrStrStatCurrentOutUnderRuns,
            nncFrStrStatCurrentStIntervalDuration,
            nncFrStrStatCurrentBestEffortPeakDelay,
            nncFrStrStatCurrentCommittedPeakDelay,
            nncFrStrStatCurrentLowDelayPeakDelay,
            nncFrStrStatCurrentRealTimePeakDelay,
            nncFrStrStatCurrentBestEffortAccDelay,
            nncFrStrStatCurrentCommittedAccDelay,
            nncFrStrStatCurrentLowDelayAccDelay,
            nncFrStrStatCurrentRealTimeAccDelay,
            nncFrStrStatCurrentBestEffortOutUCastPackets,
            nncFrStrStatCurrentCommittedOutUCastPackets,
            nncFrStrStatCurrentLowDelayOutUCastPackets,
            nncFrStrStatCurrentRealTimeOutUCastPackets,
            nncFrStrStatCurrentBestEffortUCastPacketsDEClr,
            nncFrStrStatCurrentCommittedUCastPacketsDEClr,
            nncFrStrStatCurrentLowDelayUCastPacketsDEClr,
            nncFrStrStatCurrentRealTimeUCastPacketsDEClr,
            nncFrStrStatCurrentBestEffortDiscdDEClr,
            nncFrStrStatCurrentCommittedDiscdDEClr,
            nncFrStrStatCurrentLowDelayDiscdDEClr,
            nncFrStrStatCurrentRealTimeDiscdDEClr
        }
            STATUS        current
            DESCRIPTION  "Collection of objects providing 1hr
                    current statistics for a FR stream."
    ::= { nncFrIntStatisticsGroups 1 }


    nncFrStrStatIntervalGroup    OBJECT-GROUP
        OBJECTS    {
            nncFrStrStatIntervalNumber,
            nncFrStrStatIntervalState,
            nncFrStrStatIntervalAbsoluteIntervalNumber,
            nncFrStrStatIntervalInOctets,
            nncFrStrStatIntervalOutOctets,
            nncFrStrStatIntervalInUCastPackets,
            nncFrStrStatIntervalOutUCastPackets,
            nncFrStrStatIntervalInDiscards,
            nncFrStrStatIntervalOutDiscards,
            nncFrStrStatIntervalInErrors,
            nncFrStrStatIntervalOutErrors,
            nncFrStrStatIntervalSigUserProtErrors,
            nncFrStrStatIntervalSigNetProtErrors,
            nncFrStrStatIntervalSigUserLinkRelErrors,
            nncFrStrStatIntervalSigNetLinkRelErrors,
            nncFrStrStatIntervalSigUserChanInactive,
            nncFrStrStatIntervalSigNetChanInactive,
            nncFrStrStatIntervalStSCAlarms,
            nncFrStrStatIntervalStTimeSC,
            nncFrStrStatIntervalStMaxDurationRED,
            nncFrStrStatIntervalStMCAlarms,
            nncFrStrStatIntervalStTimeMC,
            nncFrStrStatIntervalOutLinkUtilization,
            nncFrStrStatIntervalInLinkUtilization,
            nncFrStrStatIntervalInInvdLength,
            nncFrStrStatIntervalStLastErroredDLCI,
            nncFrStrStatIntervalInDiscdOctetsCOS,
            nncFrStrStatIntervalInDiscdCOSDESet,
            nncFrStrStatIntervalInDiscdCOSDEClr,
            nncFrStrStatIntervalInDiscdBadEncaps,
            nncFrStrStatIntervalOutDiscdBadEncaps,
            nncFrStrStatIntervalInDiscdUnsupEncaps,
            nncFrStrStatIntervalOutDiscdUnsupEncaps,
            nncFrStrStatIntervalOutDiscdDESet,
            nncFrStrStatIntervalOutDiscdDEClr,
            nncFrStrStatIntervalInDiscdDESet,
            nncFrStrStatIntervalInDiscdDEClr,
            nncFrStrStatIntervalStLMSigInvldField,
            nncFrStrStatIntervalStLMSigUnsupMsgType,
            nncFrStrStatIntervalStLMSigInvldEID,
            nncFrStrStatIntervalStLMSigInvldIELen,
            nncFrStrStatIntervalStLMSigInvldRepType,
            nncFrStrStatIntervalStLMSigFrmWithNoIEs,
            nncFrStrStatIntervalStUserSequenceErrs,
            nncFrStrStatIntervalStNetSequenceErrs,
            nncFrStrStatIntervalStLMUTimeoutsnT1,
            nncFrStrStatIntervalStLMUStatusMsgsRcvd,
            nncFrStrStatIntervalStLMUStatusENQMsgsSent,
            nncFrStrStatIntervalStLMUAsyncStatusRcvd,
            nncFrStrStatIntervalStLMNTimeoutsnT2,
            nncFrStrStatIntervalStLMNStatusMsgsSent,
            nncFrStrStatIntervalStLMNStatusENQMsgsRcvd,
            nncFrStrStatIntervalStLMNAsyncStatusSent,
            nncFrStrStatIntervalInCRCErrors,
            nncFrStrStatIntervalInNonIntegral,
            nncFrStrStatIntervalInReservedDLCI,
            nncFrStrStatIntervalInInvldEA,
            nncFrStrStatIntervalStFrmTooSmall,
            nncFrStrStatIntervalInAborts,
            nncFrStrStatIntervalInSumOfDisagremnts,
            nncFrStrStatIntervalInOverRuns,
            nncFrStrStatIntervalOutUnderRuns,
            nncFrStrStatIntervalStIntervalDuration,
            nncFrStrStatIntervalBestEffortPeakDelay,
            nncFrStrStatIntervalCommittedPeakDelay,
            nncFrStrStatIntervalLowDelayPeakDelay,
            nncFrStrStatIntervalRealTimePeakDelay,
            nncFrStrStatIntervalBestEffortAccDelay,
            nncFrStrStatIntervalCommittedAccDelay,
            nncFrStrStatIntervalLowDelayAccDelay,
            nncFrStrStatIntervalRealTimeAccDelay,
            nncFrStrStatIntervalBestEffortOutUCastPackets,
            nncFrStrStatIntervalCommittedOutUCastPackets,
            nncFrStrStatIntervalLowDelayOutUCastPackets,
            nncFrStrStatIntervalRealTimeOutUCastPackets,
            nncFrStrStatIntervalBestEffortUCastPacketsDEClr,
            nncFrStrStatIntervalCommittedUCastPacketsDEClr,
            nncFrStrStatIntervalLowDelayUCastPacketsDEClr,
            nncFrStrStatIntervalRealTimeUCastPacketsDEClr,
            nncFrStrStatIntervalBestEffortDiscdDEClr,
            nncFrStrStatIntervalCommittedDiscdDEClr,
            nncFrStrStatIntervalLowDelayDiscdDEClr,
            nncFrStrStatIntervalRealTimeDiscdDEClr
        }
        STATUS        current
        DESCRIPTION  "Collection of objects providing 1hr
                interval statistics for a FR stream."
    ::= { nncFrIntStatisticsGroups 2 }


    nncFrPVCEndptStatCurrentGroup    OBJECT-GROUP
        OBJECTS    {
            nncFrPVCEndptStatCurrentDLCINumber,
            nncFrPVCEndptStatCurrentState,
            nncFrPVCEndptStatCurrentAbsoluteIntervalNumber,
            nncFrPVCEndptStatCurrentInFrames,
            nncFrPVCEndptStatCurrentOutFrames,
            nncFrPVCEndptStatCurrentInOctets,
            nncFrPVCEndptStatCurrentOutOctets,
            nncFrPVCEndptStatCurrentInDiscards,
            nncFrPVCEndptStatCurrentOutExcessFrames,
            nncFrPVCEndptStatCurrentInDEFrames,
            nncFrPVCEndptStatCurrentInCosTagDeFrames,
            nncFrPVCEndptStatCurrentInOctetsDESet,
            nncFrPVCEndptStatCurrentInFramesBECNSet,
            nncFrPVCEndptStatCurrentInFramesFECNSet,
            nncFrPVCEndptStatCurrentInInvdLength,
            nncFrPVCEndptStatCurrentOutOctetsDESet,
            nncFrPVCEndptStatCurrentOutFramesBECNSet,
            nncFrPVCEndptStatCurrentOutFramesFECNSet,
            nncFrPVCEndptStatCurrentOutFramesInRed,
            nncFrPVCEndptStatCurrentInDiscdOctetsCOS,
            nncFrPVCEndptStatCurrentInDiscdDESet,
            nncFrPVCEndptStatCurrentInDiscdDEClr,
            nncFrPVCEndptStatCurrentInDiscdBadEncaps,
            nncFrPVCEndptStatCurrentInDiscdUnsupEncaps,
            nncFrPVCEndptStatCurrentInDiscdCOSDESet,
            nncFrPVCEndptStatCurrentInDiscdCOSDEClr,
            nncFrPVCEndptStatCurrentOutDiscdDESet,
            nncFrPVCEndptStatCurrentOutDiscdDEClr,
            nncFrPVCEndptStatCurrentOutDiscdBadEncaps,
            nncFrPVCEndptStatCurrentOutDiscdUnsupEncaps,
            nncFrPVCEndptStatCurrentStReasDiscards
        }
        STATUS        current
        DESCRIPTION  "Collection of objects providing 1hr
                current statistics for a FR PVC Endpoint."
    ::= { nncFrIntStatisticsGroups 3 }


    nncFrPVCEndptStatIntervalGroup    OBJECT-GROUP
  OBJECTS    {
            nncFrPVCEndptStatIntervalDLCINumber,
            nncFrPVCEndptStatIntervalNumber,
            nncFrPVCEndptStatIntervalState,
            nncFrPVCEndptStatIntervalAbsoluteIntervalNumber,
            nncFrPVCEndptStatIntervalInFrames,
            nncFrPVCEndptStatIntervalOutFrames,
            nncFrPVCEndptStatIntervalInOctets,
            nncFrPVCEndptStatIntervalOutOctets,
            nncFrPVCEndptStatIntervalInDiscards,
            nncFrPVCEndptStatIntervalOutExcessFrames,
            nncFrPVCEndptStatIntervalInDEFrames,
            nncFrPVCEndptStatIntervalInCosTagDeFrames,
            nncFrPVCEndptStatIntervalInOctetsDESet,
            nncFrPVCEndptStatIntervalInFramesBECNSet,
            nncFrPVCEndptStatIntervalInFramesFECNSet,
            nncFrPVCEndptStatIntervalInInvdLength,
            nncFrPVCEndptStatIntervalOutOctetsDESet,
            nncFrPVCEndptStatIntervalOutFramesBECNSet,
            nncFrPVCEndptStatIntervalOutFramesFECNSet,
            nncFrPVCEndptStatIntervalOutFramesInRed,
            nncFrPVCEndptStatIntervalInDiscdOctetsCOS,
            nncFrPVCEndptStatIntervalInDiscdDESet,
            nncFrPVCEndptStatIntervalInDiscdDEClr,
            nncFrPVCEndptStatIntervalInDiscdBadEncaps,
            nncFrPVCEndptStatIntervalInDiscdUnsupEncaps,
            nncFrPVCEndptStatIntervalInDiscdCOSDESet,
            nncFrPVCEndptStatIntervalInDiscdCOSDEClr,
            nncFrPVCEndptStatIntervalOutDiscdDESet,
            nncFrPVCEndptStatIntervalOutDiscdDEClr,
            nncFrPVCEndptStatIntervalOutDiscdBadEncaps,
            nncFrPVCEndptStatIntervalOutDiscdUnsupEncaps,
            nncFrPVCEndptStatIntervalStReasDiscards
        }
        STATUS        current
        DESCRIPTION  "Collection of objects providing 1hr
                current statistics for a FR PVC Endpoint."
    ::= { nncFrIntStatisticsGroups 4 }

  
    nncFrStrBertStatGroup    OBJECT-GROUP
        OBJECTS    {
            nncFrStrBertDlci,
            nncFrStrBertStatStatus,
            nncFrStrBertStatTxFrames,
            nncFrStrBertStatRxFrames,
            nncFrStrBertStatTxBytes,
            nncFrStrBertStatRxBytes,
            nncFrStrBertStatRxErrors,
            nncFrStrBertStatEstErrors
        }
        STATUS        current
        DESCRIPTION  "Collection of objects providing BERT statistics for a BERT 
                performed on a Frame Relay stream."
    ::= { nncFrIntStatisticsGroups 6 }

--------------------------------------------------------------------------------
-- Compliance Statements (mandatory)
--------------------------------------------------------------------------------
    nncFrIntStatisticsCompliance    MODULE-COMPLIANCE
        STATUS        current
        DESCRIPTION  "The compliance statement for Newbridge SNMP
                entities which have FR streams and endpoints."
        MODULE 
            MANDATORY-GROUPS {
                nncFrStrStatCurrentGroup,
                nncFrPVCEndptStatCurrentGroup
            }
    ::= { nncFrIntStatisticsCompliances 1 } 


-------------------------------------------------------------------------------
--    Review Minutes 
-------------------------------------------------------------------------------
--    MINUTES-BEGIN
--        REVIEW-DATE  "1996.02.13"
--        BODY  "
--
--    TO:    Chris Gibson*, Frank Chen*, Rick To*, Wing-Leung Chan*, 
--        Shafiq Pirbhai*, Riyaz Ismail*, Zlatco Moskun*
--    CC:    Numbers Admin, Melanie Paquette, Suzanne Poulos
--    FROM:    Sriram Darbha*
--
--    A meeting was held on 1996.02.13 to review
--      FrameRelayIntervalStatistics.mib.
--    Attendees are marked with * in the TO and CC lists above.
--
--    Outcome
--
--    It was the consensus of the review team that this file is 
--    acceptable with the indicated modifications.
--
--    Actions:
--    A1 -     Sriram Darbha to update the file as indicated in D1 below.  
--        Response:    Status: CLOSED
--
--    Decisions:
--    D1 -     FrameRelayIntervalStatistics.mib shall be updated as follows:
--        a) add absolute interval number to each table entry type
--        b) create a read object to provide depth of historical strata
--        c) create a conformance group per table
--        d) make current tables mandatory, interval tables optional
--        e) import IntervalState textual convention from
--           ATMStatistics.mib
--        f) Spell out error types on line 193
--    "
--
--    END-MINUTES
--
--
--
--    MINUTES-BEGIN
--        REVIEW-DATE  "1997.11.27"
--        BODY  "
--
--    TO:    Randy Jones, Frank Chen*, Mark Woodward*, Janice Wei, 
--        Mike Rehder* 
--    CC:    Numbers Admin, Suzanne Poulos
--    FROM:    Derrick Nagy*
--
--    A meeting was held on 1997.11.27 to review
--      FrameRelayIntervalStatistics.mib.
--    Attendees are marked with * in the TO and CC lists above.
--
--    Outcome
--
--    It was the consensus of the review team that this file is 
--    acceptable with the indicated modifications.
--
--    Actions:
--    A1 -     Derrick Nagy to update the file as indicated in D1 below.  
--        Response:    Status: CLOSED
--
--    Decisions:
--    D1 -     FrameRelayIntervalStatistics.mib shall be updated as follows:
--        a) Replace references to "StRx" and "StTx" with "In" and "out"
--        b) Remove explicit references to 36170
--        c) create a conformance group per table
--    "
--
--    END-MINUTES
END -- DEFINITION OF NNCFRINTSTATISTICS-MIB
