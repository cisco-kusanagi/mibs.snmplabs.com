--
-- 	Copyright 1997 Shiva Corporation
--

SHIVA-PSURF-MIB DEFINITIONS ::= BEGIN

IMPORTS
	Counter
		FROM RFC1155-SMI
    	OBJECT-TYPE
    		FROM RFC-1212		-- Concise MIB Definitions
	psurf
    		FROM SHIVA-MIB;

-- MIB for the PowerSurf Agent.  
-- Includes statistics and control information

    pSurfAgentState      OBJECT-TYPE
	SYNTAX	INTEGER {
		on (1),  -- this option is not supported at the present time
		off (2)  -- turns powersurf off
	}
	ACCESS	read-write
	STATUS	mandatory
	DESCRIPTION
	    "PowerSurf Agent can be turned off by settting this value to off"
	::= { psurf 1 }

    pSurfAgentCurrentState      OBJECT-TYPE
	SYNTAX	INTEGER {
	   	unlicensed (1),         -- PowerSurf license not installed
		enabled (2),            -- PowerSurf is on
		off (3),                -- PowerSurf is off
		disabled (4),           -- Powersurf is disabled
		resourceConstrained (5) -- Powersurf is temporarly disabled
	}
	ACCESS	read-only
	STATUS	mandatory
	DESCRIPTION
	    "The current  state of the PowerSurf Agent." 
	::= { psurf 2 }

    pSurfCurrentPSurfUsers	OBJECT-TYPE
	SYNTAX	Counter
	ACCESS	read-only
	STATUS	mandatory
	DESCRIPTION
	    "The current number of users accelerated by PowerSurf."
	::= { psurf 3 }

    pSurfCurrentNonPSurfUsers	OBJECT-TYPE
	SYNTAX	Counter
	ACCESS	read-only
	STATUS	mandatory
	DESCRIPTION
	    "The current number of users not accelerated by PowerSurf."
	::= { psurf 4 }

    pSurfCumulativePSurfUsers	OBJECT-TYPE
	SYNTAX	Counter
	ACCESS	read-only
	STATUS	mandatory
	DESCRIPTION
	    "The cumulative number of users accelerated by PowerSurf."
	::= { psurf 5 }

    pSurfCumulativeNonPSurfUsers	OBJECT-TYPE
	SYNTAX	Counter
	ACCESS	read-only
	STATUS	mandatory
	DESCRIPTION
	    "The cumulative number of users not accelerated by PowerSurf."
	::= { psurf 6 }

    pSurfCurrentClientConns		OBJECT-TYPE
	SYNTAX	Counter
	ACCESS	read-only
	STATUS	mandatory
	DESCRIPTION
	    "The current number of client TCP connections."
	::= { psurf 7 }

    pSurfCurrentServerConns		OBJECT-TYPE
	SYNTAX	Counter
	ACCESS	read-only
	STATUS	mandatory
	DESCRIPTION
	     "The current number of server TCP connections."
	::= { psurf 8 }

    pSurfCumulativeClientConns		OBJECT-TYPE
	SYNTAX	Counter
	ACCESS	read-only
	STATUS	mandatory
	DESCRIPTION
	    "The cumulative number of client TCP Connections."
	::= { psurf 9 }

    pSurfCumulativeServerConns		OBJECT-TYPE
	SYNTAX	Counter
	ACCESS	read-only
	STATUS	mandatory
	DESCRIPTION
	    "The cumulative number of server TCP Connections."
	::= { psurf 10 }

    pSurfCumulativeServerConnsUsed		OBJECT-TYPE
	SYNTAX	Counter
	ACCESS	read-only
	STATUS	mandatory
	DESCRIPTION
	    "The cumulative number of used server TCP connections."
	::= { psurf 11 }

    pSurfCumulativeServerConnsReused		OBJECT-TYPE
	SYNTAX	Counter
	ACCESS	read-only
	STATUS	mandatory
	DESCRIPTION
	    "The cumulative number of server TCP connections that have been
	      reused."
	::= { psurf 12 }

    pSurfClientConnsKeepAlive			OBJECT-TYPE
	SYNTAX	Counter
	ACCESS	read-only
	STATUS	mandatory
	DESCRIPTION
	    "The number of client TCP connections that were made keep-alive by
	     the PowerSurf Agent."
	::= { psurf 13 }

    pSurfClientConnsSaved			OBJECT-TYPE
	SYNTAX	Counter
	ACCESS	read-only
	STATUS	mandatory
	DESCRIPTION
	    "The number of saved client TCP connections."
	::= { psurf 14 }

    pSurfEntriesInCache			OBJECT-TYPE
	SYNTAX	Counter
	ACCESS	read-only
	STATUS	mandatory
	DESCRIPTION
	    "The number of entries in the status cache."
	::= { psurf 15 }

    pSurfCacheHits			OBJECT-TYPE
	SYNTAX	Counter
	ACCESS	read-only
	STATUS	mandatory
	DESCRIPTION
	    "The number of times status cache entries were used."
	::= { psurf 16 }

    pSurfBytesClnt2LR			OBJECT-TYPE
	SYNTAX	Counter
	ACCESS	read-only
	STATUS	mandatory
	DESCRIPTION
	    "The number of bytes that were transferred from clients to
	     remote access device."
	::= { psurf 17 }

    pSurfBytesLR2Clnt			OBJECT-TYPE
	SYNTAX	Counter
	ACCESS	read-only
	STATUS	mandatory
	DESCRIPTION
	    "The number of bytes that were transferred from remote access 
	     device to clients."
	::= { psurf 18 }

    pSurfBytesLR2Srvr			OBJECT-TYPE
	SYNTAX	Counter
	ACCESS	read-only
	STATUS	mandatory
	DESCRIPTION
	    "The number of bytes that were transferred from remote access 
	     device to web servers."
	::= { psurf 19 }

    pSurfBytesSrvr2LR			OBJECT-TYPE
	SYNTAX	Counter
	ACCESS	read-only
	STATUS	mandatory
	DESCRIPTION
	    "The number of bytes that were transferred from web servers to 
	     remote access device."
	::= { psurf 20 }

    pSurfAvrgThruPutClnt2LR			OBJECT-TYPE
	SYNTAX	Counter
	ACCESS	read-only
	STATUS	mandatory
	DESCRIPTION
	    "The average number of bytes that were transferred from clients to
	     remote access device in the last minute."
	::= { psurf 21 }

    pSurfAvrgThruPutLR2Clnt			OBJECT-TYPE
	SYNTAX	Counter
	ACCESS	read-only
	STATUS	mandatory
	DESCRIPTION
	    "The average number of bytes that were transferred from remote 
	     access device to the clients in the last minute."
	::= { psurf 22 }

    pSurfAvrgThruPutLR2Srvr			OBJECT-TYPE
	SYNTAX	Counter
	ACCESS	read-only
	STATUS	mandatory
	DESCRIPTION
	    "The average number of bytes that were transferred from remote 
	     access device to web servers in the last minute."
	::= { psurf 23 }

    pSurfAvrgThruPutSrvr2LR			OBJECT-TYPE
	SYNTAX	Counter
	ACCESS	read-only
	STATUS	mandatory
	DESCRIPTION
	    "The average number of bytes that were transferred from web 
	     servers to remote access device in the last minute."
	::= { psurf 24 }

    pSurfClearCache      OBJECT-TYPE
	SYNTAX	INTEGER {
	    yes (1)
	}
	ACCESS	read-write  -- This is really a write only variable
	STATUS	mandatory
	DESCRIPTION
	    "This can be used for clearing the PowerSurf Agent status Cache."
	::= { psurf 25 }
END
