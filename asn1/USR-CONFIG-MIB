USR-CONFIG-MIB DEFINITIONS ::= BEGIN
	IMPORTS
          OBJECT-TYPE, MODULE-IDENTITY, NOTIFICATION-TYPE, OBJECT-IDENTITY,
          Integer32
                  FROM SNMPv2-SMI
          TruthValue, DisplayString
                  FROM SNMPv2-TC
          common, UsrConfigStatus, UsrNetLogicalId,
    	  UsrUserName, UsrDisplayString, UsrNetAddress
       FROM USR-DEFINITIONS-MIB
       ifIndex, ifAdminStatus, ifOperStatus FROM IF-MIB;
usrConfig        MODULE-IDENTITY
                 LAST-UPDATED "200305190930Z"
                 ORGANIZATION "CommWorks Corporation, a 3Com Company"
                 CONTACT-INFO "Customer Support"
                 DESCRIPTION
                         "The commWorks enterprise defined MIB objects
                          for Configuration Management"
--      REVISION     "200305190930Z"
--      DESCRIPTION  "Added Ethernet Operating Mode that allows one to Change Ethernet port's Mode."
--      REVISION     "200209060930Z"
--      DESCRIPTION  "Added two new enterprise traps for LinkDown and LinkUp events. The traps contain the slot information of the card."
--      REVISION "200208231340Z"
--      DESCRIPTION "Clarified usage and leabels for usrCfgIfPromiscuousMode,
--          usrCfgResetEEpromStatus."
--               REVISION        "200208021650Z"
--               DESCRIPTION     "Obsoleted usrCfgModemGroupFilterTable and everything
--                                under it. These were moved to usr_vha.mib"
--      REVISION "200208231340Z"
--      DESCRIPTION "Clarified usage and leabels for usrCfgIfPromiscuousMode,
--                   usrCfgResetEEpromStatus."
--      REVISION     "200208151645Z"
--      DESCRIPTION  "Added two new MIB objects for new CLI Save Settings"
--      REVISION     "200208021650Z"
--      DESCRIPTION  "Obsoleted usrCfgModemGroupFilterTable and everything
--                    under it. These were moved to usr_vha.mib"
--      REVISION     "200203131300Z"
--      DESCRIPTION  "Converted to SNMPv2"
         ::= { common 1 }
   -- textual conventions
   -- 
   -- textual conventions are like pre-processor macro in 'C'
   --        (i.e. #define statements)
   -- Use them to define your own 'datatypes'
   -- Network Encapsulation Types. This enumeration should match the one 
   -- in pilgrim/config/include/config_public.h
	UsrCfgEncapsulations ::= INTEGER {
						 none(0),
	                          ethernetII(1),
		  	    	           snap(2),
				           dsap(3),
				           ethernet8023Novell(4),
			     	      ppp(5),
			          	 frameRelay(6),
				           slip(7),
     	                     arap(8),	
          	                loop(9),
                               frameRelayMgmt(10),
                               bridge(11),
                               atm1483(12),
                               atm1577(13),
                               atmLane(14),
                               mcns(15)
			}
   -- Begin managed object definitions here...
-- The Config Group
usrCfgVersion OBJECT-TYPE
	SYNTAX      DisplayString
	MAX-ACCESS  read-only
	STATUS      current
	DESCRIPTION
		"The current software version of the Config Process."
::= { usrConfig 1}
usrCfgConfigFileName OBJECT-TYPE
	SYNTAX      DisplayString
	MAX-ACCESS  read-only
	STATUS      current
	DESCRIPTION		
		"The name of a ConfigFile to read/write  permanent database records."
::= { usrConfig 2 }
usrCfgCFMStatusFlag  OBJECT-TYPE
	SYNTAX	  UsrConfigStatus
	MAX-ACCESS  read-write
	STATUS      current
	DESCRIPTION
		"Setting the value of this object to `save' causes the values
		 of the Config Group to be written out to the current config
		 file, which is stored in the cfgConfigFile object. While
		 the new ConfigFile is being written, the config process
		 will set the value of this flag set to `saving''. Any
		 attempts to set the value while it is  not `normal'
		 (i.e. the file is currently being written to the
		 ConfigFile) while result in a badValue error being
		 returned. Setting the value to `normal' will result in no
		 action."
::= { usrConfig 3 }
usrCfgCFMStatusNetFlag  OBJECT-TYPE
	SYNTAX	UsrConfigStatus
	MAX-ACCESS  read-write
	STATUS      current
	DESCRIPTION
		"Setting the value of this object to `save' causes the values
		 of all the Network Table entries to be written out to the
		 current config file, which is stored in the cfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrConfig 4 }
usrCfgCFMStatusIfFlag  OBJECT-TYPE
	SYNTAX	UsrConfigStatus
	MAX-ACCESS  read-write
	STATUS      current
	DESCRIPTION
		"Setting the value of this object to `save' causes the values
		 of all the IF Table entries to be written out to the
		 current config file, which is stored in the cfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrConfig 5 }
usrCfgCFMStatusNetSvcFlag OBJECT-TYPE
	SYNTAX		UsrConfigStatus
	MAX-ACCESS      	read-write
	STATUS      	current
	DESCRIPTION
		"Setting the value of this object to `save' causes the values
		 of the Network Service Table to be written out to the
		 current config file, which is stored in the usrCfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrConfig 6 }
usrCfgNetTable OBJECT-TYPE
	SYNTAX     SEQUENCE OF UsrCfgNetEntry
	MAX-ACCESS     not-accessible
	STATUS     current
	DESCRIPTION
		"A list of Networks currently configured in the Netserver
		 system."
::= { usrConfig 7 }
usrCfgNetEntry OBJECT-TYPE
	SYNTAX      UsrCfgNetEntry
	MAX-ACCESS      not-accessible
	STATUS      current
	DESCRIPTION
		"An entry containing management information applicable to a
		 particular network."
	INDEX { usrCfgNetName }
::= { usrCfgNetTable 1}
UsrCfgNetEntry ::=
	SEQUENCE {
        usrCfgNetName DisplayString,
		usrCfgNetIfName UsrDisplayString,
		usrCfgNetProtoType INTEGER,
		usrCfgNetEncapType UsrCfgEncapsulations,
		usrCfgNetAddress  UsrNetAddress,
		usrCfgNetStatus INTEGER,
        usrCfgNetLogicalId UsrNetLogicalId,
		usrCfgNetType INTEGER,
		usrCfgNetUserName UsrUserName,
		usrCfgNetCFMStatusFlag UsrConfigStatus,
		usrCfgNewNetIfName UsrDisplayString,
		usrCfgNewNetAddress UsrNetAddress,
		usrCfgNewNetEncapType UsrCfgEncapsulations,
		usrCfgNetRemoteAddress  UsrNetAddress,
		usrCfgNetWanType INTEGER,
		usrCfgNetRpPiNormal INTEGER,
		usrCfgNetVlanTag Integer32
		}
usrCfgNetName OBJECT-TYPE
	SYNTAX      DisplayString (SIZE (1..32))
	MAX-ACCESS  accessible-for-notify
	STATUS      current
	DESCRIPTION
		"The name of this network. Network names can either be assigned
         by a network administrator when the Network is created. Or it will
         generated by the Configuration Process when it adds the network to
		 its internal table. Generated network names will be formed by
		 concatenating the ascii forms of the protocol name, network address
		 and port number separated by hyphens."
::= { usrCfgNetEntry 1}
usrCfgNetIfName OBJECT-TYPE
	SYNTAX      UsrDisplayString (SIZE (1..32))
	MAX-ACCESS  read-write
	STATUS      current
	DESCRIPTION
		"The name of the interface this network runs on top of."
	--CONFIGURABLE
::= { usrCfgNetEntry 2 }
usrCfgNetProtoType OBJECT-TYPE
	SYNTAX     INTEGER {
                         ip(1),
		               ipx(2),
		               at(3),
				     bridge(5),
					frameRelayMgmt(6),
					frameRelayDlci(7),
					ppp(8),
					slip(9)
			          }
	MAX-ACCESS read-write
	STATUS     current
	DESCRIPTION
		"The Level 3 protocol running over this network."
	--CONFIGURABLE
::= { usrCfgNetEntry 3 } 
usrCfgNetAddress OBJECT-TYPE
	SYNTAX      UsrNetAddress
	MAX-ACCESS  read-write
	STATUS      current
	DESCRIPTION
		"The address which identifies the network. The format of
		 this object is dependent on the protocol running on this
		 network."
	--CONFIGURABLE
::= { usrCfgNetEntry 4 }
usrCfgNetEncapType OBJECT-TYPE
	SYNTAX      UsrCfgEncapsulations
	MAX-ACCESS  read-write
	STATUS      current
	DESCRIPTION
		"The type of encapsulation employed by this network."
	--CONFIGURABLE
::= { usrCfgNetEntry 5 }
usrCfgNetStatus OBJECT-TYPE
	SYNTAX      INTEGER {
			    initializing(1),
			    configuring(2),
			    enable(3),  -- Set to this value to enable network 
			    enabling(4),
                            disable(5), -- Set to this value to disable network 
                            disabling(6),
			    invalid(7), -- Set to this value to remove network
			    terminating(8),
			    reconfigure(9) -- Set this value to reconfigure a
                                           -- static IP Network.
			          }
	MAX-ACCESS  read-write
	STATUS      current
	DESCRIPTION
		"The current status of the network entry. The value of this
		 object can be set to one of four values, 'enable', 'disable',
		 'invalid' or 'reconfigure'.
		 Setting the value of 'invalid' causes the network to be removed.
		 The 'enable' value enables a network currently in the 'disable'
		 state.
		 Setting the value to 'disable', disables a network in the 
		 'enable' state. 
		 'reconfigure' will result in the network temporarily disabled
		 and re-configured using any non-NULL values in the usrCfgNewNet...
		 objects. This allows a Network Manager to change an existing
		 network's address, encapsulation, or interface without having to
		 remove the router from service. This status can only be used on
		 static IP networks. Any attempt to 'reconfigure' any other type of
		 network will result in a 'badValue' error.
		 Attempts to set the value of this object to any other values
		 is illegal and will cause a 'badValue' error to be generated."
	--CONFIGURABLE
::= { usrCfgNetEntry 6 }
usrCfgNetLogicalId OBJECT-TYPE
	SYNTAX      UsrNetLogicalId
	MAX-ACCESS  read-only
	STATUS      current
	DESCRIPTION
		"The logical identifier for this network assigned by the Pilgrim
                 forwarder process which owns this network. The value of the
		 LogicalId is returned to the Config Process in the
		 FWD_ENABLE_NETWORK_RSP IPC message."
::= { usrCfgNetEntry 7 }
usrCfgNetType OBJECT-TYPE
	SYNTAX      INTEGER {
                            static(1),
		            dynamic(2),
                            automatic(3)
                            }
	MAX-ACCESS  read-only
	STATUS      current
	DESCRIPTION
		"Networks configured via network management interaction are
           static networks.
           Networks created to service incoming calls are dynamic networks.
           Networks created automatically every time the system reboots (i.e.
           the IP Loopback Network are automatic networks. Automatic networks
           are essentially read-only network entries, the cannot be enabled,
           disabled or deleted."
::= { usrCfgNetEntry 8 }
usrCfgNetUserName OBJECT-TYPE
	SYNTAX       UsrUserName
	MAX-ACCESS   read-write
	STATUS       current
	DESCRIPTION
		"The name of a user (location) associated with a dedicated circuit
		 type network. This object's value is only meaningful for Data Link
		 Control networks (PPP, SLIP, Frame Relay, etc...) over 
		 dedicated/permanent circuits. This name is passed to the Data
		 Link Control Process when the network is created
		 (ADD NETWORK command). The DLCP will use the name to lookup a
		 location profile in User Manager database. For non-dedicated
		 circuit networks, this object's value will always be a 
		 NULL string. Attempts to SET or change the value of this object
		 for non-dedicated circuit networks will fail."
	--CONFIGURABLE
::= { usrCfgNetEntry 9 }
usrCfgNetCFMStatusFlag OBJECT-TYPE
	SYNTAX	UsrConfigStatus
	MAX-ACCESS  read-write
	STATUS      current
	DESCRIPTION
		"Setting the value of this object to `save' causes the values
		 of this Network Table entry to be written out to the
		 current config file, which is stored in the usrCfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrCfgNetEntry 10 }
--
-- The following three objects are used in conjunction with the 'reconfigure'
-- network status. Any object with a non-NULL/zero value, will be used
-- to configure the network setting when a 'reconfigure' request is made
-- through the usrCfgNetStatus object.
--
-- NOTE: These objects and the associated 'reconfigure' command only
--       apply to static IP Networks. Attempts to set values for these
--       objects for any other type of network will fail.
--
usrCfgNewNetIfName OBJECT-TYPE
	SYNTAX      UsrDisplayString (SIZE (0..32))
	MAX-ACCESS  read-write
	STATUS      current
	DESCRIPTION
		"The name of the interface this network runs on top of."
::= { usrCfgNetEntry 11 }
usrCfgNewNetAddress OBJECT-TYPE
	SYNTAX      UsrNetAddress
	MAX-ACCESS  read-write
	STATUS      current
	DESCRIPTION
		"The address which identifies the network. The format of
		 this object is dependent on the protocol running on this
		 network."
::= { usrCfgNetEntry 12 }
usrCfgNewNetEncapType OBJECT-TYPE
	SYNTAX      UsrCfgEncapsulations
	MAX-ACCESS  read-write
	STATUS      current
	DESCRIPTION
		"The type of encapsulation employed by this network."
::= { usrCfgNetEntry 13 }
usrCfgNetRemoteAddress OBJECT-TYPE
        SYNTAX      UsrNetAddress
        MAX-ACCESS  read-write
        STATUS      current
        DESCRIPTION
                "The IP address of the remote router for the network
                 configured as an IP Numbered-Point-To-Point network."
        --CONFIGURABLE
::= { usrCfgNetEntry 14 }
usrCfgNetWanType OBJECT-TYPE
        SYNTAX     INTEGER {
                         none(0),
                         unptp(1),
                         nptp(2),
                         network(3)
                        }
        MAX-ACCESS read-write
        STATUS     current
        DESCRIPTION
                "The Wan Type determines the type of the IP network
                 created on top of the WAN (eg., Frame Relay)."
        --CONFIGURABLE
::= { usrCfgNetEntry 15 }
usrCfgNetRpPiNormal OBJECT-TYPE
        SYNTAX     INTEGER {
                         rp(1),
                         pi(2),
                         normal(3)
                        }
        MAX-ACCESS read-write
        STATUS     current
        DESCRIPTION
                "This flag determines whether the interface being defined
                 is a generic one, or one which supports redundancy of
                 RP and PI interface."
        DEFVAL { normal }
        --CONFIGURABLE
::= { usrCfgNetEntry 17 }
usrCfgNetVlanTag OBJECT-TYPE
        SYNTAX     Integer32 (0..4094) 
        MAX-ACCESS     read-write
        STATUS     current
        DESCRIPTION
                "This determines the VLAN tag that needs to be added to all
                the packets going through this network. By default this value is 0.
		If zero is set then it means that no VLAN tag will be added."
        --CONFIGURABLE
::= { usrCfgNetEntry 18 }
usrCfgIfTable OBJECT-TYPE
	SYNTAX     SEQUENCE OF UsrCfgIfEntry
	MAX-ACCESS not-accessible
	STATUS     current
	DESCRIPTION
		"A list of Interface Names currently configured in the Netserver
		 system."
::= { usrConfig 8 }
usrCfgIfEntry OBJECT-TYPE
	SYNTAX      UsrCfgIfEntry
	MAX-ACCESS  not-accessible
	STATUS      current
	DESCRIPTION
		"An entry containing management information applicable to a
		 particular Interface."
	INDEX { usrCfgIfName }
::= { usrCfgIfTable 1}
UsrCfgIfEntry ::=
	SEQUENCE {
        usrCfgIfName            UsrDisplayString,
		usrCfgIfIndex           Integer32,
		usrCfgIfAdminStatus     INTEGER,
		usrCfgIfLinkUpDownTrapEnable INTEGER,
		usrCfgIfPromiscuousMode INTEGER,
		usrCfgIfInFilter DisplayString,
		usrCfgIfOutFilter DisplayString,
		usrCfgIfFilterAccess INTEGER,
		usrCfgIfSdlCmds INTEGER,
		usrCfgIfSdlCmdResults INTEGER,
		usrCfgIfSysIndex Integer32,
        usrCfgIfManualSwitch Integer32,
		usrCfgIfPolicy UsrDisplayString,
		usrCfgIfPolicyAccess INTEGER,
		usrCfgIfType  Integer32,
		usrCfgIfEthernetOperMode INTEGER
		}
usrCfgIfName OBJECT-TYPE
	SYNTAX      UsrDisplayString (SIZE (1..32))
	MAX-ACCESS      not-accessible
	STATUS      current
	DESCRIPTION
		"The name of this interface.  The value of this
           object is the same as the ifName object of the standard Interface
           table (RFC-1573). This table allows the Pilgrim CLI process to
           translate Interface names into ifIndex values. All the other tables
           in the Pilgrim system relating to interfaces are indexed by the
           ifIndex value of the related interface."
::= { usrCfgIfEntry 1}
usrCfgIfIndex OBJECT-TYPE
	SYNTAX      Integer32
	MAX-ACCESS  read-only
	STATUS      current
	DESCRIPTION
		"The interface index of this interface taken from the standard 
           (RFC-1573) Interface MIB."
::= { usrCfgIfEntry 2 }
usrCfgIfAdminStatus OBJECT-TYPE
       SYNTAX  INTEGER {
                   up(1),       -- ready to pass packets
                   down(2)
               }
       MAX-ACCESS  read-write
       STATUS  current
       DESCRIPTION
               "The permanently configured state of the interface."
	--CONFIGURABLE
::= { usrCfgIfEntry 3 }
usrCfgIfLinkUpDownTrapEnable  OBJECT-TYPE
       SYNTAX      INTEGER { enabled(1), disabled(2) }
       MAX-ACCESS  read-write
       STATUS  current
       DESCRIPTION
               "The permanently configured value, which indicates whether 
	        linkUp/linkDown traps should be generated for this
		interface."
	--CONFIGURABLE
::= { usrCfgIfEntry 4 }
usrCfgIfPromiscuousMode  OBJECT-TYPE
       SYNTAX      INTEGER {
                        enabled(1),
                        disabled(2)
                        }
       MAX-ACCESS  read-write
       STATUS      current
       DESCRIPTION
               "This object has a value of DISABLED if this interface
               only accepts packets/frames that are addressed to this
               station.  This object has a value of ENABLED when the
               station accepts all packets/frames transmitted on the
               media.  The value ENABLED is only legal on certain
               types of media.  If legal, setting this object to a
               value of ENABLED may require the interface to be reset
               before becoming effective.
               The value of ifPromiscuousMode does not affect the
               reception of broadcast and multicast packets/frames by
               the interface.
                This functionality is not supported for wireless
                components."
	--CONFIGURABLE
::= { usrCfgIfEntry 5 }
usrCfgIfInFilter OBJECT-TYPE
	SYNTAX      DisplayString (SIZE(0..20))
	MAX-ACCESS  read-write
	STATUS      current
	DESCRIPTION "The name of the input filter for a specific interface."
      --CONFIGURABLE
::= { usrCfgIfEntry 6 }
usrCfgIfOutFilter OBJECT-TYPE
	SYNTAX      DisplayString (SIZE(0..20))
	MAX-ACCESS  read-write
	STATUS      current
	DESCRIPTION "The name of the output filter for a specific interface."
       --CONFIGURABLE
::= { usrCfgIfEntry 7 }
usrCfgIfFilterAccess OBJECT-TYPE
       SYNTAX      INTEGER {
	                     off (0),
                             on (1)
                           }
       MAX-ACCESS  read-write
       STATUS      current
       DESCRIPTION "This switch will allow user filters to override the
                    interface filters. If set to 'off', user filters do not
		    override the interface filters. If set to 'on' user
		    filters can override the interface filters."
       --CONFIGURABLE
::= {usrCfgIfEntry 8 }
usrCfgIfSdlCmds OBJECT-TYPE
       	SYNTAX INTEGER{
                normal(1),
		download(2),
		forceLinkDown(3)
 	    }
	MAX-ACCESS read-write
	STATUS current
	DESCRIPTION
		"The Software Download Commands are as follows:
		normal: 
		This mode is for normal operation.
		download:
		This command trigger the download for this device.
		forceLinkDown:
		Force the Link to go down while a connection is in progress
 		and download. "
        DEFVAL { normal }
	::= { usrCfgIfEntry 9 }
usrCfgIfSdlCmdResults OBJECT-TYPE
       	SYNTAX INTEGER{
		notSelected(1),
		pending(2),
		active(3),
		failed(4),
		complete(5),
		portBusy(6)
 	    }
	MAX-ACCESS read-write
	STATUS current
	DESCRIPTION
		"The Software Download status are as follows:
 		notSelected: 
		The particular Device is not selected for software download.
		This mode is for normal operation.
 		pending:
		This Device was selected for download, but it has not started.
 		active:
		This Device is currently being downloaded to.
 		failed:
		The download process failed for some reason in this device.
 		complete:
		This Device was successfully downloaded.
		portBusy:
		This Device is busy."
        DEFVAL { notSelected }
	::= { usrCfgIfEntry 10 }
	usrCfgIfSysIndex OBJECT-TYPE
       	SYNTAX Integer32
	MAX-ACCESS read-only
	STATUS current
	DESCRIPTION
		"The index of the Positron System Table that this interface
		 belongs to. The value of this object will always be zero on
		 non-Positron systems."
	::= { usrCfgIfEntry 11 }
usrCfgIfManualSwitch OBJECT-TYPE
	SYNTAX Integer32
	MAX-ACCESS read-write
	STATUS current
	DESCRIPTION
		"This switch controls the Interface status, when a SAVE ALL
		 is issued and it was not disabled by the user. It should not
		 be modified, it is only used by CFM."
	--CONFIGURABLE
::= { usrCfgIfEntry 12  }
usrCfgIfPolicy OBJECT-TYPE
	SYNTAX      UsrDisplayString (SIZE(0..20))
	MAX-ACCESS  read-write
	STATUS      current
	DESCRIPTION "The name of the  policy for a specific interface."
      --CONFIGURABLE
::= { usrCfgIfEntry 13 }
usrCfgIfPolicyAccess OBJECT-TYPE
       SYNTAX      INTEGER {
	                        off (0),
                             on (1)
                           }
       MAX-ACCESS  read-write
       STATUS      current
       DESCRIPTION "This switch will allow user policy to override the
                    interface policy. If set to 'off', user policies do not
				override the interface policy. If set to 'on' user
				policy can override the interface policy."
       --CONFIGURABLE
::= {usrCfgIfEntry 14 }
usrCfgIfType OBJECT-TYPE  
    SYNTAX Integer32
    MAX-ACCESS read-only
    STATUS current    
    DESCRIPTION 
        "The type of interface, distinguished according to
        the physical/link protocol(s) immediately below
        the network layer in the protocol stack."
::= { usrCfgIfEntry 15  } 
usrCfgIfEthernetOperMode OBJECT-TYPE
	SYNTAX INTEGER {
				tenhalfduplex (0),
				tenfullduplex (1),
				hunhalfduplex (2),
				hunfullduplex (3),
				autonegotiate  (4),
				notapplicable (5)
				}
	MAX-ACCESS	read-write
	STATUS		current
	DESCRIPTION "This Variable allows one to change the ethernet device operating
				mode. Modes could be 10Half/10Full/100Half/100Full or Auto Negoti
				ate. This is applicable only for ETHERNET Interfaces supported on
				the HARC-I and HARC-II boards with DP83840A or Level-1 Phys."
	--CONFIGURABLE
::= { usrCfgIfEntry 25 }
usrCfgModuleTable OBJECT-TYPE
	SYNTAX     SEQUENCE OF UsrCfgModuleEntry
	MAX-ACCESS     not-accessible
	STATUS     current
	DESCRIPTION
		"A list of RoboExec Software modules currently configured in the
		 Netserver system."
::= { usrConfig 9 }
usrCfgModuleEntry OBJECT-TYPE
	SYNTAX      UsrCfgModuleEntry
	MAX-ACCESS      not-accessible
	STATUS      current
	DESCRIPTION
		"An entry containing management information applicable to a
		 particular Module."
	INDEX { usrCfgModName }
::= { usrCfgModuleTable 1}
UsrCfgModuleEntry ::=
	SEQUENCE {
          usrCfgModName
			DisplayString,
		usrCfgModType
			INTEGER,
		usrCfgModFileName
			DisplayString,
		usrCfgModCfgFileName
			DisplayString,
		usrCfgModDescr
			DisplayString,
		usrCfgModMasterProcess
			DisplayString,
		usrCfgModStatus
			INTEGER
		}
usrCfgModName OBJECT-TYPE
	SYNTAX      DisplayString (SIZE (1..32))
	MAX-ACCESS      not-accessible
	STATUS      current
	DESCRIPTION
		"The name of this module."
::= { usrCfgModuleEntry 1}
usrCfgModType OBJECT-TYPE
	SYNTAX      INTEGER { linked(1), loadable(2) }
	MAX-ACCESS  read-only
	STATUS      current
	DESCRIPTION
		"The module type."
::= { usrCfgModuleEntry 2}
usrCfgModFileName OBJECT-TYPE
	SYNTAX      DisplayString
	MAX-ACCESS  read-only
	STATUS      current
	DESCRIPTION
		"The module's down-loadable file name. For 'linked' modules
		 the value will always be a zero length string, and no
		 SET operations will be allowed. If no file name is specified
		 when a new entry is added to the table, the Config Process will
		 attempt to load the file '@file//<usrCfgModName.mod"
	--CONFIGURABLE
::= { usrCfgModuleEntry 3}
usrCfgModCfgFileName OBJECT-TYPE
	SYNTAX      DisplayString
	MAX-ACCESS  read-only
	STATUS      current
	DESCRIPTION
		"The module's Configuration file name. This file contains the
		 module's permanent configuration records. The value of this
		 object is passed to the module's master process's initialization
		 routine via the 'init_arg' parameter."
	--CONFIGURABLE
::= { usrCfgModuleEntry 4}
usrCfgModDescr OBJECT-TYPE
	SYNTAX      DisplayString (SIZE(0..128))
	MAX-ACCESS  read-only
	STATUS      current
	DESCRIPTION
		"A longer string describing the module."
::= { usrCfgModuleEntry 5}
usrCfgModMasterProcess OBJECT-TYPE
	SYNTAX      DisplayString (SIZE(1..32))
	MAX-ACCESS  read-only
	STATUS      current
	DESCRIPTION
		"The name of the master process of this module."
::= { usrCfgModuleEntry 6}
usrCfgModStatus OBJECT-TYPE
	SYNTAX      INTEGER {	initializing(1),
						configuring(2),
						loading(3),
						loaded(4),
						terminate(5),
						terminating(6),
						unload(7),
						unloading(8),
						broken(9) }
	MAX-ACCESS  read-write
	STATUS      current
	DESCRIPTION
		"Status flags to control and display the module's current state.
		 Only the values 'terminate' and 'unload' may be set by a
		 Network Manager process. Adding a new entry to the table will
		 trigger the Config Process to load the module."
::= { usrCfgModuleEntry 7}
usrCfgAvailServiceTable OBJECT-TYPE
	SYNTAX SEQUENCE OF USRCfgAvailServiceEntry
	MAX-ACCESS not-accessible
	STATUS current
	DESCRIPTION
		"This table defines the available services from the router."
::= { usrConfig 10 }
usrCfgAvailServiceEntry OBJECT-TYPE
	SYNTAX USRCfgAvailServiceEntry
	MAX-ACCESS not-accessible
	STATUS current
	DESCRIPTION
		"An entry containing management information for a 
		particular available service."
	INDEX { usrCfgAvailServiceIndex }
::= { usrCfgAvailServiceTable 1 }
USRCfgAvailServiceEntry ::=
	SEQUENCE {
		usrCfgAvailServiceIndex
			Integer32,
		usrCfgAvailServiceName
			DisplayString,
		usrCfgAvailServiceDescription
			DisplayString,
		usrCfgAvailServiceType
			INTEGER,
		usrCfgAvailServiceProtocol
			INTEGER,
		usrCfgAvailServiceModuleName
			DisplayString
	 }
usrCfgAvailServiceIndex OBJECT-TYPE
	SYNTAX Integer32
	MAX-ACCESS not-accessible
	STATUS current
	DESCRIPTION
		"An index into this table."
::= { usrCfgAvailServiceEntry 1 }
usrCfgAvailServiceName OBJECT-TYPE
	SYNTAX DisplayString (SIZE(1..32))
	MAX-ACCESS read-only
	STATUS current
	DESCRIPTION
		"The handle by which this service is known."
::= { usrCfgAvailServiceEntry 2 }
usrCfgAvailServiceDescription OBJECT-TYPE
	SYNTAX DisplayString
	MAX-ACCESS read-only
	STATUS current
	DESCRIPTION
		"A textual description of the service."
::= { usrCfgAvailServiceEntry 3 }
usrCfgAvailServiceType OBJECT-TYPE
	SYNTAX INTEGER {
			cfgSrvNetwork(1),
			cfgSrvTerminal(2),
			cfgSrvBoth(3),
			cfgSrvNeither(4)
		}
	MAX-ACCESS read-only
	STATUS current
	DESCRIPTION
		"What type of service does this entry describe?."
::= { usrCfgAvailServiceEntry 4 }
usrCfgAvailServiceProtocol OBJECT-TYPE
	SYNTAX INTEGER {
			cfgSrvTCP(1),
			cfgSrvUDP(2),
			cfgSrcIPX(3),
			cfgSrvSPX(4),
			cfgSrvDDP(5),
			cfgSrvADSP(6),
			cfgSrvNCSI(7)
		}
	MAX-ACCESS read-only
	STATUS current
	DESCRIPTION
		"This describes the Transport protocol on which the service resides."
::= { usrCfgAvailServiceEntry 5 }
usrCfgAvailServiceModuleName OBJECT-TYPE
	SYNTAX DisplayString (SIZE(1..32))
	MAX-ACCESS read-only
	STATUS current
	DESCRIPTION
		"The Pilgrim module which implements this service.."
::= { usrCfgAvailServiceEntry 6 }
usrCfgNetworkServiceTable OBJECT-TYPE
	SYNTAX SEQUENCE OF UsrCfgNetworkServiceEntry
	MAX-ACCESS not-accessible
	STATUS current
	DESCRIPTION
		"This table defines the Network services provided by Pilgrim"
::= { usrConfig 11 }
usrCfgNetworkServiceEntry OBJECT-TYPE
	SYNTAX UsrCfgNetworkServiceEntry
	MAX-ACCESS not-accessible
	STATUS current
	DESCRIPTION
		"An entry containing management information for a 
		particular network service."
	INDEX { usrCfgNetworkServiceAdminName }
::= { usrCfgNetworkServiceTable 1 }
UsrCfgNetworkServiceEntry ::=
	SEQUENCE {
		usrCfgNetworkServiceAdminName
			DisplayString,
		usrCfgNetworkServiceName
			DisplayString,
		usrCfgNetworkServiceSocketNumber
			INTEGER,
		usrCfgNetworkServiceAncillaryData
			OCTET STRING,
		usrCfgNetworkServiceCloseActiveServices
			TruthValue,
		usrCfgNetworkServiceStatus
			INTEGER,
		usrCfgNetworkServiceCFMStatusFlag
			UsrConfigStatus
	 }
usrCfgNetworkServiceAdminName OBJECT-TYPE
	SYNTAX DisplayString (SIZE(1..32))
	MAX-ACCESS not-accessible
	STATUS current
	DESCRIPTION
		"The name by which the administrator identifies this service."
::= { usrCfgNetworkServiceEntry 1 }
usrCfgNetworkServiceName OBJECT-TYPE
	SYNTAX DisplayString (SIZE(1..32))
	MAX-ACCESS read-write
	STATUS current
	DESCRIPTION
		"The available service providing this network service.
		Must be the an entry from the Available Services Table."
	--CONFIGURABLE
::= { usrCfgNetworkServiceEntry 2 }
usrCfgNetworkServiceSocketNumber OBJECT-TYPE
	SYNTAX INTEGER (0..65535)
	MAX-ACCESS read-write
	STATUS current
	DESCRIPTION
		"The number of the socket for this service."
	--CONFIGURABLE
::= { usrCfgNetworkServiceEntry 3 }
usrCfgNetworkServiceAncillaryData OBJECT-TYPE
	SYNTAX OCTET STRING
	MAX-ACCESS read-write
	STATUS current
	DESCRIPTION
		"This specifies any other data that the service needs
		for its definition. To reset this SET to 'none'."
	--CONFIGURABLE
::= { usrCfgNetworkServiceEntry 4 }
usrCfgNetworkServiceCloseActiveServices OBJECT-TYPE
	SYNTAX TruthValue
	MAX-ACCESS read-write
	STATUS current
	DESCRIPTION
		"This variable determines if active sessions using this service
		are closed when the service is set to inactive or invalid"
	--CONFIGURABLE
::= { usrCfgNetworkServiceEntry 5 }
usrCfgNetworkServiceStatus OBJECT-TYPE
	SYNTAX INTEGER {
			enable(1),
			disable(2),
			delete(3)
		}
	MAX-ACCESS read-write
	STATUS current
	DESCRIPTION
		"Setting this variable to delete removes the service."
	--CONFIGURABLE
::= { usrCfgNetworkServiceEntry 6 }
usrCfgNetworkServiceCFMStatusFlag OBJECT-TYPE
	SYNTAX	UsrConfigStatus
	MAX-ACCESS  read-write
	STATUS      current
	DESCRIPTION
		"Setting the value of this object to `save' causes the values
		 of this Network Service Table entry to be written out to the
		 current config file, which is stored in the usrCfgConfigFile
		 object. While the new ConfigFile is being written, the config
		 process will set the value of this flag set to `saving''. Any
		 attempts to set the value while it is  not `normal'
		 (i.e. the file is currently being written to the
		 ConfigFile) while result in a badValue error being
		 returned. Setting the value to `normal' will result in no
		 action."
::= { usrCfgNetworkServiceEntry 7 }
usrCfgRebootFlag OBJECT-TYPE
	SYNTAX	INTEGER {
				normal(1),
				reboot(2),
				shutdown(3),
				resetConfiguration(4)
			}
	MAX-ACCESS  read-write
	STATUS      current
	DESCRIPTION
		"Setting the value of this object to `reboot' causes the
		 the system to gracefully shutdown and then reboot. Setting
		 the value to `shutdown' causes the system to shutdown and not
		 reboot automatically. The value `resetConfiguration' will
		 reset the system configuration to the 'factory default'
		 configuration and then reboot the system. Setting
		 the value to `normal' will result in no action."
::= { usrConfig 12 }
usrCfgTransmitAuthenName OBJECT-TYPE
	SYNTAX UsrUserName
	MAX-ACCESS read-write
	STATUS current
	DESCRIPTION
		"The System wide transmit authentication user name."
	--CONFIGURABLE
::= { usrConfig 13 }
usrCfgSystemVersion OBJECT-TYPE
	SYNTAX DisplayString
	MAX-ACCESS read-only
	STATUS current
	DESCRIPTION
		"The software release version of this system."
::= { usrConfig 14 }
usrCfgImageFileName OBJECT-TYPE
	SYNTAX DisplayString
	MAX-ACCESS read-only
	STATUS current
	DESCRIPTION
		"The file name of the software image which this product loads
           when the system reboots. The value of this object is used by the
           USR Access Router Manager when it downloads a new version of the
           router software."
::= { usrConfig 15 }
usrCfgDownLoadStatus OBJECT-TYPE
	SYNTAX	INTEGER {
				normal(1),
				triggerDownLoad(2),
				deletingImageFile(3),
				readyForDownLoad(4)
			}
	MAX-ACCESS  read-write
	STATUS      current
	DESCRIPTION
		"This value is used to  prepare the system to receive a
		 new system image via TFTP. A Network Management
		 station initiates a system image download by setting the
		 value of this object to 'triggerDownLoad'. The system then sets
		 the state to 'deletingImageFile', while it removes the current
		 image file from the flash file system. This frees up space in the
		 flash file system for the new image. 
		 When the old image file is deleted, the value of this will be
		 changed to 'readyForDownLoad'. The NMS is expected to poll
		 this MIB object until this state is reached. Then it can 
		 begin a TFTP download of the new image file.
		 (NOTE: if the system crashes or reboots during the 
		 'deleteingImageFile' or 'readyForDownLoad' states, the system
		 will NOT reboot, and the image must be update via a console
		 port Software Down Load.)
		 After the new system image TFTP download has been completed,
		 the NMS **MUST** set this object back to the 'normal' state.
		 A system shutdown or reboot via the usrCfgRebootFlag object 
		 will not be allowed unless the this object has been reset to
		 'normal'."
::= { usrConfig 16 }
usrCfgLossOfServiceChecking OBJECT-TYPE
	SYNTAX TruthValue
	MAX-ACCESS read-write
	STATUS current
	DESCRIPTION
		"Specifies whether the configurator will allow the modems to
		 be busied out if a loss of service is detected.
		 This feature may not be available on all systems."
	DEFVAL	{ 1 }
	--CONFIGURABLE
::= { usrConfig 17 }
usrCfgBulkFileGroup OBJECT IDENTIFIER ::= { usrConfig 18 }
usrCfgBulkFileStatus OBJECT-TYPE
	SYNTAX	INTEGER {
				normal(1),
				createBulkFile(2),
				creatingBulkFile(3),
				restoreBulkFile(4),
				restoringBulkFile(5),
				bulkFileError(6)
			}
	MAX-ACCESS  read-write
	STATUS      current
	DESCRIPTION
		"This object is used to allow the system to prepare a
		 Bulk configuration file that is retrievable via TFTP.
		 A bulk configuration file is created by setting the
		 value of this object to 'createBulkFile'. The system
		 then sets this object to 'creatingBulkFile' and
		 concatenates the individual .cfg files into a single
		 file indicated by the object usrCfgBulkFileName.
		 The individual .cfg files can be restored by setting
		 the value of this object to 'restoreBulkFile'. The
		 system then sets this object to 'restoringBulkFile'
		 and splits the file indicated by the object
		 usrCfgBulkFileName into the individual .cfg files.
		 Note: the file indicated by the object usrCfgBulkFileName
		 must be present in the file system for this to succeed.
		 The operation is completed when the value of this object
		 is set back to 'normal' or 'bulkFileError' which indicates
		 that an error occurred."
::= { usrCfgBulkFileGroup 1 }
usrCfgBulkFileName OBJECT-TYPE
	SYNTAX	DisplayString (SIZE(0..32))
	MAX-ACCESS  read-write
	STATUS      current
	DESCRIPTION
		"This is the name of the Bulk File that will be acted upon
		 when usrCfgBulkFileStatus is set to 'createBulkFile' or
		 'restoreBulkFile'."
	DEFVAL { "ConfigBulkFile" }
	--CONFIGURABLE
::= { usrCfgBulkFileGroup 2 }
usrCfgBulkFileErrorMessage OBJECT-TYPE
	SYNTAX	OCTET STRING (SIZE(0..256))
	MAX-ACCESS	read-only
	STATUS	current
	DESCRIPTION
		"When the value of usrCfgBulkFileStatus is 'bulkFileError',
		 this object will indicate the error that occurred."
::= { usrCfgBulkFileGroup 3 }
usrConfigTraps OBJECT IDENTIFIER ::= { usrConfig 19 }
usrConfigTrapsv2 OBJECT-IDENTITY
        STATUS  current
        DESCRIPTION
                "The events for Configuration Management traps"
::= { usrConfigTraps 0 }
usrCfgDynNetCreated NOTIFICATION-TYPE
	OBJECTS { usrCfgNetName }
    STATUS  current
	DESCRIPTION
		"A usrCfgDynNetCreated message signifies that the sending 
		 CommWorks Remote Access Router has just established a
		 Dynamic Network to service a dialup network user."
::= { usrConfigTrapsv2 1 }
usrCfgDynNetRemoved NOTIFICATION-TYPE
	OBJECTS { usrCfgNetName }
        STATUS  current
	DESCRIPTION
		"A usrCfgDynNetRemoved trap signifies that the sending 
		 CommWorks Remote Access Router has just removed a
		 Dynamic Network associated with a recently disconnected
		 dialup network user"
::= { usrConfigTrapsv2 2 }
-- Enterprise traps being added to include slot number information also
usrCfgSlot OBJECT-TYPE
         SYNTAX INTEGER (0..16)
         MAX-ACCESS  read-only
         STATUS  current
         DESCRIPTION
            "The non-zero slot number holding this blade.
             If the slot number is not determinable, such as for the testbed,
             then the value is 0."
        ::= { usrConfig 40 }
usrCfgLinkUpDownTrapType  OBJECT-TYPE
       SYNTAX   INTEGER {
                rfcTrap(1),
                cfgTrap(2),
                rfcCfgTrap(3) }
       MAX-ACCESS  read-write
       STATUS  current
       DESCRIPTION
               "The type of linkUp/linkDown trap generated.
                rfcTrap(1) - IF-MIB linkUp / LinkDown trap upon link up/dn
                cfgTrap(2) - USR-CONFIG-MIB usrCfgLinkUp / usrCfgLinkDown upon link up/dn
                rfcCfgTrap(3) - both linkUp and usrCfgLinkUp trap upon link up both 
                linkDown and usrCfgLinkDown trap upon link dn "
       DEFVAL { rfcTrap }
--CONFIGURABLE
      ::= { usrConfig 41 }
usrCfgLinkDown NOTIFICATION-TYPE
    OBJECTS { ifIndex, ifAdminStatus, ifOperStatus, usrCfgSlot }
    STATUS  current
    DESCRIPTION
            "A usrCfgLinkDown trap signifies that the SNMP entity, acting in
            an agent role, has detected that the ifOperStatus object for
            one of its communication links is about to enter the down
            state from some other state (but not from the notPresent
            state).  This other state is indicated by the included value
            of ifOperStatus.  usrCfgSlot is the slot number holding the blade."
	          --#TYPE	"Network Interface Down Event"
	          --#SUMMARY	"Network Interface: %d failure on slot number %d"
	          --#ARGUMENTS { 0 3 }
	          --#SEVERITY MAJOR
	          --#STATE	NONOPERATIONAL
	          --#PROBABLECAUSE "Adaptor Error" 
    ::= { usrConfigTrapsv2 3 }
usrCfgLinkUp NOTIFICATION-TYPE
    OBJECTS { ifIndex, ifAdminStatus, ifOperStatus, usrCfgSlot }
    STATUS  current
    DESCRIPTION
            "A usrCfgLinkUp trap signifies that the SNMP entity, acting in an
            agent role, has detected that the ifOperStatus object for
            one of its communication links left the down state and
            transitioned into some other state (but not into the
            notPresent state).  This other state is indicated by the
            included value of ifOperStatus.
            usrCfgSlot is the slot number holding the blade."
	          --#TYPE	"Network Interface Up Event"
	          --#SUMMARY	"Network Interface: %d restored on slot number %d"
	          --#ARGUMENTS { 0 3 }
	          --#SEVERITY CLEARED
	          --#STATE	OPERATIONAL
	          --#PROBABLECAUSE "Disconnected cable has been connected." 
    ::= { usrConfigTrapsv2 4 }
usrCfgTunnelConnTable OBJECT-TYPE
	SYNTAX     SEQUENCE OF UsrCfgTunnelConnEntry
	MAX-ACCESS     not-accessible
	STATUS     current
	DESCRIPTION
		"A list of dynamic tunneling connections currently
           active in the Netserver system."
::= { usrConfig 20 }
usrCfgTunnelConnEntry OBJECT-TYPE
	SYNTAX      UsrCfgTunnelConnEntry
	MAX-ACCESS      not-accessible
	STATUS      current
	DESCRIPTION
		"An entry containing management information applicable to a
		 particular Connection."
	INDEX { usrCfgTunnelConnIfName }
::= { usrCfgTunnelConnTable 1}
UsrCfgTunnelConnEntry ::=
	SEQUENCE {
          usrCfgTunnelConnIfName DisplayString,
		usrCfgTunnelConnUserName OCTET STRING,
		usrCfgTunnelConnTunnelType INTEGER,
		usrCfgTunnelConnStartTime Integer32
		}
usrCfgTunnelConnIfName OBJECT-TYPE
	SYNTAX      DisplayString (SIZE (1..32))
	MAX-ACCESS      not-accessible
	STATUS      current
	DESCRIPTION
		"The name of this dynamic tunneling interface."
::= { usrCfgTunnelConnEntry 1}
usrCfgTunnelConnUserName OBJECT-TYPE
	SYNTAX      OCTET STRING (SIZE (1..32))
	MAX-ACCESS  read-only
	STATUS      current
	DESCRIPTION
		"The name of the user for this connection."
::= { usrCfgTunnelConnEntry 2}
usrCfgTunnelConnTunnelType OBJECT-TYPE
	SYNTAX      INTEGER {
                    pptp(1),
                    l2f(2),
                   l2tp(3),
                    atmp(4),
                    vtp(5),
                    ah(6),
                    ip-ip(7),
                    min-ip-ip(8),
                    esp(9),
                    gre(10),
                    drs(11)
                    }
	MAX-ACCESS  read-only
	STATUS      current
	DESCRIPTION
		"The tunneling protocol used for this connection."
::= { usrCfgTunnelConnEntry 3}
usrCfgTunnelConnStartTime OBJECT-TYPE
	SYNTAX      Integer32
	MAX-ACCESS  read-only
	STATUS      current
	DESCRIPTION
          "The start time of the connection."
::= { usrCfgTunnelConnEntry 4}
usrCfgSecurityService OBJECT-TYPE                                          
        SYNTAX  INTEGER {
                    radius(1),
                    tacacsplus(2)                                          
                }                                                          
        MAX-ACCESS  read-write
        STATUS      current
        DESCRIPTION
                "Specifies the security service client process that gets started
                at boot time."
        DEFVAL  { 1 } 
    --CONFIGURABLE
::= { usrConfig 21 }
usrCfgLogicalIfTable OBJECT-TYPE
    SYNTAX     SEQUENCE OF UsrCfgLogicalIfEntry
    MAX-ACCESS     not-accessible
    STATUS     current
    DESCRIPTION
        "A list of Logical Interface Names currently configured in the Netserver
         system."
::= { usrConfig 22 }
usrCfgLogicalIfEntry OBJECT-TYPE
    SYNTAX      UsrCfgLogicalIfEntry
    MAX-ACCESS  not-accessible
    STATUS      current
    DESCRIPTION
        "An entry containing management information applicable to a
         particular Interface."
    INDEX { usrCfgLogicalIfName }
::= { usrCfgLogicalIfTable 1}
UsrCfgLogicalIfEntry ::=
    SEQUENCE {
             usrCfgLogicalIfName DisplayString,
             usrCfgLogicalIfNonObject Integer32
             }
usrCfgLogicalIfName OBJECT-TYPE
    SYNTAX      DisplayString (SIZE (1..32))
    MAX-ACCESS  read-write
    STATUS      current
    DESCRIPTION
        "The name of this interface. "
	--CONFIGURABLE
::= { usrCfgLogicalIfEntry 1}
usrCfgLogicalIfNonObject OBJECT-TYPE
    SYNTAX      Integer32
    MAX-ACCESS  read-only
    STATUS      obsolete
    DESCRIPTION
        "Fix for compiler which doesn't accept table without
         any auxiliary objects! Code will return NO_SUCH_OBJECT."
::= { usrCfgLogicalIfEntry 2}
usrCfgLogicalIfRefTable OBJECT-TYPE
    SYNTAX     SEQUENCE OF UsrCfgLogicalIfRefEntry
    MAX-ACCESS not-accessible
    STATUS     current
    DESCRIPTION
        "A list of Logical Interface Names and Index. This table is used as a reference for 
         retrieving the stored index of LogicalIf"
::= { usrConfig 23 }
usrCfgLogicalIfRefEntry OBJECT-TYPE
    SYNTAX      UsrCfgLogicalIfRefEntry
    MAX-ACCESS  not-accessible
    STATUS      current
    DESCRIPTION
        "An entry containing management information applicable to a
         particular Interface."
    INDEX { usrCfgLogicalIfRefName }
::= { usrCfgLogicalIfRefTable 1}
UsrCfgLogicalIfRefEntry ::=
    SEQUENCE {
             usrCfgLogicalIfRefName     DisplayString,
             usrCfgLogicalIfRefIndex    Integer32
             }
usrCfgLogicalIfRefName OBJECT-TYPE
    SYNTAX      DisplayString (SIZE (1..32))
    MAX-ACCESS  read-write
    STATUS      current
    DESCRIPTION
        "The name of this interface. "
	--CONFIGURABLE
::= { usrCfgLogicalIfRefEntry 1}
usrCfgLogicalIfRefIndex OBJECT-TYPE
    SYNTAX      Integer32
    MAX-ACCESS  read-write
    STATUS      current
    DESCRIPTION
        "The index of this logical interface. "
	--CONFIGURABLE
::= { usrCfgLogicalIfRefEntry 2}
usrCfgResetEEpromStatus OBJECT-TYPE
        SYNTAX      INTEGER {
                        enabled(1),
                        disabled(2)
                        }
        MAX-ACCESS  read-write
        STATUS      current
        DESCRIPTION
                " Specifies whether boot prom needs to be initialised."
    --CONFIGURABLE
::= { usrConfig 24 }
usrCfgModemGroupFilterTable OBJECT-TYPE
    SYNTAX     SEQUENCE OF UsrCfgModemGroupFilterEntry
    MAX-ACCESS     not-accessible
    STATUS     obsolete
    DESCRIPTION
         "list of filter operations in a particular modem group.
          Obsolete : This is no longer used."
::= { usrConfig 28 }
usrCfgModemGroupFilterEntry OBJECT-TYPE
    SYNTAX      UsrCfgModemGroupFilterEntry
    MAX-ACCESS      not-accessible
    STATUS      obsolete
    DESCRIPTION
        "An entry containing management information applicable to a
         particular modem group.
         Obsolete : This is no longer used."
    INDEX { usrCfgModemGroupName }
::= { usrCfgModemGroupFilterTable 1}
UsrCfgModemGroupFilterEntry ::=
    SEQUENCE {
             usrCfgModemGroupName DisplayString,
             usrCfgModemGroupFilterAccess  INTEGER,
             usrCfgModemGroupInFilter DisplayString,
             usrCfgModemGroupOutFilter DisplayString
             }
usrCfgModemGroupName OBJECT-TYPE
    SYNTAX      DisplayString (SIZE (1..32))
    MAX-ACCESS      not-accessible
    STATUS      obsolete
    DESCRIPTION
        "The name of this modem group
         Obsolete : This is no longer used."
    --CONFIGURABLE
::= { usrCfgModemGroupFilterEntry 1}
usrCfgModemGroupFilterAccess OBJECT-TYPE
        SYNTAX      INTEGER {
                            off (0),
                             on (1)
                           }
        MAX-ACCESS  read-write
        STATUS      obsolete
     DESCRIPTION
                "This is for setting a filter access for all the
                interfaces in a particular modem group.
                Obsolete : This is no longer used."
    --CONFIGURABLE
::= { usrCfgModemGroupFilterEntry 2 }
usrCfgModemGroupInFilter OBJECT-TYPE
    SYNTAX      DisplayString (SIZE(0..20))
    MAX-ACCESS  read-write
    STATUS      obsolete
    DESCRIPTION "The name of the input filter for a specific modem group.
                 Obsolete : This is no longer used."
      --CONFIGURABLE
::= { usrCfgModemGroupFilterEntry 3 }
usrCfgModemGroupOutFilter OBJECT-TYPE
    SYNTAX      DisplayString (SIZE(0..20))
    MAX-ACCESS  read-write
    STATUS      obsolete
    DESCRIPTION "The name of the output filter for a specific group.
                 Obsolete : This is no longer used."
       --CONFIGURABLE
::= { usrCfgModemGroupFilterEntry 4 }
usrCfgTransmitPassword OBJECT-TYPE
    SYNTAX  OCTET STRING (SIZE (1..32))
    MAX-ACCESS  read-write
    STATUS  current
    DESCRIPTION
        "System password transmitted with auth name, when password is not 
	 available from other sources; reading this object returns NULL"
    --CONFIGURABLE
    ::= { usrConfig 33 }
usrCfgCFMStatusSettingsFlag  OBJECT-TYPE
	SYNTAX	  UsrConfigStatus
	MAX-ACCESS  read-write
	STATUS      current
	DESCRIPTION
		"Setting the value of this object to `save' causes the values
		 of the Config Group to be written out to the current config
		 file, which is stored in the cfgConfigFile object. While
		 the new ConfigFile is being written, the config process
		 will set the value of this flag set to `saving''. Any
		 attempts to set the value while it is  not `normal'
		 (i.e. the file is currently being written to the
		 ConfigFile) while result in a badValue error being
		 returned. Setting the value to `normal' will result in no
		 action."
::= { usrConfig 38 }
usrCfgNetworksConfigFileName OBJECT-TYPE
	SYNTAX      DisplayString
	MAX-ACCESS  read-only
	STATUS      current
	DESCRIPTION		
		"The name of a ConfigFile to read/write Configurator IP Networks."
::= { usrConfig 39 }
usrCfgIpRedundancy OBJECT-TYPE
	SYNTAX      INTEGER {
		enable(1),
		disable(2)
        }
        MAX-ACCESS  read-write
        STATUS      current
        DESCRIPTION
                " Specifies whether the redundancy interconnect feature is enabled or not."
    DEFVAL	{ disable }
    --CONFIGURABLE
::= { usrConfig 35 }
usrCfgRpIfName OBJECT-TYPE
	SYNTAX      DisplayString (SIZE (1..32))
	MAX-ACCESS  read-write
	STATUS      current
	DESCRIPTION
		"The name of the RP interface
         Returns NULL string if not configured."
	--CONFIGURABLE
::= { usrConfig 36 }
usrCfgPiIfName OBJECT-TYPE
	SYNTAX      DisplayString (SIZE (1..32))
	MAX-ACCESS  read-write
	STATUS      current
	DESCRIPTION
		"The name of the PI interface
         Returns NULL string if not configured."
	--CONFIGURABLE
::= { usrConfig 37 }
END  -- End of USR-CONFIG-MIB DEFINITIONS
-- ************************************************************************
--
--	REmib.mib - The RoboExec MIB
--
-- Author:	    Jim Halpin
--
   ROBOEXEC-RESOURCES-MIB DEFINITIONS ::= BEGIN
   IMPORTS
      OBJECT-TYPE, NOTIFICATION-TYPE, MODULE-IDENTITY, OBJECT-IDENTITY,
	  Counter32, Integer32
            FROM SNMPv2-SMI
	  common, UsrConfigStatus
            FROM USR-DEFINITIONS-MIB
      DisplayString, DateAndTime
            FROM SNMPv2-TC;
    roboExec MODULE-IDENTITY
         LAST-UPDATED "200208231355Z"
         ORGANIZATION "CommWorks Corporation, a 3Com Company"
         CONTACT-INFO "Customer Support"
         DESCRIPTION
                 "The commWorks enterprise defined MIB objects
                   for the RoboExec"
--      REVISION "200208231355Z"
--      DESCRIPTION "CLarified usage and labels for usrreMemoryTrapStatus."
--      REVISION "200205052006Z"
--      DESCRIPTION "Converted to SNMPv2"
         ::= { common 3 }
   usrreSystem		  OBJECT IDENTIFIER ::= { roboExec 1 }
   usrreSWRun		  OBJECT IDENTIFIER ::= { roboExec 2 }
   usrreEvents		  OBJECT IDENTIFIER ::= { roboExec 3 }
   usrreCounters	  OBJECT IDENTIFIER ::= { roboExec 5 }
   usrreNames		  OBJECT IDENTIFIER ::= { roboExec 6 }
   usrreFiles		  OBJECT IDENTIFIER ::= { roboExec 7 }
   usrreMemTrapSettings   OBJECT IDENTIFIER ::= { roboExec 8 }
   usrreTraps             OBJECT IDENTIFIER ::= { roboExec 9 }
   -- textual conventions
   -- memory size, expressed in units of 1024bytes
   KBytes ::=	  Integer32 (0..2147483647)
   -- The RoboExec Resources System Group
   --
   -- Implementation of this group is mandatory for all RoboExec systems.
   usrreSystemDate OBJECT-TYPE
	  SYNTAX DateAndTime
	  MAX-ACCESS read-write
	  STATUS current
	  DESCRIPTION
		    "The RoboExec's notion of the local date and time of
		    day."
	  ::= { usrreSystem 1 }
   usrreMemorySize OBJECT-TYPE
	  SYNTAX KBytes
	  MAX-ACCESS read-only
	  STATUS current
	  DESCRIPTION
		    "The amount of physical main memory maintained by
		    the RoboExec."
	  ::= { usrreSystem 2 }
   usrreFreeMemorySize OBJECT-TYPE
	  SYNTAX KBytes
	  MAX-ACCESS read-only
	  STATUS current
	  DESCRIPTION
		    "The amount of free physical main memory maintained by
		    the RoboExec."
	  ::= { usrreSystem 3 }
   usrreTextSize OBJECT-TYPE
	  SYNTAX KBytes
	  MAX-ACCESS read-only
	  STATUS current
	  DESCRIPTION
		    "The number of Kbytes of text (code) in the executable."
	  ::= { usrreSystem 4 }
   usrreInitDataSize OBJECT-TYPE
	  SYNTAX KBytes
	  MAX-ACCESS read-only
	  STATUS current
	  DESCRIPTION
		    "The number of Kbytes of initialized data in the executable."
	  ::= { usrreSystem 5 }
   usrreUninitDataSize OBJECT-TYPE
	  SYNTAX KBytes
	  MAX-ACCESS read-only
	  STATUS current
	  DESCRIPTION
		    "The number of Kbytes of uninitialized data in the executable."
	  ::= { usrreSystem 6 }
   usrreStackSize OBJECT-TYPE
	  SYNTAX KBytes
	  MAX-ACCESS read-only
	  STATUS current
	  DESCRIPTION
		    "The size of the stack in Kbytes provided for the executable."
	  ::= { usrreSystem 7 }
   usrreMaxHeapAllocated OBJECT-TYPE
	  SYNTAX KBytes
	  MAX-ACCESS read-only
	  STATUS current
	  DESCRIPTION
		    "The maximum amount of memory ever allocated from the
		    RoboExec heap."
	  ::= { usrreSystem 8 }
   usrreLargestMemoryBlockAddress OBJECT-TYPE
       SYNTAX DisplayString
       MAX-ACCESS read-only
       STATUS current
       DESCRIPTION
              "The address of the largest memory block ever
               allocated from heap."
       ::= { usrreSystem 9 }
      usrreLargestMemoryBlockSize OBJECT-TYPE
       SYNTAX KBytes
       MAX-ACCESS read-only
       STATUS current
       DESCRIPTION
              "The size (in kilobytes) of the largest memory block ever 
               allocated from heap."
       ::= { usrreSystem 10 }
      usrreLargestMemoryBlockCorrelator OBJECT-TYPE
       SYNTAX DisplayString
       MAX-ACCESS read-only
       STATUS current
       DESCRIPTION
              "An ASCII string indicating what process allocated 
               the largest memory block from heap."
       ::= { usrreSystem 11 }
      usrreLargestMemoryBlockState OBJECT-TYPE
       SYNTAX INTEGER {
                free(0),             -- Memory block was freed for further reuse
                allocated(1)  
            }       
       MAX-ACCESS read-only
       STATUS current
       DESCRIPTION
              "The state of the largest memory block:
                        0 - was freed for further reuse;
                        1 - is allocated."
       ::= { usrreSystem 12 }
      usrreCPULoadAvg OBJECT-TYPE
	  SYNTAX Integer32 (0..100)
       MAX-ACCESS read-only
       STATUS current
       DESCRIPTION
              "System CPU load Percentage (Instantaneous)."
       ::= { usrreSystem 13 }
      usrreCPULoadAvgMinute OBJECT-TYPE
	  SYNTAX Integer32 (0..100)
       MAX-ACCESS read-only
       STATUS current
       DESCRIPTION
              "System CPU load Percentage for last minute."
       ::= { usrreSystem 14 }
      usrreCPULoadAvgHour OBJECT-TYPE
	  SYNTAX Integer32 (0..100)
       MAX-ACCESS read-only
       STATUS current
       DESCRIPTION
              "System CPU load Percentage for last hour."
       ::= { usrreSystem 15 }
      usrreCPULoadAvgDay OBJECT-TYPE
	  SYNTAX Integer32 (0..100)
       MAX-ACCESS read-only
       STATUS current
       DESCRIPTION
              "System CPU load Percentage for last day."
       ::= { usrreSystem 16 }
     usrreFreeMemorySize1HourBefore OBJECT-TYPE
      SYNTAX KBytes
      MAX-ACCESS read-only
      STATUS current
      DESCRIPTION
            "The amount of free physical main memory maintained by
            the RoboExec 1 Hour Before."
      ::= { usrreSystem 17 }
      usrreFreeMemorySize12HourBefore OBJECT-TYPE
      SYNTAX KBytes
      MAX-ACCESS read-only
      STATUS current
      DESCRIPTION
            "The amount of free physical main memory maintained by
            the RoboExec 12 Hour Before."
      ::= { usrreSystem 18 }
      usrreFreeMemorySize24HourBefore OBJECT-TYPE
      SYNTAX KBytes
      MAX-ACCESS read-only
      STATUS current
      DESCRIPTION
            "The amount of free physical main memory maintained by
            the RoboExec 24 Hours Before."
      ::= { usrreSystem 19 }
      usrreTotalBufferCache OBJECT-TYPE
      SYNTAX KBytes
      MAX-ACCESS read-only
      STATUS current
      DESCRIPTION
            "The amount of total allocated buffer cache maintained
             by RoboExec."
      ::= { usrreSystem 20 }
      usrreFreeBufferCache OBJECT-TYPE
      SYNTAX KBytes
      MAX-ACCESS read-only
      STATUS current
      DESCRIPTION
            "The amount of free buffer cache maintained by
             RoboExec."
      ::= { usrreSystem 21 }
      usrreFlashMemorySize OBJECT-TYPE
	  SYNTAX KBytes
	  MAX-ACCESS read-only
	  STATUS current
	  DESCRIPTION
		    "The amount of physical flash memory maintained by
		    the RoboExec."
	  ::= { usrreSystem 22 }
   usrreFreeMemoryMaxSize OBJECT-TYPE
	  SYNTAX KBytes
	  MAX-ACCESS read-only
	  STATUS current
	  DESCRIPTION
		    "The maximum possible amount of free physical main memory
		    maintained by the RoboExec."
	  ::= { usrreSystem 23 }
   -- The RoboExec Resources Running Software Group
   --
   -- Implementation of this group is mandatory.
   --
   -- The reSWRunTable contains an entry for each distinct piece of
   -- software that is running or loaded into physical or virtual
   -- memory in preparation for running.  This includes the RoboExec's
   -- operating system, device drivers, and applications.
   usrreSWRunTable OBJECT-TYPE
	  SYNTAX SEQUENCE OF UsrreSWRunEntry
	  MAX-ACCESS not-accessible
	  STATUS current
	  DESCRIPTION
		    "The (conceptual) table of software running on the
		    RoboExec."
	  ::= { usrreSWRun 1 }
   usrreSWRunEntry OBJECT-TYPE
	  SYNTAX UsrreSWRunEntry
	  MAX-ACCESS not-accessible
	  STATUS current
	  DESCRIPTION
		    "A (conceptual) entry for one piece of software
		    running on the RoboExec Note that because the installed
		    software table only contains information for
		    software stored locally on this RoboExec, not every
		    piece of running software will be found in the
		    installed software table.	 This is true of software
		    that was loaded and run from a non-local source,
		    such as a network-mounted file system.
		    As an example of how objects in this table are
		    named, an instance of the reSWRunName object might
		    be named reSWRunName.1287"
	  INDEX { usrreSWRunIndex }
	  ::= { usrreSWRunTable 1 }
   UsrreSWRunEntry ::= SEQUENCE {
		 usrreSWRunIndex		Integer32,
		 usrreSWRunName		DisplayString,
		 usrreSWRunType		INTEGER,
		 usrreSWRunStatus		INTEGER,
		 usrreSWRunStartTime	Integer32,
		 usrreSWRunMsgSent		Counter32,
		 usrreSWRunMsgRcvd		Counter32,
      	 usrreSWRunMsgPassedFrom Counter32,
		 usrreSWRunMsgPassedTo	Counter32,
		 usrreSWRunMboxScheduled	Counter32,
		 usrreSWRunAllocated	KBytes,
		 usrreSWRunFreed		KBytes
	  }
   usrreSWRunIndex OBJECT-TYPE
	  SYNTAX Integer32 (1..2147483647)
	  MAX-ACCESS not-accessible
	  STATUS current
	  DESCRIPTION
		    "A unique value for each piece of software running
		    on the RoboExec.  Wherever possible, this should be the
		    system's native, unique identification number."
	  ::= { usrreSWRunEntry 1 }
   usrreSWRunName OBJECT-TYPE
	  SYNTAX DisplayString (SIZE (0..64))
	  MAX-ACCESS read-only
	  STATUS current
	  DESCRIPTION
		    "The name of the RoboExec Process."
	  ::= { usrreSWRunEntry 2 }
   usrreSWRunType OBJECT-TYPE
	  SYNTAX INTEGER {
			    unknown(1),
			    operatingSystem(2),
			    deviceDriver(3),
			    application(4),
			    forwarder(5)
		    }
	  MAX-ACCESS read-only
	  STATUS current
	  DESCRIPTION
			"The type of this software."
	  ::= { usrreSWRunEntry 3 }
   usrreSWRunStatus OBJECT-TYPE
	  SYNTAX INTEGER {
			running(1),
			runnable(2),	 -- waiting for resource (CPU, memory, IO)
			notRunnable(3), -- loaded but waiting for event
 			invalid(4)	 -- not loaded
		 }
	  MAX-ACCESS read-only
	  STATUS current
	  DESCRIPTION
		    "The status of this running piece of software."
	  ::= { usrreSWRunEntry 4 }
   usrreSWRunStartTime OBJECT-TYPE
	 SYNTAX Integer32 (0..2147483647)
      MAX-ACCESS read-only
      STATUS current
      DESCRIPTION
             "The time when this process started. 
              NOTE: Time equal 0 indicates that per process
              statistic information is not capturing."
      ::= { usrreSWRunEntry 5 }
   usrreSWRunMsgSent OBJECT-TYPE
	 SYNTAX Counter32
      MAX-ACCESS read-only
      STATUS current
      DESCRIPTION
             "Number of messages were sent by this process.
              NOTE: Number of messages equal 0 indicates
              that per process statistic information is not capturing."
      ::= { usrreSWRunEntry 6 }
   usrreSWRunMsgRcvd OBJECT-TYPE
	 SYNTAX Counter32
      MAX-ACCESS read-only
      STATUS current
      DESCRIPTION
             "Number of messages were received by this process.
              NOTE: Number of messages equal 0 indicates
              that per process statistic information is not capturing."
      ::= { usrreSWRunEntry 7 }
   usrreSWRunMsgPassedFrom OBJECT-TYPE
	 SYNTAX Counter32
      MAX-ACCESS read-only
      STATUS current
      DESCRIPTION
             "Number of messages were passed from this process.
              NOTE: Number of messages equal 0 indicates
              that per process statistic information is not capturing."
      ::= { usrreSWRunEntry 8 }
   usrreSWRunMsgPassedTo OBJECT-TYPE
	 SYNTAX Counter32
      MAX-ACCESS read-only
      STATUS current
      DESCRIPTION
             "Number of messages were passed this process.
              NOTE: Number of messages equal 0 indicates
              that per process statistic information is not capturing."
      ::= { usrreSWRunEntry 9 }
   usrreSWRunMboxScheduled OBJECT-TYPE
	 SYNTAX Counter32
      MAX-ACCESS read-only
      STATUS current
      DESCRIPTION
             "The total number of times all mailboxes owned by 
             this process were scheduled.
             NOTE: Number equal 0 indicates
             that per process statistic information is not capturing."
      ::= { usrreSWRunEntry 10 }
   usrreSWRunAllocated OBJECT-TYPE
	 SYNTAX KBytes
      MAX-ACCESS read-only
      STATUS current
      DESCRIPTION
             "The total amount of memory that was allocated for
             this process.
             NOTE: 0 KB indicates that per process statistic 
             information is not capturing."
      ::= { usrreSWRunEntry 11 }
   usrreSWRunFreed OBJECT-TYPE
	 SYNTAX KBytes
      MAX-ACCESS read-only
      STATUS current
      DESCRIPTION
             "The total amount of memory that was freed while
             this process was running.
             NOTE: 0 KB indicates that per process statistic 
             information is not capturing."
      ::= { usrreSWRunEntry 12 }
   -- The RoboExec Logging Level Group
   --
   -- Implementation of this group is mandatory for all RoboExec's
   --
   -- The reLogLevelTable contains an entry for each software 
   -- facility running on the RoboExec.
   usrreLogLevelConfigFileName OBJECT-TYPE
	  SYNTAX DisplayString
	  MAX-ACCESS read-only
	  STATUS current
	  DESCRIPTION		
		    "The name of a ConfigFile to read/write permanent database
		    records. If the value of this object is an empty string, then
		    the process uses the default name
		    `@file://RoboExecNMProcess.cfg'."
	  ::= { usrreEvents 1 }
   usrreLogLevelCFMStatusFlag	 OBJECT-TYPE
	  SYNTAX UsrConfigStatus
	  MAX-ACCESS read-write
	  STATUS current
	  DESCRIPTION
		    "Setting the value of this object to `save' causes the values
			of the RoboExec Logging Level Group to be written out to the
			current config file, which is stored in the
			reLogLevelConfigFileName object. While the new ConfigFile is
			being written, the value of this flag will be set to `saving'.
			Any attempts to set the value while it is  not `normal'
			(i.e. the file is currently being written to the ConfigFile)
			will result in a badValue error being returned. Setting the
			value to `normal' will result in no action."
	  ::= { usrreEvents 2 }
   usrreLogLevelTable OBJECT-TYPE
	  SYNTAX SEQUENCE OF UsrreLogLevelEntry
	  MAX-ACCESS not-accessible
	  STATUS current
	  DESCRIPTION
		    "The (conceptual) table of event log levels for the
		    RoboExec."
	  ::= { usrreEvents 3 }
   usrreLogLevelEntry OBJECT-TYPE
	  SYNTAX UsrreLogLevelEntry
	  MAX-ACCESS not-accessible
	  STATUS current
	  DESCRIPTION
		    "A (conceptual) entry for one facility on the RoboExec
		    As an example of how objects in this table are
		    named, an instance of the reSWRunName object might
		    be named reSWRunName.1287"
	  INDEX { usrreLLFacility }
	  ::= { usrreLogLevelTable 1 }
   UsrreLogLevelEntry ::= SEQUENCE {
		 usrreLLFacility	   Integer32,
		 usrreLLFacilityName   DisplayString,
		 usrreLLLogLevel	   INTEGER
	  }
   usrreLLFacility OBJECT-TYPE
	  SYNTAX Integer32 (1..64)
	  MAX-ACCESS not-accessible
	  STATUS current
	  DESCRIPTION
		    "A unique value for each software facility
		    on the RoboExec."
	  ::= { usrreLogLevelEntry 1 }
   usrreLLFacilityName OBJECT-TYPE
	  SYNTAX DisplayString (SIZE (0..64))
	  MAX-ACCESS read-only
	  STATUS current
	  DESCRIPTION
		    "A textual name of the software facility."
	  ::= { usrreLogLevelEntry 2 }
   usrreLLLogLevel OBJECT-TYPE
	  SYNTAX INTEGER { critical(0),
				    unusual(1),
				    common(2),
				    verbose(3),
				    debug(4) }
	  MAX-ACCESS read-write
	  STATUS current
	  DESCRIPTION
		    "The Logging level for this software facility."
	  --CONFIGURABLE
	  ::= { usrreLogLevelEntry 3 }
   usrreEvLocalFile OBJECT-TYPE
	  SYNTAX DisplayString
	  MAX-ACCESS read-only
	  STATUS current
	  DESCRIPTION
		    "The file name of the local NVRAM logfile."
	  ::= { usrreEvents 4 }
   usrreEvOldLocalFile OBJECT-TYPE
	  SYNTAX DisplayString
	  MAX-ACCESS read-only
	  STATUS current
	  DESCRIPTION
		    "The name of the file that the Event Handler should copy the
		    old LocalFile contents to when the pilgrim system reboots."
	  ::= { usrreEvents 5 }
   usrreEvCriticalMsgsTable OBJECT-TYPE
	  SYNTAX SEQUENCE OF UsrreEvCriticalMsgsEntry
	  MAX-ACCESS not-accessible
	  STATUS current
	  DESCRIPTION
		    "The (conceptual) table of critical event messages."
	  ::= { usrreEvents 6 }
   usrreEvStatus OBJECT-TYPE
	  SYNTAX INTEGER {
		disable(0),
		enable(1)
	}
	  MAX-ACCESS read-write
	  STATUS current
	  DESCRIPTION
              "This switch allows disabling or enabling all logging
               of critical events to the local flash file system.
               This is disable by default."
	  --CONFIGURABLE
	  ::= { usrreEvents 7 }
   usrreEvCriticalMsgsEntry OBJECT-TYPE
	  SYNTAX UsrreEvCriticalMsgsEntry
	  MAX-ACCESS not-accessible
	  STATUS current
	  DESCRIPTION
		    "A (conceptual) entry for one critical event message."
	  INDEX { usrreEvCritMsgTimeStamp }
	  ::= { usrreEvCriticalMsgsTable 1 }
   UsrreEvCriticalMsgsEntry ::= SEQUENCE {
	  usrreEvCritMsgTimeStamp Integer32,
	  usrreEvCriticalMsg  DisplayString
	}
   usrreEvCritMsgTimeStamp OBJECT-TYPE
	  SYNTAX Integer32
	  MAX-ACCESS not-accessible
	  STATUS current
	  DESCRIPTION
		    "Index into the table of critical event messages saved in the
		    NVRAM local file. This represents the time, in hundredths of
		    seconds since system startup, at which the critical event
		    occurred."
	  ::= { usrreEvCriticalMsgsEntry 1 }
   usrreEvCriticalMsg OBJECT-TYPE
	  SYNTAX DisplayString
	  MAX-ACCESS read-only
	  STATUS current
	  DESCRIPTION
		    "Text of a critical event message."
	  ::= { usrreEvCriticalMsgsEntry 2 }
   -- The RoboExec System Counters Group
   --
   -- This group references counters defined in the RoboExec for
   -- certain system calls.
   -- This section of the MIB is still under development and it is likely
   -- that counters will be obsoleted or more counters will be added.
   --
   -- Implementation of this group is mandatory for a RoboExec system.
   --
   -- Define the groups within the counters group
   usrreCntBuffers	OBJECT IDENTIFIER ::= { usrreCounters 1 }
   usrreCntHeap	OBJECT IDENTIFIER ::= { usrreCounters 2 }
   usrreCntMessage	OBJECT IDENTIFIER ::= { usrreCounters 3 }
   usrreCntEvents	OBJECT IDENTIFIER ::= { usrreCounters 4 }
   usrreCntNames	OBJECT IDENTIFIER ::= { usrreCounters 5 }
   usrreCntSched	OBJECT IDENTIFIER ::= { usrreCounters 6 }
	--
	-- Counters for the buffer calls
	--
	usrreCBgetBuffer OBJECT-TYPE
		SYNTAX Counter32
		MAX-ACCESS read-only
		STATUS current
		DESCRIPTION	"The number of times exec_get_buffer() was called"
		::= { usrreCntBuffers 1 }
	usrreCBfreeBchain OBJECT-TYPE
		SYNTAX Counter32
		MAX-ACCESS read-only
		STATUS current
		DESCRIPTION	"The number of times exec_free_bchain() was called"
		::= { usrreCntBuffers 2 }
	usrreCBreplicateBufdesc OBJECT-TYPE
		SYNTAX Counter32
		MAX-ACCESS read-only
		STATUS current
		DESCRIPTION	"The number of times exec_replicate_bufdesc() was called"
		::= { usrreCntBuffers 3 }
	usrreCBreplicateListToBchain OBJECT-TYPE
		SYNTAX Counter32
		MAX-ACCESS read-only
		STATUS current
		DESCRIPTION	"The number of times exec_replicate_list_to_bchain() was called"
		::= { usrreCntBuffers 4 }
	usrreCBreplPartialBchain OBJECT-TYPE
		SYNTAX Counter32
		MAX-ACCESS read-only
		STATUS current
		DESCRIPTION	"The number of times exec_repl_partial_bchain() was called"
		::= { usrreCntBuffers 5 }
	usrreCBduplicateBchain OBJECT-TYPE
		SYNTAX Counter32
		MAX-ACCESS read-only
		STATUS current
		DESCRIPTION	"The number of times exec_duplicate_bchain() was called"
		::= { usrreCntBuffers 6 }
	usrreCBpullupBchain OBJECT-TYPE
		SYNTAX Counter32
		MAX-ACCESS read-only
		STATUS current
		DESCRIPTION	"The number of times exec_pullup_bchain() was called"
		::= { usrreCntBuffers 7 }
	usrreCBjoinBchains OBJECT-TYPE
		SYNTAX Counter32
		MAX-ACCESS read-only
		STATUS current
		DESCRIPTION	"The number of times exec_join_bchains() was called"
		::= { usrreCntBuffers 8  }
	usrreCBtrimBchain OBJECT-TYPE
		SYNTAX Counter32
		MAX-ACCESS read-only
		STATUS current
		DESCRIPTION	"The number of times exec_trim_bchain() was called"
		::= { usrreCntBuffers 9 }
	usrreCBmaskBchain OBJECT-TYPE
		SYNTAX Counter32
		MAX-ACCESS read-only
		STATUS current
		DESCRIPTION	"The number of times exec_mask_bchain() was called"
		::= { usrreCntBuffers 10 }
	usrreCBunmaskBchain OBJECT-TYPE
		SYNTAX Counter32
		MAX-ACCESS read-only
		STATUS current
		DESCRIPTION	"The number of times exec_unmask_bchain() was called"
		::= { usrreCntBuffers 11 }
	usrreCBsetBchainSize OBJECT-TYPE
		SYNTAX Counter32
		MAX-ACCESS read-only
		STATUS current
		DESCRIPTION	"The number of calls to exec_set_bchain_size()."
		::= { usrreCntBuffers 12 }
	usrreCBbchainSize OBJECT-TYPE
		SYNTAX Counter32
		MAX-ACCESS read-only
		STATUS current
		DESCRIPTION	"The number of calls to exec_bchain_size()."
		::= { usrreCntBuffers 13 }
	usrreCBbchainCount OBJECT-TYPE
		SYNTAX Counter32
		MAX-ACCESS read-only
		STATUS current
		DESCRIPTION	"The number of calls to exec_bchain_count()."
		::= { usrreCntBuffers 14 }
	usrreCBcheckBchain OBJECT-TYPE
		SYNTAX Counter32
		MAX-ACCESS read-only
		STATUS current
		DESCRIPTION	"The number of calls to exec_check_bchain()."
		::= { usrreCntBuffers 15 }
	usrreCBcopyBchainToBlock OBJECT-TYPE
		SYNTAX Counter32
		MAX-ACCESS read-only
		STATUS current
		DESCRIPTION	"The number of calls to exec_copy_bchain_to_block()."
		::= { usrreCntBuffers 16 }
	usrreCBcopyBlockToBchain OBJECT-TYPE
		SYNTAX Counter32
		MAX-ACCESS read-only
		STATUS current
		DESCRIPTION	"The number of calls to exec_copy_block_to_bchain()."
		::= { usrreCntBuffers 17 }
	usrreCBprependToBchain OBJECT-TYPE
		SYNTAX Counter32
		MAX-ACCESS read-only
		STATUS current
		DESCRIPTION	"The number of calls to exec_prepend_to_bchain()."
		::= { usrreCntBuffers 18 }
	usrreCBappendToBchain OBJECT-TYPE
		SYNTAX Counter32
		MAX-ACCESS read-only
		STATUS current
		DESCRIPTION	"The number of calls to exec_append_to_bchain()."
		::= { usrreCntBuffers 19 }
	usrreCBdetachBuffer OBJECT-TYPE
		SYNTAX Counter32
		MAX-ACCESS read-only
		STATUS current
		DESCRIPTION	"The number of calls to exec_detach_buffer()."
		::= { usrreCntBuffers 20 }
	usrreCBbufferFromBlock OBJECT-TYPE
		SYNTAX Counter32
		MAX-ACCESS read-only
		STATUS current
		DESCRIPTION	"The number of calls to exec_buffer_from_block()."
		::= { usrreCntBuffers 21 }
	usrreCBallocProtocolBuffer OBJECT-TYPE
		SYNTAX Counter32
		MAX-ACCESS read-only
		STATUS current
		DESCRIPTION	"The number of calls to exec_alloc_protocol_buffer()."
		::= { usrreCntBuffers 22 }
	usrreCBsplitBchain OBJECT-TYPE
		SYNTAX Counter32
		MAX-ACCESS read-only
		STATUS current
		DESCRIPTION	"The number of calls to exec_split_bchain()."
		::= { usrreCntBuffers 23 }
	usrreCBtimestampBchain OBJECT-TYPE
		SYNTAX Counter32
		MAX-ACCESS read-only
		STATUS current
		DESCRIPTION	"The number of calls to exec_timestamp_bchain()."
		::= { usrreCntBuffers 24 }
	usrreCBtimediffBchain OBJECT-TYPE
		SYNTAX Counter32
		MAX-ACCESS read-only
		STATUS current
		DESCRIPTION	"The number of calls to exec_timediff_bchain()."
		::= { usrreCntBuffers 25 }
	usrreCBbchainSetCorrelator OBJECT-TYPE
		SYNTAX Counter32
		MAX-ACCESS read-only
		STATUS current
		DESCRIPTION	"The number of calls to exec_bchain_set_correlator()."
		::= { usrreCntBuffers 26 }
	usrreCBprotectBchain OBJECT-TYPE
		SYNTAX Counter32
		MAX-ACCESS read-only
		STATUS current
		DESCRIPTION	"The number of calls to exec_protect_bchain()."
		::= { usrreCntBuffers 27 }
	usrreCBunprotectBchain OBJECT-TYPE
		SYNTAX Counter32
		MAX-ACCESS read-only
		STATUS current
		DESCRIPTION	"The number of calls to exec_unprotect_bchain()."
		::= { usrreCntBuffers 28 }
	--
	-- Counters for the memory heap calls
	--
	usrreCHallocateHeap OBJECT-TYPE
		SYNTAX Counter32
		MAX-ACCESS read-only
		STATUS current
		DESCRIPTION	"The number of calls to exec_allocate_heap()."
		::= { usrreCntHeap 1 }
	usrreCHfreeHeap OBJECT-TYPE
		SYNTAX Counter32
		MAX-ACCESS read-only
		STATUS current
		DESCRIPTION	"The number of calls to exec_free_heap()."
		::= { usrreCntHeap 2 }
	usrreCHreallocHeap OBJECT-TYPE
		SYNTAX Counter32
		MAX-ACCESS read-only
		STATUS current
		DESCRIPTION	"The number of calls to exec_realloc_heap()."
		::= { usrreCntHeap 3 }
	usrreCHduplicateHeap OBJECT-TYPE
		SYNTAX Counter32
		MAX-ACCESS read-only
		STATUS current
		DESCRIPTION	"The number of calls to exec_duplicate_heap()."
		::= { usrreCntHeap 4 }
	usrreCHheapCoalesce OBJECT-TYPE
		SYNTAX Counter32
		MAX-ACCESS read-only
		STATUS current
		DESCRIPTION	"The number of calls to exec_heap_coalesce()."
		::= { usrreCntHeap 5 }
	usrreCHcoalesceToABlock OBJECT-TYPE
		SYNTAX Counter32
		MAX-ACCESS read-only
		STATUS current
		DESCRIPTION	"The number of successful calls to exec_coalesce_to_a_block()."
		::= { usrreCntHeap 6 }
	usrreCHheapInfo OBJECT-TYPE
		SYNTAX Counter32
		MAX-ACCESS read-only
		STATUS current
		DESCRIPTION	"The number of calls to exec_heap_info()."
		::= { usrreCntHeap 7 }
	usrreCHheapSetCorrelator OBJECT-TYPE
		SYNTAX Counter32
		MAX-ACCESS read-only
		STATUS current
		DESCRIPTION	"The number of calls to exec_heap_set_correlator()."
		::= { usrreCntHeap 8 }
	usrreCHuseHeap OBJECT-TYPE
		SYNTAX Counter32
		MAX-ACCESS read-only
		STATUS current
		DESCRIPTION	"The number of calls to exec_use_heap()."
		::= { usrreCntHeap 9 }
	usrreCHheapGetUseCnt OBJECT-TYPE
		SYNTAX Counter32
		MAX-ACCESS read-only
		STATUS current
		DESCRIPTION	"The number of calls to exec_heap_get_usecnt()."
		::= { usrreCntHeap 10 }
	usrreCHfreeCacheBlocks OBJECT-TYPE
		SYNTAX Counter32
		MAX-ACCESS read-only
		STATUS current
		DESCRIPTION	"The number of outstanding free blocks in the heap cache."
		::= { usrreCntHeap 11 }
	usrreCHfreeHeapBlocks OBJECT-TYPE
		SYNTAX Counter32
		MAX-ACCESS read-only
		STATUS current
		DESCRIPTION	"The number of outstanding free blocks in the heap's heap."
		::= { usrreCntHeap 12 }
	usrreCHheapCheckProtection OBJECT-TYPE
		SYNTAX Counter32
		MAX-ACCESS read-only
		STATUS current
		DESCRIPTION	"The number of calls to exec_heap_check_protection()."
		::= { usrreCntHeap 13 }
	usrreCHheapSetProtection OBJECT-TYPE
		SYNTAX Counter32
		MAX-ACCESS read-only
		STATUS current
		DESCRIPTION	"The number of calls to exec_heap_set_protection()."
		::= { usrreCntHeap 14 }
	usrreCHheapRemoveProtection OBJECT-TYPE
		SYNTAX Counter32
		MAX-ACCESS read-only
		STATUS current
		DESCRIPTION	"The number of calls to exec_heap_remove_protection()."
		::= { usrreCntHeap 15 }
	usrreCHheapProtectionInfo OBJECT-TYPE
		SYNTAX Counter32
		MAX-ACCESS read-only
		STATUS current
		DESCRIPTION	"The number of calls to exec_heap_protection_info()."
		::= { usrreCntHeap 16 }
	--
	-- Counters for the message calls
	--
	usrreCMallocMsg OBJECT-TYPE
		SYNTAX Counter32
		MAX-ACCESS read-only
		STATUS current
		DESCRIPTION	"The number of calls to exec_alloc_msg()."
		::= { usrreCntMessage 1 }
	usrreCMfreemsg OBJECT-TYPE
		SYNTAX Counter32
		MAX-ACCESS read-only
		STATUS current
		DESCRIPTION	"The number of calls to exec_freemsg()."
		::= { usrreCntMessage 2 }
	usrreCMwasMsgPassed OBJECT-TYPE
		SYNTAX Counter32
		MAX-ACCESS read-only
		STATUS current
		DESCRIPTION	"The number of calls to exec_was_msg_passed()."
		::= { usrreCntMessage 3 }
	usrreCMrespondToMsg OBJECT-TYPE
		SYNTAX Counter32
		MAX-ACCESS read-only
		STATUS current
		DESCRIPTION	"The number of calls to exec_respond_to_msg()."
		::= { usrreCntMessage 4 }
	usrreCMmessageSend OBJECT-TYPE
		SYNTAX Counter32
		MAX-ACCESS read-only
		STATUS current
		DESCRIPTION	"The number of calls to exec_message_send()."
		::= { usrreCntMessage 5 }
	usrreCMsendmsg OBJECT-TYPE
		SYNTAX Counter32
		MAX-ACCESS read-only
		STATUS current
		DESCRIPTION	"The number of calls to exec_sendmsg()."
		::= { usrreCntMessage 6 }
	usrreCMreceiveMail OBJECT-TYPE
		SYNTAX Counter32
		MAX-ACCESS read-only
		STATUS current
		DESCRIPTION	"The number of calls to exec_receive_mail()."
		::= { usrreCntMessage 7 }
	usrreCMpassmsg OBJECT-TYPE
		SYNTAX Counter32
		MAX-ACCESS read-only
		STATUS current
		DESCRIPTION	"The number of calls to exec_passmg()."
		::= { usrreCntMessage 8 }
	usrreCMcountMail OBJECT-TYPE
		SYNTAX Counter32
		MAX-ACCESS read-only
		STATUS current
		DESCRIPTION	"The number of calls to exec_count_mail()."
		::= { usrreCntMessage 9 }
	--
	-- Counters for the event calls
	--
	usrreCEevents OBJECT-TYPE
		SYNTAX Counter32
		MAX-ACCESS read-only
		STATUS current
		DESCRIPTION	"The number of calls to exec_events()."
		::= { usrreCntEvents 1 }
	usrreCEeventsLogged OBJECT-TYPE
		SYNTAX Counter32
		MAX-ACCESS read-only
		STATUS current
		DESCRIPTION	"The number of calls to exec_events() that were logged."
		::= { usrreCntEvents 2 }
	usrreCEeventsDropped OBJECT-TYPE
		SYNTAX Counter32
		MAX-ACCESS read-only
		STATUS current
		DESCRIPTION	"The number of calls to exec_events() that were dropped."
		::= { usrreCntEvents 3 }
	--
	-- Counters for the Name calls
	--
	usrreCNregisterName OBJECT-TYPE
		SYNTAX Counter32
		MAX-ACCESS read-only
		STATUS current
		DESCRIPTION	"The number of calls to exec_register_name()."
		::= { usrreCntNames 1 }
	usrreCNresolveName OBJECT-TYPE
		SYNTAX Counter32
		MAX-ACCESS read-only
		STATUS current
		DESCRIPTION	"The number of calls to exec_resolve_name()."
		::= { usrreCntNames 2 }
	usrreCNremoveName OBJECT-TYPE
		SYNTAX Counter32
		MAX-ACCESS read-only
		STATUS current
		DESCRIPTION	"The number of calls to exec_remove_name()."
		::= { usrreCntNames 3 }
	usrreCNremoveNameForData OBJECT-TYPE
		SYNTAX Counter32
		MAX-ACCESS read-only
		STATUS current
		DESCRIPTION
			"The number of names that were removed because the data they
			 pointed to was no longer there (mailbox delete e.g.)."
		::= { usrreCntNames 4 }
	usrreCNremoveNameForProc OBJECT-TYPE
		SYNTAX Counter32
		MAX-ACCESS read-only
		STATUS current
		DESCRIPTION
			"The number of names that were removed because the process
			 that owned them was killed."
		::= { usrreCntNames 5 }
	--
	-- Counters for the scheduling information
	--
	usrreCScurrentMsgsQueued OBJECT-TYPE
		SYNTAX Counter32
		MAX-ACCESS read-only
		STATUS current
		DESCRIPTION	"The current number of messages queued."
		::= { usrreCntSched 1 }
	usrreCSmaxMsgsQueued OBJECT-TYPE
		SYNTAX Counter32
		MAX-ACCESS read-only
		STATUS current
		DESCRIPTION	"The all time high number of messages queued."
		::= { usrreCntSched 2 }
	usrreCSrunTotalMsgsQueued OBJECT-TYPE
		SYNTAX Counter32
		MAX-ACCESS read-only
		STATUS current
		DESCRIPTION	"The a running total of the messages queued."
		::= { usrreCntSched 3 }
	usrreCScurrentMboxesReady OBJECT-TYPE
		SYNTAX Counter32
		MAX-ACCESS read-only
		STATUS current
		DESCRIPTION	"The current number of mailboxes ready to run."
		::= { usrreCntSched 4 }
	usrreCSmaxMboxesReady OBJECT-TYPE
		SYNTAX Counter32
		MAX-ACCESS read-only
		STATUS current
		DESCRIPTION	"The all time high number of mailboxes ready to run."
		::= { usrreCntSched 5 }
	usrreCSrunTotalMboxesReady OBJECT-TYPE
		SYNTAX Counter32
		MAX-ACCESS read-only
		STATUS current
		DESCRIPTION	"The a running total of the mailboxes ready to run."
		::= { usrreCntSched 6 }
	usrreCSschedLoops OBJECT-TYPE
		SYNTAX Counter32
		MAX-ACCESS read-only
		STATUS current
		DESCRIPTION
			"The number of times we've run through the scheduling loop."
		::= { usrreCntSched 7 }
	--
	-- The RoboExec Name Group
	--
	usrreNameTable OBJECT-TYPE
		SYNTAX SEQUENCE OF UsrreNameEntry
		MAX-ACCESS not-accessible
		STATUS current
		DESCRIPTION
			  "The (conceptual) table of the names kept by the RoboExec."
		::= { usrreNames 1 }
	 usrreNameEntry OBJECT-TYPE
		SYNTAX UsrreNameEntry
		MAX-ACCESS not-accessible
		STATUS current
		DESCRIPTION
			  "A (conceptual) entry for one name."
		INDEX { usrreNameType, usrreNameName }
		::= { usrreNameTable 1 }
	 UsrreNameEntry ::= SEQUENCE {
		usrreNameType			DisplayString,
		usrreNameName		 	DisplayString,
		usrreNameIntOrString	INTEGER,
		usrreNameIntValue		Integer32,
		usrreNameStringValue	DisplayString,
		usrreNameOwner			Integer32
		}
	 usrreNameType OBJECT-TYPE
		SYNTAX DisplayString (SIZE (0..64))
		MAX-ACCESS not-accessible
		STATUS current
		DESCRIPTION
			  "The internal type of the name."
		::= { usrreNameEntry 1 }
	 usrreNameName OBJECT-TYPE
		SYNTAX DisplayString (SIZE (0..64))
		MAX-ACCESS not-accessible
		STATUS current
		DESCRIPTION
			  "The name in the RoboExec"
		::= { usrreNameEntry 2 }
	 usrreNameIntOrString OBJECT-TYPE
		SYNTAX INTEGER {
				  integer(1),
				  string(2),
				  neither(3)
			  }
		MAX-ACCESS read-only
		STATUS current
		DESCRIPTION
			"Is the data for this name a string or an integer?"
		::= { usrreNameEntry 3 }
	 usrreNameIntValue OBJECT-TYPE
		SYNTAX Integer32
		MAX-ACCESS read-only
		STATUS current
		DESCRIPTION
			  "If the name has a numerical value, this is it.
			   Otherwise, this value is 0."
		::= { usrreNameEntry 4 }
	 usrreNameStringValue OBJECT-TYPE
		SYNTAX DisplayString (SIZE (0..200))
		MAX-ACCESS read-only
		STATUS current
		DESCRIPTION
			  "If the name has a string value, this is it.
			   Otherwise, this value is blank."
		::= { usrreNameEntry 5 }
	 usrreNameOwner OBJECT-TYPE
		SYNTAX Integer32
		MAX-ACCESS read-only
		STATUS current
		DESCRIPTION
			"The process ID of the owner of this name.
			This should correlate with the usrreSWRunIndex."
		::= { usrreNameEntry 6 }
	--
	-- The RoboExec FileSystem Group
	--
	--
	-- File system information
	--
	usrreFSInfoTable OBJECT-TYPE
		SYNTAX SEQUENCE OF UsrreFSInfoEntry
		MAX-ACCESS not-accessible
		STATUS current
		DESCRIPTION
			  "The (conceptual) table of the File System information kept
			   by the RoboExec."
		::= { usrreFiles 1 }
	 usrreFSInfoEntry OBJECT-TYPE
		SYNTAX UsrreFSInfoEntry
		MAX-ACCESS not-accessible
		STATUS current
		DESCRIPTION
			  "A (conceptual) entry for one file system."
		INDEX { usrreFSInfoIndex }
		::= { usrreFSInfoTable 1 }
	 UsrreFSInfoEntry ::= SEQUENCE {
		usrreFSInfoIndex		Integer32,
		usrreFSInfoName		DisplayString,
		usrreFSInfoType		INTEGER
		}
	 usrreFSInfoIndex OBJECT-TYPE
		SYNTAX Integer32
		MAX-ACCESS not-accessible
		STATUS current
		DESCRIPTION
			  "And index to the file systems."
		::= { usrreFSInfoEntry 1 }
	 usrreFSInfoName OBJECT-TYPE
		SYNTAX DisplayString (SIZE (0..64))
		MAX-ACCESS read-only
		STATUS current
		DESCRIPTION
			  "A name given to the file system."
		::= { usrreFSInfoEntry 2 }
	 usrreFSInfoType OBJECT-TYPE
		SYNTAX INTEGER {
				flashRAM(1),
				ram(2),
				floppyDisk(3),
				hardDisk(4)
			  }
		MAX-ACCESS read-only
		STATUS current
		DESCRIPTION
			"The type of this file system."
		::= { usrreFSInfoEntry 3 }
	--
	-- File Table
	--
	usrreFileTable OBJECT-TYPE
		SYNTAX SEQUENCE OF UsrreFileTableEntry
		MAX-ACCESS not-accessible
		STATUS current
		DESCRIPTION
			  "The (conceptual) table of the files for a file system."
		::= { usrreFiles 2 }
	 usrreFileTableEntry OBJECT-TYPE
		SYNTAX UsrreFileTableEntry
		MAX-ACCESS not-accessible
		STATUS current
		DESCRIPTION
			  "A (conceptual) entry for one file system."
		INDEX { usrreFileTableFileSystem, usrreFileTableName }
		::= { usrreFileTable 1 }
	 UsrreFileTableEntry ::= SEQUENCE {
		usrreFileTableFileSystem	Integer32,
		usrreFileTableName		 DisplayString,
		usrreFileTableSize		 Integer32,
		usrreFileTableRenameTo	 DisplayString,
		usrreFileTableStatus	 INTEGER,
		usrreFileTableCopyTo	 DisplayString,
		usrreFileTableErrorString DisplayString
		}
	 usrreFileTableFileSystem OBJECT-TYPE
		SYNTAX Integer32
		MAX-ACCESS not-accessible
		STATUS current
		DESCRIPTION
			  "The file system containing this file. This must
			   match the file system from the File System Info Table."
		::= { usrreFileTableEntry 1 }
	 usrreFileTableName OBJECT-TYPE
		SYNTAX DisplayString (SIZE (0..64))
		MAX-ACCESS not-accessible
		STATUS current
		DESCRIPTION
			  "The name given to the file."
		::= { usrreFileTableEntry 2 }
	 usrreFileTableSize OBJECT-TYPE
		SYNTAX Integer32
		MAX-ACCESS read-only
		STATUS current
		DESCRIPTION
			"The size, in octets, of the file."
		::= { usrreFileTableEntry 3 }
	 usrreFileTableRenameTo OBJECT-TYPE
		SYNTAX DisplayString (SIZE (0..64))
		MAX-ACCESS read-write
		STATUS current
		DESCRIPTION
			"In order to change the name of this file, the
			new name should be written to this object. This
            value cannot be SET to NULL but it will revert
            to NULL when name has been changed."
		::= { usrreFileTableEntry 4 }
	usrreFileTableStatus OBJECT-TYPE
		SYNTAX INTEGER {
				normal(1),
				delete(2),
				copying(3),       -- File copying in progress
				failed(4)         -- Operation failed		
			}
		MAX-ACCESS read-write
		STATUS current
		DESCRIPTION
			"The status of the file. Valid row entries in this
			table have the status field set to normal.
			The settable value is delete: write 2 to this variable 
			to delete the file. The values normal(1), in_progress(3), 
			and failed(4) are read-only"
		::= { usrreFileTableEntry 5 }
	usrreFileTableCopyTo OBJECT-TYPE
		SYNTAX DisplayString (SIZE (0..64))
		MAX-ACCESS read-write
		STATUS current
		DESCRIPTION
			"In order to copy this file, the
			new name should be written to this object. This
            value cannot be SET to NULL but it will revert
            to NULL when file has been copied."
		::= { usrreFileTableEntry 6 }
	usrreFileTableErrorString OBJECT-TYPE
         SYNTAX  DisplayString (SIZE (0..255))
         MAX-ACCESS  read-only
         STATUS  current
         DESCRIPTION
            "The error string returned when file copy or rename fails.
             Otherwise, this field is NULL."		
		::= { usrreFileTableEntry 7 }
-- Memory Trap Settings Group
	usrreMemoryTrapUpperThreshold OBJECT-TYPE
		SYNTAX Integer32 (1..100)
		MAX-ACCESS read-write
		STATUS current
		DESCRIPTION
       			"Specifies the upper Water Mark for Memory
                 Threshold. If the used memory exceeds this
                 limit, then a trap is sent."
		--CONFIGURABLE
	::= { usrreMemTrapSettings 1 }
	usrreMemoryTrapLowerThreshold OBJECT-TYPE
		SYNTAX Integer32 (1..100)
		MAX-ACCESS read-write
		STATUS current
		DESCRIPTION
       			"Specifies the lower Water Mark for Memory
                 Threshold. If the used memory size touches 
                 this lower threshold after touching the Upper
                 threshold, then only a trap will be sent whenever
                 next time it exceeds the Upper Threshold."
		--CONFIGURABLE
	::= { usrreMemTrapSettings 2 }
	usrreMemoryTrapStatus OBJECT-TYPE
   		SYNTAX     INTEGER {
                        enabled(1),
                        disabled(2)
                        }
		MAX-ACCESS read-write
		STATUS current
   		DESCRIPTION
       		        "Memory Trap Enabled or Disabled."
                --CONFIGURABLE
	::= { usrreMemTrapSettings 3 }
-- Memory Traps Group
    usrreTrapsV2    OBJECT-IDENTITY
        STATUS  current
        DESCRIPTION
            "The events for the RoboExec process."
    ::= { usrreTraps 0 }
	usrreMemoryTrapThresholdReached NOTIFICATION-TYPE
		OBJECTS {    
                usrreMemoryTrapUpperThreshold,
                usrreMemoryTrapLowerThreshold,
                usrreFreeMemorySize
        		}
        STATUS  current
		DESCRIPTION
			"This trap is generated when Used Memory Size
                         reaches Upper Threshold."
        --#TYPE "Alarm"
	    --#SUMMARY	"Memory Upper Threshold reached"
	    --#SEVERITY MAJOR
	    --#STATE	OPERATIONAL
        ::= { usrreTrapsV2 1 }
END  -- End of    ROBOEXEC-RESOURCES-MIB DEFINITIONS
-- ************************************************************************
--
--	EEgg.mib - The Pilgrim Easter Egg MIB
--
   EASTER-EGG-MIB DEFINITIONS ::= BEGIN
   IMPORTS
       OBJECT-TYPE              FROM RFC-1212
       roboExec, UsrDisplayString  FROM USR-DEFINITIONS-MIB;
   usrreEasterEgg     OBJECT IDENTIFIER ::= { roboExec 4 }
   -- The RoboExec Easter Egg Group
   --
   -- Implementation of this group is purely at the whim of the implementors
   --
   -- The reEasterEggTable contains an entry for each member of the
   -- team working on the Pilgrim project; disabled
   usrreEasterEggTable OBJECT-TYPE
       SYNTAX SEQUENCE OF UsrreEasterEggEntry
       ACCESS not-accessible
       STATUS mandatory
       DESCRIPTION
              "The table of Pilgrim developers."
       ::= { usrreEasterEgg 1 }
   usrreEasterEggEntry OBJECT-TYPE
       SYNTAX UsrreEasterEggEntry
       ACCESS not-accessible
       STATUS mandatory
       DESCRIPTION
              "An entry for one Pilgrim developer."
       INDEX { usrreEEIndex }
       ::= { usrreEasterEggTable 1 }
   UsrreEasterEggEntry ::= SEQUENCE {
           usrreEEIndex         INTEGER,
           usrreEEName          UsrDisplayString,
           usrreEENickName      UsrDisplayString,
           usrreEEQuote         UsrDisplayString
       }
   usrreEEIndex OBJECT-TYPE
       SYNTAX INTEGER
       ACCESS read-only
       STATUS mandatory
       DESCRIPTION
              "A unique value for each Pilgrim developer."
       ::= { usrreEasterEggEntry 1 }
   usrreEEName OBJECT-TYPE
       SYNTAX UsrDisplayString (SIZE (0..64))
       ACCESS read-only
       STATUS mandatory
       DESCRIPTION
              "A textual name of the developer."
       ::= { usrreEasterEggEntry 2 }
   usrreEENickName OBJECT-TYPE
       SYNTAX UsrDisplayString (SIZE (0..64))
       ACCESS read-only
       STATUS mandatory
       DESCRIPTION
              "Another name for the same person..."
	  --GORDY
       ::= { usrreEasterEggEntry 3 }
   usrreEEQuote OBJECT-TYPE
       SYNTAX UsrDisplayString
       ACCESS read-only
       STATUS mandatory
       DESCRIPTION
              "A quote of note..."
	  --GORDY
       ::= { usrreEasterEggEntry 4 }
   usrJimbo OBJECT-TYPE
       SYNTAX UsrDisplayString
       ACCESS read-only
       STATUS mandatory
       DESCRIPTION
              "An entry in the MIB tree to honor the designer of
		     the Pilgrim Network Management Architecture."
       --GORDY
       ::= { usrreEasterEgg 2 }
   END    -- End of    EASTER-EGG-MIB DEFINITIONS
-- ************************************************************************
--
--	usr_ipx.mib 
--
-- Author:         Craig C. Boyle
--
IpxHost-MIB DEFINITIONS ::= BEGIN
	IMPORTS
        OBJECT-TYPE, MODULE-IDENTITY,
        Counter32, Integer32
				  FROM SNMPv2-SMI
        DisplayString
                  FROM SNMPv2-TC
        PhysAddress, common, UsrConfigStatus
                  FROM USR-DEFINITIONS-MIB;
    usrIpx MODULE-IDENTITY
        LAST-UPDATED "200205051400Z"
        ORGANIZATION "CommWorks Corporation, a 3Com Company"
        CONTACT-INFO "Customer Support"
        DESCRIPTION
                 "The commWorks enterprise defined MIB objects for IPX"
--      REVISION "200205051400Z"
--      DESCRIPTION "Converted to SNMPv2"
    ::= { common 4 }
   -- textual conventions
   -- 
   -- textual conventions are like pre-processor macro in 'C'
   --        (i.e. #define statements)
   -- Use them to define your own 'datatypes'
   -- memory size, expressed in units of 1024bytes
   KBytes ::=    INTEGER (0..2147483647)
   NetNumber ::= OCTET STRING (SIZE(4))
   UsrIpxStates ::= INTEGER   
                        {
                        initializing(1),
	                    enable(2),   -- Normal state following powerup of reenable.
                        shutdown(3), -- Immediately following a disable command.
                        disable(4)   -- Following RIP shutdown. 
                         }
   -- Begin managed object definitions here...
    usrIpxVersionNumber OBJECT-TYPE
         SYNTAX       Integer32
         MAX-ACCESS   read-only
         STATUS       current
         DESCRIPTION
            "The version number for the IPX module."
         ::= { usrIpx 1 }
     usrIpxSplitEqualCostRoutes OBJECT-TYPE
        SYNTAX   INTEGER {
                        disable(0),
                        enable(1)
                        }
         MAX-ACCESS   read-write
         STATUS       current
         DESCRIPTION
            "Allow splitting of equal cost routes. IPX maintains multiple routes to 
             the same destination network.  When this field is enabled IPX will split
             traffic over the multiple routes.  This is also know as load balancing.
             Not currently supported by the code."
         ::= { usrIpx 2 }
    usrIpxProtocolPriority OBJECT-TYPE
         SYNTAX   INTEGER (1..3)
         MAX-ACCESS   read-write
         STATUS       current
         DESCRIPTION
                "The IPX priority relative to other protocols. 
                 Not currently supported by the code."
         ::= { usrIpx 3 }
    usrIpxMaxRegisteredPaths OBJECT-TYPE
         SYNTAX   INTEGER (1..255)
         MAX-ACCESS   read-write
         STATUS       current
         DESCRIPTION
                "The maximum number of routes to be maintained in the box. 
                 Not currently supported by the code."
         ::= { usrIpx 4 }
    usrIpxDefaultGateway OBJECT-TYPE
         SYNTAX   OCTET STRING (SIZE(10))
         MAX-ACCESS   read-write
         STATUS       current
         DESCRIPTION
                "The Default Gateway. The first leading bytes are IPX network number and the
                trailing 6 bytes of this string should contain ethernet address."
         --CONFIGURABLE
         ::= { usrIpx 5 }
     usrIpxRipTracingState OBJECT-TYPE
          SYNTAX      INTEGER {
                        disable(0),
                        enable(1)
                       }
          MAX-ACCESS      read-write
          STATUS          current
          DESCRIPTION "The state of RIP Packet Tracing. When this is enabled 
                       each packet that the IPX RIP software receives is 
                       printed to the console. This object is only applicable
                       on specially compiled DEBUG software versions."
         --CONFIGURABLE
     ::= {usrIpx 6}
     usrIpxSapTracingState OBJECT-TYPE
          SYNTAX      INTEGER {
                        disable(0),
                        enable(1)
                       }
          MAX-ACCESS      read-write
          STATUS          current
          DESCRIPTION "The state of SAP Packet Tracing. When this is enabled
                       each packet that the IPX SAP software receives is
                       printed to the console. This object is only applicable
                       on specially compiled DEBUG software versions."
         --CONFIGURABLE
     ::= {usrIpx 7}
-- IPX Static Route
--
    usrIpxStaticRouteTable OBJECT-TYPE
         SYNTAX  SEQUENCE OF USRIPXStaticRouteEntry 
         MAX-ACCESS  not-accessible
         STATUS      current
         DESCRIPTION
            ""
    ::= { usrIpx 8 }
     usrIpxStaticRouteEntry OBJECT-TYPE
        SYNTAX      USRIPXStaticRouteEntry
        MAX-ACCESS  not-accessible
        STATUS      current
        DESCRIPTION "Each entry corresponds to one static route."
        INDEX   {
                usrIpxStaticRouteSysInstance,
                usrIpxStaticRouteCircIndex,
                usrIpxStaticRouteNetNum
               }
     ::= {usrIpxStaticRouteTable 1}
     USRIPXStaticRouteEntry ::= 
          SEQUENCE {
               usrIpxStaticRouteSysInstance
                    Integer32,
               usrIpxStaticRouteCircIndex
                    Integer32,
               usrIpxStaticRouteNetNum
                    NetNumber,
               usrIpxStaticRouteExistState
                    INTEGER,
               usrIpxStaticRouteTicks
                    Integer32,
               usrIpxStaticRouteHopCount
                    Integer32,
               usrIpxStaticRouteNextHopNICAddress
                    PhysAddress,
               usrIpxStaticRouteNextHopNetNum
                    NetNumber
               }
     usrIpxStaticRouteSysInstance OBJECT-TYPE
        SYNTAX      Integer32
        MAX-ACCESS      read-write
        STATUS      	current
        DESCRIPTION "The unique identifier of the instance of IPX to
                      which this row corresponds."
     ::= {usrIpxStaticRouteEntry 1}
     usrIpxStaticRouteCircIndex OBJECT-TYPE
        SYNTAX      Integer32
        MAX-ACCESS      read-write
        STATUS      	current
        DESCRIPTION "The unique identifier of the circuit used to
                     reach the first hop in the static route."
     ::= {usrIpxStaticRouteEntry 2}
     usrIpxStaticRouteNetNum OBJECT-TYPE
        SYNTAX      NetNumber
        MAX-ACCESS      read-write
        STATUS      	current
        DESCRIPTION "The IPX network number of the route's destination."
        --CONFIGURABLE
     ::= {usrIpxStaticRouteEntry 3}
     usrIpxStaticRouteExistState OBJECT-TYPE
        SYNTAX      INTEGER {
                        off(1),
                        on(2)
                       }
        MAX-ACCESS      read-write
        STATUS      	current
        DESCRIPTION "The validity of this static route.  Entries with the
                     value set to off may be deleted from the table at the
                     implementation's discretion."
     ::= {usrIpxStaticRouteEntry 4}
     usrIpxStaticRouteTicks OBJECT-TYPE
        SYNTAX      Integer32
        MAX-ACCESS      read-write
        STATUS      	current
        DESCRIPTION "The delay, in ticks, to reach the route's destination."
        --CONFIGURABLE
     ::= {usrIpxStaticRouteEntry 5}
     usrIpxStaticRouteHopCount OBJECT-TYPE
        SYNTAX      Integer32
        MAX-ACCESS      read-write
        STATUS      	current
        DESCRIPTION "The number of router hops necessary to reach the destination."
        --CONFIGURABLE
     ::= {usrIpxStaticRouteEntry 6}
     usrIpxStaticRouteNextHopNICAddress OBJECT-TYPE
        SYNTAX      PhysAddress
        MAX-ACCESS      read-write
        STATUS      	current
        DESCRIPTION "The NIC address of the next router in the routing path to the destination."
        --CONFIGURABLE
     ::= {usrIpxStaticRouteEntry 7}
     usrIpxStaticRouteNextHopNetNum OBJECT-TYPE
        SYNTAX      NetNumber
        MAX-ACCESS      read-write
        STATUS      	current
        DESCRIPTION "The Next Hop Network Number of the router in the routing path to the destination."
        --CONFIGURABLE
     ::= {usrIpxStaticRouteEntry 8}
-- Static Services Table
--   This table contains information for all services reached via a
--   static route.
    usrIpxStaticServTable OBJECT-TYPE
         SYNTAX      SEQUENCE OF USRIPXStaticServEntry
         MAX-ACCESS      not-accessible
         STATUS      	current
         DESCRIPTION "The Static Services table contains information about
                      all services reached via statically configured routes."
       ::= {usrIpx 9}
    usrIpxStaticServEntry OBJECT-TYPE
         SYNTAX      USRIPXStaticServEntry
         MAX-ACCESS      not-accessible
         STATUS      	current
         DESCRIPTION "Each entry corresponds to one service."
         INDEX       {
                        usrIpxStaticServSysInstance,
                        usrIpxStaticServCircIndex,
                        usrIpxStaticServName,
                        usrIpxStaticServType
                      }
       ::= {usrIpxStaticServTable 1}
    USRIPXStaticServEntry ::= 
             SEQUENCE {
                           usrIpxStaticServSysInstance
                              Integer32,
                           usrIpxStaticServCircIndex
                              Integer32,
                           usrIpxStaticServName
                              OCTET STRING,
                           usrIpxStaticServType
                              OCTET STRING,
                           usrIpxStaticServExistState
                              INTEGER,
                           usrIpxStaticServNetNum
                              NetNumber,
                           usrIpxStaticServNode
                              OCTET STRING,
                           usrIpxStaticServSocket
                              OCTET STRING,
                           usrIpxStaticServHopCount
                              Integer32,
                           usrIpxStaticServNextHopNICAddress
                              PhysAddress,
                           usrIpxStaticServNextHopNetNum
                              NetNumber
                          }
    usrIpxStaticServSysInstance OBJECT-TYPE
         SYNTAX      Integer32
         MAX-ACCESS      read-write
         STATUS      	current
         DESCRIPTION "The unique identifier of the instance of IPX to which
                      this entry corresponds."
    ::= {usrIpxStaticServEntry 1}
    usrIpxStaticServCircIndex OBJECT-TYPE
         SYNTAX      Integer32
         MAX-ACCESS      read-write
         STATUS      	current
         DESCRIPTION "The circuit used to reach this service."
       ::= {usrIpxStaticServEntry 2}
    usrIpxStaticServName OBJECT-TYPE
         SYNTAX      OCTET STRING (SIZE(1..48))
         MAX-ACCESS      read-write
         STATUS      	current
         DESCRIPTION "The service name."
         --CONFIGURABLE
       ::= {usrIpxStaticServEntry 3}
    usrIpxStaticServType OBJECT-TYPE
         SYNTAX      OCTET STRING (SIZE(2))
         MAX-ACCESS      read-write
         STATUS      	current
         DESCRIPTION "The service type."
         --CONFIGURABLE
       ::= {usrIpxStaticServEntry 4}
    usrIpxStaticServExistState OBJECT-TYPE
         SYNTAX      INTEGER {
                          off(1),
                          on(2)
                           }
         MAX-ACCESS      read-write
         STATUS      	current
         DESCRIPTION "The validity of this static service.  Entries with the
                      value set to off may be deleted from the table at the
                      implementation's discretion."
       ::= {usrIpxStaticServEntry 5}
    usrIpxStaticServNetNum OBJECT-TYPE
         SYNTAX      NetNumber
         MAX-ACCESS      read-write
         STATUS      	current
         DESCRIPTION "The IPX network number portion of the IPX address of the
                      service."
         --CONFIGURABLE
       ::= {usrIpxStaticServEntry 6}
    usrIpxStaticServNode OBJECT-TYPE
         SYNTAX      OCTET STRING (SIZE(6))
         MAX-ACCESS      read-write
         STATUS      	current
         DESCRIPTION "The node portion of the IPX address of the service."
         --CONFIGURABLE
       ::= {usrIpxStaticServEntry 7}
    usrIpxStaticServSocket OBJECT-TYPE
         SYNTAX      OCTET STRING (SIZE(2))
         MAX-ACCESS      read-write
         STATUS      	current
         DESCRIPTION "The socket portion of the IPX address of the service."
         --CONFIGURABLE
       ::= {usrIpxStaticServEntry 8}
    usrIpxStaticServHopCount OBJECT-TYPE
         SYNTAX      Integer32
         MAX-ACCESS      read-write
         STATUS      	current
         DESCRIPTION "The number of router hops to the server on which the service resides."
         --CONFIGURABLE
       ::= {usrIpxStaticServEntry 9}
    usrIpxStaticServNextHopNICAddress OBJECT-TYPE
         SYNTAX      PhysAddress
         MAX-ACCESS      read-write
         STATUS      	current
         DESCRIPTION "The NIC address of next router in the path to the 
                      server on which the service resides."
         --CONFIGURABLE
       ::= {usrIpxStaticServEntry 10}
    usrIpxStaticServNextHopNetNum OBJECT-TYPE
         SYNTAX      NetNumber
         MAX-ACCESS      read-write
         STATUS      	current
         DESCRIPTION "The network number of the next router in path to the 
                      server on which the service resides."
         --CONFIGURABLE
       ::= {usrIpxStaticServEntry 11}
-- Portal MIB Variables
--
    usrIpxPortalTable OBJECT-TYPE
         SYNTAX  SEQUENCE OF USRIpxPortalEntry 
         MAX-ACCESS  not-accessible
         STATUS  	current
         DESCRIPTION
            ""
    ::= { usrIpx 10 }
     usrIpxPortalEntry OBJECT-TYPE
        SYNTAX      USRIpxPortalEntry
        MAX-ACCESS      not-accessible
        STATUS      	current
        DESCRIPTION "Each entry corresponds to one static route."
        INDEX   {
                usrIpxPortalSysInstance,
                usrIpxPortalPortNumber
               }
     ::= {usrIpxPortalTable 1}
     USRIpxPortalEntry ::= 
          SEQUENCE {
               usrIpxPortalSysInstance
                    Integer32,
               usrIpxPortalPortNumber
                    Integer32,
               usrIpxPortalNetBiosState
                    INTEGER,
               usrIpxPortalNetworkDelay
                    Integer32,
               usrIpxPortalMaxNumberRipEntries
                    Integer32,
               usrIpxPortalMaxNumberSapEntries
                    Integer32,
               usrIpxPortalRipBroadcastState
                    INTEGER,
               usrIpxPortalSapBroadcastState
                    INTEGER,
               usrIpxPortalRipPeriodicState
                    INTEGER,
               usrIpxPortalSapPeriodicState
                    INTEGER,
               usrIpxPortalNetBiosNameCachingState
                    INTEGER,
               usrIpxPortalNetBiosHops
                    Integer32,
               usrIpxPortalDiagnosticState
                    INTEGER,
               usrIpxPortalNetBiosNameCachingTimer
                    Integer32,
               usrIpxPortalMaxLearningRetries
                    Integer32,
               usrIpxPortalIpxwanState
                    INTEGER,
               usrIpxPortalLargeHopCount
                    Counter32,
               usrIpxPortalNetbsLargeHopCount
                    Counter32,
               usrIpxPortalNoNetRipPkt
                    Counter32,
               usrIpxPortalPathNotFoundToRoute
                    Counter32,
               usrIpxPortalNumberOfAgedRoutes
                    Counter32,
               usrIpxPortalWrongNetRipPkt
                    Counter32,
               usrIpxPortalNumberOfAgedSaps
                    Counter32,
               usrIpxPortalNumberOfWDogReqRcvd
                    Counter32,
               usrIpxPortalNumberOfWDogRspSent
                    Counter32,
               usrIpxPortalNumberOfSerialPktsRcvd
                    Counter32,
               usrIpxPortalNumberOfEchoReqRcvd
                    Counter32,
               usrIpxPortalNumberOfEchoRspSent
                    Counter32,
               usrIpxPortalNumberOfPktsTooLargeRcvd
                    Counter32,
               usrIpxPortalRipReceiveState
                    INTEGER,
               usrIpxPortalSapReceiveState
                    INTEGER
               }
     usrIpxPortalSysInstance OBJECT-TYPE
        SYNTAX      Integer32
        MAX-ACCESS      read-write
        STATUS      	current
        DESCRIPTION "The unique identifier of the instance of IPX to
                      which this row corresponds."
     ::= {usrIpxPortalEntry 1}
     usrIpxPortalPortNumber OBJECT-TYPE
        SYNTAX      Integer32
        MAX-ACCESS      read-write
        STATUS      	current
        DESCRIPTION "The unique identifier for this IPX portal."
     ::= {usrIpxPortalEntry 2}
     usrIpxPortalNetBiosState OBJECT-TYPE
        SYNTAX      INTEGER {
                        disable(0),
                        enable(1)
                       }
        MAX-ACCESS      read-write
        STATUS      	current
        DESCRIPTION "The state of NetBios Processing. When enabled the 
                     router maintains a NetBios name table."
     ::= {usrIpxPortalEntry 3}
     usrIpxPortalNetworkDelay OBJECT-TYPE
        SYNTAX      Integer32
        MAX-ACCESS      read-write
        STATUS      	current
        DESCRIPTION "The delay, in ticks, for this portal interface."
     ::= {usrIpxPortalEntry 4}
     usrIpxPortalMaxNumberRipEntries OBJECT-TYPE
        SYNTAX      Integer32
        MAX-ACCESS      read-write
        STATUS      	current
        DESCRIPTION "The maximum number of entries within a RIP packet."
     ::= {usrIpxPortalEntry 5}
     usrIpxPortalMaxNumberSapEntries OBJECT-TYPE
        SYNTAX      Integer32
        MAX-ACCESS      read-write
        STATUS      	current
        DESCRIPTION "The maximum number of entries within a SAP packet."
     ::= {usrIpxPortalEntry 6}
     usrIpxPortalRipBroadcastState OBJECT-TYPE
        SYNTAX      INTEGER {
                        disable(0),
                        enable(1)
                       }
        MAX-ACCESS      read-write 
        STATUS      	current
        DESCRIPTION "RIP broadcast packet state. When enabled IPX RIP will be enabled
                     to send out RIP request packets transmitted over this portal. 
                     To totally disable RIP traffic usrIpxPortalRipPeriodicState
                     must also be set to disable."
     ::= {usrIpxPortalEntry 7}
     usrIpxPortalSapBroadcastState OBJECT-TYPE
        SYNTAX      INTEGER {
                        disable(0),
                        enable(1)
                       }
        MAX-ACCESS      read-write
        STATUS      	current
        DESCRIPTION "SAP broadcast packet state. When enabled IPX SAP will be enabled
                     to send out SAP request packets transmitted over this portal. 
                     To totally disable SAP traffic usrIpxPortalSapPeriodicState
                     must also be set to disable."
     ::= {usrIpxPortalEntry 8}
     usrIpxPortalRipPeriodicState OBJECT-TYPE
        SYNTAX      INTEGER {
                        disable(0),
                        enable(1)
                       }
        MAX-ACCESS      read-write
        STATUS      	current
        DESCRIPTION "RIP periodic state."
     ::= {usrIpxPortalEntry 9}
     usrIpxPortalSapPeriodicState OBJECT-TYPE
        SYNTAX      INTEGER {
                        disable(0),
                        enable(1)
                       }
        MAX-ACCESS      read-write
        STATUS      	current
        DESCRIPTION "Controls sending periodic SAP broadcasts over this portal."
     ::= {usrIpxPortalEntry 10}
     usrIpxPortalNetBiosNameCachingState OBJECT-TYPE
        SYNTAX      INTEGER {
                        disable(0),
                        enable(1)
                       }
        MAX-ACCESS      read-write
        STATUS      	current
        DESCRIPTION "NetBios name caching state. When enabled IPX will maintain a table
                     of NetBios names"
     ::= {usrIpxPortalEntry 11}
     usrIpxPortalNetBiosHops OBJECT-TYPE
        SYNTAX      Integer32 (0..65535)
        MAX-ACCESS      read-write
        STATUS      	current
        DESCRIPTION "NetBios maximum number of hops."
     ::= {usrIpxPortalEntry 12}
     usrIpxPortalDiagnosticState OBJECT-TYPE
        SYNTAX      INTEGER {
                        disable(0),
                        enable(1)
                       }
        MAX-ACCESS      read-write
        STATUS      	current
        DESCRIPTION "Diagnostic state."
     ::= {usrIpxPortalEntry 13}
     usrIpxPortalNetBiosNameCachingTimer OBJECT-TYPE
        SYNTAX      Integer32
        MAX-ACCESS      read-write
        STATUS      	current
        DESCRIPTION "NetBios name caching timer."
     ::= {usrIpxPortalEntry 14}
     usrIpxPortalMaxLearningRetries OBJECT-TYPE
        SYNTAX      Integer32
        MAX-ACCESS      read-write
        STATUS      	current
        DESCRIPTION "Maximum number of learning retries."
     ::= {usrIpxPortalEntry 15}
     usrIpxPortalIpxwanState OBJECT-TYPE
        SYNTAX      INTEGER {
                        disable(0),
                        enable(1)
                       }
        MAX-ACCESS      read-write
        STATUS      	current
        DESCRIPTION "Ipxwan State."
        --CONFIGURABLE
     ::= {usrIpxPortalEntry 16}
     usrIpxPortalLargeHopCount OBJECT-TYPE
        SYNTAX      Counter32
        MAX-ACCESS      read-only
        STATUS      	current
        DESCRIPTION "Displays number of IPX pkts with Large hop count."
        --CONFIGURABLE
     ::= {usrIpxPortalEntry 17}
     usrIpxPortalNetbsLargeHopCount OBJECT-TYPE
        SYNTAX      Counter32
        MAX-ACCESS      read-only
        STATUS      	current
        DESCRIPTION "Displays number of Netbios pkts with Large hop count."
        --CONFIGURABLE
     ::= {usrIpxPortalEntry 18}
     usrIpxPortalNoNetRipPkt OBJECT-TYPE
        SYNTAX      Counter32
        MAX-ACCESS      read-only
        STATUS      	current
        DESCRIPTION "Displays number of Netbios pkts with Large hop count."
        --CONFIGURABLE
     ::= {usrIpxPortalEntry 19}
     usrIpxPortalPathNotFoundToRoute OBJECT-TYPE
        SYNTAX      Counter32
        MAX-ACCESS      read-only
        STATUS      	current
        DESCRIPTION "Displays number of Netbios pkts with Large hop count."
        --CONFIGURABLE
     ::= {usrIpxPortalEntry 20}
     usrIpxPortalNumberOfAgedRoutes OBJECT-TYPE
        SYNTAX      Counter32
        MAX-ACCESS      read-only
        STATUS      	current
        DESCRIPTION "Displays number of routes that r aged in routing table"
        --CONFIGURABLE
     ::= {usrIpxPortalEntry 21}
     usrIpxPortalWrongNetRipPkt OBJECT-TYPE
        SYNTAX      Counter32
        MAX-ACCESS      read-only
        STATUS      	current
        DESCRIPTION "Displays number of routes that r aged in routing table"
        --CONFIGURABLE
     ::= {usrIpxPortalEntry 22}
     usrIpxPortalNumberOfAgedSaps OBJECT-TYPE
        SYNTAX      Counter32
        MAX-ACCESS      read-only
        STATUS      	current
        DESCRIPTION "Displays number of routes that r aged in routing table"
        --CONFIGURABLE
     ::= {usrIpxPortalEntry 23}
     usrIpxPortalNumberOfWDogReqRcvd OBJECT-TYPE
        SYNTAX      Counter32
        MAX-ACCESS      read-only
        STATUS      	current
        DESCRIPTION "Displays number of routes that r aged in routing table"
        --CONFIGURABLE
     ::= {usrIpxPortalEntry 24}
     usrIpxPortalNumberOfWDogRspSent OBJECT-TYPE
        SYNTAX      Counter32
        MAX-ACCESS      read-only
        STATUS      	current
        DESCRIPTION "Displays number of routes that r aged in routing table"
        --CONFIGURABLE
     ::= {usrIpxPortalEntry 25}
     usrIpxPortalNumberOfSerialPktsRcvd OBJECT-TYPE
        SYNTAX      Counter32
        MAX-ACCESS      read-only
        STATUS      	current
        DESCRIPTION "Displays number of routes that r aged in routing table"
        --CONFIGURABLE
     ::= {usrIpxPortalEntry 26}
     usrIpxPortalNumberOfEchoReqRcvd OBJECT-TYPE
        SYNTAX      Counter32
        MAX-ACCESS      read-only
        STATUS      	current
        DESCRIPTION "Displays number of routes that r aged in routing table"
        --CONFIGURABLE
     ::= {usrIpxPortalEntry 27}
     usrIpxPortalNumberOfEchoRspSent OBJECT-TYPE
        SYNTAX      Counter32
        MAX-ACCESS      read-only
        STATUS      	current
        DESCRIPTION "Displays number of routes that r aged in routing table"
        --CONFIGURABLE
     ::= {usrIpxPortalEntry 29}
     usrIpxPortalNumberOfPktsTooLargeRcvd OBJECT-TYPE
        SYNTAX      Counter32
        MAX-ACCESS      read-only
        STATUS      	current
        DESCRIPTION "Displays number of routes that r aged in routing table"
        --CONFIGURABLE
     ::= {usrIpxPortalEntry 30}
     usrIpxPortalRipReceiveState OBJECT-TYPE
        SYNTAX      INTEGER {
                       disable(0),
                       enable(1)
                       }
        MAX-ACCESS      read-write
        STATUS      	current
        DESCRIPTION "RIP receive packet state. When enabled IPX RIP will be enabled
                     to receive RIP packets over this portal.
                     To totally disable RIP traffic usrIpxPortalRipPeriodicState
                     must also be set to disable."
        --CONFIGURABLE
     ::= {usrIpxPortalEntry 31}
     usrIpxPortalSapReceiveState OBJECT-TYPE
        SYNTAX      INTEGER {
                        disable(0),
                        enable(1)
                       }
        MAX-ACCESS      read-write
        STATUS      	current
        DESCRIPTION "SAP receive packet state. When enabled IPX SAP will be enabled
                     to receive SAP packets over this portal.
                     To totally disable SAP traffic usrIpxPortalSapPeriodicState
                     must also be set to disable."
        --CONFIGURABLE
     ::= {usrIpxPortalEntry 32}
     usrIpxDynamicNetworkRangeStart OBJECT-TYPE
        SYNTAX   NetNumber
        MAX-ACCESS   read-write
        STATUS   	current
        DESCRIPTION
                "This is the first number in a range of network numbers IPX 
                 uses to dynamically assign to dial-in users.  The end of 
                 the range is determined by the object usrIpxMaxDynamicNetworkNumbers"
        --CONFIGURABLE
     ::= { usrIpx 11 }
     usrIpxMaxDynamicNetworkNumbers OBJECT-TYPE
        SYNTAX      Integer32
        MAX-ACCESS      read-write
        STATUS      	current
        DESCRIPTION "Maximum number of network addresses available to allocate to
                     dial-in users."
        --CONFIGURABLE
     ::= { usrIpx 12 }
     usrIpxSaveConfigFlag OBJECT-TYPE
        SYNTAX      UsrConfigStatus
        MAX-ACCESS      read-write
        STATUS      	current
        DESCRIPTION "Setting the value of this object to `save' causes the values
                 of the IPX configuration to be written out to the current IPX
                 config file, which is stored in the ipxConfigFile object. While
                 the new ConfigFile is being written, the IPX process
                 will set the value of this flag set to `saving''. Any
                 attempts to set the value while it is  not `normal'
                 (i.e. the file is currently being written to the
                 ConfigFile) will result in a badValue error being
                 returned. Setting the value to `normal' will result in no
                 action."
     ::= { usrIpx 13 }
    usrIpxConfigFileName OBJECT-TYPE
        SYNTAX      DisplayString
        MAX-ACCESS      read-only
        STATUS      	current
        DESCRIPTION        
          "The name of a ConfigFile to read/write permanent database records.
           If the value of this object is an empty string, then the
           IPX process uses the default name `@file://IpxProcess.cfg'. "
    ::= { usrIpx 14 }
     usrIpxState OBJECT-TYPE
        SYNTAX      UsrIpxStates 
        MAX-ACCESS      read-only
        STATUS      	current
        DESCRIPTION "Ipx state."
     ::= { usrIpx 15 }
     usrIpxEnable OBJECT-TYPE
        SYNTAX      INTEGER {
                        disable(0),
                        enable(1)
                       }
        MAX-ACCESS      read-write
        STATUS      	current
        DESCRIPTION "To enable or disable IPX.  When Disable is set the RIP process
                     will send out shutdown messages on all its ports in order
                     to inform neighboring routers that our routes are no longer
                     valid."
        --CONFIGURABLE
     ::= { usrIpx 16 }
-- USR Service Table
--   This table contains information for all services acquired via a
--   static sap or learned sap using a reduced set of indices which is common
--   to both Static and Non-Static SAPs. This is possible in the USR application
--   as a Static SAP entry that is added to the Static table does in the add process 
--   fill out the Non-Static field members that are contained in the same entry
--   structure. 
--   For the USR application, one entry structure is used for both Static and Non-Static 
--   and the instance index for both entries, although contained in different field 
--   members is always hard-wired to '1', and the Circuit index for Static entries is 
--   always hardwired to '0'.
--   Notes: (1.) This table was added to provide delete capability for learned saps
--          which requires write access. Write access is not available for
--          the IPX Service Table contained in the novell ipx mib.
--          In addition it also provides the mechanism to delete learned or
--          or statically entered saps.
--          (2.) The USR implementation of rows for both Static and Non-Static 
--          primary entries is a doubly linked list which has both entry types linked 
--          into one list. This one list is anchored at a common point which the mib 
--          entry for each of the two types refer to as starting point for accessing
--          that type's specific row instance. The whole list is actually scanned
--          for matching indices. This is conceptually different implementation
--          than what one might expect from a strictly SNMP mib row implementation,
--          where a binary tree structure might be expected with a node in the tree
--          representing an instance and providing branching to other nodes for
--          multiple instances. The USR application's implementation for mib rows is
--          is a non-sorted (all new Static and Non-Static SAP entries are always
--          added to the end of the list) linked list.
--          (3.) The intention for this table is only to provide a mapping overlay
--          of the Static and Non-Static row entries in order to provide a means
--          for deleting learned SAP entries as well as statically entered SAP entries.
    usrIpxServTable OBJECT-TYPE
        SYNTAX      SEQUENCE OF USRIpxServEntry
        MAX-ACCESS      not-accessible
        STATUS      	current
        DESCRIPTION "The Services table contains information about
                     all services reached via statically entered saps
                     or learned saps."
    ::= {usrIpx 17}
    usrIpxServEntry OBJECT-TYPE
        SYNTAX      USRIpxServEntry
        MAX-ACCESS      not-accessible
        STATUS      	current
        DESCRIPTION "Each entry corresponds to one service."
            INDEX       {
                        usrIpxServName,
                        usrIpxServType
                      }
    ::= {usrIpxServTable 1}
    USRIpxServEntry ::= 
             SEQUENCE {
                           usrIpxServName
                              OCTET STRING,
                           usrIpxServType
                              OCTET STRING,
                           usrIpxServExistState
                              INTEGER,
                           usrIpxServProtocol
                              INTEGER,
                           usrIpxServNetNum
                              NetNumber,
                           usrIpxServNode
                              OCTET STRING,
                           usrIpxServSocket
                              OCTET STRING,
                           usrIpxServHopCount
                              Integer32
                          }
    usrIpxServName OBJECT-TYPE
        SYNTAX      OCTET STRING (SIZE(1..48))
        MAX-ACCESS      read-write
        STATUS      	current
        DESCRIPTION "The service name."
        --CONFIGURABLE
    ::= {usrIpxServEntry 1}
    usrIpxServType OBJECT-TYPE
        SYNTAX      OCTET STRING (SIZE(2))
        MAX-ACCESS      read-write
        STATUS      	current
        DESCRIPTION "The service type."
        --CONFIGURABLE
    ::= {usrIpxServEntry 2}
    usrIpxServExistState OBJECT-TYPE
        SYNTAX      INTEGER {
                            off(1),
                            on(2)
                           }
        MAX-ACCESS      read-write
        STATUS      	current
        DESCRIPTION "The validity of this service.  Entries with the
                     value set to off may be deleted from the table at the
                     implementation's discretion."
    ::= {usrIpxServEntry 3}
    usrIpxServProtocol OBJECT-TYPE
        SYNTAX      INTEGER {
                        other(1),
                        local(2),
                        nlsp(4),
                        static(5),
                        sap(6)
                       }
        MAX-ACCESS      read-write
        STATUS      	current
        DESCRIPTION "The protocol from which knowledge of this service was
                     obtained."
    ::= {usrIpxServEntry 4}
    usrIpxServNetNum OBJECT-TYPE
        SYNTAX      NetNumber
        MAX-ACCESS      read-write
        STATUS      	current
        DESCRIPTION "The IPX network number portion of the IPX address of the
                     service."
        --CONFIGURABLE
    ::= {usrIpxServEntry 5}
    usrIpxServNode OBJECT-TYPE
        SYNTAX      OCTET STRING (SIZE(6))
        MAX-ACCESS      read-write
        STATUS      	current
        DESCRIPTION "The node portion of the IPX address of the service."
        --CONFIGURABLE
    ::= {usrIpxServEntry 6}
    usrIpxServSocket OBJECT-TYPE
        SYNTAX      OCTET STRING (SIZE(2))
        MAX-ACCESS      read-write
        STATUS      	current
        DESCRIPTION "The socket portion of the IPX address of the service."
        --CONFIGURABLE
    ::= {usrIpxServEntry 7}
    usrIpxServHopCount OBJECT-TYPE
        SYNTAX      Integer32
        MAX-ACCESS      read-write
        STATUS      	current
        DESCRIPTION "The number of router hops to the server on which the 
                     service resides."
        --CONFIGURABLE
    ::= {usrIpxServEntry 8}
    usrIpxDelServiceAll OBJECT-TYPE
        SYNTAX  INTEGER {
                        nonStatic(0)
                         }
        MAX-ACCESS  read-write
        STATUS  	current
        DESCRIPTION "This object is used to clear the whole SAP table.
                 Current support is only for clearing all non-static
                 SAP entries."
    ::= { usrIpx 18 }
-- Destination Table - this table almost duplicate a destination table
-- from standard novell_ipx.mib with an exception of a new field:
-- usrIpxDestExistState
--
--   The Destination table contains information about all known
--   destinations.  The routing information shown in this table represents
--   the path currently being used to reach the destination.
    usrIpxDestTable OBJECT-TYPE
        SYNTAX      SEQUENCE OF USRIPXDestEntry
        MAX-ACCESS      not-accessible
        STATUS      	current
        DESCRIPTION "The Destination table contains information about all
                    known destinations."
   ::= {usrIpx 19}
    usrIpxDestEntry OBJECT-TYPE
        SYNTAX      USRIPXDestEntry
        MAX-ACCESS      not-accessible
        STATUS      	current
        DESCRIPTION "Each entry corresponds to one destination."
            INDEX       {
                       usrIpxDestSysInstance,
                       usrIpxDestNetNum
                       }
   ::= {usrIpxDestTable 1}
    USRIPXDestEntry ::= SEQUENCE {
                     usrIpxDestSysInstance
                        Integer32,
                     usrIpxDestNetNum
                        NetNumber,
                     usrIpxDestProtocol
                        INTEGER,
                     usrIpxDestTicks
                        Integer32,
                     usrIpxDestHopCount
                        Integer32,
                     usrIpxDestNextHopCircIndex
                        Integer32,
                     usrIpxDestNextHopNICAddress
                        PhysAddress,
                     usrIpxDestNextHopNetNum
                        NetNumber,
                     usrIpxDestExistState
                        INTEGER
                    }
    usrIpxDestSysInstance OBJECT-TYPE
        SYNTAX      Integer32
        MAX-ACCESS      read-only
        STATUS      	current
        DESCRIPTION "The unique identifier of the instance of IPX
                to which this row corresponds."
   ::= {usrIpxDestEntry 1}
    usrIpxDestNetNum OBJECT-TYPE
        SYNTAX      NetNumber
        MAX-ACCESS      read-only
        STATUS      	current
        DESCRIPTION "The IPX network number of the destination."
   ::= {usrIpxDestEntry 2}
    usrIpxDestProtocol OBJECT-TYPE
        SYNTAX      INTEGER {
                        other(1),
                        local(2),
                        rip(3),
                        nlsp(4),
                        static(5)
                       }
        MAX-ACCESS      read-only
        STATUS      	current
        DESCRIPTION "The routing protocol from which knowledge of this
                destination was obtained."
   ::= {usrIpxDestEntry 3}
    usrIpxDestTicks OBJECT-TYPE
        SYNTAX      Integer32
        MAX-ACCESS      read-only
        STATUS      	current
        DESCRIPTION "The delay in ticks to reach this destination."
    ::= {usrIpxDestEntry 4}
    usrIpxDestHopCount OBJECT-TYPE
        SYNTAX      Integer32
        MAX-ACCESS      read-only
        STATUS      	current
        DESCRIPTION "The number of hops necessary to reach the destination."
    ::= {usrIpxDestEntry 5}
    usrIpxDestNextHopCircIndex OBJECT-TYPE
        SYNTAX      Integer32
        MAX-ACCESS      read-only
        STATUS      	current
        DESCRIPTION "The unique identifier of the circuit used to reach the 
                next hop."
    ::= {usrIpxDestEntry 6}
    usrIpxDestNextHopNICAddress OBJECT-TYPE
        SYNTAX      PhysAddress
        MAX-ACCESS      read-only
        STATUS      	current
        DESCRIPTION "The NIC address of the next hop."
    ::= {usrIpxDestEntry 7}
    usrIpxDestNextHopNetNum OBJECT-TYPE
        SYNTAX      NetNumber
        MAX-ACCESS      read-only
        STATUS      	current
        DESCRIPTION "The IPX network number of the next hop."
    ::= {usrIpxDestEntry 8}
    usrIpxDestExistState OBJECT-TYPE
        SYNTAX      INTEGER {
                      off(1),
                      on(2)
                       }
        MAX-ACCESS      read-write
        STATUS      	current
        DESCRIPTION "The validity of the route to this destination.  
                Valid row entry has this field set to on. 
                Learned routes with the value set to off will
                be removed from the routing table immediately, 
                static routes may be deleted from the table at the
                implementation's discretion."
    ::= {usrIpxDestEntry 9}
    usrIpxDelRouteAll OBJECT-TYPE
        SYNTAX  INTEGER {
           disable(0),
           enable(1)
        }
        MAX-ACCESS  read-write
        STATUS  	current
        DESCRIPTION "This object is used to clear the whole routing table"
    ::= { usrIpx 20 }
    usrPPPIpxAddress OBJECT-TYPE
        SYNTAX   OCTET STRING (SIZE(4))
        MAX-ACCESS   read-write
        STATUS   	current 
        DESCRIPTION
                "The IPX ADDRESS assigned to all PPP user's if they are configured as such."
        --CONFIGURABLE
        ::= { usrIpx 21 }
END         -- End IPX host MIB definitions
-- ************************************************************************
--
--	usr_ipx_cfg.mib
--
-- Author:         Peter Dobransky
--
USR-IPX-CFG-MIB DEFINITIONS ::= BEGIN
	IMPORTS
          OBJECT-TYPE, MODULE-IDENTITY,
          Integer32
                  FROM SNMPv2-SMI
          common
                  FROM USR-DEFINITIONS-MIB;
usrIpxCfg MODULE-IDENTITY
        LAST-UPDATED "200205051315Z"
        ORGANIZATION "CommWorks Corporation, a 3Com Company"
        CONTACT-INFO "Customer Support"
        DESCRIPTION
                "The commWorks enterprise defined MIB objects
                  for the IPX Configuration process."
--      REVISION "200205051315Z"
--      DESCRIPTION "Convert to SNMPv2"
        ::= { common 20 }
   -- Begin managed object definitions here...
     usrIpxCfgNetworkTable OBJECT-TYPE
	     SYNTAX SEQUENCE OF UsrIpxCfgNetworkEntry
	     MAX-ACCESS not-accessible
	     STATUS     current
	     DESCRIPTION
		     "This table is the same as the usrIpxPortalTable,
		      with the exception that it is indexed by the Network Number
			 defined in the usrIpxStaticRouteTable. This table will be
                used only by the the Configuration File Manager process to
                load permament configuration file records for named networks
                at system boot time. Any attempt to set this table from
                either the CLI process or SNMP will fail."
     ::= { usrIpxCfg 1 }
     usrIpxCfgNetworkEntry OBJECT-TYPE
	     SYNTAX UsrIpxCfgNetworkEntry
	     MAX-ACCESS not-accessible
	     STATUS     current
	     DESCRIPTION
		     "A (conceptual) entry for one IPX Network."
	     INDEX { usrIpxCfgNetSysInstance,
                  usrIpxCfgNetNetNumber }
     ::= { usrIpxCfgNetworkTable 1 }
     UsrIpxCfgNetworkEntry ::= SEQUENCE {
               usrIpxCfgNetSysInstance
                    Integer32,
               usrIpxCfgNetNetNumber
                    Integer32,
               usrIpxCfgNetNetBiosState
                    INTEGER,
               usrIpxCfgNetNetworkDelay
                    Integer32,
               usrIpxCfgNetRipBroadcastState
                    INTEGER,
               usrIpxCfgNetSapBroadcastState
                    INTEGER,
               usrIpxCfgNetRipPeriodicState
                    INTEGER,
               usrIpxCfgNetSapPeriodicState
                    INTEGER,
               usrIpxCfgNetNetBiosNameCachingState
                    INTEGER,
               usrIpxCfgNetNetBiosHops
                    Integer32,
               usrIpxCfgNetDiagnosticState
                    INTEGER,
               usrIpxCfgNetNetBiosNameCachingTimer
                    Integer32,
               usrIpxCfgNetMaxLearningRetries
                    Integer32,
			usrIpxCfgNetRipCircState
				INTEGER,
			usrIpxCfgNetRipCircUpdate
				Integer32,
			usrIpxCfgNetRipCircAgeMultiplier
				Integer32,
			usrIpxCfgNetRipCircPacketSize
				Integer32,
			usrIpxCfgNetSapCircState
				INTEGER,
			usrIpxCfgNetSapCircUpdate
				Integer32,
			usrIpxCfgNetSapCircAgeMultiplier
				Integer32,
			usrIpxCfgNetSapCircPacketSize
				Integer32,
			usrIpxCfgNetSapCircGetNearestServerReply
				INTEGER,
			usrIpxCfgNetIpxCircExistState
				INTEGER,
			usrIpxCfgNetIpxCircOperState
				INTEGER,
			usrIpxCfgNetIpxCircType
				INTEGER,
			usrIpxCfgNetIpxCircLocalMaxPacketSize
				Integer32
	}
     usrIpxCfgNetSysInstance OBJECT-TYPE
          SYNTAX      Integer32
          MAX-ACCESS      not-accessible
          STATUS          current
          DESCRIPTION 
               "The unique identifier of the instance of IPX to which this
               row corresponds."
     ::= {usrIpxCfgNetworkEntry 1}
     usrIpxCfgNetNetNumber OBJECT-TYPE
          SYNTAX      Integer32
          MAX-ACCESS      not-accessible
          STATUS          current
          DESCRIPTION
               "The unique identifier for this IPX network."
     ::= {usrIpxCfgNetworkEntry 2}
     usrIpxCfgNetNetBiosState OBJECT-TYPE
          SYNTAX      INTEGER {
                        disable(0),
                        enable(1)
                       }
          MAX-ACCESS      read-write
          STATUS          current
          DESCRIPTION
               "The state of NetBios Processing. When enabled the router
               maintains a NetBios name table."
          --CONFIGURABLE
     ::= {usrIpxCfgNetworkEntry 3}
     usrIpxCfgNetNetworkDelay OBJECT-TYPE
          SYNTAX      Integer32
          MAX-ACCESS      read-write
          STATUS          current
          DESCRIPTION
               "The delay, in ticks, for this portal interface."
          --CONFIGURABLE
     ::= {usrIpxCfgNetworkEntry 4}
     usrIpxCfgNetRipBroadcastState OBJECT-TYPE
          SYNTAX      INTEGER {
                        disable(0),
                        enable(1)
                       }
          MAX-ACCESS      read-write 
          STATUS          current
          DESCRIPTION
               "RIP broadcast packet state. When enabled IPX RIP will be
               enabled to send out RIP request packets transmitted over this
               portal. To totally disable RIP traffic
               usrIpxPortalRipPeriodicState must also be set to disable."
          --CONFIGURABLE
     ::= {usrIpxCfgNetworkEntry 5}
     usrIpxCfgNetSapBroadcastState OBJECT-TYPE
          SYNTAX      INTEGER {
                        disable(0),
                        enable(1)
                       }
          MAX-ACCESS      read-write
          STATUS          current
          DESCRIPTION
               "SAP broadcast packet state. When enabled IPX SAP will be
               enabled to send out SAP request packets transmitted over this
               portal. To totally disable SAP traffic
               usrIpxPortalSapPeriodicState must also be set to disable."
          --CONFIGURABLE
     ::= {usrIpxCfgNetworkEntry 6}
     usrIpxCfgNetRipPeriodicState OBJECT-TYPE
          SYNTAX      INTEGER {
                        disable(0),
                        enable(1)
                       }
          MAX-ACCESS      read-write
          STATUS          current
          DESCRIPTION
               "RIP periodic state."
          --CONFIGURABLE
     ::= {usrIpxCfgNetworkEntry 7}
     usrIpxCfgNetSapPeriodicState OBJECT-TYPE
          SYNTAX      INTEGER {
                        disable(0),
                        enable(1)
                       }
          MAX-ACCESS      read-write
          STATUS          current
          DESCRIPTION
               "Controls sending periodic SAP broadcasts over this portal."
          --CONFIGURABLE
     ::= {usrIpxCfgNetworkEntry 8}
     usrIpxCfgNetNetBiosNameCachingState OBJECT-TYPE
          SYNTAX      INTEGER {
                        disable(0),
                        enable(1)
                       }
          MAX-ACCESS      read-write
          STATUS          current
          DESCRIPTION
               "NetBios name caching state. When enabled IPX will maintain a
               table of NetBios names"
          --CONFIGURABLE
     ::= {usrIpxCfgNetworkEntry 9}
     usrIpxCfgNetNetBiosHops OBJECT-TYPE
          SYNTAX      Integer32 (0..65535)
          MAX-ACCESS      read-write
          STATUS          current
          DESCRIPTION
               "NetBios maximum number of hops."
          --CONFIGURABLE
     ::= {usrIpxCfgNetworkEntry 10}
     usrIpxCfgNetDiagnosticState OBJECT-TYPE
          SYNTAX      INTEGER {
                        disable(0),
                        enable(1)
                       }
          MAX-ACCESS      read-write
          STATUS          current
          DESCRIPTION
               "Diagnostic state."
          --CONFIGURABLE
     ::= {usrIpxCfgNetworkEntry 11}
     usrIpxCfgNetNetBiosNameCachingTimer OBJECT-TYPE
          SYNTAX      Integer32
          MAX-ACCESS      read-write
          STATUS          current
          DESCRIPTION
               "NetBios name caching timer."
          --CONFIGURABLE
     ::= {usrIpxCfgNetworkEntry 12}
     usrIpxCfgNetMaxLearningRetries OBJECT-TYPE
          SYNTAX      Integer32
          MAX-ACCESS      read-write
          STATUS          current
          DESCRIPTION
               "Maximum number of learning retries."
          --CONFIGURABLE
     ::= {usrIpxCfgNetworkEntry 13}
     usrIpxCfgNetRipCircState OBJECT-TYPE
   		SYNTAX      INTEGER {
                        off(1),
                        on(2),
                        auto-on(3),
                        auto-off(4)
                       }
   		MAX-ACCESS      read-write
   		STATUS          current
   		DESCRIPTION "Indicates whether RIP information may be sent/received
          	       over this circuit."
   		DEFVAL      { auto-off }
		--CONFIGURABLE
     ::= {usrIpxCfgNetworkEntry 14}
     usrIpxCfgNetRipCircUpdate OBJECT-TYPE
   		SYNTAX      Integer32
   		MAX-ACCESS      read-write
   		STATUS          current
   		DESCRIPTION "The RIP periodic update interval, in seconds."
   		DEFVAL      { 60 }
		--CONFIGURABLE
     ::= {usrIpxCfgNetworkEntry 15}
	usrIpxCfgNetRipCircAgeMultiplier OBJECT-TYPE
		SYNTAX      Integer32
		MAX-ACCESS      read-write
		STATUS          current
		DESCRIPTION "The holding multiplier for information received in RIP
          	       periodic updates."
		DEFVAL      { 4 }
		--CONFIGURABLE
     ::= {usrIpxCfgNetworkEntry 16}
	usrIpxCfgNetRipCircPacketSize OBJECT-TYPE
   		SYNTAX      Integer32
   		MAX-ACCESS      read-write
   		STATUS          current
   		DESCRIPTION "The RIP packet size used on this circuit."
		--CONFIGURABLE
   	::= {usrIpxCfgNetworkEntry 17}
     usrIpxCfgNetSapCircState OBJECT-TYPE
		SYNTAX      INTEGER {
                        off(1),
                        on(2),
                        auto-on(3),
                        auto-off(4)
                       }
   		MAX-ACCESS      read-write
   		STATUS          current
   		DESCRIPTION "Indicates whether SAP information may be sent/received
          	       over this circuit."
 		DEFVAL      { auto-off }
		--CONFIGURABLE
   	::= {usrIpxCfgNetworkEntry 18}
	usrIpxCfgNetSapCircUpdate OBJECT-TYPE
   		SYNTAX      Integer32
   		MAX-ACCESS      read-write
   		STATUS          current
   		DESCRIPTION "The SAP periodic update interval, in seconds."
   		DEFVAL      { 60 }
		--CONFIGURABLE
   	::= {usrIpxCfgNetworkEntry 19}
	usrIpxCfgNetSapCircAgeMultiplier OBJECT-TYPE
   		SYNTAX      Integer32
   		MAX-ACCESS      read-write
   		STATUS          current
   		DESCRIPTION "The holding multiplier for information received in SAP
	                 periodic updates."
   		DEFVAL      { 4 }
		--CONFIGURABLE
   	::= {usrIpxCfgNetworkEntry 20}
	usrIpxCfgNetSapCircPacketSize OBJECT-TYPE
   		SYNTAX      Integer32
   		MAX-ACCESS      read-write
   		STATUS          current
   		DESCRIPTION "The SAP packet size used on this circuit."
		--CONFIGURABLE
   	::= {usrIpxCfgNetworkEntry 21}
	usrIpxCfgNetSapCircGetNearestServerReply OBJECT-TYPE
   		SYNTAX      INTEGER {
                        no(1),
                        yes(2)
                       }
   		MAX-ACCESS      read-write
   		STATUS          current
   		DESCRIPTION "Indicates whether to respond to SAP get nearest server
          	       requests received on this circuit."
   		DEFVAL      { yes }
		--CONFIGURABLE
   	::= {usrIpxCfgNetworkEntry 22}
	usrIpxCfgNetIpxCircExistState OBJECT-TYPE
   		SYNTAX      INTEGER {
                        off(1),
                        on(2)
                       }
   		MAX-ACCESS      read-write
   		STATUS          current
   		DESCRIPTION "The validity of this circuit entry.  A circuit with this
          	       value set to off may be deleted from the table at the
                	  IPX implementation's discretion."
		--CONFIGURABLE
   	::= {usrIpxCfgNetworkEntry 23}
	usrIpxCfgNetIpxCircOperState OBJECT-TYPE
   		SYNTAX      INTEGER {
                        down(1),
                        up(2),
                        sleeping(3)
                       }
   		MAX-ACCESS      read-write
   		STATUS          current
   		DESCRIPTION "The operational state of the circuit."
		--CONFIGURABLE
   	::= {usrIpxCfgNetworkEntry 24}
	usrIpxCfgNetIpxCircType OBJECT-TYPE
   		SYNTAX      INTEGER {
                        other(1),
                        broadcast(2),
                        ptToPt(3),
                        wanRIP(4),
                        unnumberedRIP(5),
                        dynamic(6),
                        wanWS(7)
                       }
   		MAX-ACCESS      read-write
   		STATUS          current
   		DESCRIPTION "The type of the circuit."
		--CONFIGURABLE
   	::= {usrIpxCfgNetworkEntry 25}
	usrIpxCfgNetIpxCircLocalMaxPacketSize OBJECT-TYPE
   		SYNTAX      Integer32
   		MAX-ACCESS      read-write
   		STATUS          current
   		DESCRIPTION "The maximum size (including header), in bytes, that the
          	       system supports locally on this circuit."
		--CONFIGURABLE
   	::= {usrIpxCfgNetworkEntry 26}
END  -- End of USR-IPX-CFG-MIB DEFINITIONS
-- ************************************************************************
--
--	usr_snmp.mib - The CommWorks SNMP MIB module
--
-- Author:         Jim Halpin
--
USR-SNMP-MIB DEFINITIONS ::= BEGIN
	IMPORTS
        OBJECT-TYPE, MODULE-IDENTITY,
		IpAddress, Integer32
                  FROM SNMPv2-SMI
        DisplayString
                  FROM SNMPv2-TC
        UsrLongString, common, UsrConfigStatus, UsrDisplayString
                  FROM USR-DEFINITIONS-MIB;
    usrSnmp MODULE-IDENTITY
         LAST-UPDATED "200205051300Z"
         ORGANIZATION "CommWorks Corporation, a 3Com Company"
         CONTACT-INFO "Customer Support"
         DESCRIPTION
                 "The commWorks enterprise defined MIB objects
                   for the SNMP process."
--       REVISION "200205051300Z"
--       DESCRIPTION "Convert to SNMPv2"
         ::= { common 5 }
   -- textual conventions
   -- 
   -- textual conventions are like pre-processor macro in 'C'
   --        (i.e. #define statements)
   -- Use them to define your own 'datatypes'
   -- memory size, expressed in units of 1024bytes
	-- A sample Table definition.
	usrSnmpConfigFileName OBJECT-TYPE
		SYNTAX          UsrDisplayString
		MAX-ACCESS      read-only
		STATUS          current
		DESCRIPTION		
		  "The name of a ConfigFile to read/write permanent database records.
		   If the value of this object is an empty string, then the
		   SNMP process uses the default name `@file://SnmpProcess.cfg'. "
	::= { usrSnmp 1 }
	usrSnmpCFMStatusFlag  OBJECT-TYPE
	 	SYNTAX	  UsrConfigStatus
		MAX-ACCESS      read-write
		STATUS          current
		DESCRIPTION
		  "Setting the value of this object to `save' causes the values
		   of the SNMP Group to be written out to the current config
		   file, which is stored in the usrSnmpConfigFileName object.
		   While the new ConfigFile is being written, the SNMP process
		   will set the value of this flag to `saving''. Any
		   attempts to set the value while it is not `normal'
		   (i.e. the file is currently being written to the
		   ConfigFile) while result in a badValue error being
		   returned. Setting the value to `normal' will result in no
		   action."
	::= { usrSnmp 2 }
	usrSnmpCommTable OBJECT-TYPE
		SYNTAX  SEQUENCE OF UsrSnmpCommEntry
         	MAX-ACCESS  not-accessible
         	STATUS      current
         	DESCRIPTION
            "The SNMP Community Table"
	::= { usrSnmp 3 }
	usrSnmpCommEntry OBJECT-TYPE
         	SYNTAX  UsrSnmpCommEntry
         	MAX-ACCESS  not-accessible
         	STATUS      current
         	DESCRIPTION
            ""
         INDEX   { usrSnmpCommName }
	::= { usrSnmpCommTable 1 }
	UsrSnmpCommEntry ::=
         	SEQUENCE {
         	usrSnmpCommName
            DisplayString,
         	usrSnmpCommIpAddr
            IpAddress,
         	usrSnmpCommAccess
            INTEGER,
         	usrSnmpCommStatus
            INTEGER,
         	usrSnmpCommLastError
            UsrLongString,
         	usrSnmpCommLastErrorTicks
                Integer32,
          usrSnmpCommPoolName
            UsrDisplayString,
	  usrSnmpCommPoolValid
            INTEGER,
          usrSnmpCommValidateAddress
            INTEGER
         }
	usrSnmpCommName OBJECT-TYPE
         	SYNTAX  DisplayString (SIZE (0..255))
         	MAX-ACCESS  not-accessible
         	STATUS      current
         	DESCRIPTION
            "The name of the SNMP Community."
	::= { usrSnmpCommEntry 1 }
	usrSnmpCommIpAddr OBJECT-TYPE
         	SYNTAX  IpAddress
         	MAX-ACCESS  read-write
         	STATUS      current
         	DESCRIPTION
            "The IP Address of the remote community"
		--CONFIGURABLE
	::= { usrSnmpCommEntry 2 }
	usrSnmpCommAccess OBJECT-TYPE
	 	SYNTAX   INTEGER {
			readOnly(1),
			readWrite(2),
			administrator(4)
			}
         	MAX-ACCESS   read-write
         	STATUS       current
         	DESCRIPTION
            "The allowed access for this community.
		   A value of readOnly(1) allows read-only access to user-level
		   objects.
		   A value of readWrite(2) allows read access to user-level
		   objects and write access to writable user-level objects.
		   A value of administrator(3) allows read access to all
		   objects and write access to all writable objects."
		--CONFIGURABLE
         ::= { usrSnmpCommEntry 3 }
	usrSnmpCommStatus OBJECT-TYPE
	 	SYNTAX   INTEGER {
			normal(1),
			delete(2)
			}
         	MAX-ACCESS   read-write
         	STATUS       current
         	DESCRIPTION
            "The status of the entry for this community"
         ::= { usrSnmpCommEntry 4 }
	usrSnmpCommLastError OBJECT-TYPE
         	SYNTAX  UsrLongString (SIZE (0..511))
         	MAX-ACCESS  read-only
         	STATUS      current
         	DESCRIPTION
            "If there is an error on a request, this variable may
		   contain a message indicating the error."
	::= { usrSnmpCommEntry 5 }
	usrSnmpCommLastErrorTicks OBJECT-TYPE
	 	SYNTAX   Integer32
         	MAX-ACCESS   read-only
         	STATUS       current
         	DESCRIPTION
            "If the LastError variable is set, this is set to the
		   tick count of that error."
         ::= { usrSnmpCommEntry 6 }
	usrSnmpCommPoolName OBJECT-TYPE
	 	SYNTAX   UsrDisplayString (SIZE (0..32))
         	MAX-ACCESS   read-write
         	STATUS       current
         	DESCRIPTION
            "The name of the SNMP community address pool to use
             for this community."
         --CONFIGURABLE
         ::= { usrSnmpCommEntry 7 }
	usrSnmpCommPoolValid OBJECT-TYPE
	 	SYNTAX   INTEGER {
			valid(1),
			invalid(2)
			}
         	MAX-ACCESS   read-only
         	STATUS       current
         	DESCRIPTION
            "A value of valid(1) means that the community pool
             assigned to this community exists. A value of
             invalid(2) means that the community pool assigned
             to this community does not exist."
         ::= { usrSnmpCommEntry 8 }
	usrSnmpCommValidateAddress OBJECT-TYPE
	 	SYNTAX   INTEGER {
			useAddress(1),
			usePool(2)
			}
         	MAX-ACCESS   read-write
         	STATUS       current
         	DESCRIPTION
            "If this object is set to use_address(1), the value
             of usrSnmpCommIpAddr will be used to validate that the
             management station is allowed access. If this object
             is set to use_pool(2), the IP address of the
             management station will be validate using the list
             of IP addresses configured for the usrSnmpCommPoolName."
         DEFVAL { useAddress }
         --CONFIGURABLE
         ::= { usrSnmpCommEntry 9 }
	usrSnmpTrapCommTable OBJECT-TYPE
         	SYNTAX  SEQUENCE OF UsrSnmpTrapCommEntry
         	MAX-ACCESS  not-accessible
         	STATUS      current
         	DESCRIPTION
            "The SNMP Trap Community Table"
	::= { usrSnmp 4 }
	usrSnmpTrapCommEntry OBJECT-TYPE
         	SYNTAX  UsrSnmpTrapCommEntry
         	MAX-ACCESS  not-accessible
         	STATUS      current
         	DESCRIPTION
            ""
         INDEX   { usrSnmpTrapCommName }
	::= { usrSnmpTrapCommTable 1 }
	UsrSnmpTrapCommEntry ::=
         	SEQUENCE {
         	usrSnmpTrapCommName
            UsrDisplayString,
         	usrSnmpTrapCommIpAddr
            IpAddress,
         	usrSnmpTrapCommStatus
            INTEGER,
                usrSnmpTrapCommPoolName
            UsrDisplayString,
	        usrSnmpTrapCommPoolValid
            INTEGER,
                usrSnmpTrapCommValidateAddress
            INTEGER
         }
	usrSnmpTrapCommName OBJECT-TYPE
         	SYNTAX      UsrDisplayString (SIZE (0..255))
         	MAX-ACCESS  not-accessible
         	STATUS      current
         	DESCRIPTION
            "The name of the SNMP Trap Community."
	::= { usrSnmpTrapCommEntry 1 }
	usrSnmpTrapCommIpAddr OBJECT-TYPE
         	SYNTAX  IpAddress
         	MAX-ACCESS  read-write
         	STATUS      current
         	DESCRIPTION
            "The IP Address of the remote community"
		--CONFIGURABLE
	::= { usrSnmpTrapCommEntry 2 }
	usrSnmpTrapCommStatus OBJECT-TYPE
		SYNTAX   INTEGER {
			normal(1),
			delete(2)
			}
         	MAX-ACCESS   read-write
         	STATUS       current
         	DESCRIPTION
            "The status of the entry for this community"
         ::= { usrSnmpTrapCommEntry 3 }
	usrSnmpTrapCommPoolName OBJECT-TYPE
	 	SYNTAX           UsrDisplayString (SIZE (0..32))
         	MAX-ACCESS   read-write
         	STATUS       current
         	DESCRIPTION
            "The name of the SNMP community address pool to use
             for this community."
         --CONFIGURABLE
         ::= { usrSnmpTrapCommEntry 4 }
	usrSnmpTrapCommPoolValid OBJECT-TYPE
	 	SYNTAX   INTEGER {
			valid(1),
			invalid(2)
			}
         	MAX-ACCESS   read-only
         	STATUS       current
         	DESCRIPTION
            "A value of valid(1) means that the community pool
             assigned to this community exists. A value of
             invalid(2) means that the community pool assigned
             to this community does not exist."
         ::= { usrSnmpTrapCommEntry 5 }
	usrSnmpTrapCommValidateAddress OBJECT-TYPE
	 	SYNTAX   INTEGER {
			useAddress(1),
			usePool(2)
			}
         	MAX-ACCESS   read-write
         	STATUS       current
         	DESCRIPTION
            "If this object is set to use_address(1), the value
             of usrSnmpTrapCommIpAddr will be used to validate that the
             management station is allowed access. If this object
             is set to use_pool(2), the IP address of the
             management station will be validate using the list
             of IP addresses configured for the usrSnmpCommPoolName."
         DEFVAL { useAddress }
         --CONFIGURABLE
         ::= { usrSnmpTrapCommEntry 6 }
	usrSnmpCommAddrPoolTable OBJECT-TYPE
         	SYNTAX  SEQUENCE OF UsrSnmpCommAddrPoolEntry
         	MAX-ACCESS  not-accessible
         	STATUS      current
         	DESCRIPTION
            "The SNMP Community Address Pool Table"
	::= { usrSnmp 5 }
	usrSnmpCommAddrPoolEntry OBJECT-TYPE
         	SYNTAX  UsrSnmpCommAddrPoolEntry
         	MAX-ACCESS  not-accessible
         	STATUS      current
         	DESCRIPTION
            ""
         INDEX   { usrSnmpCommAddrPoolName,
                   usrSnmpCommAddrPoolIpAddr }
	::= { usrSnmpCommAddrPoolTable 1 }
	UsrSnmpCommAddrPoolEntry ::=
         	SEQUENCE {
         	usrSnmpCommAddrPoolName
            UsrDisplayString,
         	usrSnmpCommAddrPoolIpAddr
            IpAddress,
         	usrSnmpCommAddrPoolStatus
            INTEGER,
	        usrSnmpCommAddrPoolGroupCount
            Integer32
         }
	usrSnmpCommAddrPoolName OBJECT-TYPE
         	SYNTAX      UsrDisplayString (SIZE (0..32))
         	MAX-ACCESS  not-accessible
         	STATUS      current
         	DESCRIPTION
            "The name of the SNMP Community Address Pool."
	::= { usrSnmpCommAddrPoolEntry 1 }
	usrSnmpCommAddrPoolIpAddr OBJECT-TYPE
         	SYNTAX  IpAddress
         	MAX-ACCESS  not-accessible
         	STATUS      current
         	DESCRIPTION
            "An IP Address in the SNMP community address pool."
	::= { usrSnmpCommAddrPoolEntry 2 }
	usrSnmpCommAddrPoolStatus OBJECT-TYPE
		SYNTAX   INTEGER {
			normal(1),
			delete(2)
			}
         	MAX-ACCESS   read-write
         	STATUS       current
         	DESCRIPTION
            "The status of the entry in this SNMP community
             address pool."
         --CONFIGURABLE
         ::= { usrSnmpCommAddrPoolEntry 3 }
	usrSnmpCommAddrPoolGroupCount OBJECT-TYPE
		SYNTAX   Integer32
         	MAX-ACCESS   read-only
         	STATUS       current
         	DESCRIPTION
            "The number of addresses per community."
         ::= { usrSnmpCommAddrPoolEntry 4 }
	usrSnmpTrapCommAddrPoolTable OBJECT-TYPE
         	SYNTAX  SEQUENCE OF UsrSnmpTrapCommAddrPoolEntry
         	MAX-ACCESS  not-accessible
         	STATUS      current
         	DESCRIPTION
            "The SNMP Community Address Pool Table"
	::= { usrSnmp 6 }
	usrSnmpTrapCommAddrPoolEntry OBJECT-TYPE
         	SYNTAX  UsrSnmpTrapCommAddrPoolEntry
         	MAX-ACCESS  not-accessible
         	STATUS      current
         	DESCRIPTION
            ""
         INDEX   { usrSnmpTrapCommAddrPoolName,
                   usrSnmpTrapCommAddrPoolIpAddr }
	::= { usrSnmpTrapCommAddrPoolTable 1 }
	UsrSnmpTrapCommAddrPoolEntry ::=
         	SEQUENCE {
         	usrSnmpTrapCommAddrPoolName
            UsrDisplayString,
         	usrSnmpTrapCommAddrPoolIpAddr
            IpAddress,
         	usrSnmpTrapCommAddrPoolStatus
            INTEGER,
	        usrSnmpTrapCommAddrPoolGroupCount
            Integer32
         }
	usrSnmpTrapCommAddrPoolName OBJECT-TYPE
         	SYNTAX      UsrDisplayString (SIZE (0..32))
         	MAX-ACCESS  not-accessible
         	STATUS      current
         	DESCRIPTION
            "The name of the SNMP Community Address Pool."
	::= { usrSnmpTrapCommAddrPoolEntry 1 }
	usrSnmpTrapCommAddrPoolIpAddr OBJECT-TYPE
         	SYNTAX  IpAddress
         	MAX-ACCESS  not-accessible
         	STATUS      current
         	DESCRIPTION
            "An IP Address in the SNMP community address pool."
	::= { usrSnmpTrapCommAddrPoolEntry 2 }
	usrSnmpTrapCommAddrPoolStatus OBJECT-TYPE
		SYNTAX   INTEGER {
			normal(1),
			delete(2)
			}
         	MAX-ACCESS   read-write
         	STATUS       current
         	DESCRIPTION
            "The status of the entry in this SNMP community
             address pool."
         --CONFIGURABLE
         ::= { usrSnmpTrapCommAddrPoolEntry 3 }
	usrSnmpTrapCommAddrPoolGroupCount OBJECT-TYPE
    		SYNTAX       Integer32
         	MAX-ACCESS   read-only
         	STATUS       current
         	DESCRIPTION
            "The number of addresses per community."
         ::= { usrSnmpTrapCommAddrPoolEntry 4 }
END  -- End of USR-SNMP-MIB DEFINITIONS
-- ************************************************************************
--
--	usr_event.mib
--
-- Author:         Jim Halpin
--
Event-MIB DEFINITIONS ::= BEGIN
	IMPORTS
             OBJECT-TYPE, MODULE-IDENTITY, Counter32, IpAddress
                  FROM SNMPv2-SMI
             TruthValue, DisplayString
                  FROM SNMPv2-TC
             common, UsrConfigStatus
                  FROM USR-DEFINITIONS-MIB;
usrEventHandler MODULE-IDENTITY
         LAST-UPDATED "200203181400Z"
         ORGANIZATION "CommWorks Corporation, a 3Com Company"
         CONTACT-INFO "Customer Support"
         DESCRIPTION
                 "The commWorks enterprise defined MIB objects
                   for the Event Handling Process."
--      REVISION "200203181400Z"
--      DESCRIPTION "Converted to SNMPv2"
::= { common 9 }
   -- textual conventions
   -- Begin managed object definitions here...
usrEhVersion OBJECT-TYPE
	SYNTAX		DisplayString
	MAX-ACCESS	read-only
	STATUS		current
	DESCRIPTION
		"The current software version of the Event Handler process.."
::= { usrEventHandler 1 }
usrEhConfigFileName OBJECT-TYPE
	SYNTAX		DisplayString
	MAX-ACCESS	read-only
	STATUS		current
	DESCRIPTION		
		  "The name of a ConfigFile to read/write permanent database 
                   records. If the value of this object is an empty string, 
                   then the Event process uses the default name 
                   `@file://EventProcess.cfg'."
::= { usrEventHandler 2 }
usrEhCFMStatusFlag OBJECT-TYPE
	SYNTAX		UsrConfigStatus
	MAX-ACCESS	read-write
	STATUS		current
	DESCRIPTION
		"This variable controls saving and loading of configuration
           information for the Event Handler process. The value can 
           be set to either save or load by a management station. The other
           values indicate if any configuration operation and what type
           is in progress."
::= { usrEventHandler 3 }
usrEhSyslogTable OBJECT-TYPE
	SYNTAX SEQUENCE OF UsrEhSyslogEntry
	MAX-ACCESS not-accessible
	STATUS current
	DESCRIPTION
		"The (conceptual) table of SYSLOG sink nodes."
::= { usrEventHandler 4 }
usrEhSyslogEntry OBJECT-TYPE
	SYNTAX UsrEhSyslogEntry
	MAX-ACCESS not-accessible
	STATUS current
	DESCRIPTION
		"A (conceptual) entry for one SYSLOG sink node."
	INDEX { usrEhSyslogSink }
::= { usrEhSyslogTable 1 }
UsrEhSyslogEntry ::= SEQUENCE {
	usrEhSyslogSink			        IpAddress,
	usrEhSyslogLevel			INTEGER,
	usrEhSyslogMsgCount			Counter32,
	usrEhSyslogStatus			INTEGER,
	usrEhSyslogFacility			INTEGER,
	usrEhSyslogAllowAllAuthLevels		TruthValue
--	usrEhSyslogBufferConfDepth		INTEGER
	}
usrEhSyslogSink OBJECT-TYPE
	SYNTAX		IpAddress
	MAX-ACCESS	not-accessible
	STATUS		current
	DESCRIPTION
		"The IP Address of the SYSLOG sink system. Event messages for 
                 the EVF_SYSLOG event sink will be sent to this address's UDP
                 port number 514."
::= { usrEhSyslogEntry 1 }
usrEhSyslogLevel OBJECT-TYPE
	SYNTAX	INTEGER { critical(0), unusual(1), common(2), verbose(3),
						debug(4) }
	MAX-ACCESS	read-write
	STATUS		current
	DESCRIPTION
		"The log level associated with this SYSLOG sink node."
	--CONFIGURABLE
::= { usrEhSyslogEntry 2 }
usrEhSyslogMsgCount OBJECT-TYPE
	SYNTAX		Counter32
	MAX-ACCESS	read-only
	STATUS		current
	DESCRIPTION
		"The number of event messages sent to this syslog sink."
::= { usrEhSyslogEntry 3 }
usrEhSyslogStatus OBJECT-TYPE
	SYNTAX		INTEGER { normal(1), delete(2) }
	MAX-ACCESS	read-write
	STATUS		current
	DESCRIPTION
		"Status flag for the SYSLOG sink. The value returned by the
		 Event process will always be normal. Setting the value to
		 delete will cause the entry to removed from the table."
::= { usrEhSyslogEntry 4 }
usrEhSyslogFacility OBJECT-TYPE
	SYNTAX		INTEGER { auth(1), local0(2), local1(3),
				local2(4), local3(5), local4(6),
				local5(7), local6(8), local7(9) }
	MAX-ACCESS	read-write
	STATUS		current
	DESCRIPTION
		"The SYSLOG sink node facility to which the SYSLOG message is
		 is sent."
	--CONFIGURABLE
::= { usrEhSyslogEntry 5 }
usrEhSyslogAllowAllAuthLevels OBJECT-TYPE
	SYNTAX		TruthValue
	MAX-ACCESS	read-write
	STATUS		current
	DESCRIPTION
		"Whether Pilgrim Auth facility messages get sent irrespective
                 of  their loglevels.  Default is Yes(2).  No is (1)."
	--CONFIGURABLE
::= { usrEhSyslogEntry 6 }
-- usrEhSyslogBufferConfDepth OBJECT-TYPE
--	SYNTAX		INTEGER (1..256)
--	MAX-ACCESS	read-write
--	STATUS		current
--	DESCRIPTION
--		"Maximum number of syslogs that are buffered for a particular 
--               server"
--	CONFIGURABLE
-- ::= { usrEhSyslogEntry 7 }
-- usrEhSyslogBufferReset OBJECT-TYPE
--	SYNTAX		INTEGER (1..2)
--	MAX-ACCESS	write-only
--	STATUS		current
--	DESCRIPTION
--		"Maximum number of syslogs that are buffered for a particular server"
--	CONFIGURABLE
-- ::= { usrEhSyslogEntry 8 }
-- usrEhSyslogBufferState OBJECT-TYPE
--	SYNTAX		INTEGER {
--                       enabled(1),
--                      disabled(2)
--                     }
--	MAX-ACCESS	read-write
--	STATUS		current
--	DESCRIPTION
--		"This flag states whether syslog buffering is enabled."
-- ::= { usrEventHandler 5 }
END         -- End of Event-MIB DEFINITIONS
-- ************************************************************************
--
--     usr_cip.mib 
--
--	Description:	This module contains MIB definitions for the 
--      		Call-Initiation Process. 
--
--	Author:	Hasmik Sarkezians
--
Cip-MIB DEFINITIONS ::= BEGIN
	IMPORTS
          MODULE-IDENTITY, OBJECT-TYPE, Integer32,
	  Counter32, Gauge32 , IpAddress
                FROM SNMPv2-SMI
          DisplayString, DateAndTime
                FROM SNMPv2-TC
          UsrLongString, common
                FROM USR-DEFINITIONS-MIB;
    usrCip   MODULE-IDENTITY
         LAST-UPDATED "200208012020Z"
         ORGANIZATION "CommWorks Corporation, a 3Com Company"
         CONTACT-INFO "Customer Support"
         DESCRIPTION
                 "The commWorks enterprise defined MIB objects
                   for CIP"
--      REVISION "200202182020Z"
--      DESCRIPTION
--              "Converted to SNMPv2"
         ::= { common 10 }
   -- textual conventions
   -- 
   -- textual conventions are like pre-processor macro in 'C'
   --        (i.e. #define statements)
   -- Use them to define your own 'datatypes'
   NetNumber ::= OCTET STRING (SIZE(4))
   -- Begin managed object definitions here...
    usrCipPortParamTable OBJECT-TYPE
         SYNTAX  SEQUENCE OF USRCIPPortParamEntry
         MAX-ACCESS  not-accessible
         STATUS  current
         DESCRIPTION
            "This table contains the serial port parameters."
	::= { usrCip 1 }
    usrCipPortParamEntry OBJECT-TYPE
        SYNTAX      USRCIPPortParamEntry
        MAX-ACCESS  not-accessible
        STATUS      current
        DESCRIPTION "Each entry corresponds to a serial interface."
        INDEX   {
                usrCipPortIndex
               }
     ::= {usrCipPortParamTable 1}
     USRCIPPortParamEntry ::= 
          SEQUENCE {
               usrCipPortIndex
                    Integer32,
               usrCipPortType
                    INTEGER,
               usrCipPortAccess
                    INTEGER,
               usrCipPortHostType
                    INTEGER,
               usrCipPortLoginService
                    INTEGER,
               usrCipPortTcpPortNumber
                    Integer32,
               usrCipPortLoginMsg
                    OCTET STRING,
               usrCipPortLoginPrompt
                    OCTET STRING,
               usrCipPortIpAddress
                    IpAddress,
               usrCipPortHostIpAddress
                    IpAddress,
               usrCipPortNetMask
                    Integer32,
               usrCipPortProtocol
                    INTEGER,
               usrCipPortMtu
                    Integer32,
               usrCipPortIdleTimeOut
                    Integer32,
               usrCipPortState
                    INTEGER,
               usrCipPortNumConns
                    Counter32,
               usrCipPortConnType
                    INTEGER,
               usrCipUserName
                    OCTET STRING,
               usrCipConnStartTime
                    Integer32,
               usrCipDataLinkConn
                    INTEGER,
               usrCipInitScriptName
                    DisplayString,
               usrCipIfConnType
                    INTEGER,
               usrCipPromptUserName
                    OCTET STRING,
               usrCipUserPasswd
                    OCTET STRING,
               usrCipPortIfName
                    OCTET STRING,
               usrCipPortDialPrefix
                    OCTET STRING,
               usrCipPortCfgScript
                    DisplayString,
               usrCipPortCfgScriptResult
                    UsrLongString,
               usrCipPortPromptingStyle
                    INTEGER,
               usrCipPortLoginProcessing
                    INTEGER,
               usrCipPortCallType
                   INTEGER,
	       usrCipPortDNISAuthentication
		   INTEGER,
	       usrCipPortDNISAuthTime
		   INTEGER,
	       usrCipPortDNISAuthType
		   INTEGER,
	       usrCipPortDNISPassword
		   OCTET STRING, 
	       usrCipPortDNISTimeout
		   Integer32,
	       usrCipPortParity
		   INTEGER,
               usrCipPortDomainName
                    OCTET STRING,
               usrCipPortDelimiter 
                    OCTET STRING,
               usrCipPromptDelay 
                   Integer32,
	       usrCipPromptTimeout
		   Integer32,
	       usrCipSpecialXonXoffFlow
                   INTEGER,
               usrCipCalledPhoneNumber
                   OCTET STRING,
	       usrCipCallingPhoneNumber
                   OCTET STRING,
	       usrCipPortGlobalConnId
		   Integer32,
	       usrCipPortUseDnisPool
		   INTEGER,
	       usrCipPortLoginTable
		   OCTET STRING,
     		usrCipPortMobileType
		   INTEGER
               }
     usrCipPortIndex OBJECT-TYPE
          SYNTAX      Integer32
          MAX-ACCESS  not-accessible
          STATUS      current
          DESCRIPTION "The identifier of the physical interface."
     ::= {usrCipPortParamEntry 1}
     usrCipPortType OBJECT-TYPE
          SYNTAX      INTEGER {
                         login (1),
                         network (2),
                         login-network (3)
                         }
          MAX-ACCESS  read-write
          STATUS      current
          DESCRIPTION "The type of the physical port."
        --CONFIGURABLE
     ::= {usrCipPortParamEntry 2}
     usrCipPortAccess OBJECT-TYPE
          SYNTAX      INTEGER {
                         dial-in(1),
                         dial-out(2),
                         two-way(3)
                       }
          MAX-ACCESS  read-write
          STATUS      current
          DESCRIPTION "This field specifies the direction of the calls
                         that could be made on a specific interface. 
                         Ports could be configured to be dial-in, dial-out
                         or two-way ports."
       --CONFIGURABLE
     ::= {usrCipPortParamEntry 3}
     usrCipPortHostType OBJECT-TYPE
          SYNTAX      INTEGER {
                         undefined (0),
                         default (1),
                         prompt (2),
                         specified (3)
                         }
          MAX-ACCESS  read-write
          STATUS      current
          DESCRIPTION "The host type that the dial-in user 
                       will be connected to."
        --CONFIGURABLE
     ::= {usrCipPortParamEntry 4}
     usrCipPortLoginService OBJECT-TYPE
          SYNTAX      INTEGER {
                         telnet (1),
                         rlogin (2),
                         cleartcp (3),
                         ping (4)
                         }
          MAX-ACCESS  read-write
          STATUS      current
          DESCRIPTION "The Service type that the dial-in user will 
                       be connected to."
        --CONFIGURABLE
     ::= {usrCipPortParamEntry 5}
     usrCipPortTcpPortNumber OBJECT-TYPE
          SYNTAX      Integer32
          MAX-ACCESS  read-write
          STATUS      current
          DESCRIPTION "The tcp port number associated with the service type."
        --CONFIGURABLE
     ::= {usrCipPortParamEntry 6}
     usrCipPortLoginMsg OBJECT-TYPE
          SYNTAX      OCTET STRING (SIZE(0..800))
          MAX-ACCESS  read-write
          STATUS      current
          DESCRIPTION "The salutation message associated with a specific port."
        --CONFIGURABLE
     ::= {usrCipPortParamEntry 7}
     usrCipPortLoginPrompt OBJECT-TYPE
   	  SYNTAX      OCTET STRING (SIZE(0..64))
   	  MAX-ACCESS  read-write
   	  STATUS      current
   	  DESCRIPTION "The login prompt associated with a specific port."
        --CONFIGURABLE
     ::= {usrCipPortParamEntry 8}
     usrCipPortIpAddress OBJECT-TYPE
   	  SYNTAX      IpAddress
   	  MAX-ACCESS  read-write
   	  STATUS      current
	  DESCRIPTION "The IP address for a specific serial port."
        --CONFIGURABLE
      ::= {usrCipPortParamEntry 9}
     usrCipPortHostIpAddress OBJECT-TYPE
   	  SYNTAX      IpAddress
   	  MAX-ACCESS  read-write
   	  STATUS      current
	  DESCRIPTION "A host IP address specified for this interface."
        --CONFIGURABLE
   	::= {usrCipPortParamEntry 10}
     usrCipPortNetMask OBJECT-TYPE
   	  SYNTAX      Integer32
   	  MAX-ACCESS  read-write
   	  STATUS      current
   	  DESCRIPTION "The netmask associated with a specific 
                       serial interface."
        --CONFIGURABLE
     ::= {usrCipPortParamEntry 11}
     usrCipPortProtocol OBJECT-TYPE
   	  SYNTAX      INTEGER {
                         ppp (1),
                         slip (2),
                         arap (3)
                    	   }
   	  MAX-ACCESS  read-write
   	  STATUS      current
   	  DESCRIPTION "The protocol type configured for a specific interface."
        --CONFIGURABLE
     ::= {usrCipPortParamEntry 12}
     usrCipPortMtu OBJECT-TYPE
   	  SYNTAX      Integer32
   	  MAX-ACCESS  read-write
   	  STATUS      current
   	  DESCRIPTION "The mtu value associated with a specific interface."
        --CONFIGURABLE
     ::= {usrCipPortParamEntry 13}
     usrCipPortIdleTimeOut OBJECT-TYPE
   	  SYNTAX      Integer32
   	  MAX-ACCESS  read-write
   	  STATUS      current
   	  DESCRIPTION "The maximum idle time specified for an interface."
        --CONFIGURABLE
     ::= {usrCipPortParamEntry 14}
     usrCipPortState OBJECT-TYPE
          SYNTAX        INTEGER {
                          port-disabled (0),
                          port-initializing(1),
                          port-available(2),
                          port-connecting(3),
                          port-connected(4),
                          port-disconnecting(5),
                          port-disconnected(6)
                           }
          MAX-ACCESS    read-only
          STATUS        current
          DESCRIPTION  "The state of the serial line."
     ::= {usrCipPortParamEntry 15}
     usrCipPortNumConns OBJECT-TYPE
   	  SYNTAX      Counter32
   	  MAX-ACCESS  read-only
   	  STATUS      current
   	  DESCRIPTION "The total number of connections made on this if."
     ::= {usrCipPortParamEntry 16}
     usrCipPortConnType OBJECT-TYPE
          SYNTAX        INTEGER {
                          undefined-conn(0),
                          on-demand-conn(1),
                          dial-back-conn(2),
                          continuous-conn(3),
                          manual-conn(4),
                          timed-conn(5),
                          shared-modem-conn(6),
                          dial-in-conn(7),
                          bond-conn(8),
                          dedicated-conn (9)
                           }
          MAX-ACCESS    read-only
          STATUS        current
          DESCRIPTION  "The connection type on this interface."
     ::= {usrCipPortParamEntry 17}
     usrCipUserName OBJECT-TYPE
          SYNTAX      OCTET STRING (SIZE(0..32))
   	  MAX-ACCESS  read-only
   	  STATUS      current
   	  DESCRIPTION "The name user connected to this interface. "
     ::= {usrCipPortParamEntry 18}
     usrCipConnStartTime OBJECT-TYPE
          SYNTAX      Integer32
          MAX-ACCESS  read-only
          STATUS      current
          DESCRIPTION "The start time of a connection specified 
                       on an interface."
     ::= {usrCipPortParamEntry 19}
     usrCipDataLinkConn OBJECT-TYPE
          SYNTAX        INTEGER {
                           undefined(0),
                           telnet (1),
                           rlogin (2),
                           clear-tcp (3),
                           ppp (4),
                           arap (5),
                           slip (6),
                           admin(7),
                           ping(8),
                           none(9),
                           lt2p(10),
                           pptp(11),
                           tap(12),
                           cliNas(13),
                           shell(14),
                           pingIp (15),
                           vtp (16),
                           sipRpt7111a (17),    -- wireline only
                           sipRpt7111m (18),    -- wireline only
                           sipRpt729 (19)       -- wireline only
                           }
          MAX-ACCESS    read-only
          STATUS        current
          DESCRIPTION  "The data link layer that a specific dial-in session is
                        connected to."
     ::= {usrCipPortParamEntry 20}
     usrCipInitScriptName OBJECT-TYPE
          SYNTAX      DisplayString  (SIZE(0..7))
          MAX-ACCESS  read-write
          STATUS      current
          DESCRIPTION "The name of the script"
        --CONFIGURABLE
     ::= { usrCipPortParamEntry 21 }
     usrCipIfConnType OBJECT-TYPE
          SYNTAX      INTEGER {
                        if-direct-conn (1),
                        if-direct-network-conn (2),
                        if-normal-conn (3),
                        if-prompt-passwd (4),
                        if-prompt-none (5),
						if-ppp-only(6)
                        }
          MAX-ACCESS  read-write
          STATUS      current
          DESCRIPTION "The type of the connection that i/f is configured for."
        --CONFIGURABLE
     ::= { usrCipPortParamEntry 22 }
     usrCipPromptUserName OBJECT-TYPE
          SYNTAX        OCTET STRING (SIZE(0..32))
          MAX-ACCESS    read-write
          STATUS        current
          DESCRIPTION   "This could only be set if the port is
                        configured not to prompt for username."
     --CONFIGURABLE
     ::= {usrCipPortParamEntry 23}
     usrCipUserPasswd OBJECT-TYPE
          SYNTAX      OCTET STRING (SIZE(0..15))
   	  MAX-ACCESS  read-write
   	  STATUS      current
   	  DESCRIPTION "This could only be set if the port is 
                       configured to not prompt for password."
        --CONFIGURABLE
     ::= { usrCipPortParamEntry 24 }
     usrCipPortIfName OBJECT-TYPE
          SYNTAX      OCTET STRING (SIZE(0..32))
   	  MAX-ACCESS  read-only
   	  STATUS      current
   	  DESCRIPTION "The name of the serial line interface."
     ::= { usrCipPortParamEntry 25 }
     usrCipPortDialPrefix OBJECT-TYPE
         SYNTAX         OCTET STRING (SIZE(0..64))
         MAX-ACCESS     read-write
         STATUS         current
         DESCRIPTION    "This string defines the prefix to the phone number."
       --CONFIGURABLE
    ::= {usrCipPortParamEntry 26}
    usrCipPortCfgScript OBJECT-TYPE
         SYNTAX         DisplayString (SIZE(0..32))
         MAX-ACCESS     read-write
         STATUS         current
         DESCRIPTION    "This string defines an I-modem or V.34 AT command
            			 a value of RESET will cause the modem to be reset 
                         and reinitialized with the string found in 
                         usrInitScriptCommands.
                         A value of zero indicates no command exists. It
                         cannot be SET to NULL."
    ::= { usrCipPortParamEntry 27 }
    usrCipPortCfgScriptResult OBJECT-TYPE
         SYNTAX         UsrLongString (SIZE(0..1350))
         MAX-ACCESS     read-only
         STATUS         current
         DESCRIPTION    "This string defines the result of the AT command.
                         NVT ASCII characters."
    ::= { usrCipPortParamEntry 28 }
    usrCipPortPromptingStyle OBJECT-TYPE
         SYNTAX        INTEGER {
                           local-prompting(1),
                           remote-prompting(2)
                       }                                                  
         MAX-ACCESS    read-write
         STATUS        current 
         DESCRIPTION   "This value specifies whether the NAS will provide
                       username and password prompting locally or if the  
                       prompting will be handled by a remote security server."
       --CONFIGURABLE 
    ::= { usrCipPortParamEntry 29 }
    usrCipPortLoginProcessing OBJECT-TYPE
        SYNTAX INTEGER {
                       disable-auth-for-none (1),
                       disable-auth-for-async-ppp (2),
                       disable-auth-for-sync-ppp (3),
                       disable-auth-for-ppp (4)
                       }
        MAX-ACCESS read-write
        STATUS current
        DESCRIPTION
            "This variable controls login processing.  This value can be set
             for controlling user authentication for different types of 
	     autodetected PPP calls. Default is authentication is done for 
	     all types of PPP calls.."
        --CONFIGURABLE
        ::= {usrCipPortParamEntry 30}
     usrCipPortDomainName OBJECT-TYPE
          SYNTAX      OCTET STRING (SIZE(0..240))
          MAX-ACCESS  read-write
          STATUS      current
          DESCRIPTION "The Domain Name associated with this port "
       --CONFIGURABLE
     ::= { usrCipPortParamEntry 31 }
     usrCipPortDelimiter  OBJECT-TYPE
          SYNTAX  OCTET STRING    (SIZE (0..1))
          MAX-ACCESS  read-write
          STATUS  current
          DESCRIPTION      
              "The delimiter string port domain configuration"
          --CONFIGURABLE   
          ::= { usrCipPortParamEntry 32 } 
usrCipPortCallType OBJECT-TYPE
        SYNTAX INTEGER {
                       call-type-pptp(1),
                       call-type-l2tp(2),
                       call-type-none(3)
                       }
        MAX-ACCESS read-write
        STATUS current
        DESCRIPTION
            "This variable call type associated with the interface."
        --CONFIGURABLE
        ::= {usrCipPortParamEntry 33}
	usrCipPortDNISAuthentication  OBJECT-TYPE
         SYNTAX INTEGER 
		 {
                 dnis-auth-disabled (1),
                 dnis-auth-preferred (2),
                 dnis-auth-required (3)
                 }
         MAX-ACCESS  read-write
         STATUS  current
         DESCRIPTION
             "DNIS Authentication type"
         --CONFIGURABLE
         ::= { usrCipPortParamEntry 34 }
	usrCipPortDNISAuthTime  OBJECT-TYPE
         SYNTAX INTEGER 
                         {
                         before-answer (1),
                         after-answer (2)
                         }
         MAX-ACCESS  read-write
         STATUS  current
         DESCRIPTION
             "DNIS Authentication Time"
         --CONFIGURABLE
         ::= { usrCipPortParamEntry 35 }
	usrCipPortDNISAuthType  OBJECT-TYPE
         SYNTAX INTEGER 
		 {
                 dnis (1),
                 ani (2)
                 }
         MAX-ACCESS  read-write
         STATUS  current
         DESCRIPTION
             "DNIS Authentication type"
         --CONFIGURABLE
         ::= { usrCipPortParamEntry 36 }
     usrCipPortDNISPassword OBJECT-TYPE
          SYNTAX      OCTET STRING (SIZE(0..15))
   	  MAX-ACCESS  read-write
   	  STATUS      current
   	  DESCRIPTION "The DNIS  password."
        --CONFIGURABLE
     ::= { usrCipPortParamEntry 37 }
     usrCipPortDNISTimeout OBJECT-TYPE
          SYNTAX      Integer32
          MAX-ACCESS  read-write
          STATUS      current
          DESCRIPTION "Timeout if no auth within this time"
        --CONFIGURABLE
     ::= {usrCipPortParamEntry 38}
    usrCipPortParity  OBJECT-TYPE
         SYNTAX INTEGER   
         {
             no-parity-eight-bit (1),
             even-seven-bit (2),
             odd-seven-bit (3),
             no-parity-seven-bit (4)
         }
         MAX-ACCESS  read-write      
         STATUS  current     
         DESCRIPTION
             "Port Parity"
         --CONFIGURABLE
         ::= { usrCipPortParamEntry 39 }
    usrCipPromptDelay  OBJECT-TYPE
         SYNTAX Integer32 (0..100)
         MAX-ACCESS  read-write
         STATUS  current
         DESCRIPTION
             "If user does not enter any key after banner mesg, authenticate
              user based on interface user name after this delay"
         --CONFIGURABLE
         ::= { usrCipPortParamEntry 40 }
    usrCipPromptTimeout  OBJECT-TYPE
         SYNTAX Integer32 (5..600)
         MAX-ACCESS  read-write
         STATUS  current
         DESCRIPTION
             " This is the maximum timeout while prompting for 
		username password. If nothing is typed, the session will
		be terminated. Default is 300 secs"
         --CONFIGURABLE
         ::= { usrCipPortParamEntry 41 }
    usrCipSpecialXonXoffFlow  OBJECT-TYPE
         SYNTAX INTEGER   
         {
             disabled (0),
             enabled (1)
         }
         MAX-ACCESS  read-write      
         STATUS  current     
         DESCRIPTION
             "Special Xon Xoff flow control in modem control receive side"
         --CONFIGURABLE
         ::= { usrCipPortParamEntry 42 }
	 usrCipCallingPhoneNumber OBJECT-TYPE
      SYNTAX      OCTET STRING (SIZE(0..64))
   	  MAX-ACCESS  read-only
   	  STATUS      current
   	  DESCRIPTION "Calling phone number"
     ::= { usrCipPortParamEntry 43 }
	 usrCipCalledPhoneNumber OBJECT-TYPE
      SYNTAX      OCTET STRING (SIZE(0..64))
   	  MAX-ACCESS  read-only
   	  STATUS      current
   	  DESCRIPTION "Called phone number"
     ::= { usrCipPortParamEntry 44 }
	usrCipPortGlobalConnId OBJECT-TYPE
      SYNTAX      Integer32
      MAX-ACCESS  read-only
      STATUS      current
      DESCRIPTION "Global Connection Id"
     ::= { usrCipPortParamEntry 45 }
	 usrCipPortUseDnisPool OBJECT-TYPE
         SYNTAX INTEGER 
		 {
             dnis-pool-disabled (1),
             dnis-pool-preferred (2),
             dnis-pool-required (3)
         }
         MAX-ACCESS  read-write
         STATUS  current
         DESCRIPTION
             "User DNIS pool"
         --CONFIGURABLE
     ::= { usrCipPortParamEntry 46 }
     usrCipPortLoginTable OBJECT-TYPE
         SYNTAX OCTET STRING (SIZE(0..32))
         MAX-ACCESS  read-write
         STATUS  current
         DESCRIPTION
             "Login Host Table "
         --CONFIGURABLE 
     ::= { usrCipPortParamEntry 47 }
     usrCipPortMobileType OBJECT-TYPE
          SYNTAX        INTEGER {
                          undefined-conn(0),
                          mobile-ip(1),
                          simple-ip(2)
                           }
          MAX-ACCESS    read-only
          STATUS        current
          DESCRIPTION  "The Mobile Node connected"
     ::= {usrCipPortParamEntry 48}
-- Modem Group Table 
      usrCipModemGroupTable OBJECT-TYPE
         SYNTAX  SEQUENCE OF USRCIPModemGroupEntry 
         MAX-ACCESS  not-accessible
         STATUS  current
         DESCRIPTION
            "This table contains the serial port parameters."
      ::= { usrCip 2 }
     usrCipModemGroupEntry OBJECT-TYPE
        SYNTAX      USRCIPModemGroupEntry
        MAX-ACCESS  not-accessible
        STATUS      current
        DESCRIPTION "Each entry corresponds to a serial interface.
                     All objects required for row creation."
        INDEX   {
                usrCipModemGroupName
               }
     ::= {usrCipModemGroupTable 1}
     USRCIPModemGroupEntry ::= 
          SEQUENCE {
               usrCipModemGroupName
                    DisplayString,
               usrCipModemGroupStatus
                    INTEGER,
               usrCipModemGroupCount
                    Integer32
          }
     usrCipModemGroupName OBJECT-TYPE
          SYNTAX        DisplayString (SIZE (0..32))
          MAX-ACCESS    not-accessible
          STATUS        current
          DESCRIPTION   "The identifier of a modem group."
     ::= { usrCipModemGroupEntry 1 }
     usrCipModemGroupStatus  OBJECT-TYPE
        SYNTAX          INTEGER {
                                add(0),
                                delete(1)
                                }
        MAX-ACCESS     	read-write
        STATUS          current
        DESCRIPTION     "The status could be add or delete the group member
                         specified in the usrCipGroupMembers MIB."
      --CONFIGURABLE
    ::= { usrCipModemGroupEntry 2 }
     usrCipModemGroupCount OBJECT-TYPE
          SYNTAX      Integer32
          MAX-ACCESS  read-only
          STATUS      current
          DESCRIPTION "The number of modem ports in a specific group."
     ::= { usrCipModemGroupEntry 3 }
-- The Global Host Table
      usrCipGlblHostTable OBJECT-TYPE
         SYNTAX  SEQUENCE OF USRCIPGlblHostEntry
         MAX-ACCESS  not-accessible
         STATUS  current
         DESCRIPTION
            "This table contains the global host addresses."
      ::= { usrCip 3 }
     usrCipGlblHostEntry OBJECT-TYPE
        SYNTAX      USRCIPGlblHostEntry
        MAX-ACCESS  not-accessible
        STATUS      current
        DESCRIPTION "Each entry contains a host address with tcp port numbers."
        INDEX   {
                usrCipGlblHostIndex
                }
     ::= {usrCipGlblHostTable 1}
     USRCIPGlblHostEntry ::= 
         SEQUENCE {
               usrCipGlblHostIndex
                    Integer32,
               usrCipGlblHostAddress
                    IpAddress,
               usrCipGlblHostRloginPort
                    Integer32,
               usrCipGlblHostTelnetPort
                    Integer32,
               usrCipGlblHostTcpClearPort
                    Integer32,
               usrCipGlblHostName
                    OCTET STRING,
               usrCipGlblHostState 
                    INTEGER
          }
     usrCipGlblHostIndex OBJECT-TYPE
          SYNTAX      Integer32
          MAX-ACCESS  read-write
          STATUS      current
          DESCRIPTION "The identifier of a default host table."
     ::= { usrCipGlblHostEntry 1 }
     usrCipGlblHostAddress OBJECT-TYPE
        SYNTAX  IpAddress
        MAX-ACCESS  read-write
        STATUS  current
        DESCRIPTION     
                "The global host IP address."
        --CONFIGURABLE                
     ::= { usrCipGlblHostEntry 2 }
     usrCipGlblHostRloginPort   OBJECT-TYPE
        SYNTAX  Integer32
        MAX-ACCESS  read-write
        STATUS  current
        DESCRIPTION
                "The host rlogin tcp port number."
        --CONFIGURABLE        
     ::= { usrCipGlblHostEntry 3 }        
     usrCipGlblHostTelnetPort   OBJECT-TYPE
        SYNTAX  Integer32
        MAX-ACCESS  read-write
        STATUS  current
        DESCRIPTION
                "The host telnet port number."
        --CONFIGURABLE
     ::= { usrCipGlblHostEntry 4 }
     usrCipGlblHostTcpClearPort OBJECT-TYPE
        SYNTAX  Integer32
        MAX-ACCESS  read-write
        STATUS  current
        DESCRIPTION     
                "The host tcp clear port number."
        --CONFIGURABLE
     ::= { usrCipGlblHostEntry 5 }
     usrCipGlblHostName OBJECT-TYPE
        SYNTAX  OCTET STRING (SIZE(0..32))
        MAX-ACCESS  read-write
        STATUS  current
        DESCRIPTION
                "The global host name."
        --CONFIGURABLE
     ::= { usrCipGlblHostEntry 6 }
     usrCipGlblHostState OBJECT-TYPE
        SYNTAX  INTEGER {
                        host-undefined (0),
                        host-valid (1),
                        host-invalid (2),
                        host-pending (3)
                        }
        MAX-ACCESS  read-write
        STATUS  current
        DESCRIPTION     
                "The state of a default host entry."
     ::= { usrCipGlblHostEntry 7 }
-- The Global Parameters
     usrCipGlblHostSelectionMethod      OBJECT-TYPE
        SYNTAX  INTEGER {
                        round-robin(0),
                        random(1)
                        }
        MAX-ACCESS  read-write
        STATUS  current
        DESCRIPTION
                "The method that will be used to select the 
                 default host."
        --CONFIGURABLE
        ::= {usrCip 4}	     
     usrCipGlblHostType OBJECT-TYPE
        SYNTAX  INTEGER {
                        undefined-host(0),
                        default-host(1),
                        prompt(2)
                        }
        MAX-ACCESS  read-write
        STATUS  current
        DESCRIPTION
            "The default host type."
        --CONFIGURABLE
        ::= { usrCip 5 }
     usrCipGlblLoginMsg OBJECT-TYPE
        SYNTAX  OCTET STRING (SIZE(0..255))
        MAX-ACCESS  read-write
        STATUS  current
        DESCRIPTION
                "The user login message"
        --CONFIGURABLE
        ::= { usrCip 6 }
     usrCipGlblUsrCommandPrompt OBJECT-TYPE
        SYNTAX  OCTET STRING (SIZE(0..64))
        MAX-ACCESS  read-write
        STATUS  current
        DESCRIPTION
                "The user command prompt."
        --CONFIGURABLE
        ::= { usrCip 7 }
      usrCipGlblLogNetUserPrompt OBJECT-TYPE
        SYNTAX  OCTET STRING (SIZE(0..64))
        MAX-ACCESS  read-write
        STATUS  current
        DESCRIPTION
                "The login/network command prompt."
        --CONFIGURABLE
        ::= { usrCip 8 }
     usrCipGlblMgPrompt OBJECT-TYPE
        SYNTAX  OCTET STRING (SIZE(0..64))
        MAX-ACCESS  read-write
        STATUS  current
        DESCRIPTION
                "The manage prompt."
        --CONFIGURABLE
        ::= { usrCip 9 }
     usrCipGlblUserName OBJECT-TYPE
        SYNTAX  OCTET STRING (SIZE(0..32))
        MAX-ACCESS  read-write
        STATUS  current
        DESCRIPTION
                "The default user name used in case the dial-in users don't
                 get prompted for the user name and no user name is configured
                 for the i/f."
        --CONFIGURABLE
        ::= { usrCip 10 }
     usrCipGlblNumCalls OBJECT-TYPE
        SYNTAX  Counter32
        MAX-ACCESS  read-only
        STATUS  current
        DESCRIPTION
                "The total number of calls received since the boot up time."
        ::= { usrCip 11 }
     usrCipAllowManageOnDialups OBJECT-TYPE
        SYNTAX  INTEGER {
                        manage-off(0),
                        manage-on (1)
                        }
        MAX-ACCESS  read-write
        STATUS  current
        DESCRIPTION
                "This variable turns on/off the ability to manage the system
                 through the dialup ports."
        --CONFIGURABLE
        ::= { usrCip 12 }
     usrCipHangUp OBJECT-TYPE
        SYNTAX  Integer32
        MAX-ACCESS  read-write
        STATUS  current
        DESCRIPTION
                "This variable is set only if a hangup message is sent out.
                 The value of this variable is the interface index."
        ::= {usrCip 13 }
     usrCipDialOut OBJECT-TYPE
        SYNTAX  OCTET STRING (SIZE(0..32))
        MAX-ACCESS  read-write
        STATUS  current
        DESCRIPTION
                "This variable is set through the CLI when the user
                 manually issues a dial-out."
        ::= { usrCip 14 }
     usrCipBusyOut   OBJECT-TYPE
        SYNTAX  Integer32
        MAX-ACCESS  read-write
        STATUS  current
        DESCRIPTION     
                "This variable is set only in case the user wants to 
                take the phone off hook."
        ::= {usrCip 15}
     usrInitScriptTable OBJECT-TYPE
         SYNTAX  SEQUENCE OF USRInitScriptEntry
         MAX-ACCESS  not-accessible
         STATUS  current
         DESCRIPTION
            "This table contains the global host addresses."
      ::= { usrCip 16}
     usrInitScriptEntry OBJECT-TYPE
        SYNTAX      USRInitScriptEntry
        MAX-ACCESS  not-accessible
        STATUS      current
        DESCRIPTION "Each entry contains a host address with tcp port numbers."
        INDEX   {
                usrInitScriptName
                }
     ::= {usrInitScriptTable 1}
     USRInitScriptEntry ::= 
         SEQUENCE {
               usrInitScriptName
                    DisplayString,
               usrInitScriptCommands
                    DisplayString,
	       usrInitScriptStatus
		    INTEGER
                }
     usrInitScriptName OBJECT-TYPE
          SYNTAX      DisplayString  (SIZE(0..7))
          MAX-ACCESS  not-accessible
          STATUS      current
          DESCRIPTION "The name of the script"
     ::= { usrInitScriptEntry 1 }
     usrInitScriptCommands OBJECT-TYPE
          SYNTAX        DisplayString (SIZE(0..56))
          MAX-ACCESS    read-write
          STATUS        current
          DESCRIPTION   "The AT commands that will be sent to the serial line
                         driver every time a connection goes away."
        --CONFIGURABLE
     ::= { usrInitScriptEntry 2 }
     usrInitScriptStatus  OBJECT-TYPE
        SYNTAX          INTEGER {
                                normal-status(0),
                                delete-script(1)
                                }
        MAX-ACCESS     	read-write
        STATUS          current
        DESCRIPTION     "This variable is used to delete a script from the init
                         script list."
    ::= { usrInitScriptEntry 3 }
-- MIB Variables defined for CFM purposes
     usrCipCfmPortIndexTable OBJECT-TYPE
         SYNTAX  SEQUENCE OF USRCIPCfmPortIndexEntry
         MAX-ACCESS  not-accessible
         STATUS  current
         DESCRIPTION
            "This table contains CIP port indices. It is defined 
             so that CFM process would be able to save a specific
             row of portal table."
	::= { usrCip 17 }
     usrCipCfmPortIndexEntry OBJECT-TYPE
        SYNTAX      USRCIPCfmPortIndexEntry
        MAX-ACCESS  not-accessible
        STATUS      current
        DESCRIPTION "Each entry corresponds to a serial interface."
        INDEX   {
                usrCipCfmPortIndex
               }
     ::= {usrCipCfmPortIndexTable 1}
     USRCIPCfmPortIndexEntry ::= 
          SEQUENCE {
               usrCipCfmPortIndex
                    Integer32,
               usrCipCfmPortFlag
                    Integer32
                }
     usrCipCfmPortIndex OBJECT-TYPE
          SYNTAX      Integer32
          MAX-ACCESS  read-only
          STATUS      current
          DESCRIPTION "The identifier of the physical interface."
     ::= {usrCipCfmPortIndexEntry 1}
     usrCipCfmPortFlag OBJECT-TYPE
          SYNTAX       Integer32
          MAX-ACCESS   read-write
          STATUS       current
          DESCRIPTION   "The flag that triggers a cfm operation on each
                         interface."
     ::= {usrCipCfmPortIndexEntry 2 }
-- Scalar Flags
    usrCipCfmAllPortsFlag  OBJECT-TYPE
         SYNTAX         Integer32
         MAX-ACCESS     read-write
         STATUS         current
         DESCRIPTION    "This flag triggers a CFM action."
    ::= { usrCip 18 }
    usrCipCfmModemGroupFlag OBJECT-TYPE
        SYNTAX          Integer32
        MAX-ACCESS      read-write
        STATUS          current
        DESCRIPTION     "This flag triggers a save of modem group table."
    ::= { usrCip 19 }
    usrCipCfmGlblHostTableFlag OBJECT-TYPE
        SYNTAX          Integer32
        MAX-ACCESS      read-write
        STATUS          current
        DESCRIPTION     "This flag triggers a save of global host table."
    ::= { usrCip 20 }        
    usrCipCfmInitScriptFlag OBJECT-TYPE
        SYNTAX          Integer32
        MAX-ACCESS      read-write
        STATUS          current
        DESCRIPTION     "This flag triggers a save of init script table."
    ::= { usrCip 21 }
    usrCipCfmGlblVarFlag OBJECT-TYPE
        SYNTAX          Integer32
        MAX-ACCESS      read-write
        STATUS          current
        DESCRIPTION     "This flag triggers a save of global variables."
    ::= { usrCip 22 }
   usrCipCfmSaveAllFlag OBJECT-TYPE
        SYNTAX          Integer32
        MAX-ACCESS      read-write
        STATUS          current
        DESCRIPTION     "This flag triggers a save for all of CIP tables."
    ::= { usrCip 23 }
-- Port Parameters Grouped in a Modem Group 
    usrCipModemPortParamTable OBJECT-TYPE
         SYNTAX  SEQUENCE OF USRCIPModemPortParamEntry
         MAX-ACCESS  not-accessible
         STATUS  current
         DESCRIPTION
            "This table contains the serial port parameters."
	::= { usrCip 24 }
    usrCipModemPortParamEntry OBJECT-TYPE
        SYNTAX      USRCIPModemPortParamEntry
        MAX-ACCESS  not-accessible
        STATUS      current
        DESCRIPTION "Each entry corresponds to a serial interface."
        INDEX   {
                usrCipModemPortName
               }
     ::= {usrCipModemPortParamTable 1}
     USRCIPModemPortParamEntry ::= 
          SEQUENCE {
               usrCipModemPortName
                    OCTET STRING,
               usrCipModemPortType
                    INTEGER,
               usrCipModemPortAccess
                    INTEGER,
               usrCipModemPortHostType
                    INTEGER,
               usrCipModemPortLoginService
                    INTEGER,
               usrCipModemPortTcpPortNumber
                    Integer32,
               usrCipModemPortLoginMsg
                    OCTET STRING,
               usrCipModemPortLoginPrompt
                    OCTET STRING,
               usrCipModemPortIpAddress
                    IpAddress,
               usrCipModemPortHostIpAddress
                    IpAddress,
               usrCipModemPortNetMask
                    Integer32,
               usrCipModemPortProtocol
                    INTEGER,
               usrCipModemPortMtu
                    Integer32,
               usrCipModemPortIdleTimeOut
                    Integer32,
               usrCipModemInitScriptName
                    DisplayString,
               usrCipModemIfConnType
                    INTEGER,
               usrCipModemPromptUserName
                    OCTET STRING,
               usrCipModemUserPasswd
                    OCTET STRING,
               usrCipModemDialPrefix
                    OCTET STRING,
               usrCipModemPortPromptingStyle
                    INTEGER,
               usrCipModemPortLoginProcessing
                    INTEGER,
               usrCipModemPortDNISAuthentication
                   INTEGER,
               usrCipModemPortDNISAuthTime
                   INTEGER,
               usrCipModemPortDNISAuthType 
                   INTEGER,
               usrCipModemPortDNISPassword
                   OCTET STRING,
               usrCipModemPortDNISTimeout
                   Integer32,
              usrCipModemPortParity
                    INTEGER,
              usrCipModemPromptDelay
                   Integer32,
	      usrCipModemPromptTimeout
		   Integer32,
  	      usrCipModemSpecialXonXoffFlow 
		   INTEGER,
  	      usrCipModemUseDnisPool 
		   INTEGER,
	      usrCipModemLoginTable
		   OCTET STRING
               }
     usrCipModemPortName OBJECT-TYPE
          SYNTAX        OCTET STRING (SIZE (0..32))
          MAX-ACCESS    not-accessible
          STATUS        current
          DESCRIPTION   "The identifier of a modem group."
     ::= {usrCipModemPortParamEntry 1}
     usrCipModemPortType OBJECT-TYPE
          SYNTAX      INTEGER {
                         login (1),
                         network (2),
                         login-network (3)
                         }
          MAX-ACCESS  read-write
          STATUS      current
          DESCRIPTION "The type of the physical port."
     ::= {usrCipModemPortParamEntry 2}
     usrCipModemPortAccess OBJECT-TYPE
          SYNTAX      INTEGER {
                         dial-in(1),
                         dial-out(2),
                         two-way(3)
                       }
          MAX-ACCESS  read-write
          STATUS      current
          DESCRIPTION "This field specifies the direction of the calls
                         that could be made on a specific interface. 
                         Ports could be configured to be dial-in, dial-out
                         or two-way ports."
     ::= {usrCipModemPortParamEntry 3}
     usrCipModemPortHostType OBJECT-TYPE
          SYNTAX      INTEGER {
                         default (1),
                         prompt (2),
                         specified (3)
                         }
          MAX-ACCESS  read-write
          STATUS      current
          DESCRIPTION "The host type that the dial-in user 
                       will be connected to."
     ::= {usrCipModemPortParamEntry 4}
     usrCipModemPortLoginService OBJECT-TYPE
          SYNTAX      INTEGER {
                         telnet (1),
                         rlogin (2),
                         netdata (3)
                         }
          MAX-ACCESS  read-write
          STATUS      current
          DESCRIPTION "The Service type that the dial-in user will 
                       be connected to."
     ::= {usrCipModemPortParamEntry 5}
     usrCipModemPortTcpPortNumber OBJECT-TYPE
          SYNTAX      Integer32
          MAX-ACCESS  read-write
          STATUS      current
          DESCRIPTION "The tcp port number associated with the service type."
     ::= {usrCipModemPortParamEntry 6}
     usrCipModemPortLoginMsg OBJECT-TYPE
          SYNTAX      OCTET STRING (SIZE(0..255))
          MAX-ACCESS  read-write
          STATUS      current
          DESCRIPTION "The salutation message associated with a specific port."
     ::= {usrCipModemPortParamEntry 7}
     usrCipModemPortLoginPrompt OBJECT-TYPE
   	  SYNTAX      OCTET STRING (SIZE(0..64))
   	  MAX-ACCESS  read-write
   	  STATUS      current
   	  DESCRIPTION "The login prompt associated with a specific port."
     ::= {usrCipModemPortParamEntry 8}
     usrCipModemPortIpAddress OBJECT-TYPE
   	  SYNTAX      IpAddress
   	  MAX-ACCESS  read-write
   	  STATUS      current
	  DESCRIPTION "The IP address for a specific serial port."
      ::= {usrCipModemPortParamEntry 9}
     usrCipModemPortHostIpAddress OBJECT-TYPE
   	  SYNTAX      IpAddress
   	  MAX-ACCESS  read-write
   	  STATUS      current
	  DESCRIPTION "A host IP address specified for this interface."
   	::= {usrCipModemPortParamEntry 10}
     usrCipModemPortNetMask OBJECT-TYPE
   	  SYNTAX      Integer32
   	  MAX-ACCESS  read-write
   	  STATUS      current
   	  DESCRIPTION "The netmask associated with a specific 
                       serial interface."
     ::= {usrCipModemPortParamEntry 11}
     usrCipModemPortProtocol OBJECT-TYPE
   	  SYNTAX      INTEGER {
                         ppp (1),
                         slip (2),
                         arap (3)
                    	   }
   	  MAX-ACCESS  read-write
   	  STATUS      current
   	  DESCRIPTION "The protocol type configured for a specific interface."
     ::= {usrCipModemPortParamEntry 12}
     usrCipModemPortMtu OBJECT-TYPE
   	  SYNTAX      Integer32
   	  MAX-ACCESS  read-write
   	  STATUS      current
   	  DESCRIPTION "The mtu value associated with a specific interface."
     ::= {usrCipModemPortParamEntry 13}
     usrCipModemPortIdleTimeOut OBJECT-TYPE
   	  SYNTAX      Integer32
   	  MAX-ACCESS  read-write
   	  STATUS      current
   	  DESCRIPTION "The maximum idle time specified for an interface."
     ::= {usrCipModemPortParamEntry 14}
     usrCipModemInitScriptName OBJECT-TYPE
          SYNTAX      DisplayString  (SIZE(0..7))
          MAX-ACCESS  read-write
          STATUS      current
          DESCRIPTION "The name of the script"
     ::= { usrCipModemPortParamEntry 15 }
     usrCipModemIfConnType OBJECT-TYPE
          SYNTAX      INTEGER {
                        if-direct-conn (1),
                        if-direct-network-conn (2),
                        if-normal-conn (3),
                        if-prompt-passwd (4),
                        if-prompt-none (5),
						if-ppp-only(6)
                        }
          MAX-ACCESS  read-write
          STATUS      current
          DESCRIPTION "The type of the connection that i/f is configured for."
     ::= { usrCipModemPortParamEntry 16 }
     usrCipModemPromptUserName OBJECT-TYPE
          SYNTAX        OCTET STRING (SIZE(0..32))
          MAX-ACCESS    read-write
          STATUS        current
          DESCRIPTION   "This could only be set if the port is
                        configured not to prompt for username."
     ::= { usrCipModemPortParamEntry 17 }
     usrCipModemUserPasswd OBJECT-TYPE
          SYNTAX      OCTET STRING (SIZE(0..15))
   	  MAX-ACCESS  read-write
   	  STATUS      current
   	  DESCRIPTION "This could only be set if the port is 
                       configured to not prompt for password."
     ::= { usrCipModemPortParamEntry 18 }
     usrCipModemDialPrefix OBJECT-TYPE
         SYNTAX         OCTET STRING (SIZE(0..64))
         MAX-ACCESS     read-write
         STATUS         current
         DESCRIPTION    "This string defines the prefix to the phone number."
    ::= { usrCipModemPortParamEntry 19 }
    usrCipModemPortPromptingStyle OBJECT-TYPE
         SYNTAX        INTEGER {
                           local-prompting(1),
                           remote-prompting(2)
                       }
         MAX-ACCESS    read-write
         STATUS        current
         DESCRIPTION   "This value specifies whether the NAS will provide
                       username and password prompting locally or if the
                       prompting will be handled by a remote security server."
       --CONFIGURABLE
    ::= { usrCipModemPortParamEntry 20 }
    usrCipModemPortLoginProcessing OBJECT-TYPE
        SYNTAX INTEGER {
                       enable (1),
                       disable (2)
                       }
        MAX-ACCESS read-write
        STATUS current
        DESCRIPTION
            "This variable controls login processing.  Setting the value to disable
             will cause the box to not prompt a user for login name or password.  Enabling
             this value will cause the box to perform normal login name and password prompting."
        --CONFIGURABLE
        ::= {usrCipModemPortParamEntry 21}
    usrCipModemPortDNISAuthentication  OBJECT-TYPE
         SYNTAX INTEGER    
         {     
             dnis-auth-disabled (1),
             dnis-auth-preferred (2), 
             dnis-auth-required (3)
         }      
         MAX-ACCESS  read-write
         STATUS  current       
         DESCRIPTION  
             "DNIS Authentication type"
         --CONFIGURABLE
         ::= { usrCipModemPortParamEntry 22 }
    usrCipModemPortDNISAuthTime  OBJECT-TYPE
         SYNTAX INTEGER
         {
             before-answer (1),
             after-answer (2)
         }
         MAX-ACCESS read-write
         STATUS  current
         DESCRIPTION
             "DNIS Authentication Time"
         --CONFIGURABLE
         ::= { usrCipModemPortParamEntry 23 }
    usrCipModemPortDNISAuthType  OBJECT-TYPE
         SYNTAX INTEGER
         {
             dnis (1),
             ani (2)
         }
         MAX-ACCESS read-write
         STATUS  current
         DESCRIPTION
             "DNIS Authentication type"
         --CONFIGURABLE
         ::= { usrCipModemPortParamEntry 24 }
     usrCipModemPortDNISPassword OBJECT-TYPE
          SYNTAX      OCTET STRING (SIZE(0..15))
  	  MAX-ACCESS  read-write
   	  STATUS      current
   	  DESCRIPTION "The DNIS  password."
        --CONFIGURABLE
         ::= { usrCipModemPortParamEntry 25 }
     usrCipModemPortDNISTimeout OBJECT-TYPE
          SYNTAX      Integer32
          MAX-ACCESS  read-write
          STATUS      current
          DESCRIPTION "Timeout if no auth within this time"
        --CONFIGURABLE
     ::= {usrCipModemPortParamEntry 26}
    usrCipModemPortParity  OBJECT-TYPE
         SYNTAX INTEGER       
         {      
			no-parity-eight-bit (1),
			even-seven-bit (2),  
			odd-seven-bit (3),  
			no-parity-seven-bit (4)
         }
         MAX-ACCESS  read-write
         STATUS  current
         DESCRIPTION
             "Port Parity"
         --CONFIGURABLE
         ::= { usrCipModemPortParamEntry 27 }
    usrCipModemPromptDelay  OBJECT-TYPE
         SYNTAX Integer32 (0..100)
         MAX-ACCESS   read-write
         STATUS  current
         DESCRIPTION
             "If user does not enter any key after banner mesg, authenticate
              user based on interface user name after this delay"
         --CONFIGURABLE 
         ::= { usrCipModemPortParamEntry 28 }
    usrCipModemPromptTimeout  OBJECT-TYPE
         SYNTAX Integer32 (5..600)
         MAX-ACCESS read-write
         STATUS  current
         DESCRIPTION
             " This is the maximum timeout while prompting for 
		username password. If nothing is typed, the session will
		be terminated. Default is 300 secs"
         --CONFIGURABLE
         ::= { usrCipModemPortParamEntry 29 }
      usrCipModemSpecialXonXoffFlow  OBJECT-TYPE
         SYNTAX INTEGER       
         {      
             disbaled (0),
             enabled (1)
         }
         MAX-ACCESS read-write
         STATUS  current
         DESCRIPTION
             "Special Xon Xoff flow control in modem control receive side"
         --CONFIGURABLE
         ::= { usrCipModemPortParamEntry 30 }
	 usrCipModemUseDnisPool OBJECT-TYPE
         SYNTAX INTEGER 
		 {
             dnis-pool-disabled (1),
             dnis-pool-preferred (2),
             dnis-pool-required (3)
         }
         MAX-ACCESS read-write
         STATUS  current
         DESCRIPTION
             "User DNIS pool"
         --CONFIGURABLE
     ::= { usrCipModemPortParamEntry 31 }
	 usrCipModemLoginTable OBJECT-TYPE
         SYNTAX OCTET STRING (SIZE(0..32))
         MAX-ACCESS  read-write
         STATUS  current
         DESCRIPTION
             "Login Host Table "
         --CONFIGURABLE
     ::= { usrCipModemPortParamEntry 32 }
     usrCipConfigFileName OBJECT-TYPE
         SYNTAX OCTET STRING (SIZE(0..64))
         MAX-ACCESS read-only
         STATUS current
         DESCRIPTION
           "The name of a ConfigFile to read/write permanent database
            records. If the value of this object is an empty string,
            then the default name `@file://CallInitProcess.cfg' is
            used."
     ::= { usrCip 25 }
-- Modem Group Interface Table
      usrCipModemGroupInterfaceTable OBJECT-TYPE
         SYNTAX  SEQUENCE OF USRCIPModemGroupInterfaceEntry 
         MAX-ACCESS  not-accessible
         STATUS  current
         DESCRIPTION
            "This table contains the list of interfaces that belong to 
             a particular modem group."
      ::= { usrCip 26 }
     usrCipModemGroupInterfaceEntry OBJECT-TYPE
        SYNTAX      USRCIPModemGroupInterfaceEntry
        MAX-ACCESS  not-accessible
        STATUS      current
        DESCRIPTION "Each entry corresponds to a serial interface."
        INDEX   {
                usrCipModemGroupInterfaceGroupName,
                usrCipModemGroupInterfaceName
               }
     ::= {usrCipModemGroupInterfaceTable 1}
     USRCIPModemGroupInterfaceEntry ::= 
          SEQUENCE {
               usrCipModemGroupInterfaceName
                    DisplayString,
               usrCipModemGroupInterfaceStatus
                    INTEGER,
               usrCipModemGroupInterfaceGroupName
                    DisplayString
          }
     usrCipModemGroupInterfaceGroupName OBJECT-TYPE
          SYNTAX        DisplayString
          MAX-ACCESS    not-accessible
          STATUS        current
          DESCRIPTION   "Group name that this interface belongs to."
     ::= { usrCipModemGroupInterfaceEntry 1 }
     usrCipModemGroupInterfaceName OBJECT-TYPE
          SYNTAX        DisplayString 
          MAX-ACCESS    not-accessible
          STATUS        current
          DESCRIPTION   "The identifier of a modem group."
     --CONFIGURABLE
     ::= { usrCipModemGroupInterfaceEntry 2 }
     usrCipModemGroupInterfaceStatus  OBJECT-TYPE
        SYNTAX          INTEGER {
                                add(0),
                                delete(1),
                                active(2),
                                inactive(3)
                                }
        MAX-ACCESS     	read-write
        STATUS          current
        DESCRIPTION     "The status could be add or delete the group member
                         specified in the usrCipGroupMembers MIB."
      --CONFIGURABLE
     ::= { usrCipModemGroupInterfaceEntry 3 }
     usrCipGlobalCallType  OBJECT-TYPE
           SYNTAX          INTEGER { pptp(1),l2tp(3),none(2) }
           MAX-ACCESS      read-write
           STATUS          current
           DESCRIPTION
              " Global Call Type determiner . "
           --CONFIGURABLE
           ::= { usrCip 27 }
     usrCipSingleLevelPrompting OBJECT-TYPE
        SYNTAX  INTEGER {
            disabled(0),
            enabled(1)
        }
        MAX-ACCESS  read-write
        STATUS current
        DESCRIPTION
           "If enabled, Login/Network users are presented with the HiPer
           prompt, by-passing the initial Login/Network prompt (def: disabled)."
        --CONFIGURABLE
     ::= { usrCip 28 }
   usrCipCfmChatScriptFlag OBJECT-TYPE
        SYNTAX          Integer32
        MAX-ACCESS      read-write
        STATUS          current
        DESCRIPTION     "This flag triggers a save of chat script table."
    ::= { usrCip 29 }
    usrCipChatScriptTable OBJECT-TYPE
         SYNTAX  SEQUENCE OF USRCIPChatScriptEntry
         MAX-ACCESS  not-accessible
         STATUS  current
         DESCRIPTION
            "This table contains the chatscript names."
    ::= { usrCip 30 }
    usrCIPChatScriptEntry OBJECT-TYPE
        SYNTAX      USRCIPChatScriptEntry
        MAX-ACCESS  not-accessible
        STATUS      current
        DESCRIPTION "Each entry corresponds to a chat script."
        INDEX   { usrCipChatScriptName }
     ::= {usrCipChatScriptTable 1}
    USRCIPChatScriptEntry ::=
          SEQUENCE {
               usrCipChatScriptName
                    OCTET STRING,
               usrCipChatScriptStatus
                    INTEGER,
               usrCipChatScriptString
                    OCTET STRING
    }
   usrCipChatScriptName OBJECT-TYPE
         SYNTAX  OCTET STRING (SIZE(0..64))
         MAX-ACCESS  not-accessible
         STATUS  current
         DESCRIPTION
            "The character name for this chatscript."
    ::= { usrCIPChatScriptEntry 1 }
    usrCipChatScriptStatus OBJECT-TYPE
         SYNTAX  INTEGER {
                         add(1),
                         delete(2),
                         verify(3),
                         normal(4),       -- Chat Script reading in progress
                         reading(5),     -- Chat Script reading in progress
                         verifyFailed(6),  -- Chat Script verification failed
                         starting(7),       -- Chat Script operation starting
                         verifying(8)       -- Chat script verification in progress
                         }
         MAX-ACCESS  read-write
         STATUS  current
         DESCRIPTION
            "The status of this chatscript entry. Valid row entries in this
             table have the status field set to normal. The settable values
             are normal and delete. If the instance is in the table and the
             status is starting/reading, this will be an add operation."
         --CONFIGURABLE
     ::= { usrCIPChatScriptEntry 2 }
    usrCipChatScriptString OBJECT-TYPE
         SYNTAX  OCTET STRING
         MAX-ACCESS  read-only
         STATUS  current
         DESCRIPTION
            "Chat script buffer"
    ::= { usrCIPChatScriptEntry 3 }
    usrCipDNISAuthFlag  OBJECT-TYPE
         SYNTAX  INTEGER {
                 disabled(0),
                 enabled(1)
             }
         MAX-ACCESS  read-write
         STATUS  current
         DESCRIPTION
             "This is the switch to enable/disable DNIS based
              call-authorization"
         --CONFIGURABLE
         ::= { usrCip 31 }
    usrCipDNISAuthPassword  OBJECT-TYPE
         SYNTAX  OCTET STRING (SIZE(0..127))
         MAX-ACCESS  read-write
         STATUS  current
         DESCRIPTION
             "This is the Password for the DNIS authorization request being sent out"
         --CONFIGURABLE
         ::= { usrCip 32 }
    usrCipBannerFileName  OBJECT-TYPE
         SYNTAX  OCTET STRING (SIZE(0..64))
         MAX-ACCESS  read-write
         STATUS  current
         DESCRIPTION
             "This is file name for port banner file, value zero if none."
         --CONFIGURABLE
         ::= { usrCip 33 }
    usrCipAutoAnswerFlag  OBJECT-TYPE
         SYNTAX  INTEGER {
                 disabled(0),
                 enabled(1)
             }
         MAX-ACCESS  read-write
         STATUS  current
         DESCRIPTION
             "This is the switch to enable/disable the Auto Answering of
              Modem-Sharing-Dialout Calls"
         --CONFIGURABLE
         ::= { usrCip 34 }
    usrSlotUtilizationTable OBJECT-TYPE
         SYNTAX  SEQUENCE OF USRSlotUtilizationEntry
         MAX-ACCESS  not-accessible
         STATUS  current
         DESCRIPTION
            "This table contains the chatscript names."
    ::= { usrCip 35 }
    usrSlotUtilizationEntry OBJECT-TYPE
        SYNTAX      USRSlotUtilizationEntry
        MAX-ACCESS  not-accessible
        STATUS      current
        DESCRIPTION "Each entry corresponds to a chat script."
        INDEX   { usrSlotIndex }
     ::= {usrSlotUtilizationTable 1}
    USRSlotUtilizationEntry ::=
          SEQUENCE {
               usrSlotIndex
                    Integer32,
               usrSlotId
                    Integer32,
               usrSlotActiveCalls
                    Integer32,
               usrSlotNumberOfPorts
                    Integer32,
               usrSlotUtilization
                    Integer32
    }
   usrSlotIndex OBJECT-TYPE
         SYNTAX  Integer32
         MAX-ACCESS  not-accessible
         STATUS  current
         DESCRIPTION
            "The slot index."
    ::= { usrSlotUtilizationEntry 1 }
   usrSlotId OBJECT-TYPE
         SYNTAX  Integer32
         MAX-ACCESS  read-only
         STATUS  current
         DESCRIPTION
            "The slot number in human readable format where proper offset is computed." 
    ::= { usrSlotUtilizationEntry 2 }
   usrSlotActiveCalls OBJECT-TYPE
         SYNTAX  Integer32
         MAX-ACCESS  read-only
         STATUS  current
         DESCRIPTION
            "The number of active calls on that slot at that instant." 
    ::= { usrSlotUtilizationEntry 3 }
   usrSlotNumberOfPorts OBJECT-TYPE
         SYNTAX  Integer32
         MAX-ACCESS  read-only
         STATUS  current
         DESCRIPTION
            "The number of ports on that slot."
    ::= { usrSlotUtilizationEntry 4 }
   usrSlotUtilization OBJECT-TYPE
         SYNTAX  Integer32
         MAX-ACCESS  read-only
         STATUS  current
         DESCRIPTION
            "The percent utilization of that slot. This is computed as number of active calls on that slot divided by the number of ports on that slot."
    ::= { usrSlotUtilizationEntry 5 }
    usrCipTotalCalls  OBJECT-TYPE
         SYNTAX  Integer32 
         MAX-ACCESS  read-only
         STATUS  current
         DESCRIPTION
             "Total number of calls on the chassis."
         ::= { usrCip 36 }
    usrCipTotalAvailablePorts  OBJECT-TYPE
         SYNTAX  Integer32 
         MAX-ACCESS  read-only
         STATUS  current
         DESCRIPTION
             "Total number of ports on the chassis."
         ::= { usrCip 37 }
    usrCipTotalChassisUtilization  OBJECT-TYPE
         SYNTAX  Integer32 
         MAX-ACCESS  read-only
         STATUS  current
         DESCRIPTION
             "Percent utilization of all ports on the chassis."
         ::= { usrCip 38 }
    usrCipCallsInLast24Hours  OBJECT-TYPE
         SYNTAX  Integer32 
         MAX-ACCESS  read-only
         STATUS  current
         DESCRIPTION
             "The number of calls in last 24 hours."
         ::= { usrCip 39 }
    usrCipDialinAccessManageUser  OBJECT-TYPE
         SYNTAX  INTEGER {
            disabled(2),
            enabled(1)
         }
         MAX-ACCESS  read-write
         STATUS  current
         DESCRIPTION
             "No Manage user dialin access"
		--CONFIGURABLE
         ::= { usrCip 40 }
-- CIP login table definition. An interface pointing to this table
-- use the login host ip address and login port from the table.
   usrCipCfmLoginTableFlag OBJECT-TYPE
        SYNTAX          Integer32
        MAX-ACCESS      read-write
        STATUS          current
        DESCRIPTION     "This flag triggers a save of cip login table."  
    ::= { usrCip 69 }
    usrCipLoginTable OBJECT-TYPE
    SYNTAX SEQUENCE OF UsrCipLoginEntry
    MAX-ACCESS  not-accessible
    STATUS  current
    DESCRIPTION
        ""
    ::= { usrCip 70 }
    usrCipLoginEntry    OBJECT-TYPE
    SYNTAX  UsrCipLoginEntry
    MAX-ACCESS  not-accessible
    STATUS  current
    DESCRIPTION
        ""
   INDEX  { usrCipLoginListName, usrCipLoginPref }
	   ::= { usrCipLoginTable 1 }
    UsrCipLoginEntry ::=
	SEQUENCE {
		usrCipLoginListName     OCTET STRING,
		usrCipLoginPref		Integer32,
		usrCipLoginIpAddress	IpAddress,
		usrCipLoginPort		Integer32,
		usrCipLoginListNameForPrint
                        		OCTET STRING,
		usrCipLoginEntryDelete  Integer32
	} 
    usrCipLoginListName  OBJECT-TYPE
         SYNTAX  OCTET STRING (SIZE(0..9))
         MAX-ACCESS  not-accessible
         STATUS  current
         DESCRIPTION
             "This is the cip login list name"
    ::= { usrCipLoginEntry 1 }
    usrCipLoginPref  OBJECT-TYPE
        SYNTAX  Integer32
        MAX-ACCESS  not-accessible 
        STATUS  current
        DESCRIPTION
            "login preference index"
    ::= { usrCipLoginEntry 2 }
    usrCipLoginIpAddress  OBJECT-TYPE
         SYNTAX  IpAddress
         MAX-ACCESS  read-write
         STATUS  current
         DESCRIPTION
             "This is the cip login host ip address"
     --CONFIGURABLE
     ::= { usrCipLoginEntry 3 }
    usrCipLoginPort  OBJECT-TYPE
         SYNTAX  Integer32
         MAX-ACCESS  read-write
         STATUS  current
         DESCRIPTION
             "This is the cip login host port"
     --CONFIGURABLE
     ::= { usrCipLoginEntry 4 }
    usrCipLoginListNameForPrint  OBJECT-TYPE
         SYNTAX  OCTET STRING (SIZE(0..9))
         MAX-ACCESS  read-write
         STATUS  current
         DESCRIPTION
             "This is the cip login list name. Added the second mib to print
	      the login table name. The first mib is an index to table"
     --CONFIGURABLE
     ::= { usrCipLoginEntry 5 }
    usrCipLoginEntryDelete  OBJECT-TYPE
         SYNTAX  Integer32
         MAX-ACCESS  read-write
         STATUS  current
         DESCRIPTION
             "Setting this entry will delete the particular table"
     ::= { usrCipLoginEntry 6 }
    usrCipModemUtilizationStatisticsTable OBJECT-TYPE  
           SYNTAX     SEQUENCE OF USRCIPModemUtilizationStatisticsEntry
           MAX-ACCESS not-accessible
           STATUS     current
           DESCRIPTION
             "The active calls during every hour gives 24 samples."
    ::= { usrCip 41 }
    usrCipModemUtilizationStatisticsEntry OBJECT-TYPE  
           SYNTAX     USRCIPModemUtilizationStatisticsEntry
           MAX-ACCESS not-accessible
           STATUS     current
           DESCRIPTION
                "CIP PPP Modem Utilizationstatistics"
           INDEX      { usrCipModemUtilizationStatisticsIndex }
    ::= { usrCipModemUtilizationStatisticsTable 1 }
    USRCIPModemUtilizationStatisticsEntry ::= SEQUENCE {
           usrCipModemUtilizationStatisticsIndex
                    Integer32,
           usrCipModemUtilization
                    Counter32,
           usrCipCallsPerHour
                    Counter32,
           usrCipPacketsForwadedPerHour
                    Counter32
        }
    usrCipModemUtilizationStatisticsIndex OBJECT-TYPE
           SYNTAX     Integer32
           MAX-ACCESS not-accessible
           STATUS     current
           DESCRIPTION
                 "The index for the call duration samples."
           ::= { usrCipModemUtilizationStatisticsEntry 1 }
    usrCipModemUtilization OBJECT-TYPE
           SYNTAX     Counter32   
           MAX-ACCESS read-only
           STATUS     current 
           DESCRIPTION
                 "The  percentage utilization of the modems per hour."
           ::= { usrCipModemUtilizationStatisticsEntry 2 }
    usrCipCallsPerHour OBJECT-TYPE
           SYNTAX     Counter32   
           MAX-ACCESS read-only
           STATUS     current 
           DESCRIPTION
                 "The  number of calls per hour."
           ::= { usrCipModemUtilizationStatisticsEntry 3 }
    usrCipPacketsForwadedPerHour OBJECT-TYPE
           SYNTAX     Counter32   
           MAX-ACCESS read-only
           STATUS     current 
           DESCRIPTION
                 "The  number of packets forwarded per hour."
           ::= { usrCipModemUtilizationStatisticsEntry 4 }
	usrCipCallStatisticsTable OBJECT-TYPE
           SYNTAX     SEQUENCE OF USRCIPCallStatisticsEntry
           MAX-ACCESS  not-accessible
           STATUS     current
           DESCRIPTION
                 "The  table listing the Cip Call statistics
                  for all the calls coming in."
           ::= { usrCip 42 }
    usrCipCallStatisticsEntry OBJECT-TYPE
           SYNTAX     USRCIPCallStatisticsEntry
           MAX-ACCESS not-accessible
           STATUS     current
           DESCRIPTION
				"CIP Call statistics"
           INDEX      { usrCipCallStatisticsIndex }
           ::= { usrCipCallStatisticsTable 1 }
    USRCIPCallStatisticsEntry ::= SEQUENCE {
           usrCipCallStatisticsIndex                        Integer32,
           usrCipCallStatisticsOnDemandConns                Counter32,
           usrCipCallStatisticsContinuousConns              Counter32,
           usrCipCallStatisticsDialBackConns                Counter32,
           usrCipCallStatisticsManualConns                  Counter32,
           usrCipCallStatisticsTimedConns                   Counter32,
           usrCipCallStatisticsSharedConns                  Counter32,
           usrCipCallStatisticsDialInConns                  Counter32,
           usrCipCallStatisticsBondConns                    Counter32,
           usrCipCallStatisticsDedicatedConns               Counter32,
           usrCipCallStatisticsAnalogCalls                  Counter32,
           usrCipCallStatisticsIsdnCalls                    Counter32,
           usrCipCallStatisticsDialInUsers                  Counter32,
           usrCipCallStatisticsNetworkUsers                 Counter32,
           usrCipCallStatisticsCounterResetTime             DateAndTime,
           usrCipCallStatisticsIs95cPppConns                Counter32,
           usrCipCallStatisticsEvdoPppConns                 Counter32
     }
    usrCipCallStatisticsIndex OBJECT-TYPE
           SYNTAX     Integer32
           MAX-ACCESS not-accessible
           STATUS     current
           DESCRIPTION
                 "The index for the call statistics display.
                  they are 0-now, 1-max, 2-today & 3-total."
           ::= { usrCipCallStatisticsEntry 1 }
	usrCipCallStatisticsOnDemandConns OBJECT-TYPE
           SYNTAX     Counter32
           MAX-ACCESS read-only
           STATUS     current
           DESCRIPTION
                 "The number of On Demand connections."
           ::= { usrCipCallStatisticsEntry 2 }
	usrCipCallStatisticsContinuousConns OBJECT-TYPE
           SYNTAX     Counter32
           MAX-ACCESS read-only
           STATUS     current
           DESCRIPTION
                 "The number of Continuous  connections."
           ::= { usrCipCallStatisticsEntry 3 }
	usrCipCallStatisticsDialBackConns OBJECT-TYPE
           SYNTAX     Counter32
           MAX-ACCESS read-only
           STATUS     current
           DESCRIPTION
                 "The number of Dial back connections."
           ::= { usrCipCallStatisticsEntry 4 }
	usrCipCallStatisticsManualConns OBJECT-TYPE
           SYNTAX     Counter32
           MAX-ACCESS read-only
           STATUS     current
           DESCRIPTION
                 "The number of manual connections."
           ::= { usrCipCallStatisticsEntry 5 }
	usrCipCallStatisticsTimedConns OBJECT-TYPE
           SYNTAX     Counter32
           MAX-ACCESS read-only
           STATUS     current
           DESCRIPTION
                 "The number of Timed connections."
           ::= { usrCipCallStatisticsEntry 6 }
	usrCipCallStatisticsSharedConns OBJECT-TYPE
           SYNTAX     Counter32
           MAX-ACCESS read-only
           STATUS     current
           DESCRIPTION
                 "The number of Shared connections."
           ::= { usrCipCallStatisticsEntry 7 }
	usrCipCallStatisticsDialInConns OBJECT-TYPE
           SYNTAX     Counter32
           MAX-ACCESS read-only
           STATUS     current
           DESCRIPTION
                 "The number of Dial-In connections."
           ::= { usrCipCallStatisticsEntry 8 }
	usrCipCallStatisticsBondConns OBJECT-TYPE
           SYNTAX     Counter32
           MAX-ACCESS read-only
           STATUS     current
           DESCRIPTION
                 "The number of Bond connections."
           ::= { usrCipCallStatisticsEntry 9 }
	usrCipCallStatisticsDedicatedConns OBJECT-TYPE
           SYNTAX     Counter32
           MAX-ACCESS read-only
           STATUS     current
           DESCRIPTION
                 "The number of Dedicated connections."
           ::= { usrCipCallStatisticsEntry 10 }
	usrCipCallStatisticsAnalogCalls OBJECT-TYPE
           SYNTAX     Counter32
           MAX-ACCESS read-only
           STATUS     current
           DESCRIPTION
                 "The number of analog calls."
           ::= { usrCipCallStatisticsEntry 11 }
	usrCipCallStatisticsIsdnCalls OBJECT-TYPE
           SYNTAX     Counter32
           MAX-ACCESS read-only
           STATUS     current
           DESCRIPTION
                 "The number of digital calls."
           ::= { usrCipCallStatisticsEntry 12 }
	usrCipCallStatisticsDialInUsers OBJECT-TYPE
           SYNTAX     Counter32
           MAX-ACCESS read-only
           STATUS     current
           DESCRIPTION
                 "The number of login users."
           ::= { usrCipCallStatisticsEntry 13 }
	 usrCipCallStatisticsNetworkUsers OBJECT-TYPE
           SYNTAX     Counter32
           MAX-ACCESS read-only
           STATUS     current
           DESCRIPTION
                 "The number of  Network users."
           ::= { usrCipCallStatisticsEntry 14 }
    usrCipCallStatisticsCounterResetTime	OBJECT-TYPE
      SYNTAX        DateAndTime
	  MAX-ACCESS	read-write
	  STATUS	current
	  DESCRIPTION
	    "Time the call statistics counters were last reset to value zero."
    ::= { usrCipCallStatisticsEntry 15 }
        usrCipCallStatisticsIs95cPppConns OBJECT-TYPE
           SYNTAX     Counter32
           MAX-ACCESS read-only
           STATUS     current
           DESCRIPTION
                 "Counter of IS-95C PPP Connections."
           ::= { usrCipCallStatisticsEntry 16 }
        usrCipCallStatisticsEvdoPppConns OBJECT-TYPE
           SYNTAX     Counter32
           MAX-ACCESS read-only
           STATUS     current
           DESCRIPTION
                 "Counter of EVDO PPP Connections."
           ::= { usrCipCallStatisticsEntry 17 }
	usrCipCallDurationStatisticsTable OBJECT-TYPE
           SYNTAX     SEQUENCE OF USRCIPCallDurationStatisticsEntry
           MAX-ACCESS not-accessible
           STATUS     current
           DESCRIPTION
			 "Number of calls which lasted 1, 2, 5, 10, 20, 60, 
			  120, 360, 720, 1440, 2160 and 3600 minutes & over. 
			  This gives 12 samples."
           ::= { usrCip 43 }
    usrCipCallDurationStatisticsEntry OBJECT-TYPE
           SYNTAX     USRCIPCallDurationStatisticsEntry
           MAX-ACCESS not-accessible
           STATUS     current
           DESCRIPTION
                "CIP Call Duration statistics"
           INDEX      { usrCipCallDurationStatisticsIndex }
           ::= { usrCipCallDurationStatisticsTable 1 }
    USRCIPCallDurationStatisticsEntry ::= SEQUENCE {
           usrCipCallDurationStatisticsIndex            Integer32,
           usrCipCallDurations                          Counter32
        }
    usrCipCallDurationStatisticsIndex OBJECT-TYPE
           SYNTAX     Integer32
           MAX-ACCESS not-accessible
           STATUS     current
           DESCRIPTION
                 "The index for the call duration samples."
           ::= { usrCipCallDurationStatisticsEntry 1 }
    usrCipCallDurations OBJECT-TYPE
           SYNTAX     Counter32 
           MAX-ACCESS read-only
           STATUS     current 
           DESCRIPTION
                 "The  number of calls for each samples."
           ::= { usrCipCallDurationStatisticsEntry 2 }
	usrCipPPPCompressionStatisticsTable OBJECT-TYPE
           SYNTAX     SEQUENCE OF USRCIPPPPCompressionStatisticsEntry
           MAX-ACCESS not-accessible
           STATUS     current
           DESCRIPTION
                 "The  table listing the Cip PPP Compression statistics
                  for all the calls coming in."
           ::= { usrCip 44 }
    usrCipPPPCompressionStatisticsEntry OBJECT-TYPE
           SYNTAX     USRCIPPPPCompressionStatisticsEntry
           MAX-ACCESS not-accessible
           STATUS     current
           DESCRIPTION
                "CIP PPPCompression statistics"
           INDEX      { usrCipPPPCompressionStatisticsIndex }
           ::= { usrCipPPPCompressionStatisticsTable 1 }
    USRCIPPPPCompressionStatisticsEntry ::= SEQUENCE {
           usrCipPPPCompressionStatisticsIndex                Integer32,
           usrCipPPPCompressionStatisticsMicrosoftComp        Counter32,
           usrCipPPPCompressionStatisticsAscendComp           Counter32,
           usrCipPPPCompressionStatisticsStackComp            Counter32,
           usrCipPPPCompressionStatisticsPPPUsers             Counter32,
           usrCipPPPCompressionStatisticsPPPBundlesFormed     Counter32,
           usrCipPPPCompressionStatisticsMrruNegotiated       Counter32,
           usrCipPPPCompressionStatisticsIPXNegotiated        Counter32,
           usrCipPPPCompressionStatisticsIPNegotiated         Counter32,
           usrCipPPPCompressionStatisticsVJCompression        Counter32,
           usrCipPPPCompressionStatisticsBACPNegotiated       Counter32,
           usrCipPPPCompressionStatisticsCHAPAuthenticated    Counter32,
           usrCipPPPCompressionStatisticsPAPAuthenticated     Counter32,
           usrCipPPPCompressionStatisticsMSCHAPAuthenticated  Counter32,
           usrCipPPPCompressionStatisticsEAPAuthenticated     Counter32,
           usrCipPPPCompressionStatisticsResetTime            DateAndTime,
           usrCipPPPCompressionStatisticsDeflateComp          Counter32,
    	   usrCipPPPStatisticsConnInitiated                   Counter32,
           usrCipPPPStatisticsConnRenegotiated                Counter32,
           usrCipPPPStatisticsConnSuccess                     Counter32,
           usrCipPPPStatisticsConnFailed                      Counter32,
           usrCipPPPStatisticsConnRelease                     Counter32,
           usrCipPPPStatisticsConnMobileRelease               Counter32,
           usrCipPPPStatisticsConnPDSNRelease                 Counter32,
           usrCipPPPStatisticsConnLCPFailed                   Counter32,
           usrCipPPPStatisticsConnAuthFailed                  Counter32,
           usrCipPPPStatisticsConnIPCPFailed                  Counter32,
           usrCipPPPStatisticsConnRenegPDSN                   Counter32,
           usrCipPPPStatisticsConnRenegMobile                 Counter32,
           usrCipPPPStatisticsConnRenegIPMismatch             Counter32,
           usrCipPPPStatisticsConnRenegOtherReasons           Counter32,
           usrCipPPPStatisticsConnCHAPAuthSuccess             Counter32,
           usrCipPPPStatisticsConnCHAPAuthFailed              Counter32,
           usrCipPPPStatisticsConnPAPAuthSuccess              Counter32,
           usrCipPPPStatisticsConnPAPAuthFailed               Counter32,
           usrCipPPPStatisticsConnMSCHAPAuthSuccess           Counter32,
           usrCipPPPStatisticsConnMSCHAPAuthFailed            Counter32,
           usrCipPPPStatisticsConnEAPAuthSuccess              Counter32,
           usrCipPPPStatisticsConnEAPAuthFailed               Counter32,
           usrCipPPPStatisticsNumLCPFailMaxRetx               Counter32,
           usrCipPPPStatisticsNumLCPFailUnsupport             Counter32,
           usrCipPPPStatisticsNumLCPFailUnknown               Counter32,
           usrCipPPPStatisticsNumIPCPFailMaxRetx              Counter32,
           usrCipPPPStatisticsNumIPCPFailUnsupport            Counter32,
           usrCipPPPStatisticsNumIPCPFailUnknown              Counter32,
           usrCipPPPStatisticsConnLCPEntered                  Counter32,
           usrCipPPPStatisticsConnAuthEntered                 Counter32,
           usrCipPPPStatisticsConnIPCPEntered                 Counter32,
           usrCipPPPStatisticsTotalCallsWithCompression       Counter32,
           usrCipPPPStatisticsConnsFailedBeforeLcp   	      Counter32,
           usrCipPPPStatisticsConnsReachedLcpOpen   	      Counter32,
           usrCipPPPStatisticsConnsAuthSkipped                Counter32,
           usrCipPPPStatisticsConnsCHAPAuthAborted            Counter32,
           usrCipPPPStatisticsConnsPAPAuthAborted             Counter32,
           usrCipPPPStatisticsConnsMSCHAPAuthAborted          Counter32,
           usrCipPPPStatisticsConnsEAPAuthAborted             Counter32,
           usrCipPPPStatisticsConnsAuthPassed                 Counter32,
           usrCipPPPStatisticsConnsRenegotiatedAfterSetup     Counter32
	}
	usrCipPPPCompressionStatisticsIndex OBJECT-TYPE
           SYNTAX     Integer32
           MAX-ACCESS not-accessible
           STATUS     current
           DESCRIPTION
                 "The index for the PPPCompression statistics display."
           ::= { usrCipPPPCompressionStatisticsEntry 1 }
    usrCipPPPCompressionStatisticsMicrosoftComp OBJECT-TYPE
           SYNTAX     Counter32
           MAX-ACCESS read-only
           STATUS     current
           DESCRIPTION
                 "The number of calls uses microsoft compression."
           ::= { usrCipPPPCompressionStatisticsEntry 2 }
    usrCipPPPCompressionStatisticsAscendComp OBJECT-TYPE
           SYNTAX     Counter32
           MAX-ACCESS read-only
           STATUS     current
           DESCRIPTION
                 "The number of calls uses ascend compression.."
           ::= { usrCipPPPCompressionStatisticsEntry 3 }
    usrCipPPPCompressionStatisticsStackComp OBJECT-TYPE
           SYNTAX     Counter32
           MAX-ACCESS read-only
           STATUS     current
           DESCRIPTION
                 "The number of calls uses stack compression.."
           ::= { usrCipPPPCompressionStatisticsEntry 4 }
    usrCipPPPCompressionStatisticsPPPUsers OBJECT-TYPE
           SYNTAX     Counter32
           MAX-ACCESS read-only
           STATUS     current
           DESCRIPTION
                 "The number of PPP users.."
           ::= { usrCipPPPCompressionStatisticsEntry 5 }
    usrCipPPPCompressionStatisticsPPPBundlesFormed OBJECT-TYPE
           SYNTAX     Counter32
           MAX-ACCESS read-only
           STATUS     current
           DESCRIPTION
                 "The number of PPP Bundles formed.."
           ::= { usrCipPPPCompressionStatisticsEntry 6 }
    usrCipPPPCompressionStatisticsMrruNegotiated OBJECT-TYPE
           SYNTAX     Counter32
           MAX-ACCESS read-only
           STATUS     current
           DESCRIPTION
                 "The number of calls negotiated MRRU for making a multi-link.."
           ::= { usrCipPPPCompressionStatisticsEntry 7 }
    usrCipPPPCompressionStatisticsIPXNegotiated OBJECT-TYPE
           SYNTAX     Counter32
           MAX-ACCESS read-only
           STATUS     current
           DESCRIPTION
                 "The number of calls negotiated IPX."
           ::= { usrCipPPPCompressionStatisticsEntry 8 }
    usrCipPPPCompressionStatisticsIPNegotiated OBJECT-TYPE
           SYNTAX     Counter32
           MAX-ACCESS read-only
           STATUS     current
           DESCRIPTION
                 "The number of calls negotiated IP."
           ::= { usrCipPPPCompressionStatisticsEntry 9 }
    usrCipPPPCompressionStatisticsVJCompression OBJECT-TYPE
           SYNTAX     Counter32
           MAX-ACCESS read-only
           STATUS     current
           DESCRIPTION
                 "The number of calls negotiated VJ Compression"
           ::= { usrCipPPPCompressionStatisticsEntry 10 }
    usrCipPPPCompressionStatisticsBACPNegotiated OBJECT-TYPE
           SYNTAX     Counter32
           MAX-ACCESS read-only
           STATUS     current
           DESCRIPTION
                 "The number of calls negotiated BAP."
           ::= { usrCipPPPCompressionStatisticsEntry 11 }
    usrCipPPPCompressionStatisticsCHAPAuthenticated OBJECT-TYPE
           SYNTAX     Counter32
           MAX-ACCESS read-only
           STATUS     current
           DESCRIPTION
                 "The number of calls attempted authentication using CHAP."
           ::= { usrCipPPPCompressionStatisticsEntry 12 }
    usrCipPPPCompressionStatisticsPAPAuthenticated OBJECT-TYPE
           SYNTAX     Counter32
           MAX-ACCESS read-only
           STATUS     current
           DESCRIPTION
                 "The number of calls attempted authentication using PAP."
           ::= { usrCipPPPCompressionStatisticsEntry 13 }
    usrCipPPPCompressionStatisticsMSCHAPAuthenticated OBJECT-TYPE
           SYNTAX     Counter32
           MAX-ACCESS read-only
           STATUS     current
           DESCRIPTION
                 "The number of calls attempted authentication using MSCHAP."
           ::= { usrCipPPPCompressionStatisticsEntry 14 }
    usrCipPPPCompressionStatisticsEAPAuthenticated OBJECT-TYPE
           SYNTAX     Counter32
           MAX-ACCESS read-only
           STATUS     current
           DESCRIPTION
                 "The number of calls attempted authentication using EAP."
           ::= { usrCipPPPCompressionStatisticsEntry 15 }
    usrCipPPPCompressionStatisticsResetTime	OBJECT-TYPE
           SYNTAX	DateAndTime
           MAX-ACCESS	read-write
           STATUS	current
	   DESCRIPTION
		"Time the PPP statistics counters were last reset to value zero."
    ::= { usrCipPPPCompressionStatisticsEntry 16 }
    usrCipPPPCompressionStatisticsDeflateComp OBJECT-TYPE
           SYNTAX     Counter32
           MAX-ACCESS read-only
           STATUS     current
           DESCRIPTION
                 "The number of calls uses Deflate compression.."
           ::= { usrCipPPPCompressionStatisticsEntry 17 }
    usrCipPPPStatisticsConnInitiated OBJECT-TYPE
           SYNTAX     Counter32
           MAX-ACCESS read-only
           STATUS     current
           DESCRIPTION
                 "The number of PPP calls initiated."
           ::= { usrCipPPPCompressionStatisticsEntry 18 }
    usrCipPPPStatisticsConnRenegotiated OBJECT-TYPE
           SYNTAX     Counter32
           MAX-ACCESS read-only
           STATUS     current
           DESCRIPTION
                 "The number of PPP calls renegotiated."
           ::= { usrCipPPPCompressionStatisticsEntry 19 }
    usrCipPPPStatisticsConnSuccess OBJECT-TYPE
           SYNTAX     Counter32
           MAX-ACCESS read-only
           STATUS     current
           DESCRIPTION
                 "The number of PPP calls succeeded."
           ::= { usrCipPPPCompressionStatisticsEntry 20 }
    usrCipPPPStatisticsConnFailed OBJECT-TYPE
           SYNTAX     Counter32
           MAX-ACCESS read-only
           STATUS     current
           DESCRIPTION
                 "The number of PPP calls failed."
           ::= { usrCipPPPCompressionStatisticsEntry 21 }
    usrCipPPPStatisticsConnRelease OBJECT-TYPE
           SYNTAX     Counter32
           MAX-ACCESS read-only
           STATUS     current
           DESCRIPTION
                 "The number of PPP calls released."
           ::= { usrCipPPPCompressionStatisticsEntry 22 }
    usrCipPPPStatisticsConnMobileRelease OBJECT-TYPE
           SYNTAX     Counter32
           MAX-ACCESS read-only
           STATUS     current
           DESCRIPTION
                 "The number of PPP calls released by Mobile."
           ::= { usrCipPPPCompressionStatisticsEntry 23 }
    usrCipPPPStatisticsConnPDSNRelease OBJECT-TYPE
           SYNTAX     Counter32
           MAX-ACCESS read-only
           STATUS     current
           DESCRIPTION
                 "The number of PPP calls released by PDSN."
           ::= { usrCipPPPCompressionStatisticsEntry 24 }
    usrCipPPPStatisticsConnLCPFailed   OBJECT-TYPE
           SYNTAX     Counter32
           MAX-ACCESS read-only
           STATUS     current
           DESCRIPTION
                 "The number of PPP calls failed at LCP state."
           ::= { usrCipPPPCompressionStatisticsEntry 25 }
    usrCipPPPStatisticsConnAuthFailed   OBJECT-TYPE
           SYNTAX     Counter32
           MAX-ACCESS read-only
           STATUS     current
           DESCRIPTION
                 "The number of PPP calls failed at authentication state."
           ::= { usrCipPPPCompressionStatisticsEntry 26 }
    usrCipPPPStatisticsConnIPCPFailed   OBJECT-TYPE
           SYNTAX     Counter32
           MAX-ACCESS read-only
           STATUS     current
           DESCRIPTION
                 "The number of PPP calls failed at IPCP state."
           ::= { usrCipPPPCompressionStatisticsEntry 27 }
    usrCipPPPStatisticsConnRenegPDSN   OBJECT-TYPE
           SYNTAX     Counter32
           MAX-ACCESS read-only
           STATUS     current
           DESCRIPTION
                 "The number of PPP calls renegotiated by PDSN."
           ::= { usrCipPPPCompressionStatisticsEntry 28 }
    usrCipPPPStatisticsConnRenegMobile   OBJECT-TYPE
           SYNTAX     Counter32
           MAX-ACCESS read-only
           STATUS     current
           DESCRIPTION
                 "The number of PPP calls renegotiated by Mobile."
           ::= { usrCipPPPCompressionStatisticsEntry 29 }
    usrCipPPPStatisticsConnRenegIPMismatch   OBJECT-TYPE
           SYNTAX     Counter32
           MAX-ACCESS read-only
           STATUS     current
           DESCRIPTION
                 "The number of PPP calls renegotiated due to IP mismatch."
           ::= { usrCipPPPCompressionStatisticsEntry 30 }
    usrCipPPPStatisticsConnRenegOtherReasons   OBJECT-TYPE
           SYNTAX     Counter32
           MAX-ACCESS read-only
           STATUS     current
           DESCRIPTION
                 "The number of PPP calls renegotiated due to some reason."
           ::= { usrCipPPPCompressionStatisticsEntry 31 }
    usrCipPPPStatisticsConnCHAPAuthSuccess   OBJECT-TYPE
           SYNTAX     Counter32
           MAX-ACCESS read-only
           STATUS     current
           DESCRIPTION
                 "The number of PPP calls successfully authenticated with CHAP."
           ::= { usrCipPPPCompressionStatisticsEntry 32 }
    usrCipPPPStatisticsConnCHAPAuthFailed   OBJECT-TYPE
           SYNTAX     Counter32
           MAX-ACCESS read-only
           STATUS     current
           DESCRIPTION
                 "The number of PPP calls failed in CHAP authentication."
           ::= { usrCipPPPCompressionStatisticsEntry 33 }
    usrCipPPPStatisticsConnPAPAuthSuccess   OBJECT-TYPE
           SYNTAX     Counter32
           MAX-ACCESS read-only
           STATUS     current
           DESCRIPTION
                 "The number of PPP calls successfully authenticated with PAP."
           ::= { usrCipPPPCompressionStatisticsEntry 34 }
    usrCipPPPStatisticsConnPAPAuthFailed   OBJECT-TYPE
           SYNTAX     Counter32
           MAX-ACCESS read-only
           STATUS     current
           DESCRIPTION
                 "The number of PPP calls failed in PAP authentication."
           ::= { usrCipPPPCompressionStatisticsEntry 35 }
    usrCipPPPStatisticsConnMSCHAPAuthSuccess   OBJECT-TYPE
           SYNTAX     Counter32
           MAX-ACCESS read-only
           STATUS     current
           DESCRIPTION
                 "The number of PPP calls successfully authenticated with MSCHAP."
           ::= { usrCipPPPCompressionStatisticsEntry 36 }
    usrCipPPPStatisticsConnMSCHAPAuthFailed   OBJECT-TYPE
           SYNTAX     Counter32
           MAX-ACCESS read-only
           STATUS     current
           DESCRIPTION
                 "The number of PPP calls failed in MSCHAP authentication."
           ::= { usrCipPPPCompressionStatisticsEntry 37 }
    usrCipPPPStatisticsConnEAPAuthSuccess   OBJECT-TYPE
           SYNTAX     Counter32
           MAX-ACCESS read-only
           STATUS     current
           DESCRIPTION
                 "The number of PPP calls successfully authenticated with EAP."
           ::= { usrCipPPPCompressionStatisticsEntry 38 }
    usrCipPPPStatisticsConnEAPAuthFailed   OBJECT-TYPE
           SYNTAX     Counter32
           MAX-ACCESS read-only
           STATUS     current
           DESCRIPTION
                 "The number of PPP calls failed in EAP authentication."
           ::= { usrCipPPPCompressionStatisticsEntry 39 }
    usrCipPPPStatisticsNumLCPFailMaxRetx   OBJECT-TYPE
           SYNTAX     Counter32
           MAX-ACCESS read-only
           STATUS     current
           DESCRIPTION
                 "The number of PPP calls failed after maximum retries while negotiating LCP."
           ::= { usrCipPPPCompressionStatisticsEntry 40 }
    usrCipPPPStatisticsNumLCPFailUnsupport   OBJECT-TYPE
           SYNTAX     Counter32
           MAX-ACCESS read-only
           STATUS     current
           DESCRIPTION
                 "The number of PPP calls failed due to unsupported attribute while negotiating LCP."
           ::= { usrCipPPPCompressionStatisticsEntry 41 }
    usrCipPPPStatisticsNumLCPFailUnknown   OBJECT-TYPE
           SYNTAX     Counter32
           MAX-ACCESS read-only
           STATUS     current
           DESCRIPTION
                 "The number of PPP calls failed due to unknown reason while negotiating LCP."
           ::= { usrCipPPPCompressionStatisticsEntry 42 }
    usrCipPPPStatisticsNumIPCPFailMaxRetx   OBJECT-TYPE
           SYNTAX     Counter32
           MAX-ACCESS read-only
           STATUS     current
           DESCRIPTION
                 "The number of PPP calls failed after maximum retries while negotiating IPCP."
           ::= { usrCipPPPCompressionStatisticsEntry 43 }
    usrCipPPPStatisticsNumIPCPFailUnsupport   OBJECT-TYPE
           SYNTAX     Counter32
           MAX-ACCESS read-only
           STATUS     current
           DESCRIPTION
                 "The number of PPP calls failed due to unsupported attribute while negotiating IPCP."
           ::= { usrCipPPPCompressionStatisticsEntry 44 }
    usrCipPPPStatisticsNumIPCPFailUnknown   OBJECT-TYPE
           SYNTAX     Counter32
           MAX-ACCESS read-only
           STATUS     current
           DESCRIPTION
                 "The number of PPP calls failed due to unknown reason while negotiating IPCP."
           ::= { usrCipPPPCompressionStatisticsEntry 45 }
    usrCipPPPStatisticsConnLCPEntered   OBJECT-TYPE
           SYNTAX     Counter32
           MAX-ACCESS read-only
           STATUS     current
           DESCRIPTION
                 "The number of PPP calls which entered LCP state."
           ::= { usrCipPPPCompressionStatisticsEntry 46 }
    usrCipPPPStatisticsConnAuthEntered   OBJECT-TYPE
           SYNTAX     Counter32
           MAX-ACCESS read-only
           STATUS     current
           DESCRIPTION
                 "The number of PPP calls which entered authentication state."
           ::= { usrCipPPPCompressionStatisticsEntry 47 }
    usrCipPPPStatisticsConnIPCPEntered   OBJECT-TYPE
           SYNTAX     Counter32
           MAX-ACCESS read-only
           STATUS     current
           DESCRIPTION
                 "The number of PPP calls which entered IPCP state."
           ::= { usrCipPPPCompressionStatisticsEntry 48 }
    usrCipPPPStatisticsTotalCallsWithCompression   OBJECT-TYPE
           SYNTAX     Counter32
           MAX-ACCESS read-only
           STATUS     current
           DESCRIPTION
                 "The total number of PPP calls which used compression."
           ::= { usrCipPPPCompressionStatisticsEntry 49 }
    usrCipPPPStatisticsConnsFailedBeforeLcp   OBJECT-TYPE
           SYNTAX     Counter32
           MAX-ACCESS read-only
           STATUS     current
           DESCRIPTION
                 "The number of PPP calls failed before LCP negotiated
		  even started.  An example is running out of memmory or
		  some other internal failure before LCP begins."
           ::= { usrCipPPPCompressionStatisticsEntry 50 }
    usrCipPPPStatisticsConnsReachedLcpOpen   OBJECT-TYPE
           SYNTAX     Counter32
           MAX-ACCESS read-only
           STATUS     current
           DESCRIPTION
                 "The number of PPP calls that have successfully negotiated
		  the LCP options, have reached the LCP Open stane, and have
		  proceeded to the next PPP phase (usually Authentication)."
           ::= { usrCipPPPCompressionStatisticsEntry 51 }
    usrCipPPPStatisticsConnsAuthSkipped   OBJECT-TYPE
           SYNTAX     Counter32
           MAX-ACCESS read-only
           STATUS     current
           DESCRIPTION
                 "The number of PPP calls that have negotiated to have no
		  authentication protocol, have reached the LCP Open state,
		  and therefore have skipped the PPP Authentication phase,
		  and proceeded directly to the PPP Network phase."
           ::= { usrCipPPPCompressionStatisticsEntry 52 }
    usrCipPPPStatisticsConnsCHAPAuthAborted   OBJECT-TYPE
           SYNTAX     Counter32
           MAX-ACCESS read-only
           STATUS     current
           DESCRIPTION
                 "The number of PPP calls failed during CHAP authentication
		  at a different layer than CHAP authentication
		  prior to CHAP authentication reaching a pass/fail verdict.
		  Examples are receiving a LCP Term Req or physical layer down
		  while waiting for the auth reply from a RADIUS server."
           ::= { usrCipPPPCompressionStatisticsEntry 53 }
    usrCipPPPStatisticsConnsPAPAuthAborted   OBJECT-TYPE
           SYNTAX     Counter32
           MAX-ACCESS read-only
           STATUS     current
           DESCRIPTION
                 "The number of PPP calls failed during PAP authentication
		  at a different layer than PAP authentication
		  prior to PAP authentication reaching a pass/fail verdict.
		  Examples are receiving a LCP Term Req or physical layer down
		  while waiting for the auth reply from a RADIUS server."
           ::= { usrCipPPPCompressionStatisticsEntry 54 }
    usrCipPPPStatisticsConnsMSCHAPAuthAborted   OBJECT-TYPE
           SYNTAX     Counter32
           MAX-ACCESS read-only
           STATUS     current
           DESCRIPTION
                 "The number of PPP calls failed during MSCHAP authentication
		  at a different layer than MSCHAP authentication
		  prior to MSCHAP authentication reaching a pass/fail verdict.
		  Examples are receiving a LCP Term Req or physical layer down
		  while waiting for the auth reply from a RADIUS server."
           ::= { usrCipPPPCompressionStatisticsEntry 55 }
    usrCipPPPStatisticsConnsEAPAuthAborted   OBJECT-TYPE
           SYNTAX     Counter32
           MAX-ACCESS read-only
           STATUS     current
           DESCRIPTION
                 "The number of PPP calls failed during EAP authentication
		  at a different layer than EAP authentication
		  prior to EAP authentication reaching a pass/fail verdict.
		  Examples are receiving a LCP Term Req or physical layer down
		  while waiting for the auth reply from a RADIUS server."
           ::= { usrCipPPPCompressionStatisticsEntry 56 }
    usrCipPPPStatisticsConnsAuthPassed   OBJECT-TYPE
           SYNTAX     Counter32
           MAX-ACCESS read-only
           STATUS     current
           DESCRIPTION
                 "The number of PPP calls that have successfully passed the
		  authentication phase, and have proceeded to the PPP Network
		  phase."
           ::= { usrCipPPPCompressionStatisticsEntry 57 }
    usrCipPPPStatisticsConnsRenegotiatedAfterSetup  OBJECT-TYPE
           SYNTAX     Counter32
           MAX-ACCESS read-only
           STATUS     current
           DESCRIPTION
                 "The number of PPP calls that have initiated renegotiation
		  after PPP link reached the fully setup state."
           ::= { usrCipPPPCompressionStatisticsEntry 58 }
	usrCipSpeedStatisticsTable OBJECT-TYPE
           SYNTAX     SEQUENCE OF USRCIPSpeedStatisticsEntry
           MAX-ACCESS not-accessible
           STATUS     current
           DESCRIPTION
                 "The  table listing the CIP Speed statistics
                  for all the calls coming in."
           ::= { usrCip 45 }
    usrCipSpeedStatisticsEntry OBJECT-TYPE
           SYNTAX     USRCIPSpeedStatisticsEntry
           MAX-ACCESS not-accessible
           STATUS     current
           DESCRIPTION
                "CIP Speed statistics of the incoming calls."
           INDEX      { usrCipSpeedStatisticsIndex }
           ::= { usrCipSpeedStatisticsTable 1 }
    USRCIPSpeedStatisticsEntry ::= SEQUENCE {
           usrCipSpeedStatisticsIndex                      Integer32,
           usrCipSpeedStatisticsSpeed300                   Counter32,
           usrCipSpeedStatisticsSpeed1200                  Counter32,
           usrCipSpeedStatisticsSpeed2400                  Counter32,
           usrCipSpeedStatisticsSpeed4800                  Counter32,
           usrCipSpeedStatisticsSpeed7200                  Counter32,
           usrCipSpeedStatisticsSpeed9600                  Counter32,
           usrCipSpeedStatisticsSpeed12000                 Counter32,
           usrCipSpeedStatisticsSpeed14400                 Counter32,
           usrCipSpeedStatisticsSpeed16800                 Counter32,
           usrCipSpeedStatisticsSpeed19200                 Counter32,
           usrCipSpeedStatisticsSpeed21600                 Counter32,
           usrCipSpeedStatisticsSpeed28800                 Counter32,
           usrCipSpeedStatisticsSpeed38400                 Counter32,
           usrCipSpeedStatisticsSpeed57600                 Counter32,
           usrCipSpeedStatisticsSpeed115200                Counter32,
           usrCipSpeedStatisticsSpeed288000                Counter32,
           usrCipSpeedStatisticsSpeed751200                Counter32,
           usrCipSpeedStatisticsSpeed120075                Counter32,
           usrCipSpeedStatisticsSpeed24000                 Counter32,
           usrCipSpeedStatisticsSpeed26400                 Counter32,
           usrCipSpeedStatisticsSpeed31200                 Counter32,
           usrCipSpeedStatisticsSpeed33600                 Counter32,
           usrCipSpeedStatisticsSpeed32000                 Counter32,
           usrCipSpeedStatisticsSpeed36000                 Counter32,
           usrCipSpeedStatisticsSpeed40000                 Counter32,
           usrCipSpeedStatisticsSpeed44000                 Counter32,
           usrCipSpeedStatisticsSpeed48000                 Counter32,
           usrCipSpeedStatisticsSpeed49333                 Counter32,
           usrCipSpeedStatisticsSpeed50666                 Counter32,
           usrCipSpeedStatisticsSpeed52000                 Counter32,
           usrCipSpeedStatisticsSpeed53333                 Counter32,
           usrCipSpeedStatisticsSpeed54666                 Counter32,
           usrCipSpeedStatisticsSpeed56000                 Counter32,
           usrCipSpeedStatisticsSpeed57333                 Counter32,
           usrCipSpeedStatisticsSpeed58666                 Counter32,
           usrCipSpeedStatisticsSpeed60000                 Counter32,
           usrCipSpeedStatisticsSpeed61333                 Counter32,
           usrCipSpeedStatisticsSpeed64000                 Counter32,
           usrCipSpeedStatisticsResetTime                  DateAndTime
    }
    usrCipSpeedStatisticsIndex OBJECT-TYPE
           SYNTAX     Integer32
           MAX-ACCESS not-accessible
           STATUS     current
           DESCRIPTION
                 "The index for the speed statistics display.
                  they are 0-now & 1-total."
           ::= { usrCipSpeedStatisticsEntry 1 }
    usrCipSpeedStatisticsSpeed300 OBJECT-TYPE
           SYNTAX     Counter32
           MAX-ACCESS read-only
           STATUS     current
           DESCRIPTION
                 "The number of calls with speed of 300."
           ::= { usrCipSpeedStatisticsEntry 2 }
    usrCipSpeedStatisticsSpeed1200 OBJECT-TYPE
           SYNTAX     Counter32
           MAX-ACCESS read-only
           STATUS     current
           DESCRIPTION
                 "The number of calls with speed of 1200."
           ::= { usrCipSpeedStatisticsEntry 3 }
    usrCipSpeedStatisticsSpeed2400 OBJECT-TYPE
           SYNTAX     Counter32
           MAX-ACCESS read-only
           STATUS     current
           DESCRIPTION
                 "The number of calls with speed of 2400."
           ::= { usrCipSpeedStatisticsEntry 4 }
    usrCipSpeedStatisticsSpeed4800 OBJECT-TYPE
           SYNTAX     Counter32
           MAX-ACCESS read-only
           STATUS     current
           DESCRIPTION
                 "The number of calls with speed of 4800."
           ::= { usrCipSpeedStatisticsEntry 5 }
    usrCipSpeedStatisticsSpeed7200 OBJECT-TYPE
           SYNTAX     Counter32
           MAX-ACCESS read-only
           STATUS     current
           DESCRIPTION
                 "The number of calls with speed of 7200."
           ::= { usrCipSpeedStatisticsEntry 6 }
    usrCipSpeedStatisticsSpeed9600 OBJECT-TYPE
           SYNTAX     Counter32
           MAX-ACCESS read-only
           STATUS     current
           DESCRIPTION
                 "The number of calls with speed of 9600."
           ::= { usrCipSpeedStatisticsEntry 7 }
    usrCipSpeedStatisticsSpeed12000 OBJECT-TYPE
           SYNTAX     Counter32
           MAX-ACCESS read-only
           STATUS     current
           DESCRIPTION
                 "The number of calls with speed of 12000."
           ::= { usrCipSpeedStatisticsEntry 8 }
    usrCipSpeedStatisticsSpeed14400 OBJECT-TYPE
           SYNTAX     Counter32
           MAX-ACCESS read-only
           STATUS     current
           DESCRIPTION
                 "The number of calls with speed of 14400."
           ::= { usrCipSpeedStatisticsEntry 9 }
    usrCipSpeedStatisticsSpeed16800 OBJECT-TYPE
           SYNTAX     Counter32
           MAX-ACCESS read-only
           STATUS     current
           DESCRIPTION
                 "The number of calls with speed of 16800."
           ::= { usrCipSpeedStatisticsEntry 10 }
    usrCipSpeedStatisticsSpeed19200 OBJECT-TYPE
           SYNTAX     Counter32
           MAX-ACCESS read-only
           STATUS     current
           DESCRIPTION
                 "The number of calls with speed of 19200."
           ::= { usrCipSpeedStatisticsEntry 11 }
    usrCipSpeedStatisticsSpeed21600 OBJECT-TYPE
           SYNTAX     Counter32
           MAX-ACCESS read-only
           STATUS     current
           DESCRIPTION
                 "The number of calls with speed of 21600."
           ::= { usrCipSpeedStatisticsEntry 12 }
    usrCipSpeedStatisticsSpeed28800 OBJECT-TYPE
           SYNTAX     Counter32
           MAX-ACCESS read-only
           STATUS     current
           DESCRIPTION
                 "The number of calls with speed of 28800."
           ::= { usrCipSpeedStatisticsEntry 13 }
    usrCipSpeedStatisticsSpeed38400 OBJECT-TYPE
           SYNTAX     Counter32
           MAX-ACCESS read-only
           STATUS     current
           DESCRIPTION
                 "The number of calls with speed of 38400."
           ::= { usrCipSpeedStatisticsEntry 14 }
    usrCipSpeedStatisticsSpeed57600 OBJECT-TYPE
           SYNTAX     Counter32
           MAX-ACCESS read-only
           STATUS     current
           DESCRIPTION
                 "The number of calls with speed of 57600."
           ::= { usrCipSpeedStatisticsEntry 15 }
    usrCipSpeedStatisticsSpeed115200 OBJECT-TYPE
           SYNTAX     Counter32
           MAX-ACCESS read-only
           STATUS     current
           DESCRIPTION
                 "The number of calls with speed of 115200."
           ::= { usrCipSpeedStatisticsEntry 16 }
    usrCipSpeedStatisticsSpeed288000 OBJECT-TYPE
           SYNTAX     Counter32
           MAX-ACCESS read-only
           STATUS     current
           DESCRIPTION
                 "The number of calls with speed of 288000."
           ::= { usrCipSpeedStatisticsEntry 17 }
    usrCipSpeedStatisticsSpeed751200 OBJECT-TYPE
           SYNTAX     Counter32
           MAX-ACCESS read-only
           STATUS     current
           DESCRIPTION
                 "The number of calls with speed of 75_1200."
           ::= { usrCipSpeedStatisticsEntry 18 }
    usrCipSpeedStatisticsSpeed120075 OBJECT-TYPE
           SYNTAX     Counter32
           MAX-ACCESS read-only
           STATUS     current
           DESCRIPTION
                 "The number of calls with speed of 1200_75."
           ::= { usrCipSpeedStatisticsEntry 19 }
    usrCipSpeedStatisticsSpeed24000 OBJECT-TYPE
           SYNTAX     Counter32
           MAX-ACCESS read-only
           STATUS     current
           DESCRIPTION
                 "The number of calls with speed of 24000."
           ::= { usrCipSpeedStatisticsEntry 20 }
    usrCipSpeedStatisticsSpeed26400 OBJECT-TYPE
           SYNTAX     Counter32
           MAX-ACCESS read-only
           STATUS     current
           DESCRIPTION
                 "The number of calls with a speed of 26400."
           ::= { usrCipSpeedStatisticsEntry 21 }
    usrCipSpeedStatisticsSpeed31200 OBJECT-TYPE
           SYNTAX     Counter32
           MAX-ACCESS read-only
           STATUS     current
           DESCRIPTION
                 "The number of calls with a speed of 31200."
           ::= { usrCipSpeedStatisticsEntry 22 }
    usrCipSpeedStatisticsSpeed33600 OBJECT-TYPE
           SYNTAX     Counter32
           MAX-ACCESS read-only
           STATUS     current
           DESCRIPTION
                 "The number of calls with a speed of 33600."
           ::= { usrCipSpeedStatisticsEntry 23 }
    usrCipSpeedStatisticsSpeed32000 OBJECT-TYPE
           SYNTAX     Counter32
           MAX-ACCESS read-only
           STATUS     current
           DESCRIPTION
                 "The number of calls with a speed of 32000."
           ::= { usrCipSpeedStatisticsEntry 24 }
    usrCipSpeedStatisticsSpeed36000 OBJECT-TYPE
           SYNTAX     Counter32
           MAX-ACCESS read-only
           STATUS     current
           DESCRIPTION
                 "The number of calls with a speed of 36000."
           ::= { usrCipSpeedStatisticsEntry 25 }
    usrCipSpeedStatisticsSpeed40000 OBJECT-TYPE
           SYNTAX     Counter32
           MAX-ACCESS read-only
           STATUS     current
           DESCRIPTION
                 "The number of calls with a speed of 40000."
           ::= { usrCipSpeedStatisticsEntry 26 }
    usrCipSpeedStatisticsSpeed44000 OBJECT-TYPE
           SYNTAX     Counter32
           MAX-ACCESS read-only
           STATUS     current
           DESCRIPTION
                 "The number of calls with a speed of 44000."
           ::= { usrCipSpeedStatisticsEntry 27 }
    usrCipSpeedStatisticsSpeed48000 OBJECT-TYPE
           SYNTAX     Counter32
           MAX-ACCESS read-only
           STATUS     current
           DESCRIPTION
                 "The number of calls with a speed of 48000."
           ::= { usrCipSpeedStatisticsEntry 28 }
    usrCipSpeedStatisticsSpeed49333 OBJECT-TYPE
           SYNTAX     Counter32
           MAX-ACCESS read-only
           STATUS     current
           DESCRIPTION
                 "The number of calls with a speed of 49333."
           ::= { usrCipSpeedStatisticsEntry 29 }
    usrCipSpeedStatisticsSpeed50666 OBJECT-TYPE
           SYNTAX     Counter32
           MAX-ACCESS read-only
           STATUS     current
           DESCRIPTION
                 "The number of calls with a speed of 50666."
           ::= { usrCipSpeedStatisticsEntry 30 }
    usrCipSpeedStatisticsSpeed52000 OBJECT-TYPE
           SYNTAX     Counter32
           MAX-ACCESS read-only
           STATUS     current
           DESCRIPTION
                 "The number of calls with a speed of 52000."
           ::= { usrCipSpeedStatisticsEntry 31 }
    usrCipSpeedStatisticsSpeed53333 OBJECT-TYPE
           SYNTAX     Counter32
           MAX-ACCESS read-only
           STATUS     current
           DESCRIPTION
                 "The number of calls with a speed of 53333."
           ::= { usrCipSpeedStatisticsEntry 32 }
    usrCipSpeedStatisticsSpeed54666 OBJECT-TYPE
           SYNTAX     Counter32
           MAX-ACCESS read-only
           STATUS     current
           DESCRIPTION
                 "The number of calls with a speed of 54666."
           ::= { usrCipSpeedStatisticsEntry 33 }
    usrCipSpeedStatisticsSpeed56000 OBJECT-TYPE
           SYNTAX     Counter32
           MAX-ACCESS read-only
           STATUS     current
           DESCRIPTION
                 "The number of calls with a speed of 56000."
           ::= { usrCipSpeedStatisticsEntry 34 }
    usrCipSpeedStatisticsSpeed57333 OBJECT-TYPE
           SYNTAX     Counter32
           MAX-ACCESS read-only
           STATUS     current
           DESCRIPTION
                 "The number of calls with a speed of 57333."
           ::= { usrCipSpeedStatisticsEntry 35 }
    usrCipSpeedStatisticsSpeed58666 OBJECT-TYPE
           SYNTAX     Counter32
           MAX-ACCESS read-only
           STATUS     current
           DESCRIPTION
                 "The number of calls with a speed of 58666."
           ::= { usrCipSpeedStatisticsEntry 36 }
    usrCipSpeedStatisticsSpeed60000 OBJECT-TYPE
           SYNTAX     Counter32
           MAX-ACCESS read-only
           STATUS     current
           DESCRIPTION
                 "The number of calls with a speed of 60000."
           ::= { usrCipSpeedStatisticsEntry 37 }
    usrCipSpeedStatisticsSpeed61333 OBJECT-TYPE
           SYNTAX     Counter32
           MAX-ACCESS read-only
           STATUS     current
           DESCRIPTION
                 "The number of calls with a speed of 61333."
           ::= { usrCipSpeedStatisticsEntry 38 }
    usrCipSpeedStatisticsSpeed64000 OBJECT-TYPE
           SYNTAX     Counter32
           MAX-ACCESS read-only
           STATUS     current
           DESCRIPTION
                 "The number of calls with speed of 64000."
           ::= { usrCipSpeedStatisticsEntry 39 }
    usrCipSpeedStatisticsResetTime	OBJECT-TYPE
			SYNTAX	    DateAndTime
			MAX-ACCESS	read-write
			STATUS	current
			DESCRIPTION
				"Time the Speed statistics counters were last reset to value zero."
    ::= { usrCipSpeedStatisticsEntry 40 }
    usrCipPacketSizeStatisticsTable OBJECT-TYPE
           SYNTAX     SEQUENCE OF USRCIPPacketSizeStatisticsEntry
           MAX-ACCESS not-accessible
           STATUS     current
           DESCRIPTION
	           "Size of the PPP packets in each direction.
		    packet size of every 64 bytes. ie 0-64, 64-128,
 	            128-192,, 2048. Which gives 32 samples."
           ::= { usrCip 46 }
    usrCipPacketSizeStatisticsEntry OBJECT-TYPE
           SYNTAX     USRCIPPacketSizeStatisticsEntry
           MAX-ACCESS not-accessible
           STATUS     current
           DESCRIPTION
                "CIP PPP packet size statistics"
           INDEX      { usrCipPacketSizeStatisticsIndex }
           ::= { usrCipPacketSizeStatisticsTable 1 }
    USRCIPPacketSizeStatisticsEntry ::= SEQUENCE {
           usrCipPacketSizeStatisticsIndex      Integer32,
           usrCipPacketUpLoadSizes              Counter32,
           usrCipPacketDownLoadSizes            Counter32
		}
	usrCipPacketSizeStatisticsIndex OBJECT-TYPE
           SYNTAX     Integer32
           MAX-ACCESS not-accessible
           STATUS     current
           DESCRIPTION
                 "The index for the PPP packet size samples."
           ::= { usrCipPacketSizeStatisticsEntry 1 }
    usrCipPacketUpLoadSizes OBJECT-TYPE
           SYNTAX     Counter32
           MAX-ACCESS read-only
           STATUS     current
           DESCRIPTION
                 "The PPP Upload packet size samples."
           ::= { usrCipPacketSizeStatisticsEntry 2 }
    usrCipPacketDownLoadSizes OBJECT-TYPE
           SYNTAX     Counter32
           MAX-ACCESS read-only
           STATUS     current
           DESCRIPTION
                 "The PPP Download packet size samples."
           ::= { usrCipPacketSizeStatisticsEntry 3 }
	usrCipModemDisconectReasonNoError  OBJECT-TYPE
         SYNTAX  Counter32
         MAX-ACCESS  read-only
         STATUS  current
         DESCRIPTION
             "Number of calls with disconnect reason no_error."
         ::= { usrCip 47 }
	usrCipModemDisconectReasonNoCarrier  OBJECT-TYPE
         SYNTAX  Counter32
         MAX-ACCESS  read-only
         STATUS  current
         DESCRIPTION
             "Number of calls with disconnect reason no_carrier."
         ::= { usrCip 48 }
	usrCipModemDisconectReasonNoDsr  OBJECT-TYPE
         SYNTAX  Counter32
         MAX-ACCESS  read-only
         STATUS  current
         DESCRIPTION
             "Number of calls with disconnect reason no_dsr."
         ::= { usrCip 49 }
	usrCipModemDisconectReasonTimeout  OBJECT-TYPE
         SYNTAX  Counter32
         MAX-ACCESS  read-only
         STATUS  current
         DESCRIPTION
             "Number of calls with disconnect reason timeout."
         ::= { usrCip 50 }
	usrCipModemDisconectReasonReset  OBJECT-TYPE
         SYNTAX  Counter32
         MAX-ACCESS  read-only
         STATUS  current
         DESCRIPTION
             "Number of calls with disconnect reason reset."
         ::= { usrCip 51 }
	usrCipModemDisconectReasonCallDropReq  OBJECT-TYPE
         SYNTAX  Counter32
         MAX-ACCESS  read-only
         STATUS  current
         DESCRIPTION
             "Number of calls with disconnect reason call_drop_req."
         ::= { usrCip 52 }
	usrCipModemDisconectReasonIdleTimeout  OBJECT-TYPE
         SYNTAX  Counter32
         MAX-ACCESS  read-only
         STATUS  current
         DESCRIPTION
             "Number of calls with disconnect reason idle_timeout."
         ::= { usrCip 53 }
	usrCipModemDisconectReasonSessionTimeout  OBJECT-TYPE
         SYNTAX  Counter32
         MAX-ACCESS  read-only
         STATUS  current
         DESCRIPTION
             "Number of calls with disconnect reason session_timeout."
         ::= { usrCip 54 }
	usrCipModemDisconectReasonUserReqDrop  OBJECT-TYPE
         SYNTAX  Counter32
         MAX-ACCESS  read-only
         STATUS  current
         DESCRIPTION
             "Number of calls with disconnect reason user_req_drop."
         ::= { usrCip 55 }
	usrCipModemDisconectReasonHostReqDrop  OBJECT-TYPE
         SYNTAX  Counter32
         MAX-ACCESS  read-only
         STATUS  current
         DESCRIPTION
             "Number of calls with disconnect reason host_req_drop."
         ::= { usrCip 56 }
	usrCipModemDisconectReasonServiceInterruption  OBJECT-TYPE
         SYNTAX  Counter32
         MAX-ACCESS  read-only
         STATUS  current
         DESCRIPTION
             "Number of calls with disconnect reason service_interruption."
         ::= { usrCip 57 }
	usrCipModemDisconectReasonServiceUnavailable  OBJECT-TYPE
         SYNTAX  Counter32
         MAX-ACCESS  read-only
         STATUS  current
         DESCRIPTION
             "Number of calls with disconnect reason service_unavailable."
         ::= { usrCip 58 }
	usrCipModemDisconectReasonUserInputError  OBJECT-TYPE
         SYNTAX  Counter32
         MAX-ACCESS  read-only
         STATUS  current
         DESCRIPTION
             "Number of calls with disconnect reason user_input_error."
         ::= { usrCip 59 }
	usrCipModemDisconectReasonNasDropForCallback  OBJECT-TYPE
         SYNTAX  Counter32
         MAX-ACCESS  read-only
         STATUS  current
         DESCRIPTION
             "Number of calls with disconnect reason nas_drop_for_callback."
         ::= { usrCip 60 }
        usrCipModemDisconectReasonnasDropMiscNonError  OBJECT-TYPE
         SYNTAX  Counter32
         MAX-ACCESS  read-only
         STATUS  current
         DESCRIPTION
             "Number of calls with disconnect reason nas_drop_misc_non_error."
         ::= { usrCip 61 }
	usrCipModemDisconectReasonNasInternalError  OBJECT-TYPE
         SYNTAX  Counter32
         MAX-ACCESS  read-only
         STATUS  current
         DESCRIPTION
             "Number of calls with disconnect reason nas_internal_error."
         ::= { usrCip 62 }
	usrCipStatisticsResetCallDuration    OBJECT-TYPE
         SYNTAX  DateAndTime
         MAX-ACCESS  read-write
	 STATUS  current
	 DESCRIPTION
		"Daily time we reset all the call statistics counters."
         ::= { usrCip 63 }
	usrCipStatisticsResetPPPUploadPackets    OBJECT-TYPE
	 SYNTAX  DateAndTime
	 MAX-ACCESS  read-write
	 STATUS  current
	 DESCRIPTION
		"Daily time we reset all the ppp upload packets counters."
         ::= { usrCip 64 }
	usrCipStatisticsResetPPPDownloadPackets    OBJECT-TYPE
	 SYNTAX  DateAndTime
	 MAX-ACCESS  read-write
	 STATUS  current
	 DESCRIPTION
		"Daily time we reset all the PPP download packets counters."
         ::= { usrCip 65 }
	usrCipStatisticsResetCallDisconnectReasons    OBJECT-TYPE
     SYNTAX      DateAndTime
	 MAX-ACCESS  read-write
	 STATUS  current
	 DESCRIPTION
		"Daily time we reset all the call disconnect reason counters."
         ::= { usrCip 66 }
	usrCipStatistics100PercentModemUtilization    OBJECT-TYPE
	 SYNTAX  Counter32
	 MAX-ACCESS  read-only
	 STATUS  current
	 DESCRIPTION
		" Number of minutes at modems 100 % utilization."
         ::= { usrCip 67 }
	usrCipModemCompressionStatisticsTable OBJECT-TYPE
           SYNTAX     SEQUENCE OF USRCIPModemCompressionStatisticsEntry
           MAX-ACCESS not-accessible
           STATUS     current
           DESCRIPTION
                 "The  table listing the Modem Compression statistics
                  for all the calls coming in."
           ::= { usrCip 68 }
    usrCipModemCompressionStatisticsEntry OBJECT-TYPE
           SYNTAX     USRCIPModemCompressionStatisticsEntry
           MAX-ACCESS not-accessible
           STATUS     current
           DESCRIPTION
                "CIP Modem Compression statistics"
           INDEX      { usrCipModemCompressionStatisticsIndex }
           ::= { usrCipModemCompressionStatisticsTable 1 }
    USRCIPModemCompressionStatisticsEntry ::= SEQUENCE {
           usrCipModemCompressionStatisticsIndex              Integer32,
           usrCipModemCompressionStatisticsModemCompNone      Counter32,
           usrCipModemCompressionStatisticsModemCompV42Bis    Counter32,
           usrCipModemCompressionStatisticsModemCompMnp5      Counter32,
           usrCipModemCompressionStatisticsResetTime          DateAndTime
		}
	 usrCipModemCompressionStatisticsIndex OBJECT-TYPE
           SYNTAX     Integer32
           MAX-ACCESS not-accessible
           STATUS     current
           DESCRIPTION
                 "The index for the Modem Compression statistics display.
                  they are 0-now& 1-total."
           ::= { usrCipModemCompressionStatisticsEntry 1 }
	usrCipModemCompressionStatisticsModemCompNone OBJECT-TYPE
           SYNTAX     Counter32
           MAX-ACCESS read-only
           STATUS     current
           DESCRIPTION
                 "The number of calls that has No Modem Compression."
           ::= { usrCipModemCompressionStatisticsEntry 2 }
	usrCipModemCompressionStatisticsModemCompV42Bis OBJECT-TYPE
           SYNTAX     Counter32
           MAX-ACCESS read-only
           STATUS     current
           DESCRIPTION
                 "The number of calls that has V_42Bis modem compression."
           ::= { usrCipModemCompressionStatisticsEntry 3 }
	usrCipModemCompressionStatisticsModemCompMnp5 OBJECT-TYPE
           SYNTAX     Counter32
           MAX-ACCESS read-only
           STATUS     current
           DESCRIPTION
                 "The number of calls that has mnp5 modem compression."
           ::= { usrCipModemCompressionStatisticsEntry 4 }
    usrCipModemCompressionStatisticsResetTime	OBJECT-TYPE
       SYNTAX	DateAndTime
	   MAX-ACCESS	read-write
	   STATUS	current
	   DESCRIPTION
		"Time the Speed statistics counters were last reset to value zero."
    ::= { usrCipModemCompressionStatisticsEntry 5 }
	usrCipTelnetConnectionTimeout  OBJECT-TYPE
         SYNTAX  Integer32
         MAX-ACCESS  read-write
         STATUS  current
         DESCRIPTION
             "For host rotation a configurable connection timeout"
     --CONFIGURABLE
         ::= { usrCip 71 }
    usrCipTelnetBuffering  OBJECT-TYPE
         SYNTAX  Integer32
         MAX-ACCESS  read-write
         STATUS  current
         DESCRIPTION
             "For a login user, whether CIP to TELNET buffering           
             should be turned on or off flag"
     --CONFIGURABLE
         ::= { usrCip 72 }
    usrCipPDSNAcctStyle OBJECT-TYPE
         SYNTAX  INTEGER {
		defaultPDSNStyle(1),
		emulateIWUStyle(2)
	 }
         MAX-ACCESS  read-write
         STATUS  current
         DESCRIPTION
             "This flag determines whether the PDSN emulates the IWU      
             while sending the interim accounting packets."
	 DEFVAL { defaultPDSNStyle }
     --CONFIGURABLE
         ::= { usrCip 77 }
    usrCipPppTotalReleases OBJECT-TYPE
         SYNTAX  Counter32
         MAX-ACCESS  read-only
         STATUS  current
         DESCRIPTION
	     "Count of PPP sessions which got released for any reason
	      after the PPP session was fully set up, i.e. has successfully
	      exited the IPCP stage and was in the operations stage and
	      then got released.  This counter was added for
	      Wireless IP to monitor PPP over the A10 R-P (Radio Node - PDSN)
	      link over which runs multiple PPP over GRE over IP."
         ::= { usrCip 78 }
    usrCipPppUserReleases OBJECT-TYPE
         SYNTAX  Counter32
         MAX-ACCESS  read-only
         STATUS  current
         DESCRIPTION
 	     "Count of PPP sessions which got released by the user
	      (LCP Term Req).  This counter was added for Wireless IP
	      to track the number of Mobile initiated releases  	
	      which occured after connection was fully setup, i.e. has
	      successfully exited the IPCP stage and was in the
	      operations stage, then was released."
         ::= { usrCip 79 }
    usrCipPppRpReleases OBJECT-TYPE
         SYNTAX  Counter32
         MAX-ACCESS  read-only
         STATUS  current
         DESCRIPTION
 	     "Count of PPP sessions which got released via the 3G R-P 
	      interface.
	      This counter was added for Wireless IP to track the number of 
	      RAN initiated releases which occured after the PPP connection
              was fully setup (after IPCP).  The RAN (Radio Access Node) aka
	      RN (Radio Node) aka RNN (Radio Network Node) aka PCF (Packet
     	      Communication Facility) initiates the release by de-registering
	      that mobile PPP connection by sending a Mobile-IP-like 
	      Registration Request with a lifetime of zero for that mobile
	      over the 3GPP2 A11 R-P interface.  Note that the PPP session
	      itself is carried over a GRE tunnel that forms the A10 portion 
	      of the 3GPP2 R-P interface."
         ::= { usrCip 80 }
    usrCipPppFaReleases OBJECT-TYPE
         SYNTAX  Counter32
         MAX-ACCESS  read-only
         STATUS  current
         DESCRIPTION
 	     "Count of PPP sessions which got released by request of
	      the FA (Mobile IP Foreign Agent) process in this PDSN.
	      This is only counted when the PPP session is fully setup,
	      i.e. has successfully exited the IPCP stage and was in the
	      operations stage, then was released."
         ::= { usrCip 81 }
    usrCipPppFacnReleases OBJECT-TYPE
         SYNTAX  Counter32
         MAX-ACCESS  read-only
         STATUS  current
         DESCRIPTION
 	     "Count of PPP sessions which got released by request of
	      the FACN (Foreign Agent Control Node).
	      This typically occurs when a handoff has occured for a
	      Mobile Station to another PDSN, and the FACN notifies us of
	      this fact so that the PPP resources can be released faster.
	      This is only counted when the PPP session is fully setup,
	      i.e. has successfully exited the IPCP stage and was in the
	      operations stage, then was released."
         ::= { usrCip 82 }
    usrCipPppLocalAdminReleases OBJECT-TYPE
         SYNTAX  Counter32
         MAX-ACCESS  read-only
         STATUS  current
         DESCRIPTION
 	     "Count of PPP sessions which got released by
	      a local administrative command.
	      This counter was added for Wireless IP to track the number of
	      PDSN initiated releases (Admin Command) which occured after the
	      PPP connection was fully setup (after successful IPCP)." 
         ::= { usrCip 83 }
    usrCipPppIdleTimeoutReleases OBJECT-TYPE
         SYNTAX  Counter32
         MAX-ACCESS  read-only
         STATUS  current
         DESCRIPTION
 	     "Count of PPP sessions which got released due to local Idle
	      Timeout.
	      This counter was added for Wireless IP to track the number of
	      PDSN initiated releases (Idle Timeout) which occured after the
	      PPP connection was fully setup (after successful IPCP)." 
         ::= { usrCip 84 }
    usrCipPppL2tpTunnelReleases OBJECT-TYPE
         SYNTAX  Counter32
         MAX-ACCESS  read-only
         STATUS  current
         DESCRIPTION
 	     "Count of PPP sessions which got released locally due to
	      attached an L2TP tunnel being released.
	      This counter was added for Wireless IP to track the number of
	      PDSN initiated releases (L2TP tunnel release) which occured 
	      after the L2TP connection was fully setup."
         ::= { usrCip 85 }
    usrCipPppInsufResourceReleases OBJECT-TYPE
         SYNTAX  Counter32
         MAX-ACCESS  read-only
         STATUS  obsolete
         DESCRIPTION
 	     "Count of PPP sessions which got released locally due to
	      insufficient resources.
	      This counter was added for Wireless IP to track the number of
	      PDSN initiated releases (Insufficient resources) which occured 
	      after the PPP connection was fully setup (successful IPCP).
          This unnecessary counter has been removed." 
         ::= { usrCip 86 }
    usrCipPppIngressFilteringReleases OBJECT-TYPE
         SYNTAX  Counter32
         MAX-ACCESS  read-only
         STATUS  current
         DESCRIPTION
 	     "Count of PPP sessions which got released locally due to
	      PPP renegotiations triggered by Ingress Filtering.
	      This counter was added for Wireless IP to track the number of
	      PDSN initiated releases (Ingress Filtering) which occured 
	      after the PPP connection was fully setup (successful IPCP)." 
         ::= { usrCip 87 }
    usrCipPppLocalMiscReleases OBJECT-TYPE
         SYNTAX  Counter32
         MAX-ACCESS  read-only
         STATUS  current
         DESCRIPTION
 	     "Count of PPP sessions which got released locally due to
	      miscellaneous other reasons not otherwise covered.
	      This counter was added for Wireless IP to track the number of
	      PDSN initiated releases (Miscellaneous Reason) which occured 
	      after the PPP connection was fully setup (successful IPCP)." 
         ::= { usrCip 88 }
     usrCipCallCurrentIs95cPppConns OBJECT-TYPE
         SYNTAX  Gauge32
         MAX-ACCESS  read-only
         STATUS  current
         DESCRIPTION
 	     "Number of Current Active IS-95C PPP Connections."
         ::= { usrCip 89 }
     usrCipCallActivePppConns OBJECT-TYPE
         SYNTAX  Gauge32
         MAX-ACCESS  read-only
         STATUS  current
         DESCRIPTION
 	     "Number of Active PPP Connections."
         ::= { usrCip 90 }
    usrCipShortTimeBillingSolnEnabled  OBJECT-TYPE
         SYNTAX  INTEGER {
                 enabled(1),
                 disabled(2)
             }
         MAX-ACCESS  read-write
         STATUS  current
         DESCRIPTION
             "This is the switch to enable/disable the Solution
              to Short Time Billing feature"
	 DEFVAL { disabled }
         --CONFIGURABLE
         ::= { usrCip 91 }
    usrCipShortTimeBillingSolnTimer  OBJECT-TYPE
         SYNTAX Integer32 (1..255)
         MAX-ACCESS  read-write
         STATUS  current
         DESCRIPTION
             "The value of the Short Term Billing Solution Timer"
	 DEFVAL { 5 }
         --CONFIGURABLE
         ::= { usrCip 92 }
END         -- End CIP-MIB definitions
-- ************************************************************************
--
--
--    usr_pppml.mib - The CommWorks PPP Mult-Link MIB module
--
-- Author:         <Joe Kralowetz>
--
USR-PPPML-MIB DEFINITIONS ::= BEGIN
          IMPORTS
               OBJECT-TYPE, MODULE-IDENTITY,
               IpAddress, Counter32, Integer32
                    FROM SNMPv2-SMI
               DisplayString
                    FROM SNMPv2-TC
               common, UsrConfigStatus, UsrUserName, UsrDisplayString
                    FROM USR-DEFINITIONS-MIB;
usrPPP  MODULE-IDENTITY
        LAST-UPDATED "200303172004Z"
        ORGANIZATION "CommWorks Corporation, a 3Com Company"
        CONTACT-INFO "Customer Support"
        DESCRIPTION
                "The commWorks enterprise defined MIB objects
                  for PPP multilink."
--      REVISION "200303172004Z"
--      DESCRIPTION "Added usrPPPBaseNoAuthSIP"
--      REVISION "200211221959Z"
--      DESCRIPTION "Added usrPPPBaseLCPTermOnDereg"
--      REVISION "200211112007Z"
--      DESCRIPTION "Added usrPPPBaseLCPDelay "
--      REVISION "200208231330Z"
--      DESCRIPTION "Define usrPPPBaseSessionStartMessage as DisplayString"
--      REVISION "200208142248Z"
--      DESCRIPTION "Obsoleted usrPPPBaseAcctForImatureDisc"
--      REVISION "200205051645Z"
--      DESCRIPTION "Convert to SNMPv2"
        ::= { common 11 }
          -- All representations of MAC addresses in this MIB Module use,
          -- as a textual convention (i.e. this convention does not affect
          -- their encoding), the data type:
          MacAddress ::= OCTET STRING (SIZE (6))    -- a 6 octet address in
                                                    -- the "canonical" order
          -- defined by IEEE 802.1a, i.e., as if it were transmitted least
          -- significant bit first, even though 802.5 (in contrast to other
          -- 802.x protocols) requires MAC addresses to be transmitted most
          -- significant bit first.
          --
          -- 16-bit addresses, if needed, are represented by setting their
          -- upper 4 octets to all 0's, i.e., AAFF would be represented
          -- as 00000000AAFF.
          IpxAddress ::= IpAddress   -- a 4 octet address which represents
                                     -- represents 32-bit IPX Network Address.
          usrPPPBase      OBJECT IDENTIFIER ::= { usrPPP 1 }
          usrPPPMl        OBJECT IDENTIFIER ::= { usrPPP 2 }
--
-- The PPP Base Group.
--
usrPPPBaseRxAuth OBJECT-TYPE
    SYNTAX  INTEGER {
                    none(1),
                    pap(2),
                    chap(3),
                    any(4),
                    eapMD5(5),
                    msChap(6),
                    encryptedOnly(7),
                    radiusEapProxy(8),
                    anyExceptMsChap(9),
                    mschapv2(10)
                    }
    MAX-ACCESS   read-write
    STATUS       current
    DESCRIPTION
          "Indicates whether PPP requires dial-in users
          to authenticate strictly via PAP, CHAP, EAP-MD5, with any,
          none, encrypted only (CHAP, EAP-MD5, MS-CHAP), or 
          RADIUS-EAP-Proxy."
    DEFVAL { anyExceptMsChap }
    --CONFIGURABLE
::= { usrPPPBase 1 }
usrPPPBaseCfgFileName OBJECT-TYPE
    SYNTAX       UsrDisplayString
    MAX-ACCESS   read-only
    STATUS       current
    DESCRIPTION
          "The name of a ConfigFile to read/write
          permanent database records. If the value of this
          object is an empty string, then the PPP process
          uses the default name `@file://PppFile.cfg'."
::= { usrPPPBase 2 }
usrPPPBaseCFMSaveStatus OBJECT-TYPE
    SYNTAX  UsrConfigStatus
    MAX-ACCESS  read-write
    STATUS      current
    DESCRIPTION
          "Setting the value of this object to `save'
          causes the values of the PPP Base Group
          entries to be written out to the current PPP
          config file. While the new config file is being
          written, the PPP process will set the value
          of this flag set to `saving''. Any attempts to set
          the value while it is  not `normal' (i.e. the file
          is currently being written to the config file)
          while result in a badValue error being returned.
          Setting the value to `normal' will result in no
          action."
::= { usrPPPBase 3 }
usrPPPBaseTraceInterfaceIndex OBJECT-TYPE
    SYNTAX      Integer32 (0..2147483647)
    MAX-ACCESS  read-write
    STATUS  obsolete
    DESCRIPTION
          "Sets the interface index for which the PPP
           frames will be decoded and displayed according
           to PPP Trace facility loglevel. When this value
           is set to 0 none of the interfaces is selected"
    DEFVAL { 0 }
::= { usrPPPBase 4 }
usrPPPBaseOffloading OBJECT-TYPE
    SYNTAX  INTEGER {
                    yes(2),
                    no(1)
                     }
    MAX-ACCESS   read-write
    STATUS       current
    DESCRIPTION
          "Indicates whether PPP framing can be offloaded to
          the modem card, if modem card is capable of doing it."
    DEFVAL { yes }
    --CONFIGURABLE
::= { usrPPPBase 5 }
usrPPPBaseCCPModemType OBJECT-TYPE
    SYNTAX        Integer32
    MAX-ACCESS    read-write
    STATUS        current
    DESCRIPTION
          "Indicates the types of call, for which CCP compression
          will be enabled in the Gateway card PPP module. Possible
          values are none(0x1) or all (0x10) or subset of 
          digital(0x2), compressed analog(0x4), uncompressed analog (0x08) 
          and pppoe (0x20). Default value is digital and uncompressed analog."
    DEFVAL { 20  }
    --CONFIGURABLE
::= { usrPPPBase 6 }
usrPPPBaseNBNSPrimary OBJECT-TYPE
    SYNTAX    IpAddress 
    MAX-ACCESS    read-write
    STATUS        current
    DESCRIPTION
          " Global config for NBNS primary server address. In the
            absence of user specific NBNS address, this will be send
            in IPCP negotiation"
    DEFVAL { 0  }
    --CONFIGURABLE
::= { usrPPPBase 7 }
usrPPPBaseNBNSSecondary OBJECT-TYPE
    SYNTAX  IpAddress 
    MAX-ACCESS    read-write
    STATUS        current
    DESCRIPTION
         " Global config for NBNS primary server address. In the
            absence of user specific NBNS address, this will be send
            in IPCP negotiation"
    DEFVAL { 0  }
    --CONFIGURABLE
::= { usrPPPBase 8 }
usrPPPBaseSystemDNSUsage OBJECT-TYPE
    SYNTAX  INTEGER {
                    system(0),
                    ppp(1),
                    none(2)
                     }
    MAX-ACCESS  read-write
    STATUS      current
    DESCRIPTION
          "In the absence of user configured DNS addresses,
           PPP will take DNS addresses from the system DNS
           table. Source of the DNS table can be controlled by
           this switch, system-dns or ppp-dns or none. If this
           value set to none, none of these DNS table used"
    DEFVAL { 0  }
    --CONFIGURABLE
::= { usrPPPBase 9 }
usrPPPBasePPPDNSPrimary OBJECT-TYPE
    SYNTAX  IpAddress
    MAX-ACCESS  read-write
    STATUS      current
    DESCRIPTION
          " Global config for PPP DNS primary server address. In the
            absence of user specific DNS address, this will be send
            in IPCP negotiation"
    DEFVAL { 0  }
    --CONFIGURABLE
::= { usrPPPBase 10 }
usrPPPBasePPPDNSSecondary OBJECT-TYPE
    SYNTAX  IpAddress
    MAX-ACCESS  read-write
    STATUS      current
    DESCRIPTION
          " Global config for PPP DNS secondary server address. In the
            absence of user specific DNS address, this will be send
            in IPCP negotiation"
    DEFVAL { 0  }
    --CONFIGURABLE
::= { usrPPPBase 11 }
usrPPPBaseSessionStartMessage OBJECT-TYPE
    SYNTAX       DisplayString
    MAX-ACCESS   read-write
    STATUS       current
    DESCRIPTION
         " This is the session start display message"
    --CONFIGURABLE
::= { usrPPPBase 12 }
usrPPPBaseAuthPreference OBJECT-TYPE        
    SYNTAX  INTEGER {
                    default (1),
                    pap  (2),
                    chap (3),
                    mschap (4),
                    eap (5),
                    radiuseapproxy (6)
                    }
    MAX-ACCESS  read-write
    STATUS      current
    DESCRIPTION
          "If PPP receive authentication is configured for ANY or,
           ENCRYPTED_ANY this setting can be used to set the 
           first authentication attempted" 
     DEFVAL { chap  }
    --CONFIGURABLE
::= { usrPPPBase 13 }
usrPPPBaseAcctForImatureDisc OBJECT-TYPE
    SYNTAX  INTEGER {
                   yes(2),
                   no(1)
                   }
    MAX-ACCESS   read-write
    STATUS       obsolete
    DESCRIPTION
		  "Indicates whether to send Acct Records to premature disconnect.
           NOTE: obsolete, This MIB is not supported any more"
    DEFVAL { no }
::= { usrPPPBase 14 }
--
-- The PPP Bundle Group.
--
-- The following object reflect the values of the option
-- parameters used over the PPP Bundle
--   usrPPPBundleInstance
--   usrPPPBundleOperStatus
--   usrPPPBundleUserProfile
--   usrPPPBundleActiveLinks
--   usrPPPBundleLocalMMRU
--   usrPPPBundleRemoteMMRU
--   usrPPPBundleLocalEndptClass
--   usrPPPBundleLocalEndptLength
--   usrPPPBundleLocalEndptID
--   usrPPPBundleRemoteEndptClass
--   usrPPPBundleRemoteEndptLength
--   usrPPPBundleRemoteEndptID
--   usrPPPBundleTxTotalPkts
--   usrPPPBundleTxCompPkts
--   usrPPPBundleTxNoncompPkts
--   usrPPPBundleTxEncryptPkts
--   usrPPPBundleTxNonEncryptPkts
--   usrPPPBundleTxTotalOrigBytes
--   usrPPPBundleTxTotalLineBytes
--   usrPPPBundleRxBadHdrs
--   usrPPPBundleRxTotalPkts
--   usrPPPBundleRxCompPkts
--   usrPPPBundleRxNoncompPkts
--   usrPPPBundleRxEncryptPkts
--   usrPPPBundleRxNonEncryptPkts
--   usrPPPBundleRxTotalOrigBytes
--   usrPPPBundleRxTotalLineBytes
usrPPPBundleTable   OBJECT-TYPE
     SYNTAX    SEQUENCE OF UsrPPPBundleEntry
     MAX-ACCESS    not-accessible
     STATUS        current
     DESCRIPTION
         "Table containing the Bundle parameters and
         statistics for the local PPP entity."
::= { usrPPPMl 1 }
    usrPPPBundleEntry   OBJECT-TYPE
         SYNTAX    UsrPPPBundleEntry
         MAX-ACCESS    not-accessible
         STATUS        current
         DESCRIPTION
             "Status information for the PPP bundle."
         INDEX     { usrPPPBundleInstance }
    ::= { usrPPPBundleTable 1 }
        UsrPPPBundleEntry ::= SEQUENCE {
                 usrPPPBundleInstance           Integer32,
                 usrPPPBundleOperStatus         INTEGER,
                 usrPPPBundleUserProfile        UsrUserName,
                 usrPPPBundleActiveLinks        Integer32,
                 usrPPPBundleLocalMMRU          Integer32,
                 usrPPPBundleRemoteMMRU         Integer32,
                 usrPPPBundleLocalEndptClass    INTEGER,
                 usrPPPBundleLocalEndptLength   Integer32,
                 usrPPPBundleLocalEndptID       OCTET STRING,
                 usrPPPBundleRemoteEndptClass   INTEGER,
                 usrPPPBundleRemoteEndptLength  Integer32,
                 usrPPPBundleRemoteEndptID      OCTET STRING,
                 usrPPPBundleTxTotalPkts        Counter32,
                 usrPPPBundleTxCompPkts         Counter32,
                 usrPPPBundleTxNonCompPkts      Counter32,
                 usrPPPBundleTxTotalOrigBytes   Counter32,
                 usrPPPBundleTxTotalLineBytes   Counter32,
                 usrPPPBundleRxBadHeaders       Counter32,
                 usrPPPBundleRxTotalPkts        Counter32,
                 usrPPPBundleRxCompPkts         Counter32,
                 usrPPPBundleRxNonCompPkts      Counter32,
                 usrPPPBundleRxTotalOrigBytes   Counter32,
                 usrPPPBundleRxTotalLineBytes   Counter32,
                 usrPPPBundleTxEncryptPkts      Counter32,
                 usrPPPBundleTxNonEncryptPkts   Counter32,
                 usrPPPBundleRxEncryptPkts      Counter32,
                 usrPPPBundleRxNonEncryptPkts   Counter32
                }
usrPPPBundleInstance   OBJECT-TYPE
    SYNTAX    Integer32
    MAX-ACCESS    read-only
    STATUS        current
    DESCRIPTION
         "The unique identifier of the instance of PPP
         bundle to which this entry corresponds."
::= { usrPPPBundleEntry 1 }
usrPPPBundleOperStatus   OBJECT-TYPE
    SYNTAX    INTEGER {opened(1), not-opened(2)}
    MAX-ACCESS    read-only
    STATUS        current
    DESCRIPTION
         "The operational status of the IP network
         protocol. If the value of this object is up
         then the finite state machine for the IP
         network protocol has reached the Opened state."
::= { usrPPPBundleEntry 2 }
usrPPPBundleUserProfile   OBJECT-TYPE
    SYNTAX    UsrUserName
    MAX-ACCESS    read-only
    STATUS        current
    DESCRIPTION
         "The name of the User Profile that is being used
         to contain the characteristics for this session.
         The value of this object is meaningful only when
         the link has reached the open state
         (usrPPPBundleOperStatus is up)."
::= { usrPPPBundleEntry 3 }
usrPPPBundleActiveLinks   OBJECT-TYPE
    SYNTAX    Integer32(1..2147483647)
    MAX-ACCESS    read-only
    STATUS        current
    DESCRIPTION
         "The current number of links active for this
         bundle. This count will be incremented when the
         authentication control protocol for a new link
         has reached the open state (usrPPPAuthOperStatus
         is up). This count will be decremented when the
         link is in a state where it can no longer pass
         any application data packets."
::= { usrPPPBundleEntry 4 }
usrPPPBundleLocalMMRU   OBJECT-TYPE
    SYNTAX    Integer32(1..2147483647)
    MAX-ACCESS    read-only
    STATUS        current
    DESCRIPTION
         "The current value of the MMRU for the local PPP
         Entity. This value is the MMRU that the remote
         entity is using when sending packets to the
         local PPP entity. The value of this object is
         meaningful only when the link has reached the
         open state (usrPPPBundleOperStatus is up)."
::= { usrPPPBundleEntry 5 }
usrPPPBundleRemoteMMRU   OBJECT-TYPE
    SYNTAX    Integer32(1..2147483647)
    MAX-ACCESS    read-only
    STATUS        current
    DESCRIPTION
         "The current value of the MMRU for the remote
         PPP Entity. This value is the MMRU that the
         local entity is using when sending packets to
         the remote PPP entity. The value of this object
         is meaningful only when the link has reached
         the open state (usrPPPBundleOperStatus is up)."
::= { usrPPPBundleEntry 6 }
usrPPPBundleLocalEndptClass   OBJECT-TYPE
    SYNTAX    INTEGER {
                     nullClass(1),
                     locallyAssignedAddress(2),
                     ipAddress(3),
                     ieeeMacAddress(4),
                     pppMagicNumberBlock(5),
                     networkDirNumber(6)
                    }
    MAX-ACCESS    read-only
    STATUS        current
    DESCRIPTION
         "The current value of the local Endpoint
         Descriminator Class. This value indicates the type
         of address being used as the identifier. The value
         of this object is meaningful only when the link has
         reached the open state (usrPPPBundleOperStatus is
         up)."
::= { usrPPPBundleEntry 7 }
usrPPPBundleLocalEndptLength   OBJECT-TYPE
    SYNTAX    Integer32(0..20)
    MAX-ACCESS    read-only
    STATUS        current
    DESCRIPTION
         "The maximum length of the local Endpoint
         Descriminator Address. The value of this object is
         meaningful only when the link has reached the open
         state (usrPPPBundleOperStatus is up)."
::= { usrPPPBundleEntry 8 }
usrPPPBundleLocalEndptID   OBJECT-TYPE
    SYNTAX    OCTET STRING (SIZE(20))
    MAX-ACCESS    read-only
    STATUS        current
    DESCRIPTION
         "The value of the local Endpoint Descriminator
         Address. The value of this object is meaningful
         only when the link has reached the open state
         (usrPPPBundleOperStatus is up)."
::= { usrPPPBundleEntry 9 }
usrPPPBundleRemoteEndptClass   OBJECT-TYPE
    SYNTAX    INTEGER {
                     nullClass(1),
                     locallyAssignedAddress(2),
                     ipAddress(3),
                     ieeeMacAddress(4),
                     pppMagicNumberBlock(5),
                     networkDirNumber(6)
                    }
    MAX-ACCESS    read-only
    STATUS        current
    DESCRIPTION
         "The current value of the remote Endpoint
         Descriminator Class. This value indicates the type
         of address being used as the identifier. The value
         of this object is meaningful only when the link has
         reached the open state (usrPPPBundleOperStatus is
         up)."
::= { usrPPPBundleEntry 10 }
usrPPPBundleRemoteEndptLength   OBJECT-TYPE
    SYNTAX    Integer32(0..20)
    MAX-ACCESS    read-only
    STATUS        current
    DESCRIPTION
         "The maximum length of the remote Endpoint
         Descriminator Address. The value of this object is
         meaningful only when the link has reached the open
         state (usrPPPBundleOperStatus is up)."
::= { usrPPPBundleEntry 11 }
usrPPPBundleRemoteEndptID   OBJECT-TYPE
    SYNTAX    OCTET STRING (SIZE(20))
    MAX-ACCESS    read-only
    STATUS        current
    DESCRIPTION
         "The value of the remote Endpoint Descriminator
         Address. The value of this object is meaningful
         only when the link has reached the open state
         (usrPPPBundleOperStatus is up)."
::= { usrPPPBundleEntry 12 }
usrPPPBundleTxTotalPkts   OBJECT-TYPE
    SYNTAX    Counter32
    MAX-ACCESS    read-only
    STATUS        current
    DESCRIPTION
        "The total number of packets received from an upper
         layer application for transmission over this bundle.
         The value of this object is meaningful only when the
         link has reached the open state
         (usrPPPBundleOperStatus is up)."
::= { usrPPPBundleEntry 13 }
usrPPPBundleTxCompPkts   OBJECT-TYPE
    SYNTAX    Counter32
    MAX-ACCESS    read-only
    STATUS        current
    DESCRIPTION
         "The total number of packets received from an upper
         layer application for transmission over this bundle
         that were compressed by the PPP application before
         handing the packet (or fragments) down to the lower
         layer application. The value of this object is
         meaningful only when the link has reached the open
         state (usrPPPBundleOperStatus is up). Note that this
         counter only represents packets that were compressed
         over the BUNDLE (not links). If compression occurred
         after the packet was fragmented (multilink), those
         counters can be found at the link level."
::= { usrPPPBundleEntry 14 }
usrPPPBundleTxNonCompPkts   OBJECT-TYPE
    SYNTAX    Counter32
    MAX-ACCESS    read-only
    STATUS        current
    DESCRIPTION
         "The total number of packets received from an upper
         layer application for transmission over this bundle
         that were NOT compressed by the PPP application before
         handing the packet (or fragments) down to the lower
         layer application. The value of this object is
         meaningful only when the link has reached the open
         state (usrPPPBundleOperStatus is up). Note that this
         counter only represents packets that were candidates
         for compression over the BUNDLE (not links). If
         link compression was enabled (multilink), the non-
         compressed packet counters can be found at the link
         level."
::= { usrPPPBundleEntry 15 }
usrPPPBundleTxTotalOrigBytes   OBJECT-TYPE
    SYNTAX    Counter32
    MAX-ACCESS    read-only
    STATUS        current
    DESCRIPTION
         "The total number of bytes received from an upper
         layer application for transmission over this bundle.
         This counter represents all data handed down to the
         PPP application BEFORE compression takes place.
         The value of this object is meaningful only when the
         link has reached the open state
         (usrPPPBundleOperStatus is up)."
::= { usrPPPBundleEntry 16 }
usrPPPBundleTxTotalLineBytes   OBJECT-TYPE
    SYNTAX    Counter32
    MAX-ACCESS    read-only
    STATUS        current
    DESCRIPTION
         "The total number of bytes that sent to a lower layer
         application for transmission over this bundle.  This
         counter represents all data to be handed down to
         the lower layer application AFTER compression takes
         place. The value of this object is meaningful only
         when the link has reached the open state
         (usrPPPBundleOperStatus is up)."
::= { usrPPPBundleEntry 17 }
usrPPPBundleRxBadHeaders   OBJECT-TYPE
    SYNTAX    Counter32
    MAX-ACCESS    read-only
    STATUS        current
    DESCRIPTION
         "The number of packets received with an
         incorrect PPP Header (Address, Control,
         or PID Field)."
::= { usrPPPBundleEntry 18 }
usrPPPBundleRxTotalPkts   OBJECT-TYPE
    SYNTAX    Counter32
    MAX-ACCESS    read-only
    STATUS        current
    DESCRIPTION
         "The total number of packets received from a lower
         layer application over this bundle. The value of
         this object is meaningful only when the link has
         reached the open state
         (usrPPPBundleOperStatus is up)."
::= { usrPPPBundleEntry 19 }
usrPPPBundleRxCompPkts   OBJECT-TYPE
    SYNTAX    Counter32
    MAX-ACCESS    read-only
    STATUS        current
    DESCRIPTION
         "The total number of packets received from a lower
         layer application over this bundle that were
         decompressed by the PPP application before handing
         the packet to the upper layer application. The value
         of this object is meaningful only when the link has
         reached the open state (usrPPPBundleOperStatus is up).
         Note that this counter only represents packets that
         were decompressed over the BUNDLE (not links). If
         decompression occurred before the packet was
         reassembled (multilink), those counters can be found
         at the link level."
::= { usrPPPBundleEntry 20 }
usrPPPBundleRxNonCompPkts   OBJECT-TYPE
    SYNTAX    Counter32
    MAX-ACCESS    read-only
    STATUS        current
    DESCRIPTION
         "The total number of packets received from a lower
         layer application over this bundle that were NOT
         decompressed by the PPP application before
         handing the packet to the upper layer application.
         The value of this object is meaningful only when
         the link has reached the open state
         (usrPPPBundleOperStatus is up). Note that this
         counter only represents packets that were candidates
         for decompression over the BUNDLE (not links). If
         link (de)compression was enabled (multilink), the non-
         compressed frame counters can be found at the link
         level."
::= { usrPPPBundleEntry 21 }
usrPPPBundleRxTotalOrigBytes   OBJECT-TYPE
    SYNTAX    Counter32
    MAX-ACCESS    read-only
    STATUS        current
    DESCRIPTION
         "The total number of bytes that are to be handed up
         to an upper layer application over this bundle. This
         counter represents all data to be handed up AFTER
         decompression and reassembly takes place. The value
         of this object is meaningful only when the link has
         reached the open state
         (usrPPPBundleOperStatus is up)."
::= { usrPPPBundleEntry 22 }
usrPPPBundleRxTotalLineBytes   OBJECT-TYPE
    SYNTAX    Counter32
    MAX-ACCESS    read-only
    STATUS        current
    DESCRIPTION
         "The total number of bytes received from a lower
         layer application over this bundle.  This
         counter represents all data received BEFORE
         decompression or reassembly takes place. The value
         of this object is meaningful only when the link has
         reached the open state
         (usrPPPBundleOperStatus is up)."
::= { usrPPPBundleEntry 23 }
usrPPPBundleTxEncryptPkts   OBJECT-TYPE
    SYNTAX    Counter32
    MAX-ACCESS    read-only
    STATUS        current
    DESCRIPTION
         "The total number of packets received from an upper
         layer application for transmission over this bundle
         that were encrypted by the PPP application before
         handing the packet (or fragments) down to the lower
         layer application. The value of this object is
         meaningful only when the link has reached the open
         state (usrPPPBundleOperStatus is up). Note that this
         counter only represents packets that were encrypted
         over the BUNDLE (not links). If encryption occurred
         after the packet was fragmented (multilink), those
         counters can be found at the link level."
::= { usrPPPBundleEntry 24 }
usrPPPBundleTxNonEncryptPkts   OBJECT-TYPE
    SYNTAX    Counter32
    MAX-ACCESS    read-only
    STATUS        current
    DESCRIPTION
         "The total number of packets received from an upper
         layer application for transmission over this bundle
         that were NOT encrypted by the PPP application before
         handing the packet (or fragments) down to the lower
         layer application. The value of this object is
         meaningful only when the link has reached the open
         state (usrPPPBundleOperStatus is up). Note that this
         counter only represents packets that were candidates
         for encryption over the BUNDLE (not links). If
         link encryption was enabled (multilink), the non-
         encrypted packet counters can be found at the link
         level."
::= { usrPPPBundleEntry 25 }
usrPPPBundleRxEncryptPkts   OBJECT-TYPE
    SYNTAX    Counter32
    MAX-ACCESS    read-only
    STATUS        current
    DESCRIPTION
         "The total number of packets received from a lower
         layer application over this bundle that were
         decrypted by the PPP application before handing
         the packet to the upper layer application. The value
         of this object is meaningful only when the link has
         reached the open state (usrPPPBundleOperStatus is up).
         Note that this counter only represents packets that
         were decrypted over the BUNDLE (not links). If
         decryption occurred before the packet was
         reassembled (multilink), those counters can be found
         at the link level."
::= { usrPPPBundleEntry 26 }
usrPPPBundleRxNonEncryptPkts   OBJECT-TYPE
    SYNTAX    Counter32
    MAX-ACCESS    read-only
    STATUS        current
    DESCRIPTION
         "The total number of packets received from a lower
         layer application over this bundle that were NOT
         decrypted by the PPP application before
         handing the packet to the upper layer application.
         The value of this object is meaningful only when
         the link has reached the open state
         (usrPPPBundleOperStatus is up). Note that this
         counter only represents packets that were candidates
         for decryption over the BUNDLE (not links). If
         link decryption was enabled (multilink), the non-
         encrypted frame counters can be found at the link
         level."
::= { usrPPPBundleEntry 27 }
--
-- The PPP IP NCP Group.
--
-- The following object reflect the values of the option
-- parameters used in the PPP IP Control Protocol
--   usrPPPIpLocalToRemoteCompressionProtocol
--   usrPPPIpRemoteToLocalCompressionProtocol
--   usrPPPIpRemoteMaxSlotId
--   usrPPPIpLocalMaxSlotId
--   usrPPPIpLocalIpAddress
--   usrPPPIpRemoteIpAddress
-- These values are not available until after the PPP Option
-- negotiation has completed, which is indicated by the link
-- reaching the open state (i.e., usrPPPIpOperStatus is set to
-- opened).
--
-- Therefore, when usrPPPIpOperStatus is not opened
-- the contents of these objects is undefined. The value
-- returned when accessing the objects is an implementation
-- dependent issue.
usrPPPIpTable   OBJECT-TYPE
    SYNTAX    SEQUENCE OF UsrPPPIpEntry
    MAX-ACCESS    not-accessible
    STATUS        current
    DESCRIPTION
         "Table containing the IP parameters and
         statistics for the local PPP entity."
::= { usrPPPMl 2 }
    usrPPPIpEntry   OBJECT-TYPE
        SYNTAX    UsrPPPIpEntry
        MAX-ACCESS    not-accessible
        STATUS        current
        DESCRIPTION
             "IPCP status information for the PPP bundle."
         INDEX     { usrPPPBundleInstance }
    ::= { usrPPPIpTable 1 }
        UsrPPPIpEntry ::= SEQUENCE {
             usrPPPIpOperStatus                         INTEGER,
             usrPPPIpLocalToRemoteCompressionProtocol   INTEGER,
             usrPPPIpRemoteToLocalCompressionProtocol   INTEGER,
             usrPPPIpRemoteMaxSlotId                    Integer32,
             usrPPPIpLocalMaxSlotId                     Integer32,
             usrPPPIpLocalIpAddress                     IpAddress,
             usrPPPIpRemoteIpAddress                    IpAddress
}
usrPPPIpOperStatus   OBJECT-TYPE
    SYNTAX    INTEGER {opened(1), not-opened(2)}
    MAX-ACCESS    read-only
    STATUS        current
    DESCRIPTION
         "The operational status of the IP network
         protocol. If the value of this object is up
         then the finite state machine for the IP
         network protocol has reached the Opened state."
::= { usrPPPIpEntry 1 }
usrPPPIpLocalToRemoteCompressionProtocol   OBJECT-TYPE
    SYNTAX    INTEGER {
                     none(1),
                     vj-tcp(2)
                    }
    MAX-ACCESS    read-only
    STATUS        current
    DESCRIPTION
         "The IP compression protocol that the local
         PPP-IP entity uses when sending packets to the
         remote PPP-IP entity. The value of this object
         is meaningful only when the link has reached
         the open state (usrPPPIpOperStatus is opened)."
::= { usrPPPIpEntry 2 }
usrPPPIpRemoteToLocalCompressionProtocol   OBJECT-TYPE
    SYNTAX    INTEGER {
                     none(1),
                     vj-tcp(2)
                    }
    MAX-ACCESS    read-only
    STATUS        current
    DESCRIPTION
         "The IP compression protocol that the remote
         PPP-IP entity uses when sending packets to the
         local PPP-IP entity. The value of this object
         is meaningful only when the link has reached
         the open state (usrPPPIpOperStatus is opened)."
::= { usrPPPIpEntry 3 }
usrPPPIpRemoteMaxSlotId   OBJECT-TYPE
    SYNTAX    Integer32(0..255)
    MAX-ACCESS    read-only
    STATUS        current
    DESCRIPTION
         "The Max-Slot-Id parameter that the remote node
         has advertised and that is in use on the link.
         If vj-tcp header compression is not in use on
         the link then the value of this object shall be
         0. The value of this object is meaningful only
         when the link has reached the open state
         (usrPPPIpOperStatus is opened)."
::= { usrPPPIpEntry 4 }
usrPPPIpLocalMaxSlotId   OBJECT-TYPE
    SYNTAX    Integer32(0..255)
    MAX-ACCESS    read-only
    STATUS        current
    DESCRIPTION
         "The Max-Slot-Id parameter that the local node
         has advertised and that is in use on the link.
         If vj-tcp header compression is not in use on
         the link then the value of this object shall be
         0. The value of this object is meaningful only
         when the link has reached the open state
         (usrPPPIpOperStatus is opened)."
::= { usrPPPIpEntry 5 }
usrPPPIpLocalIpAddress    OBJECT-TYPE
    SYNTAX    IpAddress
    MAX-ACCESS    read-only
    STATUS        current
    DESCRIPTION
         "The IP Address that the local node was either
         configured for or assigned by the remote node.
         The value of this object is meaningful only
         when the link has reached the open state
         (usrPPPIpOperStatus is opened)."
::= { usrPPPIpEntry 6 }
usrPPPIpRemoteIpAddress    OBJECT-TYPE
    SYNTAX    IpAddress
    MAX-ACCESS    read-only
    STATUS        current
    DESCRIPTION
         "The IP Address that the remote node supplied
         to the local node during link negotiation.
         The value of this object is meaningful only
         when the link has reached the open state
         (usrPPPIpOperStatus is opened)."
::= { usrPPPIpEntry 7 }
--
-- The PPP IPX NCP Group.
--
-- The following object reflect the values of the option
-- parameters used in the PPP IPX Control Protocol
--   usrPPPIpxLocalIpxNetAddress
--   usrPPPIpxRemoteIpxNetAddress
--   usrPPPIpxLocalIpxNodeAddress
--   usrPPPIpxRemoteIpxNodeAddress
-- These values are not available until after the PPP Option
-- negotiation has completed, which is indicated by the link
-- reaching the open state (i.e., usrPPPIpxOperStatus is set to
-- opened).
--
-- Therefore, when usrPPPIpxOperStatus is not opened
-- the contents of these objects is undefined. The value
-- returned when accessing the objects is an implementation
-- dependent issue.
usrPPPIpxTable  OBJECT-TYPE
    SYNTAX    SEQUENCE OF UsrPPPIpxEntry
    MAX-ACCESS    not-accessible
    STATUS        current
    DESCRIPTION
         "Table containing the IPX parameters and
         statistics for the local PPP entity."
::= { usrPPPMl 3 }
    usrPPPIpxEntry  OBJECT-TYPE
        SYNTAX    UsrPPPIpxEntry
        MAX-ACCESS    not-accessible
        STATUS        current
        DESCRIPTION
             "IPXCP status information for the PPP bundle."
         INDEX     { usrPPPBundleInstance }
    ::= { usrPPPIpxTable 1 }
            UsrPPPIpxEntry ::= SEQUENCE {
                 usrPPPIpxOperStatus            INTEGER,
                 usrPPPIpxLocalIpxNetAddress    IpxAddress,
                 usrPPPIpxRemoteIpxNetAddress   IpxAddress,
                 usrPPPIpxLocalIpxNodeAddress   MacAddress,
                 usrPPPIpxRemoteIpxNodeAddress  MacAddress
                }
usrPPPIpxOperStatus   OBJECT-TYPE
    SYNTAX    INTEGER {opened(1), not-opened(2)}
    MAX-ACCESS    read-only
    STATUS        current
    DESCRIPTION
         "The operational status of the IPX network
         protocol. If the value of this object is up
         then the finite state machine for the IPX
         network protocol has reached the Opened state."
::= { usrPPPIpxEntry 1 }
usrPPPIpxLocalIpxNetAddress    OBJECT-TYPE
    SYNTAX    IpxAddress
    MAX-ACCESS    read-only
    STATUS        current
    DESCRIPTION
         "The IPX Network Address that the local node was
         either configured for or assigned by the remote
         node. The value of this object is meaningful
         only when the link has reached the open state
         (usrPPPIpxOperStatus is opened)."
::= { usrPPPIpxEntry 2 }
usrPPPIpxRemoteIpxNetAddress    OBJECT-TYPE
    SYNTAX    IpxAddress
    MAX-ACCESS    read-only
    STATUS        current
    DESCRIPTION
         "The IPX Network Address that the remote node
         supplied to the local node during link negotiation.
         The value of this object is meaningful only
         when the link has reached the open state
         (usrPPPIpxOperStatus is opened)."
::= { usrPPPIpxEntry 3 }
usrPPPIpxLocalIpxNodeAddress    OBJECT-TYPE
    SYNTAX    MacAddress
    MAX-ACCESS    read-only
    STATUS        current
    DESCRIPTION
         "The IPX Node Address that the local node was
         either configured for or assigned by the remote
         node. The value of this object is meaningful
         only when the link has reached the open state
         (usrPPPIpxOperStatus is opened)."
::= { usrPPPIpxEntry 4 }
usrPPPIpxRemoteIpxNodeAddress    OBJECT-TYPE
    SYNTAX    MacAddress
    MAX-ACCESS    read-only
    STATUS        current
    DESCRIPTION
         "The IPX Node Address that the remote node
         supplied to the local node during link negotiation.
         The value of this object is meaningful only
         when the link has reached the open state
         (usrPPPIpxOperStatus is opened)."
::= { usrPPPIpxEntry 5 }
--
-- The PPP AppleTalk NCP Group.
--
-- The following object reflect the values of the option
-- parameters used in the PPP AppleTalk Control Protocol
--   usrPPPAtLocalAtNetAddress
--   usrPPPAtRemoteAtNetAddress
--   usrPPPAtLocalAtNodeAddress
--   usrPPPAtRemoteAtNodeAddress
-- These values are not available until after the PPP Option
-- negotiation has completed, which is indicated by the link
-- reaching the open state (i.e., usrPPPAtOperStatus is set to
-- opened).
--
-- Therefore, when usrPPPAtOperStatus is not opened
-- the contents of these objects is undefined. The value
-- returned when accessing the objects is an implementation
-- dependent issue.
usrPPPAtTable  OBJECT-TYPE
    SYNTAX    SEQUENCE OF UsrPPPAtEntry
    MAX-ACCESS    not-accessible
    STATUS        current
    DESCRIPTION
         "Table containing the AppleTalk parameters and
         statistics for the local PPP entity."
::= { usrPPPMl 4 }
    usrPPPAtEntry  OBJECT-TYPE
        SYNTAX    UsrPPPAtEntry
        MAX-ACCESS    not-accessible
        STATUS        current
        DESCRIPTION
             "ATCP status information for the PPP bundle."
         INDEX     { usrPPPBundleInstance }
    ::= { usrPPPAtTable 1 }
        UsrPPPAtEntry ::= SEQUENCE {
             usrPPPAtOperStatus         INTEGER,
             usrPPPAtLocalAtNetAddress  Integer32,
             usrPPPAtRemoteAtNetAddress Integer32,
             usrPPPAtLocalAtNodeAddress Integer32,
             usrPPPAtRemoteAtNodeAddress Integer32
}
usrPPPAtOperStatus   OBJECT-TYPE
    SYNTAX    INTEGER {opened(1), not-opened(2)}
    MAX-ACCESS    read-only
    STATUS        current
    DESCRIPTION
         "The operational status of the AppleTalk network
         protocol. If the value of this object is up
         then the finite state machine for the AppleTalk
         network protocol has reached the Opened state."
    ::= { usrPPPAtEntry 1 }
usrPPPAtLocalAtNetAddress    OBJECT-TYPE
    SYNTAX    Integer32
    MAX-ACCESS    read-only
    STATUS        current
    DESCRIPTION
         "The AppleTalk Network Address that the local node
         was either configured for or assigned by the remote
         node. The value of this object is meaningful
         only when the link has reached the open state
         (usrPPPAtOperStatus is opened)."
::= { usrPPPAtEntry 2 }
usrPPPAtRemoteAtNetAddress    OBJECT-TYPE
    SYNTAX    Integer32
    MAX-ACCESS    read-only
    STATUS        current
    DESCRIPTION
         "The AppleTalk Network Address that the remote node
         supplied to the local node during link negotiation.
         The value of this object is meaningful only
         when the link has reached the open state
         (usrPPPAtOperStatus is opened)."
::= { usrPPPAtEntry 3 }
usrPPPAtLocalAtNodeAddress    OBJECT-TYPE
    SYNTAX    Integer32
    MAX-ACCESS    read-only
    STATUS        current
    DESCRIPTION
         "The AppleTalk Node Address that the local node was
         either configured for or assigned by the remote
         node. The value of this object is meaningful
         only when the link has reached the open state
         (usrPPPAtOperStatus is opened)."
::= { usrPPPAtEntry 4 }
usrPPPAtRemoteAtNodeAddress    OBJECT-TYPE
    SYNTAX    Integer32
    MAX-ACCESS    read-only
    STATUS        current
    DESCRIPTION
         "The AppleTalk Node Address that the remote node
         supplied to the local node during link negotiation.
         The value of this object is meaningful only
         when the link has reached the open state
         (usrPPPAtOperStatus is opened)."
::= { usrPPPAtEntry 5 }
--
-- The PPP Bridge NCP Group.
--
-- The following object reflect the values of the option
-- parameters used in the PPP Link Control Protocol
--   usrPPPBridgeLocalToRemoteTinygramCompression
--   usrPPPBridgeRemoteToLocalTinygramCompression
--   usrPPPBridgeLocalToRemoteLanId
--   usrPPPBridgeRemoteToLocalLanId
--   usrPPPBridgeMacType
--
-- These values are not available until after the PPP Option
-- negotiation has completed, which is indicated by the link
-- reaching the open state (i.e. usrPPPBridgeOperStatus is set to
-- opened).
--
-- Therefore, when usrPPPBridgeOperStatus is not opened
-- the contents of these objects is undefined. The value
-- returned when accessing the objects is an implementation
-- dependent issue.
usrPPPBridgeTable   OBJECT-TYPE
    SYNTAX    SEQUENCE OF UsrPPPBridgeEntry
    MAX-ACCESS    not-accessible
    STATUS        current
    DESCRIPTION
         "Table containing the parameters and statistics
         for the local PPP entity that are related to
         the operation of Bridging over the PPP."
::= { usrPPPMl 5 }
    usrPPPBridgeEntry   OBJECT-TYPE
        SYNTAX    UsrPPPBridgeEntry
        MAX-ACCESS    not-accessible
        STATUS        current
        DESCRIPTION
             "Bridging information for a particular PPP
             link."
         INDEX     { usrPPPBundleInstance }
    ::= { usrPPPBridgeTable 1 }
        UsrPPPBridgeEntry ::= SEQUENCE {
             usrPPPBridgeOperStatus                         INTEGER,
             usrPPPBridgeLocalToRemoteTinygramCompression   INTEGER,
             usrPPPBridgeRemoteToLocalTinygramCompression   INTEGER,
             usrPPPBridgeLocalToRemoteLanId                 INTEGER,
             usrPPPBridgeRemoteToLocalLanId                 INTEGER,
             usrPPPBridgeMacType                            INTEGER
}
usrPPPBridgeOperStatus   OBJECT-TYPE
    SYNTAX    INTEGER {opened(1), not-opened(2)}
    MAX-ACCESS    read-only
    STATUS        current
    DESCRIPTION
         "The operational status of the Bridge network
         protocol. If the value of this object is up
         then the finite state machine for the Bridge
         network protocol has reached the Opened state."
::= { usrPPPBridgeEntry 1 }
usrPPPBridgeLocalToRemoteTinygramCompression   OBJECT-TYPE
    SYNTAX    INTEGER { true(1), false(2) }
    MAX-ACCESS    read-only
    STATUS        current
    DESCRIPTION
         "Indicates whether the local node will perform
         Tinygram Compression when sending packets to
         the remote entity. If false then the local
         entity will not perform Tinygram Compression.
         If true then the local entity will perform
         Tinygram Compression. The value of this object
         is meaningful only when the link has reached
         the open state (usrPPPBridgeOperStatus is
         opened)."
    REFERENCE
         "Section 6.7, Tinygram Compression Option, of
         RFC1220"
::= { usrPPPBridgeEntry 2 }
usrPPPBridgeRemoteToLocalTinygramCompression   OBJECT-TYPE
    SYNTAX    INTEGER { true(1), false(2) }
    MAX-ACCESS    read-only
    STATUS        current
    DESCRIPTION
         "If false then the remote entity is not
         expected to perform Tinygram Compression. If
         true then the remote entity is expected to
         perform Tinygram Compression. The value of this
         object is meaningful only when the link has
         reached the open state (usrPPPBridgeOperStatus is
         opened)."
     REFERENCE
         "Section 6.7, Tinygram Compression Option, of
         RFC1220"
::= { usrPPPBridgeEntry 3 }
usrPPPBridgeLocalToRemoteLanId   OBJECT-TYPE
    SYNTAX    INTEGER { true(1), false(2) }
    MAX-ACCESS    read-only
    STATUS        current
    DESCRIPTION
         "Indicates whether the local node will include
         the LAN Identification field in transmitted
         packets or not. If false then the local node
         will not transmit this field, true means
         that the field will be transmitted. The value
         of this object is meaningful only when the link
         has reached the open state (usrPPPBridgeOperStatus
         is opened)."
     REFERENCE
         "Section 6.8, LAN Identification Option, of
         RFC1220"
::= { usrPPPBridgeEntry 4 }
usrPPPBridgeRemoteToLocalLanId   OBJECT-TYPE
    SYNTAX    INTEGER { true(1), false(2) }
    MAX-ACCESS    read-only
    STATUS        current
    DESCRIPTION
         "Indicates whether the remote node has
         indicated that it will include the LAN
         Identification field in transmitted packets or
         not. If false then the field will not be
         transmitted, if true then the field will be
         transmitted. The value of this object is
         meaningful only when the link has reached the
         open state (usrPPPBridgeOperStatus is opened)."
     REFERENCE
         "Section 6.8, LAN Identification Option, of
         RFC1220"
::= { usrPPPBridgeEntry 5 }
usrPPPBridgeMacType   OBJECT-TYPE
    SYNTAX    INTEGER { ieee8023-ethernet(1), ieee8025(3) }
    MAX-ACCESS    read-only
    STATUS        current
    DESCRIPTION
         "Indicates which MAC framing type the local node
         will accept and process properly. The value of
         this object is meaningful only when the link has
         reached the open state (usrPPPBridgeOperStatus
         is opened)."
     REFERENCE
         "Section 6.6, MAC Type Support Selection, of
         RFC1212."
::= { usrPPPBridgeEntry 6 }
--
-- The PPP Compression CP Group.
--
-- The following object reflect the values of the option
-- parameters used in the PPP Compression Control Protocol
--   usrPPPCompOperStatus
--   usrPPPCompAlgorithm
-- These values are not available until after the PPP Option
-- negotiation has completed, which is indicated by the link
-- reaching the open state (i.e., usrPPPCompOperStatus is set to
-- opened).
--
-- Therefore, when usrPPPCompOperStatus is not opened
-- the contents of these objects is undefined. The value
-- returned when accessing the objects is an implementation
-- dependent issue.
usrPPPCompTable   OBJECT-TYPE
    SYNTAX    SEQUENCE OF UsrPPPCompEntry
    MAX-ACCESS    not-accessible
    STATUS        current
    DESCRIPTION
         "Table containing the Compression parameters and
         statistics for the local PPP entity."
::= { usrPPPMl 6 }
    usrPPPCompEntry   OBJECT-TYPE
        SYNTAX    UsrPPPCompEntry
        MAX-ACCESS    not-accessible
        STATUS        current
        DESCRIPTION
             "CCP status information for the PPP bundle."
         INDEX     { usrPPPBundleInstance }
    ::= { usrPPPCompTable 1 }
        UsrPPPCompEntry ::= SEQUENCE {
             usrPPPCompOperStatus       INTEGER,
             usrPPPCompAlgorithm        INTEGER
            }
usrPPPCompOperStatus   OBJECT-TYPE
    SYNTAX    INTEGER {opened(1), not-opened(2), paused(3)}
    MAX-ACCESS    read-only
    STATUS        current
    DESCRIPTION
         "The operational status of the Compression control
         protocol. If the value of this object is up
         then the finite state machine for the Compression
         control protocol has reached the Opened state."
::= { usrPPPCompEntry 1 }
usrPPPCompAlgorithm   OBJECT-TYPE
    SYNTAX    INTEGER {
     none(1),
     microsoft(2),
     ascend(3),
     stac(4),
     auto(5),
     deflate(6)
}
    MAX-ACCESS    read-only
    STATUS        current
    DESCRIPTION
         "The compression protocol that the local
         PPP entity uses when sending packets to the
         remote PPP entity. The value of this object
         is meaningful only when the link has reached
         the open state (usrPPPCompOperStatus is opened)."
::= { usrPPPCompEntry 2 }
--
-- The PPP Encryption Group.
--
-- The following object reflect the values of the option
-- parameters used in the PPP Encryption.  Currently only
-- MPPE is supported
--   usrPPPEncryptOperStatus
--   usrPPPEncryptAlgorithm
-- These values are not available until after the PPP Option
-- negotiation has completed, which is indicated by the link
-- reaching the open state (i.e., usrPPPEncryptOperStatus is set to
-- opened).
--
-- Therefore, when usrPPPEncryptOperStatus is not opened
-- the contents of these objects is undefined. The value
-- returned when accessing the objects is an implementation
-- dependent issue.
usrPPPEncryptTable   OBJECT-TYPE
    SYNTAX    SEQUENCE OF UsrPPPEncryptEntry
    MAX-ACCESS    not-accessible
    STATUS        current
    DESCRIPTION
         "Table containing the Encryption parameters and
         statistics for the local PPP entity."
::= { usrPPPMl 7 }
    usrPPPEncryptEntry   OBJECT-TYPE
        SYNTAX    UsrPPPEncryptEntry
        MAX-ACCESS    not-accessible
        STATUS        current
        DESCRIPTION
             "CCP (encryption) status information for the PPP bundle."
         INDEX     { usrPPPBundleInstance }
    ::= { usrPPPEncryptTable 1 }
        UsrPPPEncryptEntry ::= SEQUENCE {
             usrPPPEncryptOperStatus    INTEGER,
             usrPPPEncryptAlgorithm     INTEGER
}
usrPPPEncryptOperStatus   OBJECT-TYPE
    SYNTAX    INTEGER {opened(1), not-opened(2)}
    MAX-ACCESS    read-only
    STATUS        current
    DESCRIPTION
         "The operational status of the Compression control
         protocol when used to negotiate MPPE encryption. 
         If the value of this object is up
         then the finite state machine for the Compression
         control protocol has reached the Opened state and
         MPPE has been negotiated."
::= { usrPPPEncryptEntry 1 }
usrPPPEncryptAlgorithm   OBJECT-TYPE
    SYNTAX    INTEGER {
                     none(1),
                     microsoft40bit(2),
                     microsoft128bit(3),
                     strongest(4),
                     try(5)
                    }
    MAX-ACCESS    read-only
    STATUS        current
    DESCRIPTION
         "The encryption protocol that the local
         PPP entity uses when sending packets to the
         remote PPP entity. The value of this object
         is meaningful only when the link has reached
         the open state (usrPPPEncryptOperStatus is opened)."
::= { usrPPPEncryptEntry 2 }
usrPPPBaseProtFieldComp OBJECT-TYPE
    SYNTAX  INTEGER {
                    enabled(1),
                    disabled(0)
                    }
    MAX-ACCESS   read-write
    STATUS       current
    DESCRIPTION
          "Indicates whether PPP Protocol field compression is
           enabled/disabled."
    --CONFIGURABLE
::= { usrPPPBase 15 }
usrPPPBaseAddrFieldComp OBJECT-TYPE
    SYNTAX  INTEGER {
                    enabled(1),
                    disabled(0)
                   }
    MAX-ACCESS   read-write
    STATUS       current
    DESCRIPTION
      "Indicates whether PPP Address field compression is
       enabled/disabled."
    --CONFIGURABLE
::= { usrPPPBase 16 }
usrPPPBaseBacpBap OBJECT-TYPE
    SYNTAX  INTEGER {
                    enabled(1),
                    disabled(0)
                   }
    MAX-ACCESS   read-write
    STATUS       current
    DESCRIPTION
          "Indicates whether PPP Bacp and Bap enabled/disabled."
    --CONFIGURABLE
::= { usrPPPBase 17 }
usrPPPBaseBapPhone OBJECT-TYPE
    SYNTAX  OCTET STRING (SIZE (0..240))
    MAX-ACCESS   read-write
    STATUS       current
    DESCRIPTION
          "The hunt_group phone number to be sent in BAP call-response"
    --CONFIGURABLE
::= { usrPPPBase 18 }
usrPPPBaseMPPP OBJECT-TYPE
    SYNTAX  INTEGER {
                    enabled(1),
                    disabled(0)
                   }
    MAX-ACCESS   read-write
    STATUS       current
    DESCRIPTION
          "Indicates whether PPP Mutlilink is Enabled/Disabled"
    --CONFIGURABLE
::= { usrPPPBase 19 }
usrPPPBaseReceiveACCM OBJECT-TYPE
    SYNTAX  INTEGER {
                    enabled(1),
                    disabled(0)
                   }
    MAX-ACCESS   read-write
    STATUS       current
    DESCRIPTION
          "Indicates whether PPP receive ACCM is Enabled/Disabled"
    --CONFIGURABLE
::= { usrPPPBase 20 }
usrPPPBaseNegCallback OBJECT-TYPE
    SYNTAX  INTEGER {
                    enabled(1),
                    disabled(0)
                   }
    MAX-ACCESS   read-write
    STATUS       current
    DESCRIPTION
          "Indicates whether PPP CBCP  enabled/disabled."
    --CONFIGURABLE
::= { usrPPPBase 21 }
usrPPPSystemMRU   OBJECT-TYPE
    SYNTAX    Integer32(128..1518)
    MAX-ACCESS    read-write
    STATUS        current
    DESCRIPTION
         "The current value of the MRU for the local PPP
         Entity. This value is the MRU that the remote
         entity is using when sending packets to the
         local PPP entity." 
    DEFVAL      { 1514 }
    --CONFIGURABLE
::= { usrPPPBase 22 }
usrPPPBaseRADIUSChallengeInPAP OBJECT-TYPE
    SYNTAX  INTEGER {
                    enabled(1),
                    disabled(0)
                   }
    MAX-ACCESS   read-write
    STATUS       current
    DESCRIPTION
          "Special processing of RADIUS Challenge, if the
           authentication is PAP"
    --CONFIGURABLE
::= { usrPPPBase 23 }
usrPPPBasePapRetries OBJECT-TYPE
    SYNTAX    Integer32(0..10)
    MAX-ACCESS    read-write
    STATUS        current
    DESCRIPTION
          "Indicates the retry limit for PAP protocol. Number of times
          PAP request shall be re-transmitted before timing out"
    DEFVAL { 3 }
    --CONFIGURABLE
::= { usrPPPBase 24 }
usrPPPBaseRestartTimeout OBJECT-TYPE
    SYNTAX    Integer32(1..10)
    MAX-ACCESS    read-write
    STATUS        current
    DESCRIPTION
          "The Restart timer is used to time transmissions of
          Configure-Request and Terminate-Request packets. Expiration of
          the Restart timer causes a Timeout event, and retransmission
          of the corresponding Congigure-Request or Terminate-Request
          packet"
    DEFVAL { 3 }
    --CONFIGURABLE
::= { usrPPPBase 34 }
usrPPPBaseMaxConfigure OBJECT-TYPE
    SYNTAX    Integer32(1..20)
    MAX-ACCESS    read-write
    STATUS        current
    DESCRIPTION
          "Max-Configure indicates the number of Configure-Request
          packets sent without receiving a valid Configure-Ack,
          Configure-Nak or Configure-Reject before assuming that the
          peer is unable to repsond"
    DEFVAL { 10 }
    --CONFIGURABLE
::= { usrPPPBase 35 }
usrPPPBaseDormLCPTerm OBJECT-TYPE
    SYNTAX    INTEGER{
                     enabled(1),
                     disabled(2)
                    }
    MAX-ACCESS    read-write
    STATUS        current
    DESCRIPTION
           "A toggle switch which determines whether to send out
            LCP TERM REQ when a call is dormant"
    DEFVAL { 2 }
    --CONFIGURABLE
::= { usrPPPBase 36 }
usrPPPBaseLCPDelay OBJECT-TYPE
    SYNTAX    Integer32(0..3000)
    UNITS     "Milliseconds"
    MAX-ACCESS    read-write
    STATUS        current
    DESCRIPTION
          "Indicates the amount of time the PDSN should wait before 
          sending out an LCP Configure-Request"
    DEFVAL { 0 }
    --CONFIGURABLE
::= { usrPPPBase 37 }
usrPPPBaseLCPTermOnDereg OBJECT-TYPE
    SYNTAX  INTEGER {
                    enabled(1),
                    disabled(2)
                   }
    MAX-ACCESS   read-write
    STATUS       current
    DESCRIPTION
      "Indicates whether the PDSN should transmit an LCP Term_Req on receipt of a 
      deregistration req from the PCF"
    --CONFIGURABLE
::= { usrPPPBase 40 }
usrPPPBaseNoAuthSIP OBJECT-TYPE
    SYNTAX  INTEGER {
                    enabled(1),
                    disabled(2)
                   }
    MAX-ACCESS   read-write
    STATUS       current
    DESCRIPTION
      "Indicates whether the PDSN should allow Simple IP (SIP) calls that reject authentication
       during LCP. disabled means that the PDSN will tear down the call if the mobile node rejects 
       authentication for a simple IP call. enabled means that the PDSN will accept simple ip calls 
       from mobiles that reject authentication during LCP."
    --CONFIGURABLE
::= { usrPPPBase 43 }
END     -- End of USR-PPPML-MIB DEFINITIONS
-- ************************************************************************
--
--    usr_ppplink.mib - The CommWorks PPP Link MIB module
--
-- Author:         <Joe Kralowetz>
--
USR-PPPLINK-MIB DEFINITIONS ::= BEGIN
          IMPORTS
               OBJECT-TYPE, MODULE-IDENTITY, Integer32, Counter32
                    FROM SNMPv2-SMI
               common, UsrDisplayString
                    FROM USR-DEFINITIONS-MIB
               usrPPPBundleInstance
                    FROM USR-PPPML-MIB;
    usrPPP  MODULE-IDENTITY
            LAST-UPDATED "200208231425Z"
            ORGANIZATION "CommWorks Corporation, a 3Com Company"
            CONTACT-INFO "Customer Support"
            DESCRIPTION
                "The commWorks enterprise defined MIB objects  for PPP Link."
--          REVISION "200208231425Z"
--          DESCRIPTION "Converted to SNMPv2 and modified usrPPPLinkInterfaceName."
            ::= { common 11 }
          usrPPPLk OBJECT IDENTIFIER ::= { usrPPP 3 }
          --
          -- The PPP Link Group.
          --
          -- The following objects reflect the values of the option
          -- parameters used over the PPP Link
          --   usrPPPLinkInstance
          --   usrPPPLinkOperStatus
          --   usrPPPLinkPhysicalIndex
          --   usrPPPLinkLocalMRU
          --   usrPPPLinkRemoteMRU
          --   usrPPPLinkLocalToPeerACCMap
          --   usrPPPLinkPeerToLocalACCMap
          --   usrPPPLinkLocalToRemoteProtocolCompression
          --   usrPPPLinkRemoteToLocalProtocolCompression
          --   usrPPPLinkLocalToRemoteACCompression
          --   usrPPPLinkRemoteToLocalACCompression
          --   usrPPPLinkTxTotalFrames
          --   usrPPPLinkTxTotalBytes
          --   usrPPPLinkRxPacketTooLongs
          --   usrPPPLinkRxTotalFrames
          --   usrPPPLinkRxTotalBytes
          --
          -- These values are not available until after the PPP Option
          -- negotiation has completed, which is indicated by the link
          -- reaching the open state (i.e., ifOperStatus is set to
          -- up).
          --
          -- Therefore, when ifOperStatus is not up
          -- the contents of these objects is undefined. The value
          -- returned when accessing the objects is an implementation
          -- dependent issue.
          usrPPPLinkTable   OBJECT-TYPE
               SYNTAX       SEQUENCE OF UsrPPPLinkEntry
               MAX-ACCESS   not-accessible
               STATUS       current
               DESCRIPTION
                         "Table containing the Link parameters and
                         statistics for a local PPP entity."
               ::= { usrPPPLk 1 }
          usrPPPLinkEntry   OBJECT-TYPE
               SYNTAX       UsrPPPLinkEntry
               MAX-ACCESS   not-accessible
               STATUS       current
               DESCRIPTION
                         "Status information for a PPP link."
               INDEX     { usrPPPBundleInstance, usrPPPLinkInstance }
               ::= { usrPPPLinkTable 1 }
          UsrPPPLinkEntry ::= SEQUENCE {
               usrPPPLinkInstance
                    Integer32,
               usrPPPLinkOperStatus
                    INTEGER,
               usrPPPLinkPhysicalIndex
                    Integer32,
               usrPPPLinkInterfaceName
                    UsrDisplayString,
               usrPPPLinkLocalMRU
                    Integer32,
               usrPPPLinkRemoteMRU
                    Integer32,
               usrPPPLinkLocalToPeerACCMap
                    OCTET STRING,
               usrPPPLinkPeerToLocalACCMap
                    OCTET STRING,
               usrPPPLinkLocalToRemoteProtocolCompression
                    INTEGER,
               usrPPPLinkRemoteToLocalProtocolCompression
                    INTEGER,
               usrPPPLinkLocalToRemoteACCompression
                    INTEGER,
               usrPPPLinkRemoteToLocalACCompression
                    INTEGER,
               usrPPPLinkTxTotalFrames
                    Counter32,
               usrPPPLinkTxTotalBytes
                    Counter32,
               usrPPPLinkRxPacketTooLongs
                    Counter32,
               usrPPPLinkRxTotalFrames
                    Counter32,
               usrPPPLinkRxTotalBytes
                    Counter32
          }
          usrPPPLinkInstance   OBJECT-TYPE
               SYNTAX    Integer32
               MAX-ACCESS    read-only
               STATUS    current
               DESCRIPTION
                         "The unique identifier of the instance of PPP
                         link to which this entry corresponds."
               ::= { usrPPPLinkEntry 1 }
          usrPPPLinkOperStatus   OBJECT-TYPE
               SYNTAX    INTEGER {opened(1), not-opened(2)}
               MAX-ACCESS    read-only
               STATUS    current
               DESCRIPTION
                         "The operational status of the Link control
                         protocol. If the value of this object is up
                         then the finite state machine for the Link
                         control protocol has reached the Opened state."
               ::= { usrPPPLinkEntry 2 }
          usrPPPLinkPhysicalIndex   OBJECT-TYPE
               SYNTAX    Integer32(0..2147483647)
               MAX-ACCESS    read-only
               STATUS    current
               DESCRIPTION
                         "The value of ifIndex that identifies the
                         lower-level interface over which this PPP Link
                         is operating. This interface would usually be
                         an HDLC or RS-232 type of interface. If there
                         is no lower-layer interface element, or there
                         is no ifEntry for the element, or the element
                         can not be identified, then the value of this
                         object is 0."
               ::= { usrPPPLinkEntry 3 }
          usrPPPLinkInterfaceName   OBJECT-TYPE
               SYNTAX    UsrDisplayString (SIZE(0..32))
               MAX-ACCESS    read-only
               STATUS    current
               DESCRIPTION
                         "The value of the Name that identifies the
                         lower-level interface over which this PPP Link
                         is operating. This interface would usually be
                         an HDLC or RS-232 type of interface. If there
                         is no lower-layer interface element, or there
                         is no ifEntry for the element, or the element
                         can not be identified, then the value of this
                         object is NULL."
               ::= { usrPPPLinkEntry 4 }
          usrPPPLinkLocalMRU   OBJECT-TYPE
               SYNTAX    Integer32(1..2147483647)
               MAX-ACCESS    read-only
               STATUS    current
               DESCRIPTION
                         "The current value of the MRU for the local PPP
                         Entity. This value is the MRU that the remote
                         entity is using when sending packets to the
                         local PPP entity. The value of this object is
                         meaningful only when the link has reached the
                         open state (usrPPPLinkOperStatus is up)."
               ::= { usrPPPLinkEntry 5 }
          usrPPPLinkRemoteMRU   OBJECT-TYPE
               SYNTAX    Integer32(1..2147483647)
               MAX-ACCESS    read-only
               STATUS    current
               DESCRIPTION
                         "The current value of the MRU for the remote
                         PPP Entity. This value is the MRU that the
                         local entity is using when sending packets to
                         the remote PPP entity. The value of this object
                         is meaningful only when the link has reached
                         the open state (usrPPPLinkOperStatus is up)."
               ::= { usrPPPLinkEntry 6 }
          usrPPPLinkLocalToPeerACCMap   OBJECT-TYPE
               SYNTAX    OCTET STRING (SIZE (4))
               MAX-ACCESS    read-only
               STATUS    current
               DESCRIPTION
                         "The current value of the ACC Map used for
                         sending packets from the local PPP entity to
                         the remote PPP entity. The value of this object
                         is meaningful only when the link has reached
                         the open state (usrPPPLinkOperStatus is up)."
               ::= { usrPPPLinkEntry 7 }
          usrPPPLinkPeerToLocalACCMap   OBJECT-TYPE
               SYNTAX    OCTET STRING (SIZE (4))
               MAX-ACCESS    read-only
               STATUS    current
               DESCRIPTION
                         "The ACC Map used by the remote PPP entity when
                         transmitting packets to the local PPP entity.
                         The value of this object is meaningful only
                         when the link has reached the open state
                         (usrPPPLinkOperStatus is up)."
               ::= { usrPPPLinkEntry 8 }
          usrPPPLinkLocalToRemoteProtocolCompression
               OBJECT-TYPE
               SYNTAX    INTEGER {
                         enabled(1),
                         disabled(2)
                    }
               MAX-ACCESS    read-only
               STATUS    current
               DESCRIPTION
                         "Indicates whether the local PPP entity will
                         use Protocol Compression when transmitting
                         packets to the remote PPP entity. The value of
                         this object is meaningful only when the link
                         has reached the open state (usrPPPLinkOperStatus
                         is up)."
               ::= { usrPPPLinkEntry 9 }
          usrPPPLinkRemoteToLocalProtocolCompression
               OBJECT-TYPE
               SYNTAX    INTEGER {
                         enabled(1),
                         disabled(2)
                    }
               MAX-ACCESS    read-only
               STATUS    current
               DESCRIPTION
                         "Indicates whether the remote PPP entity will
                         use Protocol Compression when transmitting
                         packets to the local PPP entity. The value of
                         this object is meaningful only when the link
                         has reached the open state (usrPPPLinkOperStatus
                         is up)."
               ::= { usrPPPLinkEntry 10 }
          usrPPPLinkLocalToRemoteACCompression   OBJECT-TYPE
               SYNTAX    INTEGER {
                         enabled(1),
                         disabled(2)
                    }
               MAX-ACCESS    read-only
               STATUS    current
               DESCRIPTION
                         "Indicates whether the local PPP entity will
                         use Address and Control Compression when
                         transmitting packets to the remote PPP entity.
                         The value of this object is meaningful only
                         when the link has reached the open state
                         (usrPPPLinkOperStatus is up)."
               ::= { usrPPPLinkEntry 11 }
          usrPPPLinkRemoteToLocalACCompression   OBJECT-TYPE
               SYNTAX    INTEGER {
                         enabled(1),
                         disabled(2)
                    }
               MAX-ACCESS    read-only
               STATUS    current
               DESCRIPTION
                         "Indicates whether the remote PPP entity will
                         use Address and Control Compression when
                         transmitting packets to the local PPP entity.
                         The value of this object is meaningful only
                         when the link has reached the open state
                         (usrPPPLinkOperStatus is up)."
               ::= { usrPPPLinkEntry 12 }
          usrPPPLinkTxTotalFrames   OBJECT-TYPE
               SYNTAX    Counter32
               MAX-ACCESS    read-only
               STATUS    current
               DESCRIPTION
                         "The total number of frames received from the PPP
                         application for transmission over this link.
                         The value of this object is meaningful only when the
                         link has reached the open state
                         (usrPPPLinkOperStatus is up)."
               ::= { usrPPPLinkEntry 13 }
          usrPPPLinkTxTotalBytes   OBJECT-TYPE
               SYNTAX    Counter32
               MAX-ACCESS    read-only
               STATUS    current
               DESCRIPTION
                         "The total number of bytes received from the PPP
                         application for transmission over this link. The
                         value of this object is meaningful only when the
                         link has reached the open state
                         (usrPPPLinkOperStatus is up)."
               ::= { usrPPPLinkEntry 14 }
          usrPPPLinkRxPacketTooLongs   OBJECT-TYPE
               SYNTAX    Counter32
               MAX-ACCESS    read-only
               STATUS    current
               DESCRIPTION
                         "The number of received packets that have been
                         discarded because their length exceeded the
                         MRU. NOTE, packets which are longer than the
                         MRU but which are successfully received and
                         processed are NOT included in this count."
               ::= { usrPPPLinkEntry 15 }
          usrPPPLinkRxTotalFrames   OBJECT-TYPE
               SYNTAX    Counter32
               MAX-ACCESS    read-only
               STATUS    current
               DESCRIPTION
                         "The total number of frames received from a lower
                         layer application over this link. The value of
                         this object is meaningful only when the link has
                         reached the open state (usrPPPLinkOperStatus is up)."
               ::= { usrPPPLinkEntry 16 }
          usrPPPLinkRxTotalBytes   OBJECT-TYPE
               SYNTAX    Counter32
               MAX-ACCESS    read-only
               STATUS    current
               DESCRIPTION
                         "The total number of bytes received from a lower
                         layer application over this link. The value of
                         this object is meaningful only when the link has
                         reached the open state (usrPPPLinkOperStatus is
                         up)."
               ::= { usrPPPLinkEntry 17 }
          --
          -- The PPP Authentication Group.
          --
          -- The following objects reflect the values of the option
          -- parameters used in the PPP Authentication Control Protocol
          --   usrPPPAuthOperStatus
          --   usrPPPAuthLclToRemProtocol
          --   usrPPPAuthRemToLclProtocol
          usrPPPAuthTable   OBJECT-TYPE
               SYNTAX    SEQUENCE OF UsrPPPAuthEntry
               MAX-ACCESS    not-accessible
               STATUS    current
               DESCRIPTION
                         "Table containing the Authentication status
                         information for a local PPP entity."
               ::= { usrPPPLk 2 }
          usrPPPAuthEntry   OBJECT-TYPE
               SYNTAX    UsrPPPAuthEntry
               MAX-ACCESS    not-accessible
               STATUS    current
               DESCRIPTION
                         "Authentication status information for a PPP link."
               INDEX     { usrPPPBundleInstance, usrPPPLinkInstance }
               ::= { usrPPPAuthTable 1 }
          UsrPPPAuthEntry ::= SEQUENCE {
               usrPPPAuthOperStatus
                    INTEGER,
               usrPPPAuthLclToRemProtocol
                    INTEGER,
               usrPPPAuthRemToLclProtocol
                    INTEGER
          }
          usrPPPAuthOperStatus   OBJECT-TYPE
               SYNTAX    INTEGER {
                         opened(1),
                         not-opened(2)
                    }
               MAX-ACCESS    read-only
               STATUS    current
               DESCRIPTION
                         "The operational status of the Authentication control
                         protocol. If the value of this object is up
                         then the finite state machine for the Authentication
                         control protocol has reached the Opened state."
               ::= { usrPPPAuthEntry 1 }
          usrPPPAuthLclToRemProtocol OBJECT-TYPE
               SYNTAX    INTEGER {
                        none(1),
                        pap(2),
                        chap(3),
                        any(4),
                        eapMD5(5),
                        msChap(6),
                        encryptedOnly(7),
                        radiusEapProxy(8)
                    }
               MAX-ACCESS    read-only
               STATUS    current
               DESCRIPTION
                         "This is the authentication protocol that was used
                         by the local PPP entity when it authenticated the
                         local PPP entity to the remote PPP entity. The
                         value of this object is meaningful only when the
                         authentication has reached the open state
                         (usrPPPAuthOperStatus is up)."
               ::= { usrPPPAuthEntry 2 }
          usrPPPAuthRemToLclProtocol OBJECT-TYPE
               SYNTAX    INTEGER {
                        none(1),
                        pap(2),
                        chap(3),
                        any(4),
                        eapMD5(5),
                        msChap(6),
                        encryptedOnly(7),
                        radiusEapProxy(8)
                    }
               MAX-ACCESS    read-only
               STATUS    current
               DESCRIPTION
                         "This is the authentication protocol that was used
                         by the remote PPP entity when it authenticated the
                         remote PPP entity to the local PPP entity. The
                         value of this object is meaningful only when the
                         authentication has reached the open state
                         (usrPPPAuthOperStatus is up)."
               ::= { usrPPPAuthEntry 3 }
END     -- End of USR-PPPLINK-MIB DEFINITIONS
-- ************************************************************************
--
--
--	usr_ip.mib
--
-- Author:         Jim Halpin
--
USR-IP-MIB DEFINITIONS ::= BEGIN
	IMPORTS
	     Counter32, IpAddress, Integer32,
             OBJECT-TYPE, MODULE-IDENTITY
             FROM SNMPv2-SMI
             TruthValue, DisplayString
	     FROM SNMPv2-TC
             common, UsrConfigStatus, UsrNetLogicalId,
             UsrDisplayString
             FROM USR-DEFINITIONS-MIB;
   usrIp MODULE-IDENTITY
		 LAST-UPDATED "200305241530Z"
         ORGANIZATION "CommWorks Corporation, a 3Com company"
         CONTACT-INFO "Customer Support"
         DESCRIPTION    "The enterprise specific defined objects for IP"
--       REVISION       "200303241530Z"
--       DESCRIPTION    "Added new MIB Object usrIpSrcSNMPAddress"
--       REVISION       "200208151645Z"
--       DESCRIPTION    "Added new MIB object for IP networks filename"
--       REVISION       "200208231400Z"
--       DESCRIPTION "Clarify usage and labels for usrIpIeaSendUnsolicitedArp,
--          usrIpIeaForceNexthopRoute, usrIpIeaNextHopRouting,
--          usrIpSrcRouteInterfaceEnabled."
--       REVISION       "200208231400Z"
--       DESCRIPTION "Clarify usage and labels for usrIpIeaSendUnsolicitedArp,
--          usrIpIeaForceNexthopRoute, usrIpIeaNextHopRouting,
--          usrIpSrcRouteInterfaceEnabled."
--       REVISION       "200208131445Z"
--       DESCRIPTION "Modify usrIpNetRip2AuthKey"
--       REVISION       "200207261500Z"
--       DESCRIPTION "Update the description field for the MIB objects related 
--                      "to the usrIpSrcRouteTable"
--       REVISION       "200202080430Z"
--       DESCRIPTION "Merge HA and HACN into PDSN version of USR-IP-MIB so
--		             "PDSN version of MIB can manage PDSN,HA and HACN"
         ::= { common 12 }
   -- Begin managed object definitions here...
usrIpVersion OBJECT-TYPE
	SYNTAX		DisplayString
	MAX-ACCESS	read-only
	STATUS		current
	DESCRIPTION
		"The current software version of the IP Forwarder."
::= { usrIp 1 }
usrIpCFMStatusFlag OBJECT-TYPE
	SYNTAX		UsrConfigStatus
	MAX-ACCESS	read-write
	STATUS		current
	DESCRIPTION
		"This variable controls saving and loading of configuration
           information for the IP Module. The value can be SET to either 
           save(2) or load(4) by a management station; a GET following
           should return normal(1). The other values indicate if any 
           configuration operation and what type is in progress."
::= { usrIp 2 }
usrIpCfgFileName OBJECT-TYPE
	SYNTAX      DisplayString
	MAX-ACCESS  read-only
	STATUS      current
	DESCRIPTION		
		"The name of a ConfigFile to read/write  permanent database records.
		 If the value of this object is an empty string, then the
		 IP module uses the default name `@file://IPModule.cfg'. "
::= { usrIp 3 }
usrIpNetworkTable OBJECT-TYPE
	SYNTAX SEQUENCE OF UsrIpNetworkEntry
	MAX-ACCESS not-accessible
	STATUS current
	DESCRIPTION
		"The (conceptual) table of IP Networks. The objects in this table
		 are essentially read/write versions of the ipAddrTable in MIB-2.
		 These objects are defined as read/write so that they can be configured
		 by a Network Manager at the time an IP Network is added to the Netserver
		 configuration. Any attempt to modify these parameters when the network
		 is in an active state will fail."
::= { usrIp 4 }
usrIpNetworkEntry OBJECT-TYPE
	SYNTAX UsrIpNetworkEntry
	MAX-ACCESS not-accessible
	STATUS current
	DESCRIPTION
		"A (conceptual) entry for one IP Network."
	INDEX { usrIpNetId }
::= { usrIpNetworkTable 1 }
UsrIpNetworkEntry ::= SEQUENCE {
	usrIpNetId				UsrNetLogicalId,
	usrIpNetAddr				IpAddress,
	usrIpNetMask				IpAddress,
	usrIpNetBcastAddr			Integer32,
	usrIpNetReasmMaxSize			Integer32,
	usrIpNetRoutingProtocol			INTEGER,
	usrIpNetSendDefaultRoutePolicy  	INTEGER,
	usrIpNetSendRoutesPolicy 		INTEGER,
	usrIpNetSendSubnetsOnlyPolicy 	        INTEGER,
	usrIpNetAcceptDefaultRoutePolicy 	INTEGER,
	usrIpNetSilentPolicy 			INTEGER,
	usrIpNetSplitHorizonPolicy 		INTEGER,
	usrIpNetPoisonReversePolicy 		INTEGER,
	usrIpNetFlashUpdatePolicy 		INTEGER,
	usrIpNetSimpleAuthenPolicy		INTEGER,
	usrIpNetSendRipV1CompatPolicy 	        INTEGER,
	usrIpNetRcvRipV1Policy	 		INTEGER,
	usrIpNetRcvRipV2Policy	 		INTEGER,
	usrIpNetRip2AuthKey  			UsrDisplayString,
	usrIpNetReconfigNeeded                  TruthValue,
	usrIpNetRoutingMetric                   Integer32,
	usrIpNetExportMetric                    Integer32,
	usrIpNetRoutingNone                     INTEGER,
	usrIpNetRoutingRipV1			INTEGER,
	usrIpNetRoutingRipV2			INTEGER,
	usrIpNetRoutingOspf			INTEGER
	}
usrIpNetId OBJECT-TYPE
	SYNTAX		UsrNetLogicalId
	MAX-ACCESS		not-accessible
	STATUS		current
	DESCRIPTION
		"The logical identifier of the IP Network. This is the value
		 of the usrCfgNetLogicalId object in the usrCfgNetworkTable.
		 The IP forwarder returns this identifier to the Configuration
		 process in the FWD_ADD_NETWORK_RSP message. It allows management
		 applications to correlate Network Table entries with protocol
		 specific table entries."
::= { usrIpNetworkEntry 1 }
usrIpNetAddr OBJECT-TYPE
	SYNTAX  IpAddress
     MAX-ACCESS  read-only
     STATUS  current
     DESCRIPTION
		"The IP address this network has assigned to the
		 local interface."
::= { usrIpNetworkEntry 2 }
usrIpNetMask OBJECT-TYPE
     SYNTAX  IpAddress
     MAX-ACCESS  read-only
     STATUS  current
     DESCRIPTION
		"The subnet mask associated with the IP address of
           this entry.  The value of the mask is an IP
           address with all the network bits set to 1 and all
           the hosts bits set to 0."
::= { usrIpNetworkEntry 3 }
usrIpNetBcastAddr OBJECT-TYPE
     SYNTAX  Integer32 (0..1)
     MAX-ACCESS  read-write
	STATUS  current
     DESCRIPTION
          "The value of the least-significant bit in the IP
           broadcast address used for sending datagrams on
           the (logical) interface associated with the IP
           address of this entry.  For example, when the
           Internet standard all-ones broadcast address is
           used, the value will be 1.  This value applies to
           both the subnet and network broadcasts addresses
           used by the entity on this (logical) interface."
::= { usrIpNetworkEntry 4 }
usrIpNetReasmMaxSize OBJECT-TYPE
     SYNTAX  Integer32 (0..65535)
     MAX-ACCESS  read-write
     STATUS  current
     DESCRIPTION
		"The size of the largest IP datagram which this
           entity can re-assemble from incoming IP fragmented
           datagrams received on this interface."
::= { usrIpNetworkEntry 5 }
usrIpNetRoutingProtocol OBJECT-TYPE
	SYNTAX INTEGER {
			none(0),
			ripv1(1),
			ripv2(2)
		}
	MAX-ACCESS read-write
	STATUS obsolete
	DESCRIPTION
		"The routing protocol to be operated on this IP network."
::= { usrIpNetworkEntry 6 }
usrIpNetSendDefaultRoutePolicy OBJECT-TYPE
	SYNTAX	INTEGER {
		disable(0),
		enable(1)
	}
	MAX-ACCESS	read-write
	STATUS	current
	DESCRIPTION
		"Allows disabling or enabling of the send default route RIP policy.
		 This policy is enabled by default."
::= { usrIpNetworkEntry 7 }
usrIpNetSendRoutesPolicy OBJECT-TYPE
	SYNTAX	INTEGER {
		disable(0),
		enable(1)
	}
	MAX-ACCESS	read-write
	STATUS	current
	DESCRIPTION
		"Allows disabling or enabling of the send routes RIP policy.
		 This policy is enabled by default."
::= { usrIpNetworkEntry 8 }
usrIpNetSendSubnetsOnlyPolicy OBJECT-TYPE
	SYNTAX	INTEGER {
		disable(0),
		enable(1)
	}
	MAX-ACCESS	read-write
	STATUS	current
	DESCRIPTION
		"Allows disabling or enabling of the send subnets only RIP policy.
		 This policy is enabled by default."
::= { usrIpNetworkEntry 9 }
usrIpNetAcceptDefaultRoutePolicy OBJECT-TYPE
	SYNTAX	INTEGER {
		disable(0),
		enable(1)
	}
	MAX-ACCESS	read-write
	STATUS	current
	DESCRIPTION
		"Allows disabling or enabling of the accept default route RIP policy.
		 This policy is disabled by default."
::= { usrIpNetworkEntry 10 }
usrIpNetSilentPolicy OBJECT-TYPE
	SYNTAX	INTEGER {
		disable(0),
		enable(1)
	}
	MAX-ACCESS	read-write
	STATUS	current
	DESCRIPTION
		"Allows disabling or enabling of the silent policy.
		 This policy is disabled by default."
::= { usrIpNetworkEntry 11 }
usrIpNetSplitHorizonPolicy OBJECT-TYPE
	SYNTAX	INTEGER {
		disable(0),
		enable(1)
	}
	MAX-ACCESS	read-write
	STATUS	current
	DESCRIPTION
		"Allows disabling or enabling of the split horizon RIP policy.
		 This policy is enabled by default."
::= { usrIpNetworkEntry 12 }
usrIpNetPoisonReversePolicy OBJECT-TYPE
	SYNTAX	INTEGER {
		disable(0),
		enable(1)
	}
	MAX-ACCESS	read-write
	STATUS	current
	DESCRIPTION
		"Allows disabling or enabling of the poison reverse RIP policy.
	 	 This policy is enabled by default."
::= { usrIpNetworkEntry 13 }
usrIpNetFlashUpdatePolicy OBJECT-TYPE
	SYNTAX	INTEGER {
		disable(0),
		enable(1)
	}
	MAX-ACCESS	read-write
	STATUS	current
	DESCRIPTION
		"Allows disabling or enabling of the flash update RIP policy.
		 This policy is enabled by default."
::= { usrIpNetworkEntry 14 }
usrIpNetSimpleAuthenPolicy OBJECT-TYPE
	SYNTAX	INTEGER {
		disable(0),
		enable(1)
	}
	MAX-ACCESS	read-write
	STATUS	current
	DESCRIPTION
		"Allows disabling or enabling of the simple authentication RIP policy.
		 This policy is valid for RIPV2 only and is enabled by default when
		 RIPV2 is selected as the routing protocol."
::= { usrIpNetworkEntry 15 }
usrIpNetSendRipV1CompatPolicy OBJECT-TYPE
	SYNTAX	INTEGER {
		disable(0),
		enable(1)
	}
	MAX-ACCESS	read-write
	STATUS	current
	DESCRIPTION
		"Allows disabling or enabling of the send RipV1 compatible policy.
		 This policy is enabled by default."
::= { usrIpNetworkEntry 16 }
usrIpNetRcvRipV1Policy OBJECT-TYPE
	SYNTAX	INTEGER {
		disable(0),
		enable(1)
	}
	MAX-ACCESS	read-write
	STATUS	current
	DESCRIPTION
		"Allows disabling or enabling of the receive RipV1 policy.
		 This policy is enabled by default."
::= { usrIpNetworkEntry 17 }
usrIpNetRcvRipV2Policy OBJECT-TYPE
	SYNTAX	INTEGER {
		disable(0),
		enable(1)
	}
	MAX-ACCESS	read-write
	STATUS	current
	DESCRIPTION
		"Allows disabling or enabling of the receive RipV2 policy.
		 This policy is enabled by default."
::= { usrIpNetworkEntry 18 }
usrIpNetRip2AuthKey OBJECT-TYPE
	SYNTAX UsrDisplayString (SIZE(0..16))
	MAX-ACCESS read-write
	STATUS current
	DESCRIPTION
		"this variable defines the authentication key for ip rip2.  when
		 this variable is set, by default, the authentication type is also
		 set to simple."
::= { usrIpNetworkEntry 19 }
usrIpNetReconfigNeeded  OBJECT-TYPE
       SYNTAX      TruthValue
       MAX-ACCESS  read-only
       STATUS      current
       DESCRIPTION
               "This object has a value of TRUE by default. If any other
			 object in the usrIpNetworkTable has been changed since the
			 network was enabled, the value of this object becomes TRUE.
			 All object values in this table only take effect when
			 the network is enabled. This object is meant to notify 
			 the system administrator that at least one network parameter
			 has been modified and the network should be reinitialized
			 in order for the new parameter values to take effect.
			 The network can be automatically reconfigured by setting
			 the network state to 'reconfigure' in the usrCfgNetStatus
			 object of the usrCfgNetworkTable."
::= { usrIpNetworkEntry 20 }
usrIpNetRoutingMetric OBJECT-TYPE
        SYNTAX Integer32 (1..16)
        MAX-ACCESS read-write
        STATUS current
        DESCRIPTION
                "The routing metric for using this IP network."
::= { usrIpNetworkEntry 21 }
usrIpNetExportMetric OBJECT-TYPE
        SYNTAX Integer32 (0..15)
        MAX-ACCESS read-write
        STATUS current
        DESCRIPTION
                "The metric for advertising route through this IP network."
::= { usrIpNetworkEntry 22 }
usrIpNetRoutingNone OBJECT-TYPE
	SYNTAX INTEGER {
			disable(0),
			enable(1)
		}
	MAX-ACCESS read-write
	STATUS current
	DESCRIPTION
		"Specifies that no routing protocol will be operating on this 
           IP network. Only valid SET option is enable(1) since disable is
           meaningless unless a specific routing protocol is set; 
           doing this will automatically set RoutingProtocolNone to disable(0)"
::= { usrIpNetworkEntry 27 }
usrIpNetRoutingRipV1 OBJECT-TYPE
	SYNTAX INTEGER {
			disable(0),
			enable(1)
		}
	MAX-ACCESS read-write
	STATUS current
	DESCRIPTION
		"Specifies if the RIPv1 routing protocol will be operating
           or not operating on this IP network."
::= { usrIpNetworkEntry 28 }
usrIpNetRoutingRipV2 OBJECT-TYPE
	SYNTAX INTEGER {
			disable(0),
			enable(1)
		}
	MAX-ACCESS read-write
	STATUS current
	DESCRIPTION
		"Specifies if the RIPv2 routing protocol will be operating
           or not operating on this IP network."
::= { usrIpNetworkEntry 29 }
usrIpNetRoutingOspf OBJECT-TYPE
	SYNTAX INTEGER {
			disable(0),
			enable(1)
		}
	MAX-ACCESS read-write
	STATUS current
	DESCRIPTION
		"Specifies if the OSPF routing protocol will be operating
           or not operating on this IP network."
::= { usrIpNetworkEntry 30 }
usrIpAddressPoolSize	OBJECT-TYPE
	SYNTAX	Integer32 (0..254)
	MAX-ACCESS	read-write
	STATUS	obsolete
	DESCRIPTION
		"this variable denotes the size of the dynamic address assignment
		 pool.  the default size is 8. no, not olympic.  to have a size other
		 than the default, one should set the pool size to the desired number
		 before setting usrIpAddressPoolBegin."
	-- CONFIGURABLE
::= { usrIp 5 }
usrIpAddressPoolBegin	OBJECT-TYPE
	SYNTAX	IpAddress
	MAX-ACCESS read-write
	STATUS	obsolete
	DESCRIPTION
		"the variable denotes the starting ip address of the dynamic 
		 address assignment pool.  one needs to restart the system to change 
		 it once it is set."
	-- CONFIGURABLE
::= { usrIp 6 }
usrIpHostAddress	OBJECT-TYPE
	SYNTAX	IpAddress
	MAX-ACCESS read-write
	STATUS	current
	DESCRIPTION
	   "this variable shows the host ip address of the system.  it is 
	    registered automatically by the ip forwarder and is not settable
            via SNMP. In general, the host address is also the ip address of 
            the first added lan interface's ip address."
	--CONFIGURABLE
::= { usrIp 7 }
usrIpRoutesFlag OBJECT-TYPE
	SYNTAX UsrConfigStatus
	MAX-ACCESS read-write
	STATUS current
	DESCRIPTION
		"this flag triggers cfm to save/load ip static routes, good luck."
::= { usrIp 8 }
usrIpForwarding OBJECT-TYPE
     SYNTAX  INTEGER {
             forwarding(1),    -- acting as a gateway
             not-forwarding(2) -- NOT acting as a gateway
             }
	MAX-ACCESS read-write
	STATUS current
	DESCRIPTION
		"this variable mirrors the ipForwarding flag in MIB-II"
	--CONFIGURABLE
::= { usrIp 9 }
usrIpIcmp OBJECT IDENTIFIER ::= { usrIp 10 }
usrIpIcmpOutRouterAdvertise OBJECT-TYPE
     SYNTAX  Counter32
     MAX-ACCESS  read-only
     STATUS  current
     DESCRIPTION
          "The total number of ICMP Router Advertisement messages 
           that has been sent by the router.  Note this counter 
           includes all those counted by icmpOutMsgs."
::= { usrIpIcmp 1 }
usrIpIcmpInRouterAdvertise OBJECT-TYPE
     SYNTAX  Counter32
     MAX-ACCESS  read-only
     STATUS  current
     DESCRIPTION
          "The total number of ICMP Router Advertisement messages 
           that the router has received.  Note this counter 
	      includes all those counted by icmpInMsgs."
::= { usrIpIcmp 2 }
usrIpIcmpInRouterSolicit OBJECT-TYPE
     SYNTAX  Counter32
     MAX-ACCESS  read-only
     STATUS  current
     DESCRIPTION
          "The total number of ICMP Router Solicitation messages
           that has been received by the router.  Note this counter
	      includes all those counted by icmpInMsgs."
::= { usrIpIcmp 3 }
usrIpIcmpLogFlag OBJECT-TYPE
     SYNTAX  INTEGER {
             logging(1),    -- syslogging is ENABLED
             not-logging(0) -- syslogging is DISABLED
             }
	MAX-ACCESS read-write
	STATUS current
	DESCRIPTION
		"Flag indicates whether ICMP syslogging is enabled or
           or not."
	--CONFIGURABLE
::= { usrIpIcmp 4 }
usrIpIcmpRouterAdvertiseFlag OBJECT-TYPE
     SYNTAX  INTEGER {
             enable(1),    -- router advertise is ENABLED
             disable(0) -- router advertise is DISABLED
             }
	MAX-ACCESS read-write
	STATUS current
	DESCRIPTION
		"Flag indicates whether ICMP router advertisement is enabled or
           or not."
	--CONFIGURABLE
::= { usrIpIcmp 5 }
usrIpDropAllFO1 OBJECT-TYPE
     SYNTAX  INTEGER {
             enable(1),    -- dropping ip packet with FO = 1
             disable(0)    -- NOT dropping.
             }
	MAX-ACCESS read-write
	STATUS current
	DESCRIPTION
		"indicating whether ip packet with FO = 1 is to be dropped"
	--CONFIGURABLE
::= { usrIp 11 }
usrIpDropTcpFO1 OBJECT-TYPE
     SYNTAX  INTEGER {
             enable(1),   -- dropping ip packet with FO==1 AND protocol==TCP
             disable(0)   -- NOT dropping.
             }
	MAX-ACCESS read-write
	STATUS current
	DESCRIPTION
		"indicating whether ip packet with FO == 1 AND protocol == TCP 
		 is to be dropped"
	--CONFIGURABLE
::= { usrIp 12 }
usrIpDropOptions OBJECT-TYPE
     SYNTAX  INTEGER {
             enable(1),   -- dropping ip packet with options
             disable(0)   -- NOT dropping.
             }
	MAX-ACCESS read-write
	STATUS current
	DESCRIPTION
		"indicating whether ip packet with options is to be dropped"
	--CONFIGURABLE
::= { usrIp 13 }
usrIpDropSRRoute OBJECT-TYPE
     SYNTAX  INTEGER {
             enable(1),   -- dropping ip packet with OPTION==Source Route
             disable(0)   -- NOT dropping.
             }
	MAX-ACCESS read-write
	STATUS current
	DESCRIPTION
		"indicating whether ip packet with  OPTION==Source Route
		 is to be dropped"
	--CONFIGURABLE
::= { usrIp 14 }
usrIpAddrPoolTable OBJECT-TYPE
	SYNTAX SEQUENCE OF UsrIpAddrPoolEntry
	MAX-ACCESS not-accessible
	STATUS current
	DESCRIPTION
		"The table of IP Address Pools. These objects are defined 
		 as read/write so that they can be configured by a Network
		 Manager at the time an IP Address Pool is added."
::= { usrIp 15}
usrIpAddrPoolEntry OBJECT-TYPE
	SYNTAX UsrIpAddrPoolEntry
	MAX-ACCESS not-accessible
	STATUS current
	DESCRIPTION
		"A (conceptual) entry for one IP Address Pool. To create 
		 a new row in this table the objects usrIpAddrPoolBegin
	         and usrIpAddrPoolNetMask must be provided."
	INDEX { usrIpAddrPoolName}
::= { usrIpAddrPoolTable 1 }
UsrIpAddrPoolEntry ::= SEQUENCE {
	usrIpAddrPoolName		DisplayString,
	usrIpAddrPoolBegin		IpAddress,
	usrIpAddrPoolNetMask    	IpAddress,
	usrIpAddrPoolSize		Integer32,
	usrIpAddrPoolState		INTEGER,
	usrIpAddrPoolRoute 		INTEGER,
	usrIpAddrPoolStatus		INTEGER,
        usrIpAddrPoolInUse              Integer32,
        usrIpAddrPoolMaxWasted          Integer32,
	usrIpAddrPoolPriority		Integer32
	}
usrIpAddrPoolName	OBJECT-TYPE
	SYNTAX	 DisplayString (SIZE (1..16))
	MAX-ACCESS	 not-accessible
	STATUS	 current
	DESCRIPTION
		"the name of this IP address pool."
::= { usrIpAddrPoolEntry 1 }
usrIpAddrPoolBegin	OBJECT-TYPE
	SYNTAX	 IpAddress
	MAX-ACCESS	 read-write
	STATUS	 current
	DESCRIPTION
		"the starting ip address of this IP address pool."
	--CONFIGURABLE
::= { usrIpAddrPoolEntry 2 }
usrIpAddrPoolNetMask	 OBJECT-TYPE
	SYNTAX	 IpAddress
	MAX-ACCESS	 read-write
	STATUS	 current
	DESCRIPTION
		"the network mask for this IP address pool. For classful
                 pools this will be one of A/B/C/D/H; if not specified
                 with usrIpAddrPoolBegin it will default to Class A.
                 For classless pools the value of this object is
                 calculated internally based on CIDR(RFC1519)"
	--CONFIGURABLE
::= { usrIpAddrPoolEntry 3 }
usrIpAddrPoolSize	 OBJECT-TYPE
	SYNTAX	 Integer32 (1..10000)
	MAX-ACCESS	 read-write
	STATUS	 current
	DESCRIPTION
		"the number of IP addresses in this pool. the default size is 1
		Note that on the PDSN, the range is (1..4096)
		Note that on the HACN, the range is (1..4096)
		Note that on the HA, the range is (1..10000)"
	--CONFIGURABLE
::= { usrIpAddrPoolEntry 4 }
usrIpAddrPoolState	 OBJECT-TYPE
	SYNTAX	 INTEGER	{
		public(1),
		private(2)
	}
	MAX-ACCESS	 read-write
	STATUS	 current
	DESCRIPTION
		"If this object is set to public(1) an IP address can be selected
		 from this pool for any user not assigned to a pool.  If set to
		 private(2) IP addresses can only be selected from this pool by 
		 users assigned to it. "
	--CONFIGURABLE
::= { usrIpAddrPoolEntry 5 }
usrIpAddrPoolRoute	 OBJECT-TYPE
	SYNTAX	 INTEGER	{
		aggregate(1),
		no-aggregate(2),
		aggr-multiple-route(3)
	}
	MAX-ACCESS	 read-write
	STATUS	 current
	DESCRIPTION
		"If this object is set to aggregate(1) a host routes
                 within RIP updates will be aggregated.  If set to 
                 no_aggregate(2) host routes will not be aggregated."
	--CONFIGURABLE
::= { usrIpAddrPoolEntry 6 }
usrIpAddrPoolStatus 	OBJECT-TYPE
	SYNTAX	 INTEGER {
		delete(1),
		active(2),
		remove(3),
		remove-pending(4),
		delete-pending(5)
	}
	MAX-ACCESS	 read-write
	STATUS	 current
	DESCRIPTION
		"This object can only be set to delete(1) or active(2).
           If set to active(2) IP addresses can be assigned from this pool. 
		 If set to delete(1) this pool is being deleted so no new users can 	
		 be assigned IP addresses from this pool.  If set to remove(3) IP 
		 addresses are being removed from this pool so no new users can
		 be assigned IP address from this pool.  If set to remove_pending(4) 
		 this pool is currently waiting for users to release IP addresses that
		 need to be deleted, new users can be assigned IP addresses from
		 this pool.  If set to delete_pending(5) this pool is waiting for users
		 to release IP addresses so this pool can be deleted.  No new users
		can be assigned from this pool "
::= { usrIpAddrPoolEntry 7 }
usrIpAddrPoolInUse       OBJECT-TYPE
        SYNTAX   Integer32
        MAX-ACCESS   read-only 
        STATUS   current
        DESCRIPTION
                "the number of pool addresses in use.  This is calculated using the size
                 and the number of entries available. "
::= { usrIpAddrPoolEntry 8 }
usrIpAddrPoolMaxWasted       OBJECT-TYPE   
        SYNTAX   Integer32
        MAX-ACCESS   read-write
        STATUS   current     
        DESCRIPTION
                "the Max number of pool addresses wasted in case of
                 multiple routes aggr pool
		For PDSN, Range is (0..4096)
		For HA,   Range is (0..10000)"
    --CONFIGURABLE
::= { usrIpAddrPoolEntry 9 } 
usrIpAddrPoolPriority	OBJECT-TYPE
	SYNTAX	Integer32
	MAX-ACCESS	read-write
	STATUS	current
	DESCRIPTION
		"Priority for a Pool. Address pool selection for NOT round-robin
		 method shall use this field. Lowest value (1) has highest priority."
    --CONFIGURABLE
::= { usrIpAddrPoolEntry 10 }
usrIpAddressPoolFilter OBJECT-TYPE
     SYNTAX  INTEGER {
             filtering(1),       -- enable ip address_pool_filtering 
             not-filtering(2)    -- disable ip address_pool_filtering
             }
	MAX-ACCESS read-write
	STATUS current
	DESCRIPTION
		"This object may only be set to enable(1) or disable
                 (2).  If set to enable(1) and if IP address found in
                 any pools, but for which a host route does not exits, 
                 will return null route to drop packet.  If set to 
                 disable(2) there will be no check for IP address in
                 pool table.  This is disabled by default."
	--CONFIGURABLE
::= { usrIp 16 }
usrIpSRCPPPAddress OBJECT-TYPE
	SYNTAX	IpAddress
	MAX-ACCESS	read-write
	STATUS	current
	DESCRIPTION
		" This variable sets the local address for WAN links (SLIP/PPP). If zero
		system will user internal or other ethernet address for it"
	--CONFIGURABLE
::= { usrIp 17 }
usrIpSRCRADIUSAddress OBJECT-TYPE
	SYNTAX	IpAddress
	MAX-ACCESS	read-write
	STATUS	current
	DESCRIPTION
		"For all radius packets send out this will the source address. If zero
		 internal ip address or interface IP address will be the source address
		 ."
	--CONFIGURABLE
::= { usrIp 18 }
usrIpSRCSyslogAddress OBJECT-TYPE
	SYNTAX	IpAddress
	MAX-ACCESS	read-write
	STATUS	current
	DESCRIPTION
		"For all Syslog packets send out this will the source address. If zero
		 internal ip address or interface IP address will be the source address
		 ."
	--CONFIGURABLE
::= { usrIp 19 }
usrIpClearArp OBJECT-TYPE
        SYNTAX  Integer32
	MAX-ACCESS read-write
	STATUS current
	DESCRIPTION
		"This object is used to clear the entire ARP cache"
::= { usrIp 20 }
usrIpSrcIGMPAddress OBJECT-TYPE
	SYNTAX	IpAddress
	MAX-ACCESS	read-write
	STATUS	current
	DESCRIPTION
		"For all IGMP packets send out this will the source address. If zero
		 internal ip address or interface IP address will be the source address
		 ."
	--CONFIGURABLE
::= { usrIp 21 }
usrIpAddressPoolRoundRobin OBJECT-TYPE
     SYNTAX  INTEGER {
             round-robin(1),     -- enable ip address_pool_round_robin 
             not-round-robin(2)  -- disable ip address_pool_round_robin 
             }
	MAX-ACCESS read-write
	STATUS current
	DESCRIPTION
		"This object may only be set to enable(1) or disable
           (2).  If set to enable(1), addresses will be allocated
		 from address pools in round-robin fashion.  If set to
		 disable(2), addresses will be allocated from the first
		 pool until all of its addresses are depleted.  Then
		 addresses will be allocated from the next pool, and so
		 forth.  This is enabled by default."
	--CONFIGURABLE
::= { usrIp 22 }
usrIpDefaultRouteTable OBJECT-TYPE
	SYNTAX SEQUENCE OF UsrIpDefaultRouteEntry
	MAX-ACCESS not-accessible
	STATUS current
	DESCRIPTION
		"Table of default route entries. Since all default
                routes have all 0's address and mask gateway address
                will be used as a index."
::= { usrIp 23 }
usrIpDefaultRouteEntry OBJECT-TYPE
	SYNTAX UsrIpDefaultRouteEntry
	MAX-ACCESS not-accessible
	STATUS current
	DESCRIPTION
		"All 0's for the network and all 0's mask."
	INDEX { usrIpDefaultRouteGateway }
::= { usrIpDefaultRouteTable 1 }
UsrIpDefaultRouteEntry ::= SEQUENCE {
	usrIpDefaultRouteGateway        IpAddress,
        usrIpDefaultRouteStatus         INTEGER,
	usrIpDefaultRouteMetric         Integer32
	}
usrIpDefaultRouteGateway OBJECT-TYPE
    SYNTAX  IpAddress
    MAX-ACCESS  read-only
    STATUS  current
    DESCRIPTION
		"Gateway for this default route."
::= { usrIpDefaultRouteEntry 1 }
usrIpDefaultRouteStatus OBJECT-TYPE
    SYNTAX INTEGER{
          create(1),
          delete(2),
          disable(3)
    }
    MAX-ACCESS  read-write
    STATUS  current
    DESCRIPTION
		"Create/delete parameter."
	--CONFIGURABLE
::= { usrIpDefaultRouteEntry 2 }
usrIpDefaultRouteMetric OBJECT-TYPE
    SYNTAX  Integer32
    MAX-ACCESS  read-write
    STATUS  current
    DESCRIPTION
        "Metric for this default route."
	--CONFIGURABLE
::= { usrIpDefaultRouteEntry 3 }
usrGlobalSourceIpFilterFlag OBJECT-TYPE 
    SYNTAX INTEGER
    {
       disabled(2),
       enabled(1)
    }
    MAX-ACCESS   read-write 
    STATUS   current
    DESCRIPTION
        "Indicates whether Global Source address assurance  
         feature is enabled."
             --CONFIGURABLE
::= { usrIp 24 }
usrIpIeaSendUnsolicitedArp OBJECT-TYPE
    SYNTAX     INTEGER {
                    enabled(1),
                    disabled(2)
                    }
    MAX-ACCESS read-write
    STATUS current
    DESCRIPTION
      "This flag is DISABLED by default. In order to send unsolicited ARP
       request when the user gets connected, the needs to be set to ENABLED."
    --CONFIGURABLE
::= { usrIp 25 }
usrIpIeaForceNexthopRoute OBJECT-TYPE
    SYNTAX     INTEGER {
                    enabled(1),
                    disabled(2)
                    }
    MAX-ACCESS read-write
    STATUS current
    DESCRIPTION
  	    "This flag is DISABLED by default. The state DISABLED states NOT
		 to drop the connection for the user if the next hop in INVALID 
         and also to use other routes to forward the packets when the next 
         hop router is unreachable. 
		 If the state is ENABLED, then the user will be disconnected 
         if nexthop route is INVALID and also drop the packets when nexthop 
         route becomes unreachable."
    --CONFIGURABLE
::= { usrIp 26 }
usrIpSRCPingAddress OBJECT-TYPE
    SYNTAX  IpAddress
    MAX-ACCESS  read-write
    STATUS  current
    DESCRIPTION
        "This variable sets the src address for ping"
    --CONFIGURABLE
::= { usrIp 27 }
usrIpSRCTraceRouteAddress OBJECT-TYPE
    SYNTAX  IpAddress
    MAX-ACCESS  read-write
    STATUS  current
    DESCRIPTION
        "This variable sets the src address for traceroute"
    --CONFIGURABLE
::= { usrIp 28 }
usrIpProxyArpAllDialinNet OBJECT-TYPE 
    SYNTAX INTEGER
    {
       disabled(2),
       enabled(1)
    }
    MAX-ACCESS   read-write 
    STATUS   current
    DESCRIPTION
        "Indicates whether Proxy ARPing all dialin networks 
         feature is enabled. Default is disabled"
             --CONFIGURABLE
::= { usrIp 29 }
usrIpSendHostUnreachForPool OBJECT-TYPE
    SYNTAX INTEGER
    {
       disabled(2),
       enabled(1)
    }
    MAX-ACCESS   read-write
    STATUS   current
    DESCRIPTION
        "Indicates whether to send icmp unreachable for pool addresses
         Default is disabled"
   --CONFIGURABLE
::= { usrIp 30 }
usrIpIeaNextHopRouting OBJECT-TYPE
    SYNTAX     INTEGER {
                    enabled(1),
                    disabled(2)
                    }
    MAX-ACCESS read-write
    STATUS current
    DESCRIPTION
      "Indicates whether next hop routing is enabled or not.
       The default value is ENABLED"
    --CONFIGURABLE
::= { usrIp 31 }
usrIpSrcVTPAddress OBJECT-TYPE
        SYNTAX  IpAddress
        MAX-ACCESS  read-write
        STATUS  current
        DESCRIPTION
                "For all VTP packets send out this will the source address.
                 If zero internal ip address or interface IP address
                 will be the source address."
        --CONFIGURABLE 
::= { usrIp 32 }
usrIpSrcPPTPAddress OBJECT-TYPE
        SYNTAX  IpAddress
        MAX-ACCESS  read-write
        STATUS  current
        DESCRIPTION
        "For all PPTP packets sent out by the PAC, this will the source address.
         If this is zero then the internal ip addr or interface IP addr will be
         the source address ."
        --CONFIGURABLE
::= { usrIp 33 }
usrIpSrcL2TPAddress OBJECT-TYPE
    SYNTAX  IpAddress
    MAX-ACCESS  read-write
    STATUS  current
    DESCRIPTION 
        "For all L2TP packets sent out by the LAC, this will the source address.
         If this is zero then the internal ip addr or interface IP addr will be
         the source address ."
    --CONFIGURABLE
::= { usrIp 34 }
          -- the IP source address based routing table
          -- The IP routing table contains an entry for each route
          -- presently known to this entity.
          usrIpSrcRouteTable OBJECT-TYPE
              SYNTAX  SEQUENCE OF UsrIpSrcRouteEntry
              MAX-ACCESS  not-accessible
              STATUS  current
              DESCRIPTION
                      "This entity's IP Source Routing table."
              ::= { usrIp 35 }
          usrIpSrcRouteEntry OBJECT-TYPE
              SYNTAX  UsrIpSrcRouteEntry
              MAX-ACCESS  not-accessible
              STATUS  current
              DESCRIPTION
                      "A route to a particular destination."
              INDEX   { usrIpSrcRouteDest }
              ::= { usrIpSrcRouteTable 1 }
          UsrIpSrcRouteEntry ::=
              SEQUENCE {
                  usrIpSrcRouteDest
                      IpAddress,
                  usrIpSrcRouteIfIndex
                      Integer32,
                  usrIpSrcRouteMetric1
                      Integer32,
                  usrIpSrcRouteNextHop
                      IpAddress,
                  usrIpSrcRouteType
                      INTEGER,
                  usrIpSrcRouteProto
                      INTEGER,
                  usrIpSrcRouteMask
                      IpAddress,
                  usrIpSrcRouteStatus
                      INTEGER
              }
          usrIpSrcRouteDest OBJECT-TYPE
              SYNTAX  IpAddress
              MAX-ACCESS  read-write
              STATUS  current
              DESCRIPTION
                      "The destination IP address of this route.  An
                      entry with a value of 0.0.0.0 is considered a
                      default route.  Multiple routes to a single
                      destination can appear in the table, but access to
                      such multiple entries is dependent on the table-
                      access mechanisms defined by the network
                      management protocol in use.  
                      This object is not applicable to the PDSN"
                 --CONFIGURABLE
              ::= { usrIpSrcRouteEntry 1 }
          usrIpSrcRouteIfIndex OBJECT-TYPE
              SYNTAX  Integer32
              MAX-ACCESS  read-write
              STATUS  current
              DESCRIPTION
                      "The index value which uniquely identifies the
                      local interface through which the next hop of this
                      route should be reached.  The interface identified
                      by a particular value of this index is the same
                      interface as identified by the same value of
                      ifIndex.
                      This object is not applicable to the PDSN"
              ::= { usrIpSrcRouteEntry 2 }
          usrIpSrcRouteMetric1 OBJECT-TYPE
              SYNTAX  Integer32 (0..15)
              MAX-ACCESS  read-write
              STATUS  current
              DESCRIPTION
                      "The primary routing metric for this route.  The
                      semantics of this metric are determined by the
                      routing-protocol specified in the route's
                      ipRouteProto value.  If this metric is not used,
                      its value should be set to -1.
                      This object is not applicable to the PDSN"
              --CONFIGURABLE
              ::= { usrIpSrcRouteEntry 3 }
          usrIpSrcRouteNextHop OBJECT-TYPE
              SYNTAX  IpAddress
              MAX-ACCESS  read-write
              STATUS  current
              DESCRIPTION
                      "The IP address of the next hop of this route.
                      (In the case of a route bound to an interface
                      which is realized via a broadcast media, the value
                      of this field is the agent's IP address on that
                      interface.)
                      This object is not applicable to the PDSN"
               --CONFIGURABLE
              ::= { usrIpSrcRouteEntry 4 }
          usrIpSrcRouteType OBJECT-TYPE
              SYNTAX  INTEGER {
                          other(1),        -- none of the following
                          invalid(2),      -- an invalidated route
                                           -- route to directly
                          direct(3),       -- connected (sub-)network
                                           -- route to a non-local
                          indirect(4)      -- host/network/sub-network
                      }
              MAX-ACCESS  read-write
              STATUS  current
              DESCRIPTION
                      "The type of route.  Note that the values
                      direct(3) and indirect(4) refer to the notion of
                      direct and indirect routing in the IP
                      architecture. The only value settable from SNMP
                      is invalid(2).
                      Setting this object to the value invalid(2) has
                      the effect of invalidating the corresponding entry
                      in the ipRouteTable object.  That is, it
                      effectively disassociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { usrIpSrcRouteEntry 5 }
          usrIpSrcRouteProto OBJECT-TYPE
              SYNTAX  INTEGER {
                          other(1),       -- none of the following
                                          -- non-protocol information,
                                          -- e.g., manually configured
                          local(2),       -- entries
                                          -- set via a network
                          netmgmt(3),     -- management protocol
                                          -- obtained via ICMP,
                          icmp(4),        -- e.g., Redirect
                                          -- the remaining values are
                                          -- all gateway routing
                                          -- protocols
                          egp(5),
                          ggp(6),
                          hello(7),
                          rip(8),
                          is-is(9),
                          es-is(10),
                          ciscoIgrp(11),
                          bbnSpfIgp(12),
                          ospf(13),
                          bgp(14),
                          source(15)
                      }
              MAX-ACCESS  read-only
              STATUS  current
              DESCRIPTION
                      "The routing mechanism via which this route was
                      learned.  Inclusion of values for gateway routing
                      protocols is not intended to imply that hosts
                      should support those protocols.
                      This object is not applicable to the PDSN"
              ::= { usrIpSrcRouteEntry 6 }
          usrIpSrcRouteMask OBJECT-TYPE
              SYNTAX  IpAddress
              MAX-ACCESS  read-write
              STATUS  current
              DESCRIPTION
                      "Indicate the mask to be logical-ANDed with the
                      destination address before being compared to the
                      value in the ipSrcRouteDest field.  For those systems
                      that do not support arbitrary subnet masks, an
                      agent constructs the value of the ipRouteMask by
                      determining whether the value of the correspondent
                      ipSrcRouteDest field belong to a class-A, B, or C
                      network, and then using one of:
                           mask           network
                           255.0.0.0      class-A
                           255.255.0.0    class-B
                           255.255.255.0  class-C
                      If the value of the ipRouteDest is 0.0.0.0 (a
                      default route), then the mask value is also
                      0.0.0.0.  It should be noted that all IP routing
                      subsystems implicitly use this mechanism.  
                      This object is not applicable to the PDSN"
              --CONFIGURABLE
              ::= { usrIpSrcRouteEntry 7 }
          usrIpSrcRouteStatus OBJECT-TYPE
              SYNTAX  INTEGER {
                                up(1),
                                down(2),
                                invalid(3)
                                }
              MAX-ACCESS  read-write
              STATUS  current
              DESCRIPTION
                      "Whether the route is UP or DOWN - updated 
                       internally depending upon whether the network 
                       goes up or down. Not settable via SNMP.
                       This object is not applicable to the PDSN"
              ::= { usrIpSrcRouteEntry 8 }
-- The following table is modeled after IGMP.
usrIpSrcRouteInterfaceTable OBJECT-TYPE
    SYNTAX     SEQUENCE OF UsrIpSrcRouteInterfaceEntry
    MAX-ACCESS not-accessible
    STATUS     current
    DESCRIPTION
    "The table listing the interfaces on which source based routing is enabled."
    ::= { usrIp 36 }
usrIpSrcRouteInterfaceEntry OBJECT-TYPE
    SYNTAX     UsrIpSrcRouteInterfaceEntry
    MAX-ACCESS not-accessible
    STATUS     current
    DESCRIPTION
    "An entry representing an interface on which source based routing is enabled."
    INDEX      { usrIpSrcRouteInterfaceIfName }
    ::= { usrIpSrcRouteInterfaceTable 1 }
UsrIpSrcRouteInterfaceEntry ::= SEQUENCE {
    usrIpSrcRouteInterfaceIfName       DisplayString,
    usrIpSrcRouteInterfaceEnabled      INTEGER
                                        }
usrIpSrcRouteInterfaceIfName OBJECT-TYPE
    SYNTAX     DisplayString (SIZE (1..32))
    MAX-ACCESS not-accessible
    STATUS     current
    DESCRIPTION
            "The interface name for which source rbased routing is enabled."
::= { usrIpSrcRouteInterfaceEntry 1 }
usrIpSrcRouteInterfaceEnabled OBJECT-TYPE
    SYNTAX     INTEGER {
                    enabled(1),
                    disabled(2)
                    }
    MAX-ACCESS read-write                                                 
    STATUS     current                                                   
    DESCRIPTION 
             "Indicates whether source routing is enabled or not." 
    DEFVAL    { disabled }
    --CONFIGURABLE                         
::= { usrIpSrcRouteInterfaceEntry 2 }                                        
usrIpRespondToDirectedBcst OBJECT-TYPE 
    SYNTAX INTEGER
    {
       disabled(2),
       enabled(1)
    }
    MAX-ACCESS   read-write 
    STATUS   current
    DESCRIPTION
        "Disable responding to directed bcast globally"
             --CONFIGURABLE
::= { usrIp 37 }
usrIpForwardDirectedBcst OBJECT-TYPE 
    SYNTAX INTEGER
    {
       disabled(2),
       enabled(1)
    }
    MAX-ACCESS   read-write 
    STATUS   current
    DESCRIPTION
        "Enable directed bcast forwarding in IP"
             --CONFIGURABLE
::= { usrIp 39 }
usrIpStaticArpTable OBJECT-TYPE
	SYNTAX SEQUENCE OF UsrIpStaticRouteEntry
	MAX-ACCESS not-accessible
	STATUS current
	DESCRIPTION
		"Table of Static Arp cache"
::= { usrIp 38 }
usrIpStaticArpEntry OBJECT-TYPE
	SYNTAX UsrIpStaticRouteEntry
	MAX-ACCESS not-accessible
	STATUS current
	DESCRIPTION
		""
	INDEX { usrIpStaticArpIpAddr,usrIpusrIpStaticArpInt}
::= { usrIpStaticArpTable 1 }
UsrIpStaticRouteEntry ::= SEQUENCE {
	usrIpStaticArpIpAddr        IpAddress,
	usrIpusrIpStaticArpInt      OCTET STRING,
	usrIpStaticArpStatus	    INTEGER,
        usrIpStaticArpMacAddr       OCTET STRING,
	usrIpStaticArpState	    INTEGER
	}
usrIpStaticArpIpAddr OBJECT-TYPE
    SYNTAX  IpAddress
    MAX-ACCESS  read-only
    STATUS  current
    DESCRIPTION
		"The ip address of the ARP entry"
::= { usrIpStaticArpEntry 1 }
usrIpusrIpStaticArpInt OBJECT-TYPE
    SYNTAX  OCTET STRING (SIZE(0..16))
    MAX-ACCESS  read-only
    STATUS  current
    DESCRIPTION
		"The interface of the static ARP entry"
::= { usrIpStaticArpEntry 2 }
usrIpStaticArpStatus OBJECT-TYPE
    SYNTAX  INTEGER {
                add(1), -- set when arp entry added
                delete(2) -- delete entry
                }
	MAX-ACCESS read-write
	STATUS current
	DESCRIPTION
		"This object is used to identify the ARP operation.
                 It is set to 1 when an entry is added; setting it
                 to 2 will delete the entry."
   --CONFIGURABLE
::= { usrIpStaticArpEntry 3 }
usrIpStaticArpMacAddr OBJECT-TYPE
    SYNTAX OCTET STRING (SIZE(6))
	MAX-ACCESS read-write
	STATUS current
	DESCRIPTION
		"This object is used to store the associated MAC address"
   --CONFIGURABLE
::= { usrIpStaticArpEntry 4 }
usrIpStaticArpState OBJECT-TYPE
	SYNTAX	INTEGER {
		public(1),
		private(2),
                invalid(3)
	}
	MAX-ACCESS	read-write
	STATUS	current
	DESCRIPTION
		"This is the type of static arp entry. Public/private "
   --CONFIGURABLE
::= { usrIpStaticArpEntry 5 }
usrIpAggregateRouteTable OBJECT-TYPE
    SYNTAX  SEQUENCE OF UsrIpAggregateRouteEntry
    MAX-ACCESS  not-accessible
    STATUS  current
    DESCRIPTION
        "This table is used to display multiple aggregate routes for an
         IP pool. An IP pool could be segregated into multiple sub pools.
         depending on the size."          
    ::= { usrIp 40 } 
usrIpAggregateRouteEntry OBJECT-TYPE 
    SYNTAX  UsrIpAggregateRouteEntry
    MAX-ACCESS  not-accessible
    STATUS  current
    DESCRIPTION    
        "A table of PoolName, Initial Address, Aggregate Route, Endpoint address,
         Type"      
    INDEX { usrIpAggInitPoolAddress }
    ::= { usrIpAggregateRouteTable 1 }
UsrIpAggregateRouteEntry ::= 
    SEQUENCE {
        usrIpAggInitPoolAddress  
            IpAddress,
        usrIpAggPoolName
            DisplayString,     
        usrIpAggPoolAggregateRoute
            IpAddress,
        usrIpAggPoolNetMask
            IpAddress,
        usrIpAggPoolSize
            Integer32,
        usrIpAggPoolType    
            Integer32    
    }   
usrIpAggInitPoolAddress OBJECT-TYPE
    SYNTAX  IpAddress
    MAX-ACCESS  read-only
    STATUS  current
    DESCRIPTION
        "Initial pool address for aggregate pool"
    ::= { usrIpAggregateRouteEntry 1 }
usrIpAggPoolName OBJECT-TYPE
    SYNTAX  DisplayString
    MAX-ACCESS  read-only
    STATUS  current
    DESCRIPTION
        "Aggregate Pool name"
    ::= { usrIpAggregateRouteEntry 2 }
usrIpAggPoolAggregateRoute OBJECT-TYPE
    SYNTAX  IpAddress
    MAX-ACCESS  read-only
    STATUS  current
    DESCRIPTION
        "Aggregate route that will be broadcasted"
    ::= { usrIpAggregateRouteEntry 3 }
usrIpAggPoolNetMask OBJECT-TYPE
    SYNTAX  IpAddress
    MAX-ACCESS  read-only
    STATUS  current
    DESCRIPTION
        "Mask for an aggregate route pool"
    ::= { usrIpAggregateRouteEntry 4 }
usrIpAggPoolSize OBJECT-TYPE
    SYNTAX  Integer32
    MAX-ACCESS  read-only
    STATUS  current
    DESCRIPTION
        "Indicates the last valid address in this aggregate pool"
    ::= { usrIpAggregateRouteEntry 5 }
usrIpAggPoolType OBJECT-TYPE
    SYNTAX  Integer32
    MAX-ACCESS  read-only
    STATUS  current
    DESCRIPTION
        "Indicates the type of the aggregate pool. It might be
         MULTI_AGGREGATE, NON_AGGREGATE, AGGREGATE"
    ::= { usrIpAggregateRouteEntry 6 }
usrIpSrcFAAddress OBJECT-TYPE
        SYNTAX  IpAddress
        MAX-ACCESS  read-write
        STATUS  current
        DESCRIPTION
                "For all FA packets send out this will the source address.
                 If zero internal ip address or interface IP address
                 will be the source address.
		This object is valid only for PDSN."
        --CONFIGURABLE 
::= { usrIp 41 }
usrIpSrcVHAAddress OBJECT-TYPE
        SYNTAX  IpAddress
        MAX-ACCESS  read-write
        STATUS  current
        DESCRIPTION
                "For all VHA packets send out this will the source address.
                 If zero internal ip address or interface IP address
                 will be the source address.
		 This object is valid only for PDSN."
        --CONFIGURABLE 
::= { usrIp 42 }
usrIpSrcHAAddress OBJECT-TYPE
   SYNTAX IpAddress
   MAX-ACCESS read-write
   STATUS current
   DESCRIPTION
       "This will be the HA source IP address. The user will specify using
        this object that which address HA will use as its Boot IP address.
        This object is valid only for HA. "
   --CONFIGURABLE
::= { usrIp 43}
usrIpSrcHACNAddress OBJECT-TYPE
   SYNTAX IpAddress
   MAX-ACCESS read-write
   STATUS current
   DESCRIPTION
       "This will be the HACN boot IP address.
	This object is valid only for HACN"
   --CONFIGURABLE
::= { usrIp 46}
usrIpNetworksCfgFileName OBJECT-TYPE
	SYNTAX      DisplayString
	MAX-ACCESS  read-only
	STATUS      current
	DESCRIPTION		
		"The name of a ConfigFile to read/write  permanent database records.
		 If the value of this object is an empty string, then the
		 IP module uses the default name `@file://IPModule.cfg'. "
::= { usrIp 52}
usrIpSrcSNMPAddress OBJECT-TYPE
        SYNTAX  IpAddress
        MAX-ACCESS  read-write
        STATUS  current
        DESCRIPTION
                "For all SNMP packets send out this will the source address.
                 If zero internal ip address or interface IP address
                 will be the source address.
		This object is valid only for PDSN, HA, HACN."
        --CONFIGURABLE 
::= { usrIp 55 }
END         -- End USR-IP-MIB DEFINITIONS
-- ************************************************************************
--
--	usr_invarp.mib - A proprietary MIB file for Inverse ARP cache 
--
-- Author:        P K Das 
--
USR-INVERSEARP-MIB DEFINITIONS ::= BEGIN
	IMPORTS
	  RowStatus
                FROM SNMPv2-TC
          IpAddress
                FROM RFC1155-SMI
          OBJECT-TYPE,  MODULE-IDENTITY, Integer32
                FROM SNMPv2-SMI
          PhysAddress, common
                FROM USR-DEFINITIONS-MIB;
        usrInverseARP    MODULE-IDENTITY
         LAST-UPDATED "0001141020Z" -- Friday, January 14, 10:20, 2000
         ORGANIZATION "3Com Corporation, Carrier Division"
         CONTACT-INFO "Customer Support"
         DESCRIPTION
                 "The proprietary object definitions for Inverse ARP."
         ::= { common 73 }
   -- Begin managed object definitions here...
   -- The Inverse ARP Table contains the mapping of IP Address(network address)
   -- to dlci-interface pair for IP networks over Frame Relay PTP connections.
usrInverseARPTable OBJECT-TYPE
	SYNTAX SEQUENCE OF UsrInverseARPEntry
	MAX-ACCESS not-accessible
	STATUS current 
	DESCRIPTION
		"The Inverse ARP cache for Frame Relay Networks"
::= { usrInverseARP 1 }
usrInverseARPEntry OBJECT-TYPE
	SYNTAX UsrInverseARPEntry
	MAX-ACCESS not-accessible
	STATUS current
	DESCRIPTION
		"An Inverse ARP cache entry"
	INDEX { usrInverseARPIfIndex, usrInverseARPNetAddress }
::= { usrInverseARPTable 1 }
UsrInverseARPEntry ::= SEQUENCE {
        usrInverseARPIfIndex     Integer32,
        usrInverseARPPhysAddress PhysAddress,
        usrInverseARPNetAddress  IpAddress,
        usrInverseARPType        INTEGER,
        usrInverseARPAge         Integer32,
	usrInverseARPStatus      RowStatus
        }
usrInverseARPIfIndex OBJECT-TYPE
        SYNTAX  Integer32
        MAX-ACCESS  read-write
        STATUS  current
        DESCRIPTION
                "The interface on which this entry's equivalence
                is effective.  The interface identified by a
                particular value of this index is the same
                interface as identified by the same value of
                ifIndex."
        --CONFIGURABLE
::= { usrInverseARPEntry 1 }
usrInverseARPPhysAddress OBJECT-TYPE
        SYNTAX  PhysAddress
        MAX-ACCESS  read-write
        STATUS  current
        DESCRIPTION
                "The media-dependent `physical' address. For Frame Relay PTMP network,
                it's six byte long; 4 byte DLCI followed by 2byte interface(physical) index"
        --CONFIGURABLE
::= { usrInverseARPEntry 2 }
usrInverseARPNetAddress OBJECT-TYPE
        SYNTAX  IpAddress
        MAX-ACCESS  read-write
        STATUS  current
        DESCRIPTION
                "The IpAddress corresponding to the media-
                dependent `physical' address."
        --CONFIGURABLE
::= { usrInverseARPEntry 3 }
usrInverseARPType OBJECT-TYPE
        SYNTAX  INTEGER {
                    other(0),        -- none of the following
                    invalid(1),      -- an invalidated mapping
                    dynamic(2),
                    static(3)
                }
        MAX-ACCESS  read-write
        STATUS  current
        DESCRIPTION
                "The type of mapping"
        --CONFIGURABLE
::= { usrInverseARPEntry 4 }
usrInverseARPAge OBJECT-TYPE
        SYNTAX  Integer32
        MAX-ACCESS  read-write
        STATUS  current
        DESCRIPTION
                "The current timeout age of an entry"
        --CONFIGURABLE
::= { usrInverseARPEntry 5 }
usrInverseARPStatus OBJECT-TYPE
	SYNTAX  RowStatus
	MAX-ACCESS    read-write
	STATUS  current
	DESCRIPTION
		"The status of this row of the Inverse ARP Table. "
	--CONFIGURABLE
::= { usrInverseARPEntry 6 }
usrInverseARPConfigGroup OBJECT IDENTIFIER ::= { usrInverseARP 2 }
usrInverseARPTxInterval OBJECT-TYPE
        SYNTAX  Integer32
        MAX-ACCESS  read-write
        STATUS  current
        DESCRIPTION
                "The Inverse ARP transmit frequency in secs"
	--CONFIGURABLE
::= { usrInverseARPConfigGroup 1 }
usrInverseARPMaxAge OBJECT-TYPE
        SYNTAX  Integer32
        MAX-ACCESS  read-write
        STATUS  current
        DESCRIPTION
                "The Maximum age count of an entry before it is deleted from the cache. 
                 One count corresponds to one Inverse ARP transmit frequency period."
	--CONFIGURABLE
::= { usrInverseARPConfigGroup 2 }
usrInverseARPCacheClear OBJECT-TYPE
        SYNTAX  Integer32
        MAX-ACCESS  read-write
        STATUS  current
        DESCRIPTION
                "This object is used to clear the entire Inverse ARP cache."
::= { usrInverseARP 3 }
END         -- End USR-INVERSEARP-MIB definitions
--
-- ************************************************************************
--
--    usr_ip_routing.mib
--
-- Author:         han-son on
--
USR-IP-ROUTING-MIB DEFINITIONS ::= BEGIN
    IMPORTS
        OBJECT-TYPE, MODULE-IDENTITY, 
        Integer32, Counter32, IpAddress
                FROM SNMPv2-SMI
        DisplayString
                FROM SNMPv2-TC
        common, UsrNetLogicalId, UsrConfigStatus
                FROM USR-DEFINITIONS-MIB;
usrIpRouting MODULE-IDENTITY
         LAST-UPDATED "200205051245Z"
         ORGANIZATION "CommWorks Corporation, a 3Com Company"
         CONTACT-INFO "Customer Support"
         DESCRIPTION
                 "The commWorks enterprise defined MIB objects
                  for IP routing process."
--       REVISION "200205051245Z"
--       DESCRIPTION "Converted to SNMPv2"
         ::= { common 19 }
-- Begin IP routing object definitions here...
usrIpRouterId    OBJECT-TYPE
    SYNTAX    IpAddress
    MAX-ACCESS    read-write
    STATUS        current
    DESCRIPTION
        "the router id is usually the ip address of one of the router's
         lan interface ip address.  this variable can only be set when
         usrIpAdminStatus is set to disabled."
::= {usrIpRouting 1}
usrIpAdminStatus    OBJECT-TYPE
    SYNTAX    INTEGER {
            enabled(1),
            disabled(2)
        }
    MAX-ACCESS    read-write
    STATUS        current
    DESCRIPTION
        "this variable is used to enable or disable the ip routing instance."
        --CONFIGURABLE
::= {usrIpRouting 2}
usrIpStaticProtoStatus    OBJECT-TYPE
    SYNTAX    INTEGER {
            enable(1),
            disable(2)
        }
    MAX-ACCESS    read-write
    STATUS        current
    DESCRIPTION
        "this variable is used to enable or disable static remote routes"
::= {usrIpRouting 3}
usrIpASNumber    OBJECT-TYPE
    SYNTAX    Integer32 (1..65535)
    MAX-ACCESS    read-write
    STATUS        current
    DESCRIPTION
        "this is the autonomous system number used by egp, which can only be 
         modified when usrIpAdminStatus is set to disabled."
::= {usrIpRouting 4}
usrIpRtabMaxAdmin    OBJECT-TYPE
    SYNTAX        Integer32 (30..65535)
    MAX-ACCESS        read-write
    STATUS            current
    DESCRIPTION
        "the max admin route table entries for next set.  this is put in by
         rci for lightstream atm.  it is not used by lanlinker or netserver."
::= {usrIpRouting 5}
usrIpRtabMax    OBJECT-TYPE
    SYNTAX    Integer32 (30..20000)
    MAX-ACCESS    read-only
    STATUS        current
    DESCRIPTION
        "this displays the maximum routing table size, this
         value can no longer be modified. The max size of the
         routing table is determined at compilation time, 
         based on the DFLT_RTH_CNT. DFLT_RTH_CNT is currently 
         set to 3880."
::= {usrIpRouting 6}
usrIpNHEntryMax    OBJECT-TYPE
    SYNTAX        Integer32 (256..65535)
    MAX-ACCESS        read-write
    STATUS            current
    DESCRIPTION
        "this defines the maximum next hop entries, which can only be 
         modified when usrIpAdminStatus is set to disabled.  the default
         is 512"
::= {usrIpRouting 7}
usrIpRtEntryCount    OBJECT-TYPE
    SYNTAX        Counter32
    MAX-ACCESS        read-only
    STATUS            current
    DESCRIPTION
        "this keeps the number of route entries."
::= {usrIpRouting 8}
usrIpGenStat    OBJECT-TYPE
    SYNTAX    INTEGER {
            create(1),
            delete(2)
        }
    MAX-ACCESS    read-write
    STATUS        current
    DESCRIPTION
        "this variable denotes the existence of the ip routing instance,
         which can also be used to delete the routing instance."
::= {usrIpRouting 9}
usrIpRipGenStat    OBJECT-TYPE
    SYNTAX        INTEGER {
                enabled(1),
                disabled(2)
            }
    MAX-ACCESS        read-write
    STATUS            current
    DESCRIPTION
        "this mib variable is used to enable or disable the ip rip instance
         at the ip routing instance level.  it is a no op if ip rip instance
         is not yet created.
         the rip instance, i.e. usrIpRipAdminStatus, may still remain
         disabled, if it is either not created or it was disabled at ip rip
         instance level.  to fully enable the rip instance, one has to make
         sure that ip rip instance is already created and enabled on both
         levels."
::= {usrIpRouting 10}
usrIpRipAdminStatus    OBJECT-TYPE
    SYNTAX        INTEGER {
                create(1),
                delete(2)
        }
    MAX-ACCESS        read-write
    STATUS            current
    DESCRIPTION
        "this variable is used to create or delete the ip rip instance."
::= {usrIpRouting 11}
usrIpRipFlags    OBJECT-TYPE
    SYNTAX    Integer32
    MAX-ACCESS    read-write
    STATUS        current
    DESCRIPTION
        "Several Flags  are supported by this mib object,
         only RIP_FLAG_RFC1058_METRICS, RIP_FLAG_SEND_REQUEST are
         accessible.
         The only allowable values for setting are as follows:-
         24 (0x18) - SEND_REQUEST & METRICS
         8         - METRICS
         16 (0x10) - SEND_REQUEST
         0         - NONE
         Note:- when setting these values a GET will not
         necessarily return the value SET: it will
         return the SET value plus the bitmask(s)
         for inaccessible flags.
         The default flags are 0x1A (decimal 26) reflecting,
         RIP_FLAG_JITTER_UPDATE     :=    0x00000002 (default)    
         RIP_FLAG_RFC1058_METRICS   :=    0x00000008 (default)
         RIP_FLAG_SEND_REQUEST      :=    0x00000010 (default) "
::= {usrIpRouting 12}
usrIpIfbTable    OBJECT-TYPE
    SYNTAX    SEQUENCE OF UsrIpIfbEntry
    MAX-ACCESS    not-accessible
    STATUS        current
    DESCRIPTION
        "rci uses interface block to describe the system's network interface
         which is similar to pilgrim portal."
::= {usrIpRouting 13}
usrIpIfbEntry    OBJECT-TYPE
    SYNTAX    UsrIpIfbEntry
    MAX-ACCESS    not-accessible
    STATUS        current
    DESCRIPTION
        "an entry for one ip interface block."
    INDEX {usrIpIfbEntAddr, usrIpIfbEntIfIndex}
::= {usrIpIfbTable 1}
UsrIpIfbEntry ::= SEQUENCE {
    usrIpIfbEntAddr         IpAddress,
    usrIpIfbEntIfIndex        UsrNetLogicalId,
    usrIpIfbEntIfHandle        Integer32,
    usrIpIfbEntNetMask        IpAddress,
    usrIpIfbEntOnesBc        Integer32,
    usrIpIfbEntZerosBc        Integer32,
    usrIpIfbEntReasmMaxSize    Integer32,
    usrIpIfbEntType            INTEGER,
    usrIpIfbEntNbrAddr        IpAddress,
    usrIpIfbEntAdminStatus    INTEGER,
    usrIpIfbEntStat            INTEGER,
    usrIpIfbEntPortDown        INTEGER
}
usrIpIfbEntAddr    OBJECT-TYPE
    SYNTAX        IpAddress
    MAX-ACCESS        read-only
    STATUS            current
    DESCRIPTION
        "ip network interface address, i.e. host address"
::= {usrIpIfbEntry 1}
usrIpIfbEntIfIndex    OBJECT-TYPE
    SYNTAX        UsrNetLogicalId
    MAX-ACCESS        read-only
    STATUS            current
    DESCRIPTION
        "the logical identifier of the ip network."
::={usrIpIfbEntry 2}
usrIpIfbEntIfHandle    OBJECT-TYPE
    SYNTAX        Integer32
    MAX-ACCESS        read-only
    STATUS            current
    DESCRIPTION
        "don't know yet"
::= {usrIpIfbEntry 3}
usrIpIfbEntNetMask    OBJECT-TYPE
    SYNTAX        IpAddress
    MAX-ACCESS        read-only
    STATUS            current
    DESCRIPTION
        "the subnet mask associated w/ the ip address of this entry."
::= {usrIpIfbEntry 4}
usrIpIfbEntOnesBc    OBJECT-TYPE
    SYNTAX        Integer32 (0..1)
    MAX-ACCESS        read-only
    STATUS            current
    DESCRIPTION
        "the value of the least-significant bit in the ip broadcast address
         used for sending datagrams on the (logical) interface associated w/
         the ip address of this entry."
::= {usrIpIfbEntry 5}
usrIpIfbEntZerosBc    OBJECT-TYPE
    SYNTAX        Integer32 (0..1)
    MAX-ACCESS        not-accessible
    STATUS            current
    DESCRIPTION
        "the value of the least-significant bit in the ip broadcast address
         used for sending datagrams on the (logical) interface associated w/
         the ip address of this entry."
::= {usrIpIfbEntry 6}
usrIpIfbEntReasmMaxSize    OBJECT-TYPE
    SYNTAX            Integer32 (0..65535)
    MAX-ACCESS            read-only
    STATUS                current
    DESCRIPTION
        "the size of the largest ip datagram which this entity can re-assemble
         from incoming ip fragmented datagrams received on this interface.
         it is usually equivalent to the mtu of the interface."
::= {usrIpIfbEntry 7}
usrIpIfbEntType    OBJECT-TYPE
    SYNTAX        INTEGER {
                broadcast(1),
                non-broadcast(2),
                point-to-point(3)
            }
    MAX-ACCESS        read-only
    STATUS            current
    DESCRIPTION
        "this denotes the ip network (logical) type."
::= {usrIpIfbEntry 8}
usrIpIfbEntNbrAddr    OBJECT-TYPE
    SYNTAX        IpAddress
    MAX-ACCESS        read-write
    STATUS            current
    DESCRIPTION
        "this may be needed for point to point connection."
::= {usrIpIfbEntry 9}
usrIpIfbEntAdminStatus    OBJECT-TYPE
    SYNTAX            INTEGER {
                    enabled(1),
                    disabled(2)
                }
    MAX-ACCESS            read-write
    STATUS                current
    DESCRIPTION
        "this variable is used to enable or disable this interface block"
::= {usrIpIfbEntry 10}
usrIpIfbEntStat    OBJECT-TYPE
    SYNTAX        INTEGER {
                create(1),
                delete(2)
            }
    MAX-ACCESS        read-write
    STATUS        obsolete
    DESCRIPTION
        "this variable is used to create or delete an interface block."
::= {usrIpIfbEntry 11}
usrIpIfbEntPortDown    OBJECT-TYPE
    SYNTAX        INTEGER {
                active(1),
                inactive(2)
            }
    MAX-ACCESS        read-write
    STATUS        obsolete
    DESCRIPTION
        "this variable is used to indicate the state of the hardware."
::= {usrIpIfbEntry 12}
usrIpRipGenAdminStat    OBJECT-TYPE
    SYNTAX            INTEGER {
                    enabled(1),
                    disabled(2)
                }
    MAX-ACCESS            read-write
    STATUS                current
    DESCRIPTION
        "this variable is used to disable or enable the ip rip instance at
         the rip instance level."
        --CONFIGURABLE
::= {usrIpRouting 14}
usrIpRipGenIntfCnt    OBJECT-TYPE
    SYNTAX        Integer32
    MAX-ACCESS        read-only
    STATUS            current
    DESCRIPTION
        "this variable shows the number of the ip rip interfaces."
::= {usrIpRouting 15}
usrIpRipGenNbrCnt    OBJECT-TYPE
    SYNTAX        Integer32
    MAX-ACCESS        read-only
    STATUS            current
    DESCRIPTION
        "this variable shows the number of the rip neighbours."
::= {usrIpRouting 16}
usrIpRipGenJitter    OBJECT-TYPE
    SYNTAX        INTEGER {
                enabled(1),
                disabled(2)
            }
    MAX-ACCESS        read-write
    STATUS            current
    DESCRIPTION
        "this variable is used to enable or disable the rip packet
         jitter feature."
::= {usrIpRouting 17}
usrIpRipIfTable    OBJECT-TYPE
    SYNTAX        SEQUENCE OF UsrIpRipIfEntry
    MAX-ACCESS        not-accessible
    STATUS            current
    DESCRIPTION
        "rci uses interface block to describe the system's network interface
         which is similar to pilgrim portal."
::= {usrIpRouting 18}
usrIpRipIfEntry    OBJECT-TYPE
    SYNTAX        UsrIpRipIfEntry
    MAX-ACCESS        not-accessible
    STATUS            current
    DESCRIPTION
        "an entry of rip interface block."
    INDEX {usrIpRipIfEntAddr, usrIpRipIfEntAddrLessIf}
::= {usrIpRipIfTable 1}
UsrIpRipIfEntry ::= SEQUENCE {
    usrIpRipIfEntAddr            IpAddress,
    usrIpRipIfEntAddrLessIf        Integer32,
    usrIpRipIfVersion            INTEGER,
    usrIpRipIfType                INTEGER,
    usrIpRipIfAdminStat            INTEGER,
    usrIpRipIfMetric            Integer32,
    usrIpRipIfSendDefault        INTEGER,
    usrIpRipIfAcceptDefault        INTEGER,
    usrIpRipIfSubnetsOnly        INTEGER,
    usrIpRipIfSilent            INTEGER,
    usrIpRipIfSplitHorizon        INTEGER,
    usrIpRipIfPoison            INTEGER,
    usrIpRipIfFlash                INTEGER,
    usrIpRipIfDfltRouteMetric    Integer32,
    usrIpRipIfPortDown            INTEGER,
    usrIpRipIfStat                INTEGER,
    usrIpRip2IfStatRcvBadPackets Integer32,
    usrIpRip2IfStatRcvBadRoutes     Integer32,
    usrIpRip2IfStatSendUpdates     Integer32
}
usrIpRipIfEntAddr    OBJECT-TYPE
    SYNTAX        IpAddress
    MAX-ACCESS        read-only
    STATUS            current
    DESCRIPTION
        "the interface ip address."
::= {usrIpRipIfEntry 1}
usrIpRipIfEntAddrLessIf    OBJECT-TYPE
    SYNTAX            Integer32
    MAX-ACCESS            read-only
    STATUS                current
    DESCRIPTION
        "this column is used when the interface ip address is not specified.
         in general, it is equal to network id."
::= {usrIpRipIfEntry 2}
usrIpRipIfVersion    OBJECT-TYPE
    SYNTAX        INTEGER {
                ripv1(1),
                ripv2(2)
            }
    MAX-ACCESS        read-write
    STATUS            current
    DESCRIPTION
        "this variable tells what version of rip this interface is running."
::= {usrIpRipIfEntry 3}
usrIpRipIfType    OBJECT-TYPE
    SYNTAX    INTEGER {
            broadcast(1),
            non-broadcast(2),
            point-to-point(3)
        }
    MAX-ACCESS    read-write
    STATUS        current
    DESCRIPTION
        "this variable shows the interface type, i.e. broadcast,
         non-broadcast, point-to-point and undefined."
::= {usrIpRipIfEntry 4}
usrIpRipIfAdminStat    OBJECT-TYPE
    SYNTAX        INTEGER {
                enabled(1),
                disabled(2)
            }
    MAX-ACCESS        read-write
    STATUS            current
    DESCRIPTION
        "this variable shows whether the rip is enabled for this interface."
::= {usrIpRipIfEntry 5}
usrIpRipIfMetric    OBJECT-TYPE
    SYNTAX        Integer32 (1..16)
    MAX-ACCESS        read-write
    STATUS            current
    DESCRIPTION
        "this variable is to define the metric for this interface."
::= {usrIpRipIfEntry 6}
usrIpRipIfSendDefault    OBJECT-TYPE
    SYNTAX            INTEGER {
                    enabled(1),
                    disabled(2)
                }
    MAX-ACCESS            read-write
    STATUS                current
    DESCRIPTION
        "this variable is to enable advertising the default route."
::= {usrIpRipIfEntry 7}
usrIpRipIfAcceptDefault    OBJECT-TYPE
    SYNTAX            INTEGER {
                    enabled(1),
                    disabled(2)
                }
    MAX-ACCESS            read-write
    STATUS                current
    DESCRIPTION
        "this variable is to enable accepting the default route."
::= {usrIpRipIfEntry 8}
usrIpRipIfSubnetsOnly    OBJECT-TYPE
    SYNTAX            INTEGER {
                    enabled(1),
                    disabled(2)
                }
    MAX-ACCESS            read-write
    STATUS                current
    DESCRIPTION
        "this variable is to enable this interface to advertise
         only subnet routes only."
::= {usrIpRipIfEntry 9}
usrIpRipIfSilent    OBJECT-TYPE
    SYNTAX        INTEGER {
                enabled(1),
                disabled(2)
            }
    MAX-ACCESS        read-write
    STATUS            current
    DESCRIPTION
        "this variable is to enable listen-only feature for this interface."
::= {usrIpRipIfEntry 10}
usrIpRipIfSplitHorizon    OBJECT-TYPE
    SYNTAX            INTEGER {
                    enabled(1),
                    disabled(2)
                }
    MAX-ACCESS            read-write
    STATUS                current
    DESCRIPTION
        "this variable is to enable split horizon."
::= {usrIpRipIfEntry 11}
usrIpRipIfPoison    OBJECT-TYPE
    SYNTAX        INTEGER {
                enabled(1),
                disabled(2)
            }
    MAX-ACCESS        read-write
    STATUS            current
    DESCRIPTION
        "this variable is to enable poison reverse."
::= {usrIpRipIfEntry 12}
usrIpRipIfFlash    OBJECT-TYPE
    SYNTAX        INTEGER {
                enabled(1),
                disabled(2)
            }
    MAX-ACCESS        read-write
    STATUS            current
    DESCRIPTION
        "this variable is to enable sending flash update."
::= {usrIpRipIfEntry 13}
usrIpRipIfDfltRouteMetric    OBJECT-TYPE
    SYNTAX                Integer32 (1..16)
    MAX-ACCESS                read-write
    STATUS                    current
    DESCRIPTION
        "this variable specifies the metric of the default route."
::= {usrIpRipIfEntry 14}
usrIpRipIfPortDown    OBJECT-TYPE
    SYNTAX        INTEGER {
                down(1),
                up(2)
            }
    MAX-ACCESS        read-only
    STATUS            current
    DESCRIPTION
        "this variable denotes the status of the physical port."
::= {usrIpRipIfEntry 15}
usrIpRipIfStat    OBJECT-TYPE
    SYNTAX    INTEGER {
            create(1),
            delete(2)
        }
    MAX-ACCESS    read-write
    STATUS        current
    DESCRIPTION
        "this variable is to delete the rip interface."
::= {usrIpRipIfEntry 16}
usrIpRip2IfStatRcvBadPackets    OBJECT-TYPE
    SYNTAX                Integer32
    MAX-ACCESS                read-only
    STATUS                    current
    DESCRIPTION
        "ripv2 received bad packet counter."
::= {usrIpRipIfEntry 17}
usrIpRip2IfStatRcvBadRoutes    OBJECT-TYPE
    SYNTAX                Integer32
    MAX-ACCESS                read-only
    STATUS                    current
    DESCRIPTION
        "ripv2 received bad route counter."
::= {usrIpRipIfEntry 18}
usrIpRip2IfStatSendUpdates    OBJECT-TYPE
    SYNTAX                Integer32
    MAX-ACCESS                read-only
    STATUS                    current
    DESCRIPTION
        "ripv2 sent update packet counter."
::= {usrIpRipIfEntry 19}
usrIpRip2IfConfTable    OBJECT-TYPE
    SYNTAX            SEQUENCE OF UsrIpRip2IfConfEntry
    MAX-ACCESS            not-accessible
    STATUS                current
    DESCRIPTION
        "table for ripv2 specific interface configuration information"
::= {usrIpRouting 19}
usrIpRip2IfConfEntry    OBJECT-TYPE
    SYNTAX            UsrIpRip2IfConfEntry
    MAX-ACCESS            not-accessible
    STATUS                current
    DESCRIPTION
        "an entry of ripv2 interface configuration table."
    INDEX {rip2IfConfAddress, rip2IfConfIndex}
::= {usrIpRip2IfConfTable 1}
UsrIpRip2IfConfEntry ::= SEQUENCE {
    rip2IfConfAddress            IpAddress,
    rip2IfConfIndex                Integer32,
    rip2IfConfDomain            Integer32,
    rip2IfConfAuthType            INTEGER,
    rip2IfConfAuthKey            OCTET STRING,
    rip2IfConfSend                INTEGER,
    rip2IfConfReceive            INTEGER,
    rip2IfConfDefaultMetric        Integer32,
    rip2IfConfStatus            INTEGER,
    rip2IfConfSrcAddress        Integer32
}
rip2IfConfAddress    OBJECT-TYPE
    SYNTAX        IpAddress
    MAX-ACCESS        read-only
    STATUS            current
    DESCRIPTION
        "the network interface address."
::= {usrIpRip2IfConfEntry 1}
rip2IfConfIndex    OBJECT-TYPE
    SYNTAX        Integer32
    MAX-ACCESS        read-only
    STATUS            current
    DESCRIPTION
        "the network id."
::= {usrIpRip2IfConfEntry 2}
rip2IfConfDomain    OBJECT-TYPE
    SYNTAX        Integer32
    MAX-ACCESS        not-accessible
    STATUS        obsolete
    DESCRIPTION
        "this thing is obsolete."
::= {usrIpRip2IfConfEntry 3}
rip2IfConfAuthType    OBJECT-TYPE
    SYNTAX        INTEGER {
                none(1),
                simple(2),
                md5(3)
            }
    MAX-ACCESS        read-write
    STATUS            current
    DESCRIPTION
        "this variable specifies the authentication type.  md5 is not 
         supported in this version yet."
::= {usrIpRip2IfConfEntry 4}
rip2IfConfAuthKey    OBJECT-TYPE
    SYNTAX        OCTET STRING (SIZE(16))
    MAX-ACCESS        read-write
    STATUS            current
    DESCRIPTION
        "the authentication key is defined here."
::= {usrIpRip2IfConfEntry 5}
rip2IfConfSend        OBJECT-TYPE
    SYNTAX        INTEGER {
                none(1),
                version1(2),
                compatible(3),
                version2(4)
            }
    MAX-ACCESS        read-write
    STATUS            current
    DESCRIPTION
        "this variable defines the send policy."
::= {usrIpRip2IfConfEntry 6}
rip2IfConfReceive    OBJECT-TYPE
    SYNTAX        INTEGER {
                version1(1),
                version2(2),
                both(3),
                none(4)
            }
    MAX-ACCESS        read-write
    STATUS            current
    DESCRIPTION
        "this variable defines the receive policy."
::= {usrIpRip2IfConfEntry 7}
rip2IfConfDefaultMetric    OBJECT-TYPE
    SYNTAX        Integer32
    MAX-ACCESS        read-write
    STATUS            current
    DESCRIPTION
        "this variable defines the default metric of this network interface."
::= {usrIpRip2IfConfEntry 8}
rip2IfConfStatus    OBJECT-TYPE
    SYNTAX        INTEGER {
                enabled(1),
                disabled(2)
            }
    MAX-ACCESS        read-write
    STATUS            current
    DESCRIPTION
        ""
::= {usrIpRip2IfConfEntry 9}
rip2IfConfSrcAddress    OBJECT-TYPE
    SYNTAX            Integer32
    MAX-ACCESS            read-only
    STATUS                current
    DESCRIPTION
        ""
::= {usrIpRip2IfConfEntry 10}
usrIpDelRouteAll OBJECT-TYPE
    SYNTAX  Integer32
    MAX-ACCESS  read-write
    STATUS      current
    DESCRIPTION
        "This object is used to clear the whole routing table
         - setting this object with ANY value will do this."
::= { usrIpRouting 20 }
usrIPRterBaseCfgFileName OBJECT-TYPE
    SYNTAX   DisplayString 
    MAX-ACCESS   read-write
    STATUS       current
    DESCRIPTION 
        "The name of a ConfigFile to read/write
         permanent database records. If the value of this
         object is an empty string, then the SLIP process
         uses the default name `@file://SlipFile.cfg'."
::= { usrIpRouting 21 } 
usrIPRterBaseCFMSaveStatus OBJECT-TYPE
    SYNTAX  UsrConfigStatus
    MAX-ACCESS  read-write
    STATUS      current
    DESCRIPTION
        "Setting the value of this object to `save'
         causes the values of the SLIP Base Group
         entries to be written out to the current SLIP
         config file. While the new config file is being
         written, the SLIP process will set the value
         of this flag set to `saving''. Any attempts to set
         the value while it is  not `normal' (i.e. the file
         is currently being written to the config file)
         while result in a badValue error being returned.
         Setting the value to `normal' will result in no
         action."
::= { usrIpRouting 22 }
-- ------------------------------------------------------------
          -- the USR IP Routing Table Head Structure
usrIpRTH OBJECT-TYPE
    SYNTAX  SEQUENCE OF UsrIpRTHEntry
    MAX-ACCESS  not-accessible
    STATUS      current
    DESCRIPTION
        "This entity's IP Routing table."
::= { usrIpRouting 23 }
usrIpRTHEntry OBJECT-TYPE
    SYNTAX  UsrIpRTHEntry
    MAX-ACCESS  not-accessible
    STATUS      current
    DESCRIPTION
        "A route to a particular destination.
         These routes are learned or written from
         the forwarder and so these objects are
         not accessible for SET via CLI or SNMP.
         The only PDU type implemented is GETNEXT."
    INDEX   { usrIpRTHDest, usrIpRTHMask, usrIpRTHNhId }
::= { usrIpRTH 1 }
          UsrIpRTHEntry ::=
              SEQUENCE {
                  usrIpRTHDest      IpAddress,
                  usrIpRTHMask      IpAddress,
                  usrIpRTHProto     INTEGER,
                  usrIpRTHMetric    Integer32,
                  usrIpRTHClass     Integer32,
                  usrIpRTHFwdFlags  Integer32,
                  usrIpRTHAge       Integer32,
                  usrIpRTHNhId      Integer32,
                  usrIpRTHNextHop   IpAddress,
                  usrIpRTHIfIndex   Integer32
              }
usrIpRTHDest OBJECT-TYPE
    SYNTAX  IpAddress
    MAX-ACCESS  read-write
    STATUS      current
    DESCRIPTION
            "The destination IP address of this route.  An
            entry with a value of 0.0.0.0 is considered a
            default route.  Multiple routes to a single
            destination can appear in the table, but access to
            such multiple entries is dependent on the table-
            access mechanisms defined by the network
            management protocol in use."
   --CONFIGURABLE
::= { usrIpRTHEntry 1 }
usrIpRTHMask OBJECT-TYPE
    SYNTAX  IpAddress
    MAX-ACCESS  read-write
    STATUS      current
    DESCRIPTION
            "Indicate the mask to be logical-ANDed with the
            destination address before being compared to the
            value in the ipRTHDest field.  For those systems
            that do not support arbitrary subnet masks, an
            agent constructs the value of the ipRTHMask by
            determining whether the value of the correspondent
            ipRTHDest field belong to a class-A, B, or C
            network, and then using one of:
                 mask           network
                 255.0.0.0      class-A
                 255.255.0.0    class-B
                 255.255.255.0  class-C
            If the value of the ipRTHDest is 0.0.0.0 (a
            default route), then the mask value is also
            0.0.0.0.  It should be noted that all IP routing
            subsystems implicitly use this mechanism."
    --CONFIGURABLE
::= { usrIpRTHEntry 2 }
usrIpRTHProto OBJECT-TYPE
    SYNTAX  INTEGER {
                other(0),       -- none of the following
                local(1),       -- static local
                remote(2),      -- static remote
                special(3),     -- static special
                                -- the remaining values are
                                -- all gateway routing
                                -- protocols
                ospf(4),        -- OSPF
                ospfExt(5),     -- OSPF External
                ospfDisc3(6),   -- OSPF discard routes
                ospfDisc7(7),   -- OSPF discard routes
                rip(8),         -- RIP
                ripDisc(9),     -- RIP discard routes
                egp(10),        -- EGP
                bgpExt(11),     -- BGP External
                bgpInt(12),     -- BGP Internal
                bgpAggrDisc(13),-- BGP Aggregate
                redistrib(14)   -- Server redistribution
                      }
    MAX-ACCESS  read-only
    STATUS      current
    DESCRIPTION
            "The routing mechanism via which this route was
            learned.  Inclusion of values for gateway routing
            protocols is not intended to imply that hosts
            should support those protocols."
::= { usrIpRTHEntry 3 }
usrIpRTHMetric OBJECT-TYPE
    SYNTAX  Integer32
    MAX-ACCESS  read-write
    STATUS      current
    DESCRIPTION
            "The primary routing metric for this route.  The
            semantics of this metric are determined by the
            routing-protocol specified in the route's
            ipRTHProto value.  If this metric is not used,
            its value should be set to -1."
    --CONFIGURABLE
::= { usrIpRTHEntry 4 }
usrIpRTHClass OBJECT-TYPE
    SYNTAX  Integer32
    MAX-ACCESS  read-write
    STATUS      current
    DESCRIPTION
            "The forward class is preference class associated
            with this route.  There are 3 classes; the lower
            the class the more preferred the route.  
            Local routes are in Class 0.  These are the 
            most preferred routes.
            OSPF Internal routes are also in Class 0.  OSPF
            internal routes are less preferred than Local
            Routes.
            OSPF External routes are Class 1 or Class 2.
            Static configured and RIP routes are Class 1.
            BGP and EGP routes are Class 2."
::= { usrIpRTHEntry 5 }
usrIpRTHFwdFlags OBJECT-TYPE
    SYNTAX  Integer32
    MAX-ACCESS  read-write
    STATUS      current
    DESCRIPTION
            "Forward flags are hints to the forwarding engine
            as to what to do with the incoming packet."
::= { usrIpRTHEntry 6 }
usrIpRTHAge OBJECT-TYPE
    SYNTAX  Integer32
    MAX-ACCESS  read-write
    STATUS      current
    DESCRIPTION
            "The number of seconds since this route was last
            updated or otherwise determined to be correct.
            Note that no semantics of `too old' can be implied
            except through knowledge of the routing protocol
            by which the route was learned."
::= { usrIpRTHEntry 7 }
usrIpRTHNhId OBJECT-TYPE
    SYNTAX  Integer32
    MAX-ACCESS  read-write
    STATUS      current
    DESCRIPTION
            "The index into the globally defined Next Hop
             Block."
::= { usrIpRTHEntry 8 }
usrIpRTHNextHop OBJECT-TYPE
    SYNTAX  IpAddress
    MAX-ACCESS  read-write
    STATUS      current
    DESCRIPTION
            "The IP address of the next hop of this route.
            (In the case of a route bound to an interface
            which is realized via a broadcast media, the value
            of this field is the agent's IP address on that
            interface.)"
    --CONFIGURABLE
::= { usrIpRTHEntry 9 }
usrIpRTHIfIndex OBJECT-TYPE
    SYNTAX  Integer32
    MAX-ACCESS  read-write
    STATUS      current
    DESCRIPTION
            "The index value which uniquely identifies the
            local interface through which the next hop of this
            route should be reached.  The interface identified
            by a particular value of this index is the same
            interface as identified by the same value of
            ifIndex."
::= { usrIpRTHEntry 10 }
-- ------------------------------------------------------------
-- the USR IP Routing Table Entry Structure
usrIpRTE OBJECT-TYPE
    SYNTAX  SEQUENCE OF UsrIpRTEEntry
    MAX-ACCESS  not-accessible
    STATUS      current
    DESCRIPTION
            "This entity's IP Routing table."
::= { usrIpRouting 24 }
usrIpRTEEntry OBJECT-TYPE
    SYNTAX  UsrIpRTEEntry
    MAX-ACCESS  not-accessible
    STATUS      current
    DESCRIPTION
            "A route to a particular destination.
             These routes are learned or written from
             the forwarder and so these objects are
             not accessible for SET via CLI or SNMP.
             The only PDU type implemented is GETNEXT."
    INDEX   { usrIpRTEDest, usrIpRTEMask, usrIpRTEPref,
              usrIpRTEMetric, usrIpRTEProto, usrIpRTENhId }
::= { usrIpRTE 1 }
    UsrIpRTEEntry ::=
              SEQUENCE {
                  usrIpRTEDest      IpAddress,
                  usrIpRTEMask      IpAddress,
                  usrIpRTEProto     INTEGER,
                  usrIpRTEMetric    Integer32,
                  usrIpRTEAge       Integer32,
                  usrIpRTEFwdFlags  Integer32,
                  usrIpRTEPref      Integer32,
                  usrIpRTENhId      Integer32,
                  usrIpRTENextHop   IpAddress,
                  usrIpRTEIfIndex   Integer32
              }
usrIpRTEDest OBJECT-TYPE
    SYNTAX  IpAddress
    MAX-ACCESS  read-write
    STATUS      current
    DESCRIPTION
            "The destination IP address of this route.  An
            entry with a value of 0.0.0.0 is considered a
            default route.  Multiple routes to a single
            destination can appear in the table, but access to
            such multiple entries is dependent on the table-
            access mechanisms defined by the network
            management protocol in use."
    --CONFIGURABLE
::= { usrIpRTEEntry 1 }
usrIpRTEMask OBJECT-TYPE
    SYNTAX  IpAddress
    MAX-ACCESS  read-write
    STATUS      current
    DESCRIPTION
            "Indicate the mask to be logical-ANDed with the
            destination address before being compared to the
            value in the ipRTEDest field.  For those systems
            that do not support arbitrary subnet masks, an
            agent constructs the value of the ipRTEMask by
            determining whether the value of the correspondent
            ipRTEDest field belong to a class-A, B, or C
            network, and then using one of:
                 mask           network
                 255.0.0.0      class-A
                 255.255.0.0    class-B
                 255.255.255.0  class-C
            If the value of the ipRTEDest is 0.0.0.0 (a
            default route), then the mask value is also
            0.0.0.0.  It should be noted that all IP routing
            subsystems implicitly use this mechanism."
    --CONFIGURABLE
::= { usrIpRTEEntry 2 }
usrIpRTEProto OBJECT-TYPE
    SYNTAX  INTEGER {
                other(0),       -- none of the following
                local(1),       -- static local
                remote(2),      -- static remote
                special(3),     -- static special
                                -- the remaining values are
                                -- all gateway routing
                                -- protocols
                ospf(4),        -- OSPF
                ospfExt(5),     -- OSPF External
                ospfDisc3(6),   -- OSPF discard routes
                ospfDisc7(7),   -- OSPF discard routes
                rip(8),         -- RIP
                ripDisc(9),     -- RIP discard routes
                egp(10),        -- EGP
                bgpExt(11),     -- BGP External
                bgpInt(12),     -- BGP Internal
                bgpAggrDisc(13),-- BGP Aggregate
                redistrib(14)   -- Server redistribution
            }
    MAX-ACCESS  read-only
    STATUS      current
    DESCRIPTION
            "The routing mechanism via which this route was
            learned.  Inclusion of values for gateway routing
            protocols is not intended to imply that hosts
            should support those protocols."
::= { usrIpRTEEntry 3 }
usrIpRTEMetric OBJECT-TYPE
    SYNTAX  Integer32
    MAX-ACCESS  read-write
    STATUS      current
    DESCRIPTION
            "The primary routing metric for this route.  The
            semantics of this metric are determined by the
            routing-protocol specified in the route's
            ipRTEProto value.  If this metric is not used,
            its value should be set to -1."
    --CONFIGURABLE
::= { usrIpRTEEntry 4 }
usrIpRTEAge OBJECT-TYPE
    SYNTAX  Integer32
    MAX-ACCESS  read-write
    STATUS      current
    DESCRIPTION
            "The number of seconds since this route was last
            updated or otherwise determined to be correct.
            Note that no semantics of `too old' can be implied
            except through knowledge of the routing protocol
            by which the route was learned."
::= { usrIpRTEEntry 5 }
usrIpRTEFwdFlags OBJECT-TYPE
    SYNTAX  Integer32
    MAX-ACCESS  read-write
    STATUS      current
    DESCRIPTION
            "Forward flags are hints to the forwarding engine
            as to what to do with the incoming packet."
::= { usrIpRTEEntry 6 }
usrIpRTEPref OBJECT-TYPE
    SYNTAX  Integer32
    MAX-ACCESS  read-write
    STATUS      current
    DESCRIPTION
            "The preference associated with this route after
            it has been added to the routing table."
::= { usrIpRTEEntry 7 }
usrIpRTENhId OBJECT-TYPE
    SYNTAX  Integer32
    MAX-ACCESS  read-write
    STATUS      current
    DESCRIPTION
            "The index into the globally defined Next Hop
             Block."
::= { usrIpRTEEntry 8 }
usrIpRTENextHop OBJECT-TYPE
    SYNTAX  IpAddress
    MAX-ACCESS  read-write
    STATUS      current
    DESCRIPTION
            "The IP address of the next hop of this route.
            (In the case of a route bound to an interface
            which is realized via a broadcast media, the value
            of this field is the agent's IP address on that
            interface.)"
    --CONFIGURABLE
::= { usrIpRTEEntry 9 }
usrIpRTEIfIndex OBJECT-TYPE
    SYNTAX  Integer32
    MAX-ACCESS  read-write
    STATUS      current
    DESCRIPTION
            "The index value which uniquely identifies the
            local interface through which the next hop of this
            route should be reached.  The interface identified
            by a particular value of this index is the same
            interface as identified by the same value of
            ifIndex."
::= { usrIpRTEEntry 10 }
usrIpRipRXPacketCount    OBJECT-TYPE
    SYNTAX    Integer32
      MAX-ACCESS    read-only
      STATUS        current
      DESCRIPTION
              "Number of IP RIP packets received."
::= {usrIpRouting 26}
usrIpRipTXPacketCount    OBJECT-TYPE
    SYNTAX    Integer32
      MAX-ACCESS    read-only
      STATUS        current
      DESCRIPTION
              "Number of IP RIP packets transmitted."
::= {usrIpRouting 27}
usrIpRipIncorrectPacketCount    OBJECT-TYPE
    SYNTAX    Integer32
      MAX-ACCESS    read-only
      STATUS        current
      DESCRIPTION
              "Number of incorrect IP RIP packets received."
::= {usrIpRouting 28}
-- ------------------------------------------------------------
END     -- End of USR-IP-ROUTING-MIB DEFINITIONS
--
--	usr_ip_cfg.mib
--
--
-- Author:         Jim Halpin
--
USR-IP-CFG-MIB DEFINITIONS ::= BEGIN
	IMPORTS
          OBJECT-TYPE, MODULE-IDENTITY,
          Integer32
                  FROM SNMPv2-SMI
          common, UsrDisplayString
                  FROM USR-DEFINITIONS-MIB;
usrIpCfg MODULE-IDENTITY
        LAST-UPDATED "200205051800Z"
        ORGANIZATION "CommWorks Corporation, a 3Com Company"
        CONTACT-INFO "Customer Support"
        DESCRIPTION
           "The commWorks enterprise defined MIB objects IP
            Configuration."
--      REVISION "200205051800Z"
--      DESCRIPTION "Converted to SNMPv2"
        ::= { common 13 }
   -- Begin managed object definitions here...
usrIpCfgNetworkTable OBJECT-TYPE
	SYNTAX SEQUENCE OF UsrIpCfgNetworkEntry
	MAX-ACCESS not-accessible
	STATUS     current
	DESCRIPTION
		"This table is the same as the usrIpNetworkTable definied above,
		 with the exception that it is indexed by the Network Name defined
		 in the usrCfgNetworkTable. This table will be used only by the
		 the Configuration File Manager process to load permament configuration
		 file records for named networks at system boot time. Any attempt
		 to set this table from either the CLI process or SNMP will
		 fail."
::= { usrIpCfg 1 }
usrIpCfgNetworkEntry OBJECT-TYPE
	SYNTAX UsrIpCfgNetworkEntry
	MAX-ACCESS not-accessible
	STATUS     current
	DESCRIPTION
		"A (conceptual) entry for one IP Network."
	INDEX { usrIpCfgNetName }
::= { usrIpCfgNetworkTable 1 }
UsrIpCfgNetworkEntry ::= SEQUENCE {
	usrIpCfgNetName			    UsrDisplayString,
	usrIpCfgNetBcastAddr		Integer32,
	usrIpCfgNetReasmMaxSize		Integer32,
	usrIpCfgNetRoutingProtocol	INTEGER,  -- deprecated
	usrIpCfgNetSendDefaultRoutePolicy 		INTEGER,
	usrIpCfgNetSendRoutesPolicy 			INTEGER,
	usrIpCfgNetSendSubnetsOnlyPolicy 		INTEGER,
	usrIpCfgNetAcceptDefaultRoutePolicy 	INTEGER,
	usrIpCfgNetSilentPolicy 				INTEGER,
	usrIpCfgNetSplitHorizonPolicy 		INTEGER,
	usrIpCfgNetPoisonReversePolicy 		INTEGER,
	usrIpCfgNetFlashUpdatePolicy 			INTEGER,
	usrIpCfgNetSimpleAuthenPolicy			INTEGER,
	usrIpCfgNetSendRipV1CompatPolicy 		INTEGER,
	usrIpCfgNetRcvRipV1Policy	 		INTEGER,
	usrIpCfgNetRcvRipV2Policy	 		INTEGER,
	usrIpCfgNetRip2AuthKey			OCTET STRING,
	usrIpCfgNetRoutingMetric       		Integer32,
	usrIpCfgNetExportMetric       		Integer32,
	usrIpCfgNetRoutingNone			     INTEGER,
	usrIpCfgNetRoutingRipV1				INTEGER,
	usrIpCfgNetRoutingRipV2				INTEGER,
	usrIpCfgNetRoutingOspf				INTEGER
	}
usrIpCfgNetName OBJECT-TYPE
	SYNTAX          UsrDisplayString (SIZE (1..32))
	MAX-ACCESS      not-accessible
	STATUS          current
	DESCRIPTION
		"The name of this network. Network names can either be assigned
           by a network administrator when the Network is created. Or it will
           generated by the Configuration Process when it adds the network to
		 its internal table."
::= { usrIpCfgNetworkEntry 1}
usrIpCfgNetBcastAddr OBJECT-TYPE
     SYNTAX  Integer32
     MAX-ACCESS  read-write
	STATUS      current
     DESCRIPTION
          "The value of the least-significant bit in the IP
           broadcast address used for sending datagrams on
           the (logical) interface associated with the IP
           address of this entry.  For example, when the
           Internet standard all-ones broadcast address is
           used, the value will be 1.  This value applies to
           both the subnet and network broadcasts addresses
           used by the entity on this (logical) interface."
	--CONFIGURABLE
::= { usrIpCfgNetworkEntry 4 }
usrIpCfgNetReasmMaxSize OBJECT-TYPE
     SYNTAX  Integer32 (0..65535)
     MAX-ACCESS  read-write
     STATUS      current
     DESCRIPTION
		"The size of the largest IP datagram which this
           entity can re-assemble from incoming IP fragmented
           datagrams received on this interface."
	--CONFIGURABLE
::= { usrIpCfgNetworkEntry 5 }
usrIpCfgNetRoutingProtocol	OBJECT-TYPE
	SYNTAX INTEGER {
			none(0),
			ripv1(1),
			ripv2(2)
		}
	MAX-ACCESS read-write
	STATUS deprecated
	DESCRIPTION
		"The routing protocol to be operated on this IP network.  Currently,
		 there are none, rip version 1 and rip version 2."
     -- CONFIGURABLE
::= { usrIpCfgNetworkEntry 6 }
usrIpCfgNetSendDefaultRoutePolicy OBJECT-TYPE
	SYNTAX	INTEGER {
		disable(0),
		enable(1)
	}
	MAX-ACCESS	read-write
	STATUS	    current
	DESCRIPTION
		"Allows disabling or enabling of the send default route RIP policy.
		 This policy is enabled by default."
	--CONFIGURABLE
::= { usrIpCfgNetworkEntry 7 }
usrIpCfgNetSendRoutesPolicy OBJECT-TYPE
	SYNTAX	INTEGER {
		disable(0),
		enable(1)
	}
	MAX-ACCESS	read-write
	STATUS	    current
	DESCRIPTION
		"Allows disabling or enabling of the send routes RIP policy.
		 This policy is enabled by default."
	--CONFIGURABLE
::= { usrIpCfgNetworkEntry 8 }
usrIpCfgNetSendSubnetsOnlyPolicy OBJECT-TYPE
	SYNTAX	INTEGER {
		disable(0),
		enable(1)
	}
	MAX-ACCESS	read-write
	STATUS	    current
	DESCRIPTION
		"Allows disabling or enabling of the send subnets only RIP policy.
		 This policy is enabled by default."
	--CONFIGURABLE
::= { usrIpCfgNetworkEntry 9 }
usrIpCfgNetAcceptDefaultRoutePolicy OBJECT-TYPE
	SYNTAX	INTEGER {
		disable(0),
		enable(1)
	}
	MAX-ACCESS	read-write
	STATUS	    current
	DESCRIPTION
		"Allows disabling or enabling of the accept default route RIP policy.
		 This policy is disabled by default."
	--CONFIGURABLE
::= { usrIpCfgNetworkEntry 10 }
usrIpCfgNetSilentPolicy OBJECT-TYPE
	SYNTAX	INTEGER {
		disable(0),
		enable(1)
	}
	MAX-ACCESS	read-write
	STATUS	    current
	DESCRIPTION
		"Allows disabling or enabling of the silent policy.
		 This policy is disabled by default."
	--CONFIGURABLE
::= { usrIpCfgNetworkEntry 11 }
usrIpCfgNetSplitHorizonPolicy OBJECT-TYPE
	SYNTAX	INTEGER {
		disable(0),
		enable(1)
	}
	MAX-ACCESS	read-write
	STATUS	    current
	DESCRIPTION
		"Allows disabling or enabling of the split horizon RIP policy.
		 This policy is enabled by default."
	--CONFIGURABLE
::= { usrIpCfgNetworkEntry 12 }
usrIpCfgNetPoisonReversePolicy OBJECT-TYPE
	SYNTAX	INTEGER {
		disable(0),
		enable(1)
	}
	MAX-ACCESS	read-write
	STATUS	    current
	DESCRIPTION
		"Allows disabling or enabling of the poison reverse RIP policy.
	 	 This policy is enabled by default."
	--CONFIGURABLE
::= { usrIpCfgNetworkEntry 13 }
usrIpCfgNetFlashUpdatePolicy OBJECT-TYPE
	SYNTAX	INTEGER {
		disable(0),
		enable(1)
	}
	MAX-ACCESS	read-write
	STATUS	    current
	DESCRIPTION
		"Allows disabling or enabling of the flash update RIP policy.
		 This policy is enabled by default."
	--CONFIGURABLE
::= { usrIpCfgNetworkEntry 14 }
usrIpCfgNetSimpleAuthenPolicy OBJECT-TYPE
	SYNTAX	INTEGER {
		disable(0),
		enable(1)
	}
	MAX-ACCESS	read-write
	STATUS	    current
	DESCRIPTION
		"Allows disabling or enabling of the simple authentication RIP policy.
		 This policy is valid for RIPV2 only and is enabled by default when
		 RIPV2 is selected as the routing protocol."
	--CONFIGURABLE
::= { usrIpCfgNetworkEntry 15 }
usrIpCfgNetSendRipV1CompatPolicy OBJECT-TYPE
	SYNTAX	INTEGER {
		disable(0),
		enable(1)
	}
	MAX-ACCESS	read-write
	STATUS	    current
	DESCRIPTION
		"Allows disabling or enabling of the send RipV1 compatible policy.
		 This policy is enabled by default."
	--CONFIGURABLE
::= { usrIpCfgNetworkEntry 16 }
usrIpCfgNetRcvRipV1Policy OBJECT-TYPE
	SYNTAX	INTEGER {
		disable(0),
		enable(1)
	}
	MAX-ACCESS	read-write
	STATUS	    current
	DESCRIPTION
		"Allows disabling or enabling of the receive RipV1 policy.
		 This policy is enabled by default."
	--CONFIGURABLE
::= { usrIpCfgNetworkEntry 17 }
usrIpCfgNetRcvRipV2Policy OBJECT-TYPE
	SYNTAX	INTEGER {
		disable(0),
		enable(1)
	}
	MAX-ACCESS	read-write
	STATUS	    current
	DESCRIPTION
		"Allows disabling or enabling of the receive RipV2 policy.
		 This policy is enabled by default."
	--CONFIGURABLE
::= { usrIpCfgNetworkEntry 18 }
usrIpCfgNetRip2AuthKey OBJECT-TYPE
	SYNTAX OCTET STRING (SIZE(16))
	MAX-ACCESS read-write
	STATUS     current
	DESCRIPTION
		"this variable defines the authentication key for ip rip2.  when
		 this varialbe is set, by default, the authentication type is also
		 set to simple."
	--CONFIGURABLE
::= { usrIpCfgNetworkEntry 19 }
usrIpCfgNetRoutingMetric OBJECT-TYPE
        SYNTAX Integer32 (1..16)
        MAX-ACCESS read-write
        STATUS     current
        DESCRIPTION
                "The routing metric for using this IP network."
        --CONFIGURABLE
::= { usrIpCfgNetworkEntry 20 }
usrIpCfgNetExportMetric OBJECT-TYPE
        SYNTAX Integer32 (0..15)
        MAX-ACCESS read-write
        STATUS     current
        DESCRIPTION
                "The  metric for advertising routes through this IP network."
        --CONFIGURABLE
::= { usrIpCfgNetworkEntry 21 }
usrIpCfgNetRoutingNone	OBJECT-TYPE
	SYNTAX INTEGER {
			disable(0),
			enable(1)
		}
	MAX-ACCESS read-write
	STATUS     current
	DESCRIPTION
		"Specifies that no routing protocol will be operating on this 
           IP network."
	--CONFIGURABLE
::= { usrIpCfgNetworkEntry 22 }
usrIpCfgNetRoutingRipV1	OBJECT-TYPE
	SYNTAX INTEGER {
			disable(0),
			enable(1)
		}
	MAX-ACCESS read-write
	STATUS     current
	DESCRIPTION
		"Specifies that the RIPv1 routing protocol will be operating
           on this IP network."
	--CONFIGURABLE
::= { usrIpCfgNetworkEntry 23 } 
usrIpCfgNetRoutingRipV2	OBJECT-TYPE
	SYNTAX INTEGER {
			disable(0),
			enable(1)
		}
	MAX-ACCESS read-write
	STATUS     current
	DESCRIPTION
		"Specifies that the RIPv2 routing protocol will be operating
           on this IP network."
	--CONFIGURABLE
::= { usrIpCfgNetworkEntry 24 }
usrIpCfgNetRoutingOspf	OBJECT-TYPE
	SYNTAX INTEGER {
			disable(0),
			enable(1)
		}
	MAX-ACCESS read-write
	STATUS     current
	DESCRIPTION
		"Specifies that the OSPF routing protocol will be operating
           on this IP network."
	--CONFIGURABLE
::= { usrIpCfgNetworkEntry 25 }
END         -- End Template MIB definitions
-- ************************************************************************
--
--	filter.mib - Filter MIB file
--
-- Author:         Fritz Reeve
--
Usr-Filter-MIB DEFINITIONS ::= BEGIN
        IMPORTS
          OBJECT-TYPE, MODULE-IDENTITY, Integer32
                  FROM SNMPv2-SMI
          UsrDisplayString, common, UsrConfigStatus, UsrFilterName
                  FROM USR-DEFINITIONS-MIB;
usrFilter MODULE-IDENTITY
        LAST-UPDATED "200205022050Z"
        ORGANIZATION "CommWorks Corporation, a 3Com Company"
        CONTACT-INFO "Customer Support"
        DESCRIPTION
             "The commWorks enterprise defined MIB objects
                   for Filtering."
--      REVISION  "200205022050Z"
--      DESCRIPTION "Converted to SNMPv2."
     ::= { common 16 }
   -- textual conventions
   -- Begin managed object definitions here...
     usrFilterConfigFileName OBJECT-TYPE
         SYNTAX          UsrDisplayString
         MAX-ACCESS      read-only
         STATUS          current
         DESCRIPTION             
            "The name of a ConfigFile to read/write permanent database
             records.  If the value of this object is an empty string, 
             then the Filter Manager process uses the default name 
             `@file://filter.cfg'. "
     ::= { usrFilter 1 }
     usrFilterCFMStatusFlag  OBJECT-TYPE
         SYNTAX      UsrConfigStatus
         MAX-ACCESS      read-write
         STATUS          current
         DESCRIPTION
            "Setting the value of this object to `save' causes the values
             of the SNMP Group to be written out to the current config
             file, which is stored in the usrFilterConfigFileName object.
             While the new ConfigFile is being written, the SNMP process
             will set the value of this flag to `saving''. Any
             attempts to set the value while it is not `normal'
             (i.e. the file is currently being written to the
             ConfigFile) will result in a badValue error being
             returned. Setting the value to `normal' will result in no
             action."
     ::= { usrFilter 2 }
     usrFilterTable OBJECT-TYPE
         SYNTAX   SEQUENCE OF UsrFilterEntry
         MAX-ACCESS   not-accessible
         STATUS       current
         DESCRIPTION
            "A table of packet filter names.  The actual filter
             information is stored in an ASCII file in flash."
     ::= { usrFilter 3 }
     usrFilterEntry OBJECT-TYPE
         SYNTAX   UsrFilterEntry
         MAX-ACCESS   not-accessible
         STATUS       current
         DESCRIPTION
                "The parameters for a packet filter."
         INDEX {usrFilterName}
     ::= { usrFilterTable 1 }
     --
     -- The row is composed of these components
     --
     UsrFilterEntry ::=
         SEQUENCE {
         usrFilterName
            UsrFilterName,
         usrFilterStatus
            INTEGER,
         usrFilterProtocols
            INTEGER,
         usrFilterVerifyError
            UsrDisplayString
     }
     usrFilterName OBJECT-TYPE
         SYNTAX  UsrFilterName
         MAX-ACCESS  not-accessible
         STATUS      current
         DESCRIPTION
            "The character name for this filter."
     ::= { usrFilterEntry 1 }
     usrFilterStatus OBJECT-TYPE
         SYNTAX  INTEGER {
                         normal(1),
                         delete(2),
                         verify(3),
                         reading(4),       -- File reading in progress
                         verifying(5),     -- Filter verification in progress
                         compiling(6),     -- Filter compilation in progress
                         verifyFailed(7),  -- Filter verification failed
                         starting(8)       -- Filter operation starting
                         }
         MAX-ACCESS  read-write
         STATUS      current
         DESCRIPTION
            "The status of this filter entry. Valid row entries in this
             table have the status field set to normal. The settable values
             are normal and delete.  If the instance is not in the table 
             and the status is normal, this will be an add operation.  If the
             instance is in the table and the status is normal, this will be a
             modify operation.  If the instance is in the table and the 
             status is delete, this will be a delete operation.  The values 
             reading, verifying, and compiling are read-only."
         --CONFIGURABLE
     ::= { usrFilterEntry 2 }
     usrFilterProtocols OBJECT-TYPE
         SYNTAX  INTEGER {
                         bridge(1),        -- Bridge filter
                         bridge-call(2),   -- Bridge Call filter
                         ip(4),            -- IP filter
                         ip-call(8),       -- IP Call filter
                         ipx(16),          -- IPX filter
                         ipx-call(32),     -- IPX Call filter
                         atalk(64),        -- AppleTalk filter
                         atalk-call(128),  -- Appletalk Call filter
                         rip(256),         -- IP RIP filter
                         xrip(512),        -- IPX RIP filter
                         sap(1024),        -- IPX SAP filter
                         rtmp(2048),       -- AppleTalk RTMP filter
                         zip(4096),        -- Appletalk ZIP filter
                         access(8192),     -- Login Access filter
					arap(16384)       -- ARAP Zone filter 
                         }
         MAX-ACCESS  read-only
         STATUS      current
         DESCRIPTION
            "Packet filters can be created for the following protocols:
             BRIDGE, IP, IPX, AppleTalk, IP-RIP, IPX-RIP, IPX-SAP, ATALK-RTMP.
             There will be others in the future.  This object uses the 32 bit 
             integer as a bit field.  A single filter specification may contain
             one or more protocols."
     ::= { usrFilterEntry 3 }
     usrFilterVerifyError OBJECT-TYPE
         SYNTAX      UsrDisplayString
         MAX-ACCESS  read-only
         STATUS      current
         DESCRIPTION
            "The error string returned when a filter fails its verification
             process.  Otherwise, this field is NULL."
     ::= { usrFilterEntry 4 }
 usrFilterPktLogFlag OBJECT-TYPE
         SYNTAX  INTEGER {
                         all   (1),
                         radius(2),
                         off   (3)
                         }
         MAX-ACCESS  read-write
         STATUS      current
         DESCRIPTION
            "A flag that controls the generation of syslog messages for filtered
             packets.
              all    - all filtered packets will generate a syslog message.
              radius - the radius attribute, Filter-Log-Packet will control syslog
                       message generation.
              off    - no syslog messages will be generated."
         --CONFIGURABLE
     ::= { usrFilter 4 }
usrFilterPktLogSize OBJECT-TYPE
         SYNTAX  Integer32 (0..493)
         MAX-ACCESS  read-write
         STATUS      current
         DESCRIPTION
            "The size of a filtered packet that will be included in the actual 
             syslog message.  The default value is 0.  NOTE: syslog can only 
             handle 1028 bytes of ascii text, therefore packet data must 
             converted from hex to ascii, thus reducing the maxium packet data 
             size in half. When syslog begin and end strings are added it is 
             further reduced to 493 bytes." 
         --CONFIGURABLE
     ::= { usrFilter 5 }     
usrFilterPktLogCount OBJECT-TYPE
         SYNTAX  Integer32
         MAX-ACCESS  read-only
         STATUS      current
         DESCRIPTION
            "The number of packets that were filtered and sent to syslog."
     ::= { usrFilter 6 }          
END         -- End Filter MIB definitions
-- ************************************************************************
--
--
--	usr_pm.mib	   The Policy Manager MIB file
--
-- Author:         Colm Terrett
--
USR-PM-MIB DEFINITIONS ::= BEGIN
	IMPORTS
          OBJECT-TYPE, MODULE-IDENTITY, Integer32
                  FROM SNMPv2-SMI
          TruthValue, DisplayString
		  FROM SNMPv2-TC
          UsrDisplayString, common, UsrConfigStatus, UsrPolicyfileName
                  FROM USR-DEFINITIONS-MIB;
usrPm    MODULE-IDENTITY
         LAST-UPDATED "200203121800Z"
         ORGANIZATION "CommWorks Corporation, a 3Com Company"
         CONTACT-INFO "Customer Support"
         DESCRIPTION
                 "The commWorks enterprise defined MIB objects
                  for the Policy Manager process."
--       REVISION       "200203121800Z"
--       DESCRIPTION
--               "Converted to SNMPv2"
         ::= { common 69 }
   -- Begin managed object definitions here...
   --  Added dynamic ipsec MIB object.
usrPmCFMStatusFlag OBJECT-TYPE
	SYNTAX		UsrConfigStatus
	MAX-ACCESS	read-write
	STATUS		current
	DESCRIPTION
		"This variable controls saving and loading of configuration
           information for the PM Module. The value can 
           be set to either save or load by a management station. The other
           values indicate if any configuration operation and what type
           is in progress."
::= { usrPm 1 }
usrPmCfgFileName OBJECT-TYPE
	SYNTAX      UsrDisplayString
	MAX-ACCESS  read-only
	STATUS      current
	DESCRIPTION		
		"The name of a ConfigFile to read/write  permanent database records.
		 If the value of this object is an empty string, then the
		 PM module uses the default name `@file://PMModule.cfg'. "
::= { usrPm 2 }
usrPmConfigTable OBJECT-TYPE
	SYNTAX SEQUENCE OF UsrPmConfigEntry
	MAX-ACCESS not-accessible
	STATUS current
	DESCRIPTION
		""
::= { usrPm 3 }
usrPmConfigEntry OBJECT-TYPE
	SYNTAX UsrPmConfigEntry
	MAX-ACCESS not-accessible
	STATUS current
	DESCRIPTION
		""
	INDEX { usrPmConfigIndex }
::= { usrPmConfigTable 1 }
UsrPmConfigEntry ::= SEQUENCE {
	usrPmState						TruthValue,
	usrPmRemoteManAccess			TruthValue,
	usrPmRemoteManType			UsrDisplayString,
	usrPmAlarmLevel					Integer32,
	usrPmAlarmPktSize				Integer32,
	usrPmAlarmStorageLocation		UsrDisplayString,
	usrPmRefreshTimeout				Integer32,
	usrPmSupportedApplications		UsrDisplayString,
        usrPmConfigIndex Integer32
	}
usrPmConfigIndex         OBJECT-TYPE
           SYNTAX          Integer32
           MAX-ACCESS      read-only
           STATUS          current
           DESCRIPTION
              " A unique value for each PM Config file. "
           ::= { usrPmConfigEntry 9 }
usrPmState OBJECT-TYPE
 	SYNTAX  TruthValue
 	MAX-ACCESS  read-only
 	STATUS  current
 	DESCRIPTION
    "This flag shows whether the Policy Manager has been enabled or disabled."
::= { usrPmConfigEntry 1 }
usrPmRemoteManAccess OBJECT-TYPE
 	SYNTAX  TruthValue
 	MAX-ACCESS  read-only
 	STATUS  current
 	DESCRIPTION
    "This flag shows whether the Policy Manager allows remote configuration/management
    by an Management Station or not."
::= { usrPmConfigEntry 2 }
usrPmRemoteManType OBJECT-TYPE
 	SYNTAX  UsrDisplayString
 	MAX-ACCESS  read-only
 	STATUS  current
 	DESCRIPTION
    "Describes the means by which a remote management station can configure/manage the
    Policy Manager, e.g. via http, snmp etc."
::= { usrPmConfigEntry 3 }
usrPmAlarmLevel OBJECT-TYPE
 	SYNTAX  Integer32
 	MAX-ACCESS  read-only
 	STATUS  current
 	DESCRIPTION
    "This value determines the grade of information logging done by the Policy Manager
    /Flow Manager."
::= { usrPmConfigEntry 4 }
usrPmAlarmPktSize OBJECT-TYPE
 	SYNTAX  Integer32
 	MAX-ACCESS  read-only
 	STATUS  current
 	DESCRIPTION
    "The size of the packet that will be saved in syslog (or other) records."
::= { usrPmConfigEntry 5 }
usrPmAlarmStorageLocation OBJECT-TYPE
 	SYNTAX  UsrDisplayString
 	MAX-ACCESS  read-only
 	STATUS  current
 	DESCRIPTION
    "The destination for alarm messages and records."
::= { usrPmConfigEntry 6 }
usrPmRefreshTimeout OBJECT-TYPE
 	SYNTAX  Integer32
 	MAX-ACCESS  read-only
 	STATUS  current
 	DESCRIPTION
    "The time (in minutes) during checks on validity of flows in the flow database."
::= { usrPmConfigEntry 7 }
usrPmSupportedApplications OBJECT-TYPE
 	SYNTAX  UsrDisplayString
 	MAX-ACCESS  read-only
 	STATUS  current
 	DESCRIPTION
    "Client Applications registered with the Policy Manager (QOS,IPSEC,NAT,FW,SOCKS)."
::= { usrPmConfigEntry 8 }
usrPolicyTable OBJECT-TYPE
     SYNTAX   SEQUENCE OF UsrPolicyEntry
     MAX-ACCESS   not-accessible
     STATUS   current
     DESCRIPTION
        "A table of policy file names.  The actual policy
         information is stored in an ASCII file in flash."
 ::= { usrPm 4 }
usrPolicyEntry OBJECT-TYPE
     SYNTAX   UsrPolicyEntry
     MAX-ACCESS   not-accessible
     STATUS   current
     DESCRIPTION
            "The parameters for a policy file."
       INDEX {usrPolicyfileName}
 ::= { usrPolicyTable 1 }
 --
 -- The row is composed of these components
 --
 UsrPolicyEntry ::=
     SEQUENCE {
     usrPolicyfileName
       UsrPolicyfileName ,
     usrPolicyfileStatus
        INTEGER,
     usrPolicyfileAssociation
        DisplayString,
     usrPolicyfileVerifyError
        DisplayString,
     usrPolicyPrintAccess
        INTEGER
 }
 usrPolicyfileName OBJECT-TYPE
     SYNTAX  UsrPolicyfileName
     MAX-ACCESS  not-accessible
     STATUS  current
     DESCRIPTION
        "The character name for this policy file."
 ::= { usrPolicyEntry 1 }
 usrPolicyfileStatus OBJECT-TYPE
     SYNTAX  INTEGER {
                     normal(1),
                     delete(2),
                     update(4),
                     reading(8),       -- File reading in progress
                     converting(16),     -- Filter verification in progress
                     compiling(32),     -- Filter compilation in progress
                     compileFailed(64),  -- Filter verification failed
                     starting(128)       -- Filter operation starting
                     }
     MAX-ACCESS  read-write
     STATUS  current
     DESCRIPTION
        "The status of this policy file entry. Valid row entries in this
         table have the status field set to normal. The settable values
         are normal and delete.  If the instance is not in the table 
         and the status is normal, this will be an add operation.  If the
         instance is in the table and the status is normal, this will be a
         modify operation.  If the instance is in the table and the 
         status is delete, this will be a delete operation.  The values 
         reading, verifying, and compiling are read-only."
     --CONFIGURABLE
 ::= { usrPolicyEntry 2 }
 usrPolicyfileAssociation OBJECT-TYPE
     SYNTAX  DisplayString (SIZE (0..255))
     MAX-ACCESS  read-only
     STATUS  current
     DESCRIPTION
        "Details the interface/user that this Policy file is associated with."
 ::= { usrPolicyEntry 3 }
 usrPolicyfileVerifyError OBJECT-TYPE
     SYNTAX  DisplayString (SIZE (0..255))
     MAX-ACCESS  read-only
     STATUS  current
     DESCRIPTION
        "The error string returned when a policy file fails its verification
         process.  Otherwise, this field is NULL."
 ::= { usrPolicyEntry 4 }
usrPolicyPrintAccess OBJECT-TYPE
       SYNTAX      INTEGER {
                            off (0),
                            on (1)
                           }
       MAX-ACCESS      read-write
       STATUS      current
       DESCRIPTION "This  will allow user policy to be printed 
                    during compilation. "
::= { usrPolicyEntry 5 }
usrDynamicIPSec         OBJECT-TYPE
           SYNTAX          INTEGER {
                                        off (0),
                                        on (1)
                                   }
           MAX-ACCESS      read-write
           STATUS      current
           DESCRIPTION
              " This variable controls the Dynamic 
		IPSec Association capability."
     --CONFIGURABLE
::= { usrPm 5 }
END    -- End of USR-PM-MIB DEFINITIONS
-- ************************************************************************
--
--	usr_term_prot.mib
--
-- Author:         Brian Winter
--
TERM-PROT-MIB DEFINITIONS ::= BEGIN
	IMPORTS
          OBJECT-TYPE, MODULE-IDENTITY, Integer32, IpAddress
                   FROM SNMPv2-SMI
          RowStatus, DisplayString
                   FROM SNMPv2-TC
          common, UsrConfigStatus
                  FROM USR-DEFINITIONS-MIB;
usrTermProt MODULE-IDENTITY
        LAST-UPDATED "200208231615Z"
        ORGANIZATION "CommWorks Corporation, a 3Com Company"
        CONTACT-INFO "Customer Support"
        DESCRIPTION
           "The commWorks enterprise defined MIB objects  for Terminal
            Protocols Process."
       ::= { common 18 }
--      REVISION "200208231615Z"
--      DESCRIPTION "Clarified usage and labels for usrTermProtTelnetEscEnabled
--          usrTermProtTelnetShowTryingMsg, usrTermProtTelnetClientAccess,
--          usrTelnetTerminalDownloadMode, usrTermProtRloginEscEnabled,
--          usrTermProtTelnetShowDisconnect."
--      REVISION "200205051800Z"
--      DESCRIPTION "Converted to SNMPv2"
-- Begin managed object definitions here...
usrTermProtCFMStatusFlag OBJECT-TYPE
	SYNTAX		UsrConfigStatus
	MAX-ACCESS		read-write
	STATUS		    current
	DESCRIPTION
		"This variable controls saving and loading of configuration
		information for the Terminal Protocols Module. The value can 
		be set to either save or load by a management station. The other
		values indicate if any configuration operation and what type
		is in progress."
::= { usrTermProt 1 }
usrTermProtCfgFileName OBJECT-TYPE
	SYNTAX      DisplayString
	MAX-ACCESS      read-only
	STATUS          current
	DESCRIPTION		
		"The name of a ConfigFile to read/write  permanent database records.
		 If the value of this object is an empty string, then the Terminal
		 Protocols module uses the default name `@file://TermProt.cfg'. "
::= { usrTermProt 2 }
usrTermProtConnectedMsg OBJECT-TYPE
	SYNTAX      DisplayString
	MAX-ACCESS      read-write
	STATUS          current
	DESCRIPTION		
		"The string which is displayed when a ClearTCP client session
		is connected to the remote TCP host. If the value of this object
		is an empty string, the Terminal Protocols module uses a 
		default of CONNECTED"
	--CONFIGURABLE
::= { usrTermProt 3 }
usrTermProtTelnetEscEnabled OBJECT-TYPE
	SYNTAX          INTEGER {
                        enabled(1),
                        disabled(2)
                        }
	MAX-ACCESS      read-write
	STATUS          current
	DESCRIPTION		
		"If set to DISABLED, this object prevents all Telnet Clients
		from using the escape character during a session. If they
		enter that character, it will be sent as regular text. If
		set to ENABLED, the user will be permitted to enter the
		escape character to use the local Telnet command line."
	--CONFIGURABLE
::= { usrTermProt 4 }
usrTermProtAllowManageUsers OBJECT-TYPE
        SYNTAX  INTEGER {
                        manage-off(0),
                        manage-on (1)
                        }
        MAX-ACCESS  read-write
        STATUS      current
        DESCRIPTION
                "This variable turns on/off the ability to manage the system
                 through telnet server connections."
        --CONFIGURABLE
::= { usrTermProt 5 }
usrTermProtTelnetShowTryingMsg  OBJECT-TYPE
	SYNTAX          INTEGER {
                        enabled(1),
                        disabled(2)
                        }
        MAX-ACCESS  read-write
        STATUS      current
        DESCRIPTION
                "This variable turns on/off the trying status message for 
                 telnet to terminal servers."
        --CONFIGURABLE
::= { usrTermProt 6 }
usrTermProtTelnetClientAccess OBJECT-TYPE
	SYNTAX          INTEGER {
                        enabled(1),
                        disabled(2)
                        }
	MAX-ACCESS      read-write
	STATUS          current
	DESCRIPTION		
		"This indicates whether to use the client access table.
		 By default, this value will be disabled.
		If set to enabled, the users can telnet into the HARC only
		from ip addresses added in the client access table. If the value
		if set to disabled, the client access table is not referred to."
	--CONFIGURABLE
::= { usrTermProt 7 }
usrTelnetAccessTable OBJECT-TYPE
		SYNTAX  SEQUENCE OF UsrTelnetAccessEntry
         	MAX-ACCESS  not-accessible
         	STATUS      current
         	DESCRIPTION
            "The Telnet access table"
::= { usrTermProt 8 }
usrTelnetAccessEntry OBJECT-TYPE
         	SYNTAX  UsrTelnetAccessEntry
         	MAX-ACCESS  not-accessible
         	STATUS      current
         	DESCRIPTION
            ""
         INDEX   { usrTelnetAccessIpAddr }
::= { usrTelnetAccessTable 1 }
UsrTelnetAccessEntry ::=
         	SEQUENCE {
         	usrTelnetAccessIpAddr IpAddress,
         	usrTelnetAccessIpMask IpAddress,
         	usrTelnetAccessStatus INTEGER
         }
usrTelnetAccessIpAddr OBJECT-TYPE
         	SYNTAX  IpAddress
         	MAX-ACCESS  not-accessible
         	STATUS      current
         	DESCRIPTION
            "The IP Address of the station allowed for telnet into HiPerARC."
::= { usrTelnetAccessEntry 1 }
usrTelnetAccessStatus OBJECT-TYPE
	 	SYNTAX   INTEGER {
			add(1),
			normal(2),
			delete(3)
			}
         	MAX-ACCESS   read-write
         	STATUS       current
         	DESCRIPTION
            "The status of the entry for this address."
          --CONFIGURABLE
::= { usrTelnetAccessEntry 2 }
usrTelnetAccessIpMask OBJECT-TYPE
         	SYNTAX  IpAddress
         	MAX-ACCESS  read-write
         	STATUS      current
         	DESCRIPTION
            "The IP Address of the station allowed for telnet into HiPerARC."
        --CONFIGURABLE
::= { usrTelnetAccessEntry 3 }
usrTelnetTerminalDownloadMode OBJECT-TYPE
			SYNTAX      INTEGER {
                            enabled(1),
                            disabled(2)
                            }
			MAX-ACCESS  read-write
         	STATUS      current
         	DESCRIPTION
            "Will cause telnet client on non-23 port disable ECHO in local
			 and remote side"
        --CONFIGURABLE
::= { usrTermProt 9 }
usrTermProtRloginEscEnabled OBJECT-TYPE
    SYNTAX          INTEGER {
                        enabled(1),
                        disabled(2)
                        }
    MAX-ACCESS      read-write
    STATUS          current
    DESCRIPTION
        "If set to disabled, this object prevents all Rlogin Clients
        from using the escape character during a session. If they
        enter that character, it will be sent as regular text. If
        set to enabled, the user will be permitted to enter the
        escape character to use the local Telnet command line."
    --CONFIGURABLE
::= { usrTermProt 10 }
usrTermProtTelnetShowDisconnect  OBJECT-TYPE
   	SYNTAX      INTEGER {
                    enabled(1),
                    disabled(2)
                    }
    MAX-ACCESS  read-write
    STATUS      current
    DESCRIPTION
            "This variable enabled/disables the disconnect message for 
             telnet/cleartcp connections "
        --CONFIGURABLE
::= { usrTermProt 11 }
usrCTCPEncryptionTable OBJECT-TYPE
	SYNTAX SEQUENCE OF UsrCTCPEncryptionEntry
	MAX-ACCESS not-accessible
	STATUS     current
	DESCRIPTION
		"The table of cleartcp encryption ids and keys. "
::= { usrTermProt 12 }
usrTermProtTelnetBannerFile  OBJECT-TYPE
	SYNTAX      OCTET STRING
        MAX-ACCESS  read-write
        STATUS      current
        DESCRIPTION
                " Banner text displayed to admin users telneting to the system"
        --CONFIGURABLE
::= { usrTermProt 13 }
usrCTCPEncryptionEntry OBJECT-TYPE
	SYNTAX UsrCTCPEncryptionEntry
	MAX-ACCESS not-accessible
	STATUS     current
	DESCRIPTION
                "A (conceptual) entry for one encryption id and key."
	INDEX { usrCTCPEncryptionId }
::= { usrCTCPEncryptionTable 1 }
UsrCTCPEncryptionEntry ::= SEQUENCE {
	usrCTCPEncryptionId		DisplayString,
	usrCTCPEncryptionKey	Integer32,
        usrCTCPEncryptionStatus     RowStatus
	}
usrCTCPEncryptionId OBJECT-TYPE
	SYNTAX		DisplayString
	MAX-ACCESS          not-accessible
	STATUS		    current
	DESCRIPTION
		"The logical identifier of the encryption id-key Table. "
::= { usrCTCPEncryptionEntry 1 }
usrCTCPEncryptionKey OBJECT-TYPE
	SYNTAX		Integer32
	MAX-ACCESS      read-write
	STATUS		    current
	DESCRIPTION
		"Key number corresponds to the encryption-id in the table"
	--CONFIGURABLE
::= { usrCTCPEncryptionEntry 2 }
usrCTCPEncryptionStatus OBJECT-TYPE
	SYNTAX		RowStatus
	MAX-ACCESS      read-write
	STATUS		    current
	DESCRIPTION
		"The status of this row of the CTCP Encryption Table. "
	--CONFIGURABLE
::= { usrCTCPEncryptionEntry 3 }
END     -- End of TERM-PROT-MIB DEFINITIONS
-- ************************************************************************
--
--    usr_fr.mib - The Commworks Frame Relay MIB module
--
-- Author:         <Ginny Walker>
--
USR-FR-MIB DEFINITIONS ::= BEGIN
     IMPORTS
             OBJECT-TYPE, MODULE-IDENTITY,
             Integer32
                      FROM SNMPv2-SMI
             common, UsrConfigStatus, UsrDisplayString
                     FROM USR-DEFINITIONS-MIB;
    usrFR MODULE-IDENTITY
         LAST-UPDATED "200205052000Z"
         ORGANIZATION "CommWorks Corporation, a 3Com Company"
         CONTACT-INFO "Customer Support"
         DESCRIPTION
                 "The commWorks enterprise defined MIB objects
                   for Frame Relay."
--       REVISION "200205052000Z"
--       DESCRIPTION "Convert to SNMPv2 and remove obsolete
--                    tables to usr_fr_obsolete.mib. These tables
--                    were obsoleted by the implementation of
--                    RFC2115-frDTE.mib."
         ::= { common 15 }
     --  Frame Relay DTE MIB
     --
     --      the range of ifIndex
     --
     Index ::= Integer32       -- 1..ifNumber
     --
     --      the range of a Data Link Connection Identifier
     --
     DLCI ::= Integer32        -- 0..DLCINumber
     --
     -- The Frame Relay Base Group.
     --
     usrfrBaseCfgFileName OBJECT-TYPE
         SYNTAX       UsrDisplayString
         MAX-ACCESS   read-only
         STATUS       current
         DESCRIPTION
                 "The name of a ConfigFile to read/write
                 permanent database records. If the value of this
                 object is an empty string, then the FR process
                 uses the default name `@file://FrFile.cfg'."
         ::= { usrFR 1 }
     usrfrBaseCFMSaveStatus OBJECT-TYPE
         SYNTAX  UsrConfigStatus
         MAX-ACCESS  read-write
         STATUS      current
         DESCRIPTION
                 "Setting the value of this object to `save'
                 causes the values of the FR Base Group
                 entries to be written out to the current FR
                 config file. While the new config file is being
                 written, the FR process will set the value
                 of this flag set to `saving''. Any attempts to set
                 the value while it is  not `normal' (i.e. the file
                 is currently being written to the config file)
                 while result in a badValue error being returned.
                 Setting the value to `normal' will result in no
                 action."
         ::= { usrFR 2 }
--  The following OID's and leaf objects are obsoleted 
--  by rfc2115-frDTE.mib
     usrfrDlcmiTable OBJECT IDENTIFIER ::= { usrFR 3 }
     usrfrCircuitTable OBJECT IDENTIFIER ::= { usrFR 4 }
     usrfrErrTable OBJECT IDENTIFIER ::= { usrFR 5 }
     END -- End of USR-FR-MIB DEFINITIONS
-- ************************************************************************
--
--	usr_tftp.mib - The CommWorks TFTP MIB module
--
-- Author:         Peter Dobransky
--
USR-TFTP-MIB DEFINITIONS ::= BEGIN
	IMPORTS
            OBJECT-TYPE, MODULE-IDENTITY,
    		IpAddress, Integer32
                  FROM SNMPv2-SMI
            common, UsrDisplayString, UsrConfigStatus
                  FROM USR-DEFINITIONS-MIB;
usrTftp MODULE-IDENTITY
        LAST-UPDATED "200205051800Z"
        ORGANIZATION "CommWorks Corporation, a 3Com Company"
        CONTACT-INFO "Customer Support"
        DESCRIPTION
           "The commWorks enterprise defined MIB objects  for TFTP"
--      REVISION  "200205051800Z"
--      DESCRIPTION "Converted to SNMPv2"
       ::= { common 24 }
   -- textual conventions
   -- 
   -- textual conventions are like pre-processor macro in 'C'
   --        (i.e. #define statements)
   -- Use them to define your own 'datatypes'
   -- memory size, expressed in units of 1024bytes
	-- A sample Table definiton.
	usrTftpConfigFileName OBJECT-TYPE
		SYNTAX          UsrDisplayString
		MAX-ACCESS      read-only
		STATUS          current
		DESCRIPTION		
		  "The name of a ConfigFile to read/write permanent database records.
		   If the value of this object is an empty string, then the
		   TFTP process uses the default name `@file://TftpProcess.cfg'. "
	::= { usrTftp 1 }
	usrTftpCFMStatusFlag  OBJECT-TYPE
	 	SYNTAX	  UsrConfigStatus
		MAX-ACCESS      read-write
		STATUS          current
		DESCRIPTION
		  "Setting the value of this object to `save' causes the values
		   of the TFTP Group to be written out to the current config
		   file, which is stored in the usrTftpConfigFileName object.
		   While the new ConfigFile is being written, the TFTP process
		   will set the value of this flag to `saving''. Any
		   attempts to set the value while it is not `normal'
		   (i.e. the file is currently being written to the
		   ConfigFile) while result in a badValue error being
		   returned. Setting the value to `normal' will result in no
		   action."
	::= { usrTftp 2 }
     usrTftpAccessTable OBJECT-TYPE
		SYNTAX  SEQUENCE OF UsrTftpAccessEntry
         	MAX-ACCESS  not-accessible
         	STATUS      current
         	DESCRIPTION
            "The TFTP access table"
	::= { usrTftp 3 }
	usrTftpAccessEntry OBJECT-TYPE
         	SYNTAX  UsrTftpAccessEntry
         	MAX-ACCESS  not-accessible
         	STATUS      current
         	DESCRIPTION
            ""
         INDEX   { usrTftpAccessIpAddr }
	::= { usrTftpAccessTable 1 }
	UsrTftpAccessEntry ::=
         	SEQUENCE {
         	usrTftpAccessIpAddr
            IpAddress,
         	usrTftpAccessStatus
            INTEGER
         }
	usrTftpAccessIpAddr OBJECT-TYPE
         	SYNTAX  IpAddress
         	MAX-ACCESS  not-accessible
         	STATUS      current
         	DESCRIPTION
            "The IP Address of the station allowed to perform TFTP file
             transfers."
	::= { usrTftpAccessEntry 1 }
	usrTftpAccessStatus OBJECT-TYPE
	 	SYNTAX   INTEGER {
			add(1),
			normal(2),
			delete(3)
			}
         	MAX-ACCESS   read-write
         	STATUS       current
         	DESCRIPTION
            "The status of the entry for this address."
          --CONFIGURABLE
         ::= { usrTftpAccessEntry 2 }
     -- TFTP Client Request Table
     usrTftpClientRequestTable OBJECT-TYPE
          SYNTAX  SEQUENCE OF UsrTftpClientRequestEntry
          MAX-ACCESS  not-accessible
          STATUS      current
          DESCRIPTION
            "The TFTP Client Request Table"
     ::= { usrTftp 4 }
     usrTftpClientRequestEntry OBJECT-TYPE
          SYNTAX  UsrTftpClientRequestEntry
          MAX-ACCESS  not-accessible
          STATUS      current
          DESCRIPTION
            ""
         INDEX   { usrTftpClientRequestFileName }
     ::= { usrTftpClientRequestTable 1 }
     UsrTftpClientRequestEntry ::=
          SEQUENCE {
               usrTftpClientRequestFileName
                    UsrDisplayString,
               usrTftpClientRequestServer
                    OCTET STRING,
               usrTftpClientRequestAction
                    INTEGER,
               usrTftpClientRequestMode
                    INTEGER,
               usrTftpClientRequestRexmtTimeout
                    Integer32,
               usrTftpClientRequestMaxTimeout
                    Integer32,
               usrTftpClientRequestStatus
                    INTEGER,
               usrTftpClientRequestErrorString
                    UsrDisplayString
         }
     usrTftpClientRequestFileName OBJECT-TYPE
         	SYNTAX  UsrDisplayString (SIZE(0..64))
         	MAX-ACCESS  not-accessible
         	STATUS      current
         	DESCRIPTION
            "The name of the file which will either be requested from or
             sent to the TFTP server."
     ::= { usrTftpClientRequestEntry 1 }
     usrTftpClientRequestServer OBJECT-TYPE
          SYNTAX  OCTET STRING (SIZE(0..255))
          MAX-ACCESS  read-write
          STATUS      current
          DESCRIPTION
            "The name or IP address of the TFTP server. I name it is
             a domain name of type DnsName (rfc1611)"
          REFERENCE
            "RFC-1034 section 3.1"
          --CONFIGURABLE
         ::= { usrTftpClientRequestEntry 2 }
     usrTftpClientRequestAction OBJECT-TYPE
          SYNTAX  INTEGER {
                    get(1),
                    put(2)
                    }
          MAX-ACCESS  read-write
          STATUS      current
          DESCRIPTION
            "The type of request that will be sent to the TFTP server."
          --CONFIGURABLE
         ::= { usrTftpClientRequestEntry 3 }
     usrTftpClientRequestMode OBJECT-TYPE
          SYNTAX  INTEGER {
                    netascii(1),
                    octet(2)
                    }
          MAX-ACCESS  read-write
          STATUS      current
          DESCRIPTION
            "The mode in which the file will be transferred."
          DEFVAL { netascii }
          --CONFIGURABLE
         ::= { usrTftpClientRequestEntry 4 }
     usrTftpClientRequestRexmtTimeout OBJECT-TYPE
          SYNTAX  Integer32 (1..60)
          MAX-ACCESS  read-write
          STATUS      current
          DESCRIPTION
            "The retransmission time-out."
          DEFVAL { 5 }
          --CONFIGURABLE
         ::= { usrTftpClientRequestEntry 5 }
     usrTftpClientRequestMaxTimeout OBJECT-TYPE
          SYNTAX  Integer32 (1..300)
          MAX-ACCESS  read-write
          STATUS      current
          DESCRIPTION
            "The maximum number of seconds to wait for a response from
             the TFTP server. If this value is reached, the TFTP request
             will be timed out."
          DEFVAL { 25 }
          --CONFIGURABLE
         ::= { usrTftpClientRequestEntry 6 }
     usrTftpClientRequestStatus OBJECT-TYPE
          SYNTAX  INTEGER {
                    normal(1),
                    enable(2),
                    getting(3),
                    putting(4),
                    delete(5),
                    error(6)
                    }
          MAX-ACCESS  read-write
          STATUS      current
          DESCRIPTION
            "The status of this row. Setting this object to enable(2)
             will cause a request (defined by usrTftpClientRequestAction)
             to be sent to the TFTP server. Depending on the type of
             request, this object will then be set to either getting(3)
             or putting(4). When the request is completed, this object
             will be set to normal(1) which indicates success. If an
             error occurred, this object will be set to error(5) and
             the usrTftpClientRequestErrorString will indicate the
             type of error."
         ::= { usrTftpClientRequestEntry 7 }
     usrTftpClientRequestErrorString OBJECT-TYPE
          SYNTAX      UsrDisplayString
          MAX-ACCESS  read-only
          STATUS      current
          DESCRIPTION
            "This object will indicate what type of error occurred when
             the object usrTftpClientRequestStatus is set to error(5)."
         ::= { usrTftpClientRequestEntry 8 }
END  -- End of USR-TFTP-MIB DEFINITIONS
-- ************************************************************************
--
--	usr_dialout.mib - The Commworks Dial-out MIB module
--
-- Author:         Peter Dobransky
--
USR-DIALOUT-MIB DEFINITIONS ::= BEGIN
     IMPORTS
            OBJECT-TYPE, MODULE-IDENTITY,
            IpAddress, Integer32
                  FROM SNMPv2-SMI
            DisplayString
                  FROM SNMPv2-TC
            common, UsrConfigStatus
                  FROM USR-DEFINITIONS-MIB;
usrDialout MODULE-IDENTITY
        LAST-UPDATED "200205011316Z"
        ORGANIZATION "CommWorks Corporation, a 3Com Company"
        CONTACT-INFO "Customer Support"
        DESCRIPTION
                "The commWorks enterprise defined MIB objects
                 for Dialout."
--      REVISION "200205011316Z"
--      DESCRIPTION "Converted to SNMPv2"
        ::= { common 25 }
-- textual conventions
-- 
-- textual conventions are like pre-processor macro in 'C'
--        (i.e. #define statements)
-- Use them to define your own 'datatypes'
-- memory size, expressed in units of 1024bytes
usrDialoutConfigFileName OBJECT-TYPE
     SYNTAX DisplayString
     MAX-ACCESS read-only
     STATUS     current
     DESCRIPTION
       "The name of a ConfigFile to read/write permanent database
        records. If the value of this object is an empty string,
        then the Dial-out process uses the default name
        `@file://DialOutProcess.cfg'."
::= { usrDialout 1 }
usrDialoutCFMStatusFlag  OBJECT-TYPE
     SYNTAX UsrConfigStatus
     MAX-ACCESS read-write
     STATUS     current
     DESCRIPTION
       "Setting the value of this object to `save' causes the values
        of the Dial-out Group to be written out to the current config
        file, which is stored in the usrDialoutConfigFileName object.
        While the new ConfigFile is being written, the Dial-out process
        will set the value of this flag to `saving''. Any
        attempts to set the value while it is not `normal'
        (i.e. the file is currently being written to the
        ConfigFile) while result in a badValue error being
        returned. Setting the value to `normal' will result in no
        action."
::= { usrDialout 2 }
usrDialoutSecurity OBJECT-TYPE
	SYNTAX      INTEGER {
                    no(1),
                    yes(2)
                    }
	MAX-ACCESS      read-write
	STATUS          current
	DESCRIPTION
       "Setting the value of this object to yes(2) will instruct the
        Dial-out process to authenticate all network users who attempt to
        connect to a virtual port. Setting the value of this object to
        no(1) will instruct the Dial-out process to bypass the user
        authentication process."
     DEFVAL { yes }
     --CONFIGURABLE
::= { usrDialout 3 }
usrDialoutWorkstationTimeout OBJECT-TYPE
	SYNTAX      Integer32 (0..180)
	MAX-ACCESS      read-write
	STATUS          current
	DESCRIPTION
       "Even when it appears there is no activity on a connected virtual
        port, the client and server are still actively sending and
        receiving messages. If the client is re-booted, or if the client
        experiences a system error that interrupts this activity, the
        server will wait a certain amount of time before terminating the
        connection. Depending on what caused the interruption, this
        period of time may allow the client to restore the connection.
        This time-out value is specified in minutes. The default is 5
        minutes. To disable workstation time-out, set this object to 0."
     DEFVAL { 5 }
     --CONFIGURABLE
::= { usrDialout 4 }
usrDialoutUserTimeout OBJECT-TYPE
	SYNTAX      Integer32 (0..180)
	MAX-ACCESS      read-write
	STATUS          current
	DESCRIPTION
       "The User time-out is provided so that a virtual port will be
        freed for use by others when the current user is not actively
        using the virtual port. If the server does not receive any
        transmit data requests from the client for the period of the
        time-out, the session is disconnected. The time-out value is
        specified in minutes. The default is 5 minutes. To disable
        user time-out, set this object to 0."
     DEFVAL { 5 }
     --CONFIGURABLE
::= { usrDialout 5 }
usrDialoutPortTable OBJECT-TYPE
     SYNTAX     SEQUENCE OF UsrDialoutPortEntry
     MAX-ACCESS     not-accessible
     STATUS         current
     DESCRIPTION
       "A list of virtual ports available for dial-out."
::= { usrDialout 6 }
usrDialoutPortEntry OBJECT-TYPE
     SYNTAX      UsrDialoutPortEntry
     MAX-ACCESS      not-accessible
     STATUS          current
     DESCRIPTION
       "An entry containing management information applicable to a
        particular virtual port."
     INDEX { usrDialoutPortNumber }
::= { usrDialoutPortTable 1}
UsrDialoutPortEntry ::=
     SEQUENCE {
          usrDialoutPortNumber Integer32,
          usrDialoutPortGeneralName DisplayString,
          usrDialoutPortSpecificName DisplayString,
          usrDialoutPortState INTEGER,
          usrDialoutPortClientType INTEGER,
          usrDialoutPortIpxClientAddress OCTET STRING,
          usrDialoutPortIpClientAddress IpAddress
          }
usrDialoutPortNumber OBJECT-TYPE
	SYNTAX      Integer32
	MAX-ACCESS      not-accessible
	STATUS          current
	DESCRIPTION
       "The virtual port number of the dial-out port."
::= { usrDialoutPortEntry 1}
usrDialoutPortGeneralName OBJECT-TYPE
	SYNTAX      DisplayString (SIZE(8))
	MAX-ACCESS      read-only
	STATUS          current
	DESCRIPTION
       "The general service name associated with a virtual port. When a
        network user requires access to a type of service, rather than a
        specific port, the user is able to request a service by its
        general name. This provides network users access to the
        communication server ports without requiring the user to know
        the specific name or location of a port."
::= { usrDialoutPortEntry 2}
usrDialoutPortSpecificName OBJECT-TYPE
	SYNTAX      DisplayString (SIZE(14))
	MAX-ACCESS      read-only
	STATUS          current
	DESCRIPTION
       "The specific name associated with a virtual port. This allows a
        network user to locate a particular port for access to a specific
        service associated with that port."
::= { usrDialoutPortEntry 3}
usrDialoutPortState OBJECT-TYPE
	SYNTAX      INTEGER {
                    available(1),
                    unavailable(2),
                    in-use(3),
                    disconnect(4)
                    }
	MAX-ACCESS      read-write
	STATUS          current
	DESCRIPTION
       "The state of the virtual port. When a port is in the available(1)
        state, it is available to a network user. When a port is in the
        unavailable(2) state, it is not available to a network user. When
        a port is in the in-use(3) state, it is currently in use by a
        network user. Setting this object to disconnect(4) will cause a
        supervisory disconnect of the current user. Setting this object
        to any other value will have no effect."
::= { usrDialoutPortEntry 4}
usrDialoutPortClientType OBJECT-TYPE
	SYNTAX      INTEGER {
                    none(0),
                    ip(1),
                    ipx(2)
                    }
	MAX-ACCESS      read-only
	STATUS          current
	DESCRIPTION
       "The type of client that is attached to this port. This object
        is set to none(0) if no client is attached to the port."
::= { usrDialoutPortEntry 5}
usrDialoutPortIpxClientAddress OBJECT-TYPE
	SYNTAX      OCTET STRING (SIZE(6))
	MAX-ACCESS      read-only
	STATUS          current
	DESCRIPTION
       "The Ethernet address of the IPX client workstation attached
        to the port. If no client is attached to the port or an IP
        client is attached to the port, this object is set to all
        zeros."
::= { usrDialoutPortEntry 6}
usrDialoutPortIpClientAddress OBJECT-TYPE
	SYNTAX      IpAddress
	MAX-ACCESS      read-only
	STATUS          current
	DESCRIPTION
       "The IP address of the IP client workstation attached to
        the port. If no client is attached to the port or an IPX
        client is attached to the port, this object is set to all
        zeros."
::= { usrDialoutPortEntry 7}
END         -- End of USR-DIALOUT-MIB DEFINITIONS
-- ************************************************************************
--
--	usr_cli.mib
--
-- Author:         Clarise Patton
--
USR-CLI-MIB DEFINITIONS ::= BEGIN
	IMPORTS
        MODULE-IDENTITY, OBJECT-TYPE, Integer32
                  FROM SNMPv2-SMI
        DisplayString
                  FROM SNMPv2-TC
        UsrConfigStatus, common
                  FROM USR-DEFINITIONS-MIB;
    usrCli MODULE-IDENTITY
         LAST-UPDATED "200208231250Z"
         ORGANIZATION "CommWorks Corporation, a 3Com Company"
         CONTACT-INFO "Customer Support"
         DESCRIPTION
                 "The commWorks enterprise defined MIB objects
                   for the CLI"
--       REVISION    "200201091935Z"
--       DESCRIPTION "MODULE-IDENTITY created."
--       REVISION    "200208231350Z"
--       DESCRIPTION "Changed usrCliGlobalPageBreak from simple
--                    integer to enumerated integer."
     ::= { common 22 }
   -- Begin managed object definitions here...
usrCliVersion OBJECT-TYPE
	SYNTAX		DisplayString
	MAX-ACCESS	read-only
	STATUS		obsolete
	DESCRIPTION
		"The current software version of the Command Line Interpreter
	       process.."
::= { usrCli 1 }
usrCliConfigFileName OBJECT-TYPE
	SYNTAX		DisplayString
	MAX-ACCESS	read-only
	STATUS		current
	DESCRIPTION		
		  "The name of a ConfigFile to read/write permanent database
                   records."
	::= { usrCli 2 }
usrCliCFMStatusFlag OBJECT-TYPE
	SYNTAX		UsrConfigStatus
	MAX-ACCESS	read-write
	STATUS		current
	DESCRIPTION
		"This variable controls saving and loading of configuration
           information for the CLI process. The value can 
           be set to either save or load by a management station. The other
           values indicate if any configuration operation and what type
           is in progress."
::= { usrCli 3 }
usrCliHistoryDepth OBJECT-TYPE
     SYNTAX   Integer32
     MAX-ACCESS   read-write
     STATUS   current
     DESCRIPTION
            "The number of commands to be held in the History Array."
	--CONFIGURABLE
::= { usrCli 4 }
usrCliPrompt OBJECT-TYPE
     SYNTAX   DisplayString
     MAX-ACCESS   read-write
     STATUS   current
     DESCRIPTION
            "The specific prompt to be used for this CLI."
	--CONFIGURABLE
::= { usrCli 5 }
usrCliConsoleLogin OBJECT-TYPE
     SYNTAX   INTEGER {no(1),yes(2) }
     MAX-ACCESS   read-write
     STATUS   current
     DESCRIPTION
            "Whether the Console user will be required to log in.
		This defaults to Enabled and can only be changed by
		a privileged user."
	--CONFIGURABLE
::= { usrCli 6 }
usrCliConsoleIdleTimeout OBJECT-TYPE
     SYNTAX   Integer32 (0..60)
     MAX-ACCESS   read-write
     STATUS   current
     DESCRIPTION
            "If Console user is required to log in, there will be
		an idle timeout specified in minutes.  
		This will default to 5 minutes.
		There is a max of 60 minutes.  
		If this is set to 0, there will be no timeout. 
		This can only be modified by a privileged user."
	--CONFIGURABLE
::= { usrCli 7 }
usrCliGlobalPageBreak OBJECT-TYPE
     SYNTAX       INTEGER {
                    disabled(0),
                    enabled(1)
                    }
     MAX-ACCESS   read-write
     STATUS   current
     DESCRIPTION
        "This is a flag which says whether global page break is 
         enabled/disabled "
    --CONFIGURABLE
::= { usrCli 8 }
usrCliGlobalPageSize OBJECT-TYPE
     SYNTAX   Integer32
     MAX-ACCESS   read-write
     STATUS   current
     DESCRIPTION
        " This is a flag which says whether local page break is 
          enabled/disabled "
    --CONFIGURABLE
::= { usrCli 9 }
END         -- End CLI MIB definitions
-- ************************************************************************
--
--	usr_adsl.mib - ADSL Driver MIB
--
-- Author:         Jim Halpin
--
ADSL-MIB DEFINITIONS ::= BEGIN
	IMPORTS
          OBJECT-TYPE, MODULE-IDENTITY,
          Counter32, Integer32
                  FROM SNMPv2-SMI
          common, UsrDisplayString , UsrConfigStatus
                  FROM USR-DEFINITIONS-MIB;
usrAdsl MODULE-IDENTITY
        LAST-UPDATED "200205051800Z"
        ORGANIZATION "CommWorks Corporation, a 3Com Company"
        CONTACT-INFO "Customer Support"
        DESCRIPTION
           "The commWorks enterprise defined MIB objects for ADSL"
--      REVISION  "200205051800Z"
--      DESCRIPTION "Converted to SNMPv2"
       ::= { common 26 }
   -- textual conventions
   -- 
   -- textual conventions are like pre-processor macro in 'C'
   --        (i.e. #define statements)
   -- Use them to define your own 'datatypes'
   -- Begin managed object definitions here...
	usrAdslXmitPower OBJECT-TYPE
         SYNTAX   Integer32(-15..-3)
         MAX-ACCESS   read-only
         STATUS       current
         DESCRIPTION
            "Transmit power of ADSL transceiver represented in dB."
         ::= { usrAdsl 1 }
	usrAdslRmtReqDwnConstStatus OBJECT-TYPE
         SYNTAX   Integer32 (0..128)
         MAX-ACCESS   read-write
         STATUS       current
         DESCRIPTION
            	"Value corresponds to the downstream constellation
                 requested."
         ::= { usrAdsl 2 }
	usrAdslActualDwnConstStatus OBJECT-TYPE
         SYNTAX   Integer32 (0..128)
         MAX-ACCESS   read-only
         STATUS       current
         DESCRIPTION
            	"Value corresponds to the actual downstream constellation
                 that was used, which may differ from the value requested."
         ::= { usrAdsl 3 }
	usrAdslRmtReqUpConstStatus OBJECT-TYPE
         SYNTAX   Integer32 (0..128)
         MAX-ACCESS   read-only
         STATUS       current
         DESCRIPTION
            "Value corresponds to the upstream constellation requested."
         ::= { usrAdsl 4 }
	usrAdslActualUpConstStatus OBJECT-TYPE
         SYNTAX   Integer32 (0..128)
         MAX-ACCESS   read-only
         STATUS       current
         DESCRIPTION
            "Value corresponds to the actual upstream constellation that
             was used, which may differ from the value requested."
         ::= { usrAdsl 5 }
	usrAdslFwRel OBJECT-TYPE
         SYNTAX   Integer32 (0..16777215)
         MAX-ACCESS   read-only
         STATUS       current
         DESCRIPTION
            "Firmware release number of the GTI supplied transceiver
             software module."
         ::= { usrAdsl 6 }
	usrAdslStartletVerson OBJECT-TYPE
         SYNTAX   Integer32 (0..4)
         MAX-ACCESS   read-only
         STATUS       current
         DESCRIPTION
            "Value is a number that corresponds to the version number of
             the STARLET VLSI in the transceiver."
         ::= { usrAdsl 7 }
	usrAdslMeanSqError OBJECT-TYPE
         SYNTAX   INTEGER {
                           minus50db(1),
                           plus50db(2)
                          }
         MAX-ACCESS   read-only
         STATUS       current
         DESCRIPTION
            "Received signal to noise ratio."
         ::= { usrAdsl 8 }
	usrAdslEqualization OBJECT-TYPE
         SYNTAX   Integer32  -- Range values are TBD
         MAX-ACCESS   read-only -- TBD
         STATUS       current
         DESCRIPTION
            "TBD"
         ::= { usrAdsl 9 }
	usrAdslReceiverGain OBJECT-TYPE
         SYNTAX   Integer32 -- Range values are TBD
         MAX-ACCESS   read-write
         STATUS       current
         DESCRIPTION
            "Total receiver gain measured in dB."
         ::= { usrAdsl 10 }
	usrAdslBytesErrCorrected OBJECT-TYPE
         SYNTAX   Integer32 (0..255)
         MAX-ACCESS   read-only
         STATUS       current
         DESCRIPTION
            "Number of bytes corrected by Reed-Solomon error correction
             algorithm in the STARLET."
         ::= { usrAdsl 11 }
	usrAdslBytesNotErrCorrected OBJECT-TYPE
         SYNTAX   Integer32 (0..255)
         MAX-ACCESS   read-only
         STATUS       current
         DESCRIPTION
            "Number of bytes not corrected by Reed-Solomon error correction
             algorithm in the STARLET."
         ::= { usrAdsl 12 }
	usrAdslOverflowCounter OBJECT-TYPE
         SYNTAX   Counter32
         MAX-ACCESS   read-only
         STATUS       current
         DESCRIPTION
            "Running counter for when usrAdslBytesErrorCorrected or 
             usrAdslBytesNotErrorCorrected overflows"
         ::= { usrAdsl 13 }
	usrAdslOpState OBJECT-TYPE
         SYNTAX   Integer32 (0..134)
         MAX-ACCESS   read-only
         STATUS       current
         DESCRIPTION
            "Defines the high level operating state of the transceiver.
             Used by the customer to determine whether the transceiver
             is in idle mode, data mode, test mode, or startup."
         ::= { usrAdsl 14 }
	usrAdslStartupProgress OBJECT-TYPE
         SYNTAX   Integer32 (0..191)
         MAX-ACCESS   read-only
         STATUS       current
         DESCRIPTION
            "Defines the current detailed startup state of the
             transceiver.  The LSB determines the major mode
             corresponding to startup in var usrAdslOpState."
         ::= { usrAdsl 15 }
	usrAdslLastFailedStatus OBJECT-TYPE
         SYNTAX   Integer32 (0..191)
         MAX-ACCESS   read-only
         STATUS       current
         DESCRIPTION
            "Defines the last detailed state reached in
             usrAdslStartupProgress before startup failed."
         ::= { usrAdsl 16 }
	usrAdslActualBaudDataRateDwn OBJECT-TYPE
         SYNTAX   Integer32 (340..952)
         MAX-ACCESS   read-only
         STATUS       current
         DESCRIPTION
            "Actual downstream rate of kilobytes per second."
         ::= { usrAdsl 17 }
	usrAdslActualBaudDataRateDwnMar OBJECT-TYPE
         SYNTAX   Integer32 -- Range values are TBD
         MAX-ACCESS   read-only
         STATUS       current
         DESCRIPTION
            "TBD"
         ::= { usrAdsl 18 }
	usrAdslActualBaudDataRateUp OBJECT-TYPE
         SYNTAX   Integer32
         MAX-ACCESS   read-only
         STATUS       current
         DESCRIPTION
            "Actual upstream rate of kilobytes per second."
         ::= { usrAdsl 19 }
	usrAdslActualBaudDataRateUpMarg OBJECT-TYPE
         SYNTAX   Integer32 -- Range values are TBD
         MAX-ACCESS   read-only
         STATUS       current
         DESCRIPTION
            "TBD"
         ::= { usrAdsl 20 }
        usrAdslCFMStatusFlag OBJECT-TYPE
         SYNTAX  UsrConfigStatus
         MAX-ACCESS  read-write
         STATUS      current
         DESCRIPTION
                "This variable controls saving and loading of configuration
                information for the D56k WAN Driver. The value can be set
                to either save or load by a management station. The other
                values indicate if any configuration operation and what type
                is in progress."
         ::= { usrAdsl 21 }
        usrAdslCfgFileName OBJECT-TYPE
         SYNTAX      UsrDisplayString
         MAX-ACCESS  read-only
         STATUS      current
         DESCRIPTION
                "The name of a ConfigFile to read/write the D56k parameters.
                 If the value of this object is an empty string, then the
                 D56k Driver uses the default name `@file://D56k.cfg'."
         ::= { usrAdsl 22 }
        usrAdslResetStatus OBJECT-TYPE
         SYNTAX   Integer32
         MAX-ACCESS   read-write
         STATUS       current
         DESCRIPTION
            "The Reset Status of the ADSL Starlet chipset"
         ::= { usrAdsl 23 }
END  -- End of ADSL-MIB-DEFINITIONS
-- ************************************************************************
--
--      usr_ntp.mib - An enterprise specific Network Time Protocol MIB
--
-- Created:        Feb-24-1997
--
USR-NTP-MIB DEFINITIONS ::= BEGIN
        IMPORTS
          OBJECT-TYPE, MODULE-IDENTITY, Integer32, OBJECT-IDENTITY,
          Counter32, IpAddress, NOTIFICATION-TYPE
                FROM SNMPv2-SMI
          DisplayString
                FROM SNMPv2-TC
          MODULE-COMPLIANCE,
          OBJECT-GROUP
                FROM SNMPv2-CONF
          common, UsrConfigStatus, UsrDisplayString
                FROM USR-DEFINITIONS-MIB;
usrNTPMib MODULE-IDENTITY
    LAST-UPDATED        "200208231640Z"
    ORGANIZATION        "CommWorks Corporation"
    CONTACT-INFO        "Customer Support"
    DESCRIPTION
     "This MIB Module defines the CommWorks private interface
      to the Simple Network Time Protocol client process.
      The process can be configured with up to two alternate servers,
      a primary server and a secondary server. The primary server is
      always contacted first, the secondary server is contacted after
      all retransmissions to the primary failed have failed.
      The implementation is based on RFC 2030, using unicast mode
      only.
      Note that all the writable objects include a 'DEFVAL'
      clause. The clause is intended to be used as a reference only,
      in case an agent has no previously saved configuration.
      Typically, at start-up, an agent will load data saved from a
      previous session - thus 'DEFVAL' is used mainly for new
      systems."
--   REVISION   "200208231640Z"
--   DESCRIPTION "Clarified usage and labels for usrNTPEnable."
--   REVISION   "200202211500Z"
--   DESCRIPTION "Convert traps to SNMPv2"
    ::= { common 34 }
usrNTPObjects OBJECT IDENTIFIER ::= { usrNTPMib 1 }
usrNTPTraps   OBJECT IDENTIFIER ::= { usrNTPMib 3 }
-- Begin managed object definitions here...
usrNTPPrimaryServer OBJECT-TYPE
    SYNTAX      DisplayString (SIZE (0..132))
    MAX-ACCESS  read-write
    STATUS      current
    DESCRIPTION
     "The IP address or host name of the primary NTP server that the
      module will query for time synchronization.
      An empty string means that no primary server is defined."
    DEFVAL { "" }
    --CONFIGURABLE
    ::= { usrNTPObjects 1 }     
usrNTPSecondaryServer OBJECT-TYPE
    SYNTAX      DisplayString (SIZE (0..132))
    MAX-ACCESS  read-write
    STATUS      current
    DESCRIPTION
     "The IP address or host name of the secondary NTP server that the
      module will query for time synchronization whenever the primary
      server is unavailable.
      An empty string means that no secondary server is defined."
    DEFVAL { "" }
    --CONFIGURABLE
    ::= { usrNTPObjects 2 }
usrNTPPollingInterval OBJECT-TYPE
    SYNTAX      Integer32 (64..16284)
    UNITS       "seconds"
    MAX-ACCESS  read-write
    STATUS      current
    DESCRIPTION
     "The polling interval used by the NTP process to gather time
      synchronization information. In seconds.
      The range available is 64 seconds to 1024 seconds. The default is 600
      seconds (10 minutes)."
    REFERENCE "RFC 1305 (NTPv3)."
    DEFVAL { 600 }
    --CONFIGURABLE
    ::= { usrNTPObjects 3 }
usrNTPMaxRetransmits OBJECT-TYPE
    SYNTAX      Integer32 (1..200)
    MAX-ACCESS  read-write
    STATUS      current
    DESCRIPTION 
     "The maximum number of times a request will be retransmitted to a
      given server before the server is considered unavailable. The range
      allowed is 1 to 200 times. The default is 5 times."
    DEFVAL { 5 }
    --CONFIGURABLE
    ::= { usrNTPObjects 4 }
usrNTPTimeOut OBJECT-TYPE
    SYNTAX      Integer32 (1..60)
    UNITS       "seconds"
    MAX-ACCESS  read-write
    STATUS      current
    DESCRIPTION
     "The number of seconds since a request has been sent to a server,
      after which period the request is considered timed-out.
      The range for this is 1 second to 1 minute. The default is 10
      seconds."
    DEFVAL { 10 }
    --CONFIGURABLE
    ::= { usrNTPObjects 5 }
usrNTPEnable OBJECT-TYPE
    SYNTAX      INTEGER {
                    enabled(1),
                    disabled(2)
                    }
    MAX-ACCESS  read-write
    STATUS      current
    DESCRIPTION
     "This object enables or disables NTP synchronization in a
      system. Default is disabled."
    DEFVAL { disabled }
    --CONFIGURABLE
    ::= { usrNTPObjects 6 }
usrNTPProtocolVersion OBJECT-TYPE
    SYNTAX INTEGER {
        ntpV3(3),
        ntpV4(4)
      }
    MAX-ACCESS  read-write
    STATUS      current
    DESCRIPTION
     "The protocol version that the NTP client will use when sending NTP
      client requests to a server."
    DEFVAL { ntpV3 }
    --CONFIGURABLE
    ::= { usrNTPObjects 7 }
usrNTPCfmFileName OBJECT-TYPE
    SYNTAX      DisplayString (SIZE (1..32))
    MAX-ACCESS  read-only
    STATUS      current
    DESCRIPTION
     "The name of the configuration file currently in use."
    DEFVAL { "@file://Ntp.cfg" }
    ::= { usrNTPObjects 8 }
usrNTPCfmSaveFlag OBJECT-TYPE
    SYNTAX      UsrConfigStatus
    MAX-ACCESS  read-write
    STATUS      current
    DESCRIPTION
     "Setting the value of this object to `save' causes the values of the
     NTP Group to be written out to the current config file, which
     is stored in the usrNTPCfmFileName object. While the new
     ConfigFile is being written, the NTP process will set the value
     of this flag set to `saving''. Any attempts to set the value while it
     is  not `normal' (i.e. the file is currently being written to the
     ConfigFile) will result in a badValue error being returned. Setting
     the value to `normal' will result in no action."
    ::= { usrNTPObjects 9 }
usrNTPModuleVersion OBJECT-TYPE
    SYNTAX      DisplayString
    MAX-ACCESS  read-only
    STATUS      current
    DESCRIPTION
     "The current software version of the NTP module."
    ::= { usrNTPObjects 10 }
usrNTPLastGoodServer OBJECT-TYPE
    SYNTAX      DisplayString
    MAX-ACCESS  read-only
    STATUS      current
    DESCRIPTION
     "The symbolic host name of the last server from which
      time synchronization information was received (if there was a numeric
      address defined, this will be a numeric address in dot notation)."
    ::= { usrNTPObjects 11 }
usrNTPRcvdDatagrams OBJECT-TYPE
    SYNTAX      Counter32
    MAX-ACCESS  read-only
    STATUS      current
    DESCRIPTION
     "Number of datagrams received at the port on which NTP is listening to."
    ::= { usrNTPObjects 12 }
usrNTPRcvdTooShorts OBJECT-TYPE
    SYNTAX      Counter32
    MAX-ACCESS  read-only
    STATUS      current
    DESCRIPTION
     "Number of datagrams received which were too short for NTP version
      four."
    ::= { usrNTPObjects 13 }
usrNTPRcvdBadVersions OBJECT-TYPE
    SYNTAX      Counter32
    MAX-ACCESS  read-only
    STATUS      current
    DESCRIPTION
     "Number of datagrams received with a wrong NTP version."
    ::= { usrNTPObjects 14 }
usrNTPRcvdRequests OBJECT-TYPE
    SYNTAX      Counter32
    MAX-ACCESS  read-only
    STATUS      current
    DESCRIPTION
     "Number of NTP requests received."
    ::= { usrNTPObjects 15 }
usrNTPRcvdReplies OBJECT-TYPE
    SYNTAX      Counter32
    MAX-ACCESS  read-only
    STATUS      current
    DESCRIPTION
     "Number of NTP replies received."
    ::= { usrNTPObjects 16 }
usrNTPRcvdUnsuportedModes OBJECT-TYPE
    SYNTAX      Counter32
    MAX-ACCESS  read-only
    STATUS      current
    DESCRIPTION
     "Number of NTP datagrams received which had a mode value not supported
      by this entity."
    ::= { usrNTPObjects 17 }
usrNTPSentRequests OBJECT-TYPE
    SYNTAX      Counter32
    MAX-ACCESS  read-only
    STATUS      current
    DESCRIPTION
     "Number of NTP requests sent."
    ::= { usrNTPObjects 18 }
usrNTPSentReplies OBJECT-TYPE
    SYNTAX      Counter32
    MAX-ACCESS  read-only
    STATUS      current
    DESCRIPTION
     "Number of NTP replies sent since the system was last rebooted."
    ::= { usrNTPObjects 19 }
usrNTPSentRexmits OBJECT-TYPE
    SYNTAX      Counter32
    MAX-ACCESS  read-only
    STATUS      current
    DESCRIPTION
     "Number of NTP requests that were retransmitted due to lack of a timely
      reply."
    ::= { usrNTPObjects 20 }
usrNTPSendErrors OBJECT-TYPE
    SYNTAX      Counter32
    MAX-ACCESS  read-only
    STATUS      current
    DESCRIPTION
     "Number of NTP requests that could not be sent due to internal errors."
    ::= { usrNTPObjects 21 }
usrNTPDnsErrors OBJECT-TYPE
    SYNTAX      Counter32
    MAX-ACCESS  read-only
    STATUS      current
    DESCRIPTION
     "Number of times an error was returned by DNS when processing a name
      resolution request from the NTP module."
    ::= { usrNTPObjects 22 }
usrNTPServerTimeouts OBJECT-TYPE
    SYNTAX      Counter32
    MAX-ACCESS  read-only
    STATUS      current
    DESCRIPTION
     "Number of times a server was considered unavailable after requests
      were sent to it a maximum number of retransmissions without a reply."
    ::= { usrNTPObjects 23 }
usrNTPAllocErrors OBJECT-TYPE
    SYNTAX      Counter32
    MAX-ACCESS  read-only
    STATUS      current
    DESCRIPTION
     "Number of times an operation could not be performed due to a failure
      to allocate memory resources."
    ::= { usrNTPObjects 24 }
usrNTPResolvedIPAddress OBJECT-TYPE
    SYNTAX      IpAddress
    MAX-ACCESS  read-only
    STATUS      current
    DESCRIPTION
     "The IP address resolved from the 'current' server with which
      synchronization is being attempted.
      If there is no resolution, or there is no current server defined, this
      object returns zero."
    ::= { usrNTPObjects 25 }
usrNTPLastRcvdLeapIndicator OBJECT-TYPE
    SYNTAX      Integer32 (0..3)
    MAX-ACCESS  read-only
    STATUS      current
    DESCRIPTION
     "The value of the last received Leap Indicator field."
    REFERENCE "RFC 2030 (NTPv4)."
    ::= { usrNTPObjects 26 }
usrNTPLastRcvdMode OBJECT-TYPE
    SYNTAX      Integer32 (0..7)
    MAX-ACCESS  read-only
    STATUS      current
    DESCRIPTION
     "The value of the last received Mode field."
    REFERENCE "RFC 2030 (NTPv4)."
    ::= { usrNTPObjects 27 }
usrNTPLastRcvdStratum OBJECT-TYPE
    SYNTAX      Integer32 (0..255)
    MAX-ACCESS  read-only
    STATUS      current
    DESCRIPTION
     "The value of the last received Stratum field."
    REFERENCE "RFC 2030 (NTPv4)."
    ::= { usrNTPObjects 28 }
usrNTPLastRcvdPoll OBJECT-TYPE
    SYNTAX      Integer32 (0..255)
    MAX-ACCESS  read-only
    STATUS      current
    DESCRIPTION
     "The value of the last received Poll field."
    REFERENCE "RFC 2030 (NTPv4)."
    ::= { usrNTPObjects 29 }
usrNTPLastRcvdPrecision OBJECT-TYPE
    SYNTAX      Integer32 (-127..127)
    MAX-ACCESS  read-only
    STATUS      current
    DESCRIPTION
     "The value of the last received Precision field."
    REFERENCE "RFC 2030 (NTPv4)."
    ::= { usrNTPObjects 30 }
usrNTPLastRcvdRootDelay OBJECT-TYPE
    SYNTAX      Integer32
    MAX-ACCESS  read-only
    STATUS      current
    DESCRIPTION
     "The value of the last received Root Delay field."
    REFERENCE "RFC 2030 (NTPv4)."
    ::= { usrNTPObjects 31 }
usrNTPLastRcvdRootDispersion OBJECT-TYPE
    SYNTAX      Integer32
    MAX-ACCESS  read-only
    STATUS      current
    DESCRIPTION
     "The value of the last received Root Dispersion field."
    REFERENCE "RFC 2030 (NTPv4)."
    ::= { usrNTPObjects 32 }
usrNTPLastRcvdReferenceIdentifier OBJECT-TYPE
    SYNTAX      Integer32
    MAX-ACCESS  read-only
    STATUS      current
    DESCRIPTION
     "The value of the last received Reference Identifier field."
    REFERENCE "RFC 2030 (NTPv4)."
    ::= { usrNTPObjects 33 }
usrNTPLastRcvdReferenceTimestampHigh OBJECT-TYPE
    SYNTAX      Integer32
    MAX-ACCESS  read-only
    STATUS      current
    DESCRIPTION
     "The value of the last received Reference Timestamp field (high octets)."
    REFERENCE "RFC 2030 (NTPv4)."
    ::= { usrNTPObjects 34 }
usrNTPLastRcvdReferenceTimestampLow OBJECT-TYPE
    SYNTAX      Integer32
    MAX-ACCESS  read-only
    STATUS      current
    DESCRIPTION
     "The value of the last received Reference Timestamp field (low octets)."
    REFERENCE "RFC 2030 (NTPv4)."
    ::= { usrNTPObjects 35 }
usrNTPLastRcvdOriginateTimestampHigh OBJECT-TYPE
    SYNTAX      Integer32
    MAX-ACCESS  read-only
    STATUS      current
    DESCRIPTION
     "The value of the last received Originate Timestamp field (high octets)."
    REFERENCE "RFC 2030 (NTPv4)."
    ::= { usrNTPObjects 36 }
usrNTPLastRcvdOriginateTimestampLow OBJECT-TYPE
    SYNTAX      Integer32
    MAX-ACCESS  read-only
    STATUS      current
    DESCRIPTION
     "The value of the last received Originate Timestamp field (low octets)."
    REFERENCE "RFC 2030 (NTPv4)."
    ::= { usrNTPObjects 37 }
usrNTPLastRcvdReceiveTimestampHigh OBJECT-TYPE
    SYNTAX      Integer32
    MAX-ACCESS  read-only
    STATUS      current
    DESCRIPTION
     "The value of the last received Receive Timestamp field (high octets)."
    REFERENCE "RFC 2030 (NTPv4)."
    ::= { usrNTPObjects 38 }
usrNTPLastRcvdReceiveTimestampLow OBJECT-TYPE
    SYNTAX      Integer32
    MAX-ACCESS  read-only
    STATUS      current
    DESCRIPTION
     "The value of the last received Receive Timestamp field (low octets)."
    REFERENCE "RFC 2030 (NTPv4)."
    ::= { usrNTPObjects 39 }
usrNTPLastRcvdTransmitTimestampHigh OBJECT-TYPE
    SYNTAX      Integer32
    MAX-ACCESS  read-only
    STATUS      current
    DESCRIPTION
     "The value of the last received Transmit Timestamp field (high octets)."
    REFERENCE "RFC 2030 (NTPv4)."
    ::= { usrNTPObjects 40 }
usrNTPLastRcvdTransmitTimestampLow OBJECT-TYPE
    SYNTAX      Integer32
    MAX-ACCESS  read-only
    STATUS      current
    DESCRIPTION
     "The value of the last received Transmit Timestamp field (low octets)."
    REFERENCE "RFC 2030 (NTPv4)."
    ::= { usrNTPObjects 41 }
usrNTPTimeZone OBJECT-TYPE
    SYNTAX      UsrDisplayString
    MAX-ACCESS  read-write
    STATUS      current
    DESCRIPTION
      "Timezone variables; should be one of the following,
    Egypt, Libya, PRC, ROC, Hongkong, Iran, Israel, Japan, ROK, Singapore,
    Australia/Tasmania, Australia/Queensland, Australia/North,
    Australia/West, Australia/South, Australia/Victoria, Australia/NSW,
    Australia/Yancowinna, Australia/LHI, NZ, GMT, GMT-12, GMT-11, GMT-10,
    GMT-9, GMT-8, GMT-7, GMT-6, GMT-5, GMT-4, GMT-3, GMT-2, GMT-1, GMT+1,
    GMT+2, GMT+3, GMT+4, GMT+5, GMT+6, GMT+7, GMT+8, GMT+9, GMT+10, GMT+11,
    GMT+12, GMT+13, UTC, Universal, Greenwich, Zulu, GMT-0, GMT+0, GB-Eire,
    WET, Iceland, MET, EET, Turkey, W-SU, CET, Factory, US/Eastern, 
    US/Central, US/Mountain, US/Pacific, US/Alaska, US/East-Indiana, 
    US/Arizona, US/Michigan, US/Samoa, US/Aleutian, US/Hawaii, 
    Canada/Newfoundland, Canada/Atlantic, Canada/Eastern, Canada/Central,
    Canada/East-Saskatchewan, Canada/Mountain, Canada/Pacific, Canada/Yukon,
    Mexico/BajaNorte, Mexico/BajaSur, Mexico/General, Cuba, Navajo, Jamaica,
    Brazil/East, Brazil/West, Brazil/Acre, Brazil/DeNoronha, 
    Chile/Continental, Chile/EasterIsland."
    --CONFIGURABLE
    ::= { usrNTPObjects 42 }
--
-- conformance information
--
usrNTPConformance OBJECT IDENTIFIER ::= { usrNTPMib 2 }
usrNTPCompliances OBJECT IDENTIFIER ::= { usrNTPConformance 1 }
usrNTPGroups      OBJECT IDENTIFIER ::= { usrNTPConformance 2 }
usrNTPCompliance MODULE-COMPLIANCE
    STATUS        current
    DESCRIPTION
     "The compliance statement for entities which implement
      the MIB."
    MODULE    -- this module
    MANDATORY-GROUPS {
      usrNTPGroup
    }
    ::= { usrNTPCompliances 1 }
-- units of conformance
usrNTPGroup OBJECT-GROUP
    OBJECTS {
      usrNTPPrimaryServer,
      usrNTPSecondaryServer,
      usrNTPPollingInterval,
      usrNTPMaxRetransmits,
      usrNTPTimeOut,
      usrNTPEnable,
      usrNTPProtocolVersion,
      usrNTPCfmFileName,
      usrNTPCfmSaveFlag,
      usrNTPModuleVersion,
      usrNTPLastGoodServer,
      usrNTPRcvdDatagrams,
      usrNTPRcvdTooShorts,
      usrNTPRcvdBadVersions,
      usrNTPRcvdRequests,
      usrNTPRcvdReplies,
      usrNTPRcvdUnsuportedModes,
      usrNTPSentRequests,
      usrNTPSentReplies,
      usrNTPSentRexmits,
      usrNTPSendErrors,
      usrNTPDnsErrors,
      usrNTPServerTimeouts,
      usrNTPAllocErrors,
      usrNTPResolvedIPAddress,
      usrNTPLastRcvdLeapIndicator,
      usrNTPLastRcvdMode,
      usrNTPLastRcvdStratum,
      usrNTPLastRcvdPoll,
      usrNTPLastRcvdPrecision,
      usrNTPLastRcvdRootDelay,
      usrNTPLastRcvdRootDispersion,
      usrNTPLastRcvdReferenceIdentifier,
      usrNTPLastRcvdReferenceTimestampHigh,
      usrNTPLastRcvdReferenceTimestampLow,
      usrNTPLastRcvdOriginateTimestampHigh,
      usrNTPLastRcvdOriginateTimestampLow,
      usrNTPLastRcvdReceiveTimestampHigh,
      usrNTPLastRcvdReceiveTimestampLow,
      usrNTPLastRcvdTransmitTimestampHigh,
      usrNTPLastRcvdTransmitTimestampLow
    }
    STATUS        current
    DESCRIPTION
     "All objects in this MIB."
    ::= { usrNTPGroups 1 }
-- Time Zone name  table definition      
    usrNTPTimeZoneTable OBJECT-TYPE
    SYNTAX SEQUENCE OF TimeZoneEntry 
    MAX-ACCESS  not-accessible  
    STATUS  current
    DESCRIPTION
        ""
    ::= { usrNTPObjects 43 }
    timeZoneEntry    OBJECT-TYPE
    SYNTAX  TimeZoneEntry
    MAX-ACCESS  not-accessible
    STATUS  current
    DESCRIPTION
        ""
    INDEX   { usrNTPIndex  }
    ::= { usrNTPTimeZoneTable 1 }
    TimeZoneEntry ::=
    SEQUENCE {
   	usrNTPIndex 
		Integer32,
    usrNTPNextTimeZone
        DisplayString
	}
    usrNTPIndex OBJECT-TYPE
    SYNTAX  Integer32
    MAX-ACCESS  not-accessible
    STATUS  current
    DESCRIPTION
        "The key field"
    ::= { timeZoneEntry 1 }
    usrNTPNextTimeZone    OBJECT-TYPE
    SYNTAX  DisplayString
    MAX-ACCESS  read-only
    STATUS  current
    DESCRIPTION 
        "Time zone list name"
    ::= { timeZoneEntry 2 }
    usrNTPTrapsV2 OBJECT-IDENTITY
    STATUS  current
    DESCRIPTION
        "Events for NTP"
    ::= { usrNTPTraps 0 }
    usrNTPServerFailure NOTIFICATION-TYPE
        OBJECTS  {
                  usrNTPPrimaryServer,
                  usrNTPSecondaryServer
                  }
        STATUS  current
        DESCRIPTION     "This trap is generated for NTP Server
                        connectivity failure."
        --#TYPE    "Alarm"
        --#SUMMARY "NTP Server %d or %d Failure"
        --#ARGUMENTS { 0 1 }
        --#SEVERITY MAJOR
        --#STATE    OPERATIONAL
        --#PROBABLECAUSE "networkError"
    ::= { usrNTPTrapsV2 1 }
END     -- End of USR-NTP-MIB DEFINITIONS
-- ************************************************************************
--
--    usr_slip.mib - The CommWorks SLIP MIB module
--
-- Author:         <sanil>
--
USR-SLIP-MIB DEFINITIONS ::= BEGIN
          IMPORTS
               OBJECT-TYPE, MODULE-IDENTITY
				    FROM SNMPv2-SMI
			   common, UsrDisplayString, UsrConfigStatus
						FROM USR-DEFINITIONS-MIB;
usrSLIP MODULE-IDENTITY
        LAST-UPDATED "200205051800Z"
        ORGANIZATION "CommWorks Corporation, a 3Com Company"
        CONTACT-INFO "Customer Support"
        DESCRIPTION
           "The commWorks enterprise defined MIB objects for SLIP"
--      REVISION  "200205051800Z"
--      DESCRIPTION "Converted to SNMPv2"
       ::= { common 35 }
          usrSLIPBase      OBJECT IDENTIFIER ::= { usrSLIP 1 }
          usrSLIPBaseOffloading OBJECT-TYPE
              SYNTAX  INTEGER {
                        yes(2),
                        no(1)
                      }
              MAX-ACCESS   read-write
              STATUS       current
              DESCRIPTION
                      "Indicates whether SLIP framing can be offloaded to
					  the modem card, if modem card is capable of doing it."
              DEFVAL { yes }
              --CONFIGURABLE
              ::= { usrSLIPBase 1 }
          usrSLIPBaseCfgFileName OBJECT-TYPE
              SYNTAX   UsrDisplayString
              MAX-ACCESS   read-only
              STATUS       current
              DESCRIPTION
                      "The name of a ConfigFile to read/write
                      permanent database records. If the value of this
                      object is an empty string, then the SLIP process
                      uses the default name `@file://SlipFile.cfg'."
              ::= { usrSLIPBase 2 }
          usrSLIPBaseCFMSaveStatus OBJECT-TYPE
              SYNTAX  UsrConfigStatus
              MAX-ACCESS  read-write
              STATUS      current
              DESCRIPTION
                      "Setting the value of this object to `save'
                      causes the values of the SLIP Base Group
                      entries to be written out to the current SLIP
                      config file. While the new config file is being
                      written, the SLIP process will set the value
                      of this flag set to `saving''. Any attempts to set
                      the value while it is  not `normal' (i.e. the file
                      is currently being written to the config file)
                      while result in a badValue error being returned.
                      Setting the value to `normal' will result in no
                      action."
              ::= { usrSLIPBase 3 }
          usrSLIPStartMsg OBJECT-TYPE
              SYNTAX  UsrDisplayString
              MAX-ACCESS  read-write
              STATUS      current
              DESCRIPTION
                      "Startup Message for SLIP connection"
              --CONFIGURABLE
              ::= { usrSLIPBase 4 }
END     -- End of USR-SLIP-MIB DEFINITIONS
-- ************************************************************************
--
--	usr_ping.mib - The CommWorks Ping MIB
--
USR-PING-MIB DEFINITIONS ::= BEGIN
	IMPORTS
		OBJECT-TYPE, MODULE-IDENTITY, Integer32, Counter32, IpAddress
								FROM	SNMPv2-SMI
		TruthValue, DisplayString	
								FROM SNMPv2-TC
		common, UsrConfigStatus
								FROM USR-DEFINITIONS-MIB;
usrPing MODULE-IDENTITY
        LAST-UPDATED	"200102161500Z"
        ORGANIZATION	"CommWorks"
	   CONTACT-INFO	""
        DESCRIPTION
            "This MIB Module defines the Commworks enterprise specific
		   interface to the Ping for Services process."
        ::= { common 36 }
-- Begin managed object definitions here...
	usrPingVersion OBJECT-TYPE
	SYNTAX	     DisplayString
	MAX-ACCESS     read-only
	STATUS      	current
	DESCRIPTION
		"The current software version of the Ping Process."
	::= { usrPing 1}
	usrPingConfigFileName OBJECT-TYPE
	SYNTAX	     DisplayString
	MAX-ACCESS     read-only
	STATUS      	current
	DESCRIPTION		
		"The name of a ConfigFile to read/write  permanent database records.
		 If the value of this object is an empty string, then the
		 Ping process uses the default name `@file://PingProcess.cfg'. "
	::= { usrPing 2 }
	usrPingCFMStatusFlag  OBJECT-TYPE
	SYNTAX		UsrConfigStatus
	MAX-ACCESS     read-write
	STATUS      	current
	DESCRIPTION
		"Setting the value of this object to `save' causes the values
		 of the Ping Group to be written out to the current config
		 file, which is stored in the cfgPingFile object. While
		 the new ConfigFile is being written, the Ping process
		 will set the value of this flag set to `saving''. Any
		 attempts to set the value while it is  not `normal'
		 (i.e. the file is currently being written to the
		 ConfigFile) while result in a badValue error being
		 returned. Setting the value to `normal' will result in no
		 action."
	::= { usrPing 3 }
	usrPingBusyOutEnabled	OBJECT-TYPE
	SYNTAX		TruthValue
	MAX-ACCESS	read-write
	STATUS		current
	DESCRIPTION
		"The variable defines whether the Ping process will continuously
		 ping a list of systems and busy out the modems if those systems
		 do not respond in the specified period of time."
	DEFVAL	{ 1 }
	--CONFIGURABLE
	::= { usrPing 4 }
	usrPingBusyOutTable	OBJECT-TYPE
	SYNTAX		SEQUENCE OF UsrPingBusyOutEntry
	MAX-ACCESS	not-accessible
	STATUS		current
	DESCRIPTION
	      	"A list of systems to ping for connectivity."
	::= { usrPing 5 }
	usrPingBusyOutEntry OBJECT-TYPE
	SYNTAX		UsrPingBusyOutEntry
	MAX-ACCESS	not-accessible
	STATUS		current
	DESCRIPTION
			"An entry containing the server info."
	INDEX { usrPingSystem }
	::= { usrPingBusyOutTable 1 }
	UsrPingBusyOutEntry ::=
	SEQUENCE {
		usrPingSystem DisplayString,
		usrPingServerStatus				INTEGER,
		usrPingFrequency				Integer32,
		usrPingMissesAllowed			Integer32,
		usrPingTimeOut					Integer32,
		usrPingServerReachable			INTEGER,
		usrPingServerTimeSinceContacted	Integer32,
		usrPingServerNumberPingsSent		Counter32,
		usrPingServerPingsReceived		Counter32,
		usrPingServerNumberTimeouts		Counter32,
		usrPingServerNumberUnreachable	Counter32,
		usrPingServerAverageResponseTime	Integer32,
		usrPingServerAddress			IpAddress,
		usrPingServerAverageResponseTimeMS Integer32
		}
	usrPingSystem	OBJECT-TYPE
	SYNTAX		DisplayString (SIZE (0..132))
	MAX-ACCESS	not-accessible
	STATUS		current
	DESCRIPTION
		"The name or IP address of the system to ping..."
	--CONFIGURABLE
	::= { usrPingBusyOutEntry 1 }
	usrPingServerStatus	OBJECT-TYPE
	SYNTAX		INTEGER {
				enabled(1),
				disabled(2),
				delete(3)
				}
	MAX-ACCESS	read-write
	STATUS		current
	DESCRIPTION
		"Is this particular server pinged or not?"
	DEFVAL	{ enabled }
	--CONFIGURABLE
	::= { usrPingBusyOutEntry 2 }
	usrPingFrequency	OBJECT-TYPE
	SYNTAX		Integer32(1..200)
	UNITS		"seconds"
	MAX-ACCESS	read-write
	STATUS		current
	DESCRIPTION	
		"How many seconds between each ping request."
	DEFVAL	{ 30 }
	--CONFIGURABLE
	::= { usrPingBusyOutEntry 3 }
	usrPingMissesAllowed	OBJECT-TYPE
	SYNTAX		Integer32(1..1000)
	MAX-ACCESS	read-write
	STATUS		current
	DESCRIPTION	
		"The number of allowable misses before this system is declared
		 unreachable."
	DEFVAL	{ 1 }
	--CONFIGURABLE
	::= { usrPingBusyOutEntry 4 }
	usrPingTimeOut		OBJECT-TYPE
	SYNTAX		Integer32(1..6000)
	UNITS		"seconds"
	MAX-ACCESS	read-write
	STATUS		current
	DESCRIPTION
		"The number of seconds a ping request can be outstanding before
		 it is declared a miss (failure)."
	DEFVAL	{ 10 }
	--CONFIGURABLE
	::= { usrPingBusyOutEntry 5 }
	usrPingServerReachable	OBJECT-TYPE
	SYNTAX		INTEGER {
				reachable (1),
				unreachable (2),
				badNameOrAddress (3),
				unTried (4),
				dnsTimeout (5)
				}
	MAX-ACCESS	read-only
	STATUS		current
	DESCRIPTION
		"Do we consider this server connected?"
	::= { usrPingBusyOutEntry 6 }
	usrPingServerTimeSinceContacted	OBJECT-TYPE
	SYNTAX		Integer32
	UNITS		"seconds"
	MAX-ACCESS	read-only
	STATUS		current
	DESCRIPTION
		"The number of seconds since this server was contacted."
	::= { usrPingBusyOutEntry 7 }
	usrPingServerNumberPingsSent	OBJECT-TYPE
	SYNTAX		Counter32
	MAX-ACCESS	read-only
	STATUS		current
	DESCRIPTION
		"The number of ping requests sent to this server."
	::= { usrPingBusyOutEntry 8 }
	usrPingServerPingsReceived	OBJECT-TYPE
	SYNTAX		Counter32
	MAX-ACCESS	read-only
	STATUS		current
	DESCRIPTION
		"The number of ping responses received from this server."
	::= { usrPingBusyOutEntry 9 }
	usrPingServerNumberTimeouts	OBJECT-TYPE
	SYNTAX		Counter32
	MAX-ACCESS	read-only
	STATUS		current
	DESCRIPTION
		"The number of ping requests sent but not responded to in the specified time."
	::= { usrPingBusyOutEntry 10 }
	usrPingServerNumberUnreachable	OBJECT-TYPE
	SYNTAX		Counter32
	MAX-ACCESS	read-only
	STATUS		current
	DESCRIPTION
		"The number of ICMP responses received that indicate the system was unreachable."
	::= { usrPingBusyOutEntry 11 }
	usrPingServerAverageResponseTime	OBJECT-TYPE
	SYNTAX		Integer32
	UNITS		"seconds"
	MAX-ACCESS	read-only
	STATUS		current
	DESCRIPTION
		"The average response time, in seconds, between ping request and response
		 for this server."
	::= { usrPingBusyOutEntry 12 }
	usrPingServerAddress	OBJECT-TYPE
	SYNTAX		IpAddress
	MAX-ACCESS	read-only
	STATUS		current
	DESCRIPTION
		"The translated IP address of this entry"
	::= { usrPingBusyOutEntry 13 }
	usrPingServerAverageResponseTimeMS	OBJECT-TYPE
	SYNTAX		Integer32
	UNITS		"milliseconds"
	MAX-ACCESS	read-only
	STATUS		current
	DESCRIPTION
		"The average response time, in milliseconds, between ping request
		and response for this server."
	::= { usrPingBusyOutEntry 14 }
END  -- End of USR-PING-MIB DEFINITIONS
-- ************************************************************************
--
--      usr_remote_ping.mib - An enterprise specific Remote Ping MIB
--
-- Author:         Reuben Sivan
-- Created:        Feb-24-1997
--
USR-REMOTE-PING-MIB DEFINITIONS ::= BEGIN
        IMPORTS
          OBJECT-TYPE,
          Integer32,
          IpAddress,
          TimeTicks
                FROM SNMPv2-SMI
          DisplayString,
          RowStatus
                FROM SNMPv2-TC
          MODULE-COMPLIANCE,
          OBJECT-GROUP
                FROM SNMPv2-CONF
          usrRemotePing, UsrConfigStatus
                FROM USR-DEFINITIONS-MIB;
-- The remote ping MIB is a diagnostic tool intended to test reachability,
-- reliability, and round trip delay between a managed USR NAS and any IP
-- system (PC, UNIX, another NAS, etc.) implementing the common ICMP Echo
-- protocol, also known as 'ping' (from the Unix command 'ping' based
-- on that same protocol).
--
-- As a side effect the tool can also be used to estimate DNS processing
-- delays by monitoring the object usrRemotePingDNSResolutionDelay.
--
--
-- In order to test reachability to a given device, an SNMP client
-- application should:
--
-- 1. Issue an SNMP GET for the object usrRemotePingIndexNext.0.
--    (assume the reply is 'x'). This step is optional, clients might browse
--    the table or just attempt a creation on any index until it succeeds.
--
-- 2. Create a new entry in the Remote Ping table by performing a command
--    such as 'SNMP SET usrRemotePingRowStatus.x = createAndWait.
--
-- 3. If the above succeeds, set values of the various settable objects in
--    the new row.
--    In particular, make sure to set usrRemotePingDestination.x to the name
--    or address to be 'pinged'.
--
--    Alternatively, it is possible to combine several settings on a single
--    SNMP PDU. The PDU could also include a rowStatus value of createAndGo
--    (it should be the last entry in the PDU in relation with a given row)
--    in which case a new row will be created, modified and activated in one
--    transaction.
--
-- 4. After setting the various objects of row x to desired values,
--    modify usrRemotePingRowStatus.x to 'active'.
--
-- 5. If the above succeeds, clients will now typically monitor the value of
--                'usrRemotePingConnectionStatus.x'
--    in order to find out if the process is making progress as expected
--    (it should return 'pinging' or 'completed' very soon now).
--
-- 6. Once 'usrRemotePingConnectionStatus' returns the value 'pinging',
--    clients will typically monitor progress by displaying the ongoing
--    values of:
--         usrRemotePingRequestsSent
--         usrRemotePingRepliesReceived
--         usrRemotePingTimeouts
--         usrRemotePingMinRoundTripTime
--         usrRemotePingMaxRoundTripTime
--         usrRemotePingAverageRoundTripTime
--
--    Other objects could be monitored for various diagnostics purposes,
--    such as:
--         usrRemotePingResolvedIPAddress
--         usrRemotePingCreationTime
--         usrRemotePingActivationTime
--         usrRemotePingLastChanged
--
-- 7. A particular ping sequence is completed when
--    'usrRemotePingConnectionStatus' returns 'completed'. At this point,
--    all the values row x will be steady. Note that, unless
--    'usrRemotePingSelfDestroyDelay' is zero, the row will be
--    self-destroyed a number of minutes after completion (see
--    'usrRemotePingSelfDestroyDelay' which has a default value of 10 minutes).
--
-- 8. In order to start a new sequence using the configuration values
--    already available in an existing row, set 'usrRemotePingRowStatus'
--    first to 'notInService' and then again to 'active'."
--
-- The managed objects
--
usrRemotePingObjects OBJECT IDENTIFIER ::= { usrRemotePing 1 }
usrRemotePingBase OBJECT IDENTIFIER ::= { usrRemotePingObjects 1 }
--
-- base (global) objects
--
usrRemotePingIndexNext OBJECT-TYPE
    SYNTAX      Integer32
    MAX-ACCESS  read-only
    STATUS      current
    DESCRIPTION
     "This object contains an appropriate value that can be used for
      'usrRemotePingIndex' when creating a new row in the Remote Ping
      Table'. If the value 0 is returned, it indicates that the table
      contains the maximum number of rows and thus it is not possible to add
      another one."
    ::= { usrRemotePingBase 1 }
usrRemotePingNRows OBJECT-TYPE
    SYNTAX      Integer32
    MAX-ACCESS  read-only
    STATUS      current
    DESCRIPTION
     "Number of rows currently present in the remote ping table."
    ::= { usrRemotePingBase 2 }
usrRemotePingMaxRows OBJECT-TYPE
    SYNTAX      Integer32 (1..1000)
    MAX-ACCESS  read-write
    STATUS      current
    DESCRIPTION
     "Maximum number of rows allowed in the remote ping table.
      Note that setting this object to a number which is smaller than the
      current number of rows will NOT cause any row deletions - rather, the
      effect of such an action will be noted in future attempts at row creation."
    DEFVAL  { 20 }
    --CONFIGURABLE
    ::= { usrRemotePingBase 3 }
usrRemotePingConfigFileName OBJECT-TYPE
    SYNTAX      DisplayString
    MAX-ACCESS  read-only
    STATUS      current
    DESCRIPTION
     "The name of a ConfigFile to read/write  permanent database records.
     If the value of this object is an empty string, then the Remote Ping
     process uses the default name `@file://RemotePingProcess.cfg'."
    ::= { usrRemotePingBase 4 }
usrRemotePingCFMStatusFlag  OBJECT-TYPE
    SYNTAX      UsrConfigStatus
    MAX-ACCESS  read-write
    STATUS      current
    DESCRIPTION
     "Setting the value of this object to `save' causes the values of the
     Remote Ping Group to be written out to the current config file, which
     is stored in the usrRemotePingConfigFileName object. While the new
     ConfigFile is being written, the Remote Ping process will set the value
     of this flag set to `saving''. Any attempts to set the value while it
     is  not `normal' (i.e. the file is currently being written to the
     ConfigFile) will result in a badValue error being returned. Setting
     the value to `normal' will result in no action."
    ::= { usrRemotePingBase 5 }
usrRemotePingTable OBJECT-TYPE
    SYNTAX      SEQUENCE OF UsrRemotePingEntry
    MAX-ACCESS  not-accessible
    STATUS      current
    DESCRIPTION
     "A table of remote ping entries."
    ::= { usrRemotePingObjects 2 }
usrRemotePingEntry OBJECT-TYPE
    SYNTAX      UsrRemotePingEntry
    MAX-ACCESS  not-accessible
    STATUS      current
    DESCRIPTION
     "A list of control entries used to control and monitor the remote
      ping process."
    INDEX   { usrRemotePingIndex }
    ::= { usrRemotePingTable 1 }
UsrRemotePingEntry ::= SEQUENCE {
    usrRemotePingIndex                      Integer32 (1..65535),
    usrRemotePingDestination                DisplayString (SIZE (1..255)),
    usrRemotePingSize                       Integer32(1..1450),
    usrRemotePingData                       OCTET STRING (SIZE (0..255)),
    usrRemotePingTimeOut                    Integer32(1..60),
    usrRemotePingCount                      Integer32(0..65535),
    usrRemotePingInterval                   Integer32(1..65535),
    usrRemotePingTtl                        Integer32(0..16),
    usrRemotePingSelfDestroyDelay           Integer32(0..65535),
    usrRemotePingState                      INTEGER,
    usrRemotePingRequestsSent               Integer32,
    usrRemotePingRepliesReceived            Integer32,
    usrRemotePingTimeouts                   Integer32,
    usrRemotePingLastRoundTripTime          Integer32,
    usrRemotePingMinRoundTripTime           Integer32,
    usrRemotePingMaxRoundTripTime           Integer32,
    usrRemotePingAverageRoundTripTime       Integer32,
    usrRemotePingResolvedIPAddress          IpAddress,
    usrRemotePingDNSResolutionDelay         Integer32,
    usrRemotePingCreationTime               TimeTicks,
    usrRemotePingActivationTime             TimeTicks,
    usrRemotePingLastChangeTime             TimeTicks,
    usrRemotePingRowStatus                  RowStatus
}
usrRemotePingIndex OBJECT-TYPE
    SYNTAX      Integer32 (1..65535)
    MAX-ACCESS  read-only
    STATUS      current
    DESCRIPTION
     "A unique index identifying this entry in the table."
    ::= { usrRemotePingEntry 1 }
usrRemotePingDestination OBJECT-TYPE
    SYNTAX      DisplayString (SIZE (1..255))
    MAX-ACCESS  read-create
    STATUS      current
    DESCRIPTION
     "The host name or IP address (in dot notation) of the target
      destination being tested by this row. A row cannot be activated
      unless this object has a length greater than zero.
      When a row is activated, a request is sent to the internal DNS process
      to resolve the symbolic name into an IP address. That address can be
      displayed by querying the object 'usrRemotePingResolvedIPAddress'.
      If DNS fails, the object usrRemotePingConnectionStatus will indicate
      'dnsFailed'.
      This object cannot be modified whenever usrRemotePingRowStatus is
      'active'."
    DEFVAL  { "" }
    ::= { usrRemotePingEntry 2 }
usrRemotePingSize OBJECT-TYPE
    SYNTAX      Integer32(1..1450)
    MAX-ACCESS  read-create
    STATUS      current
    DESCRIPTION
     "Size of the data to be sent, in bytes.
      Note that the actual datagram will be larger than this value, as it
      will include:
        - MAC header (14 octets on Ethernet)
        - IP header (20 octets)
        - ICMP header (8 octets)
      Together these add to a typical 42 octets.
      This object cannot be modified whenever usrRemotePingRowStatus is
      'active'."
    DEFVAL  { 64 }
    ::= { usrRemotePingEntry 3 }
usrRemotePingData OBJECT-TYPE
    SYNTAX      OCTET STRING (SIZE (0..255))
    MAX-ACCESS  read-create
    STATUS      current
    DESCRIPTION
     "This object specifies the data to be transmitted. If the length of
      this object is bigger than usrRemotePingSize, only the first
      usrRemotePingSize octets will be used. If the length of this
      object is zero, the agent will use random data. If the length of
      this object is smaller than usrRemotePingSize, the data pattern
      will be repeated as many times as necessary to fill up the
      transmission buffer.
      This object cannot be modified whenever usrRemotePingRowStatus is
      'active'."
    DEFVAL  { "" }
    ::= { usrRemotePingEntry 4 }
usrRemotePingTimeOut OBJECT-TYPE
    SYNTAX      Integer32(1..60)
    MAX-ACCESS  read-create
    STATUS      current
    DESCRIPTION
     "Amount of time in seconds before deciding that a transmission has
      not been replied to.
      This object cannot be modified whenever usrRemotePingRowStatus is
      'active'."
    DEFVAL  { 20 }
    ::= { usrRemotePingEntry 5 }
usrRemotePingCount OBJECT-TYPE
    SYNTAX      Integer32(0..65535)
    MAX-ACCESS  read-create
    STATUS      current
    DESCRIPTION
     "The number of ICMP ECHO requests to be sent in this sequence.
      The conventional value of zero is interpreted as infinite: the process
      will continue forever until the row is deleted or deactivated via an
      SNMP SET command.
      This object cannot be modified whenever usrRemotePingRowStatus is
      'active'."
    DEFVAL  { 1 }
    ::= { usrRemotePingEntry 6 }
usrRemotePingInterval OBJECT-TYPE
    SYNTAX      Integer32(1..65535)
    MAX-ACCESS  read-create
    STATUS      current
    DESCRIPTION
     "Number of seconds between successive ECHO REQUEST request
      transmissions. Note that the actual interval might be different for
      any given transmission, as the agent will not send a new request
      before a previous request is completed (replied or timed-out).
      This object cannot be modified whenever usrRemotePingRowStatus is
      'active'."
    DEFVAL  { 1 }
    ::= { usrRemotePingEntry 7 }
usrRemotePingTtl OBJECT-TYPE
    SYNTAX      Integer32(0..16)
    MAX-ACCESS  read-create
    STATUS      current
    DESCRIPTION
     "The TTL (time to live) to be used for the ECHO REQUEST commands.
      If this object is zero, the TTL value currently in use by the
      IP stack will be in effect.
      This object cannot be modified whenever usrRemotePingRowStatus is
      'active'."
    DEFVAL  { 0 }
    ::= { usrRemotePingEntry 8 }
usrRemotePingSelfDestroyDelay OBJECT-TYPE
    SYNTAX      Integer32(0..65535)
    MAX-ACCESS  read-create
    STATUS      current
    DESCRIPTION
     "Number of minutes this row is allowed to be in a state of inactivity
      before it is destroyed by the agent.
      A row is considered inactive anytime 'usrRemotePingState' is one of:
        - notActive
        - dnsFailed
        - badAddress
        - completed
        - allocFailed
      The wait timer is reset upon any change in a row received through an
      SNMP 'SET' command.
      A value of zero implies no self-destruction will take place on
      this row.
      This object can be modified at any time."
    DEFVAL  { 10 }
    ::= { usrRemotePingEntry 9 }
usrRemotePingState OBJECT-TYPE
    SYNTAX      INTEGER {
      notActive(1),    -- this row is not active.
      waitingDns(2),   -- waiting for DNS resolution.
      dnsFailed(3),    -- destination address could not be resolved.
      badAddress(4),   -- the resolved IP address is illegal.
      pinging(5),      -- sending ping commands after successful DNS.
      completed(6),    -- the requested number of iterations is completed.
      allocFailed(7)   -- failed to allocate resources.
    }
    MAX-ACCESS  read-only
    STATUS      current
    DESCRIPTION
     "The state of the 'remote ping' process associated with this row.
      Before this row is activated, this object will have the value
      'notActive(1)'.
      Upon activation, if DNS resolution is needed, the object will
      receive the value 'waitingDns(2)'. If DNS times out or otherwise
      fails, this object will receive the value 'dnsFailed(3)'.
      If the resolved IP address is not legal, this object value will be
      'badAddress(4)'.
      If none of the above fails, the first ping command will be sent
      and this object will indicate the value 'pinging(5)'.
      After the desired number of ping commands have been sent and
      replied to (or timed-out) this object will receive the value
      completed(6)'.
      If there is a resource allocation error along the way, the process
      will stop and this object will receive the value allocFailed(7)."
    ::= { usrRemotePingEntry 10 }
usrRemotePingRequestsSent OBJECT-TYPE
    SYNTAX      Integer32
    MAX-ACCESS  read-only
    STATUS      current
    DESCRIPTION
     "Number of requests transmitted so far since this row became active."
    ::= { usrRemotePingEntry 11 }
usrRemotePingRepliesReceived OBJECT-TYPE
    SYNTAX      Integer32
    MAX-ACCESS  read-only
    STATUS      current
    DESCRIPTION
     "Number of replies received so far since this row became active."
    ::= { usrRemotePingEntry 12 }
usrRemotePingTimeouts OBJECT-TYPE
    SYNTAX      Integer32
    MAX-ACCESS  read-only
    STATUS      current
    DESCRIPTION
     "Number of requests timed-out (no reply received after
      'usrRemotePingTimeOut' seconds) since this row became active."
    ::= { usrRemotePingEntry 13 }
usrRemotePingLastRoundTripTime OBJECT-TYPE
    SYNTAX      Integer32
    MAX-ACCESS  read-only
    STATUS      current
    DESCRIPTION
     "The round trip time in milliseconds experienced by the last
      request-reply iteration. If the last iteration was a time-out, this
      object will return the value -1.
      This object remains zero until an actual reply or timeout is
      received."
    ::= { usrRemotePingEntry 14 }
usrRemotePingMinRoundTripTime OBJECT-TYPE
    SYNTAX      Integer32
    MAX-ACCESS  read-only
    STATUS      current
    DESCRIPTION
     "The minimum round trip time in milliseconds, not including timed out
      requests. This object remains zero until an actual reply is received."
    ::= { usrRemotePingEntry 15 }
usrRemotePingMaxRoundTripTime OBJECT-TYPE
    SYNTAX      Integer32
    MAX-ACCESS  read-only
    STATUS      current
    DESCRIPTION
     "The maximum round trip time in milliseconds, not including timed out
      requests. This object remains zero until an actual reply is received."
    ::= { usrRemotePingEntry 16 }
usrRemotePingAverageRoundTripTime OBJECT-TYPE
    SYNTAX      Integer32
    MAX-ACCESS  read-only
    STATUS      current
    DESCRIPTION
     "The average round trip time in milliseconds, not counting
      timed-out requests. This object remains zero until an actual reply is
      received."
    ::= { usrRemotePingEntry 17 }
usrRemotePingDNSResolutionDelay OBJECT-TYPE
    SYNTAX      Integer32
    MAX-ACCESS  read-only
    STATUS      current
    DESCRIPTION
     "The time elapsed, in milliseconds, since the agent issued a DNS query
      for this entry until it received a reply."
    ::= { usrRemotePingEntry 18 }
usrRemotePingResolvedIPAddress OBJECT-TYPE
    SYNTAX      IpAddress
    MAX-ACCESS  read-only
    STATUS      current
    DESCRIPTION
     "The IP address resolved from the destination address string.
      If there is no resolution, this object returns zero."
    ::= { usrRemotePingEntry 19 }
usrRemotePingCreationTime OBJECT-TYPE
    SYNTAX      TimeTicks
    MAX-ACCESS  read-only
    STATUS      current
    DESCRIPTION
     "The value of sysUpTime at the time this row was created."
    ::= { usrRemotePingEntry 20 }
usrRemotePingActivationTime OBJECT-TYPE
    SYNTAX      TimeTicks
    MAX-ACCESS  read-only
    STATUS      current
    DESCRIPTION
     "The value of sysUpTime at the time this row was last activated (or
      zero, if never)."
    ::= { usrRemotePingEntry 21 }
usrRemotePingLastChangeTime OBJECT-TYPE
    SYNTAX      TimeTicks
    MAX-ACCESS  read-only
    STATUS      current
    DESCRIPTION
     "The value of sysUpTime at the time any object in this row was last
      modified."
    ::= { usrRemotePingEntry 22 }
usrRemotePingRowStatus OBJECT-TYPE
    SYNTAX      RowStatus
    MAX-ACCESS  read-create
    STATUS      current
    DESCRIPTION
     "This object is used to create, modify or delete a row in this table.
      Setting this object to 'createAndWait' creates the row with default
      values. Right after creation the value of this object will be
      'notReady'.
      When all parameters are given proper values, this object
      will return the value 'notInService', at which point the client can
      set the object to 'active' to activate the row.
      Modifying this object from 'active' to 'notInService' will stop any
      on-going sequence, at which point the row can be re-activated by
      setting the object to 'active' again, after possibly modifying some of
      the associated parameters. Note that this will cause zeroing out of
      any on-going counters such as 'usrRemotePingRequestsSent'.
      Setting this object to 'destroy' will stop any on-going activity and
      delete the row."
    DEFVAL  { createAndWait }
    ::= { usrRemotePingEntry 23 }
--
-- conformance information
--
usrRemotePingConformance OBJECT IDENTIFIER ::= { usrRemotePing 2 }
usrRemotePingCompliances OBJECT IDENTIFIER ::= { usrRemotePingConformance 1 }
usrRemotePingGroups      OBJECT IDENTIFIER ::= { usrRemotePingConformance 2 }
usrRemotePingCompliance MODULE-COMPLIANCE
        STATUS        current
        DESCRIPTION
            "The compliance statement for entities which implement
             the MIB."
        MODULE    -- this module
            MANDATORY-GROUPS {
                usrRemotePingGroup
            }
        ::= { usrRemotePingCompliances 1 }
-- units of conformance
usrRemotePingGroup OBJECT-GROUP
        OBJECTS {
                usrRemotePingIndexNext,
                usrRemotePingNRows,
                usrRemotePingMaxRows,
                usrRemotePingIndex,
                usrRemotePingDestination,
                usrRemotePingSize,
                usrRemotePingData,
                usrRemotePingTimeOut,
                usrRemotePingCount,
                usrRemotePingInterval,
                usrRemotePingTtl,
                usrRemotePingSelfDestroyDelay,
                usrRemotePingState,
                usrRemotePingRequestsSent,
                usrRemotePingRepliesReceived,
                usrRemotePingTimeouts,
                usrRemotePingLastRoundTripTime,
                usrRemotePingMinRoundTripTime,
                usrRemotePingMaxRoundTripTime,
                usrRemotePingAverageRoundTripTime,
                usrRemotePingResolvedIPAddress,
                usrRemotePingDNSResolutionDelay,
                usrRemotePingCreationTime,
                usrRemotePingActivationTime,
                usrRemotePingLastChangeTime,
                usrRemotePingRowStatus
        }
        STATUS        current
        DESCRIPTION
          "All objects in this MIB."
        ::= { usrRemotePingGroups 1 }
END     -- End of USR-REMOTE-PING-MIB DEFINITIONS
-- ************************************************************************
--
--      usr_traceroute.mib - An enterprise specific Traceroute MIB
--
-- Author:         Jeff Haag
-- Created:        Mar-13-1997
--
--
-- The traceroute MIB is a diagnostic tool intended to retrieve route 
-- information between a managed CommWork's NAS and any IP system (PC, Unix, 
-- another NAS etc).  It only requires the routers along the way to the
-- the destination to implement IP routing and ICMP Time Exceeded messages.
-- The destination must implement UDP and return ICMP error message 
-- destination unreachable.
-- The functionality is similar to the Unix command 'traceroute' based
-- on those same protocols.
--
-- In order to determine the route to a host, the SNMP client application 
-- should do the following:
--
--
-- *********To start the traceroute*********
--
--  1. Create a new entry in the Traceroute table by performing a command
--     such as 'SNMP SET usrTracerouteRowStatus.x = createAndWait.
--
--  2. If the above succeeds, set values of the various settable objects in
--     the new row.  In particular, make sure to set 
--     usrTracerouteDestination.x to the name or address whose route is to 
--     be traced.
--
--  3. After setting the various objects of row x to desired values,
--     modify usrTracerouteRowStatus.x to 'active'.
--
-- OR
--
--  1. set values of the various settable objects in a new row.  
--     In particular, make sure to set usrTracerouteDestination.x to the 
--     name or address whose route is to be traced. 
--
--  2. Create and activate new entry in the Traceroute table by performing a command
--     such as 'SNMP SET usrTracerouteRowStatus.x = createAndGo.
--
--  3. The row status will automatically get set to active after row creation
--     and the command will begin
--
-- *********After starting the traceroute*********
--
-- 4. If the above succeeds, clients will now typically monitor the values of
--    'usrTracerouteState.x' in order to find out if the process is 
--    'completed' or an error has occurred
--
-- 5. Once 'usrTracerouteState.x' returns the value 'completed',
--    clients can view the route information in the usrTracerouteHopTable
--    by looking at rows that have a matching usrTraceRouteIndex
--
-- 6. A particular traceroute is completed when
--    'usrTracerouteState.x' returns 'completed'. At this point,
--    all the values of row x will be steady and no more entries for this 
--    traceroute will be added to the hop table. 
--
-- 7. In order to start a new sequence using the configuration values
--    already available in an existing row, set 'usrTracerouteRowStatus'
--    first to 'notInService' and then again to 'active'."  This will 
--	  automatically clean up any previous corresponding entries in the 
--    traceroute hop table
--
-- ******************
-- additional notes
-- ******************
-- a)  A row will be removed from the table after 60 minutes if there has been
--     no activity
-- b)  A row may be deleted/destroyed at any time, even if the row status is 
--     'active'
--
USR-TRACEROUTE-MIB DEFINITIONS ::= BEGIN
        IMPORTS
          OBJECT-TYPE, MODULE-IDENTITY, Integer32, IpAddress
                FROM SNMPv2-SMI
          RowStatus
                FROM SNMPv2-TC
          common, UsrDisplayString, UsrConfigStatus 
                FROM USR-DEFINITIONS-MIB;
usrTraceroute MODULE-IDENTITY
        LAST-UPDATED "200205051800Z"
        ORGANIZATION "CommWorks Corporation, a 3Com Company"
        CONTACT-INFO "Customer Support"
        DESCRIPTION
           "The commWorks enterprise defined MIB objects for TraceRoute"
--      REVISION  "200205051800Z"
--      DESCRIPTION "Converted to SNMPv2"
       ::= { common 40 }
--
-- Traceroute managed objects
--
usrTracerouteBase OBJECT IDENTIFIER ::= { usrTraceroute 1 }
--
-- Base Objects
--
usrTracerouteIndexNext OBJECT-TYPE
    SYNTAX  Integer32
    MAX-ACCESS  read-only
    STATUS      current
    DESCRIPTION
     "This object contains an appropriate value that can be used for
      'usrTracerouteIndex' when creating a new row in the Traceroute
      Table'. If the value 0 is returned, it indicates that the table
      contains the maximum number of rows and thus it is not possible to add
      another one."
    ::= { usrTracerouteBase 1 }
usrTracerouteIndexNRows OBJECT-TYPE
    SYNTAX  Integer32
    MAX-ACCESS  read-only
    STATUS      current
    DESCRIPTION
     "Number of rows currently present in the Traceroute table."
    ::= { usrTracerouteBase 2 }
usrTracerouteMaxRows OBJECT-TYPE
    SYNTAX  Integer32 (1..255)
    MAX-ACCESS  read-write
    STATUS      current
    DESCRIPTION
     "Maximum number of rows allowed in the Traceroute table.
      Note that setting this object to a number which is smaller than the
      current number of rows will NOT cause any row deletions - rather, the
      effect of such an action will be noted in future attempts at row creation."
    DEFVAL  { 20 }
    --CONFIGURABLE
    ::= { usrTracerouteBase 3 }
usrTracerouteConfigFileName OBJECT-TYPE
    SYNTAX  UsrDisplayString
    MAX-ACCESS  read-only
    STATUS      current
    DESCRIPTION
     "The name of a ConfigFile to read/write  permanent database records.
     If the value of this object is an empty string, then the Traceroute
     process uses the default name `@file://TracerouteProcess.cfg'."
    ::= { usrTracerouteBase 4 }
usrTracerouteCFMStatusFlag  OBJECT-TYPE
    SYNTAX  UsrConfigStatus
    MAX-ACCESS  read-write
    STATUS      current
    DESCRIPTION
     "Setting the value of this object to `save' causes the values of the
     Remote Ping Group to be written out to the current config file, which
     is stored in the usrTracerouteConfigFileName object. While the new
     ConfigFile is being written, the Remote Ping process will set the value
     of this flag set to `saving''. Any attempts to set the value while it
     is  not `normal' (i.e. the file is currently being written to the
     ConfigFile) while result in a badValue error being returned. Setting
     the value to `normal' will result in no action."
    ::= { usrTracerouteBase 5 }
usrTracerouteTable OBJECT-TYPE
    SYNTAX  SEQUENCE OF UsrTracerouteEntry
    MAX-ACCESS  not-accessible
    STATUS      current
    DESCRIPTION
     "A table of traceroute entries."
    ::= { usrTraceroute 2 }
usrTracerouteEntry OBJECT-TYPE
    SYNTAX  UsrTracerouteEntry
    MAX-ACCESS  not-accessible
    STATUS      current
    DESCRIPTION
     "A list of fields defining this traceroute"
    INDEX   { usrTracerouteIndex }
    ::= { usrTracerouteTable 1 }
UsrTracerouteEntry ::= SEQUENCE {
    usrTracerouteIndex                      Integer32,
    usrTracerouteDestination                UsrDisplayString (SIZE (1..255)),
    usrTracerouteResolvedIPAddress          IpAddress,
    usrTracerouteHopTimeout                 Integer32(1..60),
    usrTracerouteHopProbes                  Integer32(1..10),
    usrTracerouteMaxHops                    Integer32(1..255),
    usrTracerouteUDPPort                    Integer32(1..65000),
    usrTracerouteDataSize                   Integer32(1..8184),
    usrTracerouteHopCount                   Integer32,
    usrTracerouteState                      INTEGER,
    usrTracerouteRowStatus                  RowStatus
}
usrTracerouteIndex OBJECT-TYPE
    SYNTAX  Integer32
    MAX-ACCESS  not-accessible
    STATUS      current
    DESCRIPTION
     "A unique index identifying this entry in the table."
    ::= { usrTracerouteEntry 1 }
usrTracerouteDestination OBJECT-TYPE
    SYNTAX  UsrDisplayString (SIZE (1..255))
    MAX-ACCESS  read-write
    STATUS      current
    DESCRIPTION
     "The host name or IP address (in dot notation) of the target
      destination being traced by this row. A row cannot be activated
      unless this object has a length greater than zero.
      Router DNS services will always be used to resolve (names) and/or
	  verify addresses in dot notation.  If DNS fails, the object 
	  usrTracerouteRowState will indicate 'dnsFailed' or 'badAddress'.
      This object cannot be modified whenever usrTracerouteRowStatus is
      'active'."
    DEFVAL  { "" }
    ::= { usrTracerouteEntry 2 }
usrTracerouteResolvedIPAddress OBJECT-TYPE
    SYNTAX  IpAddress
    MAX-ACCESS  read-only
    STATUS      current
    DESCRIPTION
     "The IP address resolved from the destination address string.
      If an IP address was set in the destination field it will
      be reflected here as well.
      If an address cannot be resolved, this object returns zero and the
      state field is set to dnsFail"
    ::= { usrTracerouteEntry 3 }
usrTracerouteHopTimeout OBJECT-TYPE
    SYNTAX  Integer32(1..60)
    MAX-ACCESS  read-write
    STATUS      current
    DESCRIPTION
     "Amount of time in seconds before retrying a hop.  This object cannot 
	  be modified whenever usrTracerouteRowStatus is 'active'."
    DEFVAL  { 3 }
    ::= { usrTracerouteEntry 4 }
usrTracerouteHopProbes OBJECT-TYPE
    SYNTAX  Integer32(1..10)
    MAX-ACCESS  read-write
    STATUS      current
    DESCRIPTION
     "The maixmum number of times to try to discern a hop before moving 
	  on to the next hop"
    DEFVAL  { 3 }
    ::= { usrTracerouteEntry 5 }
usrTracerouteMaxHops OBJECT-TYPE
    SYNTAX  Integer32(1..255)
    MAX-ACCESS  read-write
    STATUS      current
    DESCRIPTION
     "The maixmum number of hops to trace before quitting."
    DEFVAL  { 30 }
    ::= { usrTracerouteEntry 6 }
usrTracerouteUDPPort OBJECT-TYPE
    SYNTAX  Integer32(1..65000)
    MAX-ACCESS  read-write
    STATUS      current
    DESCRIPTION
     "The UDP port value to use when attempting to find the route"
    DEFVAL  { 33434 }
    ::= { usrTracerouteEntry 7 }
usrTracerouteDataSize OBJECT-TYPE
    SYNTAX  Integer32(1..8184)
    MAX-ACCESS  read-write
    STATUS      current
    DESCRIPTION
     "The maixmum number of hops to trace before quitting."
    DEFVAL  { 1 }
    ::= { usrTracerouteEntry 8 }
usrTracerouteHopCount OBJECT-TYPE
    SYNTAX  Integer32
    MAX-ACCESS  read-only
    STATUS      current
    DESCRIPTION
     "The number of hops taken to get to the destination."
    ::= { usrTracerouteEntry 9 }
usrTracerouteState OBJECT-TYPE
    SYNTAX  INTEGER {
      notActive(1),        -- this row is not active.
      waitingDns(2),       -- waiting for DNS resolution.
      dnsFailed(3),        -- destination address could not be resolved.
      badAddress(4),       -- the resolved IP address is illegal.
      hopsExceeded(5),     -- the maximum number of hops was exceeded
      destUnreachable(6),  -- a route to the host could not be found
      tracing(7),          -- performing traceroute
      completed(8),        -- traceroute completed successfully
	  resourceFailure(9)   -- there was not enough resources to complete the command
    }
    MAX-ACCESS  read-only
    STATUS      current
    DESCRIPTION
     "The state of the 'traceroute' process associated with this row.
      Before this row is activated, this object will have the value
      'notActive(1)'.
      Upon activation, if DNS resolution is needed, the object will
      receive the value 'waitingDns(2)'. If DNS times out or otherwise
      fails, this object will receive the value 'dnsFailed(3)'.
      If the resolved IP address is not legal, this object value will be
      'badAddress(4)'.
      If the a timeout occurs or the hop count is exceeded, the value will
      be 'hopTimeout(6)' or 'hopsExceeded(7)'.
	  If a route to the host could not be found, a 'destUnreachable(8)'
	  value will be returned.
      If none of the above fails, the first traceroute command will be sent
      and this object will indicate the value 'tracing(9)'.
      After the completes this object will receive the value
      completed(10)'."
    ::= { usrTracerouteEntry 10 }
usrTracerouteRowStatus OBJECT-TYPE
    SYNTAX          RowStatus
    MAX-ACCESS          read-write
    STATUS              current
    DESCRIPTION
     "This object is used to create, modify or delete a row in this table.
      Setting this object to 'createAndWait' creates the row with default
      values. Right after creation the value of this object will be
      'notReady'.
      When all parameters are given proper values, this object
      will return the value 'notInService', at which point the client can
      set the object to 'active' to activate the row.
      Modifying this object from 'active' to 'notInService' will cancel any
      on-going traceroute and remove entries for it from the usrTracerouteHopTable.
      Setting the object to 'active' again will start a new traceroute with the
      supplied parameters
      Setting this object to 'destroy' will stop any on-going activity and
      delete the row."
    DEFVAL  { createAndWait }
    ::= { usrTracerouteEntry 11 }
usrTracerouteHopTable OBJECT-TYPE
    SYNTAX  SEQUENCE OF UsrTracerouteHopEntry
    MAX-ACCESS  not-accessible
    STATUS      current
    DESCRIPTION
     "A table of traceroute hop entries."
    ::= { usrTraceroute 3 }
usrTracerouteHopEntry OBJECT-TYPE
    SYNTAX  UsrTracerouteHopEntry
    MAX-ACCESS  not-accessible
    STATUS      current
    DESCRIPTION
     "A list of fields containing the hop information for all traceroute instances"
    INDEX   { usrTracerouteTableIndex, usrTracerouteHopIndex }
    ::= { usrTracerouteHopTable 1 }
UsrTracerouteHopEntry ::= SEQUENCE {
    usrTracerouteTableIndex                 Integer32,
    usrTracerouteHopIndex                   Integer32,
    usrTracerouteHopIPAddress               IpAddress,
    usrTracerouteHopRoundTripTime           Integer32
}
usrTracerouteTableIndex OBJECT-TYPE
    SYNTAX  Integer32
    MAX-ACCESS  not-accessible
    STATUS      current
    DESCRIPTION
     "The index into the usrTracerouteTable corresponding to this hop."
    ::= { usrTracerouteHopEntry 1 }
usrTracerouteHopIndex OBJECT-TYPE
    SYNTAX  Integer32
    MAX-ACCESS  not-accessible
    STATUS      current
    DESCRIPTION
     "The hop number corresponding to the usrTracerouteHopIPAddress in this row."
    ::= { usrTracerouteHopEntry 2 }
usrTracerouteHopIPAddress OBJECT-TYPE
    SYNTAX  IpAddress
    MAX-ACCESS  read-only
    STATUS      current
    DESCRIPTION
     "The IP address for a hop.  An address of zero means that there was no response
	  from that hop."
    ::= { usrTracerouteHopEntry 3 }
usrTracerouteHopRoundTripTime OBJECT-TYPE
    SYNTAX  Integer32
    MAX-ACCESS  read-only
    STATUS      current
    DESCRIPTION
     "Round trip time for this hop in milliseconds."
    ::= { usrTracerouteHopEntry 4 }
END     -- End of USR-TRACEROUTE-MIB DEFINITIONS
-- ************************************************************************
--
--	usr_tcp.mib
--
-- Author:         Jim Halpin
--
USR-TCP-MIB DEFINITIONS ::= BEGIN
	IMPORTS
          OBJECT-TYPE, MODULE-IDENTITY,
          Integer32
                  FROM SNMPv2-SMI
          common, UsrConfigStatus, UsrDisplayString
                  FROM USR-DEFINITIONS-MIB;
usrTcp  MODULE-IDENTITY
        LAST-UPDATED "200205012030Z"
        ORGANIZATION "CommWorks Corporation, a 3Com Company"
        CONTACT-INFO "Customer Support"
        DESCRIPTION
                 "The commWorks enterprise defined MIB objects for 
                  the TCP process."
--      REVISION "200205012030Z"
--      DESCRIPTION "Converted to SNMPv2"
        ::= { common 45 }
   -- Begin managed object definitions here...
usrTcpCFMStatusFlag OBJECT-TYPE
	SYNTAX		UsrConfigStatus
	MAX-ACCESS		read-write
	STATUS		    current
	DESCRIPTION
		"This variable controls saving and loading of configuration
           information for the TCP Module. The value can 
           be set to either save or load by a management station. The other
           values indicate if any configuration operation and what type
           is in progress."
::= { usrTcp 1 }
usrTcpCfgFileName OBJECT-TYPE
	SYNTAX      UsrDisplayString
	MAX-ACCESS      read-only
	STATUS          current
	DESCRIPTION		
		"The name of a ConfigFile to read/write  permanent database records.
		 If the value of this object is an empty string, then the
		 TCP module uses the default name `@file://TCPModule.cfg'. "
::= { usrTcp 2 }
usrTcpMaxConn	OBJECT-TYPE
	SYNTAX	Integer32 (0..4096)
	MAX-ACCESS	read-write
	STATUS	    current
	DESCRIPTION
		"The limit on the total number of TCP connections
           the entity can support.  In entities where the
           maximum number of connections is dynamic, this
           object should contain the value -1.
           This a read-write version of the tcpMaxConn object in rfc1213."
	--CONFIGURABLE
::= { usrTcp 3 }
usrTcpNagleStatus	OBJECT-TYPE
	SYNTAX	INTEGER {
               enable(1),       -- enable tcp nagle algorithm
               disable(0)       -- disable tcp nagle algorithm
               }
	MAX-ACCESS	read-write
	STATUS	    current
	DESCRIPTION
		"Enable or disable tcp Nagle Algorithm.  When read, it 
           returns the current setting"
	--CONFIGURABLE
::= { usrTcp 4 }
usrTcpKeepaliveStatus	OBJECT-TYPE
	SYNTAX	INTEGER {
               enable(1),       -- enable TCP keep-alives
               disable(0)       -- disable TCP keep-alives
               }
	MAX-ACCESS	read-write
	STATUS	    current
	DESCRIPTION
		"Enable or disable TCP keep-alives.  When read, it 
           returns the current setting."
	--CONFIGURABLE
::= { usrTcp 5 }
usrTcpKeepaliveInterval	OBJECT-TYPE
	SYNTAX	Integer32 (1..2147483)
	MAX-ACCESS	read-write
	STATUS	    current
	DESCRIPTION
		"The number of seconds of inactivity on a TCP session
		after which a TCP keep-alive packet is transmitted on
		the session to discover whether it is still active."
	--CONFIGURABLE
::= { usrTcp 6 }
usrTcpAheadofSegDropped	OBJECT-TYPE
	SYNTAX	Integer32
	MAX-ACCESS	read-only
	STATUS	    current
	DESCRIPTION
	"Ahead of TCP sequences received and dropped counter can 
  	also be a good indication of network packet dropping"
::= { usrTcp 7 }
END         -- End of USR-TCP-MIB DEFINITIONS
USR-IGMP-MIB DEFINITIONS ::= BEGIN
IMPORTS
    OBJECT-TYPE, MODULE-IDENTITY, OBJECT-IDENTITY, NOTIFICATION-TYPE,
    Counter32, Integer32, IpAddress, Gauge32, TimeTicks
        FROM SNMPv2-SMI
    RowStatus, TruthValue, DisplayString
        FROM SNMPv2-TC
    common, UsrDisplayString
        FROM USR-DEFINITIONS-MIB;
usrIgmp  MODULE-IDENTITY
         LAST-UPDATED "200202071020Z"
         ORGANIZATION "CommWorks Corporation, a 3Com Company"
         CONTACT-INFO "Customer Support"
         DESCRIPTION
                 "The commWorks enterprise defined MIB objects
                   for IGMP"
--       REVISION     "200202071020Z"
--       DESCRIPTION "Converted traps to SNMPv2"
    ::= { common 53 }
usrIgmpInterfaceTable OBJECT-TYPE
    SYNTAX     SEQUENCE OF UsrIgmpInterfaceEntry
    MAX-ACCESS not-accessible
    STATUS     current
    DESCRIPTION
            "The (conceptual) table listing the interfaces on which IGMP
            is enabled."
    ::= { usrIgmp 1 }
usrIgmpInterfaceEntry OBJECT-TYPE
    SYNTAX     UsrIgmpInterfaceEntry
    MAX-ACCESS not-accessible
    STATUS     current
    DESCRIPTION
            "An entry (conceptual row) representing an interface on
            which IGMP is enabled."
    INDEX      { usrIgmpInterfaceIfName }
    ::= { usrIgmpInterfaceTable 1 }
UsrIgmpInterfaceEntry ::= SEQUENCE {
    usrIgmpInterfaceIfName                DisplayString,
    usrIgmpInterfaceQueryInterval         Integer32,
    usrIgmpInterfaceStatus                RowStatus,
    usrIgmpInterfaceVersion               INTEGER,
    usrIgmpInterfaceQuerier               IpAddress,
    usrIgmpInterfaceQueryMaxResponseTime  Integer32,
    usrIgmpInterfaceVersion1QuerierTimer  Integer32,                        
    usrIgmpInterfaceWrongVersionQueries   Counter32,                        
    usrIgmpInterfaceJoins                 Counter32,                        
    usrIgmpInterfaceGroups	          Gauge32,
    usrIgmpInterfaceRobustness            Integer32,
    usrIgmpInterfaceMcastFwdEnabled       TruthValue,
    usrIgmpInterfacePushEnabled           TruthValue,
    usrIgmpInterfaceProxyEnabled          TruthValue,
    usrIgmpInterfaceShortPackets          Counter32,
    usrIgmpInterfaceBadChecksum           Counter32,
    usrIgmpInterfaceQueriesReceived       Counter32,
    usrIgmpInterfaceReportsReceived       Counter32,
    usrIgmpInterfaceReportsForKnownGroups Counter32,
    usrIgmpInterfaceReportsSent           Counter32,
    usrIgmpInterfaceWrongVersionReports   Counter32
}
usrIgmpInterfaceIfName OBJECT-TYPE
    SYNTAX     DisplayString (SIZE (1..32))
    MAX-ACCESS not-accessible
    STATUS     current
    DESCRIPTION
            "The interface name for which IGMP is enabled."
::= { usrIgmpInterfaceEntry 1 }
usrIgmpInterfaceQueryInterval OBJECT-TYPE
    SYNTAX     Integer32 (5..65535)
    UNITS      "seconds"
    MAX-ACCESS read-create
    STATUS     current
    DESCRIPTION
            "The frequency at which IGMP Host-Query packets are
            transmitted on this interface."
    DEFVAL     { 125 }
    --CONFIGURABLE
::= { usrIgmpInterfaceEntry 2 }
usrIgmpInterfaceStatus OBJECT-TYPE
    SYNTAX     RowStatus
    MAX-ACCESS read-create
    STATUS     current
    DESCRIPTION
            "The activation of a row enables IGMP on the interface.  The
            destruction of a row disables IGMP on the interface."
    --CONFIGURABLE
::= { usrIgmpInterfaceEntry 3 }
usrIgmpInterfaceVersion OBJECT-TYPE
    SYNTAX     INTEGER { version1(1), version2(2) }
    MAX-ACCESS read-create
    STATUS     current
    DESCRIPTION
            "The version of IGMP which is running on this interface.
            This object can be used to configure a router capable of
            running either value.  For IGMP to function correctly, all   
            routers on a LAN must be configured to run the same version  
            of IGMP on that LAN."                                        
    DEFVAL     { version2 }
    --CONFIGURABLE
::= { usrIgmpInterfaceEntry 4 }
usrIgmpInterfaceQuerier OBJECT-TYPE
    SYNTAX     IpAddress
    MAX-ACCESS read-only
    STATUS     current
    DESCRIPTION
            "The address of the IGMP Querier on the IP subnet to which
            this interface is attached."
::= { usrIgmpInterfaceEntry 5 }
usrIgmpInterfaceQueryMaxResponseTime OBJECT-TYPE
    SYNTAX     Integer32 (1..10)
    UNITS      "seconds"
    MAX-ACCESS read-create
    STATUS     current
    DESCRIPTION
            "The maximum query response time advertised in IGMPv2
            queries on this interface.  Smaller values allow a router to
            prune groups faster."
    DEFVAL     { 10 }
    --CONFIGURABLE                                                    
::= { usrIgmpInterfaceEntry 6 }
usrIgmpInterfaceVersion1QuerierTimer OBJECT-TYPE                            
    SYNTAX     Integer32                                                 
    MAX-ACCESS read-only                                                 
    STATUS     current                                                   
    DESCRIPTION                                                          
            "The time remaining until the host assumes that there are no 
            IGMPv1 routers present on the interface.  While this is      
            non-zero, the host will reply to all queries with version 1  
            membership reports."                                         
::= { usrIgmpInterfaceEntry 7 }                                         
usrIgmpInterfaceWrongVersionQueries OBJECT-TYPE                             
    SYNTAX     Counter32                                                 
    MAX-ACCESS read-only                                                 
    STATUS     current                                                   
    DESCRIPTION                                                          
            "The number of queries received whose IGMP version does not  
            match usrIgmpInterfaceVersion.   IGMP requires that all routers 
            on a LAN be configured to run the same version of IGMP.      
            Thus, if any queries are received with the wrong version,    
            this indicates a configuration error."                       
::= { usrIgmpInterfaceEntry 8 }                                        
usrIgmpInterfaceJoins OBJECT-TYPE                                           
    SYNTAX     Counter32                                                 
    MAX-ACCESS read-only                                                 
    STATUS     current                                                   
    DESCRIPTION                                                          
            "The number of times a group membership has been added on    
            this interface; that is, the number of times an entry for    
            this interface has been added to the Cache Table.  This      
            object gives an indication of the amount of IGMP activity    
            over time."                                                  
::= { usrIgmpInterfaceEntry 9 }                                        
usrIgmpInterfaceGroups OBJECT-TYPE
    SYNTAX     Gauge32
    MAX-ACCESS read-only
    STATUS     current
    DESCRIPTION
            "The current number of entries for this interface in the
            Cache Table."
    ::= { usrIgmpInterfaceEntry 10 }
usrIgmpInterfaceRobustness OBJECT-TYPE
    SYNTAX     Integer32 (1..5)
    MAX-ACCESS read-create
    STATUS     current
    DESCRIPTION
            "The Robustness Variable allows tuning for the expected
            packet loss on a subnet.  If a subnet is expected to be
            lossy, the Robustness Variable may be increased.  IGMP is
            robust to (Robustness Variable-1) packet losses."
    DEFVAL     { 2 }
    --CONFIGURABLE                                                    
    ::= { usrIgmpInterfaceEntry 11 }
usrIgmpInterfaceMcastFwdEnabled OBJECT-TYPE                                          
    SYNTAX     TruthValue                                                 
    MAX-ACCESS read-create                                                 
    STATUS     current                                                   
    DESCRIPTION
            "If enabled Multicast packets will be forwarded on this
             interface."   
    DEFVAL    { true }
    --CONFIGURABLE                                                        
::= { usrIgmpInterfaceEntry 12 }                                        
usrIgmpInterfacePushEnabled OBJECT-TYPE                                          
    SYNTAX     TruthValue                                                 
    MAX-ACCESS read-create                                                 
    STATUS     current                                                   
    DESCRIPTION 
            "If enabled once a Multicast group is learned on this interface  
             it will not be removed even if a report is not received within
             the membership interval." 
    DEFVAL    { false }
    --CONFIGURABLE                         
::= { usrIgmpInterfaceEntry 13 }                                        
usrIgmpInterfaceProxyEnabled OBJECT-TYPE                                          
    SYNTAX     TruthValue                                                 
    MAX-ACCESS read-create                                                 
    STATUS     current                                                   
    DESCRIPTION 
            "If enabled when a Multicast group is learned on this interface  
             it will also be joined as a proxy on the ethernet interface 
             specified in usrIgmpInterfaceProxyIfName."
    DEFVAL    { false }
    --CONFIGURABLE                         
::= { usrIgmpInterfaceEntry 14 }                                        
usrIgmpInterfaceShortPackets OBJECT-TYPE
    SYNTAX     Counter32
    MAX-ACCESS read-only
    STATUS     current
    DESCRIPTION
            "The number of short IGMP packets received on this interface."
::= { usrIgmpInterfaceEntry 15 }
usrIgmpInterfaceBadChecksum OBJECT-TYPE
    SYNTAX     Counter32
    MAX-ACCESS read-only
    STATUS     current
    DESCRIPTION
            "The number of IGMP packets with bad checksum received on 
             this interface."
::= { usrIgmpInterfaceEntry 16 }
usrIgmpInterfaceQueriesReceived OBJECT-TYPE
    SYNTAX     Counter32
    MAX-ACCESS read-only
    STATUS     current
    DESCRIPTION
            "The number of queries received on this interface."
::= { usrIgmpInterfaceEntry 17 }
usrIgmpInterfaceReportsReceived OBJECT-TYPE
    SYNTAX     Counter32
    MAX-ACCESS read-only
    STATUS     current
    DESCRIPTION
            "The number of reports received on this interface."
::= { usrIgmpInterfaceEntry 18 }
usrIgmpInterfaceReportsForKnownGroups OBJECT-TYPE
    SYNTAX     Counter32
    MAX-ACCESS read-only
    STATUS     current
    DESCRIPTION
            "The number of reports for known groups received on this 
             interface."
::= { usrIgmpInterfaceEntry 19 }
usrIgmpInterfaceReportsSent OBJECT-TYPE
    SYNTAX     Counter32
    MAX-ACCESS read-only
    STATUS     current
    DESCRIPTION
            "The number of reports sent on this interface."
::= { usrIgmpInterfaceEntry 20 }
usrIgmpInterfaceWrongVersionReports OBJECT-TYPE
    SYNTAX     Counter32
    MAX-ACCESS read-only
    STATUS     current
    DESCRIPTION
            "The number of wrong version reports received on this interface."
::= { usrIgmpInterfaceEntry 21 }
--
--  The IGMP Cache Table
--
usrIgmpCacheTable OBJECT-TYPE
    SYNTAX     SEQUENCE OF UsrIgmpCacheEntry
    MAX-ACCESS not-accessible
    STATUS     current
    DESCRIPTION
            "The (conceptual) table listing the IP multicast groups for
            which there are members on a particular interface."
::= { usrIgmp 2 }
usrIgmpCacheEntry OBJECT-TYPE
    SYNTAX     UsrIgmpCacheEntry
    MAX-ACCESS not-accessible
    STATUS     current
    DESCRIPTION
            "An entry (conceptual row) in the usrIgmpCacheTable."
    INDEX      { usrIgmpCacheAddress, usrIgmpCacheIfName }
::= { usrIgmpCacheTable 1 }
UsrIgmpCacheEntry ::= SEQUENCE {
    usrIgmpCacheAddress            IpAddress,
    usrIgmpCacheIfName             DisplayString,
    usrIgmpCacheSelf               Integer32,
    usrIgmpCacheLastReporter       IpAddress,
    usrIgmpCacheUpTime             TimeTicks,
    usrIgmpCacheExpiryTime         TimeTicks,
    usrIgmpCacheStatus             RowStatus,
    usrIgmpCacheVersion1HostTimer  Integer32                                
}
usrIgmpCacheAddress OBJECT-TYPE
    SYNTAX     IpAddress
    MAX-ACCESS not-accessible
    STATUS     current
    DESCRIPTION
            "The IP multicast group address for which this entry
            contains information."
::= { usrIgmpCacheEntry 1 }
usrIgmpCacheIfName OBJECT-TYPE
    SYNTAX     DisplayString (SIZE (1..32))
    MAX-ACCESS not-accessible
    STATUS     current
    DESCRIPTION
            "The interface name for which this entry contains 
            information for an IP multicast group address."
::= { usrIgmpCacheEntry 2 }
usrIgmpCacheSelf OBJECT-TYPE
    SYNTAX     Integer32
    MAX-ACCESS read-create
    STATUS     current
    DESCRIPTION
            "An indication of whether the local system is a member of
            or proxying this group address on this interface."
::= { usrIgmpCacheEntry 3 }
usrIgmpCacheLastReporter OBJECT-TYPE
    SYNTAX     IpAddress
    MAX-ACCESS read-only
    STATUS     current
    DESCRIPTION
            "The IP address of the source of the last membership report
            received for this IP Multicast group address on this
            interface.  If no membership report has been received, this
            object has the value 0.0.0.0."
::= { usrIgmpCacheEntry 4 }
usrIgmpCacheUpTime OBJECT-TYPE
    SYNTAX     TimeTicks
    MAX-ACCESS read-only
    STATUS     current
    DESCRIPTION
            "The time since the system joined this group address, or
            zero if the system is not currently a member."
::= { usrIgmpCacheEntry 5 }
usrIgmpCacheExpiryTime OBJECT-TYPE
    SYNTAX     TimeTicks
    MAX-ACCESS read-only
    STATUS     current
    DESCRIPTION
            "The minimum amount of time remaining before this entry will
            be aged out."
::= { usrIgmpCacheEntry 6 }
usrIgmpCacheStatus OBJECT-TYPE
    SYNTAX     RowStatus
    MAX-ACCESS read-create
    STATUS     current
    DESCRIPTION
            "The status of this entry."
    --CONFIGURABLE                                                        
::= { usrIgmpCacheEntry 7 }
usrIgmpCacheVersion1HostTimer OBJECT-TYPE                                   
    SYNTAX     Integer32
    UNITS      "seconds"
    MAX-ACCESS read-only
    STATUS     current
    DESCRIPTION
            "The time remaining until the local router will assume that
            there are no longer any IGMP version 1 members on the IP     
            subnet attached to this interface.  Upon hearing any IGMPv1
            Membership Report, this value is reset to the group
            membership timer.  While this time remaining is non-zero,
            the local router ignores any IGMPv2 Leave messages for this  
            group that it receives on this interface."                   
::= { usrIgmpCacheEntry 8 }
usrIgmpProxyInterface OBJECT-TYPE
    SYNTAX     UsrDisplayString (SIZE (1..32))
    MAX-ACCESS read-create                                                 
    STATUS     current                                                   
    DESCRIPTION 
            "The name of the interface on which all groups learned 
             on the wan connections will be proxied onto if 
             usrIgmpInterfaceProxyEnabled is enabled."
    --CONFIGURABLE                         
::= { usrIgmp 3 }
usrIgmpHeartbeatGroup OBJECT IDENTIFIER ::= { usrIgmp 4 }
usrIgmpHeartbeatInterface OBJECT-TYPE
    SYNTAX     UsrDisplayString (SIZE (1..32))
    MAX-ACCESS read-write                                                 
    STATUS     current                                                   
    DESCRIPTION 
            "The name of the interface on which to monitor
             multicast traffic for group specified in
             usrIgmpHeartbeatGroupAddr."
    --CONFIGURABLE                         
::= { usrIgmpHeartbeatGroup 1 }
usrIgmpHeartbeatGroupAddr OBJECT-TYPE
    SYNTAX     IpAddress
    MAX-ACCESS read-write
    STATUS     current
    DESCRIPTION
            "The multicast group being monitored."
    --CONFIGURABLE                         
::= { usrIgmpHeartbeatGroup 2 }
usrIgmpHeartbeatTime OBJECT-TYPE                                   
    SYNTAX     Integer32 (0..65535)
    UNITS      "seconds"
    MAX-ACCESS read-write
    STATUS     current
    DESCRIPTION
            "The time interval to monitor multicast traffic."
    DEFVAL     { 60 }
    --CONFIGURABLE                                                    
::= { usrIgmpHeartbeatGroup 3 }
usrIgmpHeartbeatWindow OBJECT-TYPE
    SYNTAX     Integer32 (0..255)
    MAX-ACCESS read-write
    STATUS     current
    DESCRIPTION
            "The number of usrIgmpHeartbeatTime intervals to monitor 
             multicast traffic on."
    DEFVAL     { 5 }
    --CONFIGURABLE                                                    
::= { usrIgmpHeartbeatGroup 4 }
usrIgmpHeartbeatThreshold OBJECT-TYPE
    SYNTAX     Integer32 (0..65535)
    MAX-ACCESS read-write
    STATUS     current
    DESCRIPTION
            "If multicast traffic in not received for this number or 
             more intervals a SNMP trap is issued."
    DEFVAL     { 3 }
    --CONFIGURABLE                                                    
::= { usrIgmpHeartbeatGroup 5 }
usrIgmpHeartbeatStatus OBJECT-TYPE
   SYNTAX      INTEGER {
                enabled(1),
                disabled(2),
                delete(3)
                }
   MAX-ACCESS  read-write
   STATUS      current
   DESCRIPTION
           "This object is used to allow the system to start or
            or stop the IGMP heartbeat feature.  This heartbeat
            feature is used to monitor multicast traffic for a 
            particular multicast group (usrIgmpHeartbeatGroupAddr)
            on a specified interface (usrIgmpHeartbeatInterface).  
            Traffic is monitored on this interface for 
            usrIgmpHeartbeatWindowSize usrIgmpHeartbeatTime intervals.
            During each time interval it is determined if multicast
            traffic was received.  After usrIgmpHeartbeatWindowSize
            time intervals the number of times we did NOT receive 
            traffic is compared against usrIgmpHeartbeatThreshold. If
            the number of intervals we did NOT receive traffic is 
            equal to or higher than usrIgmpHeartbeatThreshold a SNMP 
            trap is issued." 
    --CONFIGURABLE                                                    
::= { usrIgmpHeartbeatGroup 6 }
usrIgmpTraps OBJECT IDENTIFIER ::= { usrIgmp 5 }
usrIgmpTrapsV2 OBJECT-IDENTITY
   STATUS       current
   DESCRIPTION
           " The events for IGMP"
::= { usrIgmpTraps 0 }
usrIgmpHeartbeatTrap NOTIFICATION-TYPE
   OBJECTS { usrIgmpHeartbeatThreshold }
   STATUS       current
   DESCRIPTION
	   "A usrIgmpHeartbeatTrap signifies that the configured 
        number of time intervals have occurred without receiving 
        multicast traffic for the configured group."
    --#TYPE     "Warning"
    --#SUMMARY  "IGMP Heartbeat Threshold %d Reached"
    --#ARGUMENTS { 0 }
    --#SEVERITY MINOR
    --#STATE    OPERATIONAL
    --#PROBABLECAUSE "Network Error"
::= { usrIgmpTrapsV2 1 }
usrIgmpTrafficAffectInactivity OBJECT-TYPE
   SYNTAX      INTEGER {
                enabled(1),
                disabled(2)
                }
   MAX-ACCESS  read-write
   STATUS      current
   DESCRIPTION
           "This object is used to allow the system to treat IGMP traffic 
	    over PPP links as background traffic. If this switch is enabled 
	    then IGMP traffic will be treated as background traffic and idle 
	    timeout functionality will ignore this traffic. If this switch 
	    is disabled the IGMP multicast traffic will be treated as regular
	    traffic and connection will not be dropped." 
    --CONFIGURABLE                                                    
::= { usrIgmp 6 }
END         -- End of USR-IGMP-MIB DEFINITIONS
-- ************************************************************************
--
--     usr_mpip.mib
--
--	Description:	This module contains MIB definitions for the 
--      		MPIP Process
--
--	Author:	Balaji Tamirisa
--
USR-MPIP-MIB DEFINITIONS ::= BEGIN
          IMPORTS
                OBJECT-TYPE, MODULE-IDENTITY,
                IpAddress, Integer32
                    FROM SNMPv2-SMI
                RowStatus
                    FROM SNMPv2-TC
                UsrDisplayString, common, UsrConfigStatus
                    FROM USR-DEFINITIONS-MIB;
usrMPIP MODULE-IDENTITY
        LAST-UPDATED "200205051610Z"
        ORGANIZATION "CommWorks Corporation, a 3Com Company"
        CONTACT-INFO "Customer Support"
        DESCRIPTION
                "The commWorks enterprise defined MIB objects
                  for MPIP."
--      REVISION "200105051610Z"
--      DESCRIPTION "Converted to SNMPv2"
        ::= { common 54 }
          usrMPIPBase      OBJECT IDENTIFIER ::= { usrMPIP 1 }
--
-- The MPIP Base Group.
--
usrMPIPBaseCfgFileName OBJECT-TYPE
    SYNTAX       UsrDisplayString
    MAX-ACCESS   read-only
    STATUS       current
    DESCRIPTION
            "The name of a ConfigFile to read/write
            permanent database records. If the value of this
            object is an empty string, then the PPP process
            uses the default name `@file://MPIPProcess.cfg'."
::= { usrMPIPBase 1 }
usrMPIPBaseCFMSaveStatus OBJECT-TYPE
    SYNTAX  UsrConfigStatus
    MAX-ACCESS  read-write
    STATUS      current
    DESCRIPTION
            "Setting the value of this object to `save'
            causes the values of the MPIP Base Group
            entries to be written out to the current MPIP
            config file. While the new config file is being
            written, the MPIP process will set the value
            of this flag set to `saving''. Any attempts to set
            the value while it is  not `normal' (i.e. the file
            is currently being written to the config file)
            while result in a badValue error being returned.
            Setting the value to `normal' will result in no
            action."
::= { usrMPIPBase 2 }
usrMPIPServerStatus OBJECT-TYPE
    SYNTAX  INTEGER {
                    on(1),
                    off(0)
                    }
    MAX-ACCESS   read-write
    STATUS       current
    DESCRIPTION
            "Indicates whether MPIP server is turned off or on."
    DEFVAL { 0 }
    --CONFIGURABLE
::= { usrMPIPBase 3 }
usrMPIPClientStatus OBJECT-TYPE
    SYNTAX  INTEGER {
                    turned-on(1),
                    turned-off(0)
                    }
    MAX-ACCESS   read-write
    STATUS       current
    DESCRIPTION
            "Indicates whether MPIP Client is turned off or on."
    DEFVAL { 0 }
    --CONFIGURABLE
::= { usrMPIPBase 4 }
usrMPIPUDPPort OBJECT-TYPE
    SYNTAX        Integer32
    MAX-ACCESS    read-write
    STATUS        current
    DESCRIPTION
            "Indicates the UDP Port used by MPIP process\n"
    DEFVAL { 5912 }
    --CONFIGURABLE
::= { usrMPIPBase 5 }
usrMPIPGlobalSharedSecret OBJECT-TYPE
    SYNTAX   OCTET STRING (SIZE(16))
    MAX-ACCESS   read-write
    STATUS       current
    DESCRIPTION
            "Indicates the shared secret for auto-configuration.
             Reading this from SNMP returns NULL."
    --CONFIGURABLE
::= { usrMPIPBase 6 }
--
-- The Client Entry Table.
--
-- The following object reflect the Entries in the
-- MPIP Client Entry Table
--   usrMPIPClientIpaddr
--   usrMPIPSharedSecret
usrMPIPClientEntryTable   OBJECT-TYPE
     SYNTAX    SEQUENCE OF UsrMPIPClientEntry
     MAX-ACCESS    not-accessible
     STATUS        current
     DESCRIPTION
     "Table containing the MPIP client IP addresses
       and shared secrets."
::= { usrMPIPBase 7 }
    usrMPIPClientEntry   OBJECT-TYPE
        SYNTAX    UsrMPIPClientEntry
        MAX-ACCESS    not-accessible
        STATUS        current
        DESCRIPTION
               "Each entry in the Client Entry Table."
        INDEX     { usrMPIPClientIpaddr }
    ::= { usrMPIPClientEntryTable 1 }
          UsrMPIPClientEntry ::= SEQUENCE {
                        usrMPIPClientIpaddr         IpAddress,
                        usrMPIPClientSharedSecret   OCTET STRING,
                        usrMpipcStatus              RowStatus,
                        usrMPIPClientType           INTEGER,
                        usrMPIPClientEntryType      OCTET STRING
                        }
usrMPIPClientIpaddr OBJECT-TYPE
     SYNTAX    IpAddress
     MAX-ACCESS     not-accessible 
     STATUS         current
     DESCRIPTION
               "The unique identifier of the MPIP Client."
::= { usrMPIPClientEntry 1 }
usrMPIPClientSharedSecret OBJECT-TYPE
     SYNTAX  OCTET STRING (SIZE(16))
     MAX-ACCESS    read-write
     STATUS        current
     DESCRIPTION
               "The Shared secret between MPIP Client and Server.
                Reading this from SNMP returns NULL."
     --CONFIGURABLE
::= { usrMPIPClientEntry 2 }
usrMpipcStatus OBJECT-TYPE
     SYNTAX     RowStatus
     MAX-ACCESS read-write
     STATUS     current
     DESCRIPTION
               "The status of this row of the MPIP 
                Client Table." 
     --CONFIGURABLE
::= { usrMPIPClientEntry 3 }
usrMPIPClientType    OBJECT-TYPE
     SYNTAX        INTEGER {
                            hiper(0),
                            netserver(1)
                            }
     MAX-ACCESS        read-write
     STATUS            current
     DESCRIPTION
              "Tells whether the client is a HiperARC or Netserver"
     --CONFIGURABLE
::= { usrMPIPClientEntry 4 }
usrMPIPClientEntryType OBJECT-TYPE
     SYNTAX  OCTET STRING (SIZE(0..10))
     MAX-ACCESS    read-only
     STATUS        current
     DESCRIPTION
               "Is the client added dynamically or statically?"
::= { usrMPIPClientEntry 5 }
--
-- The Server Entry Table.
--
--  The following object reflect the Entries in the
--  MPIP Server Entry Table
--  usrMPIPServerIpaddr
--  usrMPIPServerPortNum
--  usrMPIPServerSharedSecret
--  usrMPIPCurrentState
--  usrMPIPSendSequenceNum
--  usrMPIPExpectedSequenceNum 
--  usrMPIPLastExpectedSequenceNum
--  usrMPIPSentTime
--  usrMPIPIdentification
--  usrMPIPRetransmit
usrMPIPServerEntryTable   OBJECT-TYPE
     SYNTAX    SEQUENCE OF UsrMPIPServerEntry
     MAX-ACCESS    not-accessible
     STATUS        current
     DESCRIPTION
               "Table containing the MPIP server IP addresse,
                 UDP port number, shared secret, current state,
                 send sequence number, expected sequence number,
                 last expected sequence number, MPIP sent time,
                 MPIP ID and MPIP retransmit."
     ::= { usrMPIPBase 8 }
    usrMPIPServerEntry   OBJECT-TYPE
         SYNTAX    UsrMPIPServerEntry
         MAX-ACCESS    not-accessible
         STATUS        current
         DESCRIPTION
               "Each entry in the Server Entry Table."
         INDEX     { usrMPIPServerIpaddr }
    ::= { usrMPIPServerEntryTable 1 }
UsrMPIPServerEntry ::= SEQUENCE {
                usrMPIPServerIpaddr         IpAddress,
                usrMPIPServerPortNum        Integer32,
                usrMPIPServerSharedSecret   OCTET STRING,
                usrMPIPServerPreference     Integer32,
                usrMpipsStatus              RowStatus,
                usrMPIPServerEntryType      OCTET STRING
           }
usrMPIPServerIpaddr OBJECT-TYPE
     SYNTAX    IpAddress
     MAX-ACCESS    not-accessible
     STATUS         current
     DESCRIPTION
               "The unique identifier of the MPIP Server."
::= { usrMPIPServerEntry 1 }
usrMPIPServerPortNum OBJECT-TYPE
     SYNTAX        Integer32
     MAX-ACCESS    read-write
     STATUS        current
     DESCRIPTION
               "The Server UDP Port Number."
     --CONFIGURABLE
::= { usrMPIPServerEntry 2 }
usrMPIPServerSharedSecret OBJECT-TYPE
    SYNTAX  OCTET STRING (SIZE(16))
    MAX-ACCESS    read-write
    STATUS        current
    DESCRIPTION
              "The Server's Shared secret with Client."
    --CONFIGURABLE
::= { usrMPIPServerEntry 3 }
usrMPIPServerPreference OBJECT-TYPE
    SYNTAX        Integer32
    MAX-ACCESS    read-write
    STATUS        current
    DESCRIPTION
              "The Server Priority."
    --CONFIGURABLE
::= { usrMPIPServerEntry 4 }
usrMpipsStatus OBJECT-TYPE
    SYNTAX    RowStatus
    MAX-ACCESS    read-write
    STATUS        current
    DESCRIPTION
              "Row status."
    --CONFIGURABLE
::= { usrMPIPServerEntry 5 }
usrMPIPServerEntryType OBJECT-TYPE
     SYNTAX  OCTET STRING (SIZE(0..10))
     MAX-ACCESS    read-only
     STATUS        current
     DESCRIPTION
               "Is the server added dynamically or statically?"
::= { usrMPIPServerEntry 6 }
--
-- The Bundle Table 
--
--  The following object reflect the Entries in the
--  MPIP Bundle Index
--  MPIP Bundle Table 
--  usrMPIPBundleEdoType
--  usrMPIPBundleEdoValue
--  usrMPIPBundleUsername
--  usrMPIPBundleCount
usrMPIPBundleTable   OBJECT-TYPE
     SYNTAX    SEQUENCE OF UsrMPIPBundleEntry
     MAX-ACCESS    not-accessible
     STATUS        current
     DESCRIPTION
               "Table containing the MPIP Bundle & links."
::= { usrMPIPBase 9 }
    usrMPIPBundleEntry   OBJECT-TYPE
         SYNTAX    UsrMPIPBundleEntry
         MAX-ACCESS    not-accessible
         STATUS        current
         DESCRIPTION
               "Each entry in the Bundle Table." 
         INDEX     { usrMPIPBundleIndex }
    ::= { usrMPIPBundleTable 1 }
    UsrMPIPBundleEntry ::= SEQUENCE {
                usrMPIPBundleIndex        Integer32,
                usrMPIPBundleUsername     OCTET STRING,
                usrMPIPBundleEdoType      Integer32,
                usrMPIPBundleEdoValue     OCTET STRING,
                usrMPIPBundleOwner        IpAddress,
                usrMPIPNumOfLinks         Integer32
           }
usrMPIPBundleIndex OBJECT-TYPE
    SYNTAX        Integer32
    MAX-ACCESS    read-write 
    STATUS        current
    DESCRIPTION
              "The bundle index number "
::= { usrMPIPBundleEntry 1 }
usrMPIPBundleUsername OBJECT-TYPE
    SYNTAX    OCTET STRING (SIZE(64))
    MAX-ACCESS    read-write 
    STATUS        current
    DESCRIPTION
              "User name." 
::= { usrMPIPBundleEntry 2 }
usrMPIPBundleEdoType OBJECT-TYPE
    SYNTAX    Integer32
    MAX-ACCESS    read-write 
    STATUS        current
    DESCRIPTION
              "The EDO type." 
    --CONFIGURABLE
::= { usrMPIPBundleEntry 3 }
usrMPIPBundleEdoValue OBJECT-TYPE
    SYNTAX    OCTET STRING (SIZE(20))
    MAX-ACCESS    read-write 
    STATUS        current
    DESCRIPTION
              "The EDO value." 
    --CONFIGURABLE
::= { usrMPIPBundleEntry 4 }
usrMPIPBundleOwner OBJECT-TYPE
    SYNTAX    IpAddress 
    MAX-ACCESS    read-write
    STATUS        current
    DESCRIPTION
              "Bundle Owner."
::= { usrMPIPBundleEntry 5 }
usrMPIPNumOfLinks OBJECT-TYPE
    SYNTAX        Integer32
    MAX-ACCESS    read-write
    STATUS        current
    DESCRIPTION
              "The number of links per bundle." 
    --CONFIGURABLE
::= { usrMPIPBundleEntry 6 }
--
-- The Link Table
--
--  The following object reflect the Entries in the
--  MPIP Link Table
--  usrMPIPLinkOwner
--  usrMPIPBundleOwner
--  usrMPIPLinkIdentifier
--  usrMPIPLinkBundleUsername
--  usrMPIPLinkStatus
usrMPIPLinkTable   OBJECT-TYPE
     SYNTAX    SEQUENCE OF UsrMPIPLinkEntry
     MAX-ACCESS    not-accessible
     STATUS        current
     DESCRIPTION
               "Table containing the MPIP Bundle & links."
::= { usrMPIPBase 10 }
    usrMPIPLinkEntry   OBJECT-TYPE
         SYNTAX    UsrMPIPLinkEntry
         MAX-ACCESS    not-accessible
         STATUS        current
         DESCRIPTION 
               "Each entry in the Bundle Table."
         INDEX     { usrMPIPBundleUsername }
    ::= { usrMPIPLinkTable 1 }
          UsrMPIPLinkEntry ::= SEQUENCE {
                    usrMPIPLinkNum              Integer32,
                    usrMPIPLinkBundleOwner      IpAddress, 
                    usrMPIPLinkOwner            IpAddress, 
                    usrMPIPLinkIdentifier       Integer32,
                    usrMPIPLinkBundleUsername   OCTET STRING,
                    usrMpipLinkStatus           RowStatus
           }
usrMPIPLinkNum OBJECT-TYPE
    SYNTAX        Integer32
    MAX-ACCESS    read-write
    STATUS        current
    DESCRIPTION
              "Link Identifier."
::= { usrMPIPLinkEntry 1 }
usrMPIPLinkBundleOwner OBJECT-TYPE
    SYNTAX    IpAddress 
    MAX-ACCESS    read-write
    STATUS        current
    DESCRIPTION
              "Bundle Owner."
::= { usrMPIPLinkEntry 2 }
usrMPIPLinkOwner OBJECT-TYPE
    SYNTAX    IpAddress 
    MAX-ACCESS    read-write
    STATUS        current
    DESCRIPTION
              "Link Owner."
    --CONFIGURABLE
::= { usrMPIPLinkEntry 3 }
usrMPIPLinkIdentifier OBJECT-TYPE
    SYNTAX        Integer32
    MAX-ACCESS    read-write
    STATUS        current
    DESCRIPTION
              "Link Identifier."
    --CONFIGURABLE
::= { usrMPIPLinkEntry 4 }  
usrMPIPLinkBundleUsername OBJECT-TYPE
    SYNTAX    OCTET STRING (SIZE(64))
    MAX-ACCESS    read-write
    STATUS        current
    DESCRIPTION
              "The EDO type."
    --CONFIGURABLE
::= { usrMPIPLinkEntry 5 }
usrMpipLinkStatus OBJECT-TYPE
    SYNTAX      RowStatus
    MAX-ACCESS  read-write
    STATUS      current
    DESCRIPTION
              "The status of this row of the Link Table."
    --CONFIGURABLE
::= { usrMPIPLinkEntry 6 }
--
--
usrMPIPLocalLinkTable   OBJECT-TYPE
     SYNTAX    SEQUENCE OF UsrMPIPLocalLinkEntry
     MAX-ACCESS    not-accessible
     STATUS        current
     DESCRIPTION
               "Table containing the MPIP local links."
     ::= { usrMPIPBase 11 }
    usrMPIPLocalLinkEntry   OBJECT-TYPE
         SYNTAX    UsrMPIPLocalLinkEntry
         MAX-ACCESS    not-accessible
         STATUS        current
         DESCRIPTION 
               "Each entry in the Bundle Table."
         INDEX     { usrMPIPLocalLinkUsername }
    ::= { usrMPIPLocalLinkTable 1 }
        UsrMPIPLocalLinkEntry ::= SEQUENCE {
                  usrMPIPLocalLinkCount         Integer32,
                  usrMPIPLocalLinkBundleOwner   IpAddress, 
                  usrMPIPLocalLinkUsername      OCTET STRING
           }
usrMPIPLocalLinkCount OBJECT-TYPE
    SYNTAX        Integer32
    MAX-ACCESS    read-only
    STATUS        current
    DESCRIPTION
            "Link Count."
    --CONFIGURABLE
::= { usrMPIPLocalLinkEntry 1 }  
usrMPIPLocalLinkBundleOwner OBJECT-TYPE
    SYNTAX    IpAddress 
    MAX-ACCESS    read-only
    STATUS        current
    DESCRIPTION
              "Bundle Owner."
::= { usrMPIPLocalLinkEntry 2 }
usrMPIPLocalLinkUsername OBJECT-TYPE
    SYNTAX    OCTET STRING (SIZE(64))
    MAX-ACCESS    read-only
    STATUS        current
    DESCRIPTION
              "The user name."
    --CONFIGURABLE
::= { usrMPIPLocalLinkEntry 3 }
usrMPIPACEStatus OBJECT-TYPE
    SYNTAX  INTEGER {
                     on(1),
                     off(0)
                    }
    MAX-ACCESS   read-write
    STATUS       current
    DESCRIPTION
            "Indicates whether MPIP ACE_AUTH is turned off or on."
    DEFVAL { 0 }
    --CONFIGURABLE
::= { usrMPIPBase 12 }
END     -- End of USR-MPIP-MIB DEFINITIONS
-- ************************************************************************
--
--
--	usr_dns.mib - An enterprise specific MIB file 
--                    for the Domain Name Service
--
-- Author:         Clarise E. Patton
--
USR-DNS-MIB DEFINITIONS ::= BEGIN
	IMPORTS
    	  RowStatus, DisplayString
                FROM SNMPv2-TC
          OBJECT-TYPE, MODULE-IDENTITY, 
          Integer32, Counter32, IpAddress
                FROM SNMPv2-SMI
          UsrDisplayString, UsrConfigStatus, common
                FROM USR-DEFINITIONS-MIB
          DnsName, DnsClass, DnsType, DnsQClass, DnsQType, DnsTime
                FROM DNS-SERVER-MIB;
usrDns   MODULE-IDENTITY
         LAST-UPDATED "200209061420Z"
         ORGANIZATION "CommWorks Corporation, a 3Com Company"
         CONTACT-INFO "Customer Support"
         DESCRIPTION
                 "The commWorks enterprise defined MIB objects
                  for the Domain Name Service functionality."
--       REVISION "200209061420Z"
--       DESCRIPTION "Clarify usage of usrDnsTimeout."
--       REVISION "200204061300Z"
--       DESCRIPTION "Correct SNMPv2 conversion."
::= { common 17 }
   -- Begin managed object definitions here...
usrDnsVersion OBJECT-TYPE
	SYNTAX		DisplayString
	MAX-ACCESS	read-only
	STATUS		current
	DESCRIPTION
		"The current software version of the Domain Name Server."
::= { usrDns 1 }
usrDnsCFMStatusFlag OBJECT-TYPE
	SYNTAX		UsrConfigStatus
	MAX-ACCESS	read-write
	STATUS		current
	DESCRIPTION
	"This variable controls saving and loading of all the configuration
           information for the Domain Name Service. The value can 
           be set to either save or load by a management station. The other
           values indicate if any configuration operation and what type
           is in progress."
::= { usrDns 2 }
usrDnsCfgFileName OBJECT-TYPE
	SYNTAX      UsrDisplayString
	MAX-ACCESS  read-only
	STATUS      current
	DESCRIPTION		
		"The name of a ConfigFile to read/write  permanent database records.
		 If the value of this object is an empty string, then the
		 DNS module uses the default name `@file://DNS.cfg'. "
	--CONFIGURABLE
::= { usrDns 3 }
usrDnsDomainName OBJECT-TYPE
	SYNTAX      DisplayString
	MAX-ACCESS  read-write
	STATUS      current
	DESCRIPTION		
		"The default Domain Name to be appended to a Host Name if
           it cannot be resolved without a Domain Name."
	--CONFIGURABLE
::= { usrDns 4 }
usrDnsNumberRetries OBJECT-TYPE
     SYNTAX   Integer32 (1..5)
     MAX-ACCESS   read-write
     STATUS   current
     DESCRIPTION
            "The number of times DNS will attempt to resolve a name before
             determining it cannot be resolved."
	--CONFIGURABLE
::= { usrDns 5 }
usrDnsTimeout OBJECT-TYPE
     SYNTAX   Integer32 (5..245)
     MAX-ACCESS   read-write
     STATUS   current
     DESCRIPTION
            "The number of seconds DNS will wait for a response from
             a name server before determining it is not coming.
             The minimum timeout value is 5 seconds.
             The maximum timeout value is twice the Internet MSL
             (Maximum Segment Lifetime) + the minimum = 245 secs."
     REFERENCE
             "RFC-1122 section 3.3"
	--CONFIGURABLE
::= { usrDns 6 }
usrDnsQueries OBJECT-TYPE
     SYNTAX   Counter32
     MAX-ACCESS   read-only
     STATUS   current
     DESCRIPTION
            "The total number of queries received by DNS"
::= { usrDns 7 }
usrDnsTotalResponses OBJECT-TYPE
     SYNTAX   Counter32
     MAX-ACCESS   read-only
     STATUS   current
     DESCRIPTION
            "The total number of responses sent by DNS"
::= { usrDns 8 }
usrDnsResponseOK OBJECT-TYPE
     SYNTAX   Counter32
     MAX-ACCESS   read-only
     STATUS   current
     DESCRIPTION
            "The number of success responses received by DNS"
::= { usrDns 9 }
usrDnsResponseFormat OBJECT-TYPE
     SYNTAX   Counter32
     MAX-ACCESS   read-only
     STATUS   current
     DESCRIPTION
            "The number of Format Error responses received by DNS"
::= { usrDns 10 }
usrDnsResponseServer OBJECT-TYPE
     SYNTAX   Counter32
     MAX-ACCESS   read-only
     STATUS   current
     DESCRIPTION
            "The number of Server Error responses received by DNS"
::= { usrDns 11 }
usrDnsResponseName OBJECT-TYPE
     SYNTAX   Counter32
     MAX-ACCESS   read-only
     STATUS   current
     DESCRIPTION
            "The number of No Such Name responses received by DNS"
::= { usrDns 12 }
usrDnsResponseNIY OBJECT-TYPE
     SYNTAX   Counter32
     MAX-ACCESS   read-only
     STATUS   current
     DESCRIPTION
            "The number of NIY responses sent by DNS.
	This indicates that the Server does not implement this operation"
::= { usrDns 13 }
usrDnsResponseRefused OBJECT-TYPE
     SYNTAX   Counter32
     MAX-ACCESS   read-only
     STATUS   current
     DESCRIPTION
            "The number of Refused responses sent by DNS.
	This indicates the Server refuses to perform the operation."
::= { usrDns 14 }
usrDnsResponsesLocal OBJECT-TYPE
     SYNTAX   Counter32
     MAX-ACCESS   read-only
     STATUS   current
     DESCRIPTION
            "The number of responses answered Locally by DNS"
::= { usrDns 15 }
usrDnsResponsesRemote OBJECT-TYPE
     SYNTAX   Counter32
     MAX-ACCESS   read-only
     STATUS   current
     DESCRIPTION
            "The number of responses received by DNS"
::= { usrDns 16 }
usrDnsResponseBadProt OBJECT-TYPE
     SYNTAX   Counter32
     MAX-ACCESS   read-only
     STATUS   current
     DESCRIPTION
            "The number of corrupted responses received by DNS"
::= { usrDns 17 }
usrDnsTimeOuts OBJECT-TYPE
     SYNTAX   Counter32
     MAX-ACCESS   read-only
     STATUS   current
     DESCRIPTION
            "The total number of timeouts on requests sent by DNS"
::= { usrDns 18 }
usrDnsResponseNotSent OBJECT-TYPE
     SYNTAX   Counter32
     MAX-ACCESS   read-only
     STATUS   current
     DESCRIPTION
            "The number of send failures on replies sent by DNS"
::= { usrDns 19 }
usrDnsErrorResponse OBJECT-TYPE
     SYNTAX   Counter32
     MAX-ACCESS   read-only
     STATUS   current
     DESCRIPTION
            "The number of failure  replies sent by DNS"
::= { usrDns 20 }
usrDnsHostTable OBJECT-TYPE
	SYNTAX SEQUENCE OF UsrDnsHostEntry
	MAX-ACCESS not-accessible
	STATUS current
	DESCRIPTION
		"The table of DNS Hosts. "
::= { usrDns 21 }
usrDnsHostEntry OBJECT-TYPE
	SYNTAX UsrDnsHostEntry
	MAX-ACCESS not-accessible
	STATUS current
	DESCRIPTION
		"A (conceptual) entry for one Dns Host."
	INDEX { usrDnsHostName }
::= { usrDnsHostTable 1 }
UsrDnsHostEntry ::= SEQUENCE {
	usrDnsHostName			DisplayString,
	usrDnsHostAddress		IpAddress,
	usrDnsHostStatus     	        RowStatus
	}
usrDnsHostName OBJECT-TYPE
	SYNTAX		DisplayString
	MAX-ACCESS		not-accessible
	STATUS		current
	DESCRIPTION
		"The logical identifier of the Host Table. "
::= { usrDnsHostEntry 1 }
usrDnsHostAddress OBJECT-TYPE
	SYNTAX		IpAddress
	MAX-ACCESS		read-write
	STATUS		current
	DESCRIPTION
		"The specified or resolved ip address of the named Host. "
	--CONFIGURABLE
::= { usrDnsHostEntry 2 }
usrDnsHostStatus OBJECT-TYPE
	SYNTAX		RowStatus
	MAX-ACCESS		read-write
	STATUS		current
	DESCRIPTION
		"The status of this row of the Host Table. "
	--CONFIGURABLE
::= { usrDnsHostEntry 3 }
usrDnsServerTable OBJECT-TYPE
	SYNTAX SEQUENCE OF UsrDnsServerEntry
	MAX-ACCESS not-accessible
	STATUS current
	DESCRIPTION
		"The table of DNS Servers. "
::= { usrDns 22 }
usrDnsServerEntry OBJECT-TYPE
	SYNTAX UsrDnsServerEntry
	MAX-ACCESS not-accessible
	STATUS current
	DESCRIPTION
		"A (conceptual) entry for one Dns Server."
	INDEX { usrDnsServerPreference }
::= { usrDnsServerTable 1 }
UsrDnsServerEntry ::= SEQUENCE {
	usrDnsServerPreference		Integer32,
	usrDnsServerName		DisplayString,
	usrDnsServerAddress		IpAddress,
	usrDnsServerStatus     	        RowStatus
	}
usrDnsServerPreference OBJECT-TYPE
	SYNTAX		Integer32
	MAX-ACCESS		not-accessible
	STATUS		current
	DESCRIPTION
		"The logical identifier of the Server Table. "
::= { usrDnsServerEntry 1 }
usrDnsServerName OBJECT-TYPE
	SYNTAX		DisplayString
	MAX-ACCESS		read-write
	STATUS		current
	DESCRIPTION
		"The specified name of the Server. "
	--CONFIGURABLE
::= { usrDnsServerEntry 2 }
usrDnsServerAddress OBJECT-TYPE
	SYNTAX		IpAddress
	MAX-ACCESS		read-write
	STATUS		current
	DESCRIPTION
		"The specified or resolved ip address of the named Server. "
	--CONFIGURABLE
::= { usrDnsServerEntry 3 }
usrDnsServerStatus OBJECT-TYPE
	SYNTAX		RowStatus
	MAX-ACCESS		read-write
	STATUS		current
	DESCRIPTION
		"The status of this row of the Server Table. "
	--CONFIGURABLE
::= { usrDnsServerEntry 4 }
usrDnsHostRotation OBJECT-TYPE
     SYNTAX   INTEGER { enabled(1), disabled(2) }
     MAX-ACCESS   read-write
     STATUS   current
     DESCRIPTION
            "Setting this object to a value of enabled(1) will enable
             the DNS host rotation feature. Setting this object to
             disabled(2) will disable the DNS Host Rotation feature."
     --CONFIGURABLE
::= { usrDns 23 }
-- Resolver Cache Table
usrDnsCacheTable OBJECT-TYPE
    SYNTAX      SEQUENCE OF UsrDnsCacheEntry
    MAX-ACCESS  not-accessible
    STATUS      current
    DESCRIPTION
           "This table contains information about all the resource
           records currently in the resolver's cache."
::= { usrDns 24 }
usrDnsRoundRobin OBJECT-TYPE
     SYNTAX   INTEGER { enabled(1), disabled(2) }
     MAX-ACCESS   read-write
     STATUS   current
     DESCRIPTION
            "Setting this object to a value of enabled(1) will enable
             the DNS round robin feature. Setting this object to
             disabled(2) will set the DNS into random."
     --CONFIGURABLE
::= { usrDns 26 }
usrDnsCacheEntry OBJECT-TYPE
    SYNTAX      UsrDnsCacheEntry
    MAX-ACCESS  not-accessible
    STATUS      current
    DESCRIPTION
           "An entry in the resolver's cache.  Rows may be created
           only by the resolver.  SNMP SET requests may be used to
           delete rows."
    INDEX     { usrDnsCacheRRIndex }
::= { usrDnsCacheTable 1 }
UsrDnsCacheEntry ::=
    SEQUENCE {
        usrDnsCacheRRIndex
            Integer32,
        usrDnsCacheRRClass
            DnsClass,
        usrDnsCacheRRType
            DnsType,
        usrDnsCacheRRTTL
            DnsTime,
        usrDnsCacheRRElapsedTTL
            DnsTime,
        usrDnsCacheRRSource
            IpAddress,
        usrDnsCacheRRData
            OCTET STRING,
        usrDnsCacheRRStatus
            RowStatus,
        usrDnsCacheRRPrettyName
            DnsName
    }
usrDnsCacheRRIndex OBJECT-TYPE
    SYNTAX      Integer32
    MAX-ACCESS  not-accessible
    STATUS      current
    DESCRIPTION
           "A value which makes entries in the table unique."
::= { usrDnsCacheEntry 1 }
usrDnsCacheRRClass OBJECT-TYPE
    SYNTAX      DnsClass
    MAX-ACCESS  read-only
    STATUS      current
    DESCRIPTION
           "DNS class of the Resource Record in the cache which is
           identified in this row of the table."
::= { usrDnsCacheEntry 2 }
usrDnsCacheRRType OBJECT-TYPE
    SYNTAX      DnsType
    MAX-ACCESS  read-only
    STATUS      current
    DESCRIPTION
           "DNS type of the Resource Record in the cache which is
           identified in this row of the table."
::= { usrDnsCacheEntry 3 }
usrDnsCacheRRTTL OBJECT-TYPE
    SYNTAX      DnsTime
    MAX-ACCESS  read-only
    STATUS      current
    DESCRIPTION
           "Time-To-Live of RR in DNS cache.  This is the initial
           TTL value which was received with the RR when it was
           originally received."
::= { usrDnsCacheEntry 4 }
usrDnsCacheRRElapsedTTL OBJECT-TYPE
    SYNTAX      DnsTime
    MAX-ACCESS  read-only
    STATUS      current
    DESCRIPTION
           "Elapsed seconds since RR was received."
::= { usrDnsCacheEntry 5 }
usrDnsCacheRRSource OBJECT-TYPE
    SYNTAX      IpAddress
    MAX-ACCESS  read-only
    STATUS      current
    DESCRIPTION
           "Host from which RR was received, 0.0.0.0 if unknown."
::= { usrDnsCacheEntry 6 }
usrDnsCacheRRData OBJECT-TYPE
    SYNTAX      OCTET STRING
    MAX-ACCESS  read-only
    STATUS      current
    DESCRIPTION
           "RDATA portion of a cached RR.  The value is in the
           format defined for the particular DNS class and type of
           the resource record."
    REFERENCE
           "RFC-1035 section 3.2.1."
::= { usrDnsCacheEntry 7 }
usrDnsCacheRRStatus OBJECT-TYPE
    SYNTAX      RowStatus
    MAX-ACCESS  read-write
    STATUS      current
    DESCRIPTION
           "Status column for the resolver cache table.  Since only
           the agent (DNS resolver) creates rows in this table, the
           only values that a manager may write to this variable
           are active(1) and destroy(6)."
::= { usrDnsCacheEntry 8 }
usrDnsCacheRRPrettyName OBJECT-TYPE
    SYNTAX      DnsName
    MAX-ACCESS  read-only
    STATUS      current
    DESCRIPTION
           "Name of the RR at this row in the table.  This is
           identical to the dnsResCacheRRName variable, except that
           character case is preserved in this variable, per DNS
           conventions."
    REFERENCE
           "RFC-1035 section 2.3.3."
::= { usrDnsCacheEntry 9 }
-- Resolver Negative Cache Table
usrDnsNCacheTable OBJECT-TYPE
    SYNTAX      SEQUENCE OF UsrDnsNCacheEntry
    MAX-ACCESS  not-accessible
    STATUS      current
    DESCRIPTION
           "The resolver's negative response cache.  This table
           contains information about authoritative errors that
           have been cached by the resolver."
::= { usrDns 25 }
usrDnsNCacheEntry OBJECT-TYPE
    SYNTAX      UsrDnsNCacheEntry
    MAX-ACCESS  not-accessible
    STATUS      current
    DESCRIPTION
           "An entry in the resolver's negative response cache
           table.  Only the resolver can create rows.  SNMP SET
           requests may be used to delete rows."
       INDEX     { usrDnsNCacheErrIndex }
::= { usrDnsNCacheTable 1 }
UsrDnsNCacheEntry ::=
    SEQUENCE {
        usrDnsNCacheErrIndex
            Integer32,
        usrDnsNCacheErrQClass
            DnsQClass,
        usrDnsNCacheErrQType
            DnsQType,
        usrDnsNCacheErrTTL
            DnsTime,
        usrDnsNCacheErrElapsedTTL
            DnsTime,
        usrDnsNCacheErrSource
            IpAddress,
        usrDnsNCacheErrCode
            INTEGER,
        usrDnsNCacheErrStatus
            RowStatus,
        usrDnsNCacheErrPrettyName
            DnsName
    }
usrDnsNCacheErrIndex OBJECT-TYPE
    SYNTAX      Integer32
    MAX-ACCESS  read-only
    STATUS      current
    DESCRIPTION
           "A value which makes entries in the table unique."
::= { usrDnsNCacheEntry 9 }
usrDnsNCacheErrQClass OBJECT-TYPE
    SYNTAX      DnsQClass
    MAX-ACCESS  read-only
    STATUS      current
    DESCRIPTION
           "DNS QCLASS associated with a cached authoritative
           error."
::= { usrDnsNCacheEntry 2 }
usrDnsNCacheErrQType OBJECT-TYPE
    SYNTAX      DnsQType
    MAX-ACCESS  read-only
    STATUS      current
    DESCRIPTION
           "DNS QTYPE associated with a cached authoritative error."
::= { usrDnsNCacheEntry 3 }
usrDnsNCacheErrTTL OBJECT-TYPE
    SYNTAX      DnsTime
    MAX-ACCESS  read-only
    STATUS      current
    DESCRIPTION
           "Time-To-Live of a cached authoritative error at the time
           of the error, it should not be decremented by the number
           of seconds since it was received.  This should be the
           TTL as copied from the MINIMUM field of the SOA that
           accompanied the authoritative error, or a smaller value
           if the resolver implements a ceiling on negative
           response cache TTLs."
    REFERENCE
           "RFC-1034 section 4.3.4."
::= { usrDnsNCacheEntry 4 }
usrDnsNCacheErrElapsedTTL OBJECT-TYPE
    SYNTAX      DnsTime
    MAX-ACCESS  read-only
    STATUS      current
    DESCRIPTION
           "Elapsed seconds since authoritative error was received."
::= { usrDnsNCacheEntry 5 }
usrDnsNCacheErrSource OBJECT-TYPE
    SYNTAX      IpAddress
    MAX-ACCESS  read-only
    STATUS      current
    DESCRIPTION
           "Host which sent the authoritative error, 0.0.0.0 if
           unknown."
::= { usrDnsNCacheEntry 6 }
usrDnsNCacheErrCode OBJECT-TYPE
    SYNTAX      INTEGER { nonexistantName(1), noData(2), other(3) }
    MAX-ACCESS  read-only
    STATUS      current
    DESCRIPTION
           "The authoritative error that has been cached:
           nonexistantName(1) indicates an authoritative name error
           (RCODE = 3).
           noData(2) indicates an authoritative response with no
           error (RCODE = 0) and no relevant data.
           other(3) indicates some other cached authoritative
           error.  At present, no such errors are known to exist."
::= { usrDnsNCacheEntry 7 }
usrDnsNCacheErrStatus OBJECT-TYPE
    SYNTAX      RowStatus
    MAX-ACCESS  read-write
    STATUS      current
    DESCRIPTION
           "Status column for the resolver negative response cache
           table.  Since only the agent (DNS resolver) creates rows
           in this table, the only values that a manager may write
           to this variable are active(1) and destroy(6)."
::= { usrDnsNCacheEntry 8 }
usrDnsNCacheErrPrettyName OBJECT-TYPE
    SYNTAX      DnsName
    MAX-ACCESS  read-only
    STATUS      current
    DESCRIPTION
           "QNAME associated with this row in the table.  This is
           identical to the dnsResNCacheErrQName variable, except
           that character case is preserved in this variable, per
           DNS conventions."
    REFERENCE
           "RFC-1035 section 2.3.3."
::= { usrDnsNCacheEntry 10 }
END         -- End USR-DNS-MIB definitions
-- ************************************************************************
--
--
--	usr_tap.mib - An enterprise specific MIB file for 
--                    the Port Tapping Service
--
-- Author:         J Senthilnathan
--
USR-TAP-MIB DEFINITIONS ::= BEGIN
       IMPORTS
          OBJECT-TYPE, MODULE-IDENTITY,
          IpAddress, Integer32
                FROM SNMPv2-SMI
          UsrDisplayString, common
                FROM USR-DEFINITIONS-MIB;
usrTap  MODULE-IDENTITY
        LAST-UPDATED "200204061326Z"
        ORGANIZATION "CommWorks Corporation, a 3Com Company"
        CONTACT-INFO "Customer Support"
        DESCRIPTION
                "The commWorks enterprise defined MIB objects for
                 the Port Tapping Service functionality."
--      REVISION      "200204061326Z"
--      DESCRIPTION " Corrected SNMPv2 format"
::= { common 57 }
   -- Begin managed object definitions here...
usrTapTable OBJECT-TYPE
	SYNTAX SEQUENCE OF UsrTapEntry
	MAX-ACCESS not-accessible
	STATUS current
	DESCRIPTION
		"The table of Tap entries. "
::= { usrTap 1 }
usrTapEntry OBJECT-TYPE
	SYNTAX UsrTapEntry
	MAX-ACCESS not-accessible
	STATUS current
	DESCRIPTION
		"A entry for one tap."
	INDEX { usrTapOutput }
::= { usrTapTable 1 }
UsrTapEntry ::= SEQUENCE {
	usrTapIfaceName		UsrDisplayString,
	usrTapIface		    Integer32,
	usrTapUserName		UsrDisplayString,
	usrTapUser		    Integer32,
	usrTapNext		    Integer32,
	usrTapPermanent 	INTEGER,
	usrTapOutput		INTEGER,
	usrTapFormat		INTEGER,
	usrTapFacility		INTEGER,
	usrTapPriority     	INTEGER,
	usrTapAddress     	IpAddress,
	usrTapOutputIcb		Integer32,
	usrTapStatus		Integer32
	}
usrTapIfaceName OBJECT-TYPE
	SYNTAX		UsrDisplayString 
	MAX-ACCESS	read-write
	STATUS		current
	DESCRIPTION
		"The name of the interface being tapped."
::= { usrTapEntry 1 }
usrTapUserName OBJECT-TYPE
	SYNTAX		UsrDisplayString 
	MAX-ACCESS	read-write
	STATUS		current
	DESCRIPTION
		"The name of the user being tapped."
::= { usrTapEntry 2 }
usrTapOutput OBJECT-TYPE
	SYNTAX		INTEGER { syslog(0), screen(1) }
	MAX-ACCESS	read-write
	STATUS		current
	DESCRIPTION
		"The tapped output can be sent to syslog or to screen."
::= { usrTapEntry 3 }
usrTapFormat OBJECT-TYPE
	SYNTAX		INTEGER { ascii(0), hex(1), clear(2) }
	MAX-ACCESS	read-write
	STATUS		current
	DESCRIPTION
		"The output can be in hex, ascii or clear formats."
::= { usrTapEntry 4 }
usrTapFacility OBJECT-TYPE
	SYNTAX		INTEGER { auth(1), local0(2), local1(3), local2(4), local3(5), local4(6), local5(7), local6(8), local7(9) }
	MAX-ACCESS	read-write
	STATUS		current
	DESCRIPTION
		"The syslog facility used for logging."
::= { usrTapEntry 5 }
usrTapPriority OBJECT-TYPE
	SYNTAX		INTEGER { critical(0), unusual(1), common(2), verbose(3) }
	MAX-ACCESS	read-write
	STATUS		current
	DESCRIPTION
		"The syslog level used for logging."
::= { usrTapEntry 6 }
usrTapAddress OBJECT-TYPE
	SYNTAX		IpAddress 
	MAX-ACCESS	read-write
	STATUS		current
	DESCRIPTION
		"The IP address for logging the output to."
::= { usrTapEntry 7 }
usrTapOutputIcb OBJECT-TYPE
	SYNTAX		Integer32 
	MAX-ACCESS	read-write
	STATUS		current
	DESCRIPTION
		"The icb ptr for tap commands issued via cli."
::= { usrTapEntry 8 }
usrTapStatus OBJECT-TYPE
	SYNTAX		Integer32 
	MAX-ACCESS	read-write
	STATUS		current
	DESCRIPTION
		"The status of the tap"
::= { usrTapEntry 9 }
usrTapIface OBJECT-TYPE
	SYNTAX		Integer32 
	MAX-ACCESS	read-write
	STATUS		current
	DESCRIPTION
		"Whether this is a interface based tap."
::= { usrTapEntry 10 }
usrTapUser OBJECT-TYPE
	SYNTAX		Integer32 
	MAX-ACCESS	read-write
	STATUS		current
	DESCRIPTION
		"Whether this is a user based tap."
::= { usrTapEntry 11 }
usrTapNext OBJECT-TYPE
	SYNTAX		Integer32 
	MAX-ACCESS	read-write
	STATUS		current
	DESCRIPTION
		"Whether the next call is to be tapped."
::= { usrTapEntry 12 }
usrTapPermanent OBJECT-TYPE
	SYNTAX		INTEGER { temporary(0), permanent(1) }
	MAX-ACCESS	read-write
	STATUS		current
	DESCRIPTION
		"Whether the tap is permanent (user profile has it) or temp (CLI issued)"
::= { usrTapEntry 13 }
END         -- End USR-TAP-MIB definitions
   USR-L2TP-MIB DEFINITIONS ::= BEGIN
   IMPORTS
           OBJECT-IDENTITY, OBJECT-TYPE, MODULE-IDENTITY,
           Integer32, IpAddress, Counter32, Unsigned32
                  FROM SNMPv2-SMI
           TruthValue, RowStatus
                  FROM SNMPv2-TC
           common, UsrDisplayString, UsrConfigStatus
                  FROM USR-DEFINITIONS-MIB;
   usrL2TP MODULE-IDENTITY
            LAST-UPDATED "200208121820Z"
            ORGANIZATION "CommWorks Corporation, a 3Com Company"
            CONTACT-INFO "Customer Support"
            DESCRIPTION
                    "The commWorks enterprise defined MIB objects for L2TP"
--          REVISION "200208121820Z"
--          DESCRIPTION "Changed labels to clarify behaviour of
--                       usrL2tpPasswordEncryptStyle."
--          REVISION "200204051850Z"
--          DESCRIPTION " Added objects to SEQUENCE and corrected
--                        SNMPv2 formats."
           ::= { common 55 }
   usrL2TPGlobal  OBJECT-IDENTITY
           STATUS          current
           DESCRIPTION
              "The root of the L2TP global Object-Identifiers."
           ::= { usrL2TP 1 }
   usrL2TPConfigTable OBJECT-TYPE
           SYNTAX          SEQUENCE OF UsrL2TPConfigEntry
           MAX-ACCESS      not-accessible
           STATUS          current
           DESCRIPTION
              ""
           ::= { usrL2TPGlobal 1 }
   usrL2tpConfigEntry OBJECT-TYPE
           SYNTAX          UsrL2TPConfigEntry
           MAX-ACCESS      not-accessible
           STATUS          current
           DESCRIPTION
              "."
           INDEX           { usrL2tpConfigIndex }
           ::= { usrL2TPConfigTable 1 }
   UsrL2TPConfigEntry ::= SEQUENCE {
           usrL2tpConfigIndex
                   Integer32,
           usrL2tpLoadBalancing
                   TruthValue,
	   		usrL2tpDialOut
					OCTET STRING,
			usrL2tpLnsFlag INTEGER ,
		usrL2tpPasswordEncryptStyle INTEGER,
 	usrL2TPLcpRenegotiateAtLNS INTEGER,
    		usrL2tpAuthenticationRequiredOnOutgoingTunnels
					TruthValue,
           usrL2tpNumberOfEchoRetransmissions
                   Integer32(0..65535),
           usrL2tpEchoRetransmissionInterval
                   Integer32(0..65535)
		}
   usrL2tpConfigIndex      OBJECT-TYPE
           SYNTAX          Integer32
           MAX-ACCESS      read-only
           STATUS          current
           DESCRIPTION
              " A unique value for each l2tp protocol stack. "
           ::= { usrL2tpConfigEntry 1 }
   usrL2tpLoadBalancing  OBJECT-TYPE
           SYNTAX          TruthValue
           MAX-ACCESS      read-write
           STATUS          current
           DESCRIPTION
              "Defines If Load Balancing is enabled or not."
           DEFVAL          { true }
		 --CONFIGURABLE
           ::= { usrL2tpConfigEntry 2 }
   usrL2tpDialOut OBJECT-TYPE       
        SYNTAX  OCTET STRING (SIZE(0..32))
        MAX-ACCESS  read-write
        STATUS  current
        DESCRIPTION
                "This variable is set through the CLI when the user
                 manually issues a L2TP dial-out."      
        ::= { usrL2tpConfigEntry 3 }
   usrL2tpLnsFlag OBJECT-TYPE
      SYNTAX   INTEGER { enabled(1), disabled(2) }
      MAX-ACCESS   read-write
      STATUS   current     
      DESCRIPTION
             "Setting this object to a value of enabled(1) will enable
              the L2TP lns enable feature. Setting this object to
              disabled(2) will disable the L2TP LNS feature."
     --CONFIGURABLE
   ::= { usrL2tpConfigEntry 4 } 
    usrL2tpPasswordEncryptStyle OBJECT-TYPE
      SYNTAX   INTEGER { noSalt(1), withSalt(2) }
      MAX-ACCESS   read-write
      STATUS   current     
      DESCRIPTION
             "Original labels were Draft-3 and Draft-6. This value
              defines the encryption style for tunnel password as 
              retrieved from RADIUS. It indicates whether or not
              a salt or secret key value will be used to encrypt 
              the password."
	DEFVAL { noSalt }
     --CONFIGURABLE
   ::= { usrL2tpConfigEntry  5 }
	usrL2TPLcpRenegotiateAtLNS OBJECT-TYPE
	SYNTAX  INTEGER {
		enabled(1),                                        
		disabled(2)
		} 
	MAX-ACCESS   read-write
	STATUS   current
	DESCRIPTION
		"This flag is used to enable/disable LCP renegotiation
		for calls when doing proxy LCP on LNS"
	--CONFIGURABLE    
	::= { usrL2tpConfigEntry 6 }
    usrL2tpAuthenticationRequiredOnOutgoingTunnels   OBJECT-TYPE
           SYNTAX          TruthValue
           MAX-ACCESS      read-write
           STATUS          current
           DESCRIPTION
              "When set to a value of true(1) requires that all
              outgoing tunnels request tunnel authentication."
           DEFVAL          { true }
		 --CONFIGURABLE
           ::= { usrL2tpConfigEntry 7 }
   usrL2tpNumberOfEchoRetransmissions  OBJECT-TYPE
           SYNTAX          Integer32 (0..65535)
           MAX-ACCESS      read-write
           STATUS          current
           DESCRIPTION
              "This object defines the number of Hello retransmission's
              which the L2TP stack will attempt before assuming that
              the peer is no longer reachable. The default value for
              this object is five (5)."
           DEFVAL          { 5 }
		 --CONFIGURABLE
           ::= { usrL2tpConfigEntry 8 }
   usrL2tpEchoRetransmissionInterval   OBJECT-TYPE
           SYNTAX          Integer32(0..65535)
           MAX-ACCESS      read-write
           STATUS          current
           DESCRIPTION
              "This object defines the number of seconds between each
              retransmission."
           DEFVAL          { 10 }
		 --CONFIGURABLE
           ::= { usrL2tpConfigEntry 9 }
   usrL2tpTunnel OBJECT IDENTIFIER ::= {usrL2TP 2}
   usrL2tpTunnelQueryTable OBJECT-TYPE
           SYNTAX          SEQUENCE OF UsrL2tpTunnelQueryEntry
           MAX-ACCESS      not-accessible
           STATUS          current
           DESCRIPTION
              "A table containing the READ ONLY propietary extension
			   parameters for L2TP Tunnel MIB."
           ::= { usrL2tpTunnel 1 }
   usrL2tpTunnelQueryEntry OBJECT-TYPE
           SYNTAX          UsrL2tpTunnelQueryEntry
           MAX-ACCESS      not-accessible
           STATUS          current
           DESCRIPTION
              "  "
           INDEX           { usrL2tpTunnelLogicalStackIndex,
                             usrL2tpTunnelLocalControlTunnelId }
           ::= { usrL2tpTunnelQueryTable 1 }
   UsrL2tpTunnelQueryEntry ::= SEQUENCE {
           usrL2tpTunnelLogicalStackIndex
                   Integer32,
           usrL2tpTunnelLocalControlTunnelId
                   Integer32,
           usrL2tpTunnelSecurityLevel
                   INTEGER,
		usrL2tpTunnelDisconnect
                   Integer32}
    usrL2tpTunnelLogicalStackIndex OBJECT-TYPE
           SYNTAX          Integer32
           MAX-ACCESS      read-only     
           STATUS          current
           DESCRIPTION
              "This object contains a reference to the logical
              l2tp protocol stack and must be the same as the
              l2tpConfigIndex."
           ::= { usrL2tpTunnelQueryEntry 1 }  
   usrL2tpTunnelLocalControlTunnelId OBJECT-TYPE   
           SYNTAX          Integer32
           MAX-ACCESS      read-only      
           STATUS          current
           DESCRIPTION
              "This object contains the local tunnel Identifier."
           ::= { usrL2tpTunnelQueryEntry 2 }      
   usrL2tpTunnelSecurityLevel OBJECT-TYPE
           SYNTAX          INTEGER{
                                    none(0),
                                    control-Only(1),
                                    data-Only(2),
                                    both-Data-And-Control(3)
                                  }
           MAX-ACCESS      read-only
           STATUS          current
           DESCRIPTION
              "This field contains the security level 
              of the tunnel."
		   ::= {usrL2tpTunnelQueryEntry 3}
	usrL2tpTunnelDisconnect	OBJECT-TYPE
           SYNTAX          Integer32
           MAX-ACCESS      read-write  
           STATUS          current
           DESCRIPTION
              "This object is used to disconnect a specific tunnel."
           ::= { usrL2tpTunnelQueryEntry 4 }
	 usrL2tpSession OBJECT-IDENTITY      
          STATUS         current    
          DESCRIPTION               
             "The root of L2TP Session Module Object-identifiers."
          ::= { usrL2TP 3 }
   usrL2tpSessionTable OBJECT-TYPE    
           SYNTAX    SEQUENCE OF UsrL2tpSessionEntry
           MAX-ACCESS not-accessible
           STATUS current
           DESCRIPTION
              ""
           ::= { usrL2tpSession 1 }
   usrL2tpSessionEntry OBJECT-TYPE
           SYNTAX          UsrL2tpSessionEntry
           MAX-ACCESS      not-accessible
           STATUS          current 
           DESCRIPTION
              "."
           INDEX           { usrL2tpSessionLogicalStackIndex,
                           usrL2tpSessionTunnelID , usrL2tpSessionLocalCallID }
           ::= { usrL2tpSessionTable 1 }
   UsrL2tpSessionEntry ::= SEQUENCE {
	   usrL2tpSessionLogicalStackIndex
                   Integer32,
       usrL2tpSessionTunnelID
                   Integer32,
       usrL2tpSessionLocalCallID
                   Integer32,
		usrL2tpSessionDisconnect	
                   Integer32
				}
   usrL2tpSessionLogicalStackIndex OBJECT-TYPE
           SYNTAX          Integer32
           MAX-ACCESS      read-only
           STATUS          current
           DESCRIPTION
              "This object contains a reference to the logical
              l2tp protocol stack and must be the same as the
              l2tpConfigIndex and l2tpTunelLogicalStackIndex."
           ::= { usrL2tpSessionEntry 1 }
   usrL2tpSessionTunnelID OBJECT-TYPE
           SYNTAX          Integer32
           MAX-ACCESS      read-only
           STATUS          current
           DESCRIPTION
              "This object contains the control Channel Tunnel
              identifier for this session"
           ::= { usrL2tpSessionEntry 2 }
   usrL2tpSessionLocalCallID  OBJECT-TYPE
           SYNTAX          Integer32
           MAX-ACCESS      read-only
           STATUS          current
           DESCRIPTION
              "This object contains the local call identifier
              for the session.  "
           ::= { usrL2tpSessionEntry 3 }
	    usrL2tpSessionDisconnect OBJECT-TYPE
           SYNTAX          Integer32
           MAX-ACCESS      read-write
           STATUS          current
           DESCRIPTION
              "This object is used to disconnect a specific tunnel."
           ::= { usrL2tpSessionEntry 4 }
	usrL2tpHostTable OBJECT-TYPE
        	SYNTAX SEQUENCE OF UsrL2tpHostEntry
        	MAX-ACCESS not-accessible
        	STATUS current
        	DESCRIPTION
                "The table of L2TP LNSs. "
			::= { usrL2TP 4 }
	usrL2tpHostEntry OBJECT-TYPE
		        SYNTAX UsrL2tpHostEntry
	        	MAX-ACCESS not-accessible
	        	STATUS current
	        	DESCRIPTION
	              "A (conceptual) entry for one pptp Host."
	        	INDEX { usrL2tpHostIndex }
				::= { usrL2tpHostTable 1 }
	UsrL2tpHostEntry ::= SEQUENCE {
	        usrL2tpHostIndex       Integer32,
	        usrL2tpHostAddress     IpAddress,
	        usrL2tpHostStatus      RowStatus,
	        usrL2tpSharedSecret    OCTET STRING,
	        usrL2tpSharedSecretStatus    TruthValue,
			usrL2tpSecurityLevel	INTEGER	
	        }
	usrL2tpHostIndex OBJECT-TYPE
	        SYNTAX          Integer32
	        MAX-ACCESS      not-accessible
	        STATUS          current
	        DESCRIPTION
	              "The logical identifier of the Host Table. "
			::= { usrL2tpHostEntry 1 }
	usrL2tpHostAddress OBJECT-TYPE
	        SYNTAX          IpAddress
	        MAX-ACCESS      read-write
	        STATUS          current
	        DESCRIPTION
	                "The specified or resolved ip address of the named Host. "
	        --CONFIGURABLE
			::= { usrL2tpHostEntry 2 }
	usrL2tpHostStatus OBJECT-TYPE
	        SYNTAX          RowStatus
	        MAX-ACCESS      read-write
	        STATUS          current
	        DESCRIPTION
	            "The status of this row of the Host Table. "
	        --CONFIGURABLE
			::= { usrL2tpHostEntry 3 }
	 usrL2tpSharedSecret OBJECT-TYPE
                SYNTAX          OCTET STRING  (SIZE(0..128))
                MAX-ACCESS      read-write
                STATUS          current
                DESCRIPTION
                      "The Shared Secret For This Host. "
		 --CONFIGURABLE
                        ::= { usrL2tpHostEntry 4 }
	 usrL2tpSharedSecretStatus OBJECT-TYPE
                SYNTAX          TruthValue 
                MAX-ACCESS      read-write
                STATUS          current
                DESCRIPTION
                      "The Shared Secret Status For This Host. "
		 --CONFIGURABLE
                        ::= { usrL2tpHostEntry 5 }
     usrL2tpSecurityLevel OBJECT-TYPE    
                SYNTAX          INTEGER{
                                    none(0),
                                    control-Only(1),
                                    data-Only(2),
                                    both-Data-And-Control(3)
                                  }
                MAX-ACCESS      read-write
                STATUS          current
                DESCRIPTION   
                      "The Security Level For This Host. "
		 --CONFIGURABLE
                        ::= { usrL2tpHostEntry 6 }
	usrL2TPConfigFileName OBJECT-TYPE
          SYNTAX      UsrDisplayString
          MAX-ACCESS  read-only
          STATUS      current
          DESCRIPTION
          "The name of a ConfigFile to read/write permanent database records.
           If the value of this object is an empty string, then the
           L2TP process uses the default name `@file://L2tpProcess.cfg'. "
          ::= { usrL2TP 5 }
    usrL2TPCFMStatusFlag  OBJECT-TYPE
          SYNTAX         UsrConfigStatus
          MAX-ACCESS     read-write
          STATUS         current
          DESCRIPTION
                 "CFM Config Flag"
          ::= { usrL2TP 6 }                   
   -- mr5579 crigg - New L2TP stats for Statistics and MIBs v0.5
   usrL2tpStatsTable OBJECT-TYPE
           SYNTAX          SEQUENCE OF UsrL2tpStatsEntry
           MAX-ACCESS      not-accessible
           STATUS          current
           DESCRIPTION
              "A table containing a single row containing new
	       L2TP counters"
          ::= { usrL2TP 7 }                   
   usrL2tpStatsEntry OBJECT-TYPE
           SYNTAX          UsrL2tpStatsEntry
           MAX-ACCESS      not-accessible
           STATUS          current
           DESCRIPTION
              "  "
           INDEX           { usrL2tpStatsIndex }
           ::= { usrL2tpStatsTable 1 }
   UsrL2tpStatsEntry ::= SEQUENCE {
   	usrL2tpStatsIndex		  Integer32,
   	usrL2tpStatsTunnelSetupAttempts   Counter32,
   	usrL2tpStatsTunnelSetupCompleteds Counter32,
   	usrL2tpStatsTunnelSetupFaileds    Counter32,
   	usrL2tpStatsCountersResetTime     Unsigned32
	}                   
   usrL2tpStatsIndex          OBJECT-TYPE
           SYNTAX          Integer32
           MAX-ACCESS      read-only
           STATUS          current
           DESCRIPTION
              " Should be the same value as l2tpConfigIndex and l2tpStatsIndex
		to reference the same logical l2tp protocol stack. 
		On HiPer ARC, this index is always 1"
           ::= { usrL2tpStatsEntry 1 }
   usrL2tpStatsTunnelSetupAttempts             OBJECT-TYPE
           SYNTAX          Counter32
           MAX-ACCESS      read-only
           STATUS          current
           DESCRIPTION
              "Count of L2TP tunnel setup attempts.
	       Discontinuity is indicated by usrL2tpStatsCountersResetTime."
	   REFERENCE
	      "1051 PRD 3G R2.0 v1.2 sec 4.5.2.1"
           ::= { usrL2tpStatsEntry 2}
   usrL2tpStatsTunnelSetupCompleteds           OBJECT-TYPE
           SYNTAX          Counter32
           MAX-ACCESS      read-only
           STATUS          current
           DESCRIPTION
              "Count of L2TP tunnel setups completed  (L2TP tunnel
	       setup attempts that reached the established state).
	       Discontinuity is indicated by usrL2tpStatsCountersResetTime."
	   REFERENCE
	      "1051 PRD 3G R2.0 v1.2 sec 4.5.2.1"
           ::= { usrL2tpStatsEntry 3}
   usrL2tpStatsTunnelSetupFaileds              OBJECT-TYPE
           SYNTAX          Counter32
           MAX-ACCESS      read-only
           STATUS          current
           DESCRIPTION
              "Count of L2TP tunnel setups that failed  (L2TP tunnel
	       setup attempts that terminated without reaching the
	       established state).
	       Discontinuity is indicated by usrL2tpStatsCountersResetTime."
	   REFERENCE
	      "1051 PRD 3G R2.0 v1.2 sec 4.5.2.1"
           ::= { usrL2tpStatsEntry 4}
   usrL2tpStatsCountersResetTime              OBJECT-TYPE
           SYNTAX          Unsigned32 
           MAX-ACCESS      read-write
           STATUS          current
           DESCRIPTION
              "Reading:
		   Time the L2TP statistics counters were last reset.
	       Resetting counters causes a discontinuity in the monotonically 
	       increasing value of the counters.  Management stations that 
	       sample these counters need also to sample this object so that 
	       they can know that a discontinuity occured with respect to the
	       previous sample.  Its value is number of seconds since EPOCH.
	       EPOCH is seconds since 00:00:00 UTC, Jan 1, 1970.  
	       Writing:
		   Writing 0 causes the following global L2TP stats to be reset
		   to 0:
           		l2tpStatsFailedAuthentications
           		l2tpStatsMalformedPackets
           		l2tpStatsControlTunnelRecvPackets
           		l2tpStatsControlTunnelWithDataRecvPackets
          		l2tpStatsControlTunnelWithoutDataRecvPackets
          		l2tpStatsProcessedControlTunnelRecvPackets
           		l2tpStatsInSequenceControlTunnelRecvPackets
           		l2tpStatsOutSequenceControlTunnelRecvPackets
           		l2tpStatsInOrderControlTunnelRecvPackets
           		l2tpStatsOutOfOrderControlTunnelRecvPackets
           		l2tpStatsFlowDiscardedControlTunnelRecvPackets
           		l2tpStatsOutOfOrderDiscardedControlTunnelRecvPackets
           		l2tpStatsControlTunnelSendPackets
           		l2tpStatsControlTunnelWithdataSendPackets
           		l2tpStatsControlTunnelWithoutdataSendPackets
           		l2tpStatsControlTunnelFlowControlTimeouts
           		l2tpStatsLocalControlTunnelFlowControlEnables
           		l2tpStatsRemoteControlTunnelFlowControlEnables
           		l2tpStatsControlTunnelReassemblyTimeouts
           		l2tpStatsDataTunnelRecvPackets
           		l2tpStatsDataTunnelWithdataRecvPackets
           		l2tpStatsDataTunnelWithoutdataRecvPackets
           		l2tpStatsProcessedDataTunnelRecvPackets
           		l2tpStatsInSequenceDataTunnelRecvPackets
           		l2tpStatsOutSequenceDataTunnelRecvPackets
           		l2tpStatsInOrderDataTunnelRecvPackets
           		l2tpStatsOutOfOrderDataTunnelRecvPackets
           		l2tpStatsFlowDiscardedDataTunnelRecvPackets
           		l2tpStatsOutOfOrderDiscardedDataTunnelRecvPackets
           		l2tpStatsDataTunnelSendPackets
           		l2tpStatsDataTunnelWithdataSendPackets
           		l2tpStatsDataTunnelWithoutdataSendPackets
           		l2tpStatsDataTunnelFlowControlTimeouts
           		l2tpStatsLocalDataTunnelFlowControlEnables
           		l2tpStatsRemoteDataTunnelFlowControlEnables
           		l2tpStatsDataTunnelReassemblyTimeouts
			usrL2tpStatsTunnelSetupAttempts
			usrL2tpStatsTunnelSetupCompleteds
			usrL2tpStatsTunnelSetupFaileds
		    Writing other values are rejected.
		"
           ::= { usrL2tpStatsEntry 5}
END
