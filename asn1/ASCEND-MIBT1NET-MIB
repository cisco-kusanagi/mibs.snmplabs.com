--			Ascend mibt1net MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBT1NET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibt1NetworkProfile  OBJECT IDENTIFIER ::= { configuration 127}
    mibt1NetworkProfileV1  OBJECT IDENTIFIER ::= { configuration 126}

	-- The mibt1NetworkProfile table
	--
	-- This table contains parameters for the mibt1NetworkProfile profile
	--

    mibt1NetworkProfileTable	OBJECT-TYPE
	SYNTAX		SEQUENCE OF Mibt1NetworkProfileEntry
	ACCESS		not-accessible
	STATUS		mandatory
	DESCRIPTION	"A list of mibt1NetworkProfile profile entries."
	::= { mibt1NetworkProfile 1 }

    mibt1NetworkProfileEntry	OBJECT-TYPE
	SYNTAX		Mibt1NetworkProfileEntry
	ACCESS		not-accessible
	STATUS		mandatory
	DESCRIPTION	"A mibt1NetworkProfile entry containing objects that
			 maps to the parameters of mibt1NetworkProfile profile."
	INDEX		{ t1NetworkProfile-Shelf-o, t1NetworkProfile-Slot-o, t1NetworkProfile-Item-o }
	::= { mibt1NetworkProfileTable 1 }

    Mibt1NetworkProfileEntry ::=
	SEQUENCE {
	    t1NetworkProfile-Shelf-o
		INTEGER,
	    t1NetworkProfile-Slot-o
		INTEGER,
	    t1NetworkProfile-Item-o
		INTEGER,
	    t1NetworkProfile-Name
		DisplayString,
	    t1NetworkProfile-PhysicalAddress-Shelf
		INTEGER,
	    t1NetworkProfile-PhysicalAddress-Slot
		INTEGER,
	    t1NetworkProfile-PhysicalAddress-ItemNumber
		INTEGER,
	    t1NetworkProfile-LineInterface-Enabled
		INTEGER,
	    t1NetworkProfile-LineInterface-TOnlineType
		INTEGER,
	    t1NetworkProfile-LineInterface-FrameType
		INTEGER,
	    t1NetworkProfile-LineInterface-Encoding
		INTEGER,
	    t1NetworkProfile-LineInterface-ClockSource
		INTEGER,
	    t1NetworkProfile-LineInterface-ClockPriority
		INTEGER,
	    t1NetworkProfile-LineInterface-SignalingMode
		INTEGER,
	    t1NetworkProfile-LineInterface-IsdnEmulationSide
		INTEGER,
	    t1NetworkProfile-LineInterface-RobbedBitMode
		INTEGER,
	    t1NetworkProfile-LineInterface-DefaultCallType
		INTEGER,
	    t1NetworkProfile-LineInterface-SwitchType
		INTEGER,
	    t1NetworkProfile-LineInterface-NfasGroupId
		INTEGER,
	    t1NetworkProfile-LineInterface-NfasId
		INTEGER,
	    t1NetworkProfile-LineInterface-IncomingCallHandling
		INTEGER,
	    t1NetworkProfile-LineInterface-DeleteDigits
		INTEGER,
	    t1NetworkProfile-LineInterface-AddDigitString
		DisplayString,
	    t1NetworkProfile-LineInterface-CallByCall
		INTEGER,
	    t1NetworkProfile-LineInterface-NetworkSpecificFacilities
		INTEGER,
	    t1NetworkProfile-LineInterface-PbxAnswerNumber
		DisplayString,
	    t1NetworkProfile-LineInterface-AnswerService
		INTEGER,
	    t1NetworkProfile-LineInterface-oPBXType
		INTEGER,
	    t1NetworkProfile-LineInterface-DataSense
		INTEGER,
	    t1NetworkProfile-LineInterface-IdleMode
		INTEGER,
	    t1NetworkProfile-LineInterface-oFDL
		INTEGER,
	    t1NetworkProfile-LineInterface-FrontEndType
		INTEGER,
	    t1NetworkProfile-LineInterface-oDSXLineLength
		INTEGER,
	    t1NetworkProfile-LineInterface-oCSUBuildOut
		INTEGER,
	    t1NetworkProfile-LineInterface-OverlapReceiving
		INTEGER,
	    t1NetworkProfile-LineInterface-PriPrefixNumber
		DisplayString,
	    t1NetworkProfile-LineInterface-TrailingDigits
		INTEGER,
	    t1NetworkProfile-LineInterface-T302Timer
		INTEGER,
	    t1NetworkProfile-LineInterface-Layer3End
		INTEGER,
	    t1NetworkProfile-LineInterface-Layer2End
		INTEGER,
	    t1NetworkProfile-LineInterface-NlValue
		INTEGER,
	    t1NetworkProfile-LineInterface-LoopAvoidance
		INTEGER,
	    t1NetworkProfile-LineInterface-MaintenanceState
		INTEGER,
	    t1NetworkProfile-LineInterface-NumberComplete
		INTEGER,
	    t1NetworkProfile-LineInterface-GroupBAnswerSignal
		INTEGER,
	    t1NetworkProfile-LineInterface-GroupBBusySignal
		INTEGER,
	    t1NetworkProfile-LineInterface-GroupBNoMatchSignal
		INTEGER,
	    t1NetworkProfile-LineInterface-GroupBCollectSignal
		INTEGER,
	    t1NetworkProfile-LineInterface-GroupBNoChargeSignal
		INTEGER,
	    t1NetworkProfile-LineInterface-GroupIiSignal
		INTEGER,
	    t1NetworkProfile-LineInterface-InputSampleCount
		INTEGER,
	    t1NetworkProfile-LineInterface-AnswerDelay
		INTEGER,
	    t1NetworkProfile-LineInterface-CallerId
		INTEGER,
	    t1NetworkProfile-LineInterface-LineSignaling
		INTEGER,
	    t1NetworkProfile-LineInterface-Timer1CollectCall
		INTEGER,
	    t1NetworkProfile-LineInterface-Timer2CollectCall
		INTEGER,
	    t1NetworkProfile-LineInterface-SendDiscVal
		INTEGER,
	    t1NetworkProfile-LineInterface-HuntGrpPhoneNumber1
		DisplayString,
	    t1NetworkProfile-LineInterface-HuntGrpPhoneNumber2
		DisplayString,
	    t1NetworkProfile-LineInterface-HuntGrpPhoneNumber3
		DisplayString,
	    t1NetworkProfile-LineInterface-PriTypeOfNumber
		INTEGER,
	    t1NetworkProfile-LineInterface-PriNumberingPlanId
		INTEGER,
	    t1NetworkProfile-LineInterface-SuperFrameSrcLineNumber
		INTEGER,
	    t1NetworkProfile-LineInterface-CollectIncomingDigits
		INTEGER,
	    t1NetworkProfile-LineInterface-T1InterDigitTimeout
		INTEGER,
	    t1NetworkProfile-LineInterface-R1UseAnir
		INTEGER,
	    t1NetworkProfile-LineInterface-R1FirstDigitTimer
		INTEGER,
	    t1NetworkProfile-LineInterface-R1AnirDelay
		INTEGER,
	    t1NetworkProfile-LineInterface-R1AnirTimer
		INTEGER,
	    t1NetworkProfile-LineInterface-R1Modified
		INTEGER,
	    t1NetworkProfile-LineInterface-FirstDs0
		INTEGER,
	    t1NetworkProfile-LineInterface-LastDs0
		INTEGER,
	    t1NetworkProfile-LineInterface-NailedGroup
		INTEGER,
	    t1NetworkProfile-LineInterface-Ss7Continuity-IncomingProcedure
		INTEGER,
	    t1NetworkProfile-LineInterface-Ss7Continuity-OutgoingProcedure
		INTEGER,
	    t1NetworkProfile-LineInterface-LineProvision
		INTEGER,
	    t1NetworkProfile-LineInterface-Gr303Mode
		INTEGER,
	    t1NetworkProfile-LineInterface-Gr303GroupId
		INTEGER,
	    t1NetworkProfile-LineInterface-Gr303Ds1Id
		INTEGER,
	    t1NetworkProfile-LineInterface-SwitchVersion
		INTEGER,
	    t1NetworkProfile-LineInterface-DownTransDelay
		INTEGER,
	    t1NetworkProfile-LineInterface-UpTransDelay
		INTEGER,
	    t1NetworkProfile-LineInterface-StatusChangeTrapEnable
		INTEGER,
	    t1NetworkProfile-LineInterface-CauseCodeVerificationEnable
		INTEGER,
	    t1NetworkProfile-BackToBack
		INTEGER,
	    t1NetworkProfile-ChannelUsage
		INTEGER,
	    t1NetworkProfile-Action-o
		INTEGER
	}

    t1NetworkProfile-Shelf-o	OBJECT-TYPE
	SYNTAX	INTEGER
	ACCESS	read-only
	STATUS	mandatory
	DESCRIPTION	""
	::= { mibt1NetworkProfileEntry 1 }

    t1NetworkProfile-Slot-o	OBJECT-TYPE
	SYNTAX	INTEGER
	ACCESS	read-only
	STATUS	mandatory
	DESCRIPTION	""
	::= { mibt1NetworkProfileEntry 2 }

    t1NetworkProfile-Item-o	OBJECT-TYPE
	SYNTAX	INTEGER
	ACCESS	read-only
	STATUS	mandatory
	DESCRIPTION	""
	::= { mibt1NetworkProfileEntry 3 }

    t1NetworkProfile-Name	OBJECT-TYPE
	SYNTAX	DisplayString
	ACCESS	read-write
	STATUS	mandatory
	DESCRIPTION	"Name of DS1 line."
	::= { mibt1NetworkProfileEntry 4 }

    t1NetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibt1NetworkProfileEntry 5 }

    t1NetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibt1NetworkProfileEntry 6 }

    t1NetworkProfile-PhysicalAddress-ItemNumber	OBJECT-TYPE
	SYNTAX	INTEGER
	ACCESS	read-write
	STATUS	mandatory
	DESCRIPTION	"A number that specifies an addressable entity within the context of shelf and slot."
	::= { mibt1NetworkProfileEntry 7 }

    t1NetworkProfile-LineInterface-Enabled	OBJECT-TYPE
	SYNTAX	INTEGER {
		    no (1),
		    yes (2)
		}
	ACCESS	read-write
	STATUS	mandatory
	DESCRIPTION	"TRUE if the line is enabled, otherwise FALSE."
	::= { mibt1NetworkProfileEntry 8 }

    t1NetworkProfile-LineInterface-TOnlineType	OBJECT-TYPE
	SYNTAX	INTEGER {
		    none (1),
		    nt (2),
		    te (3),
		    numberOfTonline (4)
		}
	ACCESS	read-write
	STATUS	mandatory
	DESCRIPTION	"The tonline type of an e1 line."
	::= { mibt1NetworkProfileEntry 9 }

    t1NetworkProfile-LineInterface-FrameType	OBJECT-TYPE
	SYNTAX	INTEGER {
		    d4 (1),
		    esf (2),
		    g703 (3),
		    n-2ds (4)
		}
	ACCESS	read-write
	STATUS	mandatory
	DESCRIPTION	"The super-framing mode that is used on the physical link(s)."
	::= { mibt1NetworkProfileEntry 10 }

    t1NetworkProfile-LineInterface-Encoding	OBJECT-TYPE
	SYNTAX	INTEGER {
		    ami (1),
		    b8zs (2),
		    hdb3 (3),
		    none (4)
		}
	ACCESS	read-write
	STATUS	mandatory
	DESCRIPTION	"The layer 1 line encoding used for the physical link(s)."
	::= { mibt1NetworkProfileEntry 11 }

    t1NetworkProfile-LineInterface-ClockSource	OBJECT-TYPE
	SYNTAX	INTEGER {
		    eligible (1),
		    notEligible (2)
		}
	ACCESS	read-write
	STATUS	mandatory
	DESCRIPTION	""
	::= { mibt1NetworkProfileEntry 12 }

    t1NetworkProfile-LineInterface-ClockPriority	OBJECT-TYPE
	SYNTAX	INTEGER {
		    highPriority (2),
		    middlePriority (3),
		    lowPriority (4)
		}
	ACCESS	read-write
	STATUS	mandatory
	DESCRIPTION	"Clock priority assigned to the T1 line. Used to select particular lines as clock source."
	::= { mibt1NetworkProfileEntry 13 }

    t1NetworkProfile-LineInterface-SignalingMode	OBJECT-TYPE
	SYNTAX	INTEGER {
		    inband (1),
		    isdn (2),
		    isdnNfas (3),
		    e1R2Signaling (5),
		    e1KoreanSignaling (6),
		    e1P7Signaling (7),
		    e1ChineseSignaling (8),
		    e1MeteredSignaling (9),
		    e1NoSignaling (10),
		    e1DpnssSignaling (11),
		    e1ArgentinaSignaling (13),
		    e1BrazilSignaling (14),
		    e1PhilippineSignaling (15),
		    e1IndianSignaling (16),
		    e1CzechSignaling (17),
		    e1MalaysiaSignaling (19),
		    e1NewZealandSignaling (20),
		    e1IsraelSignaling (21),
		    e1ThailandSignaling (22),
		    e1KuwaitSignaling (23),
		    e1MexicoSignaling (24),
		    dtmfR2Signaling (25),
		    tunneledPriSignaling (27),
		    inbandFgdInFgdOut (28),
		    inbandFgdInFgcOut (29),
		    inbandFgcInFgcOut (30),
		    inbandFgcInFgdOut (31),
		    e1VietnamSignaling (32),
		    ss7SigTrunk (33),
		    h248DataTrunk (34)
		}
	ACCESS	read-write
	STATUS	mandatory
	DESCRIPTION	"Inband, ISDN, ISDN_NFAS, PBX or SS7 signaling."
	::= { mibt1NetworkProfileEntry 14 }

    t1NetworkProfile-LineInterface-IsdnEmulationSide	OBJECT-TYPE
	SYNTAX	INTEGER {
		    te (1),
		    nt (2)
		}
	ACCESS	read-write
	STATUS	mandatory
	DESCRIPTION	"Side the line will emulate: TE (user), or NT (network)."
	::= { mibt1NetworkProfileEntry 15 }

    t1NetworkProfile-LineInterface-RobbedBitMode	OBJECT-TYPE
	SYNTAX	INTEGER {
		    winkStart (1),
		    idleStart (2),
		    incW200 (3),
		    incW400 (4),
		    loopStart (5),
		    groundStart (6)
		}
	ACCESS	read-write
	STATUS	mandatory
	DESCRIPTION	"Wink start, idle start, incoming wink."
	::= { mibt1NetworkProfileEntry 16 }

    t1NetworkProfile-LineInterface-DefaultCallType	OBJECT-TYPE
	SYNTAX	INTEGER {
		    digital (1),
		    voice (2),
		    dnisOrVoice (3),
		    dnisOrDigital (4),
		    voip (5),
		    dnisOrVoip (6)
		}
	ACCESS	read-write
	STATUS	mandatory
	DESCRIPTION	"Specify the default call-type for incoming calls, for purposes of call routing and signalling."
	::= { mibt1NetworkProfileEntry 17 }

    t1NetworkProfile-LineInterface-SwitchType	OBJECT-TYPE
	SYNTAX	INTEGER {
		    attPri (1),
		    ntiPri (2),
		    globandPri (3),
		    japanPri (4),
		    vn3Pri (5),
		    onetr6Pri (6),
		    net5Pri (7),
		    danishPri (8),
		    australPri (9),
		    natIsdn2Pri (10),
		    taiwanPri (31),
		    isdxDpnss (11),
		    islxDpnss (12),
		    mercuryDpnss (13),
		    dass2 (14),
		    btSs7 (32),
		    unknownBri (15),
		    att5essBri (16),
		    dms100Nt1Bri (17),
		    nisdn1Bri (18),
		    vn2Bri (19),
		    btnr191Bri (20),
		    net3Bri (21),
		    ptpNet3Bri (22),
		    kddBri (23),
		    belgianBri (24),
		    australBri (25),
		    swissBri (26),
		    german1tr6Bri (27),
		    dutch1tr6Bri (28),
		    switchCas (29),
		    idslPtpBri (30)
		}
	ACCESS	read-write
	STATUS	mandatory
	DESCRIPTION	"The network switch type, needed for ISDN/NFAS signaling."
	::= { mibt1NetworkProfileEntry 18 }

    t1NetworkProfile-LineInterface-NfasGroupId	OBJECT-TYPE
	SYNTAX	INTEGER
	ACCESS	read-write
	STATUS	mandatory
	DESCRIPTION	"For NFAS lines: the nfas group id. Not used with robbed bit signaling."
	::= { mibt1NetworkProfileEntry 19 }

    t1NetworkProfile-LineInterface-NfasId	OBJECT-TYPE
	SYNTAX	INTEGER
	ACCESS	read-write
	STATUS	mandatory
	DESCRIPTION	"For NFAS lines: the interface id. For SS7 lines when Q.931+ control protocol is used: interface id. Not used with robbed bit signaling."
	::= { mibt1NetworkProfileEntry 20 }

    t1NetworkProfile-LineInterface-IncomingCallHandling	OBJECT-TYPE
	SYNTAX	INTEGER {
		    rejectAll (1),
		    internalProcessing (2),
		    ss7GatewayProcessing (3)
		}
	ACCESS	read-write
	STATUS	mandatory
	DESCRIPTION	"This parameter is used to determine the type of processing required for incoming calls from this line."
	::= { mibt1NetworkProfileEntry 21 }

    t1NetworkProfile-LineInterface-DeleteDigits	OBJECT-TYPE
	SYNTAX	INTEGER
	ACCESS	read-write
	STATUS	mandatory
	DESCRIPTION	"Number of digits to delete from numbers received from a PBX."
	::= { mibt1NetworkProfileEntry 22 }

    t1NetworkProfile-LineInterface-AddDigitString	OBJECT-TYPE
	SYNTAX	DisplayString
	ACCESS	read-write
	STATUS	mandatory
	DESCRIPTION	"String of digits to prepend to phone number received from PBX."
	::= { mibt1NetworkProfileEntry 23 }

    t1NetworkProfile-LineInterface-CallByCall	OBJECT-TYPE
	SYNTAX	INTEGER
	ACCESS	read-write
	STATUS	mandatory
	DESCRIPTION	"Call-by-call value to set when routing calls from PBX to network."
	::= { mibt1NetworkProfileEntry 24 }

    t1NetworkProfile-LineInterface-NetworkSpecificFacilities	OBJECT-TYPE
	SYNTAX	INTEGER
	ACCESS	read-write
	STATUS	mandatory
	DESCRIPTION	"Network Specific Facilities (NSF) value to store in the NSF IE of the outgoing Q.931 Setup message. This sets the full 8 bits of the IE."
	::= { mibt1NetworkProfileEntry 87 }

    t1NetworkProfile-LineInterface-PbxAnswerNumber	OBJECT-TYPE
	SYNTAX	DisplayString
	ACCESS	read-write
	STATUS	mandatory
	DESCRIPTION	"The answer number that is the equivalent of a port answer-number used for the network to pbx routing."
	::= { mibt1NetworkProfileEntry 25 }

    t1NetworkProfile-LineInterface-AnswerService	OBJECT-TYPE
	SYNTAX	INTEGER {
		    voice (1),
		    n-56kRestricted (2),
		    n-64kClear (3),
		    n-64kRestricted (4),
		    n-56kClear (5),
		    n-384kRestricted (6),
		    n-384kClear (7),
		    n-1536kClear (8),
		    n-1536kRestricted (9),
		    n-128kClear (10),
		    n-192kClear (11),
		    n-256kClear (12),
		    n-320kClear (13),
		    dws384Clear (14),
		    n-448Clear (15),
		    n-512Clear (16),
		    n-576Clear (17),
		    n-640Clear (18),
		    n-704Clear (19),
		    n-768Clear (20),
		    n-832Clear (21),
		    n-896Clear (22),
		    n-960Clear (23),
		    n-1024Clear (24),
		    n-1088Clear (25),
		    n-1152Clear (26),
		    n-1216Clear (27),
		    n-1280Clear (28),
		    n-1344Clear (29),
		    n-1408Clear (30),
		    n-1472Clear (31),
		    n-1600Clear (32),
		    n-1664Clear (33),
		    n-1728Clear (34),
		    n-1792Clear (35),
		    n-1856Clear (36),
		    n-1920Clear (37),
		    x30RestrictedBearer (39),
		    v110ClearBearer (40),
		    n-64kX30Restricted (41),
		    n-56kV110Clear (42),
		    modem (43),
		    atmodem (44),
		    n-2456kV110 (46),
		    n-4856kV110 (47),
		    n-9656kV110 (48),
		    n-19256kV110 (49),
		    n-38456kV110 (50),
		    n-2456krV110 (51),
		    n-4856krV110 (52),
		    n-9656krV110 (53),
		    n-19256krV110 (54),
		    n-38456krV110 (55),
		    n-2464kV110 (56),
		    n-4864kV110 (57),
		    n-9664kV110 (58),
		    n-19264kV110 (59),
		    n-38464kV110 (60),
		    n-2464krV110 (61),
		    n-4864krV110 (62),
		    n-9664krV110 (63),
		    n-19264krV110 (64),
		    n-38464krV110 (65),
		    v32 (66),
		    phs64k (67),
		    voiceOverIp (68),
		    atmSvc (70),
		    frameRelaySvc (71),
		    vpnTunnel (72),
		    wormarq (73),
		    n-14456kV110 (74),
		    n-28856kV110 (75),
		    n-14456krV110 (76),
		    n-28856krV110 (77),
		    n-14464kV110 (78),
		    n-28864kV110 (79),
		    n-14464krV110 (80),
		    n-28864krV110 (81),
		    modem31khzAudio (82),
		    x25Svc (83),
		    n-144kClear (255),
		    iptoip (263)
		}
	ACCESS	read-write
	STATUS	mandatory
	DESCRIPTION	"The switched service type (or none) that is used for routing network calls to the pbx."
	::= { mibt1NetworkProfileEntry 26 }

    t1NetworkProfile-LineInterface-oPBXType	OBJECT-TYPE
	SYNTAX	INTEGER {
		    hostPbxVoice (1),
		    hostPbxData (2),
		    hostPbxLeasedData (3),
		    hostPbxLeased11 (4)
		}
	ACCESS	read-write
	STATUS	mandatory
	DESCRIPTION	"The PBX Class as defined in the enumeration above."
	::= { mibt1NetworkProfileEntry 27 }

    t1NetworkProfile-LineInterface-DataSense	OBJECT-TYPE
	SYNTAX	INTEGER {
		    normal (1),
		    inv (2)
		}
	ACCESS	read-write
	STATUS	mandatory
	DESCRIPTION	"D-channel normal or inverted data. Currently unused (normal data is always selected."
	::= { mibt1NetworkProfileEntry 28 }

    t1NetworkProfile-LineInterface-IdleMode	OBJECT-TYPE
	SYNTAX	INTEGER {
		    markIdle (1),
		    flagIdle (2)
		}
	ACCESS	read-write
	STATUS	mandatory
	DESCRIPTION	"D-channel mark or flag idle. Currently unused (flag idle is always selected."
	::= { mibt1NetworkProfileEntry 29 }

    t1NetworkProfile-LineInterface-oFDL	OBJECT-TYPE
	SYNTAX	INTEGER {
		    none (1),
		    atNT (2),
		    ansi (3),
		    sprint (4)
		}
	ACCESS	read-write
	STATUS	mandatory
	DESCRIPTION	"Who's FDL are we using. Used only if frame-type is ESF - Ignored otherwise."
	::= { mibt1NetworkProfileEntry 30 }

    t1NetworkProfile-LineInterface-FrontEndType	OBJECT-TYPE
	SYNTAX	INTEGER {
		    csu (1),
		    dsx (2)
		}
	ACCESS	read-write
	STATUS	mandatory
	DESCRIPTION	"The front end type (CSU/DSX) of the T1 transceiver."
	::= { mibt1NetworkProfileEntry 31 }

    t1NetworkProfile-LineInterface-oDSXLineLength	OBJECT-TYPE
	SYNTAX	INTEGER {
		    n-1133 (1),
		    n-134266 (2),
		    n-267399 (3),
		    n-400533 (4),
		    n-534655 (5)
		}
	ACCESS	read-write
	STATUS	mandatory
	DESCRIPTION	"The length of the physical T1 line (for DSX lines)."
	::= { mibt1NetworkProfileEntry 32 }

    t1NetworkProfile-LineInterface-oCSUBuildOut	OBJECT-TYPE
	SYNTAX	INTEGER {
		    n-0Db (1),
		    n-75Db (2),
		    n-15Db (3),
		    n-2255Db (4)
		}
	ACCESS	read-write
	STATUS	mandatory
	DESCRIPTION	"Line buildout value for CSU lines."
	::= { mibt1NetworkProfileEntry 33 }

    t1NetworkProfile-LineInterface-OverlapReceiving	OBJECT-TYPE
	SYNTAX	INTEGER {
		    no (1),
		    yes (2)
		}
	ACCESS	read-write
	STATUS	mandatory
	DESCRIPTION	"TRUE if overlap receiving procedure may be used to handle incoming call, FALSE if not"
	::= { mibt1NetworkProfileEntry 34 }

    t1NetworkProfile-LineInterface-PriPrefixNumber	OBJECT-TYPE
	SYNTAX	DisplayString
	ACCESS	read-write
	STATUS	mandatory
	DESCRIPTION	"The unique prefix of the PRI called party number. It is used to determine whether SETUP message contains any trailing digits when overlap receiving procedure is used to handle the incoming call. Defaults to '' to not count the trailing digits."
	::= { mibt1NetworkProfileEntry 35 }

    t1NetworkProfile-LineInterface-TrailingDigits	OBJECT-TYPE
	SYNTAX	INTEGER
	ACCESS	read-write
	STATUS	mandatory
	DESCRIPTION	"Number of trailing digits expected from the called party number information elements of INFORMATION messages when overlap receiving procedure is used to handle the incoming call. SETUP message may contain some trailing digits in the called party number information element. Defaults to 2."
	::= { mibt1NetworkProfileEntry 36 }

    t1NetworkProfile-LineInterface-T302Timer	OBJECT-TYPE
	SYNTAX	INTEGER
	ACCESS	read-write
	STATUS	mandatory
	DESCRIPTION	"Number of milliseconds to wait for additional called number information elements for an incoming call using overlap receiving procedure. Defaults to 10000."
	::= { mibt1NetworkProfileEntry 37 }

    t1NetworkProfile-LineInterface-Layer3End	OBJECT-TYPE
	SYNTAX	INTEGER {
		    false (1),
		    true (2)
		}
	ACCESS	read-write
	STATUS	mandatory
	DESCRIPTION	"If x-side, layer 3 favors outgoing call when a call collision occurs."
	::= { mibt1NetworkProfileEntry 38 }

    t1NetworkProfile-LineInterface-Layer2End	OBJECT-TYPE
	SYNTAX	INTEGER {
		    false (1),
		    true (2)
		}
	ACCESS	read-write
	STATUS	mandatory
	DESCRIPTION	"This parameter is used to determine the address to send when two PBXs are connected back-to-back; one side must act as an ET, and the other side acts as a PBX. If a-side, layer 2 acts as ET."
	::= { mibt1NetworkProfileEntry 39 }

    t1NetworkProfile-LineInterface-NlValue	OBJECT-TYPE
	SYNTAX	INTEGER
	ACCESS	read-write
	STATUS	mandatory
	DESCRIPTION	"Number of re-transmissions; default to 64."
	::= { mibt1NetworkProfileEntry 40 }

    t1NetworkProfile-LineInterface-LoopAvoidance	OBJECT-TYPE
	SYNTAX	INTEGER
	ACCESS	read-write
	STATUS	mandatory
	DESCRIPTION	"Loop Avoidance; the number of transit PBXs through which a call may be routed (1 to 26 default 7)."
	::= { mibt1NetworkProfileEntry 41 }

    t1NetworkProfile-LineInterface-MaintenanceState	OBJECT-TYPE
	SYNTAX	INTEGER {
		    no (1),
		    yes (2)
		}
	ACCESS	read-write
	STATUS	mandatory
	DESCRIPTION	"TRUE if the line is in user-requested maintenance mode, otherwise FALSE."
	::= { mibt1NetworkProfileEntry 42 }

    t1NetworkProfile-LineInterface-NumberComplete	OBJECT-TYPE
	SYNTAX	INTEGER {
		    n-1Digits (1),
		    n-2Digits (2),
		    n-3Digits (3),
		    n-4Digits (4),
		    n-5Digits (5),
		    n-6Digits (6),
		    n-7Digits (7),
		    n-8Digits (8),
		    n-9Digits (9),
		    n-10Digits (10),
		    endOfPulsing (11),
		    n-0Digits (12),
		    n-11Digits (13),
		    n-12Digits (14),
		    n-13Digits (15),
		    n-14Digits (16),
		    n-15Digits (17),
		    timeOut (18)
		}
	ACCESS	read-write
	STATUS	mandatory
	DESCRIPTION	"The criteria for having received enough digits on an incoming R2 call. Can either be 1, 2, 3, 4, 5, 6, 7, 8, 9, 10, 11, 12 13, 14, or 15 digits received, or the end-of-pulsing signal received, or time-out."
	::= { mibt1NetworkProfileEntry 43 }

    t1NetworkProfile-LineInterface-GroupBAnswerSignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send prior to answering a call."
	::= { mibt1NetworkProfileEntry 44 }

    t1NetworkProfile-LineInterface-GroupBBusySignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send to reject a call."
	::= { mibt1NetworkProfileEntry 45 }

    t1NetworkProfile-LineInterface-GroupBNoMatchSignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send to reject a call with invalid call number."
	::= { mibt1NetworkProfileEntry 46 }

    t1NetworkProfile-LineInterface-GroupBCollectSignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send to answer/reject a collect call."
	::= { mibt1NetworkProfileEntry 47 }

    t1NetworkProfile-LineInterface-GroupBNoChargeSignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send if subscriber line is idle / no charge"
	::= { mibt1NetworkProfileEntry 82 }

    t1NetworkProfile-LineInterface-GroupIiSignal	OBJECT-TYPE
	SYNTAX	INTEGER {
		    signalIi1 (1),
		    signalIi2 (2),
		    signalIi3 (3),
		    signalIi4 (4),
		    signalIi5 (5),
		    signalIi6 (6),
		    signalIi7 (7),
		    signalIi8 (8),
		    signalIi9 (9),
		    signalIi10 (10),
		    signalIi11 (11),
		    signalIi12 (12),
		    signalIi13 (13),
		    signalIi14 (14),
		    signalIi15 (15)
		}
	ACCESS	read-write
	STATUS	mandatory
	DESCRIPTION	"The group II signal to send after sending all address digits."
	::= { mibt1NetworkProfileEntry 48 }

    t1NetworkProfile-LineInterface-InputSampleCount	OBJECT-TYPE
	SYNTAX	INTEGER {
		    oneSample (1),
		    twoSamples (2)
		}
	ACCESS	read-write
	STATUS	mandatory
	DESCRIPTION	"The number of Goertzel input samples (each Goertzel sample is of length N=205) to compute in order to decode DTMF tones, the more samples, the more acccurate the detection result"
	::= { mibt1NetworkProfileEntry 49 }

    t1NetworkProfile-LineInterface-AnswerDelay	OBJECT-TYPE
	SYNTAX	INTEGER
	ACCESS	read-write
	STATUS	mandatory
	DESCRIPTION	"Number of milliseconds to wait before answering an incoming R2 call."
	::= { mibt1NetworkProfileEntry 50 }

    t1NetworkProfile-LineInterface-CallerId	OBJECT-TYPE
	SYNTAX	INTEGER {
		    noCallerId (1),
		    getCallerId (2)
		}
	ACCESS	read-write
	STATUS	mandatory
	DESCRIPTION	"TRUE if the caller Id is enabled, otherwise FALSE."
	::= { mibt1NetworkProfileEntry 51 }

    t1NetworkProfile-LineInterface-LineSignaling	OBJECT-TYPE
	SYNTAX	INTEGER {
		    abBitsLineSignaling (1),
		    aBitOnly0EqualBBit (2),
		    aBitOnly1EqualBBit (3)
		}
	ACCESS	read-write
	STATUS	mandatory
	DESCRIPTION	"The line signaling of E1 line."
	::= { mibt1NetworkProfileEntry 52 }

    t1NetworkProfile-LineInterface-Timer1CollectCall	OBJECT-TYPE
	SYNTAX	INTEGER
	ACCESS	read-write
	STATUS	mandatory
	DESCRIPTION	"Adjustable between 0 ~ 2000ms"
	::= { mibt1NetworkProfileEntry 53 }

    t1NetworkProfile-LineInterface-Timer2CollectCall	OBJECT-TYPE
	SYNTAX	INTEGER
	ACCESS	read-write
	STATUS	mandatory
	DESCRIPTION	"Adjustable between 10 ~ 2000ms"
	::= { mibt1NetworkProfileEntry 54 }

    t1NetworkProfile-LineInterface-SendDiscVal	OBJECT-TYPE
	SYNTAX	INTEGER
	ACCESS	read-write
	STATUS	mandatory
	DESCRIPTION	"Number of seconds before sending ISDN disconnect to switch. 0 means disable."
	::= { mibt1NetworkProfileEntry 55 }

    t1NetworkProfile-LineInterface-HuntGrpPhoneNumber1	OBJECT-TYPE
	SYNTAX	DisplayString
	ACCESS	read-write
	STATUS	mandatory
	DESCRIPTION	"The hunt group phone number associated with this line. Manually entered field which is read-write accessible via SNMP."
	::= { mibt1NetworkProfileEntry 56 }

    t1NetworkProfile-LineInterface-HuntGrpPhoneNumber2	OBJECT-TYPE
	SYNTAX	DisplayString
	ACCESS	read-write
	STATUS	mandatory
	DESCRIPTION	"The hunt group phone number associated with this line. Manually entered field which is read-write accessible via SNMP."
	::= { mibt1NetworkProfileEntry 57 }

    t1NetworkProfile-LineInterface-HuntGrpPhoneNumber3	OBJECT-TYPE
	SYNTAX	DisplayString
	ACCESS	read-write
	STATUS	mandatory
	DESCRIPTION	"The hunt group phone number associated with this line. Manually entered field which is read-write accessible via SNMP."
	::= { mibt1NetworkProfileEntry 58 }

    t1NetworkProfile-LineInterface-PriTypeOfNumber	OBJECT-TYPE
	SYNTAX	INTEGER
	ACCESS	read-write
	STATUS	mandatory
	DESCRIPTION	"PRI Called Party element's Type-Of-Number value for outgoing T1-to-PRI calls."
	::= { mibt1NetworkProfileEntry 59 }

    t1NetworkProfile-LineInterface-PriNumberingPlanId	OBJECT-TYPE
	SYNTAX	INTEGER
	ACCESS	read-write
	STATUS	mandatory
	DESCRIPTION	"PRI Called Party element's Numbering-Plan-ID value for outgoing T1-to-PRI calls."
	::= { mibt1NetworkProfileEntry 60 }

    t1NetworkProfile-LineInterface-SuperFrameSrcLineNumber	OBJECT-TYPE
	SYNTAX	INTEGER
	ACCESS	read-write
	STATUS	mandatory
	DESCRIPTION	"The line from which the the Super-Frame sync pulse is taken. Needed by the 'Dropped&Inserted' line so that it can become synchronized to the source line."
	::= { mibt1NetworkProfileEntry 61 }

    t1NetworkProfile-LineInterface-CollectIncomingDigits	OBJECT-TYPE
	SYNTAX	INTEGER {
		    no (1),
		    yes (2)
		}
	ACCESS	read-write
	STATUS	mandatory
	DESCRIPTION	"TRUE collect incoming called/calling digits, otherwise FALSE."
	::= { mibt1NetworkProfileEntry 62 }

    t1NetworkProfile-LineInterface-T1InterDigitTimeout	OBJECT-TYPE
	SYNTAX	INTEGER
	ACCESS	read-write
	STATUS	mandatory
	DESCRIPTION	"Inter-Digit Timeout (in milliseconds) for inband T1 and E1 R2 lines."
	::= { mibt1NetworkProfileEntry 63 }

    t1NetworkProfile-LineInterface-R1UseAnir	OBJECT-TYPE
	SYNTAX	INTEGER {
		    no (1),
		    yes (2)
		}
	ACCESS	read-write
	STATUS	mandatory
	DESCRIPTION	"TRUE if the line is to use R1 signaling ANIR (CLID), otherwise FALSE."
	::= { mibt1NetworkProfileEntry 64 }

    t1NetworkProfile-LineInterface-R1FirstDigitTimer	OBJECT-TYPE
	SYNTAX	INTEGER
	ACCESS	read-write
	STATUS	mandatory
	DESCRIPTION	"The timer between sending KPA and receiving first Digit in R1 signaling in milliseconds."
	::= { mibt1NetworkProfileEntry 65 }

    t1NetworkProfile-LineInterface-R1AnirDelay	OBJECT-TYPE
	SYNTAX	INTEGER
	ACCESS	read-write
	STATUS	mandatory
	DESCRIPTION	"Delay in milliseconds between receiving ST and sending ANIR signal."
	::= { mibt1NetworkProfileEntry 66 }

    t1NetworkProfile-LineInterface-R1AnirTimer	OBJECT-TYPE
	SYNTAX	INTEGER
	ACCESS	read-write
	STATUS	mandatory
	DESCRIPTION	"Time in milliseconds of ANIR signal."
	::= { mibt1NetworkProfileEntry 67 }

    t1NetworkProfile-LineInterface-R1Modified	OBJECT-TYPE
	SYNTAX	INTEGER {
		    no (1),
		    yes (2)
		}
	ACCESS	read-write
	STATUS	mandatory
	DESCRIPTION	"Use R1 modified signaling. Default is FALSE."
	::= { mibt1NetworkProfileEntry 68 }

    t1NetworkProfile-LineInterface-FirstDs0	OBJECT-TYPE
	SYNTAX	INTEGER
	ACCESS	read-write
	STATUS	mandatory
	DESCRIPTION	"When using fractional T1/E1 the first DS0 used. Default is 1"
	::= { mibt1NetworkProfileEntry 69 }

    t1NetworkProfile-LineInterface-LastDs0	OBJECT-TYPE
	SYNTAX	INTEGER
	ACCESS	read-write
	STATUS	mandatory
	DESCRIPTION	"When using fractional T1/E1 the last DS0 used. Default is 24"
	::= { mibt1NetworkProfileEntry 70 }

    t1NetworkProfile-LineInterface-NailedGroup	OBJECT-TYPE
	SYNTAX	INTEGER
	ACCESS	read-write
	STATUS	mandatory
	DESCRIPTION	"A number that identifies the set of lines that makes up a nailed group. 0 means this line is not part of a nailed group."
	::= { mibt1NetworkProfileEntry 71 }

    t1NetworkProfile-LineInterface-Ss7Continuity-IncomingProcedure	OBJECT-TYPE
	SYNTAX	INTEGER {
		    loopback (2),
		    transponder (3)
		}
	ACCESS	read-write
	STATUS	mandatory
	DESCRIPTION	"Procedure used for incoming continuity check on this line."
	::= { mibt1NetworkProfileEntry 72 }

    t1NetworkProfile-LineInterface-Ss7Continuity-OutgoingProcedure	OBJECT-TYPE
	SYNTAX	INTEGER {
		    singleTone2010 (2),
		    send2010Expect1780 (3),
		    send1780Expect2010 (4),
		    singleTone2000 (5),
		    send2000Expect1780 (6),
		    send1780Expect2000 (7)
		}
	ACCESS	read-write
	STATUS	mandatory
	DESCRIPTION	"Procedure used for outgoing continuity check on this line."
	::= { mibt1NetworkProfileEntry 73 }

    t1NetworkProfile-LineInterface-LineProvision	OBJECT-TYPE
	SYNTAX	INTEGER {
		    lineProvisionNone (1),
		    lineProvisionH0 (2),
		    lineProvisionH11 (3),
		    lineProvisionH0H11 (4),
		    lineProvisionH12 (5),
		    lineProvisionH0H12 (6),
		    lineProvisionH11H12 (7),
		    lineProvisionH0H11H12 (8)
		}
	ACCESS	read-write
	STATUS	mandatory
	DESCRIPTION	"Line Provision."
	::= { mibt1NetworkProfileEntry 74 }

    t1NetworkProfile-LineInterface-Gr303Mode	OBJECT-TYPE
	SYNTAX	INTEGER {
		    gr303Disabled (1),
		    gr3035essPri (2),
		    gr303DmsPri (3),
		    gr303Secondary (4),
		    gr303Normal (5)
		}
	ACCESS	read-write
	STATUS	mandatory
	DESCRIPTION	"GR-303 Mode."
	::= { mibt1NetworkProfileEntry 75 }

    t1NetworkProfile-LineInterface-Gr303GroupId	OBJECT-TYPE
	SYNTAX	INTEGER
	ACCESS	read-write
	STATUS	mandatory
	DESCRIPTION	"For GR303 lines: the interface group id."
	::= { mibt1NetworkProfileEntry 76 }

    t1NetworkProfile-LineInterface-Gr303Ds1Id	OBJECT-TYPE
	SYNTAX	INTEGER
	ACCESS	read-write
	STATUS	mandatory
	DESCRIPTION	"For GR303 lines: The logical DS1 id."
	::= { mibt1NetworkProfileEntry 77 }

    t1NetworkProfile-LineInterface-SwitchVersion	OBJECT-TYPE
	SYNTAX	INTEGER {
		    switchVersionGeneric (1),
		    switchVersionDefinityG3v4 (2)
		}
	ACCESS	read-write
	STATUS	mandatory
	DESCRIPTION	"Switch Version."
	::= { mibt1NetworkProfileEntry 78 }

    t1NetworkProfile-LineInterface-DownTransDelay	OBJECT-TYPE
	SYNTAX	INTEGER
	ACCESS	read-write
	STATUS	mandatory
	DESCRIPTION	"To control the delay in line state transition from up to down when loss of carrier is detected. Each unit of this value is equal to .1 seconds of Delay in UP to DOWN transition."
	::= { mibt1NetworkProfileEntry 84 }

    t1NetworkProfile-LineInterface-UpTransDelay	OBJECT-TYPE
	SYNTAX	INTEGER
	ACCESS	read-write
	STATUS	mandatory
	DESCRIPTION	"To control the delay in line state transition from down to up when carrier is detected. Each unit of this value is equal to .1 seconds of Delay in DOWN to UP transition."
	::= { mibt1NetworkProfileEntry 85 }

    t1NetworkProfile-LineInterface-StatusChangeTrapEnable	OBJECT-TYPE
	SYNTAX	INTEGER {
		    no (1),
		    yes (2)
		}
	ACCESS	read-write
	STATUS	mandatory
	DESCRIPTION	"When set to yes, a line status change trap is sent. NOTE: when the line status change results from a higher level line status change, i.e., ds3, then no trap for the ds1 are sent. The default setting is No."
	::= { mibt1NetworkProfileEntry 83 }

    t1NetworkProfile-LineInterface-CauseCodeVerificationEnable	OBJECT-TYPE
	SYNTAX	INTEGER {
		    no (1),
		    yes (2)
		}
	ACCESS	read-write
	STATUS	mandatory
	DESCRIPTION	"When set to yes, the received CAUSE value will be verified to ensure that cause is defined for the configured switch type. If the switch does not support the cause code, then INVALID ELEM CONTENTS (Cause value 100) will be used for generating PSTN Q931 response. When set to no, the received CAUSE value will be used to generate the PSTN Q931 response."
	::= { mibt1NetworkProfileEntry 88 }

    t1NetworkProfile-BackToBack	OBJECT-TYPE
	SYNTAX	INTEGER {
		    false (1),
		    true (2)
		}
	ACCESS	read-write
	STATUS	mandatory
	DESCRIPTION	"Indicates whether the Multiband is connected back-to-back to another Muliband, rather than a DPNSS PBX. If this field is TRUE, than we don't need to disable receiving interrupts when too many are coming in beyond our processing power. NOTE: GPT's iSDX keeps re-transmitting a frame at 8 ms intervals until it receives an acknowledgement."
	::= { mibt1NetworkProfileEntry 79 }

    t1NetworkProfile-ChannelUsage	OBJECT-TYPE
	SYNTAX	INTEGER {
		    lineUnavailable (1),
		    lineDisable (2),
		    t1LineQuiesce (3),
		    dropAndInsert (4),
		    dualNetworkInterface (5),
		    tOnlineUsrInterface (6),
		    tOnlineZgrInterface (7)
		}
	ACCESS	read-write
	STATUS	mandatory
	DESCRIPTION	"This is the use of the first T1 interface."
	::= { mibt1NetworkProfileEntry 80 }

    t1NetworkProfile-Action-o	OBJECT-TYPE
	SYNTAX	INTEGER {
		    noAction (1),
		    createProfile (2),
		    deleteProfile (3)
		}
	ACCESS	read-write
	STATUS	mandatory
	DESCRIPTION	""
	::= { mibt1NetworkProfileEntry 81 }


	-- The mibt1NetworkProfile__line_interface__channel_config table
	--
	-- This table contains parameters for the mibt1NetworkProfile__line_interface__channel_config profile
	--

    mibt1NetworkProfile-LineInterface-ChannelConfigTable	OBJECT-TYPE
	SYNTAX		SEQUENCE OF Mibt1NetworkProfile-LineInterface-ChannelConfigEntry
	ACCESS		not-accessible
	STATUS		mandatory
	DESCRIPTION	"A list of mibt1NetworkProfile__line_interface__channel_config profile entries."
	::= { mibt1NetworkProfile 2 }

    mibt1NetworkProfile-LineInterface-ChannelConfigEntry	OBJECT-TYPE
	SYNTAX		Mibt1NetworkProfile-LineInterface-ChannelConfigEntry
	ACCESS		not-accessible
	STATUS		mandatory
	DESCRIPTION	"A mibt1NetworkProfile__line_interface__channel_config entry containing objects that
			 maps to the parameters of mibt1NetworkProfile__line_interface__channel_config profile."
	INDEX		{ t1NetworkProfile-LineInterface-ChannelConfig-Shelf-o, t1NetworkProfile-LineInterface-ChannelConfig-Slot-o, t1NetworkProfile-LineInterface-ChannelConfig-Item-o, t1NetworkProfile-LineInterface-ChannelConfig-Index-o }
	::= { mibt1NetworkProfile-LineInterface-ChannelConfigTable 1 }

    Mibt1NetworkProfile-LineInterface-ChannelConfigEntry ::=
	SEQUENCE {
	    t1NetworkProfile-LineInterface-ChannelConfig-Shelf-o
		INTEGER,
	    t1NetworkProfile-LineInterface-ChannelConfig-Slot-o
		INTEGER,
	    t1NetworkProfile-LineInterface-ChannelConfig-Item-o
		INTEGER,
	    t1NetworkProfile-LineInterface-ChannelConfig-Index-o
		INTEGER,
	    t1NetworkProfile-LineInterface-ChannelConfig-ChannelUsage
		INTEGER,
	    t1NetworkProfile-LineInterface-ChannelConfig-TrunkGroup
		INTEGER,
	    t1NetworkProfile-LineInterface-ChannelConfig-PhoneNumber
		DisplayString,
	    t1NetworkProfile-LineInterface-ChannelConfig-RoutePort-SlotNumber-SlotNumber
		INTEGER,
	    t1NetworkProfile-LineInterface-ChannelConfig-RoutePort-SlotNumber-ShelfNumber
		INTEGER,
	    t1NetworkProfile-LineInterface-ChannelConfig-RoutePort-RelativePortNumber-RelativePortNumber
		INTEGER,
	    t1NetworkProfile-LineInterface-ChannelConfig-NailedGroup
		INTEGER,
	    t1NetworkProfile-LineInterface-ChannelConfig-ChanGroup
		INTEGER,
	    t1NetworkProfile-LineInterface-ChannelConfig-DestChanGroup
		INTEGER,
	    t1NetworkProfile-LineInterface-ChannelConfig-DialPlanNumber
		INTEGER,
	    t1NetworkProfile-LineInterface-ChannelConfig-NumberOfDialPlanSelectDigits
		INTEGER,
	    t1NetworkProfile-LineInterface-ChannelConfig-IdlePattern
		INTEGER
	}

    t1NetworkProfile-LineInterface-ChannelConfig-Shelf-o	OBJECT-TYPE
	SYNTAX	INTEGER
	ACCESS	read-only
	STATUS	mandatory
	DESCRIPTION	""
	::= { mibt1NetworkProfile-LineInterface-ChannelConfigEntry 1 }

    t1NetworkProfile-LineInterface-ChannelConfig-Slot-o	OBJECT-TYPE
	SYNTAX	INTEGER
	ACCESS	read-only
	STATUS	mandatory
	DESCRIPTION	""
	::= { mibt1NetworkProfile-LineInterface-ChannelConfigEntry 2 }

    t1NetworkProfile-LineInterface-ChannelConfig-Item-o	OBJECT-TYPE
	SYNTAX	INTEGER
	ACCESS	read-only
	STATUS	mandatory
	DESCRIPTION	""
	::= { mibt1NetworkProfile-LineInterface-ChannelConfigEntry 3 }

    t1NetworkProfile-LineInterface-ChannelConfig-Index-o	OBJECT-TYPE
	SYNTAX	INTEGER
	ACCESS	read-only
	STATUS	mandatory
	DESCRIPTION	""
	::= { mibt1NetworkProfile-LineInterface-ChannelConfigEntry 4 }

    t1NetworkProfile-LineInterface-ChannelConfig-ChannelUsage	OBJECT-TYPE
	SYNTAX	INTEGER {
		    unusedChannel (1),
		    switchedChannel (2),
		    nailed64Channel (3),
		    dChannel (4),
		    nfasPrimaryDChannel (5),
		    nfasSecondaryDChannel (6),
		    semiPermChannel (7),
		    ss7SignalingChannel (8)
		}
	ACCESS	read-write
	STATUS	mandatory
	DESCRIPTION	"The usage for this specific channel. May be different than the usage for the line, e.g. a nailed channel (clear 64) in a line otherwise used for switched calls."
	::= { mibt1NetworkProfile-LineInterface-ChannelConfigEntry 5 }

    t1NetworkProfile-LineInterface-ChannelConfig-TrunkGroup	OBJECT-TYPE
	SYNTAX	INTEGER
	ACCESS	read-write
	STATUS	mandatory
	DESCRIPTION	"The trunk group assigned to this channel."
	::= { mibt1NetworkProfile-LineInterface-ChannelConfigEntry 6 }

    t1NetworkProfile-LineInterface-ChannelConfig-PhoneNumber	OBJECT-TYPE
	SYNTAX	DisplayString
	ACCESS	read-write
	STATUS	mandatory
	DESCRIPTION	"The phone number of this channel. This is the number sent to the far end in an inverse multiplexed call when instructing the far end to add more bandwidth. The number should contain the minimum number of digits to identify the channel. If the channel is part of a hunt group, the phone number should be blank."
	::= { mibt1NetworkProfile-LineInterface-ChannelConfigEntry 7 }

    t1NetworkProfile-LineInterface-ChannelConfig-RoutePort-SlotNumber-SlotNumber	OBJECT-TYPE
	SYNTAX	INTEGER
	ACCESS	read-write
	STATUS	mandatory
	DESCRIPTION	""
	::= { mibt1NetworkProfile-LineInterface-ChannelConfigEntry 8 }

    t1NetworkProfile-LineInterface-ChannelConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibt1NetworkProfile-LineInterface-ChannelConfigEntry 9 }

    t1NetworkProfile-LineInterface-ChannelConfig-RoutePort-RelativePortNumber-RelativePortNumber	OBJECT-TYPE
	SYNTAX	INTEGER
	ACCESS	read-write
	STATUS	mandatory
	DESCRIPTION	""
	::= { mibt1NetworkProfile-LineInterface-ChannelConfigEntry 10 }

    t1NetworkProfile-LineInterface-ChannelConfig-NailedGroup	OBJECT-TYPE
	SYNTAX	INTEGER
	ACCESS	read-write
	STATUS	mandatory
	DESCRIPTION	"A number that identifies the set of channels that makes up a nailed group."
	::= { mibt1NetworkProfile-LineInterface-ChannelConfigEntry 14 }

    t1NetworkProfile-LineInterface-ChannelConfig-ChanGroup	OBJECT-TYPE
	SYNTAX	INTEGER
	ACCESS	read-write
	STATUS	mandatory
	DESCRIPTION	"A number that identifies the channel-group to which this channel belongs."
	::= { mibt1NetworkProfile-LineInterface-ChannelConfigEntry 15 }

    t1NetworkProfile-LineInterface-ChannelConfig-DestChanGroup	OBJECT-TYPE
	SYNTAX	INTEGER
	ACCESS	read-write
	STATUS	mandatory
	DESCRIPTION	"A number that identifies the channel-group to which any incoming calls on this channel will be directed."
	::= { mibt1NetworkProfile-LineInterface-ChannelConfigEntry 16 }

    t1NetworkProfile-LineInterface-ChannelConfig-DialPlanNumber	OBJECT-TYPE
	SYNTAX	INTEGER
	ACCESS	read-write
	STATUS	mandatory
	DESCRIPTION	"A number that identifies the dial plan from the dial plan menu."
	::= { mibt1NetworkProfile-LineInterface-ChannelConfigEntry 17 }

    t1NetworkProfile-LineInterface-ChannelConfig-NumberOfDialPlanSelectDigits	OBJECT-TYPE
	SYNTAX	INTEGER
	ACCESS	read-write
	STATUS	mandatory
	DESCRIPTION	"The number of leading digits in the incoming phone number to use for selecting the Dial Plan."
	::= { mibt1NetworkProfile-LineInterface-ChannelConfigEntry 18 }

    t1NetworkProfile-LineInterface-ChannelConfig-IdlePattern	OBJECT-TYPE
	SYNTAX	INTEGER
	ACCESS	read-write
	STATUS	mandatory
	DESCRIPTION	"The idle pattern is the data pattern sent on a channel when it is idle. The idle pattern can be any value from 0(0x00) to 255(0xff)"
	::= { mibt1NetworkProfile-LineInterface-ChannelConfigEntry 19 }


	-- The mibt1NetworkProfile_v1 table
	--
	-- This table contains parameters for the mibt1NetworkProfile_v1 profile
	--

    mibt1NetworkProfileV1Table	OBJECT-TYPE
	SYNTAX		SEQUENCE OF Mibt1NetworkProfileV1Entry
	ACCESS		not-accessible
	STATUS		mandatory
	DESCRIPTION	"A list of mibt1NetworkProfile_v1 profile entries."
	::= { mibt1NetworkProfileV1 1 }

    mibt1NetworkProfileV1Entry	OBJECT-TYPE
	SYNTAX		Mibt1NetworkProfileV1Entry
	ACCESS		not-accessible
	STATUS		mandatory
	DESCRIPTION	"A mibt1NetworkProfile_v1 entry containing objects that
			 maps to the parameters of mibt1NetworkProfile_v1 profile."
	INDEX		{ t1NetworkProfileV1-Name }
	::= { mibt1NetworkProfileV1Table 1 }

    Mibt1NetworkProfileV1Entry ::=
	SEQUENCE {
	    t1NetworkProfileV1-ProfileNumber
		INTEGER,
	    t1NetworkProfileV1-Name
		DisplayString,
	    t1NetworkProfileV1-PhysicalAddress-Shelf
		INTEGER,
	    t1NetworkProfileV1-PhysicalAddress-Slot
		INTEGER,
	    t1NetworkProfileV1-PhysicalAddress-ItemNumber
		INTEGER,
	    t1NetworkProfileV1-BackToBack
		INTEGER,
	    t1NetworkProfileV1-PrimaryChannelUsage
		INTEGER,
	    t1NetworkProfileV1-SecondaryChannelUsage
		INTEGER,
	    t1NetworkProfileV1-TertiaryChannelUsage
		INTEGER,
	    t1NetworkProfileV1-Action-o
		INTEGER
	}

    t1NetworkProfileV1-ProfileNumber	OBJECT-TYPE
	SYNTAX	INTEGER
	ACCESS	read-write
	STATUS	mandatory
	DESCRIPTION	"For potential backwards compatibility. The current design consists of one line profile numbered 0."
	::= { mibt1NetworkProfileV1Entry 1 }

    t1NetworkProfileV1-Name	OBJECT-TYPE
	SYNTAX	DisplayString
	ACCESS	read-only
	STATUS	mandatory
	DESCRIPTION	"Name of DS1 line."
	::= { mibt1NetworkProfileV1Entry 2 }

    t1NetworkProfileV1-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibt1NetworkProfileV1Entry 3 }

    t1NetworkProfileV1-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibt1NetworkProfileV1Entry 4 }

    t1NetworkProfileV1-PhysicalAddress-ItemNumber	OBJECT-TYPE
	SYNTAX	INTEGER
	ACCESS	read-write
	STATUS	mandatory
	DESCRIPTION	"A number that specifies an addressable entity within the context of shelf and slot."
	::= { mibt1NetworkProfileV1Entry 5 }

    t1NetworkProfileV1-BackToBack	OBJECT-TYPE
	SYNTAX	INTEGER {
		    false (1),
		    true (2)
		}
	ACCESS	read-write
	STATUS	mandatory
	DESCRIPTION	"Indicates whether the Multiband is connected back-to-back to another Muliband, rather than a DPNSS PBX. If this field is TRUE, than we don't need to disable receiving interrupts when too many are coming in beyond our processing power. NOTE: GPT's iSDX keeps re-transmitting a frame at 8 ms intervals until it receives an acknowledgement."
	::= { mibt1NetworkProfileV1Entry 6 }

    t1NetworkProfileV1-PrimaryChannelUsage	OBJECT-TYPE
	SYNTAX	INTEGER {
		    lineUnavailable (1),
		    lineDisable (2),
		    t1LineQuiesce (3),
		    dropAndInsert (4),
		    dualNetworkInterface (5),
		    tOnlineUsrInterface (6),
		    tOnlineZgrInterface (7)
		}
	ACCESS	read-write
	STATUS	mandatory
	DESCRIPTION	"This is the use of the first T1 interface."
	::= { mibt1NetworkProfileV1Entry 7 }

    t1NetworkProfileV1-SecondaryChannelUsage	OBJECT-TYPE
	SYNTAX	INTEGER {
		    lineUnavailable (1),
		    lineDisable (2),
		    t1LineQuiesce (3),
		    dropAndInsert (4),
		    dualNetworkInterface (5),
		    tOnlineUsrInterface (6),
		    tOnlineZgrInterface (7)
		}
	ACCESS	read-write
	STATUS	mandatory
	DESCRIPTION	"The Multiband uses the first T1 interface as the primary interface and treats the secondary interface special. This is the use of the second interface."
	::= { mibt1NetworkProfileV1Entry 8 }

    t1NetworkProfileV1-TertiaryChannelUsage	OBJECT-TYPE
	SYNTAX	INTEGER {
		    lineUnavailable (1),
		    lineDisable (2),
		    t1LineQuiesce (3),
		    dropAndInsert (4),
		    dualNetworkInterface (5),
		    tOnlineUsrInterface (6),
		    tOnlineZgrInterface (7)
		}
	ACCESS	read-write
	STATUS	mandatory
	DESCRIPTION	"This is the use of the 3rd T1 interface."
	::= { mibt1NetworkProfileV1Entry 9 }

    t1NetworkProfileV1-Action-o	OBJECT-TYPE
	SYNTAX	INTEGER {
		    noAction (1),
		    createProfile (2),
		    deleteProfile (3)
		}
	ACCESS	read-write
	STATUS	mandatory
	DESCRIPTION	""
	::= { mibt1NetworkProfileV1Entry 10 }


	-- The mibt1NetworkProfile_v1__line_interface table
	--
	-- This table contains parameters for the mibt1NetworkProfile_v1__line_interface profile
	--

    mibt1NetworkProfileV1-LineInterfaceTable	OBJECT-TYPE
	SYNTAX		SEQUENCE OF Mibt1NetworkProfileV1-LineInterfaceEntry
	ACCESS		not-accessible
	STATUS		mandatory
	DESCRIPTION	"A list of mibt1NetworkProfile_v1__line_interface profile entries."
	::= { mibt1NetworkProfileV1 2 }

    mibt1NetworkProfileV1-LineInterfaceEntry	OBJECT-TYPE
	SYNTAX		Mibt1NetworkProfileV1-LineInterfaceEntry
	ACCESS		not-accessible
	STATUS		mandatory
	DESCRIPTION	"A mibt1NetworkProfile_v1__line_interface entry containing objects that
			 maps to the parameters of mibt1NetworkProfile_v1__line_interface profile."
	INDEX		{ t1NetworkProfileV1-LineInterface-Name, t1NetworkProfileV1-LineInterface-Index-o }
	::= { mibt1NetworkProfileV1-LineInterfaceTable 1 }

    Mibt1NetworkProfileV1-LineInterfaceEntry ::=
	SEQUENCE {
	    t1NetworkProfileV1-LineInterface-Name
		DisplayString,
	    t1NetworkProfileV1-LineInterface-Index-o
		INTEGER,
	    t1NetworkProfileV1-LineInterface-Enabled
		INTEGER,
	    t1NetworkProfileV1-LineInterface-TOnlineType
		INTEGER,
	    t1NetworkProfileV1-LineInterface-FrameType
		INTEGER,
	    t1NetworkProfileV1-LineInterface-Encoding
		INTEGER,
	    t1NetworkProfileV1-LineInterface-ClockSource
		INTEGER,
	    t1NetworkProfileV1-LineInterface-ClockPriority
		INTEGER,
	    t1NetworkProfileV1-LineInterface-SignalingMode
		INTEGER,
	    t1NetworkProfileV1-LineInterface-IsdnEmulationSide
		INTEGER,
	    t1NetworkProfileV1-LineInterface-RobbedBitMode
		INTEGER,
	    t1NetworkProfileV1-LineInterface-DefaultCallType
		INTEGER,
	    t1NetworkProfileV1-LineInterface-SwitchType
		INTEGER,
	    t1NetworkProfileV1-LineInterface-NfasGroupId
		INTEGER,
	    t1NetworkProfileV1-LineInterface-NfasId
		INTEGER,
	    t1NetworkProfileV1-LineInterface-IncomingCallHandling
		INTEGER,
	    t1NetworkProfileV1-LineInterface-DeleteDigits
		INTEGER,
	    t1NetworkProfileV1-LineInterface-AddDigitString
		DisplayString,
	    t1NetworkProfileV1-LineInterface-CallByCall
		INTEGER,
	    t1NetworkProfileV1-LineInterface-NetworkSpecificFacilities
		INTEGER,
	    t1NetworkProfileV1-LineInterface-PbxAnswerNumber
		DisplayString,
	    t1NetworkProfileV1-LineInterface-AnswerService
		INTEGER,
	    t1NetworkProfileV1-LineInterface-oPBXType
		INTEGER,
	    t1NetworkProfileV1-LineInterface-DataSense
		INTEGER,
	    t1NetworkProfileV1-LineInterface-IdleMode
		INTEGER,
	    t1NetworkProfileV1-LineInterface-oFDL
		INTEGER,
	    t1NetworkProfileV1-LineInterface-FrontEndType
		INTEGER,
	    t1NetworkProfileV1-LineInterface-oDSXLineLength
		INTEGER,
	    t1NetworkProfileV1-LineInterface-oCSUBuildOut
		INTEGER,
	    t1NetworkProfileV1-LineInterface-OverlapReceiving
		INTEGER,
	    t1NetworkProfileV1-LineInterface-PriPrefixNumber
		DisplayString,
	    t1NetworkProfileV1-LineInterface-TrailingDigits
		INTEGER,
	    t1NetworkProfileV1-LineInterface-T302Timer
		INTEGER,
	    t1NetworkProfileV1-LineInterface-Layer3End
		INTEGER,
	    t1NetworkProfileV1-LineInterface-Layer2End
		INTEGER,
	    t1NetworkProfileV1-LineInterface-NlValue
		INTEGER,
	    t1NetworkProfileV1-LineInterface-LoopAvoidance
		INTEGER,
	    t1NetworkProfileV1-LineInterface-MaintenanceState
		INTEGER,
	    t1NetworkProfileV1-LineInterface-NumberComplete
		INTEGER,
	    t1NetworkProfileV1-LineInterface-GroupBAnswerSignal
		INTEGER,
	    t1NetworkProfileV1-LineInterface-GroupBBusySignal
		INTEGER,
	    t1NetworkProfileV1-LineInterface-GroupBNoMatchSignal
		INTEGER,
	    t1NetworkProfileV1-LineInterface-GroupBCollectSignal
		INTEGER,
	    t1NetworkProfileV1-LineInterface-GroupBNoChargeSignal
		INTEGER,
	    t1NetworkProfileV1-LineInterface-GroupIiSignal
		INTEGER,
	    t1NetworkProfileV1-LineInterface-InputSampleCount
		INTEGER,
	    t1NetworkProfileV1-LineInterface-AnswerDelay
		INTEGER,
	    t1NetworkProfileV1-LineInterface-CallerId
		INTEGER,
	    t1NetworkProfileV1-LineInterface-LineSignaling
		INTEGER,
	    t1NetworkProfileV1-LineInterface-Timer1CollectCall
		INTEGER,
	    t1NetworkProfileV1-LineInterface-Timer2CollectCall
		INTEGER,
	    t1NetworkProfileV1-LineInterface-SendDiscVal
		INTEGER,
	    t1NetworkProfileV1-LineInterface-HuntGrpPhoneNumber1
		DisplayString,
	    t1NetworkProfileV1-LineInterface-HuntGrpPhoneNumber2
		DisplayString,
	    t1NetworkProfileV1-LineInterface-HuntGrpPhoneNumber3
		DisplayString,
	    t1NetworkProfileV1-LineInterface-PriTypeOfNumber
		INTEGER,
	    t1NetworkProfileV1-LineInterface-PriNumberingPlanId
		INTEGER,
	    t1NetworkProfileV1-LineInterface-SuperFrameSrcLineNumber
		INTEGER,
	    t1NetworkProfileV1-LineInterface-CollectIncomingDigits
		INTEGER,
	    t1NetworkProfileV1-LineInterface-T1InterDigitTimeout
		INTEGER,
	    t1NetworkProfileV1-LineInterface-R1UseAnir
		INTEGER,
	    t1NetworkProfileV1-LineInterface-R1FirstDigitTimer
		INTEGER,
	    t1NetworkProfileV1-LineInterface-R1AnirDelay
		INTEGER,
	    t1NetworkProfileV1-LineInterface-R1AnirTimer
		INTEGER,
	    t1NetworkProfileV1-LineInterface-R1Modified
		INTEGER,
	    t1NetworkProfileV1-LineInterface-FirstDs0
		INTEGER,
	    t1NetworkProfileV1-LineInterface-LastDs0
		INTEGER,
	    t1NetworkProfileV1-LineInterface-NailedGroup
		INTEGER,
	    t1NetworkProfileV1-LineInterface-Ss7Continuity-IncomingProcedure
		INTEGER,
	    t1NetworkProfileV1-LineInterface-Ss7Continuity-OutgoingProcedure
		INTEGER,
	    t1NetworkProfileV1-LineInterface-LineProvision
		INTEGER,
	    t1NetworkProfileV1-LineInterface-Gr303Mode
		INTEGER,
	    t1NetworkProfileV1-LineInterface-Gr303GroupId
		INTEGER,
	    t1NetworkProfileV1-LineInterface-Gr303Ds1Id
		INTEGER,
	    t1NetworkProfileV1-LineInterface-SwitchVersion
		INTEGER,
	    t1NetworkProfileV1-LineInterface-DownTransDelay
		INTEGER,
	    t1NetworkProfileV1-LineInterface-UpTransDelay
		INTEGER,
	    t1NetworkProfileV1-LineInterface-StatusChangeTrapEnable
		INTEGER,
	    t1NetworkProfileV1-LineInterface-CauseCodeVerificationEnable
		INTEGER
	}

    t1NetworkProfileV1-LineInterface-Name	OBJECT-TYPE
	SYNTAX	DisplayString
	ACCESS	read-only
	STATUS	mandatory
	DESCRIPTION	""
	::= { mibt1NetworkProfileV1-LineInterfaceEntry 1 }

    t1NetworkProfileV1-LineInterface-Index-o	OBJECT-TYPE
	SYNTAX	INTEGER
	ACCESS	read-only
	STATUS	mandatory
	DESCRIPTION	""
	::= { mibt1NetworkProfileV1-LineInterfaceEntry 2 }

    t1NetworkProfileV1-LineInterface-Enabled	OBJECT-TYPE
	SYNTAX	INTEGER {
		    no (1),
		    yes (2)
		}
	ACCESS	read-write
	STATUS	mandatory
	DESCRIPTION	"TRUE if the line is enabled, otherwise FALSE."
	::= { mibt1NetworkProfileV1-LineInterfaceEntry 3 }

    t1NetworkProfileV1-LineInterface-TOnlineType	OBJECT-TYPE
	SYNTAX	INTEGER {
		    none (1),
		    nt (2),
		    te (3),
		    numberOfTonline (4)
		}
	ACCESS	read-write
	STATUS	mandatory
	DESCRIPTION	"The tonline type of an e1 line."
	::= { mibt1NetworkProfileV1-LineInterfaceEntry 4 }

    t1NetworkProfileV1-LineInterface-FrameType	OBJECT-TYPE
	SYNTAX	INTEGER {
		    d4 (1),
		    esf (2),
		    g703 (3),
		    n-2ds (4)
		}
	ACCESS	read-write
	STATUS	mandatory
	DESCRIPTION	"The super-framing mode that is used on the physical link(s)."
	::= { mibt1NetworkProfileV1-LineInterfaceEntry 5 }

    t1NetworkProfileV1-LineInterface-Encoding	OBJECT-TYPE
	SYNTAX	INTEGER {
		    ami (1),
		    b8zs (2),
		    hdb3 (3),
		    none (4)
		}
	ACCESS	read-write
	STATUS	mandatory
	DESCRIPTION	"The layer 1 line encoding used for the physical link(s)."
	::= { mibt1NetworkProfileV1-LineInterfaceEntry 6 }

    t1NetworkProfileV1-LineInterface-ClockSource	OBJECT-TYPE
	SYNTAX	INTEGER {
		    eligible (1),
		    notEligible (2)
		}
	ACCESS	read-write
	STATUS	mandatory
	DESCRIPTION	""
	::= { mibt1NetworkProfileV1-LineInterfaceEntry 7 }

    t1NetworkProfileV1-LineInterface-ClockPriority	OBJECT-TYPE
	SYNTAX	INTEGER {
		    highPriority (2),
		    middlePriority (3),
		    lowPriority (4)
		}
	ACCESS	read-write
	STATUS	mandatory
	DESCRIPTION	"Clock priority assigned to the T1 line. Used to select particular lines as clock source."
	::= { mibt1NetworkProfileV1-LineInterfaceEntry 8 }

    t1NetworkProfileV1-LineInterface-SignalingMode	OBJECT-TYPE
	SYNTAX	INTEGER {
		    inband (1),
		    isdn (2),
		    isdnNfas (3),
		    e1R2Signaling (5),
		    e1KoreanSignaling (6),
		    e1P7Signaling (7),
		    e1ChineseSignaling (8),
		    e1MeteredSignaling (9),
		    e1NoSignaling (10),
		    e1DpnssSignaling (11),
		    e1ArgentinaSignaling (13),
		    e1BrazilSignaling (14),
		    e1PhilippineSignaling (15),
		    e1IndianSignaling (16),
		    e1CzechSignaling (17),
		    e1MalaysiaSignaling (19),
		    e1NewZealandSignaling (20),
		    e1IsraelSignaling (21),
		    e1ThailandSignaling (22),
		    e1KuwaitSignaling (23),
		    e1MexicoSignaling (24),
		    dtmfR2Signaling (25),
		    tunneledPriSignaling (27),
		    inbandFgdInFgdOut (28),
		    inbandFgdInFgcOut (29),
		    inbandFgcInFgcOut (30),
		    inbandFgcInFgdOut (31),
		    e1VietnamSignaling (32),
		    ss7SigTrunk (33),
		    h248DataTrunk (34)
		}
	ACCESS	read-write
	STATUS	mandatory
	DESCRIPTION	"Inband, ISDN, ISDN_NFAS, PBX or SS7 signaling."
	::= { mibt1NetworkProfileV1-LineInterfaceEntry 9 }

    t1NetworkProfileV1-LineInterface-IsdnEmulationSide	OBJECT-TYPE
	SYNTAX	INTEGER {
		    te (1),
		    nt (2)
		}
	ACCESS	read-write
	STATUS	mandatory
	DESCRIPTION	"Side the line will emulate: TE (user), or NT (network)."
	::= { mibt1NetworkProfileV1-LineInterfaceEntry 10 }

    t1NetworkProfileV1-LineInterface-RobbedBitMode	OBJECT-TYPE
	SYNTAX	INTEGER {
		    winkStart (1),
		    idleStart (2),
		    incW200 (3),
		    incW400 (4),
		    loopStart (5),
		    groundStart (6)
		}
	ACCESS	read-write
	STATUS	mandatory
	DESCRIPTION	"Wink start, idle start, incoming wink."
	::= { mibt1NetworkProfileV1-LineInterfaceEntry 11 }

    t1NetworkProfileV1-LineInterface-DefaultCallType	OBJECT-TYPE
	SYNTAX	INTEGER {
		    digital (1),
		    voice (2),
		    dnisOrVoice (3),
		    dnisOrDigital (4),
		    voip (5),
		    dnisOrVoip (6)
		}
	ACCESS	read-write
	STATUS	mandatory
	DESCRIPTION	"Specify the default call-type for incoming calls, for purposes of call routing and signalling."
	::= { mibt1NetworkProfileV1-LineInterfaceEntry 12 }

    t1NetworkProfileV1-LineInterface-SwitchType	OBJECT-TYPE
	SYNTAX	INTEGER {
		    attPri (1),
		    ntiPri (2),
		    globandPri (3),
		    japanPri (4),
		    vn3Pri (5),
		    onetr6Pri (6),
		    net5Pri (7),
		    danishPri (8),
		    australPri (9),
		    natIsdn2Pri (10),
		    taiwanPri (31),
		    isdxDpnss (11),
		    islxDpnss (12),
		    mercuryDpnss (13),
		    dass2 (14),
		    btSs7 (32),
		    unknownBri (15),
		    att5essBri (16),
		    dms100Nt1Bri (17),
		    nisdn1Bri (18),
		    vn2Bri (19),
		    btnr191Bri (20),
		    net3Bri (21),
		    ptpNet3Bri (22),
		    kddBri (23),
		    belgianBri (24),
		    australBri (25),
		    swissBri (26),
		    german1tr6Bri (27),
		    dutch1tr6Bri (28),
		    switchCas (29),
		    idslPtpBri (30)
		}
	ACCESS	read-write
	STATUS	mandatory
	DESCRIPTION	"The network switch type, needed for ISDN/NFAS signaling."
	::= { mibt1NetworkProfileV1-LineInterfaceEntry 13 }

    t1NetworkProfileV1-LineInterface-NfasGroupId	OBJECT-TYPE
	SYNTAX	INTEGER
	ACCESS	read-write
	STATUS	mandatory
	DESCRIPTION	"For NFAS lines: the nfas group id. Not used with robbed bit signaling."
	::= { mibt1NetworkProfileV1-LineInterfaceEntry 14 }

    t1NetworkProfileV1-LineInterface-NfasId	OBJECT-TYPE
	SYNTAX	INTEGER
	ACCESS	read-write
	STATUS	mandatory
	DESCRIPTION	"For NFAS lines: the interface id. For SS7 lines when Q.931+ control protocol is used: interface id. Not used with robbed bit signaling."
	::= { mibt1NetworkProfileV1-LineInterfaceEntry 15 }

    t1NetworkProfileV1-LineInterface-IncomingCallHandling	OBJECT-TYPE
	SYNTAX	INTEGER {
		    rejectAll (1),
		    internalProcessing (2),
		    ss7GatewayProcessing (3)
		}
	ACCESS	read-write
	STATUS	mandatory
	DESCRIPTION	"This parameter is used to determine the type of processing required for incoming calls from this line."
	::= { mibt1NetworkProfileV1-LineInterfaceEntry 16 }

    t1NetworkProfileV1-LineInterface-DeleteDigits	OBJECT-TYPE
	SYNTAX	INTEGER
	ACCESS	read-write
	STATUS	mandatory
	DESCRIPTION	"Number of digits to delete from numbers received from a PBX."
	::= { mibt1NetworkProfileV1-LineInterfaceEntry 17 }

    t1NetworkProfileV1-LineInterface-AddDigitString	OBJECT-TYPE
	SYNTAX	DisplayString
	ACCESS	read-write
	STATUS	mandatory
	DESCRIPTION	"String of digits to prepend to phone number received from PBX."
	::= { mibt1NetworkProfileV1-LineInterfaceEntry 18 }

    t1NetworkProfileV1-LineInterface-CallByCall	OBJECT-TYPE
	SYNTAX	INTEGER
	ACCESS	read-write
	STATUS	mandatory
	DESCRIPTION	"Call-by-call value to set when routing calls from PBX to network."
	::= { mibt1NetworkProfileV1-LineInterfaceEntry 19 }

    t1NetworkProfileV1-LineInterface-NetworkSpecificFacilities	OBJECT-TYPE
	SYNTAX	INTEGER
	ACCESS	read-write
	STATUS	mandatory
	DESCRIPTION	"Network Specific Facilities (NSF) value to store in the NSF IE of the outgoing Q.931 Setup message. This sets the full 8 bits of the IE."
	::= { mibt1NetworkProfileV1-LineInterfaceEntry 79 }

    t1NetworkProfileV1-LineInterface-PbxAnswerNumber	OBJECT-TYPE
	SYNTAX	DisplayString
	ACCESS	read-write
	STATUS	mandatory
	DESCRIPTION	"The answer number that is the equivalent of a port answer-number used for the network to pbx routing."
	::= { mibt1NetworkProfileV1-LineInterfaceEntry 20 }

    t1NetworkProfileV1-LineInterface-AnswerService	OBJECT-TYPE
	SYNTAX	INTEGER {
		    voice (1),
		    n-56kRestricted (2),
		    n-64kClear (3),
		    n-64kRestricted (4),
		    n-56kClear (5),
		    n-384kRestricted (6),
		    n-384kClear (7),
		    n-1536kClear (8),
		    n-1536kRestricted (9),
		    n-128kClear (10),
		    n-192kClear (11),
		    n-256kClear (12),
		    n-320kClear (13),
		    dws384Clear (14),
		    n-448Clear (15),
		    n-512Clear (16),
		    n-576Clear (17),
		    n-640Clear (18),
		    n-704Clear (19),
		    n-768Clear (20),
		    n-832Clear (21),
		    n-896Clear (22),
		    n-960Clear (23),
		    n-1024Clear (24),
		    n-1088Clear (25),
		    n-1152Clear (26),
		    n-1216Clear (27),
		    n-1280Clear (28),
		    n-1344Clear (29),
		    n-1408Clear (30),
		    n-1472Clear (31),
		    n-1600Clear (32),
		    n-1664Clear (33),
		    n-1728Clear (34),
		    n-1792Clear (35),
		    n-1856Clear (36),
		    n-1920Clear (37),
		    x30RestrictedBearer (39),
		    v110ClearBearer (40),
		    n-64kX30Restricted (41),
		    n-56kV110Clear (42),
		    modem (43),
		    atmodem (44),
		    n-2456kV110 (46),
		    n-4856kV110 (47),
		    n-9656kV110 (48),
		    n-19256kV110 (49),
		    n-38456kV110 (50),
		    n-2456krV110 (51),
		    n-4856krV110 (52),
		    n-9656krV110 (53),
		    n-19256krV110 (54),
		    n-38456krV110 (55),
		    n-2464kV110 (56),
		    n-4864kV110 (57),
		    n-9664kV110 (58),
		    n-19264kV110 (59),
		    n-38464kV110 (60),
		    n-2464krV110 (61),
		    n-4864krV110 (62),
		    n-9664krV110 (63),
		    n-19264krV110 (64),
		    n-38464krV110 (65),
		    v32 (66),
		    phs64k (67),
		    voiceOverIp (68),
		    atmSvc (70),
		    frameRelaySvc (71),
		    vpnTunnel (72),
		    wormarq (73),
		    n-14456kV110 (74),
		    n-28856kV110 (75),
		    n-14456krV110 (76),
		    n-28856krV110 (77),
		    n-14464kV110 (78),
		    n-28864kV110 (79),
		    n-14464krV110 (80),
		    n-28864krV110 (81),
		    modem31khzAudio (82),
		    x25Svc (83),
		    n-144kClear (255),
		    iptoip (263)
		}
	ACCESS	read-write
	STATUS	mandatory
	DESCRIPTION	"The switched service type (or none) that is used for routing network calls to the pbx."
	::= { mibt1NetworkProfileV1-LineInterfaceEntry 21 }

    t1NetworkProfileV1-LineInterface-oPBXType	OBJECT-TYPE
	SYNTAX	INTEGER {
		    hostPbxVoice (1),
		    hostPbxData (2),
		    hostPbxLeasedData (3),
		    hostPbxLeased11 (4)
		}
	ACCESS	read-write
	STATUS	mandatory
	DESCRIPTION	"The PBX Class as defined in the enumeration above."
	::= { mibt1NetworkProfileV1-LineInterfaceEntry 22 }

    t1NetworkProfileV1-LineInterface-DataSense	OBJECT-TYPE
	SYNTAX	INTEGER {
		    normal (1),
		    inv (2)
		}
	ACCESS	read-write
	STATUS	mandatory
	DESCRIPTION	"D-channel normal or inverted data. Currently unused (normal data is always selected."
	::= { mibt1NetworkProfileV1-LineInterfaceEntry 23 }

    t1NetworkProfileV1-LineInterface-IdleMode	OBJECT-TYPE
	SYNTAX	INTEGER {
		    markIdle (1),
		    flagIdle (2)
		}
	ACCESS	read-write
	STATUS	mandatory
	DESCRIPTION	"D-channel mark or flag idle. Currently unused (flag idle is always selected."
	::= { mibt1NetworkProfileV1-LineInterfaceEntry 24 }

    t1NetworkProfileV1-LineInterface-oFDL	OBJECT-TYPE
	SYNTAX	INTEGER {
		    none (1),
		    atNT (2),
		    ansi (3),
		    sprint (4)
		}
	ACCESS	read-write
	STATUS	mandatory
	DESCRIPTION	"Who's FDL are we using. Used only if frame-type is ESF - Ignored otherwise."
	::= { mibt1NetworkProfileV1-LineInterfaceEntry 25 }

    t1NetworkProfileV1-LineInterface-FrontEndType	OBJECT-TYPE
	SYNTAX	INTEGER {
		    csu (1),
		    dsx (2)
		}
	ACCESS	read-write
	STATUS	mandatory
	DESCRIPTION	"The front end type (CSU/DSX) of the T1 transceiver."
	::= { mibt1NetworkProfileV1-LineInterfaceEntry 26 }

    t1NetworkProfileV1-LineInterface-oDSXLineLength	OBJECT-TYPE
	SYNTAX	INTEGER {
		    n-1133 (1),
		    n-134266 (2),
		    n-267399 (3),
		    n-400533 (4),
		    n-534655 (5)
		}
	ACCESS	read-write
	STATUS	mandatory
	DESCRIPTION	"The length of the physical T1 line (for DSX lines)."
	::= { mibt1NetworkProfileV1-LineInterfaceEntry 27 }

    t1NetworkProfileV1-LineInterface-oCSUBuildOut	OBJECT-TYPE
	SYNTAX	INTEGER {
		    n-0Db (1),
		    n-75Db (2),
		    n-15Db (3),
		    n-2255Db (4)
		}
	ACCESS	read-write
	STATUS	mandatory
	DESCRIPTION	"Line buildout value for CSU lines."
	::= { mibt1NetworkProfileV1-LineInterfaceEntry 28 }

    t1NetworkProfileV1-LineInterface-OverlapReceiving	OBJECT-TYPE
	SYNTAX	INTEGER {
		    no (1),
		    yes (2)
		}
	ACCESS	read-write
	STATUS	mandatory
	DESCRIPTION	"TRUE if overlap receiving procedure may be used to handle incoming call, FALSE if not"
	::= { mibt1NetworkProfileV1-LineInterfaceEntry 29 }

    t1NetworkProfileV1-LineInterface-PriPrefixNumber	OBJECT-TYPE
	SYNTAX	DisplayString
	ACCESS	read-write
	STATUS	mandatory
	DESCRIPTION	"The unique prefix of the PRI called party number. It is used to determine whether SETUP message contains any trailing digits when overlap receiving procedure is used to handle the incoming call. Defaults to '' to not count the trailing digits."
	::= { mibt1NetworkProfileV1-LineInterfaceEntry 30 }

    t1NetworkProfileV1-LineInterface-TrailingDigits	OBJECT-TYPE
	SYNTAX	INTEGER
	ACCESS	read-write
	STATUS	mandatory
	DESCRIPTION	"Number of trailing digits expected from the called party number information elements of INFORMATION messages when overlap receiving procedure is used to handle the incoming call. SETUP message may contain some trailing digits in the called party number information element. Defaults to 2."
	::= { mibt1NetworkProfileV1-LineInterfaceEntry 31 }

    t1NetworkProfileV1-LineInterface-T302Timer	OBJECT-TYPE
	SYNTAX	INTEGER
	ACCESS	read-write
	STATUS	mandatory
	DESCRIPTION	"Number of milliseconds to wait for additional called number information elements for an incoming call using overlap receiving procedure. Defaults to 10000."
	::= { mibt1NetworkProfileV1-LineInterfaceEntry 32 }

    t1NetworkProfileV1-LineInterface-Layer3End	OBJECT-TYPE
	SYNTAX	INTEGER {
		    false (1),
		    true (2)
		}
	ACCESS	read-write
	STATUS	mandatory
	DESCRIPTION	"If x-side, layer 3 favors outgoing call when a call collision occurs."
	::= { mibt1NetworkProfileV1-LineInterfaceEntry 33 }

    t1NetworkProfileV1-LineInterface-Layer2End	OBJECT-TYPE
	SYNTAX	INTEGER {
		    false (1),
		    true (2)
		}
	ACCESS	read-write
	STATUS	mandatory
	DESCRIPTION	"This parameter is used to determine the address to send when two PBXs are connected back-to-back; one side must act as an ET, and the other side acts as a PBX. If a-side, layer 2 acts as ET."
	::= { mibt1NetworkProfileV1-LineInterfaceEntry 34 }

    t1NetworkProfileV1-LineInterface-NlValue	OBJECT-TYPE
	SYNTAX	INTEGER
	ACCESS	read-write
	STATUS	mandatory
	DESCRIPTION	"Number of re-transmissions; default to 64."
	::= { mibt1NetworkProfileV1-LineInterfaceEntry 35 }

    t1NetworkProfileV1-LineInterface-LoopAvoidance	OBJECT-TYPE
	SYNTAX	INTEGER
	ACCESS	read-write
	STATUS	mandatory
	DESCRIPTION	"Loop Avoidance; the number of transit PBXs through which a call may be routed (1 to 26 default 7)."
	::= { mibt1NetworkProfileV1-LineInterfaceEntry 36 }

    t1NetworkProfileV1-LineInterface-MaintenanceState	OBJECT-TYPE
	SYNTAX	INTEGER {
		    no (1),
		    yes (2)
		}
	ACCESS	read-write
	STATUS	mandatory
	DESCRIPTION	"TRUE if the line is in user-requested maintenance mode, otherwise FALSE."
	::= { mibt1NetworkProfileV1-LineInterfaceEntry 37 }

    t1NetworkProfileV1-LineInterface-NumberComplete	OBJECT-TYPE
	SYNTAX	INTEGER {
		    n-1Digits (1),
		    n-2Digits (2),
		    n-3Digits (3),
		    n-4Digits (4),
		    n-5Digits (5),
		    n-6Digits (6),
		    n-7Digits (7),
		    n-8Digits (8),
		    n-9Digits (9),
		    n-10Digits (10),
		    endOfPulsing (11),
		    n-0Digits (12),
		    n-11Digits (13),
		    n-12Digits (14),
		    n-13Digits (15),
		    n-14Digits (16),
		    n-15Digits (17),
		    timeOut (18)
		}
	ACCESS	read-write
	STATUS	mandatory
	DESCRIPTION	"The criteria for having received enough digits on an incoming R2 call. Can either be 1, 2, 3, 4, 5, 6, 7, 8, 9, 10, 11, 12 13, 14, or 15 digits received, or the end-of-pulsing signal received, or time-out."
	::= { mibt1NetworkProfileV1-LineInterfaceEntry 38 }

    t1NetworkProfileV1-LineInterface-GroupBAnswerSignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send prior to answering a call."
	::= { mibt1NetworkProfileV1-LineInterfaceEntry 39 }

    t1NetworkProfileV1-LineInterface-GroupBBusySignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send to reject a call."
	::= { mibt1NetworkProfileV1-LineInterfaceEntry 40 }

    t1NetworkProfileV1-LineInterface-GroupBNoMatchSignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send to reject a call with invalid call number."
	::= { mibt1NetworkProfileV1-LineInterfaceEntry 41 }

    t1NetworkProfileV1-LineInterface-GroupBCollectSignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send to answer/reject a collect call."
	::= { mibt1NetworkProfileV1-LineInterfaceEntry 42 }

    t1NetworkProfileV1-LineInterface-GroupBNoChargeSignal	OBJECT-TYPE
	SYNTAX	INTEGER {
		    signalB1 (1),
		    signalB2 (2),
		    signalB3 (3),
		    signalB4 (4),
		    signalB5 (5),
		    signalB6 (6),
		    signalB7 (7),
		    signalB8 (8),
		    signalB9 (9),
		    signalB10 (10),
		    signalB11 (11),
		    signalB12 (12),
		    signalB13 (13),
		    signalB14 (14),
		    signalB15 (15)
		}
	ACCESS	read-write
	STATUS	mandatory
	DESCRIPTION	"The group B signal to send if subscriber line is idle / no charge"
	::= { mibt1NetworkProfileV1-LineInterfaceEntry 74 }

    t1NetworkProfileV1-LineInterface-GroupIiSignal	OBJECT-TYPE
	SYNTAX	INTEGER {
		    signalIi1 (1),
		    signalIi2 (2),
		    signalIi3 (3),
		    signalIi4 (4),
		    signalIi5 (5),
		    signalIi6 (6),
		    signalIi7 (7),
		    signalIi8 (8),
		    signalIi9 (9),
		    signalIi10 (10),
		    signalIi11 (11),
		    signalIi12 (12),
		    signalIi13 (13),
		    signalIi14 (14),
		    signalIi15 (15)
		}
	ACCESS	read-write
	STATUS	mandatory
	DESCRIPTION	"The group II signal to send after sending all address digits."
	::= { mibt1NetworkProfileV1-LineInterfaceEntry 43 }

    t1NetworkProfileV1-LineInterface-InputSampleCount	OBJECT-TYPE
	SYNTAX	INTEGER {
		    oneSample (1),
		    twoSamples (2)
		}
	ACCESS	read-write
	STATUS	mandatory
	DESCRIPTION	"The number of Goertzel input samples (each Goertzel sample is of length N=205) to compute in order to decode DTMF tones, the more samples, the more acccurate the detection result"
	::= { mibt1NetworkProfileV1-LineInterfaceEntry 44 }

    t1NetworkProfileV1-LineInterface-AnswerDelay	OBJECT-TYPE
	SYNTAX	INTEGER
	ACCESS	read-write
	STATUS	mandatory
	DESCRIPTION	"Number of milliseconds to wait before answering an incoming R2 call."
	::= { mibt1NetworkProfileV1-LineInterfaceEntry 45 }

    t1NetworkProfileV1-LineInterface-CallerId	OBJECT-TYPE
	SYNTAX	INTEGER {
		    noCallerId (1),
		    getCallerId (2)
		}
	ACCESS	read-write
	STATUS	mandatory
	DESCRIPTION	"TRUE if the caller Id is enabled, otherwise FALSE."
	::= { mibt1NetworkProfileV1-LineInterfaceEntry 46 }

    t1NetworkProfileV1-LineInterface-LineSignaling	OBJECT-TYPE
	SYNTAX	INTEGER {
		    abBitsLineSignaling (1),
		    aBitOnly0EqualBBit (2),
		    aBitOnly1EqualBBit (3)
		}
	ACCESS	read-write
	STATUS	mandatory
	DESCRIPTION	"The line signaling of E1 line."
	::= { mibt1NetworkProfileV1-LineInterfaceEntry 47 }

    t1NetworkProfileV1-LineInterface-Timer1CollectCall	OBJECT-TYPE
	SYNTAX	INTEGER
	ACCESS	read-write
	STATUS	mandatory
	DESCRIPTION	"Adjustable between 0 ~ 2000ms"
	::= { mibt1NetworkProfileV1-LineInterfaceEntry 48 }

    t1NetworkProfileV1-LineInterface-Timer2CollectCall	OBJECT-TYPE
	SYNTAX	INTEGER
	ACCESS	read-write
	STATUS	mandatory
	DESCRIPTION	"Adjustable between 10 ~ 2000ms"
	::= { mibt1NetworkProfileV1-LineInterfaceEntry 49 }

    t1NetworkProfileV1-LineInterface-SendDiscVal	OBJECT-TYPE
	SYNTAX	INTEGER
	ACCESS	read-write
	STATUS	mandatory
	DESCRIPTION	"Number of seconds before sending ISDN disconnect to switch. 0 means disable."
	::= { mibt1NetworkProfileV1-LineInterfaceEntry 50 }

    t1NetworkProfileV1-LineInterface-HuntGrpPhoneNumber1	OBJECT-TYPE
	SYNTAX	DisplayString
	ACCESS	read-write
	STATUS	mandatory
	DESCRIPTION	"The hunt group phone number associated with this line. Manually entered field which is read-write accessible via SNMP."
	::= { mibt1NetworkProfileV1-LineInterfaceEntry 51 }

    t1NetworkProfileV1-LineInterface-HuntGrpPhoneNumber2	OBJECT-TYPE
	SYNTAX	DisplayString
	ACCESS	read-write
	STATUS	mandatory
	DESCRIPTION	"The hunt group phone number associated with this line. Manually entered field which is read-write accessible via SNMP."
	::= { mibt1NetworkProfileV1-LineInterfaceEntry 52 }

    t1NetworkProfileV1-LineInterface-HuntGrpPhoneNumber3	OBJECT-TYPE
	SYNTAX	DisplayString
	ACCESS	read-write
	STATUS	mandatory
	DESCRIPTION	"The hunt group phone number associated with this line. Manually entered field which is read-write accessible via SNMP."
	::= { mibt1NetworkProfileV1-LineInterfaceEntry 53 }

    t1NetworkProfileV1-LineInterface-PriTypeOfNumber	OBJECT-TYPE
	SYNTAX	INTEGER
	ACCESS	read-write
	STATUS	mandatory
	DESCRIPTION	"PRI Called Party element's Type-Of-Number value for outgoing T1-to-PRI calls."
	::= { mibt1NetworkProfileV1-LineInterfaceEntry 54 }

    t1NetworkProfileV1-LineInterface-PriNumberingPlanId	OBJECT-TYPE
	SYNTAX	INTEGER
	ACCESS	read-write
	STATUS	mandatory
	DESCRIPTION	"PRI Called Party element's Numbering-Plan-ID value for outgoing T1-to-PRI calls."
	::= { mibt1NetworkProfileV1-LineInterfaceEntry 55 }

    t1NetworkProfileV1-LineInterface-SuperFrameSrcLineNumber	OBJECT-TYPE
	SYNTAX	INTEGER
	ACCESS	read-write
	STATUS	mandatory
	DESCRIPTION	"The line from which the the Super-Frame sync pulse is taken. Needed by the 'Dropped&Inserted' line so that it can become synchronized to the source line."
	::= { mibt1NetworkProfileV1-LineInterfaceEntry 56 }

    t1NetworkProfileV1-LineInterface-CollectIncomingDigits	OBJECT-TYPE
	SYNTAX	INTEGER {
		    no (1),
		    yes (2)
		}
	ACCESS	read-write
	STATUS	mandatory
	DESCRIPTION	"TRUE collect incoming called/calling digits, otherwise FALSE."
	::= { mibt1NetworkProfileV1-LineInterfaceEntry 57 }

    t1NetworkProfileV1-LineInterface-T1InterDigitTimeout	OBJECT-TYPE
	SYNTAX	INTEGER
	ACCESS	read-write
	STATUS	mandatory
	DESCRIPTION	"Inter-Digit Timeout (in milliseconds) for inband T1 and E1 R2 lines."
	::= { mibt1NetworkProfileV1-LineInterfaceEntry 58 }

    t1NetworkProfileV1-LineInterface-R1UseAnir	OBJECT-TYPE
	SYNTAX	INTEGER {
		    no (1),
		    yes (2)
		}
	ACCESS	read-write
	STATUS	mandatory
	DESCRIPTION	"TRUE if the line is to use R1 signaling ANIR (CLID), otherwise FALSE."
	::= { mibt1NetworkProfileV1-LineInterfaceEntry 59 }

    t1NetworkProfileV1-LineInterface-R1FirstDigitTimer	OBJECT-TYPE
	SYNTAX	INTEGER
	ACCESS	read-write
	STATUS	mandatory
	DESCRIPTION	"The timer between sending KPA and receiving first Digit in R1 signaling in milliseconds."
	::= { mibt1NetworkProfileV1-LineInterfaceEntry 60 }

    t1NetworkProfileV1-LineInterface-R1AnirDelay	OBJECT-TYPE
	SYNTAX	INTEGER
	ACCESS	read-write
	STATUS	mandatory
	DESCRIPTION	"Delay in milliseconds between receiving ST and sending ANIR signal."
	::= { mibt1NetworkProfileV1-LineInterfaceEntry 61 }

    t1NetworkProfileV1-LineInterface-R1AnirTimer	OBJECT-TYPE
	SYNTAX	INTEGER
	ACCESS	read-write
	STATUS	mandatory
	DESCRIPTION	"Time in milliseconds of ANIR signal."
	::= { mibt1NetworkProfileV1-LineInterfaceEntry 62 }

    t1NetworkProfileV1-LineInterface-R1Modified	OBJECT-TYPE
	SYNTAX	INTEGER {
		    no (1),
		    yes (2)
		}
	ACCESS	read-write
	STATUS	mandatory
	DESCRIPTION	"Use R1 modified signaling. Default is FALSE."
	::= { mibt1NetworkProfileV1-LineInterfaceEntry 63 }

    t1NetworkProfileV1-LineInterface-FirstDs0	OBJECT-TYPE
	SYNTAX	INTEGER
	ACCESS	read-write
	STATUS	mandatory
	DESCRIPTION	"When using fractional T1/E1 the first DS0 used. Default is 1"
	::= { mibt1NetworkProfileV1-LineInterfaceEntry 64 }

    t1NetworkProfileV1-LineInterface-LastDs0	OBJECT-TYPE
	SYNTAX	INTEGER
	ACCESS	read-write
	STATUS	mandatory
	DESCRIPTION	"When using fractional T1/E1 the last DS0 used. Default is 24"
	::= { mibt1NetworkProfileV1-LineInterfaceEntry 65 }

    t1NetworkProfileV1-LineInterface-NailedGroup	OBJECT-TYPE
	SYNTAX	INTEGER
	ACCESS	read-write
	STATUS	mandatory
	DESCRIPTION	"A number that identifies the set of lines that makes up a nailed group. 0 means this line is not part of a nailed group."
	::= { mibt1NetworkProfileV1-LineInterfaceEntry 66 }

    t1NetworkProfileV1-LineInterface-Ss7Continuity-IncomingProcedure	OBJECT-TYPE
	SYNTAX	INTEGER {
		    loopback (2),
		    transponder (3)
		}
	ACCESS	read-write
	STATUS	mandatory
	DESCRIPTION	"Procedure used for incoming continuity check on this line."
	::= { mibt1NetworkProfileV1-LineInterfaceEntry 67 }

    t1NetworkProfileV1-LineInterface-Ss7Continuity-OutgoingProcedure	OBJECT-TYPE
	SYNTAX	INTEGER {
		    singleTone2010 (2),
		    send2010Expect1780 (3),
		    send1780Expect2010 (4),
		    singleTone2000 (5),
		    send2000Expect1780 (6),
		    send1780Expect2000 (7)
		}
	ACCESS	read-write
	STATUS	mandatory
	DESCRIPTION	"Procedure used for outgoing continuity check on this line."
	::= { mibt1NetworkProfileV1-LineInterfaceEntry 68 }

    t1NetworkProfileV1-LineInterface-LineProvision	OBJECT-TYPE
	SYNTAX	INTEGER {
		    lineProvisionNone (1),
		    lineProvisionH0 (2),
		    lineProvisionH11 (3),
		    lineProvisionH0H11 (4),
		    lineProvisionH12 (5),
		    lineProvisionH0H12 (6),
		    lineProvisionH11H12 (7),
		    lineProvisionH0H11H12 (8)
		}
	ACCESS	read-write
	STATUS	mandatory
	DESCRIPTION	"Line Provision."
	::= { mibt1NetworkProfileV1-LineInterfaceEntry 69 }

    t1NetworkProfileV1-LineInterface-Gr303Mode	OBJECT-TYPE
	SYNTAX	INTEGER {
		    gr303Disabled (1),
		    gr3035essPri (2),
		    gr303DmsPri (3),
		    gr303Secondary (4),
		    gr303Normal (5)
		}
	ACCESS	read-write
	STATUS	mandatory
	DESCRIPTION	"GR-303 Mode."
	::= { mibt1NetworkProfileV1-LineInterfaceEntry 70 }

    t1NetworkProfileV1-LineInterface-Gr303GroupId	OBJECT-TYPE
	SYNTAX	INTEGER
	ACCESS	read-write
	STATUS	mandatory
	DESCRIPTION	"For GR303 lines: the interface group id."
	::= { mibt1NetworkProfileV1-LineInterfaceEntry 71 }

    t1NetworkProfileV1-LineInterface-Gr303Ds1Id	OBJECT-TYPE
	SYNTAX	INTEGER
	ACCESS	read-write
	STATUS	mandatory
	DESCRIPTION	"For GR303 lines: The logical DS1 id."
	::= { mibt1NetworkProfileV1-LineInterfaceEntry 72 }

    t1NetworkProfileV1-LineInterface-SwitchVersion	OBJECT-TYPE
	SYNTAX	INTEGER {
		    switchVersionGeneric (1),
		    switchVersionDefinityG3v4 (2)
		}
	ACCESS	read-write
	STATUS	mandatory
	DESCRIPTION	"Switch Version."
	::= { mibt1NetworkProfileV1-LineInterfaceEntry 73 }

    t1NetworkProfileV1-LineInterface-DownTransDelay	OBJECT-TYPE
	SYNTAX	INTEGER
	ACCESS	read-write
	STATUS	mandatory
	DESCRIPTION	"To control the delay in line state transition from up to down when loss of carrier is detected. Each unit of this value is equal to .1 seconds of Delay in UP to DOWN transition."
	::= { mibt1NetworkProfileV1-LineInterfaceEntry 76 }

    t1NetworkProfileV1-LineInterface-UpTransDelay	OBJECT-TYPE
	SYNTAX	INTEGER
	ACCESS	read-write
	STATUS	mandatory
	DESCRIPTION	"To control the delay in line state transition from down to up when carrier is detected. Each unit of this value is equal to .1 seconds of Delay in DOWN to UP transition."
	::= { mibt1NetworkProfileV1-LineInterfaceEntry 77 }

    t1NetworkProfileV1-LineInterface-StatusChangeTrapEnable	OBJECT-TYPE
	SYNTAX	INTEGER {
		    no (1),
		    yes (2)
		}
	ACCESS	read-write
	STATUS	mandatory
	DESCRIPTION	"When set to yes, a line status change trap is sent. NOTE: when the line status change results from a higher level line status change, i.e., ds3, then no trap for the ds1 are sent. The default setting is No."
	::= { mibt1NetworkProfileV1-LineInterfaceEntry 75 }

    t1NetworkProfileV1-LineInterface-CauseCodeVerificationEnable	OBJECT-TYPE
	SYNTAX	INTEGER {
		    no (1),
		    yes (2)
		}
	ACCESS	read-write
	STATUS	mandatory
	DESCRIPTION	"When set to yes, the received CAUSE value will be verified to ensure that cause is defined for the configured switch type. If the switch does not support the cause code, then INVALID ELEM CONTENTS (Cause value 100) will be used for generating PSTN Q931 response. When set to no, the received CAUSE value will be used to generate the PSTN Q931 response."
	::= { mibt1NetworkProfileV1-LineInterfaceEntry 80 }


	-- The mibt1NetworkProfile_v1__line_interface__channel_config table
	--
	-- This table contains parameters for the mibt1NetworkProfile_v1__line_interface__channel_config profile
	--

    mibt1NetworkProfileV1-LineInterface-ChannelConfigTable	OBJECT-TYPE
	SYNTAX		SEQUENCE OF Mibt1NetworkProfileV1-LineInterface-ChannelConfigEntry
	ACCESS		not-accessible
	STATUS		mandatory
	DESCRIPTION	"A list of mibt1NetworkProfile_v1__line_interface__channel_config profile entries."
	::= { mibt1NetworkProfileV1 3 }

    mibt1NetworkProfileV1-LineInterface-ChannelConfigEntry	OBJECT-TYPE
	SYNTAX		Mibt1NetworkProfileV1-LineInterface-ChannelConfigEntry
	ACCESS		not-accessible
	STATUS		mandatory
	DESCRIPTION	"A mibt1NetworkProfile_v1__line_interface__channel_config entry containing objects that
			 maps to the parameters of mibt1NetworkProfile_v1__line_interface__channel_config profile."
	INDEX		{ t1NetworkProfileV1-LineInterface-ChannelConfig-Name, t1NetworkProfileV1-LineInterface-ChannelConfig-Index-o, t1NetworkProfileV1-LineInterface-ChannelConfig-Index1-o }
	::= { mibt1NetworkProfileV1-LineInterface-ChannelConfigTable 1 }

    Mibt1NetworkProfileV1-LineInterface-ChannelConfigEntry ::=
	SEQUENCE {
	    t1NetworkProfileV1-LineInterface-ChannelConfig-Name
		DisplayString,
	    t1NetworkProfileV1-LineInterface-ChannelConfig-Index-o
		INTEGER,
	    t1NetworkProfileV1-LineInterface-ChannelConfig-Index1-o
		INTEGER,
	    t1NetworkProfileV1-LineInterface-ChannelConfig-ChannelUsage
		INTEGER,
	    t1NetworkProfileV1-LineInterface-ChannelConfig-TrunkGroup
		INTEGER,
	    t1NetworkProfileV1-LineInterface-ChannelConfig-PhoneNumber
		DisplayString,
	    t1NetworkProfileV1-LineInterface-ChannelConfig-RoutePort-SlotNumber-SlotNumber
		INTEGER,
	    t1NetworkProfileV1-LineInterface-ChannelConfig-RoutePort-SlotNumber-ShelfNumber
		INTEGER,
	    t1NetworkProfileV1-LineInterface-ChannelConfig-RoutePort-RelativePortNumber-RelativePortNumber
		INTEGER,
	    t1NetworkProfileV1-LineInterface-ChannelConfig-NailedGroup
		INTEGER,
	    t1NetworkProfileV1-LineInterface-ChannelConfig-ChanGroup
		INTEGER,
	    t1NetworkProfileV1-LineInterface-ChannelConfig-DestChanGroup
		INTEGER,
	    t1NetworkProfileV1-LineInterface-ChannelConfig-DialPlanNumber
		INTEGER,
	    t1NetworkProfileV1-LineInterface-ChannelConfig-NumberOfDialPlanSelectDigits
		INTEGER,
	    t1NetworkProfileV1-LineInterface-ChannelConfig-IdlePattern
		INTEGER
	}

    t1NetworkProfileV1-LineInterface-ChannelConfig-Name	OBJECT-TYPE
	SYNTAX	DisplayString
	ACCESS	read-only
	STATUS	mandatory
	DESCRIPTION	""
	::= { mibt1NetworkProfileV1-LineInterface-ChannelConfigEntry 1 }

    t1NetworkProfileV1-LineInterface-ChannelConfig-Index-o	OBJECT-TYPE
	SYNTAX	INTEGER
	ACCESS	read-only
	STATUS	mandatory
	DESCRIPTION	""
	::= { mibt1NetworkProfileV1-LineInterface-ChannelConfigEntry 2 }

    t1NetworkProfileV1-LineInterface-ChannelConfig-Index1-o	OBJECT-TYPE
	SYNTAX	INTEGER
	ACCESS	read-only
	STATUS	mandatory
	DESCRIPTION	""
	::= { mibt1NetworkProfileV1-LineInterface-ChannelConfigEntry 3 }

    t1NetworkProfileV1-LineInterface-ChannelConfig-ChannelUsage	OBJECT-TYPE
	SYNTAX	INTEGER {
		    unusedChannel (1),
		    switchedChannel (2),
		    nailed64Channel (3),
		    dChannel (4),
		    nfasPrimaryDChannel (5),
		    nfasSecondaryDChannel (6),
		    semiPermChannel (7),
		    ss7SignalingChannel (8)
		}
	ACCESS	read-write
	STATUS	mandatory
	DESCRIPTION	"The usage for this specific channel. May be different than the usage for the line, e.g. a nailed channel (clear 64) in a line otherwise used for switched calls."
	::= { mibt1NetworkProfileV1-LineInterface-ChannelConfigEntry 4 }

    t1NetworkProfileV1-LineInterface-ChannelConfig-TrunkGroup	OBJECT-TYPE
	SYNTAX	INTEGER
	ACCESS	read-write
	STATUS	mandatory
	DESCRIPTION	"The trunk group assigned to this channel."
	::= { mibt1NetworkProfileV1-LineInterface-ChannelConfigEntry 5 }

    t1NetworkProfileV1-LineInterface-ChannelConfig-PhoneNumber	OBJECT-TYPE
	SYNTAX	DisplayString
	ACCESS	read-write
	STATUS	mandatory
	DESCRIPTION	"The phone number of this channel. This is the number sent to the far end in an inverse multiplexed call when instructing the far end to add more bandwidth. The number should contain the minimum number of digits to identify the channel. If the channel is part of a hunt group, the phone number should be blank."
	::= { mibt1NetworkProfileV1-LineInterface-ChannelConfigEntry 6 }

    t1NetworkProfileV1-LineInterface-ChannelConfig-RoutePort-SlotNumber-SlotNumber	OBJECT-TYPE
	SYNTAX	INTEGER
	ACCESS	read-write
	STATUS	mandatory
	DESCRIPTION	""
	::= { mibt1NetworkProfileV1-LineInterface-ChannelConfigEntry 7 }

    t1NetworkProfileV1-LineInterface-ChannelConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibt1NetworkProfileV1-LineInterface-ChannelConfigEntry 8 }

    t1NetworkProfileV1-LineInterface-ChannelConfig-RoutePort-RelativePortNumber-RelativePortNumber	OBJECT-TYPE
	SYNTAX	INTEGER
	ACCESS	read-write
	STATUS	mandatory
	DESCRIPTION	""
	::= { mibt1NetworkProfileV1-LineInterface-ChannelConfigEntry 9 }

    t1NetworkProfileV1-LineInterface-ChannelConfig-NailedGroup	OBJECT-TYPE
	SYNTAX	INTEGER
	ACCESS	read-write
	STATUS	mandatory
	DESCRIPTION	"A number that identifies the set of channels that makes up a nailed group."
	::= { mibt1NetworkProfileV1-LineInterface-ChannelConfigEntry 13 }

    t1NetworkProfileV1-LineInterface-ChannelConfig-ChanGroup	OBJECT-TYPE
	SYNTAX	INTEGER
	ACCESS	read-write
	STATUS	mandatory
	DESCRIPTION	"A number that identifies the channel-group to which this channel belongs."
	::= { mibt1NetworkProfileV1-LineInterface-ChannelConfigEntry 14 }

    t1NetworkProfileV1-LineInterface-ChannelConfig-DestChanGroup	OBJECT-TYPE
	SYNTAX	INTEGER
	ACCESS	read-write
	STATUS	mandatory
	DESCRIPTION	"A number that identifies the channel-group to which any incoming calls on this channel will be directed."
	::= { mibt1NetworkProfileV1-LineInterface-ChannelConfigEntry 15 }

    t1NetworkProfileV1-LineInterface-ChannelConfig-DialPlanNumber	OBJECT-TYPE
	SYNTAX	INTEGER
	ACCESS	read-write
	STATUS	mandatory
	DESCRIPTION	"A number that identifies the dial plan from the dial plan menu."
	::= { mibt1NetworkProfileV1-LineInterface-ChannelConfigEntry 16 }

    t1NetworkProfileV1-LineInterface-ChannelConfig-NumberOfDialPlanSelectDigits	OBJECT-TYPE
	SYNTAX	INTEGER
	ACCESS	read-write
	STATUS	mandatory
	DESCRIPTION	"The number of leading digits in the incoming phone number to use for selecting the Dial Plan."
	::= { mibt1NetworkProfileV1-LineInterface-ChannelConfigEntry 17 }

    t1NetworkProfileV1-LineInterface-ChannelConfig-IdlePattern	OBJECT-TYPE
	SYNTAX	INTEGER
	ACCESS	read-write
	STATUS	mandatory
	DESCRIPTION	"The idle pattern is the data pattern sent on a channel when it is idle. The idle pattern can be any value from 0(0x00) to 255(0xff)"
	::= { mibt1NetworkProfileV1-LineInterface-ChannelConfigEntry 18 }

END
