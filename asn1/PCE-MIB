--          *****************************
--          *                           *
--          *         PCE   MIB         *
--          *                           *
--          *****************************

--          vendredi, 21 avril 2000, 15:24:34 MET DST

--          MIB_MIB_STD_V04.2.R003_E001
--          Reference


--          P C E
--          4 / 16 Avenue du General Leclerc
--          92260 Fontenay aux roses



    PCE-MIB DEFINITIONS ::= BEGIN

    IMPORTS
	TRAP-TYPE FROM RFC-1215
        enterprises, OBJECT-TYPE, NetworkAddress,
	IpAddress, Counter, Gauge, TimeTicks
                FROM RFC1155-SMI
        DisplayString, PhysAddress
                FROM RFC1213-MIB;

    pce         OBJECT IDENTIFIER ::= { enterprises 866 }

    products OBJECT IDENTIFIER ::= { pce 1 }

    manager OBJECT IDENTIFIER ::= { pce 2 }

    systemDescription OBJECT IDENTIFIER ::= { pce 3 }

    projects OBJECT IDENTIFIER ::= { pce 4 }

    frxSoftware OBJECT IDENTIFIER ::= { pce 20 }
        frxConfig OBJECT IDENTIFIER ::= { frxSoftware 1 }
        frxManagement OBJECT IDENTIFIER ::= { frxSoftware 10 }
        frxDiagnostic OBJECT IDENTIFIER ::= { frxSoftware 20 }

    vcxSoftware OBJECT IDENTIFIER ::= { pce 30 }
        vcxConfig OBJECT IDENTIFIER ::= { vcxSoftware 1 }
    	  dvbConfig OBJECT IDENTIFIER ::= { vcxSoftware 20 }

    mmxSoftware OBJECT IDENTIFIER ::= { pce 40 }

    compacProxySoftware OBJECT IDENTIFIER ::= { pce 51 }



    compacV9toV11 OBJECT IDENTIFIER ::= { products 1 }


    transProduct OBJECT IDENTIFIER ::= { products 10 }


    netAccessProduct OBJECT IDENTIFIER ::= { products 20 }


    adaptis OBJECT IDENTIFIER ::= { netAccessProduct 10 }


    vpx10 OBJECT IDENTIFIER ::= { netAccessProduct 20 }


    vpx20 OBJECT IDENTIFIER ::= { netAccessProduct 21 }


    mcx103 OBJECT IDENTIFIER ::= { netAccessProduct 30 }


    mcx104 OBJECT IDENTIFIER ::= { netAccessProduct 31 }


    atLan OBJECT IDENTIFIER ::= { netAccessProduct 40 }


    mcx300 OBJECT IDENTIFIER ::= { netAccessProduct 50 }


    frx300 OBJECT IDENTIFIER ::= { netAccessProduct 60 }


    vcx100 OBJECT IDENTIFIER ::= { netAccessProduct 90 }


    avb1002-EM OBJECT IDENTIFIER ::= { netAccessProduct 200 }


    avb1002-FXS-FXO OBJECT IDENTIFIER ::= { netAccessProduct 201 }


    sc103-3W OBJECT IDENTIFIER ::= { netAccessProduct 210 }


    sc103-6W OBJECT IDENTIFIER ::= { netAccessProduct 211 }


    sc103-6W-M OBJECT IDENTIFIER ::= { netAccessProduct 212 }


    sc104 OBJECT IDENTIFIER ::= { netAccessProduct 220 }


    sc106 OBJECT IDENTIFIER ::= { netAccessProduct 225 }


    sc112 OBJECT IDENTIFIER ::= { netAccessProduct 226 }


    sc300-1W-1E OBJECT IDENTIFIER ::= { netAccessProduct 230 }


    sc300-3W-1E OBJECT IDENTIFIER ::= { netAccessProduct 231 }


    sc300-4W OBJECT IDENTIFIER ::= { netAccessProduct 232 }


    sc310-8W OBJECT IDENTIFIER ::= { netAccessProduct 240 }


    sc310-12W OBJECT IDENTIFIER ::= { netAccessProduct 241 }


    sc320-4W-1TR OBJECT IDENTIFIER ::= { netAccessProduct 250 }


    sc320-8W-1TR OBJECT IDENTIFIER ::= { netAccessProduct 251 }


    sc330 OBJECT IDENTIFIER ::= { netAccessProduct 254 }


    sc1200 OBJECT IDENTIFIER ::= { netAccessProduct 255 }


    netConcentratorProduct OBJECT IDENTIFIER ::= { products 30 }


    mcx09 OBJECT IDENTIFIER ::= { netConcentratorProduct 20 }


    mcx109 OBJECT IDENTIFIER ::= { netConcentratorProduct 21 }


    mcx106 OBJECT IDENTIFIER ::= { netConcentratorProduct 30 }


    mcx112 OBJECT IDENTIFIER ::= { netConcentratorProduct 35 }


    mcx212 OBJECT IDENTIFIER ::= { netConcentratorProduct 40 }


    mcx212Y OBJECT IDENTIFIER ::= { netConcentratorProduct 41 }


    mcx512 OBJECT IDENTIFIER ::= { netConcentratorProduct 45 }


    mcx512Y OBJECT IDENTIFIER ::= { netConcentratorProduct 46 }


    lmx506 OBJECT IDENTIFIER ::= { netConcentratorProduct 50 }


    frx800 OBJECT IDENTIFIER ::= { netConcentratorProduct 60 }


    sc512 OBJECT IDENTIFIER ::= { netConcentratorProduct 210 }


    sc512Y OBJECT IDENTIFIER ::= { netConcentratorProduct 211 }


    hpb1025-8W OBJECT IDENTIFIER ::= { netConcentratorProduct 220 }


    hpb1025-12W OBJECT IDENTIFIER ::= { netConcentratorProduct 221 }


    spb1033 OBJECT IDENTIFIER ::= { netConcentratorProduct 250 }


    dvb1008 OBJECT IDENTIFIER ::= { netConcentratorProduct 270 }


    netBackboneProduct OBJECT IDENTIFIER ::= { products 40 }


    npx09 OBJECT IDENTIFIER ::= { netBackboneProduct 20 }


    npx90 OBJECT IDENTIFIER ::= { netBackboneProduct 21 }


    frx1000 OBJECT IDENTIFIER ::= { netBackboneProduct 60 }


    frx2000 OBJECT IDENTIFIER ::= { netBackboneProduct 65 }


    frx2000Y OBJECT IDENTIFIER ::= { netBackboneProduct 70 }


    mmx5000 OBJECT IDENTIFIER ::= { netBackboneProduct 100 }


    mmx10000 OBJECT IDENTIFIER ::= { netBackboneProduct 105 }


    sc5000 OBJECT IDENTIFIER ::= { netBackboneProduct 200 }


    netCentralSiteProduct OBJECT IDENTIFIER ::= { products 50 }


    fpb2025 OBJECT IDENTIFIER ::= { netCentralSiteProduct 200 }


    rpb2025 OBJECT IDENTIFIER ::= { netCentralSiteProduct 201 }


    spb2033 OBJECT IDENTIFIER ::= { netCentralSiteProduct 250 }


    dvb2030 OBJECT IDENTIFIER ::= { netCentralSiteProduct 270 }




    nodeName OBJECT-TYPE
        SYNTAX  DisplayString
        ACCESS  read-only
        STATUS  mandatory
        DESCRIPTION
                "This describes the name of the node whose status
                has changed."
        ::={ manager 1 }


    nodeStatus OBJECT-TYPE
        SYNTAX  INTEGER {
                notMonitored(8),
                inService(1),
                serviceInterrupted(2),
                unknown(3),
                crippled(4),
                functionOccupied(6),
                callForBackupAddress(7)
        }
        ACCESS  read-only
        STATUS  mandatory
        DESCRIPTION
                "This describes the status of the node."
        ::={ manager 2 }


    portLabel OBJECT-TYPE
        SYNTAX  DisplayString
        ACCESS  read-only
        STATUS  mandatory
        DESCRIPTION
                "This describes the label of the port whose status
                has changed."
        ::={ manager 3 }


    portNumber OBJECT-TYPE
        SYNTAX  INTEGER
        ACCESS  read-only
        STATUS  mandatory
        DESCRIPTION
                "This describes the number of the port whose
                status has changed."
        ::={ manager 4 }


    portStatus OBJECT-TYPE
        SYNTAX  INTEGER {
                notMonitored(8),
                inService(1),
                serviceInterrupted(2),
                unknown(3),
                shiftToPstn(5)
        }
        ACCESS  read-only
        STATUS  mandatory
        DESCRIPTION
                "This describes the status of the port."
        ::={ manager 5 }


    changeDescription OBJECT-TYPE
        SYNTAX  DisplayString
        ACCESS  read-only
        STATUS  mandatory
        DESCRIPTION
                "Description of the status report."
        ::={ manager 6 }



    nodeStatusChanged TRAP-TYPE
        ENTERPRISE  pce
        VARIABLES   { nodeName,
                      nodeStatus,
                      changeDescription }
        DESCRIPTION ""
        ::= 0


    lineStatusChanged TRAP-TYPE
        ENTERPRISE  pce
        VARIABLES   { nodeName,
                      portNumber,
                      portLabel,
                      portStatus,
                      changeDescription }
        DESCRIPTION ""
        ::= 1



    fcControl OBJECT IDENTIFIER ::= { frxConfig 1 }


    fcCtlConfigurationState OBJECT-TYPE
        SYNTAX  INTEGER {
                noChange(1),
                notReady(2),
                limitedReset(10),
                reboot(11),
                savingInProgress(20),
                loadingInProgress(21)
                }
        ACCESS  read-only
        STATUS  mandatory
        DESCRIPTION
                "The value of this object indicates the current
                state of the configuration (see
                fcCtlConfigurationCommand to manage this
                configuration) :
                   noChange : not any objects has been modified
                        since the last 'load' command or the last
                        boot,
                   notReady : this configuration can not be saved
                        because it has not been checked or it has
                        been checked but it contains some errors,
                   limitedReset : this configuration may be saved
                        and it may be taken into account by a
                        'hotReset' command,
                   reboot : this configuration may be saved and it
                        will be taken into account by the next
                        'reboot' command (the 'hotReset' command
                        is not enough complete),
                   savingInProgress : this configuration is beeing
                        saved, do not modify any parameter while
                        this saving is being processed,
                   loadingInProgress : a new configuration is
                        beeing loaded, do not modify any parameter
                        while this loading is being processed."
        ::= { fcControl 1 }


    fcCtlStateCheckingResults OBJECT-TYPE
        SYNTAX  DisplayString (SIZE(0..32))
        ACCESS  read-only
        STATUS  mandatory
        DESCRIPTION
                "The value of this object indicates the results of
                the checking controls of the configuration. This
                message is also recorded in fcCtlErrorTable."
        ::= { fcControl 2 }


    fcCtlConfigurationCommand OBJECT-TYPE
        SYNTAX  INTEGER {
                ready(1),
                check(2),
                load(5),
                save(6),
                erase(7),
                hotReset(10),
                reboot(20)
                }
        ACCESS  read-write
        STATUS  mandatory
        DESCRIPTION
                "The value of this object is the command used to
                manage the current configuration :
                   ready : this value is always returned by the
                        equipment in response to a GET request,
                   check : a SET to this value starts the global
                        checking of the current configuration (the
                        possible errors are described in
                        fcCtlStateCheckingResults), determines
                        which ports are concerned by the
                        modifications (see fcCtlAlteredLpTable and
                        fcCtlAlteredIfTable for the list of these
                        ports) and sets fcCtlConfigurationState to
                        'notReady', 'limitedReset' or 'reboot',
                   load : a SET to this value starts the loading
                        of the configuration from
                        fcCtlStorageDevice, this configuration
                        replaces the current one (do not modify
                        any parameter while this loading is being
                        processed),
                   save : a SET to this value starts the saving of
                        the current configuration to
                        fcCtlStorageDevice (do not modify any
                        parameter while this saving is being
                        processed). This saving procedure must
                        follow a checking command with correct
                        results.
                   erase : not available,
                   hotReset : a SET to this value resets (i.e.,
                        disconnects and connects) the ports, the
                        parameters of which have been changed (see
                        fcCtlAlteredLpTable and
                        fcCtlAlteredIfTable for the list of these
                        ports), this is possible only if
                        fcCtlConfigurationState is equal to
                        'limitedReset',
                   reboot : a SET to this value reboots the
                        equipment, the configuration taken into
                        account is specified by fcCtlBootDevice.

                When the current configuration is going to be
                modified, it is advisable to save a valid one on
                the backupNvram to avoid the loss of accessibility
                to the equipment.

                The default value is 'ready'."
        ::= { fcControl 10 }


    fcCtlBootDevice OBJECT-TYPE
        SYNTAX  INTEGER {
                normalNvram(1),
                backupNvram(2),
                startCard(3)
                }
        ACCESS  read-write
        STATUS  mandatory
        DESCRIPTION
                "The value of this object is the device containing
                the configuration which will be used by the
                equipment at next boot time. When the equipment
                fails to boot because of an inconsistent
                configuration, it will retry to boot with another
                one as following :

                   normalNvram : normal non volatile random access
                        memory (i.e., first part of the EEPROM),
                        when it boots the equipment tries to use
                        the configuration from :
                             1st time : normalNvram,
                             2nd time normalNvram,
                             3rd time backupNvram,
                             4th time flashMemory.
                   backupNvram : backup non volatile random access
                        memory (i.e., second part of the EEPROM),
                        when it boots the equipment tries to use
                        the configuration from :
                             1st time backupNvram,
                             2nd time backupNvram,
                             3rd time flashMemory.
                   startCard : start card, when it boots the
                        equipment tries to use the configuration
                        from :
                             1st time startCard,
                             2nd time startCard,
                             3rd time backupNvram,
                             4th time flashMemory.

                The default value is 'normalNvram'."
        ::= { fcControl 20 }


    fcCtlStorageDevice OBJECT-TYPE
        SYNTAX  INTEGER {
                normalNvram(1),
                backupNvram(2),
                startCard(3),
                flashMemory(4)
                }
        ACCESS  read-write
        STATUS  mandatory
        DESCRIPTION
                "The value of this object is the device where the
                next load or save command will operate :
                   normalNvram : normal non volatile random access
                        memory (i.e., first part of the EEPROM),
                   backupNvram : backup non volatile random access
                        memory (i.e., second part of the EEPROM),
                   startCard : start card,
                   flashMemory : flash memory, this device is not
                        available for the save command (this
                        configuration is a minimum one).

                The default value is 'normalNvram'."
        ::= { fcControl 21 }


    fcCtlAlteredLpTable OBJECT-TYPE
        SYNTAX  SEQUENCE OF FcCtlAlteredLpEntry
        ACCESS  not-accessible
        STATUS  mandatory
        DESCRIPTION
                "This table contains the logical ports that will be
                reinitialized by the next hotReset command."
        ::= { fcControl 30 }


    fcCtlAlteredLpEntry OBJECT-TYPE
        SYNTAX  FcCtlAlteredLpEntry
        ACCESS  not-accessible
        STATUS  mandatory
        DESCRIPTION
                "An entry of fcCtlAlteredLpTable."
        INDEX   { fcCtlAlteredLpId }
        ::= { fcCtlAlteredLpTable 1 }


        FcCtlAlteredLpEntry ::=
                SEQUENCE {
                    fcCtlAlteredLpId
                        INTEGER
                }


    fcCtlAlteredLpId OBJECT-TYPE
        SYNTAX  INTEGER (0..181)
        ACCESS  read-only
        STATUS  mandatory
        DESCRIPTION
                "The value of this object identifies one and only
                one logical port which will be reinitialized by
                the next hotReset command (see
                fcCtlConfigurationCommand)."
        ::= { fcCtlAlteredLpEntry 1 }


    fcCtlAlteredDlciTable OBJECT-TYPE
        SYNTAX  SEQUENCE OF FcCtlAlteredDlciEntry
        ACCESS  not-accessible
        STATUS  mandatory
        DESCRIPTION
                ""
        ::= { fcControl 31 }


    fcCtlAlteredDlciEntry OBJECT-TYPE
        SYNTAX  FcCtlAlteredDlciEntry
        ACCESS  not-accessible
        STATUS  mandatory
        DESCRIPTION
                "An entry of fcCtlAlteredDlciTable."
        INDEX   { fcCtlAlteredDlciPpId,
                  fcCtlAlteredDlciNum }
        ::= { fcCtlAlteredDlciTable 1 }


        FcCtlAlteredDlciEntry ::=
                SEQUENCE {
                    fcCtlAlteredDlciPpId
                        INTEGER,
                    fcCtlAlteredDlciNum
                        INTEGER,
                    fcCtlAlteredDlciState
                        INTEGER
                }


    fcCtlAlteredDlciPpId OBJECT-TYPE
        SYNTAX  INTEGER (0..181)
        ACCESS  read-only
        STATUS  mandatory
        DESCRIPTION
                "PP id"
        ::= { fcCtlAlteredDlciEntry 1 }


    fcCtlAlteredDlciNum OBJECT-TYPE
        SYNTAX  INTEGER (0..1023)
        ACCESS  read-only
        STATUS  mandatory
        DESCRIPTION
                "DLCI"
        ::= { fcCtlAlteredDlciEntry 2 }


    fcCtlAlteredDlciState OBJECT-TYPE
        SYNTAX  INTEGER {
                added(1),
                notchanged(2),
                modified(3),
                suppressed(4)
                }
        ACCESS  read-write
        STATUS  mandatory
        DESCRIPTION
                "Etat"
        ::= { fcCtlAlteredDlciEntry 3 }


    fcCtlAlteredIfTable OBJECT-TYPE
        SYNTAX  SEQUENCE OF FcCtlAlteredIfEntry
        ACCESS  not-accessible
        STATUS  mandatory
        DESCRIPTION
                "This table contains the interfaces that will be
                reinitialized by the next hotReset command."
        ::= { fcControl 32 }


    fcCtlAlteredIfEntry OBJECT-TYPE
        SYNTAX  FcCtlAlteredIfEntry
        ACCESS  not-accessible
        STATUS  mandatory
        DESCRIPTION
                "An entry of fcCtlAlteredIfTable."
        INDEX   { fcCtlAlteredIfId }
        ::= { fcCtlAlteredIfTable 1 }


        FcCtlAlteredIfEntry ::=
                SEQUENCE {
                    fcCtlAlteredIfId
                        INTEGER
                }


    fcCtlAlteredIfId OBJECT-TYPE
        SYNTAX  INTEGER (0..181)
        ACCESS  read-only
        STATUS  mandatory
        DESCRIPTION
                "The value of this object identifies one and only
                one interface which will be reinitialized by the
                next hotReset command (see
                fcCtlConfigurationCommand)."
        ::= { fcCtlAlteredIfEntry 1 }


    fcCtlErrorTable OBJECT-TYPE
        SYNTAX  SEQUENCE OF FcCtlErrorEntry
        ACCESS  not-accessible
        STATUS  mandatory
        DESCRIPTION
                "This table contains the last 8 configuration
                messages. The last message is the first one in the
                table (fcCtlErrorIndex = 1), the oldest is the
                last one (fcCtlErrorIndex = 8)."
        ::= { fcControl 40 }


    fcCtlErrorEntry OBJECT-TYPE
        SYNTAX  FcCtlErrorEntry
        ACCESS  not-accessible
        STATUS  mandatory
        DESCRIPTION
                "An entry of fcCtlErrorTable."
        INDEX   { fcCtlErrorIndex }
        ::= { fcCtlErrorTable 1 }


        FcCtlErrorEntry ::=
                SEQUENCE {
                    fcCtlErrorIndex
                        INTEGER,
                    fcCtlErrorCode
                        INTEGER,
                    fcCtlErrorMessage
                        DisplayString,
                    fcCtlErrorTime
                        TimeTicks
                }


    fcCtlErrorIndex OBJECT-TYPE
        SYNTAX  INTEGER (1..8)
        ACCESS  read-only
        STATUS  mandatory
        DESCRIPTION
                "The value of this object identifies one and only
                one message. '1' identifies the last message and
                '8' the oldest one."
        ::= { fcCtlErrorEntry 1 }


    fcCtlErrorCode OBJECT-TYPE
        SYNTAX  INTEGER (0..255)
        ACCESS  read-only
        STATUS  mandatory
        DESCRIPTION
                "The value of this object is the error code for
                this error. '0' means that this message does not
                contain an error but some useful informations."
        ::= { fcCtlErrorEntry 2 }


    fcCtlErrorMessage OBJECT-TYPE
        SYNTAX  DisplayString (SIZE(0..32))
        ACCESS  read-only
        STATUS  mandatory
        DESCRIPTION
                "The value of this object is the textual
                description of this message."
        ::= { fcCtlErrorEntry 3 }


    fcCtlErrorTime OBJECT-TYPE
        SYNTAX  TimeTicks
        ACCESS  read-only
        STATUS  mandatory
        DESCRIPTION
                "The value of this object is the value of sysUpTime
                when this message was recorded."
        ::= { fcCtlErrorEntry 4 }


    fcCtlHRCheckMessagesTable OBJECT-TYPE
        SYNTAX  SEQUENCE OF FcCtlHRCheckMessagesEntry
        ACCESS  not-accessible
        STATUS  mandatory
        DESCRIPTION
                "This table contains ."
        ::= { fcControl 50 }


    fcCtlHRCheckMessagesEntry OBJECT-TYPE
        SYNTAX  FcCtlHRCheckMessagesEntry
        ACCESS  not-accessible
        STATUS  mandatory
        DESCRIPTION
                "An entry of fcCtlHRCheckMessagesTable."
        INDEX   { fcCtlHRCheckMsgIndex }
        ::= { fcCtlHRCheckMessagesTable 1 }


        FcCtlHRCheckMessagesEntry ::=
                SEQUENCE {
                    fcCtlHRCheckMsgIndex
                        INTEGER,
                    fcCtlHRCheckMsgCode
                        OCTET STRING,
                    fcCtlHRCheckMessage
                        DisplayString
                }


    fcCtlHRCheckMsgIndex OBJECT-TYPE
        SYNTAX  INTEGER (1..8)
        ACCESS  read-only
        STATUS  mandatory
        DESCRIPTION
                "The value of this object identifies one and only
                one message."
        ::= { fcCtlHRCheckMessagesEntry 1 }


    fcCtlHRCheckMsgCode OBJECT-TYPE
        SYNTAX  OCTET STRING (SIZE(4))
        ACCESS  read-only
        STATUS  mandatory
        DESCRIPTION
                "The value of this object is ."
        ::= { fcCtlHRCheckMessagesEntry 2 }


    fcCtlHRCheckMessage OBJECT-TYPE
        SYNTAX  DisplayString (SIZE(0..64))
        ACCESS  read-only
        STATUS  mandatory
        DESCRIPTION
                "The value of this object is ."
        ::= { fcCtlHRCheckMessagesEntry 3 }


    fcSystem OBJECT IDENTIFIER ::= { frxConfig 2 }


    fcsConfigDescription OBJECT IDENTIFIER ::= { fcSystem 1 }


    fcsConfigDescName OBJECT-TYPE
        SYNTAX  DisplayString (SIZE(0..8))
        ACCESS  read-write
        STATUS  mandatory
        DESCRIPTION
                "The value of this object is a textual comment. It
                can be used to store a little description of the
                configuration or of the equipment.

                This is a 0 to 8 ASCII characters string.
                The default value is 'Default'."
        ::= { fcsConfigDescription 1 }


    fcsConfigDescAuthor OBJECT-TYPE
        SYNTAX  DisplayString (SIZE(0..8))
        ACCESS  read-write
        STATUS  mandatory
        DESCRIPTION
                "The value of this object is a textual comment. It
                can be used to store the name of the person who
                creates the configuration.

                This is a 0 to 8 ASCII characters string.
                The default value is 'PCE'."
        ::= { fcsConfigDescription 2 }


    fcsConfigDescDate OBJECT-TYPE
        SYNTAX  OCTET STRING (SIZE(3))
        ACCESS  read-write
        STATUS  mandatory
        DESCRIPTION
                "The value of this object is an octet string
                comment. It can be used to store the date when the
                configuration is created.

                This is a three-bytes octet string with digits in
                the range 0 to 9.
                   The default value is '01 01 96'."
        ::= { fcsConfigDescription 3 }


    fcsConfigDescVersion OBJECT-TYPE
        SYNTAX  INTEGER (1..254)
        ACCESS  read-write
        STATUS  mandatory
        DESCRIPTION
                "The value of this object can be used to store the
                version of the configuration.

                This is a decimal integer in the range 1 to 254.
                The default value is '1'."
        ::= { fcsConfigDescription 4 }


    fcsHardwareDescription OBJECT IDENTIFIER ::= { fcSystem 2 }


    fcsHardDescReplicatedMode OBJECT-TYPE
        SYNTAX  INTEGER {
                off(1),
                onTwoModules(3),
                onThreeModules(4)
                }
        ACCESS  read-write
        STATUS  mandatory
        DESCRIPTION
                "The value of this object indicates whether the
                replicated mode is enabled (on two or three
                modules) or not. The replicated mode permits,
                inside a unit with two or three modules, to backup
                all the lines of a breakdown module on the
                remaining ones. This feature can be enabled only
                on a particular hardware.

                The default value is 'off'."
        ::= { fcsHardwareDescription 1 }


    fcsModuleTable OBJECT-TYPE
        SYNTAX  SEQUENCE OF FcsModuleEntry
        ACCESS  not-accessible
        STATUS  mandatory
        DESCRIPTION
                "This table defines for each module of the
                subscriber number of the bridge and routers
                entities, and which of these entities must be
                initialized (i.e., must reserve resources).

                It is not possible to add or delete an entry of
                this table."
        ::= { fcSystem 5 }


    fcsModuleEntry OBJECT-TYPE
        SYNTAX  FcsModuleEntry
        ACCESS  not-accessible
        STATUS  mandatory
        DESCRIPTION
                "An entry of fcsModuleTable."
        INDEX   { fcsModuleId }
        ::= { fcsModuleTable 1 }


        FcsModuleEntry ::=
                SEQUENCE {
                    fcsModuleId
                        INTEGER,
                    fcsModuleSubscriberNumber
                        OCTET STRING,
                    fcsModuleBridgeInit
                        INTEGER,
                    fcsModuleIpxRouterInit
                        INTEGER,
                    fcsModuleClnpRouterInit
                        INTEGER
                }


    fcsModuleId OBJECT-TYPE
        SYNTAX  INTEGER (0..2)
        ACCESS  read-only
        STATUS  mandatory
        DESCRIPTION
                "The value of this object identifies one and only
                one module."
        ::= { fcsModuleEntry 1 }


    fcsModuleSubscriberNumber OBJECT-TYPE
        SYNTAX  OCTET STRING (SIZE(1))
        ACCESS  read-write
        STATUS  mandatory
        DESCRIPTION
                "The value of this object is the subscriber number
                added to the DNICZO of the equipment to make the
                calling address in a call sent from the bridge or
                routers entities of this module.

                This is a one-byte octet string with 2 digits in
                the range 0 to 9.
                The default values are '93' for the module 0, '94'
                for the module 1, '95' for the module 2."
        ::= { fcsModuleEntry 2 }


    fcsModuleBridgeInit OBJECT-TYPE
        SYNTAX  INTEGER {
                off(1),
                on(2)
                }
        ACCESS  read-write
        STATUS  mandatory
        DESCRIPTION
                "The value of this object indicates whether the
                bridge entity is initialized on this module or
                not. When not initialized this entity does not
                reserve resources that thus are available for
                other entities.

                The default value is 'off' for each of the three
                modules."
        ::= { fcsModuleEntry 5 }


    fcsModuleIpxRouterInit OBJECT-TYPE
        SYNTAX  INTEGER {
                off(1),
                on(2)
                }
        ACCESS  read-write
        STATUS  mandatory
        DESCRIPTION
                "The value of this object indicates whether the IPX
                router entity is initialized on this module or
                not. When not initialized this entity does not
                reserve resources that thus are available for
                other entities.

                The default value is 'off' for each of the three
                modules."
        ::= { fcsModuleEntry 6 }


    fcsModuleClnpRouterInit OBJECT-TYPE
        SYNTAX  INTEGER {
                off(1),
                on(2)
                }
        ACCESS  read-write
        STATUS  mandatory
        DESCRIPTION
                "The value of this object indicates whether the
                CLNP router entity is initialized on this module
                or not. When not initialized this entity does not
                reserve resources that thus are available for
                other entities.

                The default value is 'off' for each of the three
                modules."
        ::= { fcsModuleEntry 7 }


    fcManagement OBJECT IDENTIFIER ::= { frxConfig 3 }


    fcmManagementFunctions OBJECT IDENTIFIER ::= { fcManagement 1 }


    fcmMgtFctActivationTable OBJECT-TYPE
        SYNTAX  SEQUENCE OF FcmMgtFctActivationEntry
        ACCESS  not-accessible
        STATUS  mandatory
        DESCRIPTION
                "This table indicates the activation of each
                management function.

                It is not possible to add or delete an entry of
                this table."
        ::= { fcmManagementFunctions 1 }


    fcmMgtFctActivationEntry OBJECT-TYPE
        SYNTAX  FcmMgtFctActivationEntry
        ACCESS  not-accessible
        STATUS  mandatory
        DESCRIPTION
                "An entry of fcmMgtFctActivationTable."
        INDEX   { fcmMgfActName }
        ::= { fcmMgtFctActivationTable 1 }


        FcmMgtFctActivationEntry ::=
                SEQUENCE {
                    fcmMgfActName
                        INTEGER,
                    fcmMgfActAdminStatus
                        INTEGER,
                    fcmMgfActPassword
                        DisplayString
                }


    fcmMgfActName OBJECT-TYPE
        SYNTAX  INTEGER {
                trafficGeneration(1),
                observation(2),
                statistics(3),
                outstandingEvents(4),
                fileTransfer(5),
                telemaintenance(6),
                alarm(8),
                userInterface(10),
                billing(11),
                extendedStatistics(12),
                exploitationAccess(17)
                }
        ACCESS  read-only
        STATUS  mandatory
        DESCRIPTION
                "The value of this object identifies oneand only
                one management function."
        ::= { fcmMgtFctActivationEntry 1 }


    fcmMgfActAdminStatus OBJECT-TYPE
        SYNTAX  INTEGER {
                off(1),
                on(2)
                }
        ACCESS  read-write
        STATUS  mandatory
        DESCRIPTION
                "The value of this object indicates whether this
                management function is initialized or not. When
                not initialized this management function does not
                reserve resources that thus are available for
                other entities.

                The default values are :
                   trafficGeneration :    on,
                   observation :          on,
                   statistics :           on,
                   outstandingEvents :    on,
                   fileTransfer :         on,
                   telemaintenance :      on,
                   alarm :                off,
                   userInterface :        on,
                   billing :              on,
                   extendedStatistics :   off,
                   exploitationAccess :   on."
        ::= { fcmMgtFctActivationEntry 2 }


    fcmMgfActPassword OBJECT-TYPE
        SYNTAX  DisplayString (SIZE(0..6))
        ACCESS  read-write
        STATUS  mandatory
        DESCRIPTION
                "The value of this object is the password needed to
                enable this management function. This password
                takes place in the call user data of a call to
                this management function. It must contains 1 to 6
                alphanumeric characters (except for 'alarm' which
                can not be called and then does not use a
                password).

                The default values are :
                   trafficGeneration :    GG,
                   observation :          OO,
                   statistics :           SS,
                   outstandingEvents :    EE,
                   fileTransfer :         TT,
                   telemaintenance :      MM,
                   alarm :                (empty),
                   userInterface :        RR,
                   billing :              TX,
                   extendedStatistics :   SC,
                   exploitationAccess :   PP."
        ::= { fcmMgtFctActivationEntry 3 }


    fcmMgtFctParameters OBJECT IDENTIFIER ::= { fcmManagementFunctions 2 }


    fcmMgfGeneratorCount OBJECT-TYPE
        SYNTAX  INTEGER (1..15)
        ACCESS  read-write
        STATUS  mandatory
        DESCRIPTION
                "The value of this object is the maximum number of
                traffic generators that may be enabled.

                This is a decimal integer in the range 1 to 15.
                The default value is '1'."
        ::= { fcmMgtFctParameters 1 }


    fcmMgfGeneratorsAction OBJECT-TYPE
        SYNTAX  INTEGER {
                output(1),
                input(2)
                }
        ACCESS  read-write
        STATUS  mandatory
        DESCRIPTION
                "The value of this object indicates whether the
                generators send traffic ('output') or receive
                traffic ('input').

                The default value is 'output'."
        ::= { fcmMgtFctParameters 2 }


    fcmMgfGeneratorsDelay OBJECT-TYPE
        SYNTAX  INTEGER (0..98)
        ACCESS  read-write
        STATUS  mandatory
        DESCRIPTION
                "The value of this object indicates, when the
                generators send traffic, the delay in seconds
                between two successive sent packets.

                This is a decimal integer in the range 0 to 98.
                The default value is '1'."
        ::= { fcmMgtFctParameters 3 }


    fcmMgfAlarmsSubscriber1 OBJECT-TYPE
        SYNTAX  OCTET STRING (SIZE(8))
        ACCESS  read-write
        STATUS  mandatory
        DESCRIPTION
                "The value of this object indicates the X121
                address of the main manager to which the alarms
                will be sent.

                This is a eight-bytes octet string with up to 15
                digits in the range 0 to 9. It must be padded with
                'F' digits for a total of 16 digits. The equipment
                configurator does not need this final padding.
                The default value is 'FF FF FF FF FF FF FF FF'
                meaning 'empty value' (blank value on the
                equipment configurator)."
        ::= { fcmMgtFctParameters 10 }


    fcmMgfAlarmsSubscriber2 OBJECT-TYPE
        SYNTAX  OCTET STRING (SIZE(8))
        ACCESS  read-write
        STATUS  mandatory
        DESCRIPTION
                "The value of this object indicates the X121
                address of the backup manager to which the alarms
                will be sent.

                This is a eight-bytes octet string with up to 15
                digits in the range 0 to 9. It must be padded with
                'F' digits for a total of 16 digits. The equipment
                configurator does not need this final padding.
                The default value is 'FF FF FF FF FF FF FF FF'
                meaning 'empty value' (blank value on the
                equipment configurator)."
        ::= { fcmMgtFctParameters 11 }


    fcmMgfStatSummingPeriod OBJECT-TYPE
        SYNTAX  INTEGER (10..990)
        ACCESS  read-write
        STATUS  mandatory
        DESCRIPTION
                "The value of this object indicates the period, in
                seconds, during which the statistics are
                calculated in the 'notInfinite' summing mode (see
                fmsCtrlSumming).

                This is a decimal integer in the range 10 to 990
                by step of 10.
                The default value is '10'."
        ::= { fcmMgtFctParameters 20 }


    fcmMgfStatBufferThreshold OBJECT-TYPE
        SYNTAX  INTEGER (0..100)
        ACCESS  read-write
        STATUS  mandatory
        DESCRIPTION
                "The value of this object indicates a threshold in
                percents used by the statistics management
                function. The statistics management function
                calculates how long more than
                fcmMgfStatBufferThreshold percents of buffers are
                used and how long more than
                fcmMgfStatBufferThreshold percents of CPU is busy.

                This is a decimal integer in the range 0 to 100.
                The default value is '75'."
        ::= { fcmMgtFctParameters 21 }


    fcmMgfStatThroughputSamplingPeriod OBJECT-TYPE
        SYNTAX  INTEGER (10..1800)
        ACCESS  read-write
        STATUS  mandatory
        DESCRIPTION
                "The value of this object indicates a sampling
                period in seconds used by the statistics
                management function. The statistics management
                function determines the observed throughput by
                counting the octets sent or received on a line
                during this sampling period. More this sampling
                period is small, more precise is the evaluated
                throughput.

                This is a decimal integer in the range 10 to 1800
                by step of 10.
                The default value is '60'."
        ::= { fcmMgtFctParameters 25 }


    fcmMgfStatOutputThreshold OBJECT-TYPE
        SYNTAX  INTEGER (0..100)
        ACCESS  read-write
        STATUS  mandatory
        DESCRIPTION
                "The value of this object indicates a threshold in
                percents used by the statistics management
                function. The statistics management function
                calculates how long the observed outgoing
                throughput is superior to fcmMgfStatOuputThreshold
                percents of the maximum throughput of the line.

                This is a decimal integer in the range 0 to 100.
                The default value is '75'."
        ::= { fcmMgtFctParameters 26 }


    fcmMgfStatInputThreshold OBJECT-TYPE
        SYNTAX  INTEGER (0..100)
        ACCESS  read-write
        STATUS  mandatory
        DESCRIPTION
                "The value of this object indicates a threshold in
                percents used by the statistics management
                function. The statistics management function
                calculates how long the observed incoming
                throughput is superior to fcmMgfStatOuputThreshold
                percents of the maximum throughput of the line.

                This is a decimal integer in the range 0 to 100.
                The default value is '75'."
        ::= { fcmMgtFctParameters 27 }


    fcmMgfStatLogChannelSamplingPeriod OBJECT-TYPE
        SYNTAX  INTEGER (10..1800)
        ACCESS  read-write
        STATUS  mandatory
        DESCRIPTION
                "The value of this object indicates a period in
                seconds used by the statistics management
                function. The statistics management function
                periodically counts the busy logical channels on a
                line every fcmMgfStatLogChannelSamplingPeriod
                seconds.

                This is a decimal integer in the range 10 to 1800
                by step of 10.
                The default value is '60'."
        ::= { fcmMgtFctParameters 30 }


    fcmMgfStatLogChannelThreshold OBJECT-TYPE
        SYNTAX  INTEGER (0..100)
        ACCESS  read-write
        STATUS  mandatory
        DESCRIPTION
                "The value of this object indicates a threshold in
                percents used by the statistics management
                function. The statistics management function
                calculates how long the observed number of the
                busy logical channels is superior to
                fcmMgfStatLogChannelThreshold percents of the
                maximum number of logical channels for a line.

                This is a decimal integer in the range 0 to 100.
                The default value is '75'."
        ::= { fcmMgtFctParameters 31 }


    fcmMgfConversionAimedPoint OBJECT-TYPE
        SYNTAX  INTEGER {
                off(1),
                on(2)
                }
        ACCESS  read-write
        STATUS  mandatory
        DESCRIPTION
                "Conversion adresse : point vise"
        ::= { fcmMgtFctParameters 32 }


    fcmMgfConversionIncomingCall OBJECT-TYPE
        SYNTAX  INTEGER {
                off(1),
                callingAddress(2),
                calledAddress(3),
                callingAddressAndCalledAddress(4)
                }
        ACCESS  read-write
        STATUS  mandatory
        DESCRIPTION
                "Conversion d'adresse sur appel entrant"
        ::= { fcmMgtFctParameters 33 }


    fcmMgfConversionOutgoingCall OBJECT-TYPE
        SYNTAX  INTEGER {
                off(1),
                callingAddress(2),
                calledAddress(3),
                callingAddressAndCalledAddress(4)
                }
        ACCESS  read-write
        STATUS  mandatory
        DESCRIPTION
                "Conversion adresse sur appel sortant"
        ::= { fcmMgtFctParameters 34 }


    fcmMgfConversionAddressCheck OBJECT-TYPE
        SYNTAX  INTEGER {
                off(1),
                onIncomingCall(2),
                onOutgoingCall(3),
                onIncomingCallAndOutgoingCall(4)
                }
        ACCESS  read-write
        STATUS  mandatory
        DESCRIPTION
                "Conversion adresse : controle de la presence dans
                les tables de conversion"
        ::= { fcmMgtFctParameters 35 }


    fcmMgfConvMultiCalledAddrInCall OBJECT-TYPE
        SYNTAX  INTEGER (1..99)
        ACCESS  read-write
        STATUS  mandatory
        DESCRIPTION
                "Numero d'identification pour conversion d'adresse
                d'appele multi-criteres en entree"
        ::= { fcmMgtFctParameters 36 }


    fcmMgfConvMultiCallingAddrInCall OBJECT-TYPE
        SYNTAX  INTEGER (1..99)
        ACCESS  read-write
        STATUS  mandatory
        DESCRIPTION
                "Numero d'identification pour conversion d'adresse
                d'appelant multi-criteres en entree"
        ::= { fcmMgtFctParameters 37 }


    fcmMgfConvMultiCalledAddrOutCall OBJECT-TYPE
        SYNTAX  INTEGER (1..99)
        ACCESS  read-write
        STATUS  mandatory
        DESCRIPTION
                "Numero d'identification pour conversion d'adresse
                d'appele multi-criteres en sortie"
        ::= { fcmMgtFctParameters 38 }


    fcmMgfConvMultiCallingAddrOutCall OBJECT-TYPE
        SYNTAX  INTEGER (1..99)
        ACCESS  read-write
        STATUS  mandatory
        DESCRIPTION
                "Numero d'identification pour conversion d'adresse
                d'appelant multi-criteres en sortie"
        ::= { fcmMgtFctParameters 39 }


    fcmMgfBISDNChannelOpening OBJECT-TYPE
        SYNTAX  INTEGER {
                off(1),
                on(2)
                }
        ACCESS  read-write
        STATUS  mandatory
        DESCRIPTION
                "The value of this object describes the way ISDN
                backup will operate :
                   off: B ISDN channel opening is automatic
                   on:  B ISDN channel opening is under management
                        center control. A comparison is done
                        between the calling address and the
                        Manager and backup addresses defined in
                        the management functions. If one of these
                        addresses matches, the B ISDN channel is
                        opened, otherwise the restart works only
                        if the B channel is already open.
                The default value is 'off'."
        ::= { fcmMgtFctParameters 40 }


    fcmMgfCallAcceptwithReverseCharging OBJECT-TYPE
        SYNTAX  INTEGER {
                no(1),
                yes(2)
                }
        ACCESS  read-write
        STATUS  mandatory
        DESCRIPTION
                "Acceptation appel avec TAD"
        ::= { fcmMgtFctParameters 41 }


    fcmMgfClosedUserGroup OBJECT-TYPE
        SYNTAX  INTEGER {
                noCheck(2),
                clear(1),
                subscribe(3),
                subscribeAndRemove(4)
                }
        ACCESS  read-write
        STATUS  mandatory
        DESCRIPTION
                "GFA"
        ::= { fcmMgtFctParameters 42 }


    fcmMgtFctCugTable OBJECT-TYPE
        SYNTAX  SEQUENCE OF FcmMgtFctCugEntry
        ACCESS  not-accessible
        STATUS  mandatory
        DESCRIPTION
                "This table defines the configuration of four
                couples internal GFU / external GFU for each
                operating function.
                "
        ::= { fcmManagementFunctions 3 }


    fcmMgtFctCugEntry OBJECT-TYPE
        SYNTAX  FcmMgtFctCugEntry
        ACCESS  not-accessible
        STATUS  mandatory
        DESCRIPTION
                "An entry of fcmMgtFctCugTable."
        INDEX   { fcmMgtFctCugFunctionId,
                  fcmMgtFctCugGroupId }
        ::= { fcmMgtFctCugTable 1 }


        FcmMgtFctCugEntry ::=
                SEQUENCE {
                    fcmMgtFctCugFunctionId
                        INTEGER,
                    fcmMgtFctCugGroupId
                        INTEGER,
                    fcmMgtFctCugClosedUserGroupExt
                        INTEGER,
                    fcmMgtFctCugClosedUserGroupInt
                        INTEGER,
                    fcmMgtFctCugChecking
                        INTEGER
                }


    fcmMgtFctCugFunctionId OBJECT-TYPE
        SYNTAX  INTEGER {
                observation(1),
                statistics(2),
                outstandingEvents(3),
                alarm(4),
                trafficGeneration(5),
                telemaintenance(7),
                configuration(8),
                billing(10),
                extendedStatistics(11),
                pae(14)
                }
        ACCESS  read-only
        STATUS  mandatory
        DESCRIPTION
                "The value of this object defines the operating
                function"
        ::= { fcmMgtFctCugEntry 1 }


    fcmMgtFctCugGroupId OBJECT-TYPE
        SYNTAX  INTEGER (0..3)
        ACCESS  read-only
        STATUS  mandatory
        DESCRIPTION
                "The value of this object defines the number of the
                group for each couple internal GFU / external GFU
                This is a decimal integer in the range 0 to 3.
                The default value is '0'.
                "
        ::= { fcmMgtFctCugEntry 2 }


    fcmMgtFctCugClosedUserGroupExt OBJECT-TYPE
        SYNTAX  INTEGER (0..99)
        ACCESS  read-write
        STATUS  mandatory
        DESCRIPTION
                "GFU externe
                This is a decimal integer in the range 0 to 99.
                The default value is ' '.
                "
        ::= { fcmMgtFctCugEntry 3 }


    fcmMgtFctCugClosedUserGroupInt OBJECT-TYPE
        SYNTAX  INTEGER (0..99)
        ACCESS  read-write
        STATUS  mandatory
        DESCRIPTION
                "GFU interne
                The value of this object indicates a 

                This is a decimal integer in the range 0 to 99.
                The default value is ' '.
                "
        ::= { fcmMgtFctCugEntry 4 }


    fcmMgtFctCugChecking OBJECT-TYPE
        SYNTAX  INTEGER {
                onOutgoingCall(3),
                onIncomingCallAndOutgoingCall(1)
                }
        ACCESS  read-write
        STATUS  mandatory
        DESCRIPTION
                "The value of this object defines on which call the
                equipment checks this CUG. The default values is
                'onIncomingCallAndOutgoingCall'."
        ::= { fcmMgtFctCugEntry 5 }


    fcmAlarms OBJECT IDENTIFIER ::= { fcManagement 2 }


    fcmAlrmEventTable OBJECT-TYPE
        SYNTAX  SEQUENCE OF FcmAlrmEventEntry
        ACCESS  not-accessible
        STATUS  mandatory
        DESCRIPTION
                "This table defines, for each family, the selection
                of events which may be sent as alarms on the one
                hand, and as SNMP traps on the other hand. For
                most of these families, their events are sent for
                the physical ports selected in
                fcmAlrmPhysPortTable.

                It is not possible to add or delete an entry of
                this table."
        ::= { fcmAlarms 1 }


    fcmAlrmEventEntry OBJECT-TYPE
        SYNTAX  FcmAlrmEventEntry
        ACCESS  not-accessible
        STATUS  mandatory
        DESCRIPTION
                "An entry of fcmAlrmEventTable."
        INDEX   { fcmAlrmEvtFamilyId }
        ::= { fcmAlrmEventTable 1 }


        FcmAlrmEventEntry ::=
                SEQUENCE {
                    fcmAlrmEvtFamilyId
                        INTEGER,
                    fcmAlrmEvtEventSelection
                        INTEGER,
                    fcmAlrmEvtEvent1
                        OCTET STRING,
                    fcmAlrmEvtEvent2
                        OCTET STRING,
                    fcmAlrmEvtEvent3
                        OCTET STRING,
                    fcmAlrmEvtEvent4
                        OCTET STRING,
                    fcmAlrmEvtEvent5
                        OCTET STRING,
                    fcmAlrmEvtEvent6
                        OCTET STRING,
                    fcmAlrmEvtEvent7
                        OCTET STRING
                }


    fcmAlrmEvtFamilyId OBJECT-TYPE
        SYNTAX  INTEGER {
                troubleReport-00(1),
                management-01(2),
                synchronousSignalling-02(3),
                x25SynchronousProcedure-03(4),
                synchronousLink-04(5),
                linePhysicalLevel-05(6),
                asynchronousProtocolLevel-06(7),
                asynchronousCommandSyntax-07(8),
                asynchronousSemanticLevel-08(9),
                sdlcProcedure-09(10),
                vipProcedure-0A(11),
                tvipFradBscProcedure-0B(12),
                dlcBscProcedure-0C(13),
                mlp-0D(14),
                pstnProcedure-0E(15),
                securizedVcEsv-0F(16),
                securizedVcN4-10(17),
                securizedVcIr-11(18),
                isdnDChannelProcedure-12(19),
                x29Rerouting-13(20),
                ethernetBridgeAndIpRouterFunctions-14(21),
                dlcMtrFrad-15(22),
                compressionProcedure-16(23),
                dlmFunction-17(24),
                configurationFunction-18(25),
                lmiFunction-19(26),
                ppp-1A(27),
                frameRelaySna-1B(28)
                }
        ACCESS  read-only
        STATUS  mandatory
        DESCRIPTION
                "The value of this object identifies one and only
                one events family (the hexadecimal code of this
                family is the last part of the value-name). This
                entry selects events of this family which may be
                sent as alarms on the one hand, and as SNMP traps
                on the other hand."
        ::= { fcmAlrmEventEntry 1 }


    fcmAlrmEvtEventSelection OBJECT-TYPE
        SYNTAX  INTEGER {
                mentioned(1),
                all(2)
                }
        ACCESS  read-write
        STATUS  mandatory
        DESCRIPTION
                "The value of this object indicates whether all the
                events of this family are selected or only those
                mentioned for this family (in this case one to
                seven events may be selected).

                The default value is 'mentioned'."
        ::= { fcmAlrmEventEntry 2 }


    fcmAlrmEvtEvent1 OBJECT-TYPE
        SYNTAX  OCTET STRING (SIZE(1))
        ACCESS  read-write
        STATUS  mandatory
        DESCRIPTION
                "The value of this object is an event of this
                family which is selected when
                fcmAlrmEvtEventSelection is set to 'mentioned'.

                This is a one-byte octet string with 2 digits in
                the range 0 to F.
                The default value is 'FF' meaning 'empty value'
                (blank value on the equipment configurator)."
        ::= { fcmAlrmEventEntry 3 }


    fcmAlrmEvtEvent2 OBJECT-TYPE
        SYNTAX  OCTET STRING (SIZE(1))
        ACCESS  read-write
        STATUS  mandatory
        DESCRIPTION
                "The value of this object is an event of this
                family which is selected when
                fcmAlrmEvtEventSelection is set to 'mentioned'.

                This is a one-byte octet string with 2 digits in
                the range 0 to F.
                The default value is 'FF' meaning 'empty value'
                (blank value on the equipment configurator)."
        ::= { fcmAlrmEventEntry 4 }


    fcmAlrmEvtEvent3 OBJECT-TYPE
        SYNTAX  OCTET STRING (SIZE(1))
        ACCESS  read-write
        STATUS  mandatory
        DESCRIPTION
                "The value of this object is an event of this
                family which is selected when
                fcmAlrmEvtEventSelection is set to 'mentioned'.

                This is a one-byte octet string with 2 digits in
                the range 0 to F.
                The default value is 'FF' meaning 'empty value'
                (blank value on the equipment configurator)."
        ::= { fcmAlrmEventEntry 5 }


    fcmAlrmEvtEvent4 OBJECT-TYPE
        SYNTAX  OCTET STRING (SIZE(1))
        ACCESS  read-write
        STATUS  mandatory
        DESCRIPTION
                "The value of this object is an event of this
                family which is selected when
                fcmAlrmEvtEventSelection is set to 'mentioned'.

                This is a one-byte octet string with 2 digits in
                the range 0 to F.
                The default value is 'FF' meaning 'empty value'
                (blank value on the equipment configurator)."
        ::= { fcmAlrmEventEntry 6 }


    fcmAlrmEvtEvent5 OBJECT-TYPE
        SYNTAX  OCTET STRING (SIZE(1))
        ACCESS  read-write
        STATUS  mandatory
        DESCRIPTION
                "The value of this object is an event of this
                family which is selected when
                fcmAlrmEvtEventSelection is set to 'mentioned'.

                This is a one-byte octet string with 2 digits in
                the range 0 to F.
                The default value is 'FF' meaning 'empty value'
                (blank value on the equipment configurator)."
        ::= { fcmAlrmEventEntry 7 }


    fcmAlrmEvtEvent6 OBJECT-TYPE
        SYNTAX  OCTET STRING (SIZE(1))
        ACCESS  read-write
        STATUS  mandatory
        DESCRIPTION
                "The value of this object is an event of this
                family which is selected when
                fcmAlrmEvtEventSelection is set to 'mentioned'.

                This is a one-byte octet string with 2 digits in
                the range 0 to F.
                The default value is 'FF' meaning 'empty value'
                (blank value on the equipment configurator)."
        ::= { fcmAlrmEventEntry 8 }


    fcmAlrmEvtEvent7 OBJECT-TYPE
        SYNTAX  OCTET STRING (SIZE(1))
        ACCESS  read-write
        STATUS  mandatory
        DESCRIPTION
                "The value of this object is an event of this
                family which is selected when
                fcmAlrmEvtEventSelection is set to 'mentioned'.

                This is a one-byte octet string with 2 digits in
                the range 0 to F.
                The default value is 'FF' meaning 'empty value'
                (blank value on the equipment configurator)."
        ::= { fcmAlrmEventEntry 9 }


    fcmAlrmPhysPortTable OBJECT-TYPE
        SYNTAX  SEQUENCE OF FcmAlrmPhysPortEntry
        ACCESS  not-accessible
        STATUS  mandatory
        DESCRIPTION
                "This table defines, for each family, the selection
                of lines from which the events selected in
                fcmAlrmEventTable will be sent as alarms on the
                one hand, and as SNMP traps on the other hand.

                It is not possible to add or delete an entry of
                this table."
        ::= { fcmAlarms 2 }


    fcmAlrmPhysPortEntry OBJECT-TYPE
        SYNTAX  FcmAlrmPhysPortEntry
        ACCESS  not-accessible
        STATUS  mandatory
        DESCRIPTION
                "An entry of fcmAlrmPhysPortTable."
        INDEX   { fcmAlrmPpFamilyId }
        ::= { fcmAlrmPhysPortTable 1 }


        FcmAlrmPhysPortEntry ::=
                SEQUENCE {
                    fcmAlrmPpFamilyId
                        INTEGER,
                    fcmAlrmPpPhysPortSelection
                        INTEGER,
                    fcmAlrmPpPhysPort1
                        INTEGER,
                    fcmAlrmPpPhysPort2
                        INTEGER,
                    fcmAlrmPpPhysPort3
                        INTEGER,
                    fcmAlrmPpPhysPort4
                        INTEGER,
                    fcmAlrmPpPhysPort5
                        INTEGER,
                    fcmAlrmPpPhysPort6
                        INTEGER,
                    fcmAlrmPpPhysPort7
                        INTEGER
                }


    fcmAlrmPpFamilyId OBJECT-TYPE
        SYNTAX  INTEGER {
                troubleReport-00(1),
                management-01(2),
                synchronousSignalling-02(3),
                x25SynchronousProcedure-03(4),
                synchronousLink-04(5),
                linePhysicalLevel-05(6),
                asynchronousProtocolLevel-06(7),
                asynchronousCommandSyntax-07(8),
                asynchronousSemanticLevel-08(9),
                sdlcProcedure-09(10),
                vipProcedure-0A(11),
                tvipFradBscProcedure-0B(12),
                dlcBscProcedure-0C(13),
                mlp-0D(14),
                pstnProcedure-0E(15),
                isdnDChannelProcedure-12(19),
                dlcMtrFrad-15(22),
                compressionProcedure-16(23),
                dlmFunction-17(24),
                configurationFunction-18(25),
                lmiFunction-19(26),
                ppp-1A(27),
                frameRelaySna-1B(28)
                }
        ACCESS  read-only
        STATUS  mandatory
        DESCRIPTION
                "The value of this object identifies one and only
                one events family (the hexadecimal code of this
                family is the last part of the value-name). This
                entry selects lines from which the events selected
                in fcmAlrmEventTable will be sent as alarms on the
                one hand, and as SNMP traps on the other hand."
        ::= { fcmAlrmPhysPortEntry 1 }


    fcmAlrmPpPhysPortSelection OBJECT-TYPE
        SYNTAX  INTEGER {
                mentioned(1),
                allExceptMentioned(2)
                }
        ACCESS  read-write
        STATUS  mandatory
        DESCRIPTION
                "The value of this object indicates whether the
                selected events of this family are sent only for
                the physical ports  mentioned for this family or
                for all the physical ports except those mentioned
                (note in this second case that all the physical
                ports are selected when none is specified).

                The default value is 'mentioned'."
        ::= { fcmAlrmPhysPortEntry 2 }


    fcmAlrmPpPhysPort1 OBJECT-TYPE
        SYNTAX  INTEGER (0..35)
        ACCESS  read-write
        STATUS  mandatory
        DESCRIPTION
                "The value of this object is a physical port for
                which the selected events of this family will be
                or will not be sent according to
                fcmAlrmPpPhysPortSelection.

                This is a decimal integer in the range 0 to 35.
                The default value is '255' meaning 'empty value'
                (blank value on the equipment configurator)."
        ::= { fcmAlrmPhysPortEntry 3 }


    fcmAlrmPpPhysPort2 OBJECT-TYPE
        SYNTAX  INTEGER (0..35)
        ACCESS  read-write
        STATUS  mandatory
        DESCRIPTION
                "The value of this object is a physical port for
                which the selected events of this family will be
                or will not be sent according to
                fcmAlrmPpPhysPortSelection.

                This is a decimal integer in the range 0 to 35.
                The default value is '255' meaning 'empty value'
                (blank value on the equipment configurator)."
        ::= { fcmAlrmPhysPortEntry 4 }


    fcmAlrmPpPhysPort3 OBJECT-TYPE
        SYNTAX  INTEGER (0..35)
        ACCESS  read-write
        STATUS  mandatory
        DESCRIPTION
                "The value of this object is a physical port for
                which the selected events of this family will be
                or will not be sent according to
                fcmAlrmPpPhysPortSelection.

                This is a decimal integer in the range 0 to 35.
                The default value is '255' meaning 'empty value'
                (blank value on the equipment configurator)."
        ::= { fcmAlrmPhysPortEntry 5 }


    fcmAlrmPpPhysPort4 OBJECT-TYPE
        SYNTAX  INTEGER (0..35)
        ACCESS  read-write
        STATUS  mandatory
        DESCRIPTION
                "The value of this object is a physical port for
                which the selected events of this family will be
                or will not be sent according to
                fcmAlrmPpPhysPortSelection.

                This is a decimal integer in the range 0 to 35.
                The default value is '255' meaning 'empty value'
                (blank value on the equipment configurator)."
        ::= { fcmAlrmPhysPortEntry 6 }


    fcmAlrmPpPhysPort5 OBJECT-TYPE
        SYNTAX  INTEGER (0..35)
        ACCESS  read-write
        STATUS  mandatory
        DESCRIPTION
                "The value of this object is a physical port for
                which the selected events of this family will be
                or will not be sent according to
                fcmAlrmPpPhysPortSelection.

                This is a decimal integer in the range 0 to 35.
                The default value is '255' meaning 'empty value'
                (blank value on the equipment configurator)."
        ::= { fcmAlrmPhysPortEntry 7 }


    fcmAlrmPpPhysPort6 OBJECT-TYPE
        SYNTAX  INTEGER (0..35)
        ACCESS  read-write
        STATUS  mandatory
        DESCRIPTION
                "The value of this object is a physical port for
                which the selected events of this family will be
                or will not be sent according to
                fcmAlrmPpPhysPortSelection.

                This is a decimal integer in the range 0 to 35.
                The default value is '255' meaning 'empty value'
                (blank value on the equipment configurator)."
        ::= { fcmAlrmPhysPortEntry 8 }


    fcmAlrmPpPhysPort7 OBJECT-TYPE
        SYNTAX  INTEGER (0..35)
        ACCESS  read-write
        STATUS  mandatory
        DESCRIPTION
                "The value of this object is a physical port for
                which the selected events of this family will be
                or will not be sent according to
                fcmAlrmPpPhysPortSelection.

                This is a decimal integer in the range 0 to 35.
                The default value is '255' meaning 'empty value'
                (blank value on the equipment configurator)."
        ::= { fcmAlrmPhysPortEntry 9 }


    fcInterfaces OBJECT IDENTIFIER ::= { frxConfig 10 }


    fcfPhysicalPortTable OBJECT-TYPE
        SYNTAX  SEQUENCE OF FcfPhysicalPortEntry
        ACCESS  not-accessible
        STATUS  mandatory
        DESCRIPTION
                "This table defines how the physical ports of the
                equipment are used to build the interfaces.

                It is not possible to add or delete an entry of
                this table."
        ::= { fcInterfaces 1 }


    fcfPhysicalPortEntry OBJECT-TYPE
        SYNTAX  FcfPhysicalPortEntry
        ACCESS  not-accessible
        STATUS  mandatory
        DESCRIPTION
                "An entry of fcfPhysicalPortTable."
        INDEX   { fcfPhysPortId }
        ::= { fcfPhysicalPortTable 1 }


        FcfPhysicalPortEntry ::=
                SEQUENCE {
                    fcfPhysPortId
                        INTEGER,
                    fcfPhysPortConnector
                        INTEGER,
                    fcfInterfaceType
                        INTEGER
                }


    fcfPhysPortId OBJECT-TYPE
        SYNTAX  INTEGER (0..36)
        ACCESS  read-only
        STATUS  mandatory
        DESCRIPTION
                "The value of this object identifies one and only
                one physical port. A physical port has the same
                number than the physical connector which it goes
                with (this number is indicated on the equipment).

                This is a decimal integer in the range 0 to the
                number of the physical ports minus 1 (36 at the
                most)."
        ::= { fcfPhysicalPortEntry 1 }


    fcfPhysPortConnector OBJECT-TYPE
        SYNTAX  INTEGER {
                ethernet(1),
                db25orRj45(2),
                link(3),
                db9orRj45(4)
                }
        ACCESS  read-only
        STATUS  mandatory
        DESCRIPTION
                "The value of this object indicates whether the
                connector type is Ethernet or DB25 or RJ45."
        ::= { fcfPhysicalPortEntry 2 }


    fcfInterfaceType OBJECT-TYPE
        SYNTAX  INTEGER {
                unUsed(1),
                ethernetAuto(2),
                ethernet10baseT(3),
                ethernetAui(4),
                line(5),
                isdnBChannel(6),
                isdnDChannel(7),
                interUnitLinks(8),
                e1(9),
                ds1(10),
                isdnPri(11),
                lineorB(12),
                tokenRing(13)
                }
        ACCESS  read-write
        STATUS  mandatory
        DESCRIPTION
                "The value of this object indicates how this
                physical port is used to build an interface (the
                interface identifiers are set by the equipment) :
                   unUsed : this physical port is not used,
                   ethernetAui : this physical port will support
                        an ethernet interface with the same
                        identifier (AUI connector for 10 base 5
                        ethernet),
                   ethernet10baseT : this physical port will
                        support an ethernet interface with the
                        same identifier (RJ 45 connector for 10
                        base T ethernet),
                   ethernetAuto : this physical port will support
                        an ethernet interface with the same
                        identifier (automatic detection between 10
                        base 5 and 10 base T),
                   line : this physical port will support a serial
                        line interface with the same identifier
                        (the characteristics of this serial line
                        interface are described in fcfLineTable),
                   isdnBChannel : this physical port will support
                        a B-channel of an ISDN Basic Rate
                        Interface,
                   isdnDChannel : this physical port will support
                        a D-channel of an ISDN Basic Rate
                        Interface with the same identifier (the
                        characteristics of this ISDN BRI are
                        described in
                        fcfIsdnBasicRateInterfaceTable).
                   interUnitLinks : this physical port will
                        support a UnitLinks Interface,
                   e1 : this physical port will support a E1
                        Interface,
                   ds1 : this physical port will support a DS1
                        Interface,
                   isdnPri : this physical port will support a
                        Primary Rate Interface,
                   tokenRing : this physical port will support a
                        token ring Interface,
                   analogVoiceEM : this physical port will support
                        a EM analog voice Interface,
                   analogVoiceFxs : this physical port will
                        support a Fxs analog voice Interface,
                   analogVoiceFxo : this physical port will
                        support a Fxo analog voice Interface,
                   isdnBri : this physical port will support a
                        Basic Rate Interface,

                Each equipment has its own characteristics and the
                building of the interfaces must be done according
                to its hardware limitations.

                The default value is 'unUsed'."
        ::= { fcfPhysicalPortEntry 3 }


    fcfLines OBJECT IDENTIFIER ::= { fcInterfaces 2 }


    fcfLineTable OBJECT-TYPE
        SYNTAX  SEQUENCE OF FcfLineEntry
        ACCESS  not-accessible
        STATUS  mandatory
        DESCRIPTION
                "This table defines the characteristics of the
                serial line interfaces.

                It is not possible to add or delete an entry of
                this table (each entry corresponds, in
                fcfPhysicalPortTable, to one instance of
                fcfInterfaceType equal to 'line')."
        ::= { fcfLines 1 }


    fcfLineEntry OBJECT-TYPE
        SYNTAX  FcfLineEntry
        ACCESS  not-accessible
        STATUS  mandatory
        DESCRIPTION
                "An entry of fcfLineTable."
        INDEX   { fcfLineInterfaceId }
        ::= { fcfLineTable 1 }


        FcfLineEntry ::=
                SEQUENCE {
                    fcfLineInterfaceId
                        INTEGER,
                    fcfLineType
                        INTEGER,
                    fcfLineModemManagement
                        INTEGER,
                    fcfLineSpeed
                        INTEGER,
                    fcfLineLinkCheckPeriod
                        INTEGER,
                    fcfLineCheckPeriodCount
                        INTEGER
                }


    fcfLineInterfaceId OBJECT-TYPE
        SYNTAX  INTEGER (0..35)
        ACCESS  read-only
        STATUS  mandatory
        DESCRIPTION
                "The value of this object identifies one and only
                one serial line interface. Each serial line
                interface corresponds, in fcfPhysicalPortTable, to
                one instance of fcfInterfaceType equal to 'line'.

                This is a decimal integer in the range 0 to 35."
        ::= { fcfLineEntry 1 }


    fcfLineType OBJECT-TYPE
        SYNTAX  INTEGER {
                synchroneV28Dte(1),
                synchroneV28Dce(2),
                asynchroneV28Dte(3),
                asynchroneV28Dce(4),
                v11Dte(5),
                v11Dce(6),
                v35Dte(7),
                v35Dce(8),
                g703(9)
                }
        ACCESS  read-write
        STATUS  mandatory
        DESCRIPTION
                "The value of this object indicates which DTE/DCE
                interface characteristics (physical layer) are
                used on this serial line interface :

                   synchronousV28Dte : Synchronous, V28, the
                        equipment is a DTE,
                   synchronousV28Dce : Synchronous, V28, the
                        equipment is a DCE,
                   asynchronousV28Dte : Asynchronous, V28, the
                        equipment is a DTE,
                   asynchronousV28Dce : Asynchronous, V28, the
                        equipment is a DCE,
                   v11Dte : Synchronous, V11, the equipment is a
                        DTE,
                   v11Dce : Synchronous, V11, the equipment is a
                        DCE,
                   v35Dte : Synchronous, V35, the equipment is a
                        DTE,
                   v35Dce : Synchronous, V35, the equipment is a
                        DCE,
                   g703 : G703.

                The selection of this type must be done according
                to the hardware characteristics of this serial
                line interface.

                The default value is 'synchronousV28Dte'."
        ::= { fcfLineEntry 2 }


    fcfLineModemManagement OBJECT-TYPE
        SYNTAX  INTEGER {
                off(1),
                on(2)
                }
        ACCESS  read-write
        STATUS  mandatory
        DESCRIPTION
                "The value of this object indicates whether a modem
                is drived by the equipment or not. The
                characteristics of the modem are described in
                fcfLineModemTable.

                The default value is 'off'."
        ::= { fcfLineEntry 3 }


    fcfLineSpeed OBJECT-TYPE
        SYNTAX  INTEGER {
                s300(23),
                s600(2),
                s1200(3),
                s2400(6),
                s3200(7),
                s4800(8),
                s9600(10),
                s14400(9),
                s19200(11),
                s28800(26),
                s38400(12),
                s48000(13),
                s56000(14),
                s57600(24),
                s64000(15),
                s72000(16),
                s115200(25),
                s128000(17),
                s144000(18),
                s256000(19),
                s512000(20),
                s1024000(21),
                s2048000(22)
                }
        ACCESS  read-write
        STATUS  mandatory
        DESCRIPTION
                "The value of this object indicates the speed in
                bits per second used on this serial line
                interface. The values s300, s57600 and s115200 can
                not be used on synchronous serial line interfaces.

                The default value is 's19200'."
        ::= { fcfLineEntry 4 }


    fcfLineLinkCheckPeriod OBJECT-TYPE
        SYNTAX  INTEGER (200..50800)
        ACCESS  read-write
        STATUS  mandatory
        DESCRIPTION
                "The value of this object indicates a period in
                milliseconds used to look after the circuits of
                this serial line interface. Each circuit state is
                checked every fcfLineLinkCheckPeriod milliseconds
                and when it changes and remains changed after
                fcfLineCheckPeriodCount checkings, this new state
                is delivered to the upper level.

                This is a decimal integer in the range 200 to
                50800 by step of 200.
                The default value is '2000'."
        ::= { fcfLineEntry 5 }


    fcfLineCheckPeriodCount OBJECT-TYPE
        SYNTAX  INTEGER (1..250)
        ACCESS  read-write
        STATUS  mandatory
        DESCRIPTION
                "The value of this object indicates the number of
                checkings of the circuits of this serial line
                interface. Each circuit state is checked every
                fcfLineLinkCheckPeriod milliseconds and when it
                changes and remains changed after
                fcfLineCheckPeriodCount checkings, this new state
                is delivered to the upper level.

                This is a decimal integer in the range 1 to 250.
                The default value is '3'."
        ::= { fcfLineEntry 6 }


    fcfLineV28AsynOutDteSignalTable OBJECT-TYPE
        SYNTAX  SEQUENCE OF FcfLineV28AsynOutDteSignalEntry
        ACCESS  not-accessible
        STATUS  mandatory
        DESCRIPTION
                "This table defines how the outgoing circuits are
                used on asynchronous V28 serial line interfaces
                when the equipment is a DTE.

                It is not possible to add or delete an entry of
                this table (each entry corresponds, in
                fcfLineTable, to one instance of fcfLineType equal
                to 'asynchronousV28Dte')."
        ::= { fcfLines 5 }


    fcfLineV28AsynOutDteSignalEntry OBJECT-TYPE
        SYNTAX  FcfLineV28AsynOutDteSignalEntry
        ACCESS  not-accessible
        STATUS  mandatory
        DESCRIPTION
                "An entry of fcfLineV28AsynOutDteSignalTable."
        INDEX   { fcfLineV28AsynOutDteInterfaceId }
        ::= { fcfLineV28AsynOutDteSignalTable 1 }


        FcfLineV28AsynOutDteSignalEntry ::=
                SEQUENCE {
                    fcfLineV28AsynOutDteInterfaceId
                        INTEGER,
                    fcfLineV28AsynOutDteRts105
                        INTEGER,
                    fcfLineV28AsynOutDteDtr108
                        INTEGER,
                    fcfLineV28AsynOutDteDrs111
                        INTEGER,
                    fcfLineV28AsynOutDteRil140
                        INTEGER,
                    fcfLineV28AsynOutDteLl141
                        INTEGER
                }


    fcfLineV28AsynOutDteInterfaceId OBJECT-TYPE
        SYNTAX  INTEGER (0..35)
        ACCESS  read-only
        STATUS  mandatory
        DESCRIPTION
                "The value of this object identifies one and only
                one asynchronous V28 DTE serial line interface.
                Each asynchronous V28 DTE serial line interface
                corresponds, in fcfLineTable, to one instance of
                fcfLineType equal to 'asynchronousV28Dte'.

                This is a decimal integer in the range 0 to 35."
        ::= { fcfLineV28AsynOutDteSignalEntry 1 }


    fcfLineV28AsynOutDteRts105 OBJECT-TYPE
        SYNTAX  INTEGER {
                off(1),
                on(2)
                }
        ACCESS  read-write
        STATUS  mandatory
        DESCRIPTION
                "The value of this object defines whether the
                circuit 105 (request to send) is set, in any case,
                to 'on' or to 'off'.

                The default value is 'on'."
        ::= { fcfLineV28AsynOutDteSignalEntry 2 }


    fcfLineV28AsynOutDteDtr108 OBJECT-TYPE
        SYNTAX  INTEGER {
                off(1),
                on(2)
                }
        ACCESS  read-write
        STATUS  mandatory
        DESCRIPTION
                "The value of this object defines whether the
                circuit 108 (108/1 : connect data set to line or
                108/2 : data terminal ready) is set, in any case,
                to 'on' or to 'off'.

                The default value is 'on'."
        ::= { fcfLineV28AsynOutDteSignalEntry 3 }


    fcfLineV28AsynOutDteDrs111 OBJECT-TYPE
        SYNTAX  INTEGER {
                off(1),
                on(2)
                }
        ACCESS  read-write
        STATUS  mandatory
        DESCRIPTION
                "The value of this object defines whether the
                circuit 111 (data signalling rate selector) is
                set, in any case, to 'on' or to 'off'.

                The default value is 'on'."
        ::= { fcfLineV28AsynOutDteSignalEntry 4 }


    fcfLineV28AsynOutDteRil140 OBJECT-TYPE
        SYNTAX  INTEGER {
                off(1),
                on(2)
                }
        ACCESS  read-write
        STATUS  mandatory
        DESCRIPTION
                "The value of this object defines whether the
                circuit 140 (loopback / maintance test) is set, in
                any case, to 'on' or to 'off'.

                The default value is 'off'."
        ::= { fcfLineV28AsynOutDteSignalEntry 5 }


    fcfLineV28AsynOutDteLl141 OBJECT-TYPE
        SYNTAX  INTEGER {
                off(1),
                on(2)
                }
        ACCESS  read-write
        STATUS  mandatory
        DESCRIPTION
                "The value of this object defines whether the
                circuit 141 (local loopback) is set, in any case,
                to 'on' or to 'off'.

                The default value is 'off'."
        ::= { fcfLineV28AsynOutDteSignalEntry 6 }


    fcfLineV28AsynOutDceSignalTable OBJECT-TYPE
        SYNTAX  SEQUENCE OF FcfLineV28AsynOutDceSignalEntry
        ACCESS  not-accessible
        STATUS  mandatory
        DESCRIPTION
                "This table defines how the outgoing circuits are
                used on asynchronous V28 serial line interfaces
                when the equipment is a DCE.

                It is not possible to add or delete an entry of
                this table (each entry corresponds, in
                fcfLineTable, to one instance of fcfLineType equal
                to 'asynchronousV28Dce')."
        ::= { fcfLines 6 }


    fcfLineV28AsynOutDceSignalEntry OBJECT-TYPE
        SYNTAX  FcfLineV28AsynOutDceSignalEntry
        ACCESS  not-accessible
        STATUS  mandatory
        DESCRIPTION
                "An entry of fcfLineV28AsynOutDceSignalTable."
        INDEX   { fcfLineV28AsynOutDceInterfaceId }
        ::= { fcfLineV28AsynOutDceSignalTable 1 }


        FcfLineV28AsynOutDceSignalEntry ::=
                SEQUENCE {
                    fcfLineV28AsynOutDceInterfaceId
                        INTEGER,
                    fcfLineV28AsynOutDceCts106
                        INTEGER,
                    fcfLineV28AsynOutDceDsr107
                        INTEGER,
                    fcfLineV28AsynOutDceDcd109
                        INTEGER,
                    fcfLineV28AsynOutDceSi117
                        INTEGER,
                    fcfLineV28AsynOutDceTi142
                        INTEGER
                }


    fcfLineV28AsynOutDceInterfaceId OBJECT-TYPE
        SYNTAX  INTEGER (0..35)
        ACCESS  read-only
        STATUS  mandatory
        DESCRIPTION
                "The value of this object identifies one and only
                one asynchronous V28 DCE serial line interface.
                Each asynchronous V28 DCE serial line interface
                corresponds, in fcfLineTable, to one instance of
                fcfLineType equal to 'asynchronousV28Dce'.

                This is a decimal integer in the range 0 to 35."
        ::= { fcfLineV28AsynOutDceSignalEntry 1 }


    fcfLineV28AsynOutDceCts106 OBJECT-TYPE
        SYNTAX  INTEGER {
                off(1),
                on(2)
                }
        ACCESS  read-write
        STATUS  mandatory
        DESCRIPTION
                "The value of this object defines whether the
                circuit 106 (ready for sending) is set, in any
                case, to 'on' or to 'off'.

                The default value is 'on'."
        ::= { fcfLineV28AsynOutDceSignalEntry 2 }


    fcfLineV28AsynOutDceDsr107 OBJECT-TYPE
        SYNTAX  INTEGER {
                off(1),
                on(2)
                }
        ACCESS  read-write
        STATUS  mandatory
        DESCRIPTION
                "The value of this object defines whether the
                circuit 107 (data set ready) is set, in any case,
                to 'on' or to 'off'.

                The default value is 'on'."
        ::= { fcfLineV28AsynOutDceSignalEntry 3 }


    fcfLineV28AsynOutDceDcd109 OBJECT-TYPE
        SYNTAX  INTEGER {
                off(1),
                on(2)
                }
        ACCESS  read-write
        STATUS  mandatory
        DESCRIPTION
                "The value of this object defines whether the
                circuit 109 (data channel received line signal
                detector) is set, in any case, to 'on' or to
                'off'.

                The default value is 'on'."
        ::= { fcfLineV28AsynOutDceSignalEntry 4 }


    fcfLineV28AsynOutDceSi117 OBJECT-TYPE
        SYNTAX  INTEGER {
                off(1),
                on(2)
                }
        ACCESS  read-write
        STATUS  mandatory
        DESCRIPTION
                "The value of this object defines whether the
                circuit 117 (standby indicator) is set, in any
                case, to 'on' or to 'off'.

                The default value is 'off'."
        ::= { fcfLineV28AsynOutDceSignalEntry 5 }


    fcfLineV28AsynOutDceTi142 OBJECT-TYPE
        SYNTAX  INTEGER {
                off(1),
                on(2)
                }
        ACCESS  read-write
        STATUS  mandatory
        DESCRIPTION
                "The value of this object defines whether the
                circuit 142 (test indicator) is set, in any case,
                to 'on' or to 'off'.

                The default value is 'off'."
        ::= { fcfLineV28AsynOutDceSignalEntry 6 }


    fcfLineV28AsynInDteSignalTable OBJECT-TYPE
        SYNTAX  SEQUENCE OF FcfLineV28AsynInDteSignalEntry
        ACCESS  not-accessible
        STATUS  mandatory
        DESCRIPTION
                "This table defines how the incoming circuits are
                interpreted on asynchronous V28 serial line
                interfaces when the equipment is a DTE.

                It is not possible to add or delete an entry of
                this table (each entry corresponds, in
                fcfLineTable, to one instance of fcfLineType equal
                to 'asynchronousV28Dte')."
        ::= { fcfLines 7 }


    fcfLineV28AsynInDteSignalEntry OBJECT-TYPE
        SYNTAX  FcfLineV28AsynInDteSignalEntry
        ACCESS  not-accessible
        STATUS  mandatory
        DESCRIPTION
                "An entry of fcfLineV28AsynInDteSignalTable."
        INDEX   { fcfLineV28AsynInDteInterfaceId }
        ::= { fcfLineV28AsynInDteSignalTable 1 }


        FcfLineV28AsynInDteSignalEntry ::=
                SEQUENCE {
                    fcfLineV28AsynInDteInterfaceId
                        INTEGER,
                    fcfLineV28AsynInDteEnablingSig1
                        INTEGER,
                    fcfLineV28AsynInDteEnablingSig2
                        INTEGER,
                    fcfLineV28AsynInDteSigMonitored1
                        INTEGER,
                    fcfLineV28AsynInDteSigMonitored2
                        INTEGER
                }


    fcfLineV28AsynInDteInterfaceId OBJECT-TYPE
        SYNTAX  INTEGER (0..35)
        ACCESS  read-only
        STATUS  mandatory
        DESCRIPTION
                "The value of this object identifies one and only
                one asynchronous V28 DTE serial line interface.
                Each asynchronous V28 DTE serial line interface
                corresponds, in fcfLineTable, to one instance of
                fcfLineType equal to 'asynchronousV28Dte'.

                This is a decimal integer in the range 0 to 35."
        ::= { fcfLineV28AsynInDteSignalEntry 1 }


    fcfLineV28AsynInDteEnablingSig1 OBJECT-TYPE
        SYNTAX  INTEGER {
                none(1),
                cts106(33),
                dsr107(2),
                dcd109(9),
                cts106-dsr107(34),
                cts106-dcd109(41),
                dsr107-dcd109(10),
                cts106-dsr107-dcd109(42)
                }
        ACCESS  read-write
        STATUS  mandatory
        DESCRIPTION
                "The value of this object defines which circuits
                are scanned to determine whether this serial line
                interface is up or down. Secondary circuits may
                also be simultaneously scanned (see
                fcfLineV28AsynInDteEnablingSig2).

                   none : the circuits 106, 107, 109 are not used.
                        If also the circuits 117 and 142 are not
                        used the state of this interface is
                        determined by another method,
                   cts106 : the circuit 106 (ready for sending) is
                        used,
                   dsr107 : the circuit 107 (data set ready) is
                        used,
                   dcd109 : the circuit 109 (data channel received
                        line signal detector) is used,
                   cts106-dsr107 : both circuits 106 and 107 are
                        used,
                   cts106-dcd109 : both circuits 106 and 109 are
                        used,
                   dsr107-dcd109 : both circuits 107 and 109 are
                        used,
                   cts106-dsr107-dcd109 : both circuits 106, 107
                        and 109 are used.

                The default value is 'cts106'."
        ::= { fcfLineV28AsynInDteSignalEntry 2 }


    fcfLineV28AsynInDteEnablingSig2 OBJECT-TYPE
        SYNTAX  INTEGER {
                none(1),
                si117(5),
                ti142(3)
                }
        ACCESS  read-write
        STATUS  mandatory
        DESCRIPTION
                "The value of this object defines which circuits
                are scanned to determine whether this serial line
                interface is up or down. Main circuits may also be
                simultaneously scanned (see
                fcfLineV28AsynInDteEnablingSig1).

                   none : the circuits 117, 142 are not used. If
                        also the circuits 106, 107 and 109 are not
                        used the state of this interface is
                        determined by another method,
                   si117 : the circuit 117 (standby indicator) is
                        used,
                   ti142 : the circuit 142 (test indicator) is
                        used.

                The default value is 'none'."
        ::= { fcfLineV28AsynInDteSignalEntry 3 }


    fcfLineV28AsynInDteSigMonitored1 OBJECT-TYPE
        SYNTAX  INTEGER {
                none(1),
                cts106(33),
                dsr107(2),
                dcd109(9),
                cts106-dsr107(34),
                cts106-dcd109(41),
                dsr107-dcd109(10),
                cts106-dsr107-dcd109(42)
                }
        ACCESS  read-write
        STATUS  mandatory
        DESCRIPTION
                "The value of this object defines which circuits
                are monitored to eventually generate the
                corresponding event when the state of one of them
                changes. Secondary circuits may also be
                simultaneously monitored (see
                fcfLineV28AsynInDteMonitored2).

                   none : the circuits 106, 107, 109 are not
                        monitored,
                   cts106 : the circuit 106 (ready for sending) is
                        monitored,
                   dsr107 : the circuit 107 (data set ready) is
                        monitored,
                   dcd109 : the circuit 109 (data channel received
                        line signal detector) is monitored,
                   cts106-dsr107 : both circuits 106 and 107 are
                        monitored,
                   cts106-dcd109 : both circuits 106 and 109 are
                        monitored,
                   dsr107-dcd109 : both circuits 107 and 109 are
                        monitored,
                   cts106-dsr107-dcd109 : both circuits 106, 107
                        and 109 are monitored.

                The default value is 'cts106'."
        ::= { fcfLineV28AsynInDteSignalEntry 4 }


    fcfLineV28AsynInDteSigMonitored2 OBJECT-TYPE
        SYNTAX  INTEGER {
                none(1),
                si117(5),
                ti142(3)
                }
        ACCESS  read-write
        STATUS  mandatory
        DESCRIPTION
                "The value of this object defines which circuits
                are monitored to eventually generate the
                corresponding event when the state of one of them
                changes. Main circuits may also be simultaneously
                monitored (see fcfLineV28AsynInDteMonitored1).

                   none : the circuits 117, 142 are not monitored,
                   si117 : the circuit 117 (standby indicator) is
                        monitored,
                   ti142 : the circuit 142 (test indicator) is
                        monitored.

                The default value is 'none'."
        ::= { fcfLineV28AsynInDteSignalEntry 5 }


    fcfLineV28AsynInDceSignalTable OBJECT-TYPE
        SYNTAX  SEQUENCE OF FcfLineV28AsynInDceSignalEntry
        ACCESS  not-accessible
        STATUS  mandatory
        DESCRIPTION
                "This table defines how the incoming circuits are
                interpreted on asynchronous V28 serial line
                interfaces when the equipment is a DCE.

                It is not possible to add or delete an entry of
                this table (each entry corresponds, in
                fcfLineTable, to one instance of fcfLineType equal
                to 'asynchronousV28Dce')."
        ::= { fcfLines 8 }


    fcfLineV28AsynInDceSignalEntry OBJECT-TYPE
        SYNTAX  FcfLineV28AsynInDceSignalEntry
        ACCESS  not-accessible
        STATUS  mandatory
        DESCRIPTION
                "An entry of fcfLineV28AsynInDceSignalTable."
        INDEX   { fcfLineV28AsynInDceInterfaceId }
        ::= { fcfLineV28AsynInDceSignalTable 1 }


        FcfLineV28AsynInDceSignalEntry ::=
                SEQUENCE {
                    fcfLineV28AsynInDceInterfaceId
                        INTEGER,
                    fcfLineV28AsynInDceEnablingSig1
                        INTEGER,
                    fcfLineV28AsynInDceEnablingSig2
                        INTEGER,
                    fcfLineV28AsynInDceSigMonitored1
                        INTEGER,
                    fcfLineV28AsynInDceSigMonitored2
                        INTEGER
                }


    fcfLineV28AsynInDceInterfaceId OBJECT-TYPE
        SYNTAX  INTEGER (0..35)
        ACCESS  read-only
        STATUS  mandatory
        DESCRIPTION
                "The value of this object identifies one and only
                one asynchronous V28 DCE serial line interface.
                Each asynchronous V28 DCE serial line interface
                corresponds, in fcfLineTable, to one instance of
                fcfLineType equal to 'asynchronousV28Dce'.

                This is a decimal integer in the range 0 to 35."
        ::= { fcfLineV28AsynInDceSignalEntry 1 }


    fcfLineV28AsynInDceEnablingSig1 OBJECT-TYPE
        SYNTAX  INTEGER {
                none(1),
                rts105(9),
                dtr108(33),
                rts105-dtr108(41)
                }
        ACCESS  read-write
        STATUS  mandatory
        DESCRIPTION
                "The value of this object defines which circuits
                are scanned to determine whether this serial line
                interface is up or down. Secondary circuits may
                also be simultaneously scanned (see
                fcfLineV28AsynInDceEnablingSig2).

                   none : the circuits 105, 108 are not used. If
                        also the circuits 111, 140 and 141 are not
                        used the state of this interface is
                        determined by another method,
                   rts105 : the circuit 105 (request to send) is
                        used,
                   dtr108 : the circuit 108 (108/1 connect data
                        set to line, 108/2 data terminal ready) is
                        used,
                   rts105-dtr108 : both circuits 105 and 108 are
                        used.

                The default value is 'rts105'."
        ::= { fcfLineV28AsynInDceSignalEntry 2 }


    fcfLineV28AsynInDceEnablingSig2 OBJECT-TYPE
        SYNTAX  INTEGER {
                none(1),
                drs111(2),
                ril140(3),
                ll141(5)
                }
        ACCESS  read-write
        STATUS  mandatory
        DESCRIPTION
                "The value of this object defines which circuits
                are scanned to determine whether this serial line
                interface is up or down. Main circuits may also be
                simultaneously scanned (see
                fcfLineV28AsynInDceEnablingSig1).

                   none : the circuits 111, 140, 141 are not used.
                        If also the circuits 105 and 108 are not
                        used the state of this interface is
                        determined by another method,
                   drs111 : the circuit 111 (data signal rate
                        selector) is used,
                   ril140 : the circuit 140 (loopback /
                        maintenance test) is used,
                   ll141 : the circuit 141 (local loopback) is
                        used.

                The default value is 'none'."
        ::= { fcfLineV28AsynInDceSignalEntry 3 }


    fcfLineV28AsynInDceSigMonitored1 OBJECT-TYPE
        SYNTAX  INTEGER {
                none(1),
                rts105(9),
                dtr108(33),
                rts105-dtr108(41)
                }
        ACCESS  read-write
        STATUS  mandatory
        DESCRIPTION
                "The value of this object defines which circuits
                are monitored to eventually generate the
                corresponding event when the state of one of them
                changes. Secondary circuits may also be
                simultaneously monitored (see
                fcfLineV28AsynInDceMonitored2).

                   none : the circuits 105, 108 are not monitored,
                   rts105 : the circuit 105 (request to send) is
                        monitored,
                   dtr108 : the circuit 108 (108/1 connect data
                        set to line, 108/2 data terminal ready) is
                        monitored,
                   rts105-dtr108 : both circuits 105 and 108 are
                        monitored.

                The default value is 'rts105'."
        ::= { fcfLineV28AsynInDceSignalEntry 4 }


    fcfLineV28AsynInDceSigMonitored2 OBJECT-TYPE
        SYNTAX  INTEGER {
                none(1),
                rts111(2),
                ril140(3),
                ll141(5)
                }
        ACCESS  read-write
        STATUS  mandatory
        DESCRIPTION
                "The value of this object defines which circuits
                are monitored to eventually generate the
                corresponding event when the state of one of them
                changes. Main circuits may also be simultaneously
                monitored (see fcfLineV28AsynInDceMonitored1).

                   none : the circuits 111, 140, 141 are not
                        monitored,
                   drs111 : the circuit 111 (data signal rate
                        selector) is monitored,
                   ril140 : the circuit 140 (loopback /
                        maintenance test) is monitored,
                   ll141 : the circuit 141 (local loopback) is
                        monitored.

                The default value is 'none'."
        ::= { fcfLineV28AsynInDceSignalEntry 5 }


    fcfLineV28DteSignalTable OBJECT-TYPE
        SYNTAX  SEQUENCE OF FcfLineV28DteSignalEntry
        ACCESS  not-accessible
        STATUS  mandatory
        DESCRIPTION
                "This table defines how the incoming circuits are
                monitored and interpreted on synchronous V28
                serial line interfaces when the equipment is a
                DTE.

                It is not possible to add or delete an entry of
                this table (each entry corresponds, in
                fcfLineTable, to one instance of fcfLineType equal
                to 'synchronousV28Dte')."
        ::= { fcfLines 11 }


    fcfLineV28DteSignalEntry OBJECT-TYPE
        SYNTAX  FcfLineV28DteSignalEntry
        ACCESS  not-accessible
        STATUS  mandatory
        DESCRIPTION
                "An entry of fcfLineV28DteSignalTable."
        INDEX   { fcfLineV28DteInterfaceId }
        ::= { fcfLineV28DteSignalTable 1 }


        FcfLineV28DteSignalEntry ::=
                SEQUENCE {
                    fcfLineV28DteInterfaceId
                        INTEGER,
                    fcfLineV28DteCts106
                        INTEGER,
                    fcfLineV28DteDsr107
                        INTEGER,
                    fcfLineV28DteDcd109
                        INTEGER,
                    fcfLineV28DteSi117
                        INTEGER,
                    fcfLineV28DteTi142
                        INTEGER,
                    fcfLineV28DteSyn
                        INTEGER
                }


    fcfLineV28DteInterfaceId OBJECT-TYPE
        SYNTAX  INTEGER (0..35)
        ACCESS  read-only
        STATUS  mandatory
        DESCRIPTION
                "The value of this object identifies one and only
                one synchronous V28 DTE serial line interface.
                Each synchronous V28 DTE serial line interface
                corresponds, in fcfLineTable, to one instance of
                fcfLineType equal to 'synchronousV28Dte'.

                This is a decimal integer in the range 0 to 35."
        ::= { fcfLineV28DteSignalEntry 1 }


    fcfLineV28DteCts106 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                106 (ready fo sending) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV28DteSignalEntry 2 }


    fcfLineV28DteDsr107 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                107 (data set ready) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV28DteSignalEntry 3 }


    fcfLineV28DteDcd109 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                109 (data channel received line signal detector)
                is monitored to eventually generate the
                corresponding event when its state changes and,
                when it is monitored, how it is scanned to
                determine whether this serial line interface is up
                or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV28DteSignalEntry 4 }


    fcfLineV28DteSi117 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                117 (standby indicator) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV28DteSignalEntry 5 }


    fcfLineV28DteTi142 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                142 (test indicator) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV28DteSignalEntry 6 }


    fcfLineV28DteSyn OBJECT-TYPE
        SYNTAX  INTEGER {
                notMonitored(1),
                monitoredOff(2),
                monitoredOn(3)
                }
        ACCESS  read-write
        STATUS  mandatory
        DESCRIPTION
                "The value of this object defines how the flags are
                checked to determine whether this serial line
                interface is up or down.

                   notMonitored : the flags are not checked,
                   monitoredOff : the flags are checked and they
                        must be not present to determine that this
                        serial line interface is in the UP state,
                   monitoredOn : the flags are checked and they
                        must be present to determine that this
                        serial line interface is in the UP state.

                The default value is 'monitoredOn'."
        ::= { fcfLineV28DteSignalEntry 7 }


    fcfLineV28DceSignalTable OBJECT-TYPE
        SYNTAX  SEQUENCE OF FcfLineV28DceSignalEntry
        ACCESS  not-accessible
        STATUS  mandatory
        DESCRIPTION
                "This table defines how the incoming circuits are
                monitored and interpreted on synchronous V28
                serial line interfaces when the equipment is a
                DCE.

                It is not possible to add or delete an entry of
                this table (each entry corresponds, in
                fcfLineTable, to one instance of fcfLineType equal
                to 'synchronousV28Dce')."
        ::= { fcfLines 12 }


    fcfLineV28DceSignalEntry OBJECT-TYPE
        SYNTAX  FcfLineV28DceSignalEntry
        ACCESS  not-accessible
        STATUS  mandatory
        DESCRIPTION
                "An entry of fcfLineV28DceSignalTable."
        INDEX   { fcfLineV28DceInterfaceId }
        ::= { fcfLineV28DceSignalTable 1 }


        FcfLineV28DceSignalEntry ::=
                SEQUENCE {
                    fcfLineV28DceInterfaceId
                        INTEGER,
                    fcfLineV28DceRts105
                        INTEGER,
                    fcfLineV28DceDtr108
                        INTEGER,
                    fcfLineV28DceDrs111
                        INTEGER,
                    fcfLineV28DceRil140
                        INTEGER,
                    fcfLineV28DceLl141
                        INTEGER,
                    fcfLineV28DceSyn
                        INTEGER
                }


    fcfLineV28DceInterfaceId OBJECT-TYPE
        SYNTAX  INTEGER (0..35)
        ACCESS  read-only
        STATUS  mandatory
        DESCRIPTION
                "The value of this object identifies one and only
                one synchronous V28 DCE serial line interface.
                Each synchronous V28 DCE serial line interface
                corresponds, in fcfLineTable, to one instance of
                fcfLineType equal to 'synchronousV28Dce'.

                This is a decimal integer in the range 0 to 35."
        ::= { fcfLineV28DceSignalEntry 1 }


    fcfLineV28DceRts105 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                105 (request to send) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV28DceSignalEntry 2 }


    fcfLineV28DceDtr108 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                108 (108/1 connect data set to line, 108/2 data
                terminal ready) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV28DceSignalEntry 3 }


    fcfLineV28DceDrs111 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                111 (data signal rate selector) is monitored to
                eventually generate the corresponding event when
                its state changes and, when it is monitored, how
                it is scanned to determine whether this serial
                line interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV28DceSignalEntry 4 }


    fcfLineV28DceRil140 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                140 (loopback / maintenance test) is monitored to
                eventually generate the corresponding event when
                its state changes and, when it is monitored, how
                it is scanned to determine whether this serial
                line interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV28DceSignalEntry 5 }


    fcfLineV28DceLl141 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                141 (local loopback) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV28DceSignalEntry 6 }


    fcfLineV28DceSyn OBJECT-TYPE
        SYNTAX  INTEGER {
                notMonitored(1),
                monitoredOff(2),
                monitoredOn(3)
                }
        ACCESS  read-write
        STATUS  mandatory
        DESCRIPTION
                "The value of this object defines how the flags are
                checked to determine whether this serial line
                interface is up or down.

                   notMonitored : the flags are not checked,
                   monitoredOff : the flags are checked and they
                        must be not present to determine that this
                        serial line interface is in the UP state,
                   monitoredOn : the flags are checked and they
                        must be present to determine that this
                        serial line interface is in the UP state.

                The default value is 'monitoredOn'."
        ::= { fcfLineV28DceSignalEntry 7 }


    fcfLineV11DteSignalTable OBJECT-TYPE
        SYNTAX  SEQUENCE OF FcfLineV11DteSignalEntry
        ACCESS  not-accessible
        STATUS  mandatory
        DESCRIPTION
                "This table defines how the incoming circuits are
                monitored and interpreted on synchronous V11
                serial line interfaces when the equipment is a
                DTE.

                It is not possible to add or delete an entry of
                this table (each entry corresponds, in
                fcfLineTable, to one instance of fcfLineType equal
                to 'synchronousV11Dte')."
        ::= { fcfLines 15 }


    fcfLineV11DteSignalEntry OBJECT-TYPE
        SYNTAX  FcfLineV11DteSignalEntry
        ACCESS  not-accessible
        STATUS  mandatory
        DESCRIPTION
                "An entry of fcfLineV11DteSignalTable."
        INDEX   { fcfLineV11DteInterfaceId }
        ::= { fcfLineV11DteSignalTable 1 }


        FcfLineV11DteSignalEntry ::=
                SEQUENCE {
                    fcfLineV11DteInterfaceId
                        INTEGER,
                    fcfLineV11DteIndication109
                        INTEGER,
                    fcfLineV11DteSyn
                        INTEGER
                }


    fcfLineV11DteInterfaceId OBJECT-TYPE
        SYNTAX  INTEGER (0..35)
        ACCESS  read-only
        STATUS  mandatory
        DESCRIPTION
                "The value of this object identifies one and only
                one synchronous V11 DTE serial line interface.
                Each synchronous V11 DTE serial line interface
                corresponds, in fcfLineTable, to one instance of
                fcfLineType equal to 'synchronousV11Dte'.

                This is a decimal integer in the range 0 to 35."
        ::= { fcfLineV11DteSignalEntry 1 }


    fcfLineV11DteIndication109 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                109 (I, indication) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV11DteSignalEntry 2 }


    fcfLineV11DteSyn OBJECT-TYPE
        SYNTAX  INTEGER {
                notMonitored(1),
                monitoredOff(2),
                monitoredOn(3)
                }
        ACCESS  read-write
        STATUS  mandatory
        DESCRIPTION
                "The value of this object defines how the flags are
                checked to determine whether this serial line
                interface is up or down.

                   notMonitored : the flags are not checked,
                   monitoredOff : the flags are checked and they
                        must be not present to determine that this
                        serial line interface is in the UP state,
                   monitoredOn : the flags are checked and they
                        must be present to determine that this
                        serial line interface is in the UP state.

                The default value is 'notMonitored'."
        ::= { fcfLineV11DteSignalEntry 3 }


    fcfLineV11DceSignalTable OBJECT-TYPE
        SYNTAX  SEQUENCE OF FcfLineV11DceSignalEntry
        ACCESS  not-accessible
        STATUS  mandatory
        DESCRIPTION
                "This table defines how the incoming circuits are
                monitored and interpreted on synchronous V11
                serial line interfaces when the equipment is a
                DCE.

                It is not possible to add or delete an entry of
                this table (each entry corresponds, in
                fcfLineTable, to one instance of fcfLineType equal
                to 'synchronousV11Dce')."
        ::= { fcfLines 16 }


    fcfLineV11DceSignalEntry OBJECT-TYPE
        SYNTAX  FcfLineV11DceSignalEntry
        ACCESS  not-accessible
        STATUS  mandatory
        DESCRIPTION
                "An entry of fcfLineV11DceSignalTable."
        INDEX   { fcfLineV11DceInterfaceId }
        ::= { fcfLineV11DceSignalTable 1 }


        FcfLineV11DceSignalEntry ::=
                SEQUENCE {
                    fcfLineV11DceInterfaceId
                        INTEGER,
                    fcfLineV11DceControl105
                        INTEGER,
                    fcfLineV11DceSyn
                        INTEGER
                }


    fcfLineV11DceInterfaceId OBJECT-TYPE
        SYNTAX  INTEGER (0..35)
        ACCESS  read-only
        STATUS  mandatory
        DESCRIPTION
                "The value of this object identifies one and only
                one synchronous V11 DCE serial line interface.
                Each synchronous V11 DCE serial line interface
                corresponds, in fcfLineTable, to one instance of
                fcfLineType equal to 'synchronousV11Dce'.

                This is a decimal integer in the range 0 to 35."
        ::= { fcfLineV11DceSignalEntry 1 }


    fcfLineV11DceControl105 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                105 (C, control) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV11DceSignalEntry 2 }


    fcfLineV11DceSyn OBJECT-TYPE
        SYNTAX  INTEGER {
                notMonitored(1),
                monitoredOff(2),
                monitoredOn(3)
                }
        ACCESS  read-write
        STATUS  mandatory
        DESCRIPTION
                "The value of this object defines how the flags are
                checked to determine whether this serial line
                interface is up or down.

                   notMonitored : the flags are not checked,
                   monitoredOff : the flags are checked and they
                        must be not present to determine that this
                        serial line interface is in the UP state,
                   monitoredOn : the flags are checked and they
                        must be present to determine that this
                        serial line interface is in the UP state.

                The default value is 'notMonitored'."
        ::= { fcfLineV11DceSignalEntry 3 }


    fcfLineV35DteSignalTable OBJECT-TYPE
        SYNTAX  SEQUENCE OF FcfLineV35DteSignalEntry
        ACCESS  not-accessible
        STATUS  mandatory
        DESCRIPTION
                "This table defines how the incoming circuits are
                monitored and interpreted on V35 serial line
                interfaces when the equipment is a DTE.

                It is not possible to add or delete an entry of
                this table (each entry corresponds, in
                fcfLineTable, to one instance of fcfLineType equal
                to 'v35Dte')."
        ::= { fcfLines 19 }


    fcfLineV35DteSignalEntry OBJECT-TYPE
        SYNTAX  FcfLineV35DteSignalEntry
        ACCESS  not-accessible
        STATUS  mandatory
        DESCRIPTION
                "An entry of fcfLineV35DteSignalTable."
        INDEX   { fcfLineV35DteInterfaceId }
        ::= { fcfLineV35DteSignalTable 1 }


        FcfLineV35DteSignalEntry ::=
                SEQUENCE {
                    fcfLineV35DteInterfaceId
                        INTEGER,
                    fcfLineV35DteD106
                        INTEGER,
                    fcfLineV35DteE107
                        INTEGER,
                    fcfLineV35DteF109
                        INTEGER,
                    fcfLineV35DteTi142
                        INTEGER,
                    fcfLineV35DteSyn
                        INTEGER
                }


    fcfLineV35DteInterfaceId OBJECT-TYPE
        SYNTAX  INTEGER (0..35)
        ACCESS  read-only
        STATUS  mandatory
        DESCRIPTION
                "The value of this object identifies one and only
                one V35 DTE serial line interface. Each V35 DTE
                serial line interface corresponds, in
                fcfLineTable, to one instance of fcfLineType equal
                to 'v35Dte'.

                This is a decimal integer in the range 0 to 35."
        ::= { fcfLineV35DteSignalEntry 1 }


    fcfLineV35DteD106 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                106 (pin D, ready fo sending) is monitored to
                eventually generate the corresponding event when
                its state changes and, when it is monitored, how
                it is scanned to determine whether this serial
                line interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV35DteSignalEntry 2 }


    fcfLineV35DteE107 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                107 (pin E, data set ready) is monitored to
                eventually generate the corresponding event when
                its state changes and, when it is monitored, how
                it is scanned to determine whether this serial
                line interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV35DteSignalEntry 3 }


    fcfLineV35DteF109 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                109 (pin F, data channel received line signal
                detector) is monitored to eventually generate the
                corresponding event when its state changes and,
                when it is monitored, how it is scanned to
                determine whether this serial line interface is up
                or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV35DteSignalEntry 4 }


    fcfLineV35DteTi142 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                142 (pin NN, test indicator) is monitored to
                eventually generate the corresponding event when
                its state changes and, when it is monitored, how
                it is scanned to determine whether this serial
                line interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV35DteSignalEntry 5 }


    fcfLineV35DteSyn OBJECT-TYPE
        SYNTAX  INTEGER {
                notMonitored(1),
                monitoredOff(2),
                monitoredOn(3)
                }
        ACCESS  read-write
        STATUS  mandatory
        DESCRIPTION
                "The value of this object defines how the flags are
                checked to determine whether this serial line
                interface is up or down.

                   notMonitored : the flags are not checked,
                   monitoredOff : the flags are checked and they
                        must be not present to determine that this
                        serial line interface is in the UP state,
                   monitoredOn : the flags are checked and they
                        must be present to determine that this
                        serial line interface is in the UP state.

                The default value is 'monitoredOn'.."
        ::= { fcfLineV35DteSignalEntry 6 }


    fcfLineV35DceSignalTable OBJECT-TYPE
        SYNTAX  SEQUENCE OF FcfLineV35DceSignalEntry
        ACCESS  not-accessible
        STATUS  mandatory
        DESCRIPTION
                "This table defines how the incoming circuits are
                monitored and interpreted on V35 serial line
                interfaces when the equipment is a DCE.

                It is not possible to add or delete an entry of
                this table (each entry corresponds, in
                fcfLineTable, to one instance of fcfLineType equal
                to 'v35Dce')."
        ::= { fcfLines 20 }


    fcfLineV35DceSignalEntry OBJECT-TYPE
        SYNTAX  FcfLineV35DceSignalEntry
        ACCESS  not-accessible
        STATUS  mandatory
        DESCRIPTION
                "An entry of fcfLineV35DceSignalTable."
        INDEX   { fcfLineV35DceInterfaceId }
        ::= { fcfLineV35DceSignalTable 1 }


        FcfLineV35DceSignalEntry ::=
                SEQUENCE {
                    fcfLineV35DceInterfaceId
                        INTEGER,
                    fcfLineV35DceC105
                        INTEGER,
                    fcfLineV35DceH108
                        INTEGER,
                    fcfLineV35DceRil140
                        INTEGER,
                    fcfLineV35DceLl141
                        INTEGER,
                    fcfLineV35DceSyn
                        INTEGER
                }


    fcfLineV35DceInterfaceId OBJECT-TYPE
        SYNTAX  INTEGER (0..35)
        ACCESS  read-only
        STATUS  mandatory
        DESCRIPTION
                "The value of this object identifies one and only
                one V35 DCE serial line interface. Each V35 DCE
                serial line interface corresponds, in
                fcfLineTable, to one instance of fcfLineType equal
                to 'v35Dce'.

                This is a decimal integer in the range 0 to 35."
        ::= { fcfLineV35DceSignalEntry 1 }


    fcfLineV35DceC105 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                105 (pin C, request to send) is monitored to
                eventually generate the corresponding event when
                its state changes and, when it is monitored, how
                it is scanned to determine whether this serial
                line interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV35DceSignalEntry 2 }


    fcfLineV35DceH108 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                108 (pin H, 108/1 connect data set to line, 108/2
                data terminal ready) is monitored to eventually
                generate the corresponding event when its state
                changes and, when it is monitored, how it is
                scanned to determine whether this serial line
                interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'monitoredOn'."
        ::= { fcfLineV35DceSignalEntry 3 }


    fcfLineV35DceRil140 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                140 (pin N, loopback / maintenance test) is
                monitored to eventually generate the corresponding
                event when its state changes and, when it is
                monitored, how it is scanned to determine whether
                this serial line interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV35DceSignalEntry 4 }


    fcfLineV35DceLl141 OBJECT-TYPE
        SYNTAX  INTEGER {
                notMonitored(1),
                monitoredNotSignificant(2),
                monitoredOff(3),
                monitoredOn(4)
                }
        ACCESS  read-write
        STATUS  mandatory
        DESCRIPTION
                "The value of this object defines how the circuit
                141 (pin L, local loopback) is monitored to
                eventually generate the corresponding event when
                its state changes and, when it is monitored, how
                it is scanned to determine whether this serial
                line interface is up or down.

                   notMonitored : this circuit is not used,
                   monitoredNotSignificant : this circuit is
                        monitored (eventually events are
                        generated) but it is not scanned to
                        determine the state of this serial line
                        interface,
                   monitoredOff : this circuit is monitored
                        (eventually events are generated) and it
                        must be in the OFF condition to determine
                        that this serial line interface is in the
                        UP state,
                   monitoredOn : this circuit is monitored
                        (eventually events are generated) and it
                        must be in the ON condition to determine
                        that this serial line interface is in the
                        UP state.

                The default value is 'notMonitored'."
        ::= { fcfLineV35DceSignalEntry 5 }


    fcfLineV35DceSyn OBJECT-TYPE
        SYNTAX  INTEGER {
                notMonitored(1),
                monitoredOff(2),
                monitoredOn(3)
                }
        ACCESS  read-write
        STATUS  mandatory
        DESCRIPTION
                "The value of this object defines how the flags are
                checked to determine whether this serial line
                interface is up or down.

                   notMonitored : the flags are not checked,
                   monitoredOff : the flags are checked and they
                        must be not present to determine that this
                        serial line interface is in the UP state,
                   monitoredOn : the flags are checked and they
                        must be present to determine that this
                        serial line interface is in the UP state.

                The default value is 'monitoredOn'."
        ::= { fcfLineV35DceSignalEntry 6 }


    fcfLineModem OBJECT IDENTIFIER ::= { fcfLines 30 }


    fcfLineModemTable OBJECT-TYPE
        SYNTAX  SEQUENCE OF FcfLineModemEntry
        ACCESS  not-accessible
        STATUS  mandatory
        DESCRIPTION
                "This table defines, for each serial line interface
                facing to a modem, how this modem is managed.

                It is not possible to add or delete an entry of
                this table (each entry corresponds, in
                fcfLineTable, to one instance of
                fcfLineModemManagement equal to 'on')."
        ::= { fcfLineModem 1 }


    fcfLineModemEntry OBJECT-TYPE
        SYNTAX  FcfLineModemEntry
        ACCESS  not-accessible
        STATUS  mandatory
        DESCRIPTION
                "An entry of fcfLineModemTable."
        INDEX   { fcfLineModInterfaceId }
        ::= { fcfLineModemTable 1 }


        FcfLineModemEntry ::=
                SEQUENCE {
                    fcfLineModInterfaceId
                        INTEGER,
                    fcfLineModType
                        INTEGER,
                    fcfLineModLinkUpTimer
                        INTEGER,
                    fcfLineModNewDiallingTimer
                        INTEGER,
                    fcfLineModDiallingCount
                        INTEGER,
                    fcfLineModUnuseTimer
                        INTEGER,
                    fcfLineModSpeed
                        INTEGER,
                    fcfLineModCallDirection
                        INTEGER,
                    fcfLineModInitString
                        DisplayString,
                    fcfLineModOutputXidString
                        INTEGER,
                    fcfLineModOutputXidStringId
                        INTEGER,
                    fcfLineModInputXidString
                        INTEGER,
                    fcfLineModInputXidStringCount
                        INTEGER
                }


    fcfLineModInterfaceId OBJECT-TYPE
        SYNTAX  INTEGER (0..35)
        ACCESS  read-only
        STATUS  mandatory
        DESCRIPTION
                "The value of this object identifies one and only
                one serial line interface facing to a modem. Each
                of these serial line interfaces corresponds, in
                fcfLineTable, to one instance of
                fcfLineModemManagement equal to 'on'.

                This is a decimal integer in the range 0 to 35."
        ::= { fcfLineModemEntry 1 }


    fcfLineModType OBJECT-TYPE
        SYNTAX  INTEGER {
                direct(1),
                addressedAt(2),
                addressedV25Bis(3)
                }
        ACCESS  read-write
        STATUS  mandatory
        DESCRIPTION
                "The value of this object defines how the automatic
                calling and/or answering data stations is operated
                on this serial line interface :

                   direct : The 'direct call and/or answer
                        controlled by the DTE (circuit 108/1)'
                        mode gives to the equipment (in DTE mode)
                        the capacity of calling a number
                        pre-recorded in the modem (in DCE mode),
                        by means of the 108/1 control circuit. It
                        gives also to the equipment the capacity
                        of accepting incoming calls on a'per call'
                        basis.
                   addressedAt : The 'addressed call and/or answer
                        authorized by the DTE (circuit 108/2)'
                        mode gives to the equipment (in DTE mode)
                        extensive facilities by means of
                        instructions exchanged between the DTE and
                        the DCE on circuits 103 (transmitted data)
                        and 104 (received data). It gives also to
                        the equipment the capacity to accept 'a
                        priori' an incoming call. The commands /
                        indications use the AT format.
                   addressedV25Bis : The 'addressed call and/or
                        answer authorized by the DTE (circuit
                        108/2)' mode gives to the equipment (in
                        DTE mode) extensive facilities by means of
                        instructions exchanged between the DTE and
                        the DCE on circuits 103 (transmitted data)
                        and 104 (received data). It gives also to
                        the equipment the capacity to accept 'a
                        priori' an incoming call. The commands /
                        indications use the ITU-T V.25 bis
                        recommendation format.

                The default value is 'addressedV25Bis'."
        ::= { fcfLineModemEntry 2 }


    fcfLineModLinkUpTimer OBJECT-TYPE
        SYNTAX  INTEGER (1..250)
        ACCESS  read-write
        STATUS  mandatory
        DESCRIPTION
                "The value of this object is the management timer
                in seconds for this serial line interface. It
                starts when the first call request is sent to the
                modem and it is normally stopped when the serial
                line interface is 'up'. The serial line interface
                state is set to 'down' when this timer runs out.
                The value of this timer must be larger than the
                total duration of the successive dialling attempts
                to not interrupt this processing (see
                fcfLineModNewDiallingTimer and
                fcfLineModDiallingCount).

                This is a decimal integer in the range 1 to 250.
                The default value is '180'."
        ::= { fcfLineModemEntry 3 }


    fcfLineModNewDiallingTimer OBJECT-TYPE
        SYNTAX  INTEGER (0..2500)
        ACCESS  read-write
        STATUS  mandatory
        DESCRIPTION
                "The value of this object is the dialling timer in
                seconds for this serial line interface. It starts
                when a call request is sent to the modem and it is
                normally stopped when the call is successfull or
                when the modem answers with an error message. The
                call request is sent again when this timer runs
                out. After transmission of the call request
                fcfLineModDiallingCount times the serial line
                interface state is set to 'down'.

                This is a decimal integer in the range 0 to 2500
                by step of 10.
                The default value is '30'."
        ::= { fcfLineModemEntry 4 }


    fcfLineModDiallingCount OBJECT-TYPE
        SYNTAX  INTEGER (0..250)
        ACCESS  read-write
        STATUS  mandatory
        DESCRIPTION
                "The value of this object is the maximum number of
                attempts to complete a sucessfull call for this
                serial line interface. A new call request is sent
                to the modem when fcfLineModNewDiallingTimer runs
                out.

                This is a decimal integer in the range 0 to 250.
                The default value is '3'."
        ::= { fcfLineModemEntry 5 }


    fcfLineModUnuseTimer OBJECT-TYPE
        SYNTAX  INTEGER (0..254)
        ACCESS  read-write
        STATUS  mandatory
        DESCRIPTION
                "The value of this object is the unuse timer in
                seconds for this serial line interface. This
                function is specified in order to clear a call
                when no communications are established on it. This
                timer starts upon the clearing of the last
                communication using this call and it is normally
                stopped when a new one is initiated. The equipment
                clears the call when this timer runs out. The
                value '0' disables the processing of this timer.

                This is a decimal integer in the range 0 to 250 by
                step of 10.
                The default value is '10'."
        ::= { fcfLineModemEntry 6 }


    fcfLineModSpeed OBJECT-TYPE
        SYNTAX  INTEGER {
                s150(1),
                s300(2),
                s600(3),
                s1200(4),
                s2400(5),
                s4800(9),
                s9600(11),
                s19200(12),
                s28800(13),
                s38400(14),
                s57600(15),
                s115200(16)
                }
        ACCESS  read-write
        STATUS  mandatory
        DESCRIPTION
                "The value of this object indicates the speed in
                bits per second used between the equipment and the
                modem for this serial line interface. The other
                characteristics of this communication are : no
                parity, one stop bit, eight bits per character.

                The default value is 's9600'."
        ::= { fcfLineModemEntry 7 }


    fcfLineModCallDirection OBJECT-TYPE
        SYNTAX  INTEGER {
                calling(3),
                called(2),
                auto(1)
                }
        ACCESS  read-write
        STATUS  mandatory
        DESCRIPTION
                "The value of this object defines the mode used to
                establish the connection with the remote system
                for this serial line interface :
                   calling : the caller is the equipment,
                   called : the caller is the remote system,
                   auto : automatic choise between 'calling' and
                        'called' (not accepted when fcfLineModType
                        is set to 'direct').

                The default value is 'auto'."
        ::= { fcfLineModemEntry 8 }


    fcfLineModInitString OBJECT-TYPE
        SYNTAX  DisplayString (SIZE(0..50))
        ACCESS  read-write
        STATUS  mandatory
        DESCRIPTION
                "The value of this object is a characters string
                sent by the equipment to the modem when the state
                of this serial line interface becomes 'up'.

                This is a 0 to 50 ASCII characters string.
                The default value is the empty string."
        ::= { fcfLineModemEntry 9 }


    fcfLineModOutputXidString OBJECT-TYPE
        SYNTAX  INTEGER {
                off(1),
                on(2)
                }
        ACCESS  read-write
        STATUS  mandatory
        DESCRIPTION
                "The value of this object indicates, for this
                serial line interface, whether an XID string is
                sent by the equipment or not prior to the
                estblishment of any virtual call (exchange
                identification procedure). This XID string is
                defined by fcfLineModOutputXidStringId. This
                mechanism may be enabled only when this serial
                line interface is used by the X25 protocol.

                The default value is 'off'."
        ::= { fcfLineModemEntry 10 }


    fcfLineModOutputXidStringId OBJECT-TYPE
        SYNTAX  INTEGER (0..3)
        ACCESS  read-write
        STATUS  mandatory
        DESCRIPTION
                "The value of this object indicates, for this
                serial line interface, which XID string will be
                sent by the equipment prior to the estblishment of
                any virtual call (exchange identification
                procedure). This XID string is defined in
                fcfLineModXidStringTable.

                This is a decimal integer in the range 0 to 3.
                The default value is '255' meaning 'empty value'
                (blank value on the equipment configurator)."
        ::= { fcfLineModemEntry 11 }


    fcfLineModInputXidString OBJECT-TYPE
        SYNTAX  INTEGER {
                off(1),
                on(2)
                }
        ACCESS  read-write
        STATUS  mandatory
        DESCRIPTION
                "The value of this object indicates, for this
                serial line interface, whether an XID string will
                be received by the equipment or not prior to the
                estblishment of any virtual call (exchange
                identification procedure). If yes
                fcfLineModInputXidStringCount defines how many XID
                strings will be received. This mechanism may be
                enabled only when this serial line interface is
                used by the X25 protocol.

                The default value is 'off'."
        ::= { fcfLineModemEntry 12 }


    fcfLineModInputXidStringCount OBJECT-TYPE
        SYNTAX  INTEGER (0..250)
        ACCESS  read-write
        STATUS  mandatory
        DESCRIPTION
                "The value of this object defines, for this serial
                line interface, how many XID strings will be
                received by the equipment prior to the
                estblishment of any virtual call (exchange
                identification procedure) if this mechanism is
                enabled (see fcfLineModInputXidString).

                This is a decimal integer in the range 0 to 250.
                The default value is '1'."
        ::= { fcfLineModemEntry 13 }


    fcfLineModXidStringTable OBJECT-TYPE
        SYNTAX  SEQUENCE OF FcfLineModXidStringEntry
        ACCESS  not-accessible
        STATUS  mandatory
        DESCRIPTION
                "This table contains the XID strings that are sent
                by the equipment prior to the estblishment of any
                virtual call (exchange identification procedure)
                on serial line interfaces according to
                fcfLineModOutputXidString. An XID string,
                identified by fcfLineModXidStringId, is the
                concatenation, in ascending order of
                fcfLineModXidStringEltNum, of 1 to 4 elements of 0
                to 32 bytes.

                Set any writable object(s) of this table to valid
                value(s) with a new index value to create an entry
                (the objects of the entry not present in this SET
                REQUEST will take their default values). Set
                fcfLineModXidStringEltStatus to 'invalid' to
                delete an entry."
        ::= { fcfLineModem 2 }


    fcfLineModXidStringEntry OBJECT-TYPE
        SYNTAX  FcfLineModXidStringEntry
        ACCESS  not-accessible
        STATUS  mandatory
        DESCRIPTION
                "An entry of fcfLineModXidStringTable."
        INDEX   { fcfLineModXidStringId,
                  fcfLineModXidStringEltNum }
        ::= { fcfLineModXidStringTable 1 }


        FcfLineModXidStringEntry ::=
                SEQUENCE {
                    fcfLineModXidStringId
                        INTEGER,
                    fcfLineModXidStringEltNum
                        INTEGER,
                    fcfLineModXidStringEltStatus
                        INTEGER,
                    fcfLineModXidStringElement
                        OCTET STRING
                }


    fcfLineModXidStringId OBJECT-TYPE
        SYNTAX  INTEGER (0..3)
        ACCESS  read-only
        STATUS  mandatory
        DESCRIPTION
                "The value of this object identifies one and only
                one XID string which is sent by the equipment
                prior to the estblishment of any virtual call
                (exchange identification procedure) on serial line
                interfaces according to fcfLineModOutputXidString.
                This XID string is the concatenation, in ascending
                order of fcfLineModXidStringEltNum, of 1 to 4
                elements of 0 to 32 bytes.

                This is a decimal integer in the range 0 to 3."
        ::= { fcfLineModXidStringEntry 1 }


    fcfLineModXidStringEltNum OBJECT-TYPE
        SYNTAX  INTEGER (1..4)
        ACCESS  read-only
        STATUS  mandatory
        DESCRIPTION
                "The value of this object identifies one and only
                one element of this XID string. The whole XID
                string is the concatenation, in ascending order of
                this value, of all of its elements.

                This is a decimal integer in the range 1 to 4."
        ::= { fcfLineModXidStringEntry 2 }


    fcfLineModXidStringEltStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcfLineModXidStringEntry 3 }


    fcfLineModXidStringElement OBJECT-TYPE
        SYNTAX  OCTET STRING (SIZE(33))
        ACCESS  read-write
        STATUS  mandatory
        DESCRIPTION
                "The value of this object contains the bytes of
                this element of this XID string. The whole XID
                string is the concatenation, in ascending order of
                fcfLineModXidStringEltNum, of all of its elements.

                This is a thirty-three-bytes octet string with up
                to 66 digits in the range 0 to F. The first byte
                contains the number of following useful bytes. It
                must be padded with 'F' digits for a total of 66
                digits.
                The equipment configurator does not need this
                final padding neither the first byte (which is
                automatically updated).

                The default value is 'empty' : first byte set to
                '00', others set to 'FF' (blank value on the
                equipment configurator)."
        ::= { fcfLineModXidStringEntry 4 }


    fcfLineDVBTable OBJECT-TYPE
        SYNTAX  SEQUENCE OF FcfLineDVBEntry
        ACCESS  not-accessible
        STATUS  mandatory
        DESCRIPTION
                ""
        ::= { fcfLines 31 }


    fcfLineDVBEntry OBJECT-TYPE
        SYNTAX  FcfLineDVBEntry
        ACCESS  not-accessible
        STATUS  mandatory
        DESCRIPTION
                "An entry of fcfLineDVBTable."
        INDEX   { fcfLineDVBInterfaceId }
        ::= { fcfLineDVBTable 1 }


        FcfLineDVBEntry ::=
                SEQUENCE {
                    fcfLineDVBInterfaceId
                        INTEGER,
                    fcfLineDVBStatus
                        INTEGER,
                    fcfLineDVBConnection
                        INTEGER
                }


    fcfLineDVBInterfaceId OBJECT-TYPE
        SYNTAX  INTEGER (0..35)
        ACCESS  read-only
        STATUS  mandatory
        DESCRIPTION
                "IF id"
        ::= { fcfLineDVBEntry 1 }


    fcfLineDVBStatus OBJECT-TYPE
        SYNTAX  INTEGER {
                valid(1),
                invalid(2)
                }
        ACCESS  read-write
        STATUS  mandatory
        DESCRIPTION
                "Status"
        ::= { fcfLineDVBEntry 2 }


    fcfLineDVBConnection OBJECT-TYPE
        SYNTAX  INTEGER {
                none(1),
                lsForDvb1(2),
                lsForDvb2(3)
                }
        ACCESS  read-write
        STATUS  mandatory
        DESCRIPTION
                "Link with DVB"
        ::= { fcfLineDVBEntry 3 }


    fcfIsdn OBJECT IDENTIFIER ::= { fcInterfaces 5 }


    fcfIsdnBasicRateInterfaceTable OBJECT-TYPE
        SYNTAX  SEQUENCE OF FcfIsdnBasicRateInterfaceEntry
        ACCESS  not-accessible
        STATUS  mandatory
        DESCRIPTION
                "This table defines the characteristics of the
                integrated services digital network (ISDN) basic
                rate interfaces (BRI).

                It is not possible to add or delete an entry of
                this table (each entry corresponds, in
                fcfPhysicalPortTable, to one instance of
                fcfInterfaceType equal to 'isdnDChannel')."
        ::= { fcfIsdn 1 }


    fcfIsdnBasicRateInterfaceEntry OBJECT-TYPE
        SYNTAX  FcfIsdnBasicRateInterfaceEntry
        ACCESS  not-accessible
        STATUS  mandatory
        DESCRIPTION
                "An entry of fcfIsdnBasicRateInterfaceTable."
        INDEX   { fcfIsdnBasicRateInterfaceId }
        ::= { fcfIsdnBasicRateInterfaceTable 1 }


        FcfIsdnBasicRateInterfaceEntry ::=
                SEQUENCE {
                    fcfIsdnBasicRateInterfaceId
                        INTEGER,
                    fcfIsdnBriSignalling
                        INTEGER,
                    fcfIsdnBriCountry
                        INTEGER,
                    fcfIsdnBriInterfaceCheckPeriod
                        INTEGER,
                    fcfIsdnBriFilterRepeatCount
                        INTEGER,
                    fcfIsdnBriEnablingTimer
                        INTEGER,
                    fcfIsdnBriDisablingTimer
                        INTEGER
                }


    fcfIsdnBasicRateInterfaceId OBJECT-TYPE
        SYNTAX  INTEGER (0..35)
        ACCESS  read-only
        STATUS  mandatory
        DESCRIPTION
                "The value of this object identifies one and only
                one integrated services digital network (ISDN)
                basic rate interface (BRI). Each ISDN BRI
                corresponds, in fcfPhysicalPortTable, to one
                instance of fcfInterfaceType equal to
                'isdnDChannel' or 'isdnBri'.

                This is a decimal integer in the range 0 to 35."
        ::= { fcfIsdnBasicRateInterfaceEntry 1 }


    fcfIsdnBriSignalling OBJECT-TYPE
        SYNTAX  INTEGER {
                off(1),
                on(2)
                }
        ACCESS  read-write
        STATUS  mandatory
        DESCRIPTION
                "The value of this object indicates, for this basic
                rate interface, whether signalling is enabled or
                not. It must be set to 'on' to use the B-channels.

                The default value is 'on'."
        ::= { fcfIsdnBasicRateInterfaceEntry 2 }


    fcfIsdnBriCountry OBJECT-TYPE
        SYNTAX  INTEGER {
                franceVn2(1),
                franceVn3(2),
                unitedKingdom(3),
                switzerland(4),
                europeanIsdn(5),
                japan(6)
                }
        ACCESS  read-write
        STATUS  mandatory
        DESCRIPTION
                "The value of this object permits to take into
                account the national characteristics of some ISDN
                implementations :
                   franceVn2 : France VN 2 implementation,
                   franceVn3 : France VN 3 implementation,
                   franceVn4 : France VN 4 implementation,
                   unitedKingdom : France VN 2 implementation,
                   switzerland : Switzerland implementation,
                   europeanIsdn : Europe implementation.
                   japan : japan implementation.
                   usa : usa implementation.

                The default value is 'europeanIsdn'."
        ::= { fcfIsdnBasicRateInterfaceEntry 3 }


    fcfIsdnBriInterfaceCheckPeriod OBJECT-TYPE
        SYNTAX  INTEGER (0..51000)
        ACCESS  read-write
        STATUS  mandatory
        DESCRIPTION
                "The value of this object indicates a period in
                milliseconds of detection of power source 1 or
                power source 2, whichever may be provided for this
                basic rate interface. The power source is checked
                every fcfIsdnBriInterfaceCheckPeriod milliseconds
                and when it changes and remains changed after
                fcfIsdnBriFilterRepeatCount checkings, this new
                state is delivered to the upper level.

                This is a decimal integer in the range 0 to 51000
                by step of 200.
                The default value is '200'."
        ::= { fcfIsdnBasicRateInterfaceEntry 4 }


    fcfIsdnBriFilterRepeatCount OBJECT-TYPE
        SYNTAX  INTEGER (0..255)
        ACCESS  read-write
        STATUS  mandatory
        DESCRIPTION
                "The value of this object indicates the number of
                detections of power source 1 or power source 2,
                whichever may be provided for this basic rate
                interface. The power source is checked every
                fcfIsdnBriInterfaceCheckPeriod milliseconds and
                when it changes and remains changed after
                fcfIsdnBriFilterRepeatCount checkings, this new
                state is delivered to the upper level.

                This is a decimal integer in the range 0 to 255.
                The default value is '2'."
        ::= { fcfIsdnBasicRateInterfaceEntry 5 }


    fcfIsdnBriEnablingTimer OBJECT-TYPE
        SYNTAX  INTEGER (200..30000)
        ACCESS  read-write
        STATUS  mandatory
        DESCRIPTION
                "The value of this object is the activation timer
                in milliseconds for this basic rate interface
                (timer 3). The deactivation function is specified
                in order to permit this interface and the
                network-side interface to be placed in a low power
                consumption mode when no calls are in progress.
                This timer starts upon the reception of an
                ACTIVATE REQUEST by the layer 1 and it is normally
                stopped when the ACTIVATED state is reached. The
                equipment sends DEACTIVATE INDICATIONS when this
                timer runs out

                This is a decimal integer in the range 200 to
                30000 by step of 200.
                The default value is '10000'."
        ::= { fcfIsdnBasicRateInterfaceEntry 6 }


    fcfIsdnBriDisablingTimer OBJECT-TYPE
        SYNTAX  INTEGER (0..1000)
        ACCESS  read-write
        STATUS  mandatory
        DESCRIPTION
                "The value of this object is the deactivation delay
                in milliseconds for this basic rate interface. The
                deactivation function is specified in order to
                permit this interface and the network-side
                interface to be placed in a low power consumption
                mode when no calls are in progress. The layer 2 is
                informed of the reception of an DEACTIVATE
                INDICATION by the layer 1 when this delay runs
                out.

                This is a decimal integer in the range 0 to 1000
                by step of 200.
                The default value is '600'."
        ::= { fcfIsdnBasicRateInterfaceEntry 7 }


    fcfIsdnPrimaryRateInterfaceTable OBJECT-TYPE
        SYNTAX  SEQUENCE OF FcfIsdnPrimaryRateInterfaceEntry
        ACCESS  not-accessible
        STATUS  mandatory
        DESCRIPTION
                ""
        ::= { fcfIsdn 2 }


    fcfIsdnPrimaryRateInterfaceEntry OBJECT-TYPE
        SYNTAX  FcfIsdnPrimaryRateInterfaceEntry
        ACCESS  not-accessible
        STATUS  mandatory
        DESCRIPTION
                "An entry of fcfIsdnPrimaryRateInterfaceTable."
        INDEX   { fcfIsdnPrimaryRateInterfaceId }
        ::= { fcfIsdnPrimaryRateInterfaceTable 1 }


        FcfIsdnPrimaryRateInterfaceEntry ::=
                SEQUENCE {
                    fcfIsdnPrimaryRateInterfaceId
                        INTEGER,
                    fcfIsdnPriSignalling
                        INTEGER,
                    fcfIsdnPriCountry
                        INTEGER,
                    fcfIsdnPriINbBChannel
                        INTEGER,
                    fcfIsdnPriCrc4
                        INTEGER
                }


    fcfIsdnPrimaryRateInterfaceId OBJECT-TYPE
        SYNTAX  INTEGER (0..35)
        ACCESS  read-only
        STATUS  mandatory
        DESCRIPTION
                "The value of this object identifies one and only
                one integrated services digital network (ISDN)
                primary rate interface (PRI). Each ISDN PRI
                corresponds, in fcfPhysicalPortTable, to one
                instance of fcfInterfaceType equal to 'isdnPri'.

                This is a decimal integer in the range 0 to 35."
        ::= { fcfIsdnPrimaryRateInterfaceEntry 1 }


    fcfIsdnPriSignalling OBJECT-TYPE
        SYNTAX  INTEGER {
                off(1),
                on(2)
                }
        ACCESS  read-write
        STATUS  mandatory
        DESCRIPTION
                "The value of this object indicates, for this
                primary rate interface, whether signalling is
                enabled or not. It must be set to 'on' to use the
                B-channels.

                The default value is 'on'."
        ::= { fcfIsdnPrimaryRateInterfaceEntry 2 }


    fcfIsdnPriCountry OBJECT-TYPE
        SYNTAX  INTEGER {
                franceVn2(1),
                franceVn3(2),
                unitedKingdom(3),
                switzerland(4),
                europeanIsdn(5)
                }
        ACCESS  read-write
        STATUS  mandatory
        DESCRIPTION
                "The value of this object permits to take into
                account the national characteristics of some ISDN
                implementations :
                   franceVn2 : France VN 2 implementation,
                   franceVn3 : France VN 3 implementation,
                   franceVn4 : France VN 4 implementation,
                   unitedKingdom : France VN 2 implementation,
                   switzerland : Switzerland implementation,
                   europeanIsdn : Europe implementation.
                   japan : japan implementation.
                   usa : usa implementation.

                The default value is 'europeanIsdn'."
        ::= { fcfIsdnPrimaryRateInterfaceEntry 3 }


    fcfIsdnPriINbBChannel OBJECT-TYPE
        SYNTAX  INTEGER (0..30)
        ACCESS  read-write
        STATUS  mandatory
        DESCRIPTION
                "The value of this object is the number of B
                channels for this ISDN primary rate interface.

                This is a decimal integer in the range 0 to 30 by
                step of 1.
                The default value is '30'."
        ::= { fcfIsdnPrimaryRateInterfaceEntry 10 }


    fcfIsdnPriCrc4 OBJECT-TYPE
        SYNTAX  INTEGER {
                off(1),
                on(2)
                }
        ACCESS  read-write
        STATUS  mandatory
        DESCRIPTION
                "The value of this object indicates, for this
                primary rate interface, whether cyclic redundancy
                code management is enabled or not.

                The default value is 'off'."
        ::= { fcfIsdnPrimaryRateInterfaceEntry 11 }


    fcfIsdnDChannelSignallingTable OBJECT-TYPE
        SYNTAX  SEQUENCE OF FcfIsdnDChannelSignallingEntry
        ACCESS  not-accessible
        STATUS  mandatory
        DESCRIPTION
                "This table defines the signalling characteristics
                of the integrated services digital network (ISDN)
                basic rate interfaces (BRI).

                It is not possible to add or delete an entry of
                this table (each entry corresponds, in
                fcfIsdnBasicRateInterfaceTable, to one instance of
                fcfIsdnBriSignalling equal to 'on')."
        ::= { fcfIsdn 10 }


    fcfIsdnDChannelSignallingEntry OBJECT-TYPE
        SYNTAX  FcfIsdnDChannelSignallingEntry
        ACCESS  not-accessible
        STATUS  mandatory
        DESCRIPTION
                "An entry of fcfIsdnDChannelSignallingTable."
        INDEX   { fcfIsdnDSigIsdnInterfaceId }
        ::= { fcfIsdnDChannelSignallingTable 1 }


        FcfIsdnDChannelSignallingEntry ::=
                SEQUENCE {
                    fcfIsdnDSigIsdnInterfaceId
                        INTEGER,
                    fcfIsdnDSigIsdnNumber
                        OCTET STRING,
                    fcfIsdnDSigUnuseTimer
                        INTEGER,
                    fcfIsdnDSigCalledSubAddressCheck
                        INTEGER,
                    fcfIsdnDSigDirectInwardDialingCheck
                        INTEGER,
                    fcfIsdnDSigInactivityTimer
                        INTEGER,
                    fcfIsdnDSigMulDialsRetryTimer
                        INTEGER,
                    fcfIsdnDSigMulDialsCycleTimer
                        INTEGER,
                    fcfIsdnDSigMulDialsCycleCount
                        INTEGER,
                    fcfIsdnDSigMulDialsTotalDuration
                        INTEGER,
                    fcfIsdnDSigLowLayerCompatibility
                        INTEGER,
                    fcfIsdnDSigHighLayerCompatibility
                        INTEGER,
                    fcfIsdnDSigHighLayerCharactIdent
                        INTEGER
                }


    fcfIsdnDSigIsdnInterfaceId OBJECT-TYPE
        SYNTAX  INTEGER (0..35)
        ACCESS  read-only
        STATUS  mandatory
        DESCRIPTION
                "The value of this object identifies one and only
                one integrated services digital network (ISDN)
                basic rate interface (BRI) with signalling
                procedures. Each ISDN BRI corresponds, in
                fcfIsdnBasicRateInterfaceTable, to one instance of
                fcfIsdnBriSignalling equal to 'on'.

                This is a decimal integer in the range 0 to 35."
        ::= { fcfIsdnDChannelSignallingEntry 1 }


    fcfIsdnDSigIsdnNumber OBJECT-TYPE
        SYNTAX  OCTET STRING (SIZE(11))
        ACCESS  read-write
        STATUS  mandatory
        DESCRIPTION
                "The value of this object indicates the ISDN
                address (the ISDN number and the optional
                subaddress) of this basic rate interface.

                This is a eleven-bytes octet string with :
                   up to 16 digits in the range 0 to 9 for the
                        ISDN number,
                   an optional separator marking the end of the
                        ISDN number and the beginning of the ISDN
                        subaddress : digit 'A' (':' on the
                        equipment configurator),
                   optional 1 to 4 digits in the range 0 to 9 for
                        the ISDN subaddress,
                   mandatory 'F' digits to pad the value until a
                        total of 22 digits (the equipment
                        configurator does not need this final
                        padding).

                The default value is 'FF FF FF FF FF FF FF FF FF
                FF FF' meaning 'empty value' (blank value on the
                equipment configurator)."
        ::= { fcfIsdnDChannelSignallingEntry 2 }


    fcfIsdnDSigUnuseTimer OBJECT-TYPE
        SYNTAX  INTEGER (0..2550)
        ACCESS  read-write
        STATUS  mandatory
        DESCRIPTION
                "The value of this object is the unuse timer in
                seconds for this basic rate interface. This
                function is specified in order to clear a call
                when no communications are established on it. This
                timer starts upon the clearing of the last
                communication using this call and it is normally
                stopped when a new one is initiated. The equipment
                clears the call when this timer runs out. The
                value '0' disables the processing of this timer.

                This is a decimal integer in the range 0 to 2550
                by step of 10.
                The default value is '10'."
        ::= { fcfIsdnDChannelSignallingEntry 3 }


    fcfIsdnDSigCalledSubAddressCheck OBJECT-TYPE
        SYNTAX  INTEGER {
                off(1),
                on(2)
                }
        ACCESS  read-write
        STATUS  mandatory
        DESCRIPTION
                "The value of this object indicates, for this basic
                rate interface, whether ISDN subaddresses are
                checked or not. When it is set to 'on' the
                incoming calls are cleared if the called party
                subaddress is not present in the SETUP message.

                The default value is 'off'."
        ::= { fcfIsdnDChannelSignallingEntry 4 }


    fcfIsdnDSigDirectInwardDialingCheck OBJECT-TYPE
        SYNTAX  INTEGER {
                off(1),
                on(2)
                }
        ACCESS  read-write
        STATUS  mandatory
        DESCRIPTION
                "The value of this object indicates, for this basic
                rate interface, whether the direct dialling-in
                (DDI) service is used or not. When the direct
                dialling-in is in use, this basic rate interface
                accepts only the incoming calls with the called
                party number equal to its own ISDN number defined
                by fcfIsdnDSigIsdnNumber (the ISDN subaddress is
                not concerned).

                The default value is 'off'."
        ::= { fcfIsdnDChannelSignallingEntry 5 }


    fcfIsdnDSigInactivityTimer OBJECT-TYPE
        SYNTAX  INTEGER (0..120)
        ACCESS  read-write
        STATUS  mandatory
        DESCRIPTION
                "The value of this object is the inactivity timer
                in seconds for this basic rate interface. This
                timer starts upon the establishment of the call
                and it restarts at each expiry if no trafic has
                been using it during this period.. The value '0'
                disables the processing of this timer.

                This is a decimal integer in the range 0 to 120.
                The default value is '0'."
        ::= { fcfIsdnDChannelSignallingEntry 6 }


    fcfIsdnDSigMulDialsRetryTimer OBJECT-TYPE
        SYNTAX  INTEGER (1..254)
        ACCESS  read-write
        STATUS  mandatory
        DESCRIPTION
                "The value of this object is the retry timer in
                seconds for this basic rate interface. To reach a
                particular destination the equipment may
                successively try one or several times to call one
                remote ISDN interfaces. This timer starts when a
                call is initiated towards a particular remote ISDN
                interface and it is normally stopped when this
                call is successfull. A new call towards this
                remote ISDN interface is initated when this timer
                runs out.

                This is a decimal integer in the range 1 to 254.
                The default value is '5'."
        ::= { fcfIsdnDChannelSignallingEntry 10 }


    fcfIsdnDSigMulDialsCycleTimer OBJECT-TYPE
        SYNTAX  INTEGER (1..254)
        ACCESS  read-write
        STATUS  mandatory
        DESCRIPTION
                "The value of this object is the cycle timer in
                seconds for this basic rate interface. To reach a
                particular destination the equipment may
                successively try one or several times to call one
                or several remote ISDN interfaces. This is a cycle
                of calls and there may be several identical
                cycles. The cycle timer starts when a cycle of
                calls is initiated and it is normally stopped when
                one call is successfull. A new cycle of calls is
                initated when this timer runs out.

                This is a decimal integer in the range 1 to 254.
                The default value is '10'."
        ::= { fcfIsdnDChannelSignallingEntry 11 }


    fcfIsdnDSigMulDialsCycleCount OBJECT-TYPE
        SYNTAX  INTEGER (1..255)
        ACCESS  read-write
        STATUS  mandatory
        DESCRIPTION
                "The value of this object is the maximum number of
                cycle of calls for this basic rate interface. To
                reach a particular destination the equipment may
                successively try one or several times to call one
                or several remote ISDN interfaces. This is a cycle
                of calls and there may be several identical
                cycles.

                This is a decimal integer in the range 1 to 255.
                The default value is '3'."
        ::= { fcfIsdnDChannelSignallingEntry 12 }


    fcfIsdnDSigMulDialsTotalDuration OBJECT-TYPE
        SYNTAX  INTEGER (5..100)
        ACCESS  read-write
        STATUS  mandatory
        DESCRIPTION
                "The value of this object is, for this basic rate
                interface, the maximum duration in seconds of
                successive tries to reach a destination. To reach
                a particular destination the equipment may
                successively try one or several times to call one
                or several remote ISDN interfaces. This is a cycle
                of calls and there may be several identical
                cycles. This timer starts when the first cycle of
                calls is initiated and it is normally stopped when
                one call is successfull. If this timer runs out
                the destination is said unreachable.

                This is a decimal integer in the range 5 to 100.
                The default value is '100'."
        ::= { fcfIsdnDChannelSignallingEntry 13 }


    fcfIsdnDSigLowLayerCompatibility OBJECT-TYPE
        SYNTAX  INTEGER {
                notTransmittedAndNotChecked(1),
                transmittedAndNotChecked(2),
                notTransmittedAndChecked(3),
                transmittedAndChecked(4)
                }
        ACCESS  read-write
        STATUS  mandatory
        DESCRIPTION
                "The value of this object indicates whether the low
                layer compatibility information element (LLC IE)
                is present or not in the CONNECT and SETUP call
                establishment messages sent from this basic rate
                interface (outgoing call) and whether it is
                checked or not in the same messages received by
                this basic rate interface (incoming call).

                The checking of LLC IE in the incoming calls is
                made as described below :
                   the coding standard must be set to 'CCITT
                        standardized coding',
                   the information transfer capability must be set
                        to 'unrestricted digital information',
                   the transfer mode must be set to 'circuit
                        mode',
                   the information transfer rate must be set to
                        '64 kbit/s',
                   the user information layer 1 protocol must be
                        set to 'CCITT standardized rate adaption
                        X.31 HDLC flag stuffing',
                   the user information layer 2 protocol must be
                        set to 'CCITT Recommendation X.25 link
                        layer' or 'CCITT Recommendation X.25
                        multilink',
                   the user information layer 3 protocol must be
                        set to 'CCITT Recommendation X.25 packet
                        layer',
                   the other octets of the LLC IE are not checked,

                This object may be set to one of the following
                values :
                   notTransmittedAndNotChecked : the LLC IE is not
                        present in the outgoing calls and it is
                        not checked in the incoming calls,
                   transmittedAndNotChecked : the LLC IE is
                        present in the outgoing calls and it is
                        not checked in the incoming calls,
                   notTransmittedAndChecked : the LLC IE is not
                        present in the outgoing calls and it is
                        checked in the incoming calls,
                   transmittedAndChecked : the LLC IE is present
                        in the outgoing calls and it is checked in
                        the incoming calls.

                The default value is 'notTransmittedAndChecked'."
        ::= { fcfIsdnDChannelSignallingEntry 20 }


    fcfIsdnDSigHighLayerCompatibility OBJECT-TYPE
        SYNTAX  INTEGER {
                notTransmittedAndNotChecked(1),
                transmittedAndNotChecked(2),
                notTransmittedAndChecked(3),
                transmittedAndChecked(4)
                }
        ACCESS  read-write
        STATUS  mandatory
        DESCRIPTION
                "The value of this object indicates whether the
                high layer compatibility information element (HLC
                IE) is present or not in the SETUP call
                establishment messages sent from this basic rate
                interface (outgoing call) and whether it is
                checked or not in the same messages received by
                this basic rate interface (incoming call).

                The checking of HLC IE in the incoming calls
                consists in verifying that the HLC IE is equal to
                the value of fcfIsdnDSigHighLayerCharactIdent.

                This object may be set to one of the following
                values :
                   notTransmittedAndNotChecked : the HLC IE is not
                        present in the outgoing calls and it is
                        not checked in the incoming calls,
                   transmittedAndNotChecked : the HLC IE is
                        present in the outgoing calls and it is
                        not checked in the incoming calls,
                   notTransmittedAndChecked : the HLC IE is not
                        present in the outgoing calls and it is
                        checked in the incoming calls,
                   transmittedAndChecked : the HLC IE is present
                        in the outgoing calls and it is checked in
                        the incoming calls.

                The default value is 'notTransmittedAndChecked'."
        ::= { fcfIsdnDChannelSignallingEntry 21 }


    fcfIsdnDSigHighLayerCharactIdent OBJECT-TYPE
        SYNTAX  INTEGER {
                ccittOsiApplication(193),
                nationalUnknownNetworkedService(128),
                nationalNotStandardizedApplication(255)
                }
        ACCESS  read-write
        STATUS  mandatory
        DESCRIPTION
                "The value of this object indicates the value of
                the high layer compatibility information element
                (HLC IE) which must be present in the SETUP call
                establishment messages received by this basic rate
                interface (incoming call) when the checking is
                enabled (see fcfIsdnDSigHighLayerCompatibility) :

                ccittOsiApplication :
                   the coding standard must be set to 'CCITT
                        standardized coding',
                   the interpretation must be set to 'first
                        (primary only) high layer characteristics
                        identification to be used in the call',
                   the presentation method of protocol profile
                        must be set to 'high layer protocol
                        profile (without specification of
                        attributes)',
                   the high layer characteristics identification
                        must be set to 'OSI application
                        (recommendation X.200 series)',

                nationalUnknownNetworkedService :
                   the coding standard must be set to 'national
                        standard (only when the desired HLC cannot
                        be represented with the CCITT-standardized
                        coding)',
                   the interpretation must be set to 'first
                        (primary only) high layer characteristics
                        identification to be used in the call',
                   the presentation method of protocol profile
                        must be set to 'high layer protocol
                        profile (without specification of
                        attributes)',
                   the high layer characteristics identification
                        must be set to 'unknown networked
                        service',

                nationalNotStandardizedApplication :
                   the coding standard must be set to 'national
                        standard (only when the desired HLC cannot
                        be represented with the CCITT-standardized
                        coding)',
                   the interpretation must be set to 'first
                        (primary only) high layer characteristics
                        identification to be used in the call',
                   the presentation method of protocol profile
                        must be set to 'high layer protocol
                        profile (without specification of
                        attributes)',
                   the high layer characteristics identification
                        must be set to 'not standardized
                        application',

                The default value is 'notTransmittedAndChecked'."
        ::= { fcfIsdnDChannelSignallingEntry 22 }


    fcfIsdnDChannelSigTimerTable OBJECT-TYPE
        SYNTAX  SEQUENCE OF FcfIsdnDChannelSigTimerEntry
        ACCESS  not-accessible
        STATUS  mandatory
        DESCRIPTION
                "This table defines the signalling timers of the
                integrated services digital network (ISDN) basic
                rate interfaces (BRI).

                It is not possible to add or delete an entry of
                this table (each entry corresponds, in
                fcfIsdnBasicRateInterfaceTable, to one instance of
                fcfIsdnBriSignalling equal to 'on')."
        ::= { fcfIsdn 11 }


    fcfIsdnDChannelSigTimerEntry OBJECT-TYPE
        SYNTAX  FcfIsdnDChannelSigTimerEntry
        ACCESS  not-accessible
        STATUS  mandatory
        DESCRIPTION
                "An entry of fcfIsdnDChannelSigTimerTable."
        INDEX   { fcfIsdnDTimIsdnInterfaceId }
        ::= { fcfIsdnDChannelSigTimerTable 1 }


        FcfIsdnDChannelSigTimerEntry ::=
                SEQUENCE {
                    fcfIsdnDTimIsdnInterfaceId
                        INTEGER,
                    fcfIsdnDTimBChannelUpTimer
                        INTEGER,
                    fcfIsdnDTimT301AlertConnectTimer
                        INTEGER,
                    fcfIsdnDTimT303SetupResponseTimer
                        INTEGER,
                    fcfIsdnDTimT305DisconnectResponseTimer
                        INTEGER,
                    fcfIsdnDTimT308ReleaseResponseTimer
                        INTEGER,
                    fcfIsdnDTimT309DataLinkFailureTimer
                        INTEGER,
                    fcfIsdnDTimT310CallProceedingTimer
                        INTEGER,
                    fcfIsdnDTimT313ConnectAcknowledgeTimer
                        INTEGER
                }


    fcfIsdnDTimIsdnInterfaceId OBJECT-TYPE
        SYNTAX  INTEGER (0..35)
        ACCESS  read-only
        STATUS  mandatory
        DESCRIPTION
                "The value of this object identifies one and only
                one integrated services digital network (ISDN)
                basic rate interface (BRI) with signalling
                procedures. Each ISDN BRI corresponds, in
                fcfIsdnBasicRateInterfaceTable, to one instance of
                fcfIsdnBriSignalling equal to 'on'.

                This is a decimal integer in the range 0 to 35."
        ::= { fcfIsdnDChannelSigTimerEntry 1 }


    fcfIsdnDTimBChannelUpTimer OBJECT-TYPE
        SYNTAX  INTEGER (1..2550)
        ACCESS  read-write
        STATUS  mandatory
        DESCRIPTION
                "The value of this object is the up state timer in
                seconds for this basic rate interface. This timer
                starts when the ISDN call is successfull (i.e., a
                B-channel is established) and it is normally
                stopped when the protocol stack layered on this
                B-channel is in the up state. The call is cleared
                when this timer runs out.

                This is a decimal integer in the range 1 to 2550
                by step of 10.
                The default value is '60'."
        ::= { fcfIsdnDChannelSigTimerEntry 2 }


    fcfIsdnDTimT301AlertConnectTimer OBJECT-TYPE
        SYNTAX  INTEGER (1..2550)
        ACCESS  read-write
        STATUS  mandatory
        DESCRIPTION
                "The value of this object is the T301 timer in
                seconds for this basic rate interface. This timer
                starts when an ALERTING call establishment message
                is received and it is normally stopped when a
                CONNECT message is received. The call is cleared
                when this timer runs out.

                This is a decimal integer in the range 1 to 2550
                by step of 10.
                The default value is '20'."
        ::= { fcfIsdnDChannelSigTimerEntry 10 }


    fcfIsdnDTimT303SetupResponseTimer OBJECT-TYPE
        SYNTAX  INTEGER (1..255)
        ACCESS  read-write
        STATUS  mandatory
        DESCRIPTION
                "The value of this object is the T303 timer in
                seconds for this basic rate interface. This timer
                starts when a SETUP call establishment message is
                sent and it is normally stopped when an ALERTING,
                CONNECT, SETUP ACKNOWLEDGE, CALL PROCEEDING or
                RELEASE COMPLETE message is received. When this
                timer runs out for the first time the equipment
                retransmits the SETUP message and restarts this
                timer. When this timer runs out for the second
                time the equipment clears the call.

                This is a decimal integer in the range 1 to 255.
                The default value is '4'."
        ::= { fcfIsdnDChannelSigTimerEntry 11 }


    fcfIsdnDTimT305DisconnectResponseTimer OBJECT-TYPE
        SYNTAX  INTEGER (1..255)
        ACCESS  read-write
        STATUS  mandatory
        DESCRIPTION
                "The value of this object is the T305 timer in
                seconds for this basic rate interface. This timer
                starts when a DISCONNECT call clearing message is
                sent and it is normally stopped when a RELEASE or
                DISCONNECT message is received. When this timer
                runs out the equipment sent a RELEASE message.

                This is a decimal integer in the range 1 to 255.
                The default value is '30'."
        ::= { fcfIsdnDChannelSigTimerEntry 12 }


    fcfIsdnDTimT308ReleaseResponseTimer OBJECT-TYPE
        SYNTAX  INTEGER (1..255)
        ACCESS  read-write
        STATUS  mandatory
        DESCRIPTION
                "The value of this object is the T308 timer in
                seconds for this basic rate interface. This timer
                starts when a RELEASE call clearing message is
                sent and it is normally stopped when a RELEASE
                COMPLETE or RELEASE message is received. When this
                timer runs out for the first time the equipment
                retransmits the RELEASE message and restarts this
                timer. When this timer runs out for the second
                time the equipment places the B-channel in
                maintenance condition.

                This is a decimal integer in the range 1 to 255.
                The default value is '4'."
        ::= { fcfIsdnDChannelSigTimerEntry 13 }


    fcfIsdnDTimT309DataLinkFailureTimer OBJECT-TYPE
        SYNTAX  INTEGER (0..180)
        ACCESS  read-write
        STATUS  mandatory
        DESCRIPTION
                "The value of this object is the T309 timer in
                seconds for this basic rate interface. This timer
                starts when the data link is disconnected and it
                is normally stopped when it is reconnected. The
                call is cleared when this timer runs out.

                This is a decimal integer in the range 0 to 180.
                The default value is '60'."
        ::= { fcfIsdnDChannelSigTimerEntry 14 }


    fcfIsdnDTimT310CallProceedingTimer OBJECT-TYPE
        SYNTAX  INTEGER (1..255)
        ACCESS  read-write
        STATUS  mandatory
        DESCRIPTION
                "The value of this object is the T310 timer in
                seconds for this basic rate interface. This timer
                starts when a CALL PROCEEDING call establishment
                message is received and it is normally stopped
                when an ALERTING, CONNECT, DISCONNECT or PROGRESS
                message is received. The DISCONNECT message is
                sent when this timer runs out.

                This is a decimal integer in the range 1 to 255.
                The default value is '40'."
        ::= { fcfIsdnDChannelSigTimerEntry 15 }


    fcfIsdnDTimT313ConnectAcknowledgeTimer OBJECT-TYPE
        SYNTAX  INTEGER (1..255)
        ACCESS  read-write
        STATUS  mandatory
        DESCRIPTION
                "The value of this object is the T313 timer in
                seconds for this basic rate interface. This timer
                starts when a CONNECT call establishment message
                is sent and it is normally stopped when a CONNECT
                ACKNOWLEDGE message is received. The DISCONNECT
                message is sent when this timer runs out.

                This is a decimal integer in the range 1 to 255.
                The default value is '4'."
        ::= { fcfIsdnDChannelSigTimerEntry 16 }


    fcfIsdnRemotePeerTable OBJECT-TYPE
        SYNTAX  SEQUENCE OF FcfIsdnRemotePeerEntry
        ACCESS  not-accessible
        STATUS  mandatory
        DESCRIPTION
                "This table contains the interfaces which may be
                connected to the equipment through an ISDN. Each
                of these remote ISDN interfaces is identified by a
                decimal integer in the range 0 to 249.

                Set any writable object(s) of this table to valid
                value(s) with a new index value to create an entry
                (the objects of the entry not present in this SET
                REQUEST will take their default values). Set
                fcfIsdnRemStatus to 'invalid' to delete an entry."
        ::= { fcfIsdn 20 }


    fcfIsdnRemotePeerEntry OBJECT-TYPE
        SYNTAX  FcfIsdnRemotePeerEntry
        ACCESS  not-accessible
        STATUS  mandatory
        DESCRIPTION
                "An entry of fcfIsdnRemotePeerTable."
        INDEX   { fcfIsdnRemRemotePeerId }
        ::= { fcfIsdnRemotePeerTable 1 }


        FcfIsdnRemotePeerEntry ::=
                SEQUENCE {
                    fcfIsdnRemRemotePeerId
                        INTEGER,
                    fcfIsdnRemStatus
                        INTEGER,
                    fcfIsdnRemIsdnNumber
                        OCTET STRING,
                    fcfIsdnRemCallDirection
                        INTEGER
                }


    fcfIsdnRemRemotePeerId OBJECT-TYPE
        SYNTAX  INTEGER (0..999)
        ACCESS  read-only
        STATUS  mandatory
        DESCRIPTION
                "The value of this object identifies one and only
                one remote ISDN interface which may be connected
                to the equipment through an ISDN.

                This is a decimal integer in the range 0 to 249 in
                releases before 4.2, in the range 0 to 999 after."
        ::= { fcfIsdnRemotePeerEntry 1 }


    fcfIsdnRemStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcfIsdnRemotePeerEntry 2 }


    fcfIsdnRemIsdnNumber OBJECT-TYPE
        SYNTAX  OCTET STRING (SIZE(11))
        ACCESS  read-write
        STATUS  mandatory
        DESCRIPTION
                "The value of this object is the ISDN address (the
                ISDN number and the optional subaddress) of this
                remote ISDN interface.

                This is a eleven-bytes octet string with :
                   up to 16 digits in the range 0 to 9 for the
                        ISDN number,
                   an optional separator marking the end of the
                        ISDN number and the beginning of the ISDN
                        subaddress : digit 'A' (':' on the
                        equipment configurator),
                   optional 1 to 4 digits in the range 0 to 9 for
                        the ISDN subaddress,
                   mandatory 'F' digits to pad the value until a
                        total of 22 digits (the equipment
                        configurator does not need this final
                        padding).

                This value is automatically completed by a
                selection of digits from the X121 address when
                this X121 address contains two digits 'A' (':' on
                the equipment configurator) to make the complete
                ISDN address. See, in the fcLogicalPorts group,
                the tables which defines the connections to the
                ISDN remote interfaces.

                The default value is 'FF FF FF FF FF FF FF FF FF
                FF FF' meaning 'empty value' (blank value on the
                equipment configurator)."
        ::= { fcfIsdnRemotePeerEntry 3 }


    fcfIsdnRemCallDirection OBJECT-TYPE
        SYNTAX  INTEGER {
                calling(32),
                called(16),
                auto(48)
                }
        ACCESS  read-write
        STATUS  mandatory
        DESCRIPTION
                "The value of this object defines the mode used to
                establish the call with this remote ISDN interface
                :
                   calling : the caller is one of the ISDN
                        interface of the equipment,
                   called : the caller is this remote ISDN
                        interface,
                   auto : automatic choise between 'calling' and
                        'called'.

                   The default value is 'auto'."
        ::= { fcfIsdnRemotePeerEntry 4 }


    fcfE1Ds1 OBJECT IDENTIFIER ::= { fcInterfaces 15 }


    fcfE1Ds1PhysTable OBJECT-TYPE
        SYNTAX  SEQUENCE OF FcfE1Ds1PhysEntry
        ACCESS  not-accessible
        STATUS  mandatory
        DESCRIPTION
                ""
        ::= { fcfE1Ds1 1 }


    fcfE1Ds1PhysEntry OBJECT-TYPE
        SYNTAX  FcfE1Ds1PhysEntry
        ACCESS  not-accessible
        STATUS  mandatory
        DESCRIPTION
                "An entry of fcfE1Ds1PhysTable."
        INDEX   { fcfE1Ds1PhysIfId }
        ::= { fcfE1Ds1PhysTable 1 }


        FcfE1Ds1PhysEntry ::=
                SEQUENCE {
                    fcfE1Ds1PhysIfId
                        INTEGER,
                    fcfE1Ds1PhysStatus
                        INTEGER,
                    fcfE1Ds1PhysPhysicalPort
                        INTEGER
                }


    fcfE1Ds1PhysIfId OBJECT-TYPE
        SYNTAX  INTEGER (0..35)
        ACCESS  read-only
        STATUS  mandatory
        DESCRIPTION
                "IF E1 ou DS1 Physique id"
        ::= { fcfE1Ds1PhysEntry 1 }


    fcfE1Ds1PhysStatus OBJECT-TYPE
        SYNTAX  INTEGER {
                valid(1),
                invalid(2)
                }
        ACCESS  read-write
        STATUS  mandatory
        DESCRIPTION
                "Status"
        ::= { fcfE1Ds1PhysEntry 2 }


    fcfE1Ds1PhysPhysicalPort OBJECT-TYPE
        SYNTAX  INTEGER (0..35)
        ACCESS  read-write
        STATUS  mandatory
        DESCRIPTION
                "PP E1 ou DS1"
        ::= { fcfE1Ds1PhysEntry 3 }


    fcfE1PhysPortTable OBJECT-TYPE
        SYNTAX  SEQUENCE OF FcfE1PhysPortEntry
        ACCESS  not-accessible
        STATUS  mandatory
        DESCRIPTION
                ""
        ::= { fcfE1Ds1 3 }


    fcfE1PhysPortEntry OBJECT-TYPE
        SYNTAX  FcfE1PhysPortEntry
        ACCESS  not-accessible
        STATUS  mandatory
        DESCRIPTION
                "An entry of fcfE1PhysPortTable."
        INDEX   { fcfE1PhysPortId }
        ::= { fcfE1PhysPortTable 1 }


        FcfE1PhysPortEntry ::=
                SEQUENCE {
                    fcfE1PhysPortId
                        INTEGER,
                    fcfE1PhysPortSynchSrc
                        INTEGER,
                    fcfE1PhysPortFraming
                        INTEGER,
                    fcfE1PhysPortFlowType
                        INTEGER
                }


    fcfE1PhysPortId OBJECT-TYPE
        SYNTAX  INTEGER (0..35)
        ACCESS  read-only
        STATUS  mandatory
        DESCRIPTION
                "PP E1 If id"
        ::= { fcfE1PhysPortEntry 1 }


    fcfE1PhysPortSynchSrc OBJECT-TYPE
        SYNTAX  INTEGER {
                network(1),
                freeRun(2)
                }
        ACCESS  read-write
        STATUS  mandatory
        DESCRIPTION
                "Synchronisation Source"
        ::= { fcfE1PhysPortEntry 2 }


    fcfE1PhysPortFraming OBJECT-TYPE
        SYNTAX  INTEGER {
                doubleframe(1),
                multiframeWithCrc4(2),
                extendedCrc4(3)
                }
        ACCESS  read-write
        STATUS  mandatory
        DESCRIPTION
                "Framing"
        ::= { fcfE1PhysPortEntry 3 }


    fcfE1PhysPortFlowType OBJECT-TYPE
        SYNTAX  INTEGER {
                data(1),
                voice(2),
                voiceAndData(3)
                }
        ACCESS  read-write
        STATUS  mandatory
        DESCRIPTION
                "Type de flux"
        ::= { fcfE1PhysPortEntry 4 }


    fcfE1Ds1ChannelTable OBJECT-TYPE
        SYNTAX  SEQUENCE OF FcfE1Ds1ChannelEntry
        ACCESS  not-accessible
        STATUS  mandatory
        DESCRIPTION
                ""
        ::= { fcfE1Ds1 5 }


    fcfE1Ds1ChannelEntry OBJECT-TYPE
        SYNTAX  FcfE1Ds1ChannelEntry
        ACCESS  not-accessible
        STATUS  mandatory
        DESCRIPTION
                "An entry of fcfE1Ds1ChannelTable."
        INDEX   { fcfE1Ds1ChannelIfId }
        ::= { fcfE1Ds1ChannelTable 1 }


        FcfE1Ds1ChannelEntry ::=
                SEQUENCE {
                    fcfE1Ds1ChannelIfId
                        INTEGER,
                    fcfE1Ds1ChannelStatus
                        INTEGER,
                    fcfE1Ds1ChannelPhysIf
                        INTEGER,
                    fcfE1Ds1ChannelSlots
                        DisplayString
                }


    fcfE1Ds1ChannelIfId OBJECT-TYPE
        SYNTAX  INTEGER (42..181)
        ACCESS  read-only
        STATUS  mandatory
        DESCRIPTION
                "IF E1 ou DS1 Canal id"
        ::= { fcfE1Ds1ChannelEntry 1 }


    fcfE1Ds1ChannelStatus OBJECT-TYPE
        SYNTAX  INTEGER {
                valid(1),
                invalid(2)
                }
        ACCESS  read-write
        STATUS  mandatory
        DESCRIPTION
                "Status"
        ::= { fcfE1Ds1ChannelEntry 2 }


    fcfE1Ds1ChannelPhysIf OBJECT-TYPE
        SYNTAX  INTEGER (0..35)
        ACCESS  read-write
        STATUS  mandatory
        DESCRIPTION
                "Interface E1 ou DS1 Physique"
        ::= { fcfE1Ds1ChannelEntry 3 }


    fcfE1Ds1ChannelSlots OBJECT-TYPE
        SYNTAX  DisplayString (SIZE(0..24))
        ACCESS  read-write
        STATUS  mandatory
        DESCRIPTION
                "Slots"
        ::= { fcfE1Ds1ChannelEntry 4 }


    fcfE1Ds1DropInsertTable OBJECT-TYPE
        SYNTAX  SEQUENCE OF FcfE1Ds1DropInsertEntry
        ACCESS  not-accessible
        STATUS  mandatory
        DESCRIPTION
                ""
        ::= { fcfE1Ds1 10 }


    fcfE1Ds1DropInsertEntry OBJECT-TYPE
        SYNTAX  FcfE1Ds1DropInsertEntry
        ACCESS  not-accessible
        STATUS  mandatory
        DESCRIPTION
                "An entry of fcfE1Ds1DropInsertTable."
        INDEX   { fcfE1Ds1DropInsertIf1,
                  fcfE1Ds1DropInsertIf2 }
        ::= { fcfE1Ds1DropInsertTable 1 }


        FcfE1Ds1DropInsertEntry ::=
                SEQUENCE {
                    fcfE1Ds1DropInsertIf1
                        INTEGER,
                    fcfE1Ds1DropInsertIf2
                        INTEGER,
                    fcfE1Ds1DropInsertStatus
                        INTEGER
                }


    fcfE1Ds1DropInsertIf1 OBJECT-TYPE
        SYNTAX  INTEGER (42..181)
        ACCESS  read-only
        STATUS  mandatory
        DESCRIPTION
                "Interface Canal 1"
        ::= { fcfE1Ds1DropInsertEntry 1 }


    fcfE1Ds1DropInsertIf2 OBJECT-TYPE
        SYNTAX  INTEGER (42..181)
        ACCESS  read-only
        STATUS  mandatory
        DESCRIPTION
                "Interface Canal 2"
        ::= { fcfE1Ds1DropInsertEntry 2 }


    fcfE1Ds1DropInsertStatus OBJECT-TYPE
        SYNTAX  INTEGER {
                valid(1),
                invalid(2)
                }
        ACCESS  read-write
        STATUS  mandatory
        DESCRIPTION
                "Status"
        ::= { fcfE1Ds1DropInsertEntry 3 }


    fcfTokenRing OBJECT IDENTIFIER ::= { fcInterfaces 20 }


    fcfTokenRingTable OBJECT-TYPE
        SYNTAX  SEQUENCE OF FcfTokenRingEntry
        ACCESS  not-accessible
        STATUS  mandatory
        DESCRIPTION
                ""
        ::= { fcfTokenRing 1 }


    fcfTokenRingEntry OBJECT-TYPE
        SYNTAX  FcfTokenRingEntry
        ACCESS  not-accessible
        STATUS  mandatory
        DESCRIPTION
                "An entry of fcfTokenRingTable."
        INDEX   { fcfTokenRingInterfaceId }
        ::= { fcfTokenRingTable 1 }


        FcfTokenRingEntry ::=
                SEQUENCE {
                    fcfTokenRingInterfaceId
                        INTEGER,
                    fcfTokenRingSpeed
                        INTEGER,
                    fcfTokenRingLinkCheckPeriod
                        INTEGER,
                    fcfTokenRingCheckPeriodCount
                        INTEGER
                }


    fcfTokenRingInterfaceId OBJECT-TYPE
        SYNTAX  INTEGER (0..35)
        ACCESS  read-only
        STATUS  mandatory
        DESCRIPTION
                "IF id"
        ::= { fcfTokenRingEntry 1 }


    fcfTokenRingSpeed OBJECT-TYPE
        SYNTAX  INTEGER {
                s4000000(1),
                s16000000(2)
                }
        ACCESS  read-write
        STATUS  mandatory
        DESCRIPTION
                "Vitesse"
        ::= { fcfTokenRingEntry 2 }


    fcfTokenRingLinkCheckPeriod OBJECT-TYPE
        SYNTAX  INTEGER (1..255)
        ACCESS  read-write
        STATUS  mandatory
        DESCRIPTION
                "Periode de surveillance jonction (msec)"
        ::= { fcfTokenRingEntry 3 }


    fcfTokenRingCheckPeriodCount OBJECT-TYPE
        SYNTAX  INTEGER (1..250)
        ACCESS  read-write
        STATUS  mandatory
        DESCRIPTION
                "Confirmation au bout de n periodes"
        ::= { fcfTokenRingEntry 4 }


    fcFrameRelaySwitch OBJECT IDENTIFIER ::= { frxConfig 15 }


    fcFrSwitchingTable OBJECT-TYPE
        SYNTAX  SEQUENCE OF FcFrSwitchingEntry
        ACCESS  not-accessible
        STATUS  mandatory
        DESCRIPTION
                "This table defines the static part of ralaying
                table used by the frame relay switch to establish
                bi-directional connections between PVC
                (Permanenent Virtual Circuit) end points. A PVC
                end point is defined by the couple (interface
                identifier, data link connection identifier)."
        ::= { fcFrameRelaySwitch 1 }


    fcFrSwitchingEntry OBJECT-TYPE
        SYNTAX  FcFrSwitchingEntry
        ACCESS  not-accessible
        STATUS  mandatory
        DESCRIPTION
                "An entry of fcFrSwitchingTable."
        INDEX   { fcFrSwInputInterfaceId,
                  fcFrSwInputDlci }
        ::= { fcFrSwitchingTable 1 }


        FcFrSwitchingEntry ::=
                SEQUENCE {
                    fcFrSwInputInterfaceId
                        INTEGER,
                    fcFrSwInputDlci
                        INTEGER,
                    fcFrSwStatus
                        INTEGER,
                    fcFrSwOutputInterfaceId
                        INTEGER,
                    fcFrSwOutputDlci
                        INTEGER,
                    fcFrSwPriority
                        INTEGER
                }


    fcFrSwInputInterfaceId OBJECT-TYPE
        SYNTAX  INTEGER (0..35)
        ACCESS  read-only
        STATUS  mandatory
        DESCRIPTION
                "The value of this object is the interface
                identifier for this PVC end point. The possible
                values are : '0..35'. If it is unused, the value
                of this parameter is '255'."
        ::= { fcFrSwitchingEntry 1 }


    fcFrSwInputDlci OBJECT-TYPE
        SYNTAX  INTEGER (16..991)
        ACCESS  read-only
        STATUS  mandatory
        DESCRIPTION
                "The value of this object is the Data Link
                Connection Identifier for this PVC end point. The
                possible values are : '0..1023. If it is unused,
                the value of this parameter is '65535'. The PVC
                end point connected to this PVC end point is
                defined by fcFrSwOutputInterfaceId and
                fcFrSwOutputDlci."
        ::= { fcFrSwitchingEntry 2 }


    fcFrSwStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcFrSwitchingEntry 3 }


    fcFrSwOutputInterfaceId OBJECT-TYPE
        SYNTAX  INTEGER (0..35)
        ACCESS  read-write
        STATUS  mandatory
        DESCRIPTION
                "The value of this object is the interface
                identifier for the connected PVC end point. The
                possible values are : '0..35'. If it is unused,
                the value of this parameter is '255'."
        ::= { fcFrSwitchingEntry 4 }


    fcFrSwOutputDlci OBJECT-TYPE
        SYNTAX  INTEGER (16..991)
        ACCESS  read-write
        STATUS  mandatory
        DESCRIPTION
                "The value of this object is the Data Link
                Connection Identifier for the connected PVC end
                point. The possible values are : '0..1023. If it
                is unused, the value of this parameter is '65535'."
        ::= { fcFrSwitchingEntry 5 }


    fcFrSwPriority OBJECT-TYPE
        SYNTAX  INTEGER {
                off(1),
                on(2)
                }
        ACCESS  read-write
        STATUS  mandatory
        DESCRIPTION
                "The value of this object indicates if this PVC end
                point connection is foreground. The default value
                is 'off'."
        ::= { fcFrSwitchingEntry 6 }


    fcLogicalPorts OBJECT IDENTIFIER ::= { frxConfig 20 }


    fclLogicalPortTable OBJECT-TYPE
        SYNTAX  SEQUENCE OF FclLogicalPortEntry
        ACCESS  not-accessible
        STATUS  mandatory
        DESCRIPTION
                "This table defines the parameters of a logical
                port. A logical port permits the transmission
                between systems with a specific stack of
                protocols, over one physical port or more."
        ::= { fcLogicalPorts 1 }


    fclLogicalPortEntry OBJECT-TYPE
        SYNTAX  FclLogicalPortEntry
        ACCESS  not-accessible
        STATUS  mandatory
        DESCRIPTION
                "An entry of fclLogicalPortTable."
        INDEX   { fclLogPortId }
        ::= { fclLogicalPortTable 1 }


        FclLogicalPortEntry ::=
                SEQUENCE {
                    fclLogPortId
                        INTEGER,
                    fclLogPortStatus
                        INTEGER,
                    fclLogPortType
                        INTEGER
                }


    fclLogPortId OBJECT-TYPE
        SYNTAX  INTEGER (0..181)
        ACCESS  read-only
        STATUS  mandatory
        DESCRIPTION
                "The value of this object identifies one and only
                one logical port. The possible values are :
                '0..131. If it is unused, the value of this
                parameter is '255'."
        ::= { fclLogicalPortEntry 1 }


    fclLogPortStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclLogicalPortEntry 2 }


    fclLogPortType OBJECT-TYPE
        SYNTAX  INTEGER {
                ethernet-tr(1),
                asynchronous(10),
                fra(11),
                hdlc(12),
                sdlc(13),
                vip(14),
                bsc3270(15),
                bsc2780or3780(16),
                bscSCT(17),
                x25Access(20),
                x25InDIsdn(21),
                x25InBIsdn(22),
                x25InPstn(23),
                x25InterNode(24),
                x25Mlp(25),
                pppSerialLink(30),
                pppPstn(31),
                pppIsdn(32),
                frCe(40),
                frTe(41),
                frSe(42),
                frSeInBIsdn(45),
                interUnitLink(50)
                }
        ACCESS  read-write
        STATUS  mandatory
        DESCRIPTION
                "The value of this object identifies the stack of
                protocols used by this logical port. The default
                value is 'x25InterNode'."
        ::= { fclLogicalPortEntry 3 }


    fclEthernet OBJECT IDENTIFIER ::= { fcLogicalPorts 2 }


    fclEthernetTable OBJECT-TYPE
        SYNTAX  SEQUENCE OF FclEthernetEntry
        ACCESS  not-accessible
        STATUS  mandatory
        DESCRIPTION
                "This table defines the parameters of an ethernet
                logical port."
        ::= { fclEthernet 1 }


    fclEthernetEntry OBJECT-TYPE
        SYNTAX  FclEthernetEntry
        ACCESS  not-accessible
        STATUS  mandatory
        DESCRIPTION
                "An entry of fclEthernetTable."
        INDEX   { fclEthLogPortId }
        ::= { fclEthernetTable 1 }


        FclEthernetEntry ::=
                SEQUENCE {
                    fclEthLogPortId
                        INTEGER,
                    fclEthInterfaceId
                        INTEGER
                }


    fclEthLogPortId OBJECT-TYPE
        SYNTAX  INTEGER (0..181)
        ACCESS  read-only
        STATUS  mandatory
        DESCRIPTION
                "The value of this object identifies one and only
                one ethernet logical port. The possible values are
                : '0..131'. If it is unused, the value of this
                parameter is '255'."
        ::= { fclEthernetEntry 1 }


    fclEthInterfaceId OBJECT-TYPE
        SYNTAX  INTEGER (0..35)
        ACCESS  read-write
        STATUS  mandatory
        DESCRIPTION
                "The value of this object identifies the ethernet
                interface used by this logical port. The possible
                values are : '0..35'. If it is unused, the value
                of this parameter is '255'."
        ::= { fclEthernetEntry 2 }


    fclAsynchronousAccessLogPort OBJECT IDENTIFIER ::= { fcLogicalPorts 5 }


    fclAsynLogPortTable OBJECT-TYPE
        SYNTAX  SEQUENCE OF FclAsynLogPortEntry
        ACCESS  not-accessible
        STATUS  mandatory
        DESCRIPTION
                "This table defines the general parameters of
                asynchronous logical ports."
        ::= { fclAsynchronousAccessLogPort 1 }


    fclAsynLogPortEntry OBJECT-TYPE
        SYNTAX  FclAsynLogPortEntry
        ACCESS  not-accessible
        STATUS  mandatory
        DESCRIPTION
                "An entry of fclAsynLogPortTable."
        INDEX   { fclAsynLpLogPortId }
        ::= { fclAsynLogPortTable 1 }


        FclAsynLogPortEntry ::=
                SEQUENCE {
                    fclAsynLpLogPortId
                        INTEGER,
                    fclAsynLpInterfaceId
                        INTEGER,
                    fclAsynLpSubscriberNumber
                        OCTET STRING,
                    fclAsynLpConfigId
                        INTEGER,
                    fclAsynLpTerminalType
                        INTEGER
                }


    fclAsynLpLogPortId OBJECT-TYPE
        SYNTAX  INTEGER (0..181)
        ACCESS  read-only
        STATUS  mandatory
        DESCRIPTION
                "The value of this object identifies one and only
                one asynchronous logical port. The possible values
                are : '0..131'. If it is unused, the value of this
                parameter is '255'."
        ::= { fclAsynLogPortEntry 1 }


    fclAsynLpInterfaceId OBJECT-TYPE
        SYNTAX  INTEGER (0..35)
        ACCESS  read-write
        STATUS  mandatory
        DESCRIPTION
                "The value of this object identifies the line
                interface used by this asynchronous logical port.
                The possible values are : '0..35'. If it is
                unused, the value of this parameter is '255'. The
                default value is '255'."
        ::= { fclAsynLogPortEntry 2 }


    fclAsynLpSubscriberNumber OBJECT-TYPE
        SYNTAX  OCTET STRING (SIZE(1))
        ACCESS  read-write
        STATUS  mandatory
        DESCRIPTION
                "The value of this object is the SB number added to
                the DNICZO of the equipment to make the calling
                address in a call sent from this logical port. The
                value must contain 2 digits (digits 0..9). The
                default value is 'FF'."
        ::= { fclAsynLogPortEntry 3 }


    fclAsynLpConfigId OBJECT-TYPE
        SYNTAX  INTEGER (0..199)
        ACCESS  read-write
        STATUS  mandatory
        DESCRIPTION
                "The value of this object identifies the
                asynchronous configuration used by this
                asynchronous logical port. This asynchronous
                configuration must be present in
                fclAsynCfgConfigTable. The possible values are :
                '0..199. If it is unused, the value of this
                parameter is '255'."
        ::= { fclAsynLogPortEntry 4 }


    fclAsynLpTerminalType OBJECT-TYPE
        SYNTAX  INTEGER {
                pad(1),
                videotext(2),
                lowSpeedComputerPort(3),
                lowSpeedComputerPortWithAutoCalls(4),
                kioskClient(7),
                multiStandardPad(6),
                x28Plus(20)
                }
        ACCESS  read-write
        STATUS  mandatory
        DESCRIPTION
                "The value of this object is the type of the
                terminal connected to this asynchronous logical
                port. The default value is 'pad'."
        ::= { fclAsynLogPortEntry 5 }


    fclAsynPadLogPort OBJECT IDENTIFIER ::= { fclAsynchronousAccessLogPort 2 }


    fclAsynPadLpTable OBJECT-TYPE
        SYNTAX  SEQUENCE OF FclAsynPadLpEntry
        ACCESS  not-accessible
        STATUS  mandatory
        DESCRIPTION
                "This table defines the specific parameters of an
                asynchronous logical port when the terminal type
                is 'pad'."
        ::= { fclAsynPadLogPort 1 }


    fclAsynPadLpEntry OBJECT-TYPE
        SYNTAX  FclAsynPadLpEntry
        ACCESS  not-accessible
        STATUS  mandatory
        DESCRIPTION
                "An entry of fclAsynPadLpTable."
        INDEX   { fclAsynPadLpLogPortId }
        ::= { fclAsynPadLpTable 1 }


        FclAsynPadLpEntry ::=
                SEQUENCE {
                    fclAsynPadLpLogPortId
                        INTEGER,
                    fclAsynPadLpLink
                        INTEGER,
                    fclAsynPadLpSpeedDetection
                        INTEGER,
                    fclAsynPadLpEquipment
                        INTEGER,
                    fclAsynPadLpMnemonicType
                        INTEGER,
                    fclAsynPadLpNui
                        INTEGER,
                    fclAsynPadLpCombinedFlowCtrl
                        INTEGER
                }


    fclAsynPadLpLogPortId OBJECT-TYPE
        SYNTAX  INTEGER (0..181)
        ACCESS  read-only
        STATUS  mandatory
        DESCRIPTION
                "The value of this object identifies one and only
                one asynchronous logical port used to connect a
                'pad' terminal. The possible values are :
                '0..131'. If it is unused, the value of this
                parameter is '255'."
        ::= { fclAsynPadLpEntry 1 }


    fclAsynPadLpLink OBJECT-TYPE
        SYNTAX  INTEGER {
                pstn(1),
                leasedLine(2),
                direct(3),
                directWithRtsCtsFlowCtrl(4),
                pstnV25bis(5)
                }
        ACCESS  read-write
        STATUS  mandatory
        DESCRIPTION
                "The value of this object indicates the type of
                link used to connect the terminal to the
                equipment. The default value is 'direct'."
        ::= { fclAsynPadLpEntry 2 }


    fclAsynPadLpSpeedDetection OBJECT-TYPE
        SYNTAX  INTEGER {
                off(1),
                on(2)
                }
        ACCESS  read-write
        STATUS  mandatory
        DESCRIPTION
                "The value of this object indicates if the
                automatic speed detection is used. The default
                value is 'off'."
        ::= { fclAsynPadLpEntry 3 }


    fclAsynPadLpEquipment OBJECT-TYPE
        SYNTAX  INTEGER {
                other(1),
                hpHost(2),
                hpTerminal(3)
                }
        ACCESS  read-write
        STATUS  mandatory
        DESCRIPTION
                "The value of this object indicates the terminal in
                facing. 'other' means 'all equipment except
                Hewlett Packard'. The default value is 'other'."
        ::= { fclAsynPadLpEntry 4 }


    fclAsynPadLpMnemonicType OBJECT-TYPE
        SYNTAX  INTEGER {
                pad(1),
                vdxRemoteAuth(2),
                vdxTeletel(3),
                vdxLocalAuth(4)
                }
        ACCESS  read-write
        STATUS  mandatory
        DESCRIPTION
                "The value of this object indicates the mnemonic
                type. When set to 'pad' the mnemonic must begin
                with a point, the call command is allowed, the X28
                command is allowed, the call data and the password
                are checked by the remote host. When set to
                'vdxRemoteAuth' the mnemonic may optionaly begin
                with a point, the call command is forbidden, the
                X28 command is forbidden, the call data and the
                password are checked by the remote host. When set
                to 'vdxTeletel' the mnemonic may optionaly begin
                with a point, the call command is allowed, the X28
                command is forbidden, the call data and the
                password are checked by the remote host. When set
                to 'vdxLocalAuth' the mnemonic may optionaly begin
                with a point, the call command is forbidden, the
                X28 command is forbidden, the call data and the
                password are checked by the pad. The default is
                'pad'."
        ::= { fclAsynPadLpEntry 5 }


    fclAsynPadLpNui OBJECT-TYPE
        SYNTAX  INTEGER {
                none(1),
                none-rc(7),
                optional-transmitOrRc(6),
                optional-checkNuaOrRc(4),
                mandatory-check(2),
                mandatory-check-nua(3),
                mandatory-transmit(5),
                command-transmitOrRc(11)
                }
        ACCESS  read-write
        STATUS  mandatory
        DESCRIPTION
                "The value of this object indicates the treatment
                of the NUI (Network User Identifier). The
                authorized values are 'none' (not checking),
                'none-rc' (not checking, but reverse charging),
                'optional-transmitOrRc' (The NUI is optional. If
                it is present, the NUI is transmitted, else
                reverse charging), 'optional-checkNuaOrRc' (The
                NUI is optional, if the NUI is present then it is
                checked else reverse charging), 'mandatory-check'
                (The NUI is mandatory and checked),
                'mandatory-check-nua' (The NUI is mandatory and
                checked. After checking, the NUI is coded in NUA),
                'mandatory-transmit' (The NUI is mandatory but not
                checked, and it is transmitted),
                'command-transmitOrRc' (NUI ON or NUI OFF is
                manadatory before a communication). The default
                value is 'none'."
        ::= { fclAsynPadLpEntry 6 }


    fclAsynPadLpCombinedFlowCtrl OBJECT-TYPE
        SYNTAX  INTEGER {
                off(1),
                on(2)
                }
        ACCESS  read-write
        STATUS  mandatory
        DESCRIPTION
                "The value of this object indicates wheter combined
                flow control (by XON/XOFF and RTS/CTS) is enabled
                or not. The default value is 'off'."
        ::= { fclAsynPadLpEntry 7 }


    fclAsynPadHomePageTable OBJECT-TYPE
        SYNTAX  SEQUENCE OF FclAsynPadHomePageEntry
        ACCESS  not-accessible
        STATUS  mandatory
        DESCRIPTION
                "This table defines the home page of the PAD. The
                home page is made of blocks. Each block contains a
                message and its graphical attributes."
        ::= { fclAsynPadLogPort 10 }


    fclAsynPadHomePageEntry OBJECT-TYPE
        SYNTAX  FclAsynPadHomePageEntry
        ACCESS  not-accessible
        STATUS  mandatory
        DESCRIPTION
                "An entry of fclAsynPadHomePageTable."
        INDEX   { fclAsynPadPageBlocId }
        ::= { fclAsynPadHomePageTable 1 }


        FclAsynPadHomePageEntry ::=
                SEQUENCE {
                    fclAsynPadPageBlocId
                        INTEGER,
                    fclAsynPadPageStatus
                        INTEGER,
                    fclAsynPadPageMessage
                        DisplayString,
                    fclAsynPadPageAttributes
                        OCTET STRING
                }


    fclAsynPadPageBlocId OBJECT-TYPE
        SYNTAX  INTEGER (0..19)
        ACCESS  read-only
        STATUS  mandatory
        DESCRIPTION
                "The value of this object is the block identifier.
                The possible values are '0..99'. If it is unused,
                the value is '255'."
        ::= { fclAsynPadHomePageEntry 1 }


    fclAsynPadPageStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclAsynPadHomePageEntry 2 }


    fclAsynPadPageMessage OBJECT-TYPE
        SYNTAX  DisplayString (SIZE(0..12))
        ACCESS  read-write
        STATUS  mandatory
        DESCRIPTION
                "The value of this object is the message. This
                message may contains from 0 to 12 characters. The
                default value is the empty string."
        ::= { fclAsynPadHomePageEntry 3 }


    fclAsynPadPageAttributes OBJECT-TYPE
        SYNTAX  OCTET STRING (SIZE(11))
        ACCESS  read-write
        STATUS  mandatory
        DESCRIPTION
                "The value of this object defines the attributes
                used to display the message. 11 bytes from 00 to
                FF must be specified. The first byte contains the
                number of following useful bytes. The trailing
                bytes must be set to 'FF'. The equipment
                configurator does not need this final completion.
                The default value is 'empty' (first byte set to
                '00')."
        ::= { fclAsynPadHomePageEntry 4 }


    fclAsynVdxLogPort OBJECT IDENTIFIER ::= { fclAsynchronousAccessLogPort 3 }


    fclAsynVdxLpTable OBJECT-TYPE
        SYNTAX  SEQUENCE OF FclAsynVdxLpEntry
        ACCESS  not-accessible
        STATUS  mandatory
        DESCRIPTION
                "This table defines the specific parameters of an
                asynchronous logical port when the terminal type
                is 'videotext'."
        ::= { fclAsynVdxLogPort 1 }


    fclAsynVdxLpEntry OBJECT-TYPE
        SYNTAX  FclAsynVdxLpEntry
        ACCESS  not-accessible
        STATUS  mandatory
        DESCRIPTION
                "An entry of fclAsynVdxLpTable."
        INDEX   { fclAsynVdxLpLogPortId }
        ::= { fclAsynVdxLpTable 1 }


        FclAsynVdxLpEntry ::=
                SEQUENCE {
                    fclAsynVdxLpLogPortId
                        INTEGER,
                    fclAsynVdxLpLink
                        INTEGER,
                    fclAsynVdxLpMnemonicType
                        INTEGER,
                    fclAsynVdxLpNui
                        INTEGER,
                    fclAsynVdxLpParityBit
                        INTEGER,
                    fclAsynVdxLpPceSubThreshold
                        INTEGER,
                    fclAsynVdxLpPceNackTimer
                        INTEGER
                }


    fclAsynVdxLpLogPortId OBJECT-TYPE
        SYNTAX  INTEGER (0..181)
        ACCESS  read-only
        STATUS  mandatory
        DESCRIPTION
                "The value of this object identifies one and only
                one asynchronous logical port used to connect a
                'videotext' terminal. The possible values are :
                '0..131'. If it is unused, the value of this
                parameter is '255'."
        ::= { fclAsynVdxLpEntry 1 }


    fclAsynVdxLpLink OBJECT-TYPE
        SYNTAX  INTEGER {
                pstn(1),
                leasedLine(2),
                direct(3),
                directWithRtsCtsFlowCtrl(4),
                pstnV25bis(5)
                }
        ACCESS  read-write
        STATUS  mandatory
        DESCRIPTION
                "The value of this object indicates the type of
                link used to connect the terminal to the
                equipment. The default value is 'direct'."
        ::= { fclAsynVdxLpEntry 2 }


    fclAsynVdxLpMnemonicType OBJECT-TYPE
        SYNTAX  INTEGER {
                pad(1),
                vdxRemoteAuth(2),
                vdxTeletel(3),
                vdxLocalAuth(4)
                }
        ACCESS  read-write
        STATUS  mandatory
        DESCRIPTION
                "The value of this object indicates the mnemonic
                type. When set to 'pad' the mnemonic must begin
                with a point, the call command is allowed, the X28
                command is allowed, the call data and the password
                are checked by the remote host. When set to
                'vdxRemoteAuth' the mnemonic may optionaly begin
                with a point, the call command is forbidden, the
                X28 command is forbidden, the call data and the
                password are checked by the remote host. When set
                to 'vdxTeletel' the mnemonic may optionaly begin
                with a point, the call command is allowed, the X28
                command is forbidden, the call data and the
                password are checked by the remote host. When set
                to 'vdxLocalAuth' the mnemonic may optionaly begin
                with a point, the call command is forbidden, the
                X28 command is forbidden, the call data and the
                password are checked by the pad. The default is
                'pad'."
        ::= { fclAsynVdxLpEntry 5 }


    fclAsynVdxLpNui OBJECT-TYPE
        SYNTAX  INTEGER {
                none(1),
                none-rc(7),
                optional-transmitOrRc(6),
                optional-checkNuaOrRc(4),
                mandatory-check(2),
                mandatory-check-nua(3),
                mandatory-transmit(5),
                command-transmitOrRc(11)
                }
        ACCESS  read-write
        STATUS  mandatory
        DESCRIPTION
                "The value of this object indicates the treatment
                of the NUI (Network User Identifier). The
                authorized values are 'none' (not checking),
                'none-rc' (not checking, but reverse charging),
                'optional-transmitOrRc' (The NUI is optional. If
                it is present, the NUI is transmitted, else
                reverse charging), 'optional-checkNuaOrRc' (The
                NUI is optional, if the NUI is present then it is
                checked else reverse charging), 'mandatory-check'
                (The NUI is mandatory and checked),
                'mandatory-check-nua' (The NUI is mandatory and
                checked. After checking, the NUI is coded in NUA),
                'mandatory-transmit' (The NUI is mandatory but not
                checked, and it is transmitted),
                'command-transmitOrRc' (NUI ON or NUI OFF is
                manadatory before a communication). The default
                value is 'none'."
        ::= { fclAsynVdxLpEntry 6 }


    fclAsynVdxLpParityBit OBJECT-TYPE
        SYNTAX  INTEGER {
                none(1),
                setTo1(2)
                }
        ACCESS  read-write
        STATUS  mandatory
        DESCRIPTION
                "Parite X25"
        ::= { fclAsynVdxLpEntry 10 }


    fclAsynVdxLpPceSubThreshold OBJECT-TYPE
        SYNTAX  INTEGER (1..254)
        ACCESS  read-write
        STATUS  mandatory
        DESCRIPTION
                "Seuil de Comptage SUB (PCE)"
        ::= { fclAsynVdxLpEntry 11 }


    fclAsynVdxLpPceNackTimer OBJECT-TYPE
        SYNTAX  INTEGER (100..25400)
        ACCESS  read-write
        STATUS  mandatory
        DESCRIPTION
                "Tempo d'emission NACK (PCE) msec"
        ::= { fclAsynVdxLpEntry 12 }


    fclAsynVdxHomePageTable OBJECT-TYPE
        SYNTAX  SEQUENCE OF FclAsynVdxHomePageEntry
        ACCESS  not-accessible
        STATUS  mandatory
        DESCRIPTION
                "This table defines the home page of the VIDEOTEXT
                PAD. The home page is made of blocks. Each block
                contains a message and its graphical attributes."
        ::= { fclAsynVdxLogPort 10 }


    fclAsynVdxHomePageEntry OBJECT-TYPE
        SYNTAX  FclAsynVdxHomePageEntry
        ACCESS  not-accessible
        STATUS  mandatory
        DESCRIPTION
                "An entry of fclAsynVdxHomePageTable."
        INDEX   { fclAsynVdxPageBlocId }
        ::= { fclAsynVdxHomePageTable 1 }


        FclAsynVdxHomePageEntry ::=
                SEQUENCE {
                    fclAsynVdxPageBlocId
                        INTEGER,
                    fclAsynVdxPageStatus
                        INTEGER,
                    fclAsynVdxPageMessage
                        DisplayString,
                    fclAsynVdxPageAttributes
                        OCTET STRING
                }


    fclAsynVdxPageBlocId OBJECT-TYPE
        SYNTAX  INTEGER (0..99)
        ACCESS  read-only
        STATUS  mandatory
        DESCRIPTION
                "The value of this object is the block identifier.
                The possible values are '0..99'. If it is unused,
                the value is '255'."
        ::= { fclAsynVdxHomePageEntry 1 }


    fclAsynVdxPageStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclAsynVdxHomePageEntry 2 }


    fclAsynVdxPageMessage OBJECT-TYPE
        SYNTAX  DisplayString (SIZE(0..12))
        ACCESS  read-write
        STATUS  mandatory
        DESCRIPTION
                "The value of this object is the message. This
                message may contains from 0 to 12 characters. The
                default value is the empty string."
        ::= { fclAsynVdxHomePageEntry 3 }


    fclAsynVdxPageAttributes OBJECT-TYPE
        SYNTAX  OCTET STRING (SIZE(11))
        ACCESS  read-write
        STATUS  mandatory
        DESCRIPTION
                "The value of this object defines the attributes
                used to display the message. 11 bytes from 00 to
                FF must be specified. The first byte contains the
                number of following useful bytes. The trailing
                bytes must be set to 'FF'. The equipment
                configurator does not need this final completion.
                The values are defined by the TELETEL standard.
                The default value is 'empty' (first byte set to
                '00')."
        ::= { fclAsynVdxHomePageEntry 4 }


    fclAsynLowSpeedCpLogPort OBJECT IDENTIFIER ::= { fclAsynchronousAccessLogPort 4 }


    fclAsynLscpLpTable OBJECT-TYPE
        SYNTAX  SEQUENCE OF FclAsynLscpLpEntry
        ACCESS  not-accessible
        STATUS  mandatory
        DESCRIPTION
                "This table defines the specific parameters of an
                asynchronous logical port when the terminal type
                is 'lowSpeedComputerPort' or
                'lowSpeedComputerPortWithAutoCalls'."
        ::= { fclAsynLowSpeedCpLogPort 1 }


    fclAsynLscpLpEntry OBJECT-TYPE
        SYNTAX  FclAsynLscpLpEntry
        ACCESS  not-accessible
        STATUS  mandatory
        DESCRIPTION
                "An entry of fclAsynLscpLpTable."
        INDEX   { fclAsynLscpLpLogPortId }
        ::= { fclAsynLscpLpTable 1 }


        FclAsynLscpLpEntry ::=
                SEQUENCE {
                    fclAsynLscpLpLogPortId
                        INTEGER,
                    fclAsynLscpLpLink
                        INTEGER,
                    fclAsynLscpLpEquipment
                        INTEGER
                }


    fclAsynLscpLpLogPortId OBJECT-TYPE
        SYNTAX  INTEGER (0..181)
        ACCESS  read-only
        STATUS  mandatory
        DESCRIPTION
                "The value of this object identifies one and only
                one asynchronous logical port used to connect a
                'lowSpeedComputerPort' terminal. The possible
                values are : '0..131'. If it is unused, the value
                of this parameter is '255'."
        ::= { fclAsynLscpLpEntry 1 }


    fclAsynLscpLpLink OBJECT-TYPE
        SYNTAX  INTEGER {
                leasedLine(2),
                direct(3)
                }
        ACCESS  read-write
        STATUS  mandatory
        DESCRIPTION
                "The value of this object indicates the type of
                link used to connect the terminal to the
                equipment. The default value is 'direct'."
        ::= { fclAsynLscpLpEntry 2 }


    fclAsynLscpLpEquipment OBJECT-TYPE
        SYNTAX  INTEGER {
                other(1),
                hpHost(2),
                hpTerminal(3)
                }
        ACCESS  read-write
        STATUS  mandatory
        DESCRIPTION
                "The value of this object indicates the terminal in
                facing. 'other' means 'all equipment except
                Hewlett Packard'. The default value is 'other'."
        ::= { fclAsynLscpLpEntry 4 }


    fclAsynMultiStandardPadLogPort OBJECT IDENTIFIER ::= { fclAsynchronousAccessLogPort 5 }


    fclAsynMultiLpTable OBJECT-TYPE
        SYNTAX  SEQUENCE OF FclAsynMultiLpEntry
        ACCESS  not-accessible
        STATUS  mandatory
        DESCRIPTION
                "This table defines the specific parameters of an
                asynchronous logical port when the terminal type
                is 'multiStandardPad'."
        ::= { fclAsynMultiStandardPadLogPort 1 }


    fclAsynMultiLpEntry OBJECT-TYPE
        SYNTAX  FclAsynMultiLpEntry
        ACCESS  not-accessible
        STATUS  mandatory
        DESCRIPTION
                "An entry of fclAsynMultiLpTable."
        INDEX   { fclAsynMultiLpLogPortId }
        ::= { fclAsynMultiLpTable 1 }


        FclAsynMultiLpEntry ::=
                SEQUENCE {
                    fclAsynMultiLpLogPortId
                        INTEGER,
                    fclAsynMultiLpAuthStep1
                        INTEGER,
                    fclAsynMultiLpAuthStep2
                        INTEGER,
                    fclAsynMultiLpAuthStep3
                        INTEGER,
                    fclAsynMultiLpAuthStep4
                        INTEGER
                }


    fclAsynMultiLpLogPortId OBJECT-TYPE
        SYNTAX  INTEGER (0..181)
        ACCESS  read-only
        STATUS  mandatory
        DESCRIPTION
                "The value of this object identifies one and only
                one asynchronous logical port used to connect a
                'multiStandardPad' terminal. The possible values
                are : '0..131'. If it is unused, the value of this
                parameter is '255'."
        ::= { fclAsynMultiLpEntry 1 }


    fclAsynMultiLpAuthStep1 OBJECT-TYPE
        SYNTAX  INTEGER {
                undefined(1),
                tfi-noParity(2),
                tfi-evenParity(3),
                enquire(4),
                ter(5)
                }
        ACCESS  read-write
        STATUS  mandatory
        DESCRIPTION
                "The value of this object defines the treatment
                used in the first step of authentication.
                'undefined' means 'no treatment. The default value
                is 'undefined'."
        ::= { fclAsynMultiLpEntry 10 }


    fclAsynMultiLpAuthStep2 OBJECT-TYPE
        SYNTAX  INTEGER {
                undefined(1),
                tfi-noParity(2),
                tfi-evenParity(3),
                enquire(4),
                ter(5)
                }
        ACCESS  read-write
        STATUS  mandatory
        DESCRIPTION
                "The value of this object defines the treatment
                used in the second step of authentication.
                'undefined' means 'no treatment. The default value
                is 'undefined'."
        ::= { fclAsynMultiLpEntry 11 }


    fclAsynMultiLpAuthStep3 OBJECT-TYPE
        SYNTAX  INTEGER {
                undefined(1),
                tfi-noParity(2),
                tfi-evenParity(3),
                enquire(4),
                ter(5)
                }
        ACCESS  read-write
        STATUS  mandatory
        DESCRIPTION
                "The value of this object defines the treatment
                used in the third step of authentication.
                'undefined' means 'no treatment. The default value
                is 'undefined'."
        ::= { fclAsynMultiLpEntry 12 }


    fclAsynMultiLpAuthStep4 OBJECT-TYPE
        SYNTAX  INTEGER {
                undefined(1),
                tfi-noParity(2),
                tfi-evenParity(3),
                enquire(4),
                ter(5)
                }
        ACCESS  read-write
        STATUS  mandatory
        DESCRIPTION
                "The value of this object defines the treatment
                used in the fourth step of authentication.
                'undefined' means 'no treatment. The default value
                is 'undefined'."
        ::= { fclAsynMultiLpEntry 13 }


    fclAsynX28PlusLogPort OBJECT IDENTIFIER ::= { fclAsynchronousAccessLogPort 6 }


    fclAsynX28PlusLpTable OBJECT-TYPE
        SYNTAX  SEQUENCE OF FclAsynX28PlusLpEntry
        ACCESS  not-accessible
        STATUS  mandatory
        DESCRIPTION
                "This table defines the specific parameters of an
                asynchronous logical port when the terminal type
                is 'x28plus'."
        ::= { fclAsynX28PlusLogPort 1 }


    fclAsynX28PlusLpEntry OBJECT-TYPE
        SYNTAX  FclAsynX28PlusLpEntry
        ACCESS  not-accessible
        STATUS  mandatory
        DESCRIPTION
                "An entry of fclAsynX28PlusLpTable."
        INDEX   { fclAsynX28PlusLpLogPortId }
        ::= { fclAsynX28PlusLpTable 1 }


        FclAsynX28PlusLpEntry ::=
                SEQUENCE {
                    fclAsynX28PlusLpLogPortId
                        INTEGER,
                    fclAsynX28PlusLpLink
                        INTEGER,
                    fclAsynX28PlusLpSpeedDetection
                        INTEGER,
                    fclAsynX28PlusLpEquipment
                        INTEGER,
                    fclAsynX28PlusLpMnemonicType
                        INTEGER,
                    fclAsynX28PlusLpFullDuplex
                        INTEGER,
                    fclAsynX28PlusLpIdleTimerSelection
                        INTEGER,
                    fclAsynX28PlusLpIdleTimerDelay
                        INTEGER,
                    fclAsynX28PlusLpX3Mode
                        INTEGER,
                    fclAsynX28PlusLpEscapeDigit
                        INTEGER,
                    fclAsynX28PlusLpConIdTelenet
                        INTEGER,
                    fclAsynX28PlusLpConIdRemote
                        INTEGER,
                    fclAsynX28PlusLpRemPrSentOnCalls
                        INTEGER,
                    fclAsynX28PlusLpEasyMnemo
                        INTEGER,
                    fclAsynX28PlusLpMonSignalCTS
                        INTEGER,
                    fclAsynX28PlusLpMonSignalDSR
                        INTEGER,
                    fclAsynX28PlusLpMonSignalDCD
                        INTEGER
                }


    fclAsynX28PlusLpLogPortId OBJECT-TYPE
        SYNTAX  INTEGER (0..181)
        ACCESS  read-only
        STATUS  mandatory
        DESCRIPTION
                "The value of this object identifies one and only
                one asynchronous logical port used to connect a
                'x28plus' terminal. The possible values are :
                '0..131'. If it is unused, the value of this
                parameter is '255'."
        ::= { fclAsynX28PlusLpEntry 1 }


    fclAsynX28PlusLpLink OBJECT-TYPE
        SYNTAX  INTEGER {
                pstn(1),
                leasedLine(2),
                direct(3),
                directWithRtsCtsFlowCtrl(4),
                pstnV25bis(5)
                }
        ACCESS  read-write
        STATUS  mandatory
        DESCRIPTION
                "The value of this object indicates the type of
                link used to connect the terminal to the
                equipment. The default value is 'direct'."
        ::= { fclAsynX28PlusLpEntry 2 }


    fclAsynX28PlusLpSpeedDetection OBJECT-TYPE
        SYNTAX  INTEGER {
                off(1),
                on(2)
                }
        ACCESS  read-write
        STATUS  mandatory
        DESCRIPTION
                "The value of this object indicates if the
                automatic speed detection is used. The default
                value is 'on'."
        ::= { fclAsynX28PlusLpEntry 3 }


    fclAsynX28PlusLpEquipment OBJECT-TYPE
        SYNTAX  INTEGER {
                other(1),
                hpHost(2),
                hpTerminal(3)
                }
        ACCESS  read-write
        STATUS  mandatory
        DESCRIPTION
                "The value of this object indicates the terminal in
                facing. 'other' means 'all equipment except
                Hewlett Packard'. The default value is 'other'."
        ::= { fclAsynX28PlusLpEntry 4 }


    fclAsynX28PlusLpMnemonicType OBJECT-TYPE
        SYNTAX  INTEGER {
                pad(1),
                vdxRemoteAuth(2),
                vdxTeletel(3),
                vdxLocalAuth(4)
                }
        ACCESS  read-write
        STATUS  mandatory
        DESCRIPTION
                "The value of this object indicates the mnemonic
                type. When set to 'pad' the mnemonic must begin
                with a point, the call command is allowed, the X28
                command is allowed, the call data and the password
                are checked by the remote host. When set to
                'vdxRemoteAuth' the mnemonic may optionaly begin
                with a point, the call command is forbidden, the
                X28 command is forbidden, the call data and the
                password are checked by the remote host. When set
                to 'vdxTeletel' the mnemonic may optionaly begin
                with a point, the call command is allowed, the X28
                command is forbidden, the call data and the
                password are checked by the remote host. When set
                to 'vdxLocalAuth' the mnemonic may optionaly begin
                with a point, the call command is forbidden, the
                X28 command is forbidden, the call data and the
                password are checked by the pad. The default is
                'pad'."
        ::= { fclAsynX28PlusLpEntry 5 }


    fclAsynX28PlusLpFullDuplex OBJECT-TYPE
        SYNTAX  INTEGER {
                off(1),
                on(2)
                }
        ACCESS  read-write
        STATUS  mandatory
        DESCRIPTION
                "The value of this object indicates whether the
                line is in full duplex (with echo) or half duplex
                (without echo). The echo of a transfer mode
                character is also defined by the X3 parameter
                number 2. The authorized values are 'off' (line in
                half duplex), 'on' (line in full duplex). The
                default value is 'on'."
        ::= { fclAsynX28PlusLpEntry 10 }


    fclAsynX28PlusLpIdleTimerSelection OBJECT-TYPE
        SYNTAX  INTEGER {
                off(1),
                on(2)
                }
        ACCESS  read-write
        STATUS  mandatory
        DESCRIPTION
                "The value of this object indicates whether the
                timers fclAsynCfgX3P04IdleTimerDelay and
                fclAsynX28PlusLpIdleTimerDelay are enabled or not.
                The data are sent upon when one of these two
                timers expires. The default value is 'on'."
        ::= { fclAsynX28PlusLpEntry 11 }


    fclAsynX28PlusLpIdleTimerDelay OBJECT-TYPE
        SYNTAX  INTEGER (0..12750)
        ACCESS  read-write
        STATUS  mandatory
        DESCRIPTION
                "The value of this object defines the data
                forwarding time-out in milliseconds. This timer is
                started at reception time of the first character.
                When this time-out expires, the PAD sends the
                received characters to the network. The time-out
                is restarted upon reception of the first character
                to follow. The authorized values are '0..12750'
                milliseconds. The default value is '0'."
        ::= { fclAsynX28PlusLpEntry 12 }


    fclAsynX28PlusLpX3Mode OBJECT-TYPE
        SYNTAX  INTEGER {
                transparent(1),
                networkVirtualTerminal(2)
                }
        ACCESS  read-write
        STATUS  mandatory
        DESCRIPTION
                "The value of this object indicates the X3 mode.
                The authorized value are 'transparent' (X3
                parameters 1, 13 and 15 are interpreted : case of
                escape, no LF insertion after CR) or
                'networkVirtualTerminal' (X3 parameters 1, 13 and
                15 are not inhibited). The default value is
                'networkVirtualTerminal'."
        ::= { fclAsynX28PlusLpEntry 13 }


    fclAsynX28PlusLpEscapeDigit OBJECT-TYPE
        SYNTAX  INTEGER (0..9)
        ACCESS  read-write
        STATUS  mandatory
        DESCRIPTION
                "Digit d'echappement"
        ::= { fclAsynX28PlusLpEntry 14 }


    fclAsynX28PlusLpConIdTelenet OBJECT-TYPE
        SYNTAX  INTEGER (0..35)
        ACCESS  read-write
        STATUS  mandatory
        DESCRIPTION
                "Config ID TELENET"
        ::= { fclAsynX28PlusLpEntry 15 }


    fclAsynX28PlusLpConIdRemote OBJECT-TYPE
        SYNTAX  INTEGER (0..35)
        ACCESS  read-write
        STATUS  mandatory
        DESCRIPTION
                "Config ID Remote X3 et TELENET"
        ::= { fclAsynX28PlusLpEntry 16 }


    fclAsynX28PlusLpRemPrSentOnCalls OBJECT-TYPE
        SYNTAX  INTEGER {
                never(1),
                inBound(2),
                outBound(3),
                both(4)
                }
        ACCESS  read-write
        STATUS  mandatory
        DESCRIPTION
                "Envoi du profil distant"
        ::= { fclAsynX28PlusLpEntry 17 }


    fclAsynX28PlusLpEasyMnemo OBJECT-TYPE
        SYNTAX  INTEGER {
                off(1),
                on(2)
                }
        ACCESS  read-write
        STATUS  mandatory
        DESCRIPTION
                "Facilite mnemonique"
        ::= { fclAsynX28PlusLpEntry 20 }


    fclAsynX28PlusLpMonSignalCTS OBJECT-TYPE
        SYNTAX  INTEGER {
                no(1),
                yes(2)
                }
        ACCESS  read-write
        STATUS  mandatory
        DESCRIPTION
                "Gestion du signal sortant106CTS (DCE)/108DTR(DTE)"
        ::= { fclAsynX28PlusLpEntry 21 }


    fclAsynX28PlusLpMonSignalDSR OBJECT-TYPE
        SYNTAX  INTEGER {
                no(1),
                yes(2)
                }
        ACCESS  read-write
        STATUS  mandatory
        DESCRIPTION
                "Gestion du signal sortant 107DSR (DCE)/111DRS(DTE)"
        ::= { fclAsynX28PlusLpEntry 22 }


    fclAsynX28PlusLpMonSignalDCD OBJECT-TYPE
        SYNTAX  INTEGER {
                no(1),
                yes(2)
                }
        ACCESS  read-write
        STATUS  mandatory
        DESCRIPTION
                "Gestion du signal sortant 109DCD(DCE)/105RTS(DTE)"
        ::= { fclAsynX28PlusLpEntry 23 }


    fclAsynX28PlusGeneralParameters OBJECT IDENTIFIER ::= { fclAsynX28PlusLogPort 2 }


    fclAsynX28PlusGenParDNIC OBJECT-TYPE
        SYNTAX  OCTET STRING (SIZE(2))
        ACCESS  read-write
        STATUS  mandatory
        DESCRIPTION
                "DNIC pour adresse abregee"
        ::= { fclAsynX28PlusGeneralParameters 1 }


    fclAsynX28PlusConfTELENETTable OBJECT-TYPE
        SYNTAX  SEQUENCE OF FclAsynX28PlusConfTELENETEntry
        ACCESS  not-accessible
        STATUS  mandatory
        DESCRIPTION
                ""
        ::= { fclAsynX28PlusLogPort 3 }


    fclAsynX28PlusConfTELENETEntry OBJECT-TYPE
        SYNTAX  FclAsynX28PlusConfTELENETEntry
        ACCESS  not-accessible
        STATUS  mandatory
        DESCRIPTION
                "An entry of fclAsynX28PlusConfTELENETTable."
        INDEX   { fclAsynX28PlusCfgTELENETConfigId }
        ::= { fclAsynX28PlusConfTELENETTable 1 }


        FclAsynX28PlusConfTELENETEntry ::=
                SEQUENCE {
                    fclAsynX28PlusCfgTELENETConfigId
                        INTEGER,
                    fclAsynX28PlusCfgTELENETDescription
                        DisplayString
                }


    fclAsynX28PlusCfgTELENETConfigId OBJECT-TYPE
        SYNTAX  INTEGER (0..35)
        ACCESS  read-only
        STATUS  mandatory
        DESCRIPTION
                "Config Id"
        ::= { fclAsynX28PlusConfTELENETEntry 1 }


    fclAsynX28PlusCfgTELENETDescription OBJECT-TYPE
        SYNTAX  DisplayString (SIZE(0..32))
        ACCESS  read-write
        STATUS  mandatory
        DESCRIPTION
                "Description"
        ::= { fclAsynX28PlusConfTELENETEntry 2 }


    fclAsynX28PlusParTELENETTable OBJECT-TYPE
        SYNTAX  SEQUENCE OF FclAsynX28PlusParTELENETEntry
        ACCESS  not-accessible
        STATUS  mandatory
        DESCRIPTION
                ""
        ::= { fclAsynX28PlusLogPort 4 }


    fclAsynX28PlusParTELENETEntry OBJECT-TYPE
        SYNTAX  FclAsynX28PlusParTELENETEntry
        ACCESS  not-accessible
        STATUS  mandatory
        DESCRIPTION
                "An entry of fclAsynX28PlusParTELENETTable."
        INDEX   { fclAsynX28PlusParTelConfigId }
        ::= { fclAsynX28PlusParTELENETTable 1 }


        FclAsynX28PlusParTELENETEntry ::=
                SEQUENCE {
                    fclAsynX28PlusParTelConfigId
                        INTEGER,
                    fclAsynX28PlusParTelLpFullDuplex
                        INTEGER,
                    fclAsynX28PlusParTelLpIdleTimerSelection
                        INTEGER,
                    fclAsynX28PlusParTelLpIdleTimerDelay
                        INTEGER,
                    fclAsynX28PlusParTelLpX3Mode
                        INTEGER
                }


    fclAsynX28PlusParTelConfigId OBJECT-TYPE
        SYNTAX  INTEGER (0..35)
        ACCESS  read-only
        STATUS  mandatory
        DESCRIPTION
                "Config Id"
        ::= { fclAsynX28PlusParTELENETEntry 1 }


    fclAsynX28PlusParTelLpFullDuplex OBJECT-TYPE
        SYNTAX  INTEGER {
                off(1),
                on(2)
                }
        ACCESS  read-write
        STATUS  mandatory
        DESCRIPTION
                "Ligne FullDuplex"
        ::= { fclAsynX28PlusParTELENETEntry 10 }


    fclAsynX28PlusParTelLpIdleTimerSelection OBJECT-TYPE
        SYNTAX  INTEGER {
                off(1),
                on(2)
                }
        ACCESS  read-write
        STATUS  mandatory
        DESCRIPTION
                "Envoi sur tempo"
        ::= { fclAsynX28PlusParTELENETEntry 11 }


    fclAsynX28PlusParTelLpIdleTimerDelay OBJECT-TYPE
        SYNTAX  INTEGER (0..12750)
        ACCESS  read-write
        STATUS  mandatory
        DESCRIPTION
                "Tempo d'envoi de donnees"
        ::= { fclAsynX28PlusParTELENETEntry 12 }


    fclAsynX28PlusParTelLpX3Mode OBJECT-TYPE
        SYNTAX  INTEGER {
                transparent(1),
                networkVirtualTerminal(2)
                }
        ACCESS  read-write
        STATUS  mandatory
        DESCRIPTION
                "Terminal Virtuel"
        ::= { fclAsynX28PlusParTELENETEntry 13 }


    fclAsynX28PlusConfRemoteTable OBJECT-TYPE
        SYNTAX  SEQUENCE OF FclAsynX28PlusConfRemoteEntry
        ACCESS  not-accessible
        STATUS  mandatory
        DESCRIPTION
                ""
        ::= { fclAsynX28PlusLogPort 5 }


    fclAsynX28PlusConfRemoteEntry OBJECT-TYPE
        SYNTAX  FclAsynX28PlusConfRemoteEntry
        ACCESS  not-accessible
        STATUS  mandatory
        DESCRIPTION
                "An entry of fclAsynX28PlusConfRemoteTable."
        INDEX   { fclAsynX28PlusRemoteConfigId }
        ::= { fclAsynX28PlusConfRemoteTable 1 }


        FclAsynX28PlusConfRemoteEntry ::=
                SEQUENCE {
                    fclAsynX28PlusRemoteConfigId
                        INTEGER,
                    fclAsynX28PlusRemoteCfgDescription
                        DisplayString
                }


    fclAsynX28PlusRemoteConfigId OBJECT-TYPE
        SYNTAX  INTEGER (0..35)
        ACCESS  read-only
        STATUS  mandatory
        DESCRIPTION
                "Config Id"
        ::= { fclAsynX28PlusConfRemoteEntry 1 }


    fclAsynX28PlusRemoteCfgDescription OBJECT-TYPE
        SYNTAX  DisplayString (SIZE(0..32))
        ACCESS  read-write
        STATUS  mandatory
        DESCRIPTION
                "Description"
        ::= { fclAsynX28PlusConfRemoteEntry 2 }


    fclAsynX28PlusRemoteCfgX3Part1Table OBJECT-TYPE
        SYNTAX  SEQUENCE OF FclAsynX28PlusRemoteCfgX3Part1Entry
        ACCESS  not-accessible
        STATUS  mandatory
        DESCRIPTION
                ""
        ::= { fclAsynX28PlusLogPort 6 }


    fclAsynX28PlusRemoteCfgX3Part1Entry OBJECT-TYPE
        SYNTAX  FclAsynX28PlusRemoteCfgX3Part1Entry
        ACCESS  not-accessible
        STATUS  mandatory
        DESCRIPTION
                "An entry of fclAsynX28PlusRemoteCfgX3Part1Table."
        INDEX   { fclAsynX28PlusRemConfigId }
        ::= { fclAsynX28PlusRemoteCfgX3Part1Table 1 }


        FclAsynX28PlusRemoteCfgX3Part1Entry ::=
                SEQUENCE {
                    fclAsynX28PlusRemConfigId
                        INTEGER,
                    fclAsynX28PlusRemCfgX3P01EscapeChar
                        INTEGER,
                    fclAsynX28PlusRemCfgX3P02Echo
                        INTEGER,
                    fclAsynX28PlusRemCfgX3P03ForwardingChar
                        INTEGER,
                    fclAsynX28PlusRemCfgX3P04IdleTimerDelay
                        INTEGER,
                    fclAsynX28PlusRemCfgX3P05OutputFlowCtrl
                        INTEGER,
                    fclAsynX28PlusRemCfgX3P06ServiceSignals
                        INTEGER,
                    fclAsynX28PlusRemCfgX3P07BreakHandling
                        INTEGER,
                    fclAsynX28PlusRemCfgX3P08OutputDiscard
                        INTEGER,
                    fclAsynX28PlusRemCfgX3P09CrPadding
                        INTEGER,
                    fclAsynX28PlusRemCfgX3P10LineFolding
                        INTEGER,
                    fclAsynX28PlusRemCfgX3P11BinarySpeed
                        INTEGER
                }


    fclAsynX28PlusRemConfigId OBJECT-TYPE
        SYNTAX  INTEGER (0..199)
        ACCESS  read-only
        STATUS  mandatory
        DESCRIPTION
                "Config Id"
        ::= { fclAsynX28PlusRemoteCfgX3Part1Entry 1 }


    fclAsynX28PlusRemCfgX3P01EscapeChar OBJECT-TYPE
        SYNTAX  INTEGER (0..126)
        ACCESS  read-write
        STATUS  mandatory
        DESCRIPTION
                "Caractere d'echappement"
        ::= { fclAsynX28PlusRemoteCfgX3Part1Entry 11 }


    fclAsynX28PlusRemCfgX3P02Echo OBJECT-TYPE
        SYNTAX  INTEGER {
                val0-off(1),
                val1-on(2),
                not-used(255)
                }
        ACCESS  read-write
        STATUS  mandatory
        DESCRIPTION
                "Echo"
        ::= { fclAsynX28PlusRemoteCfgX3Part1Entry 12 }


    fclAsynX28PlusRemCfgX3P03ForwardingChar OBJECT-TYPE
        SYNTAX  INTEGER {
                val0-none(1),
                val2-cr(3),
                val6-crEscBelEnqAck(7),
                val18-crEotEtx(19),
                val32-htLfVtFf(33),
                val126-allCtrlChars(127),
                val127-allChars(128),
                val128-allCtrlChars-vdxFunctionKeys(129),
                val253-encapsCharacSLIP(254),
                not-used(255)
                }
        ACCESS  read-write
        STATUS  mandatory
        DESCRIPTION
                "Caractere d'envoi des donnees"
        ::= { fclAsynX28PlusRemoteCfgX3Part1Entry 13 }


    fclAsynX28PlusRemCfgX3P04IdleTimerDelay OBJECT-TYPE
        SYNTAX  INTEGER (0..250)
        ACCESS  read-write
        STATUS  mandatory
        DESCRIPTION
                "Delai d'envoi (en 1/20eme de seconde)"
        ::= { fclAsynX28PlusRemoteCfgX3Part1Entry 14 }


    fclAsynX28PlusRemCfgX3P05OutputFlowCtrl OBJECT-TYPE
        SYNTAX  INTEGER {
                val0-none(1),
                val1-xonXoffInTransfer(2),
                val2-xonXoff(3),
                val8-rtsCtsInTransfer(9),
                not-used(255)
                }
        ACCESS  read-write
        STATUS  mandatory
        DESCRIPTION
                "Control de flux PAD vers Terminal"
        ::= { fclAsynX28PlusRemoteCfgX3Part1Entry 15 }


    fclAsynX28PlusRemCfgX3P06ServiceSignals OBJECT-TYPE
        SYNTAX  INTEGER {
                val0-none(1),
                val1-servSignal-stdFormat(2),
                val5-servSignalAndPrompt-stdFormat(6),
                val9-servSignal-explicitFormat(10),
                val13-servSignalAndPrompt-explicitFormat(14),
                not-used(255)
                }
        ACCESS  read-write
        STATUS  mandatory
        DESCRIPTION
                "Transmission des indications par le PAD"
        ::= { fclAsynX28PlusRemoteCfgX3Part1Entry 16 }


    fclAsynX28PlusRemCfgX3P07BreakHandling OBJECT-TYPE
        SYNTAX  INTEGER {
                val0-forwardingChar(1),
                val1-interrupt(2),
                val2-reset(3),
                val4-breakIndication(5),
                val5-interrupt-breakIndication(6),
                val8-escapeFromTransfer(9),
                val21-interrupt-breakIndication-discardOutput(22),
                not-used(255)
                }
        ACCESS  read-write
        STATUS  mandatory
        DESCRIPTION
                "Reaction sur Break"
        ::= { fclAsynX28PlusRemoteCfgX3Part1Entry 17 }


    fclAsynX28PlusRemCfgX3P08OutputDiscard OBJECT-TYPE
        SYNTAX  INTEGER {
                val0-off(1),
                val1-on(2),
                not-used(255)
                }
        ACCESS  read-write
        STATUS  mandatory
        DESCRIPTION
                "Arret de la remise des donnees"
        ::= { fclAsynX28PlusRemoteCfgX3Part1Entry 18 }


    fclAsynX28PlusRemCfgX3P09CrPadding OBJECT-TYPE
        SYNTAX  INTEGER (0..250)
        ACCESS  read-write
        STATUS  mandatory
        DESCRIPTION
                "Bourrage apres RC"
        ::= { fclAsynX28PlusRemoteCfgX3Part1Entry 19 }


    fclAsynX28PlusRemCfgX3P10LineFolding OBJECT-TYPE
        SYNTAX  INTEGER (0..250)
        ACCESS  read-write
        STATUS  mandatory
        DESCRIPTION
                "Pliage de ligne"
        ::= { fclAsynX28PlusRemoteCfgX3Part1Entry 20 }


    fclAsynX28PlusRemCfgX3P11BinarySpeed OBJECT-TYPE
        SYNTAX  INTEGER {
                val0-110(1),
                val1-134-5(2),
                val2-300(3),
                val3-1200(4),
                val4-600(5),
                val5-75(6),
                val6-150(7),
                val7-1800(8),
                val8-200(9),
                val9-100(10),
                val10-50(11),
                val11-in75Out1200(12),
                val12-2400(13),
                val13-4800(14),
                val14-9600(15),
                val15-19200(16),
                val23-28800(24),
                val17-57600(18),
                val20-38400(21),
                val21-out1200In75(22),
                val22-115200(23),
                not-used(255)
                }
        ACCESS  read-write
        STATUS  mandatory
        DESCRIPTION
                "Debit binaire (en bit/s)"
        ::= { fclAsynX28PlusRemoteCfgX3Part1Entry 21 }


    fclAsynX28PlusRemoteCfgX3Part2Table OBJECT-TYPE
        SYNTAX  SEQUENCE OF FclAsynX28PlusRemoteCfgX3Part2Entry
        ACCESS  not-accessible
        STATUS  mandatory
        DESCRIPTION
                ""
        ::= { fclAsynX28PlusLogPort 7 }


    fclAsynX28PlusRemoteCfgX3Part2Entry OBJECT-TYPE
        SYNTAX  FclAsynX28PlusRemoteCfgX3Part2Entry
        ACCESS  not-accessible
        STATUS  mandatory
        DESCRIPTION
                "An entry of fclAsynX28PlusRemoteCfgX3Part2Table."
        INDEX   { fclAsynX28PlusRemCfgX3Part2ConfigId }
        ::= { fclAsynX28PlusRemoteCfgX3Part2Table 1 }


        FclAsynX28PlusRemoteCfgX3Part2Entry ::=
                SEQUENCE {
                    fclAsynX28PlusRemCfgX3Part2ConfigId
                        INTEGER,
                    fclAsynX28PlusRemCfgX3P12InputFlowCtrl
                        INTEGER,
                    fclAsynX28PlusRemCfgX3P13LfInsertion
                        INTEGER,
                    fclAsynX28PlusRemCfgX3P14LfPadding
                        INTEGER,
                    fclAsynX28PlusRemCfgX3P15Editing
                        INTEGER,
                    fclAsynX28PlusRemCfgX3P16CharDelete
                        INTEGER,
                    fclAsynX28PlusRemCfgX3P17LineDelete
                        INTEGER,
                    fclAsynX28PlusRemCfgX3P18LineDisplay
                        INTEGER,
                    fclAsynX28PlusRemCfgX3P19EditingSignal
                        INTEGER,
                    fclAsynX28PlusRemCfgX3P20EchoMask
                        INTEGER,
                    fclAsynX28PlusRemCfgX3P21Parity
                        INTEGER,
                    fclAsynX28PlusRemCfgX3P22PageWait
                        INTEGER
                }


    fclAsynX28PlusRemCfgX3Part2ConfigId OBJECT-TYPE
        SYNTAX  INTEGER (0..199)
        ACCESS  read-only
        STATUS  mandatory
        DESCRIPTION
                "Config Id"
        ::= { fclAsynX28PlusRemoteCfgX3Part2Entry 1 }


    fclAsynX28PlusRemCfgX3P12InputFlowCtrl OBJECT-TYPE
        SYNTAX  INTEGER {
                val0-none(1),
                val1-xonXoff(2),
                val8-rtsCts(9),
                not-used(255)
                }
        ACCESS  read-write
        STATUS  mandatory
        DESCRIPTION
                "Control de flux Terminal vers PAD"
        ::= { fclAsynX28PlusRemoteCfgX3Part2Entry 22 }


    fclAsynX28PlusRemCfgX3P13LfInsertion OBJECT-TYPE
        SYNTAX  INTEGER {
                val0-none(1),
                val1-outCr(2),
                val2-inCr(3),
                val3-outCr-inCr(4),
                val4-outCrEcho(5),
                val5-outCr-outCrEcho(6),
                val6-inCr-outCrEcho(7),
                val7-outCr-inCr-outCrEcho(8),
                not-used(255)
                }
        ACCESS  read-write
        STATUS  mandatory
        DESCRIPTION
                "Insertion de LF apres RC"
        ::= { fclAsynX28PlusRemoteCfgX3Part2Entry 23 }


    fclAsynX28PlusRemCfgX3P14LfPadding OBJECT-TYPE
        SYNTAX  INTEGER (0..250)
        ACCESS  read-write
        STATUS  mandatory
        DESCRIPTION
                "Bourrage apres LF"
        ::= { fclAsynX28PlusRemoteCfgX3Part2Entry 24 }


    fclAsynX28PlusRemCfgX3P15Editing OBJECT-TYPE
        SYNTAX  INTEGER {
                val0-off(1),
                val1-on(2),
                not-used(255)
                }
        ACCESS  read-write
        STATUS  mandatory
        DESCRIPTION
                "Edition"
        ::= { fclAsynX28PlusRemoteCfgX3Part2Entry 25 }


    fclAsynX28PlusRemCfgX3P16CharDelete OBJECT-TYPE
        SYNTAX  INTEGER (0..128)
        ACCESS  read-write
        STATUS  mandatory
        DESCRIPTION
                "Caractere d'effacement d'un caractere"
        ::= { fclAsynX28PlusRemoteCfgX3Part2Entry 26 }


    fclAsynX28PlusRemCfgX3P17LineDelete OBJECT-TYPE
        SYNTAX  INTEGER (0..128)
        ACCESS  read-write
        STATUS  mandatory
        DESCRIPTION
                "Caractere d'effacement d'une ligne"
        ::= { fclAsynX28PlusRemoteCfgX3Part2Entry 27 }


    fclAsynX28PlusRemCfgX3P18LineDisplay OBJECT-TYPE
        SYNTAX  INTEGER (0..127)
        ACCESS  read-write
        STATUS  mandatory
        DESCRIPTION
                "Caractere d'affichage d'une ligne"
        ::= { fclAsynX28PlusRemoteCfgX3Part2Entry 28 }


    fclAsynX28PlusRemCfgX3P19EditingSignal OBJECT-TYPE
        SYNTAX  INTEGER {
                val0-none(1),
                val1-printingTerminal(2),
                val2-displayTerminal(3),
                not-used(255)
                }
        ACCESS  read-write
        STATUS  mandatory
        DESCRIPTION
                "Indication d'edition"
        ::= { fclAsynX28PlusRemoteCfgX3Part2Entry 29 }


    fclAsynX28PlusRemCfgX3P20EchoMask OBJECT-TYPE
        SYNTAX  INTEGER (0..255)
        ACCESS  read-write
        STATUS  mandatory
        DESCRIPTION
                "Masque d'echo"
        ::= { fclAsynX28PlusRemoteCfgX3Part2Entry 30 }


    fclAsynX28PlusRemCfgX3P21Parity OBJECT-TYPE
        SYNTAX  INTEGER {
                val0-none(1),
                val1-check(2),
                val2-generate(3),
                val3-check-generate(4),
                not-used(255)
                }
        ACCESS  read-write
        STATUS  mandatory
        DESCRIPTION
                "Traitement de la parite"
        ::= { fclAsynX28PlusRemoteCfgX3Part2Entry 31 }


    fclAsynX28PlusRemCfgX3P22PageWait OBJECT-TYPE
        SYNTAX  INTEGER (0..127)
        ACCESS  read-write
        STATUS  mandatory
        DESCRIPTION
                "Attente en fin de page"
        ::= { fclAsynX28PlusRemoteCfgX3Part2Entry 32 }


    fclAsynX28PlusRemoteTELENETTable OBJECT-TYPE
        SYNTAX  SEQUENCE OF FclAsynX28PlusRemoteTELENETEntry
        ACCESS  not-accessible
        STATUS  mandatory
        DESCRIPTION
                ""
        ::= { fclAsynX28PlusLogPort 8 }


    fclAsynX28PlusRemoteTELENETEntry OBJECT-TYPE
        SYNTAX  FclAsynX28PlusRemoteTELENETEntry
        ACCESS  not-accessible
        STATUS  mandatory
        DESCRIPTION
                "An entry of fclAsynX28PlusRemoteTELENETTable."
        INDEX   { fclAsynX28PlusRemCfgTELENETConfigId }
        ::= { fclAsynX28PlusRemoteTELENETTable 1 }


        FclAsynX28PlusRemoteTELENETEntry ::=
                SEQUENCE {
                    fclAsynX28PlusRemCfgTELENETConfigId
                        INTEGER,
                    fclAsynX28PlusRemLpFullDuplex
                        INTEGER,
                    fclAsynX28PlusRemLpIdleTimerSelection
                        INTEGER,
                    fclAsynX28PlusRemLpIdleTimerDelay
                        INTEGER,
                    fclAsynX28PlusRemLpX3Mode
                        INTEGER
                }


    fclAsynX28PlusRemCfgTELENETConfigId OBJECT-TYPE
        SYNTAX  INTEGER (0..35)
        ACCESS  read-only
        STATUS  mandatory
        DESCRIPTION
                "Config Id"
        ::= { fclAsynX28PlusRemoteTELENETEntry 1 }


    fclAsynX28PlusRemLpFullDuplex OBJECT-TYPE
        SYNTAX  INTEGER {
                off(1),
                on(2),
                not-used(255)
                }
        ACCESS  read-write
        STATUS  mandatory
        DESCRIPTION
                "Ligne FullDuplex"
        ::= { fclAsynX28PlusRemoteTELENETEntry 10 }


    fclAsynX28PlusRemLpIdleTimerSelection OBJECT-TYPE
        SYNTAX  INTEGER {
                off(1),
                on(2),
                not-used(255)
                }
        ACCESS  read-write
        STATUS  mandatory
        DESCRIPTION
                "Envoi sur tempo"
        ::= { fclAsynX28PlusRemoteTELENETEntry 11 }


    fclAsynX28PlusRemLpIdleTimerDelay OBJECT-TYPE
        SYNTAX  INTEGER (0..12750)
        ACCESS  read-write
        STATUS  mandatory
        DESCRIPTION
                "Tempo d'envoi de donnees"
        ::= { fclAsynX28PlusRemoteTELENETEntry 12 }


    fclAsynX28PlusRemLpX3Mode OBJECT-TYPE
        SYNTAX  INTEGER {
                transparent(1),
                networkVirtualTerminal(2),
                not-used(255)
                }
        ACCESS  read-write
        STATUS  mandatory
        DESCRIPTION
                "Terminal Virtuel"
        ::= { fclAsynX28PlusRemoteTELENETEntry 13 }


    fclAsynGeneralParameters OBJECT IDENTIFIER ::= { fclAsynchronousAccessLogPort 7 }


    fclAsynGenParLanguageType OBJECT-TYPE
        SYNTAX  INTEGER {
                french(1),
                english(2)
                }
        ACCESS  read-write
        STATUS  mandatory
        DESCRIPTION
                "Type de langue"
        ::= { fclAsynGeneralParameters 1 }


    fclAsynConfiguration OBJECT IDENTIFIER ::= { fclAsynchronousAccessLogPort 10 }


    fclAsynCfgConfigTable OBJECT-TYPE
        SYNTAX  SEQUENCE OF FclAsynCfgConfigEntry
        ACCESS  not-accessible
        STATUS  mandatory
        DESCRIPTION
                "This table contains the asynchronous
                configurations used in the asynchronous logical
                port table."
        ::= { fclAsynConfiguration 1 }


    fclAsynCfgConfigEntry OBJECT-TYPE
        SYNTAX  FclAsynCfgConfigEntry
        ACCESS  not-accessible
        STATUS  mandatory
        DESCRIPTION
                "An entry of fclAsynCfgConfigTable."
        INDEX   { fclAsynCfgConfigId }
        ::= { fclAsynCfgConfigTable 1 }


        FclAsynCfgConfigEntry ::=
                SEQUENCE {
                    fclAsynCfgConfigId
                        INTEGER,
                    fclAsynCfgStatus
                        INTEGER,
                    fclAsynCfgDescription
                        DisplayString,
                    fclAsynCfgX3ProfileId
                        INTEGER,
                    fclAsynCfgX3ModifCount
                        INTEGER,
                    fclAsynCfgConnectionProfileId
                        INTEGER,
                    fclAsynCfgConnModifCount
                        INTEGER
                }


    fclAsynCfgConfigId OBJECT-TYPE
        SYNTAX  INTEGER (0..199)
        ACCESS  read-only
        STATUS  mandatory
        DESCRIPTION
                "The value of this object identifies one and only
                one asynchronous configuration. This configuration
                may be referenced by fclAsynLpConfigId in the
                asynchronous logical port table.
                The possible values are : '0..199. If it is
                unused, the value of this parameter is '255'.
                The configuration parameters are described in :
                   fclAsynCfgX3Part1Table : X3 part 1,
                   fclAsynCfgX3Part2Table : X3 part 2,
                   fclAsynCfgConnLinkTable : data link level
                        (connection part),
                   fclAsynCfgConnFacilityTable  : facility level
                        (connection part),
                   fclAsynCfgConnServiceTable : service level
                        (connection part).
                When creating a new configuration each parameter
                takes its default value. Setting a profile allows
                the user to fill all the parameters with values
                pre-defined in this profile but each one may also
                be individually modified."
        ::= { fclAsynCfgConfigEntry 1 }


    fclAsynCfgStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclAsynCfgConfigEntry 2 }


    fclAsynCfgDescription OBJECT-TYPE
        SYNTAX  DisplayString (SIZE(0..32))
        ACCESS  read-write
        STATUS  mandatory
        DESCRIPTION
                "The value of this object stores a text description
                of the configuration elaborated by the user. This
                description may contains from 0 to 32 characters.
                The default value is 'TTY'."
        ::= { fclAsynCfgConfigEntry 3 }


    fclAsynCfgX3ProfileId OBJECT-TYPE
        SYNTAX  INTEGER (0..199)
        ACCESS  read-write
        STATUS  mandatory
        DESCRIPTION
                "The value of this object is the profile number
                used to automatically valorize all the X3
                parameters in an entry of the two tables which
                composes the X3 part of asynchronous
                configurations (see fclAsynCfgConfigId).

                The possible values are :
                   00 Plain terminal,
                   01 Transparent terminal or LSCP,
                   02 LSCP,
                   03 Terminal communicating with LSCP,
                   04 Same as profile 03 with send time-out and
                      padding,
                   05 Terminal with control by PAD,
                   06 Same es profile 00 with special break and
                      break,
                   08 Same as profile 05 with echo,
                   09 Telex terminals,
                   10 Same as profile 05 without control by PAD,
                   11 Same as profile 02 without control by PAD,
                   12 Same as profile 00 without echo,
                   13 Block mode terminal controlled by PAD
                      without send time-out,
                   14 Same as profile 13 with authorized DLE,
                   15 Same as profile 13 without control,
                   16 Host HEWLETT PACKARD,
                   17 Terminal HEWLETT PACKARD,
                   20 Same as profile 00 with control and
                      teleprinter adapted editing,
                   21 Same as profile 20 with display-terminal
                      adapted editing,
                   22 Same as profile 13 with control bye DTE-C,
                   23 Same as profile 21 for data base
                      application,
                   30 VIDEOTEX terminal,
                   32 Multi-standard VIDEOTEX terminal,
                   80 User defined profile : the values in this
                      profile are defined by the user (they may be
                      specified in groups
                      fclAsynCfgX3UserProfilePart1 and
                      fclAsynCfgX3UserProfilePart2,
                   89 Special terminal,
                   90 Plain terminal without padding or send
                      time-out,
                   91 Plain transparent LSCP.

                If it is unused, the value of this parameter is
                '255'.
                The default value is '89' (meaning that default
                values of X3 parameters are those pre-defined in
                profile number 89)."
        ::= { fclAsynCfgConfigEntry 4 }


    fclAsynCfgX3ModifCount OBJECT-TYPE
        SYNTAX  INTEGER (0..255)
        ACCESS  read-only
        STATUS  mandatory
        DESCRIPTION
                "The value of this object indicates how many X3
                parameters have not the value defined in the
                profile specified by fclAsynCfgX3ProfileId (i.e
                how many individual modifications)."
        ::= { fclAsynCfgConfigEntry 5 }


    fclAsynCfgConnectionProfileId OBJECT-TYPE
        SYNTAX  INTEGER (0..199)
        ACCESS  read-write
        STATUS  mandatory
        DESCRIPTION
                "The value of this object is the profile number
                used to automatically valorize all the connection
                parameters in an entry of the three tables which
                composes the connection part of asynchronous
                configurations (see fclAsynCfgConfigId).

                The possible values are :
                   07 Terminal with automatic baud rate detect,
                   08 Direct connected terminal,
                   09 Terminal connection PSTN,
                   10 Terminal connected by dedicated line,
                   11 LSCP terminal - direct connection,
                   12 LSCP terminal - dedicated line connection,
                   13 LSCP-A terminal - direct connection,
                   14 LSCP-A terminal - dedicated line connection,
                   15 Minitel terminal - direct connection,
                   16 Minitel terminal - PSTN connection,
                   34 TTY terminal - PSTN connection (V.25 bis),
                   35 Minitel terminal - PSTN connection (V.25
                      bis),
                   36 Minitel terminal - PSTN connection (modem
                      turnaround),
                   37 Multistandard videotex terminal,
                   38 Kiosk micro computer,

                If it is unused, the value of this parameter is
                '255'.
                The default value is '8' (meaning that default
                values of connection parameters are those
                pre-defined in profile number 08)."
        ::= { fclAsynCfgConfigEntry 6 }


    fclAsynCfgConnModifCount OBJECT-TYPE
        SYNTAX  INTEGER (0..255)
        ACCESS  read-only
        STATUS  mandatory
        DESCRIPTION
                "The value of this object indicates how many
                connection parameters have not the value defined
                in the profile specified by
                fclAsynCfgConnectionProfileId (i.e how many
                individual modifications)."
        ::= { fclAsynCfgConfigEntry 7 }


    fclAsynCfgX3Part1Table OBJECT-TYPE
        SYNTAX  SEQUENCE OF FclAsynCfgX3Part1Entry
        ACCESS  not-accessible
        STATUS  mandatory
        DESCRIPTION
                "This table contains the X3 parameters (part 1) of
                asynchronous configurations."
        ::= { fclAsynConfiguration 11 }


    fclAsynCfgX3Part1Entry OBJECT-TYPE
        SYNTAX  FclAsynCfgX3Part1Entry
        ACCESS  not-accessible
        STATUS  mandatory
        DESCRIPTION
                "An entry of fclAsynCfgX3Part1Table."
        INDEX   { fclAsynCfgX3Part1ConfigId }
        ::= { fclAsynCfgX3Part1Table 1 }


        FclAsynCfgX3Part1Entry ::=
                SEQUENCE {
                    fclAsynCfgX3Part1ConfigId
                        INTEGER,
                    fclAsynCfgX3Part1ProfileId
                        INTEGER,
                    fclAsynCfgX3P01EscapeChar
                        INTEGER,
                    fclAsynCfgX3P02Echo
                        INTEGER,
                    fclAsynCfgX3P03ForwardingChar
                        INTEGER,
                    fclAsynCfgX3P04IdleTimerDelay
                        INTEGER,
                    fclAsynCfgX3P05OutputFlowCtrl
                        INTEGER,
                    fclAsynCfgX3P06ServiceSignals
                        INTEGER,
                    fclAsynCfgX3P07BreakHandling
                        INTEGER,
                    fclAsynCfgX3P08OutputDiscard
                        INTEGER,
                    fclAsynCfgX3P09CrPadding
                        INTEGER,
                    fclAsynCfgX3P10LineFolding
                        INTEGER,
                    fclAsynCfgX3P11BinarySpeed
                        INTEGER
                }


    fclAsynCfgX3Part1ConfigId OBJECT-TYPE
        SYNTAX  INTEGER (0..199)
        ACCESS  read-only
        STATUS  mandatory
        DESCRIPTION
                "The value of this object identifies one and only
                one asynchronous configuration. The possible
                values are : '0..199. If it is unused, the value
                of this parameter is '255'."
        ::= { fclAsynCfgX3Part1Entry 1 }


    fclAsynCfgX3Part1ProfileId OBJECT-TYPE
        SYNTAX  INTEGER (0..199)
        ACCESS  read-only
        STATUS  mandatory
        DESCRIPTION
                "The value of this object is the X3 profile number
                used to create this configuration."
        ::= { fclAsynCfgX3Part1Entry 2 }


    fclAsynCfgX3P01EscapeChar OBJECT-TYPE
        SYNTAX  INTEGER (0..126)
        ACCESS  read-write
        STATUS  mandatory
        DESCRIPTION
                "The value of this object is the character to
                escape from the data transfer state and to recall
                the PAD. The authorized values are '0..126'. The
                value '0' indicates no escape. The value '1' is
                the DLE character. The values '2..126' are the
                ASCII code of the character. The default value is
                '1'."
        ::= { fclAsynCfgX3Part1Entry 11 }


    fclAsynCfgX3P02Echo OBJECT-TYPE
        SYNTAX  INTEGER {
                val0-off(1),
                val1-on(2)
                }
        ACCESS  read-write
        STATUS  mandatory
        DESCRIPTION
                "The value of this object indicates whether the
                echo is local not. The authorized values are 'off'
                (echoing by the terminal), 'on' (echoing by the
                equipment). The default value is 'on'."
        ::= { fclAsynCfgX3Part1Entry 12 }


    fclAsynCfgX3P03ForwardingChar OBJECT-TYPE
        SYNTAX  INTEGER {
                val0-none(1),
                val2-cr(3),
                val6-crEscBelEnqAck(7),
                val18-crEotEtx(19),
                val32-htLfVtFf(33),
                val126-allCtrlChars(127),
                val127-allChars(128),
                val128-allCtrlChars-vdxFunctionKeys(129),
                val253-encapsCharacSLIP(254),
                val254-encapsCharacPPP(255)
                }
        ACCESS  read-write
        STATUS  mandatory
        DESCRIPTION
                "The value of this object is the data forwarding
                character(s). The authorized values are 'none' (no
                character), 'CR' (Carriage Return), 'CR ESC BEL
                ENQ ACK' (Carriage Return, Escape, Bell, Enquire,
                Acknowledge), 'CR EOT ETX' (Carriage Return, End
                Of Text, End Of Transmission), 'HT LF VT FF'
                (Horizontal Tabulation, Line Feed, Vertical
                Tabulation, Form Feed), 'all Ctrl Chars' (all
                control characters), 'all Chars' (all characters),
                'all Ctrl Chars vdxFunctionKeys' (all control
                characters and videotext function keys),
                'encapsCharacSLIP', 'encapsCharacPPP'. The default
                value is 'all Ctrl Chars'."
        ::= { fclAsynCfgX3Part1Entry 13 }


    fclAsynCfgX3P04IdleTimerDelay OBJECT-TYPE
        SYNTAX  INTEGER (0..250)
        ACCESS  read-write
        STATUS  mandatory
        DESCRIPTION
                "The value of this object is the idle timer delay
                in twentieths of a second. The authorized values
                are '0..250'. The value '0' will indicate that no
                data forwarding on time-out is required. The
                default value is '0'."
        ::= { fclAsynCfgX3Part1Entry 14 }


    fclAsynCfgX3P05OutputFlowCtrl OBJECT-TYPE
        SYNTAX  INTEGER {
                val0-none(1),
                val1-xonXoffInTransfer(2),
                val2-xonXoff(3),
                val8-rtsCtsInTransfer(9)
                }
        ACCESS  read-write
        STATUS  mandatory
        DESCRIPTION
                "The value of this object indicates the flow
                control type from the equipment to the terminal.
                The authorized values are 'none' (no use of XON
                and XOFF), 'xonXoffInTransfer' (use of XON and
                XOFF in data transfer), 'xonXoff' (use of XON and
                XOFF in data transfer and command),
                'rtsCtsInTransfer' (use of CTS and RTS signals in
                transfer). The default value is 'none'."
        ::= { fclAsynCfgX3Part1Entry 15 }


    fclAsynCfgX3P06ServiceSignals OBJECT-TYPE
        SYNTAX  INTEGER {
                val0-none(1),
                val1-servSignal-stdFormat(2),
                val5-servSignalAndPrompt-stdFormat(6),
                val9-servSignal-explicitFormat(10),
                val13-servSignalAndPrompt-explicitFormat(14)
                }
        ACCESS  read-write
        STATUS  mandatory
        DESCRIPTION
                "The value of this object is the control of service
                signals and command signals sent by the equipment.
                The authorized values are 'none' (no service
                signals are transmitted to the start-stop mode
                DTE), 'servSignal-stdFormat' (service signals
                other than the prompt PAD service signal are
                transmitted in the standard format),
                'servSignalAndPrompt-stdFormat' (service signals
                and the prompt service signal are transmitted in
                the standard format), 'servSignal-explicitFormat'
                (service signals other than the prompt service
                signal are transmitted in the explicit format),
                'servSignalAndPrompt-explicitFormat' (service
                signals and the prompt service signal are
                transmitted in the explicit format). The default
                value is 'servSignalAndPrompt-explicitFormat'."
        ::= { fclAsynCfgX3Part1Entry 16 }


    fclAsynCfgX3P07BreakHandling OBJECT-TYPE
        SYNTAX  INTEGER {
                val0-forwardingChar(1),
                val1-interrupt(2),
                val2-reset(3),
                val4-breakIndication(5),
                val5-interrupt-breakIndication(6),
                val8-escapeFromTransfer(9),
                val21-interrupt-breakIndication-discardOutput(22)
                }
        ACCESS  read-write
        STATUS  mandatory
        DESCRIPTION
                "The value of this object is the selection of
                equipment operations on receipt of break signal
                from the start-stop mode DTE. The authorized
                values are 'forwardingChar' (no particular
                operation), 'interrupt' (send to packet mode DTE
                or other PAD an interrupt packet), 'reset'
                (reset), 'interrupt-breakIndication' (send to
                packet mode DTE or other PAD an interrupt packet
                and an indication of break PAD message),
                'escapeFromTransfer' (escape from data transfer
                state), 'interrupt-breakIndication-discardOutput'
                (send to packet mode DTE or other PAD an interrupt
                packet and an indication of break PAD message, and
                discard output to start-stop mode DTE). The
                default value is 'reset'."
        ::= { fclAsynCfgX3Part1Entry 17 }


    fclAsynCfgX3P08OutputDiscard OBJECT-TYPE
        SYNTAX  INTEGER {
                val0-off(1),
                val1-on(2)
                }
        ACCESS  read-write
        STATUS  mandatory
        DESCRIPTION
                "The value of this object indicates whether data
                are sent to the terminal or not. The authorized
                values are 'off' (normal data delivery to the
                start-stop mode DTE), 'on' (discard output to
                start-stop mode DTE). The default value is 'off'."
        ::= { fclAsynCfgX3Part1Entry 18 }


    fclAsynCfgX3P09CrPadding OBJECT-TYPE
        SYNTAX  INTEGER (0..250)
        ACCESS  read-write
        STATUS  mandatory
        DESCRIPTION
                "The value of this object indicates the padding
                after carriage return. The authorized values are
                '0..250'. A value between '0' and '250' will
                indicate the number of padding characters to be
                generated by the equipment after a carriage return
                character is transmitted to the start-stop mode
                DTE. When the value of this parameter is '0',
                there will be no padding except that PAD service
                signals will contain a number of padding
                characters according to the data rate of the
                start-stop mode DTE. The default value is '4'."
        ::= { fclAsynCfgX3Part1Entry 19 }


    fclAsynCfgX3P10LineFolding OBJECT-TYPE
        SYNTAX  INTEGER (0..250)
        ACCESS  read-write
        STATUS  mandatory
        DESCRIPTION
                "The value of this object indicates the line
                folding. The authorized values are '0..250'. The
                value '0' indicates no line folding. A value
                between '1' and '250' will indicate the number of
                graphic characters per line that will be
                transmitted by the equipment without inserting
                appropriate format effectors. The default value is
                '0'."
        ::= { fclAsynCfgX3Part1Entry 20 }


    fclAsynCfgX3P11BinarySpeed OBJECT-TYPE
        SYNTAX  INTEGER {
                val0-110(1),
                val1-134-5(2),
                val2-300(3),
                val3-1200(4),
                val4-600(5),
                val5-75(6),
                val6-150(7),
                val7-1800(8),
                val8-200(9),
                val9-100(10),
                val10-50(11),
                val11-in75Out1200(12),
                val12-2400(13),
                val13-4800(14),
                val14-9600(15),
                val15-19200(16),
                val23-28800(24),
                val17-57600(18),
                val20-38400(21),
                val21-out1200In75(22),
                val22-115200(23)
                }
        ACCESS  read-write
        STATUS  mandatory
        DESCRIPTION
                "The value of this object is the binary speed in
                bits per second."
        ::= { fclAsynCfgX3Part1Entry 21 }


    fclAsynCfgX3Part2Table OBJECT-TYPE
        SYNTAX  SEQUENCE OF FclAsynCfgX3Part2Entry
        ACCESS  not-accessible
        STATUS  mandatory
        DESCRIPTION
                "This table contains the X3 parameters (part 2) of
                asynchronous configurations."
        ::= { fclAsynConfiguration 12 }


    fclAsynCfgX3Part2Entry OBJECT-TYPE
        SYNTAX  FclAsynCfgX3Part2Entry
        ACCESS  not-accessible
        STATUS  mandatory
        DESCRIPTION
                "An entry of fclAsynCfgX3Part2Table."
        INDEX   { fclAsynCfgX3Part2ConfigId }
        ::= { fclAsynCfgX3Part2Table 1 }


        FclAsynCfgX3Part2Entry ::=
                SEQUENCE {
                    fclAsynCfgX3Part2ConfigId
                        INTEGER,
                    fclAsynCfgX3Part2ProfileId
                        INTEGER,
                    fclAsynCfgX3P12InputFlowCtrl
                        INTEGER,
                    fclAsynCfgX3P13LfInsertion
                        INTEGER,
                    fclAsynCfgX3P14LfPadding
                        INTEGER,
                    fclAsynCfgX3P15Editing
                        INTEGER,
                    fclAsynCfgX3P16CharDelete
                        INTEGER,
                    fclAsynCfgX3P17LineDelete
                        INTEGER,
                    fclAsynCfgX3P18LineDisplay
                        INTEGER,
                    fclAsynCfgX3P19EditingSignal
                        INTEGER,
                    fclAsynCfgX3P20EchoMask
                        INTEGER,
                    fclAsynCfgX3P21Parity
                        INTEGER,
                    fclAsynCfgX3P22PageWait
                        INTEGER
                }


    fclAsynCfgX3Part2ConfigId OBJECT-TYPE
        SYNTAX  INTEGER (0..199)
        ACCESS  read-only
        STATUS  mandatory
        DESCRIPTION
                "The value of this object identifies one and only
                one asynchronous configuration. The possible
                values are : '0..199. If it is unused, the value
                of this parameter is '255'."
        ::= { fclAsynCfgX3Part2Entry 1 }


    fclAsynCfgX3Part2ProfileId OBJECT-TYPE
        SYNTAX  INTEGER (0..199)
        ACCESS  read-only
        STATUS  mandatory
        DESCRIPTION
                "The value of this object is the X3 profile number
                used to create this configuration."
        ::= { fclAsynCfgX3Part2Entry 2 }


    fclAsynCfgX3P12InputFlowCtrl OBJECT-TYPE
        SYNTAX  INTEGER {
                val0-none(1),
                val1-xonXoff(2),
                val8-rtsCts(9)
                }
        ACCESS  read-write
        STATUS  mandatory
        DESCRIPTION
                "The value of this object indicates the flow
                control type from the start-stop mode DTE to the
                equipment. The authorized values are 'none' (no
                use of XON and XOFF for flow control), 'xonXoff'
                (use of XON and XOFF for flow control), 'rtsCts'
                (use of RTS and CTS for flow control). The default
                value is 'xonXoff'."
        ::= { fclAsynCfgX3Part2Entry 22 }


    fclAsynCfgX3P13LfInsertion OBJECT-TYPE
        SYNTAX  INTEGER {
                val0-none(1),
                val1-outCr(2),
                val2-inCr(3),
                val3-outCr-inCr(4),
                val4-outCrEcho(5),
                val5-outCr-outCrEcho(6),
                val6-inCr-outCrEcho(7),
                val7-outCr-inCr-outCrEcho(8)
                }
        ACCESS  read-write
        STATUS  mandatory
        DESCRIPTION
                "The value of this object indicates where there is
                the Line Feed insertion after Carriage Return. The
                authorized values are 'none' (no Line Feed
                insertion), 'outCr' (insert Line Feed after each
                Carriage Return in the data stream to the
                start-stop mode DTE), 'inCr' (insert Line Feed
                after each Carriage Return in the data stream from
                the start-stop mode DTE), 'outCr-inCr' (insert
                Line Feed after each Carriage Return in the data
                stream from and to the start-stop mode DTE),
                'outCrEcho' (insert Line Feed after each Carriage
                Return in the echo stream to the start-stop mode
                DTE), 'outCr-outCrEcho' ('outCr' + 'outCrEcho'),
                'inCr-outCrEcho' ('inCr' + 'outCrEcho'),
                'outCr-inCr-outCrEcho' ('outCr-inCr' +
                'outCrEcho'). The default value is 'none'."
        ::= { fclAsynCfgX3Part2Entry 23 }


    fclAsynCfgX3P14LfPadding OBJECT-TYPE
        SYNTAX  INTEGER (0..250)
        ACCESS  read-write
        STATUS  mandatory
        DESCRIPTION
                "The value of this object is the Line Feed padding.
                The authorized values are '0..250'. A value
                between '0' and '250' will indicate the number of
                padding characters to be generated by the
                equipement after a Line Feed character transmitted
                to the start-stop mode DTE during the data
                transfer state. The default value is '0'."
        ::= { fclAsynCfgX3Part2Entry 24 }


    fclAsynCfgX3P15Editing OBJECT-TYPE
        SYNTAX  INTEGER {
                val0-off(1),
                val1-on(2)
                }
        ACCESS  read-write
        STATUS  mandatory
        DESCRIPTION
                "The value of this object indicates the editing
                mode. The authorized values are 'off', 'on'. The
                default value is 'on'."
        ::= { fclAsynCfgX3Part2Entry 25 }


    fclAsynCfgX3P16CharDelete OBJECT-TYPE
        SYNTAX  INTEGER (0..128)
        ACCESS  read-write
        STATUS  mandatory
        DESCRIPTION
                "The value of this object is the 'character delete'
                character. The authorized values are '0..128'. The
                default value is '127'."
        ::= { fclAsynCfgX3Part2Entry 26 }


    fclAsynCfgX3P17LineDelete OBJECT-TYPE
        SYNTAX  INTEGER (0..128)
        ACCESS  read-write
        STATUS  mandatory
        DESCRIPTION
                "The value of this object is the 'line delete'
                character. The authorized values are '0..128'. The
                default value is '24'."
        ::= { fclAsynCfgX3Part2Entry 27 }


    fclAsynCfgX3P18LineDisplay OBJECT-TYPE
        SYNTAX  INTEGER (0..127)
        ACCESS  read-write
        STATUS  mandatory
        DESCRIPTION
                "The value of this object is the 'line display'
                character. The authorized values are '0..127'. The
                default value is '0'."
        ::= { fclAsynCfgX3Part2Entry 28 }


    fclAsynCfgX3P19EditingSignal OBJECT-TYPE
        SYNTAX  INTEGER {
                val0-none(1),
                val1-printingTerminal(2),
                val2-displayTerminal(3)
                }
        ACCESS  read-write
        STATUS  mandatory
        DESCRIPTION
                "The value of this object defines the editing PAD
                service signals. The authorized values are 'none'
                (no editing PAD service signals),
                'printingTerminal' (editing PAD service signals
                for printing terminals), 'displayTerminal'
                (editing PAD service signals for display
                terminals). The default value is 'displayTerminal'."
        ::= { fclAsynCfgX3Part2Entry 29 }


    fclAsynCfgX3P20EchoMask OBJECT-TYPE
        SYNTAX  INTEGER (0..255)
        ACCESS  read-write
        STATUS  mandatory
        DESCRIPTION
                "The value of this object is the echo mask. The
                authorized values are '0..255'. The default value
                is '64'."
        ::= { fclAsynCfgX3Part2Entry 30 }


    fclAsynCfgX3P21Parity OBJECT-TYPE
        SYNTAX  INTEGER {
                val0-none(1),
                val1-check(2),
                val2-generate(3),
                val3-check-generate(4)
                }
        ACCESS  read-write
        STATUS  mandatory
        DESCRIPTION
                "The value of this object indicates the parity
                treatment. The authorized values are 'none' (no
                parity checking or generation), 'check' (parity
                checking), 'generate' (parity generation),
                'check-generate' (parity checking and generation).
                The default value is 'none'."
        ::= { fclAsynCfgX3Part2Entry 31 }


    fclAsynCfgX3P22PageWait OBJECT-TYPE
        SYNTAX  INTEGER (0..127)
        ACCESS  read-write
        STATUS  mandatory
        DESCRIPTION
                "The value of this object defines the page wait.
                The authorized values are '0..127'. The value '0'
                indicates that the page wait is disabled. A value
                between '1' and '127' is the number of Line Feed
                characters sent by the equipment to the start-stop
                mode DTE. The default value is '0'."
        ::= { fclAsynCfgX3Part2Entry 32 }


    fclAsynCfgX3UserProfilePart1 OBJECT IDENTIFIER ::= { fclAsynConfiguration 15 }


    fclAsynCfgX3UserProfileId OBJECT-TYPE
        SYNTAX  INTEGER (0..199)
        ACCESS  read-only
        STATUS  mandatory
        DESCRIPTION
                "The value of this object is 80 the number of the
                user profile. This profile may be used, as any
                other X3 profile, to make a new asynchronous
                configuration in fclAsynCfgConfigTable."
        ::= { fclAsynCfgX3UserProfilePart1 3 }


    fclAsynCfgX3UserProfileDesc OBJECT-TYPE
        SYNTAX  DisplayString (SIZE(0..32))
        ACCESS  read-write
        STATUS  mandatory
        DESCRIPTION
                "The value of this object stores a text description
                of the user profile elaborated by the user. This
                description may contains from 0 to 32 characters.
                The default value is 'User profile'."
        ::= { fclAsynCfgX3UserProfilePart1 4 }


    fclAsynCfgX3UserP01EscapeChar OBJECT-TYPE
        SYNTAX  INTEGER (0..126)
        ACCESS  read-write
        STATUS  mandatory
        DESCRIPTION
                "The value of this object is the character to
                escape from the data transfer state and to recall
                the PAD. The authorized values are '0..126'. The
                value '0' indicates no escape. The value '1' is
                the DLE character. The values '2..126' are the
                ASCII code of the character. The default value is
                '1'."
        ::= { fclAsynCfgX3UserProfilePart1 11 }


    fclAsynCfgX3UserP02Echo OBJECT-TYPE
        SYNTAX  INTEGER {
                val0-off(1),
                val1-on(2)
                }
        ACCESS  read-write
        STATUS  mandatory
        DESCRIPTION
                "The value of this object indicates whether the
                echo is local not. The authorized values are 'off'
                (echoing by the terminal), 'on' (echoing by the
                equipment). The default value is 'on'."
        ::= { fclAsynCfgX3UserProfilePart1 12 }


    fclAsynCfgX3UserP03ForwardingChar OBJECT-TYPE
        SYNTAX  INTEGER {
                val0-none(1),
                val2-cr(3),
                val6-crEscBelEnqAck(7),
                val18-crEotEtx(19),
                val32-htLfVtFf(33),
                val126-allCtrlChars(127),
                val127-allChars(128),
                val128-allCtrlChars-vdxFunctionKeys(129),
                val253-encapsCharacSLIP(254),
                val254-encapsCharacPPP(255)
                }
        ACCESS  read-write
        STATUS  mandatory
        DESCRIPTION
                "The value of this object is the data forwarding
                character(s). The authorized values are 'none' (no
                character), 'CR' (Carriage Return), 'CR ESC BEL
                ENQ ACK' (Carriage Return, Escape, Bell, Enquire,
                Acknowledge), 'CR EOT ETX' (Carriage Return, End
                Of Text, End Of Transmission), 'HT LF VT FF'
                (Horizontal Tabulation, Line Feed, Vertical
                Tabulation, Form Feed), 'all Ctrl Chars' (all
                control characters), 'all Chars' (all characters),
                'all Ctrl Chars vdxFunctionKeys' (all control
                characters and videotext function keys)
                'encapsCharacSLIP', 'encapsCharacPPP'. The default
                value is 'all Ctrl Chars'."
        ::= { fclAsynCfgX3UserProfilePart1 13 }


    fclAsynCfgX3UserP04IdleTimerDelay OBJECT-TYPE
        SYNTAX  INTEGER (0..250)
        ACCESS  read-write
        STATUS  mandatory
        DESCRIPTION
                "The value of this object is the idle timer delay
                in twentieths of a second. The authorized values
                are '0..250'. The value '0' will indicate that no
                data forwarding on time-out is required. The
                default value is '0'."
        ::= { fclAsynCfgX3UserProfilePart1 14 }


    fclAsynCfgX3UserP05OutputFlowCtrl OBJECT-TYPE
        SYNTAX  INTEGER {
                val0-none(1),
                val1-xonXoffInTransfer(2),
                val2-xonXoff(3),
                val8-rtsCtsInTransfer(9)
                }
        ACCESS  read-write
        STATUS  mandatory
        DESCRIPTION
                "The value of this object indicates the flow
                control type from the equipment to the terminal.
                The authorized values are 'none' (no use of XON
                and XOFF), 'xonXoffInTransfer' (use of XON and
                XOFF in data transfer), 'xonXoff' (use of XON and
                XOFF in data transfer and command),
                'rtsCtsInTransfer' (use of CTS and RTS signals in
                transfer). The default value is 'none'."
        ::= { fclAsynCfgX3UserProfilePart1 15 }


    fclAsynCfgX3UserP06ServiceSignals OBJECT-TYPE
        SYNTAX  INTEGER {
                val0-none(1),
                val1-servSignal-stdFormat(2),
                val5-servSignalAndPrompt-stdFormat(6),
                val9-servSignal-explicitFormat(10),
                val13-servSignalAndPrompt-explicitFormat(14)
                }
        ACCESS  read-write
        STATUS  mandatory
        DESCRIPTION
                "The value of this object is the control of service
                signals and command signals sent by the equipment.
                The authorized values are 'none' (no service
                signals are transmitted to the start-stop mode
                DTE), 'servSignal-stdFormat' (service signals
                other than the prompt PAD service signal are
                transmitted in the standard format),
                'servSignalAndPrompt-stdFormat' (service signals
                and the prompt service signal are transmitted in
                the standard format), 'servSignal-explicitFormat'
                (service signals other than the prompt service
                signal are transmitted in the explicit format),
                'servSignalAndPrompt-explicitFormat' (service
                signals and the prompt service signal are
                transmitted in the explicit format). The default
                value is 'servSignalAndPrompt-explicitFormat'."
        ::= { fclAsynCfgX3UserProfilePart1 16 }


    fclAsynCfgX3UserP07BreakHandling OBJECT-TYPE
        SYNTAX  INTEGER {
                val0-forwardingChar(1),
                val1-interrupt(2),
                val2-reset(3),
                val4-breakIndication(5),
                val5-interrupt-breakIndication(6),
                val8-escapeFromTransfer(9),
                val21-interrupt-breakIndication-discardOutput(22)
                }
        ACCESS  read-write
        STATUS  mandatory
        DESCRIPTION
                "The value of this object is the selection of
                equipment operations on receipt of break signal
                from the start-stop mode DTE. The authorized
                values are 'forwardingChar' (no particular
                operation), 'interrupt' (send to packet mode DTE
                or other PAD an interrupt packet), 'reset'
                (reset), 'interrupt-breakIndication' (send to
                packet mode DTE or other PAD an interrupt packet
                and an indication of break PAD message),
                'escapeFromTransfer' (escape from data transfer
                state), 'interrupt-breakIndication-discardOutput'
                (send to packet mode DTE or other PAD an interrupt
                packet and an indication of break PAD message, and
                discard output to start-stop mode DTE). The
                default value is 'reset'."
        ::= { fclAsynCfgX3UserProfilePart1 17 }


    fclAsynCfgX3UserP08OutputDiscard OBJECT-TYPE
        SYNTAX  INTEGER {
                val0-off(1),
                val1-on(2)
                }
        ACCESS  read-write
        STATUS  mandatory
        DESCRIPTION
                "The value of this object indicates whether data
                are sent to the terminal or not. The authorized
                values are 'off' (normal data delivery to the
                start-stop mode DTE), 'on' (discard output to
                start-stop mode DTE). The default value is 'off'."
        ::= { fclAsynCfgX3UserProfilePart1 18 }


    fclAsynCfgX3UserP09CrPadding OBJECT-TYPE
        SYNTAX  INTEGER (0..250)
        ACCESS  read-write
        STATUS  mandatory
        DESCRIPTION
                "The value of this object indicates the padding
                after carriage return. The authorized values are
                '0..250'. A value between '0' and '250' will
                indicate the number of padding characters to be
                generated by the equipment after a carriage return
                character is transmitted to the start-stop mode
                DTE. When the value of this parameter is '0',
                there will be no padding except that PAD service
                signals will contain a number of padding
                characters according to the data rate of the
                start-stop mode DTE. The default value is '4'."
        ::= { fclAsynCfgX3UserProfilePart1 19 }


    fclAsynCfgX3UserP10LineFolding OBJECT-TYPE
        SYNTAX  INTEGER (0..250)
        ACCESS  read-write
        STATUS  mandatory
        DESCRIPTION
                "The value of this object indicates the line
                folding. The authorized values are '0..250'. The
                value '0' indicates no line folding. A value
                between '1' and '250' will indicate the number of
                graphic characters per line that will be
                transmitted by the equipment without inserting
                appropriate format effectors. The default value is
                '0'."
        ::= { fclAsynCfgX3UserProfilePart1 20 }


    fclAsynCfgX3UserP11BinarySpeed OBJECT-TYPE
        SYNTAX  INTEGER {
                val0-110(1),
                val1-134-5(2),
                val2-300(3),
                val3-1200(4),
                val4-600(5),
                val5-75(6),
                val6-150(7),
                val7-1800(8),
                val8-200(9),
                val9-100(10),
                val10-50(11),
                val11-75-1200(12),
                val12-2400(13),
                val13-4800(14),
                val14-9600(15),
                val15-19200(16),
                val23-28800(24),
                val17-57600(18),
                val20-38400(21),
                val21-1200-75(22),
                val22-115200(23)
                }
        ACCESS  read-write
        STATUS  mandatory
        DESCRIPTION
                "The value of this object is the binary speed in
                bits per second."
        ::= { fclAsynCfgX3UserProfilePart1 21 }


    fclAsynCfgX3UserProfilePart2 OBJECT IDENTIFIER ::= { fclAsynConfiguration 16 }


    fclAsynCfgX3UserP12InputFlowCtrl OBJECT-TYPE
        SYNTAX  INTEGER {
                val0-none(1),
                val1-xonXoff(2),
                val8-rtsCts(9)
                }
        ACCESS  read-write
        STATUS  mandatory
        DESCRIPTION
                "The value of this object indicates the flow
                control type from the start-stop mode DTE to the
                equipment. The authorized values are 'none' (no
                use of XON and XOFF for flow control), 'xonXoff'
                (use of XON and XOFF for flow control), 'rtsCts'
                (use of RTS and CTS for flow control). The default
                value is 'xonXoff'."
        ::= { fclAsynCfgX3UserProfilePart2 22 }


    fclAsynCfgX3UserP13LfInsertion OBJECT-TYPE
        SYNTAX  INTEGER {
                val0-none(1),
                val1-outCr(2),
                val2-inCr(3),
                val3-outCr-inCr(4),
                val4-outCrEcho(5),
                val5-outCr-outCrEcho(6),
                val6-inCr-outCrEcho(7),
                val7-outCr-inCr-outCrEcho(8)
                }
        ACCESS  read-write
        STATUS  mandatory
        DESCRIPTION
                "The value of this object indicates where there is
                the Line Feed insertion after Carriage Return. The
                authorized values are 'none' (no Line Feed
                insertion), 'outCr' (insert Line Feed after each
                Carriage Return in the data stream to the
                start-stop mode DTE), 'inCr' (insert Line Feed
                after each Carriage Return in the data stream from
                the start-stop mode DTE), 'outCr-inCr' (insert
                Line Feed after each Carriage Return in the data
                stream from and to the start-stop mode DTE),
                'outCrEcho' (insert Line Feed after each Carriage
                Return in the echo stream to the start-stop mode
                DTE), 'outCr-outCrEcho' ('outCr' + 'outCrEcho'),
                'inCr-outCrEcho' ('inCr' + 'outCrEcho'),
                'outCr-inCr-outCrEcho' ('outCr-inCr' +
                'outCrEcho'). The default value is 'none'."
        ::= { fclAsynCfgX3UserProfilePart2 23 }


    fclAsynCfgX3UserP14LfPadding OBJECT-TYPE
        SYNTAX  INTEGER (0..250)
        ACCESS  read-write
        STATUS  mandatory
        DESCRIPTION
                "The value of this object is the Line Feed padding.
                The authorized values are '0..250'. A value
                between '0' and '250' will indicate the number of
                padding characters to be generated by the
                equipement after a Line Feed character transmitted
                to the start-stop mode DTE during the data
                transfer state. The default value is '0'."
        ::= { fclAsynCfgX3UserProfilePart2 24 }


    fclAsynCfgX3UserP15Editing OBJECT-TYPE
        SYNTAX  INTEGER {
                val0-off(1),
                val1-on(2)
                }
        ACCESS  read-write
        STATUS  mandatory
        DESCRIPTION
                "The value of this object indicates the editing
                mode. The authorized values are 'off', 'on'. The
                default value is 'on'."
        ::= { fclAsynCfgX3UserProfilePart2 25 }


    fclAsynCfgX3UserP16CharDelete OBJECT-TYPE
        SYNTAX  INTEGER (0..128)
        ACCESS  read-write
        STATUS  mandatory
        DESCRIPTION
                "The value of this object is the 'character delete'
                character. The authorized values are '0..128'. The
                default value is '127'."
        ::= { fclAsynCfgX3UserProfilePart2 26 }


    fclAsynCfgX3UserP17LineDelete OBJECT-TYPE
        SYNTAX  INTEGER (0..128)
        ACCESS  read-write
        STATUS  mandatory
        DESCRIPTION
                "The value of this object is the 'line delete'
                character. The authorized values are '0..128'. The
                default value is '24'."
        ::= { fclAsynCfgX3UserProfilePart2 27 }


    fclAsynCfgX3UserP18LineDisplay OBJECT-TYPE
        SYNTAX  INTEGER (0..127)
        ACCESS  read-write
        STATUS  mandatory
        DESCRIPTION
                "The value of this object is the 'line display'
                character. The authorized values are '0..127'. The
                default value is '0'."
        ::= { fclAsynCfgX3UserProfilePart2 28 }


    fclAsynCfgX3UserP19EditingSignal OBJECT-TYPE
        SYNTAX  INTEGER {
                val0-none(1),
                val1-printingTerminal(2),
                val2-displayTerminal(3)
                }
        ACCESS  read-write
        STATUS  mandatory
        DESCRIPTION
                "The value of this object defines the editing PAD
                service signals. The authorized values are 'none'
                (no editing PAD service signals),
                'printingTerminal' (editing PAD service signals
                for printing terminals), 'displayTerminal'
                (editing PAD service signals for display
                terminals). The default value is 'displayTerminal'."
        ::= { fclAsynCfgX3UserProfilePart2 29 }


    fclAsynCfgX3UserP20EchoMask OBJECT-TYPE
        SYNTAX  INTEGER (0..255)
        ACCESS  read-write
        STATUS  mandatory
        DESCRIPTION
                "The value of this object is the echo mask. The
                authorized values are '0..255'. The default value
                is '64'."
        ::= { fclAsynCfgX3UserProfilePart2 30 }


    fclAsynCfgX3UserP21Parity OBJECT-TYPE
        SYNTAX  INTEGER {
                val0-none(1),
                val1-check(2),
                val2-generate(3),
                val3-check-generate(4)
                }
        ACCESS  read-write
        STATUS  mandatory
        DESCRIPTION
                "The value of this object indicates the parity
                treatment. The authorized values are 'none' (no
                parity checking or generation), 'check' (parity
                checking), 'generate' (parity generation),
                'check-generate' (parity checking and generation).
                The default value is 'none'."
        ::= { fclAsynCfgX3UserProfilePart2 31 }


    fclAsynCfgX3UserP22PageWait OBJECT-TYPE
        SYNTAX  INTEGER (0..127)
        ACCESS  read-write
        STATUS  mandatory
        DESCRIPTION
                "The value of this object defines the page wait.
                The authorized values are '0..127'. The value '0'
                indicates that the page wait is disabled. A value
                between '1' and '127' is the number of Line Feed
                characters sent by the equipment to the start-stop
                mode DTE. The default value is '0'."
        ::= { fclAsynCfgX3UserProfilePart2 32 }


    fclAsynCfgConnLinkTable OBJECT-TYPE
        SYNTAX  SEQUENCE OF FclAsynCfgConnLinkEntry
        ACCESS  not-accessible
        STATUS  mandatory
        DESCRIPTION
                "This table contains the connection parameters
                (link part) of asynchronous configurations."
        ::= { fclAsynConfiguration 21 }


    fclAsynCfgConnLinkEntry OBJECT-TYPE
        SYNTAX  FclAsynCfgConnLinkEntry
        ACCESS  not-accessible
        STATUS  mandatory
        DESCRIPTION
                "An entry of fclAsynCfgConnLinkTable."
        INDEX   { fclAsynCfgLinkConfigId }
        ::= { fclAsynCfgConnLinkTable 1 }


        FclAsynCfgConnLinkEntry ::=
                SEQUENCE {
                    fclAsynCfgLinkConfigId
                        INTEGER,
                    fclAsynCfgLinkXonXoffParity
                        INTEGER,
                    fclAsynCfgLinkServSignalParity
                        INTEGER,
                    fclAsynCfgLinkDataParity
                        INTEGER,
                    fclAsynCfgLinkBitCount
                        INTEGER,
                    fclAsynCfgLinkStopBitCount
                        INTEGER,
                    fclAsynCfgLinkXonXoffSignal
                        INTEGER,
                    fclAsynCfgLinkInactivityTimer
                        INTEGER,
                    fclAsynCfgLinkBlockSize
                        INTEGER,
                    fclAsynCfgLinkCallResponseTimer
                        INTEGER
                }


    fclAsynCfgLinkConfigId OBJECT-TYPE
        SYNTAX  INTEGER (0..199)
        ACCESS  read-only
        STATUS  mandatory
        DESCRIPTION
                "The value of this object identifies one and only
                one asynchronous configuration. The possible
                values are : '0..199. If it is unused, the value
                of this parameter is '255'."
        ::= { fclAsynCfgConnLinkEntry 1 }


    fclAsynCfgLinkXonXoffParity OBJECT-TYPE
        SYNTAX  INTEGER {
                none(3),
                even(1),
                odd(2)
                }
        ACCESS  read-write
        STATUS  mandatory
        DESCRIPTION
                "The value of this object indicates the XON/XOFF
                parity. The default value is 'even'."
        ::= { fclAsynCfgConnLinkEntry 2 }


    fclAsynCfgLinkServSignalParity OBJECT-TYPE
        SYNTAX  INTEGER {
                none(3),
                even(1),
                odd(2)
                }
        ACCESS  read-write
        STATUS  mandatory
        DESCRIPTION
                "The value of this object indicates the signals
                parity. The default value is 'even'."
        ::= { fclAsynCfgConnLinkEntry 3 }


    fclAsynCfgLinkDataParity OBJECT-TYPE
        SYNTAX  INTEGER {
                none(1),
                even(4),
                odd(2)
                }
        ACCESS  read-write
        STATUS  mandatory
        DESCRIPTION
                "The value of this object indicates the data
                parity. The default value is 'even'."
        ::= { fclAsynCfgConnLinkEntry 4 }


    fclAsynCfgLinkBitCount OBJECT-TYPE
        SYNTAX  INTEGER (7..8)
        ACCESS  read-write
        STATUS  mandatory
        DESCRIPTION
                "The value of this object indicates the number of
                bits by characters. The authorized values are '7'
                or '8'. The default value is '7'."
        ::= { fclAsynCfgConnLinkEntry 5 }


    fclAsynCfgLinkStopBitCount OBJECT-TYPE
        SYNTAX  INTEGER {
                one(4),
                oneAndAHalf(8),
                two(12)
                }
        ACCESS  read-write
        STATUS  mandatory
        DESCRIPTION
                "The value of this object defines the number of
                stop bits. The default value is 'one'."
        ::= { fclAsynCfgConnLinkEntry 6 }


    fclAsynCfgLinkXonXoffSignal OBJECT-TYPE
        SYNTAX  INTEGER {
                off(1),
                on(2)
                }
        ACCESS  read-write
        STATUS  mandatory
        DESCRIPTION
                "The value of this object indicates if there are a
                transmission of XOFF when moving to the command
                mode and a transmission of XON when moving to the
                data transmission mode. The default value is 'on'."
        ::= { fclAsynCfgConnLinkEntry 7 }


    fclAsynCfgLinkInactivityTimer OBJECT-TYPE
        SYNTAX  INTEGER (0..2500)
        ACCESS  read-write
        STATUS  mandatory
        DESCRIPTION
                "The value of this object defines the line
                inactivity time-out in transfer state. When the
                time-out expires, the call is cleared. For a
                Minitel using a PSTN profile, the telephone
                communication is cut when the VC is cleared (This
                after T/2 seconds). The authorized values are
                '0..2500'. The value '0' indicates no time-out.
                The default value is '0'."
        ::= { fclAsynCfgConnLinkEntry 8 }


    fclAsynCfgLinkBlockSize OBJECT-TYPE
        SYNTAX  INTEGER (1..128)
        ACCESS  read-write
        STATUS  mandatory
        DESCRIPTION
                "The value of this object indicates the number of
                bytes received by the equipment in the receive
                buffers. The authorized values are '1..128'. The
                default value is '128'."
        ::= { fclAsynCfgConnLinkEntry 9 }


    fclAsynCfgLinkCallResponseTimer OBJECT-TYPE
        SYNTAX  INTEGER (10..2500)
        ACCESS  read-write
        STATUS  mandatory
        DESCRIPTION
                "The value of this object is the supervision
                time-out for response to a call request packet
                sent on the link. A clear packet is sent if there
                is no response after this period. The authorized
                values are '10..2500'. The default value is '20'."
        ::= { fclAsynCfgConnLinkEntry 10 }


    fclAsynCfgConnFacilityTable OBJECT-TYPE
        SYNTAX  SEQUENCE OF FclAsynCfgConnFacilityEntry
        ACCESS  not-accessible
        STATUS  mandatory
        DESCRIPTION
                "This table contains the connection parameters
                (facility part) of asynchronous configurations."
        ::= { fclAsynConfiguration 25 }


    fclAsynCfgConnFacilityEntry OBJECT-TYPE
        SYNTAX  FclAsynCfgConnFacilityEntry
        ACCESS  not-accessible
        STATUS  mandatory
        DESCRIPTION
                "An entry of fclAsynCfgConnFacilityTable."
        INDEX   { fclAsynCfgFacConfigId }
        ::= { fclAsynCfgConnFacilityTable 1 }


        FclAsynCfgConnFacilityEntry ::=
                SEQUENCE {
                    fclAsynCfgFacConfigId
                        INTEGER,
                    fclAsynCfgFacClosedUserGroup
                        INTEGER,
                    fclAsynCfgFacReverseCharging
                        INTEGER,
                    fclAsynCfgFacThroughputClass
                        INTEGER,
                    fclAsynCfgFacDefOutThroughputClass
                        INTEGER,
                    fclAsynCfgFacDefInThroughputClass
                        INTEGER,
                    fclAsynCfgFacMaxOutThroughputClass
                        INTEGER,
                    fclAsynCfgFacMaxInThroughputClass
                        INTEGER,
                    fclAsynCfgFacPacketSize
                        INTEGER,
                    fclAsynCfgFacDefOutPacketSize
                        INTEGER,
                    fclAsynCfgFacDefInPacketSize
                        INTEGER,
                    fclAsynCfgFacMaxOutPacketSize
                        INTEGER,
                    fclAsynCfgFacMaxInPacketSize
                        INTEGER,
                    fclAsynCfgFacMinOutPacketSize
                        INTEGER,
                    fclAsynCfgFacMinInPacketSize
                        INTEGER,
                    fclAsynCfgFacWindowSize
                        INTEGER,
                    fclAsynCfgFacDefOutWindowSize
                        INTEGER,
                    fclAsynCfgFacDefInWindowSize
                        INTEGER,
                    fclAsynCfgFacMaxOutWindowSize
                        INTEGER,
                    fclAsynCfgFacMaxInWindowSize
                        INTEGER
                }


    fclAsynCfgFacConfigId OBJECT-TYPE
        SYNTAX  INTEGER (0..199)
        ACCESS  read-only
        STATUS  mandatory
        DESCRIPTION
                "The value of this object identifies one and only
                one asynchronous configuration. The possible
                values are : '0..199. If it is unused, the value
                of this parameter is '255'."
        ::= { fclAsynCfgConnFacilityEntry 1 }


    fclAsynCfgFacClosedUserGroup OBJECT-TYPE
        SYNTAX  INTEGER {
                noCheck(2),
                clear(1),
                subscribe(3)
                }
        ACCESS  read-write
        STATUS  mandatory
        DESCRIPTION
                "The value of this object specifies the behaviour
                of the equipment with respect to the Closed User
                Group (CUG) facility. There are 3 possible values
                :
                   noCheck : the CUG is not checked,
                   clear : clearing if the CUG is present in the
                        call packet,
                   subscribe : clearing if the CUG is not present
                        in the call packet.
                   The default value is 'noCheck'."
        ::= { fclAsynCfgConnFacilityEntry 2 }


    fclAsynCfgFacReverseCharging OBJECT-TYPE
        SYNTAX  INTEGER {
                refuse(1),
                accept(2)
                }
        ACCESS  read-write
        STATUS  mandatory
        DESCRIPTION
                "The value of this object specifies the behaviour
                of the equipment with respect to the reverse
                charging facility. If the called subscriber
                doesn't accept the reverse charging, the call is
                not transmitted and a clear is sent. The default
                value is 'refuse'."
        ::= { fclAsynCfgConnFacilityEntry 3 }


    fclAsynCfgFacThroughputClass OBJECT-TYPE
        SYNTAX  INTEGER {
                clear(1),
                subscribe(2)
                }
        ACCESS  read-write
        STATUS  mandatory
        DESCRIPTION
                "The value of this object indicates if the
                subscriber connected to the link has subscribed to
                throughput class negociation facility. The
                authorized values are 'clear' (not subscriber) or
                'subscribe'. The default value is 'clear'."
        ::= { fclAsynCfgConnFacilityEntry 10 }


    fclAsynCfgFacDefOutThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the default
                throughput class in transmit direction (equipment
                to remote peer). The default value is 9600 bits
                per second."
        ::= { fclAsynCfgConnFacilityEntry 11 }


    fclAsynCfgFacDefInThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the default
                throughput class in receive direction (remote peer
                to equipment). The default value is 9600 bits per
                second."
        ::= { fclAsynCfgConnFacilityEntry 12 }


    fclAsynCfgFacMaxOutThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the maximum
                throughput class in transmit direction (equipment
                to remote peer). The default value is 9600 bits
                per second."
        ::= { fclAsynCfgConnFacilityEntry 13 }


    fclAsynCfgFacMaxInThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the maximum
                throughput class in receive direction (remote peer
                to equipment). The default value is 9600 bits per
                second."
        ::= { fclAsynCfgConnFacilityEntry 14 }


    fclAsynCfgFacPacketSize OBJECT-TYPE
        SYNTAX  INTEGER {
                clear(1),
                subscribe(2)
                }
        ACCESS  read-write
        STATUS  mandatory
        DESCRIPTION
                "The value of this object indicates if the
                subscriber connected to the link has subscribed to
                packet size negociation facility. The authorized
                values are 'clear' (not subscriber) or
                'subscribe'. The default value is 'clear'."
        ::= { fclAsynCfgConnFacilityEntry 20 }


    fclAsynCfgFacDefOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the default
                packet size in transmit direction (equipment to
                remote peer). The default value is 128 octets."
        ::= { fclAsynCfgConnFacilityEntry 21 }


    fclAsynCfgFacDefInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the default
                packet size in receive direction (remote peer to
                equipment). The default value is 128 octets."
        ::= { fclAsynCfgConnFacilityEntry 22 }


    fclAsynCfgFacMaxOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the maximum
                packet size in transmit direction (equipment to
                remote peer). The default value is 128 octets."
        ::= { fclAsynCfgConnFacilityEntry 23 }


    fclAsynCfgFacMaxInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the maximum
                packet size in receive direction (remote peer to
                equipment). The default value is 128 octets."
        ::= { fclAsynCfgConnFacilityEntry 24 }


    fclAsynCfgFacMinOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the minimum
                packet size in transmit direction (equipment to
                remote peer). The default value is 16 octets."
        ::= { fclAsynCfgConnFacilityEntry 25 }


    fclAsynCfgFacMinInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the minimum
                packet size in receive direction (remote peer to
                equipment). The default value is 16 octets."
        ::= { fclAsynCfgConnFacilityEntry 26 }


    fclAsynCfgFacWindowSize OBJECT-TYPE
        SYNTAX  INTEGER {
                clear(1),
                subscribe(2)
                }
        ACCESS  read-write
        STATUS  mandatory
        DESCRIPTION
                "The value of this object indicates if the
                subscriber connected to the link has subscribed to
                the negociation of the transmit window size
                facility. The authorized values are 'clear' (not
                subscriber) or 'subscribe'. The default value is
                'clear'."
        ::= { fclAsynCfgConnFacilityEntry 30 }


    fclAsynCfgFacDefOutWindowSize OBJECT-TYPE
        SYNTAX  INTEGER (1..7)
        ACCESS  read-write
        STATUS  mandatory
        DESCRIPTION
                "The value of this object indicates the default
                window size in transmit direction (equipment to
                remote peer). The authorized values are '1..7'.
                The default value is '2'."
        ::= { fclAsynCfgConnFacilityEntry 31 }


    fclAsynCfgFacDefInWindowSize OBJECT-TYPE
        SYNTAX  INTEGER (1..7)
        ACCESS  read-write
        STATUS  mandatory
        DESCRIPTION
                "The value of this object indicates the default
                window size in receive direction (remote peer to
                equipment). The authorized values are '1..7'. The
                default value is '4'."
        ::= { fclAsynCfgConnFacilityEntry 32 }


    fclAsynCfgFacMaxOutWindowSize OBJECT-TYPE
        SYNTAX  INTEGER (1..7)
        ACCESS  read-write
        STATUS  mandatory
        DESCRIPTION
                "The value of this object indicates the maximum
                window size in transmit direction (equipment to
                remote peer). The authorized values are '1..7'.
                The default value is '3'."
        ::= { fclAsynCfgConnFacilityEntry 33 }


    fclAsynCfgFacMaxInWindowSize OBJECT-TYPE
        SYNTAX  INTEGER (1..7)
        ACCESS  read-write
        STATUS  mandatory
        DESCRIPTION
                "The value of this object indicates the maximum
                window size in receive direction (remote peer to
                equipment). The authorized values are '1..7'. The
                default value is '4'."
        ::= { fclAsynCfgConnFacilityEntry 34 }


    fclAsynCfgConnServiceTable OBJECT-TYPE
        SYNTAX  SEQUENCE OF FclAsynCfgConnServiceEntry
        ACCESS  not-accessible
        STATUS  mandatory
        DESCRIPTION
                "This table contains the connection parameters
                (service part) of asynchronous configurations."
        ::= { fclAsynConfiguration 30 }


    fclAsynCfgConnServiceEntry OBJECT-TYPE
        SYNTAX  FclAsynCfgConnServiceEntry
        ACCESS  not-accessible
        STATUS  mandatory
        DESCRIPTION
                "An entry of fclAsynCfgConnServiceTable."
        INDEX   { fclAsynCfgSerConfigId }
        ::= { fclAsynCfgConnServiceTable 1 }


        FclAsynCfgConnServiceEntry ::=
                SEQUENCE {
                    fclAsynCfgSerConfigId
                        INTEGER,
                    fclAsynCfgSerCompression
                        INTEGER,
                    fclAsynCfgSerCompressNegociation
                        INTEGER,
                    fclAsynCfgSerCompressScrambling
                        INTEGER,
                    fclAsynCfgSerCompressMultiPacketsTimer
                        INTEGER,
                    fclAsynCfgSerX29Reselection
                        INTEGER,
                    fclAsynCfgSerCallReturnTransmission
                        INTEGER,
                    fclAsynCfgSerDBitModification
                        INTEGER,
                    fclAsynCfgSerReliableVc
                        INTEGER,
                    fclAsynCfgSerCos
                        INTEGER,
                    fclAsynCfgSerCir
                        INTEGER,
                    fclAsynCfgSerMinCir
                        INTEGER,
                    fclAsynCfgSerConversionAimedPoint
                        INTEGER,
                    fclAsynCfgSerConversionIncomingCall
                        INTEGER,
                    fclAsynCfgSerConversionOutgoingCall
                        INTEGER,
                    fclAsynCfgSerConversionAddressCheck
                        INTEGER
                }


    fclAsynCfgSerConfigId OBJECT-TYPE
        SYNTAX  INTEGER (0..199)
        ACCESS  read-only
        STATUS  mandatory
        DESCRIPTION
                "The value of this object identifies one and only
                one asynchronous configuration. The possible
                values are : '0..199. If it is unused, the value
                of this parameter is '255'."
        ::= { fclAsynCfgConnServiceEntry 1 }


    fclAsynCfgSerCompression OBJECT-TYPE
        SYNTAX  INTEGER {
                off(1),
                networkToSubscriber(2),
                subscriberToNetwork(3),
                bothway(4)
                }
        ACCESS  read-write
        STATUS  mandatory
        DESCRIPTION
                "The value of this object indicates the compression
                enabling for each direction. The authorized values
                are :
                   off : no compression,
                   networkToSubscriber : compression of the flow
                        from the remote peer to the equipment,
                   subscriberToNetwork : compression of the flow
                        from the equipment to the remote peer,
                   bothway : compression of the two flows from and
                        to the equipment.
                The default value is 'off'."
        ::= { fclAsynCfgConnServiceEntry 2 }


    fclAsynCfgSerCompressNegociation OBJECT-TYPE
        SYNTAX  INTEGER {
                off(1),
                onOptionalCompression(2),
                onMandatoryCompression(3)
                }
        ACCESS  read-write
        STATUS  mandatory
        DESCRIPTION
                "The value of this object indicates whether the
                compression facility is negociated or not and, if
                negociated, the optional/obligatory status. The
                authorized values are :
                   off' :no negociation,
                   onOptionalCompression : negociation but
                        compression is optional,
                   onMandatoryCompression : negociation and
                        compression is mandatory.
                The default value is 'off'."
        ::= { fclAsynCfgConnServiceEntry 3 }


    fclAsynCfgSerCompressScrambling OBJECT-TYPE
        SYNTAX  INTEGER {
                off(1),
                on(2)
                }
        ACCESS  read-write
        STATUS  mandatory
        DESCRIPTION
                "The value of this object indicates, when the
                compression is active, whether the scrambling is
                enabled or not. The default value is 'off'."
        ::= { fclAsynCfgConnServiceEntry 4 }


    fclAsynCfgSerCompressMultiPacketsTimer OBJECT-TYPE
        SYNTAX  INTEGER (0..1500)
        ACCESS  read-write
        STATUS  mandatory
        DESCRIPTION
                "The value of this object defines the maximum
                waiting time, in milliseconds by steps of 100
                milliseconds , which, if there is not another
                packet to compress, the packet of compressed
                packets is sent beyond (this permits to reduce the
                number of packets transmitted to the remote peer).
                The authorized values are '0..1500'. '0' means no
                packets grouping (i. e. : each packet is
                individually compressed and sent). The default
                value is '0'."
        ::= { fclAsynCfgConnServiceEntry 5 }


    fclAsynCfgSerX29Reselection OBJECT-TYPE
        SYNTAX  INTEGER {
                off(1),
                on(2)
                }
        ACCESS  read-write
        STATUS  mandatory
        DESCRIPTION
                "The value of this object indicates whether the
                subscriber connected to the link has subscribed to
                X29 reselection or not. The default value is 'off'."
        ::= { fclAsynCfgConnServiceEntry 6 }


    fclAsynCfgSerCallReturnTransmission OBJECT-TYPE
        SYNTAX  INTEGER {
                off(1),
                on(3)
                }
        ACCESS  read-write
        STATUS  mandatory
        DESCRIPTION
                "The value of this object indicates whether the
                'call return' packet may be sent on this link or
                not. The 'call return' packet, sent to the
                previous equipment, makes this equipments search
                for another route to join the called DTE. The
                defaut value is 'on'."
        ::= { fclAsynCfgConnServiceEntry 7 }


    fclAsynCfgSerDBitModification OBJECT-TYPE
        SYNTAX  INTEGER {
                off(1),
                clear(2),
                on(3)
                }
        ACCESS  read-write
        STATUS  mandatory
        DESCRIPTION
                "The value of this object specifies the management
                of the D bit. The authorized values are 'off' or
                'clear' (in this case, there is clearing ....) or
                'on'. The default value is 'on'."
        ::= { fclAsynCfgConnServiceEntry 8 }


    fclAsynCfgSerReliableVc OBJECT-TYPE
        SYNTAX  INTEGER {
                off(1),
                clear(3),
                subscribe(2),
                check(4)
                }
        ACCESS  read-write
        STATUS  mandatory
        DESCRIPTION
                "The value of this object is used to enable the
                Reliable Virtual Circuit service. The authorized
                values are :
                   off : no RVC, the VCs are considered as normal
                        VCs, no particular processing,
                   clear : RVCs are not allowed for the
                        subscriber, each attempt to establish a
                        RVC provokes a clear of the connection,
                   subscribe : all calls transmitted by the
                        subscriber establish RVCs, it is also
                        possible to receive calls with RVC option,
                   check :
                     for a link to a subscriber : when a call with
                        RVC option is received, a RVC is
                        established
                     for a link to a network : the RVC option is
                        ignored when it is present in a call sent
                        by a local subscriber, the connection is
                        cleared when the RVC option is present in
                        a call sent by the network.
                The default value is 'off'."
        ::= { fclAsynCfgConnServiceEntry 9 }


    fclAsynCfgSerCos OBJECT-TYPE
        SYNTAX  INTEGER {
                ubr(3),
                vbr(1)
                }
        ACCESS  read-write
        STATUS  mandatory
        DESCRIPTION
                "COS"
        ::= { fclAsynCfgConnServiceEntry 20 }


    fclAsynCfgSerCir OBJECT-TYPE
        SYNTAX  INTEGER (600..2048000)
        ACCESS  read-write
        STATUS  mandatory
        DESCRIPTION
                "Entrant CIR"
        ::= { fclAsynCfgConnServiceEntry 21 }


    fclAsynCfgSerMinCir OBJECT-TYPE
        SYNTAX  INTEGER (0..2048000)
        ACCESS  read-write
        STATUS  mandatory
        DESCRIPTION
                "Entrant CIR mini"
        ::= { fclAsynCfgConnServiceEntry 22 }


    fclAsynCfgSerConversionAimedPoint OBJECT-TYPE
        SYNTAX  INTEGER {
                off(1),
                on(2)
                }
        ACCESS  read-write
        STATUS  mandatory
        DESCRIPTION
                "Conversion adresse : point vise"
        ::= { fclAsynCfgConnServiceEntry 30 }


    fclAsynCfgSerConversionIncomingCall OBJECT-TYPE
        SYNTAX  INTEGER {
                off(1),
                callingAddress(2),
                calledAddress(3),
                callingAddressAndCalledAddress(4)
                }
        ACCESS  read-write
        STATUS  mandatory
        DESCRIPTION
                "Conversion d'adresse sur appel entrant"
        ::= { fclAsynCfgConnServiceEntry 31 }


    fclAsynCfgSerConversionOutgoingCall OBJECT-TYPE
        SYNTAX  INTEGER {
                off(1),
                callingAddress(2),
                calledAddress(3),
                callingAddressAndCalledAddress(4)
                }
        ACCESS  read-write
        STATUS  mandatory
        DESCRIPTION
                "Conversion adresse sur appel sortant"
        ::= { fclAsynCfgConnServiceEntry 32 }


    fclAsynCfgSerConversionAddressCheck OBJECT-TYPE
        SYNTAX  INTEGER {
                off(1),
                onIncomingCall(2),
                onOutgoingCall(3),
                onIncomingCallAndOutgoingCall(4)
                }
        ACCESS  read-write
        STATUS  mandatory
        DESCRIPTION
                "Conversion adresse : controle de la presence dans
                les tables de conversion"
        ::= { fclAsynCfgConnServiceEntry 33 }


    fclAsynAutoCalls OBJECT IDENTIFIER ::= { fclAsynchronousAccessLogPort 20 }


    fclAsynAutoCallTable OBJECT-TYPE
        SYNTAX  SEQUENCE OF FclAsynAutoCallEntry
        ACCESS  not-accessible
        STATUS  mandatory
        DESCRIPTION
                "This table contains the asynchronous logical ports
                for which a call is automatically sent when the
                operational state of this LP becomes 'up'. For
                each LP this table defines the addres of the
                called remote peer and the different parameters of
                the call processing."
        ::= { fclAsynAutoCalls 1 }


    fclAsynAutoCallEntry OBJECT-TYPE
        SYNTAX  FclAsynAutoCallEntry
        ACCESS  not-accessible
        STATUS  mandatory
        DESCRIPTION
                "An entry of fclAsynAutoCallTable."
        INDEX   { fclAsynAutoLogPortId }
        ::= { fclAsynAutoCallTable 1 }


        FclAsynAutoCallEntry ::=
                SEQUENCE {
                    fclAsynAutoLogPortId
                        INTEGER,
                    fclAsynAutoStatus
                        INTEGER,
                    fclAsynAutoCalledAddr
                        OCTET STRING,
                    fclAsynAutoFacility
                        INTEGER,
                    fclAsynAutoFacThroughputClass
                        INTEGER,
                    fclAsynAutoCallUserDataAscii
                        DisplayString,
                    fclAsynAutoCallUserDataHexa
                        OCTET STRING,
                    fclAsynAutoMinimumRecallTimer
                        INTEGER,
                    fclAsynAutoDiscardCharDuringTimer
                        INTEGER
                }


    fclAsynAutoLogPortId OBJECT-TYPE
        SYNTAX  INTEGER (0..181)
        ACCESS  read-only
        STATUS  mandatory
        DESCRIPTION
                "The value of this object identifies one and only
                one asynchronous logical port. The possible values
                are : '0..131'. If it is unused, the value of this
                parameter is '255'."
        ::= { fclAsynAutoCallEntry 1 }


    fclAsynAutoStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclAsynAutoCallEntry 2 }


    fclAsynAutoCalledAddr OBJECT-TYPE
        SYNTAX  OCTET STRING (SIZE(8))
        ACCESS  read-write
        STATUS  mandatory
        DESCRIPTION
                "The value of this object is the X121 address of
                the called remote peer. This value is the called
                address specified in the call packet sent from
                this logical port. The value may contain up to 15
                digits (digits 0..9). The value must be completed
                with 'F' digits for a total of 16 digits. The
                equipment configurator does not need final
                completion. The default value is 'FF FF FF FF FF
                FF FF FF' meaning 'empty value' (blank value on
                the equipment configurator)."
        ::= { fclAsynAutoCallEntry 5 }


    fclAsynAutoFacility OBJECT-TYPE
        SYNTAX  INTEGER {
                none(1),
                reverseCharging(2),
                cug(3),
                reverseCharging-cug(4),
                throughputClass(5)
                }
        ACCESS  read-write
        STATUS  mandatory
        DESCRIPTION
                "The value of this object indicates the facilities
                set in the call packet. The authorized values are
                'none' (no facility), 'reverseCharging' (code
                '0101'), 'cug' (code '0300'),
                'reverseCharging-cug' (code '01010300'),
                'throughputClass' (code '02xx' where 'x' is the
                throughput class code defined by
                fclAsynAutoFacThroughputClass). The default value
                is 'none'."
        ::= { fclAsynAutoCallEntry 6 }


    fclAsynAutoFacThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the throughput
                class facility set in the call packet when the
                object fclAsynAutoFacility is set to
                'throughputClass'. The authorized values, in bits
                per second, are 75 (code '3'), 150 (code '4'), 300
                (code '5'), 600 (code '6'), 1200 (code '7'), 2400
                (code '8'), 4800 (code '9'), 9600 (code 'A'),
                19200 (code 'B'), 48000 (code 'C'), 64000 (code
                'D'), 128000 (code 'E'), 192000 (code 'F'). The
                default value is 'none'."
        ::= { fclAsynAutoCallEntry 7 }


    fclAsynAutoCallUserDataAscii OBJECT-TYPE
        SYNTAX  DisplayString (SIZE(0..12))
        ACCESS  read-write
        STATUS  mandatory
        DESCRIPTION
                "The value of this object is the call user data
                specified in DisplayString format. When both
                objects fclAsynAutoCallUserDataAscii and
                fclAsynAutoCallUserDataAscii are not empty the
                first one is ignored. The value may contain up to
                12 characters. The default value is an empty
                string."
        ::= { fclAsynAutoCallEntry 10 }


    fclAsynAutoCallUserDataHexa OBJECT-TYPE
        SYNTAX  OCTET STRING (SIZE(13))
        ACCESS  read-write
        STATUS  mandatory
        DESCRIPTION
                "The value of this object is the call user data
                specified in OCTET STRING format. When both
                objects fclAsynAutoCallUserDataAscii and
                fclAsynAutoCallUserDataAscii are not empty the
                first one is ignored. 13 bytes from 00 to FF must
                be specified. The first byte contains the number
                of following useful bytes. The trailing bytes must
                be set to 'FF'. The equipment configurator does
                not need this final completion. The default value
                is 'empty' (first byte set to '00')."
        ::= { fclAsynAutoCallEntry 11 }


    fclAsynAutoMinimumRecallTimer OBJECT-TYPE
        SYNTAX  INTEGER (0..990)
        ACCESS  read-write
        STATUS  mandatory
        DESCRIPTION
                "The value of this object specifies the minimum
                recall time (in seconds) between two successive
                calls. The authorized values are '0..990' by step
                of 10. The default value is '0'."
        ::= { fclAsynAutoCallEntry 15 }


    fclAsynAutoDiscardCharDuringTimer OBJECT-TYPE
        SYNTAX  INTEGER {
                off(1),
                on(2)
                }
        ACCESS  read-write
        STATUS  mandatory
        DESCRIPTION
                "The value of this object specifies the reaction of
                the equipment receiving a character from the
                asynchronous device during the recall time :
                either stops the timer and lets the operator with
                his asynchronous device to type any X28 command
                ('No' value), or discards the character and lets
                go on the recall timer('Yes' value). The
                authorized values are 'Yes' or 'No'. The default
                value is 'No'."
        ::= { fclAsynAutoCallEntry 16 }


    fclAsynAutoVdxKeyTranslationTable OBJECT-TYPE
        SYNTAX  SEQUENCE OF FclAsynAutoVdxKeyTranslationEntry
        ACCESS  not-accessible
        STATUS  mandatory
        DESCRIPTION
                "This table contains the logical ports for which a
                call is automatically sent when the operational
                state of this LP becomes 'up'. This table
                describes how the videotext keyboard function keys
                are translated."
        ::= { fclAsynAutoCalls 2 }


    fclAsynAutoVdxKeyTranslationEntry OBJECT-TYPE
        SYNTAX  FclAsynAutoVdxKeyTranslationEntry
        ACCESS  not-accessible
        STATUS  mandatory
        DESCRIPTION
                "An entry of fclAsynAutoVdxKeyTranslationTable."
        INDEX   { fclAsynAutoTransLpId }
        ::= { fclAsynAutoVdxKeyTranslationTable 1 }


        FclAsynAutoVdxKeyTranslationEntry ::=
                SEQUENCE {
                    fclAsynAutoTransLpId
                        INTEGER,
                    fclAsynAutoTransTranscoding
                        INTEGER,
                    fclAsynAutoTransProfile
                        INTEGER,
                    fclAsynAutoTransAutoTermMode
                        INTEGER,
                    fclAsynAutoTransCFKeyHandling
                        INTEGER,
                    fclAsynAutoTransClearHangUp
                        INTEGER
                }


    fclAsynAutoTransLpId OBJECT-TYPE
        SYNTAX  INTEGER (0..181)
        ACCESS  read-only
        STATUS  mandatory
        DESCRIPTION
                "The value of this object identifies one and only
                one asynchronous logical port. The possible values
                are : '0..131'. If it is unused, the value of this
                parameter is '255'."
        ::= { fclAsynAutoVdxKeyTranslationEntry 1 }


    fclAsynAutoTransTranscoding OBJECT-TYPE
        SYNTAX  INTEGER {
                off(1),
                on(2)
                }
        ACCESS  read-write
        STATUS  mandatory
        DESCRIPTION
                "The value of this object indicates whether the
                videotext keyboard function keys are transcoded or
                not. The default value is 'off'."
        ::= { fclAsynAutoVdxKeyTranslationEntry 2 }


    fclAsynAutoTransProfile OBJECT-TYPE
        SYNTAX  INTEGER {
                p1(1),
                p2(2)
                }
        ACCESS  read-write
        STATUS  mandatory
        DESCRIPTION
                "The value of this object is the X3 profile number
                used during the transfert. The authorized values
                are 'p1' (profile number 1), 'p2' (profile number
                2). The default value is 'p1'."
        ::= { fclAsynAutoVdxKeyTranslationEntry 3 }


    fclAsynAutoTransAutoTermMode OBJECT-TYPE
        SYNTAX  INTEGER {
                off(1),
                on(2)
                }
        ACCESS  read-write
        STATUS  mandatory
        DESCRIPTION
                "The value of this object indicates whether the
                automatic changeover to data communication
                standard during data transfert is enabled or not.
                The default value is 'off'."
        ::= { fclAsynAutoVdxKeyTranslationEntry 4 }


    fclAsynAutoTransCFKeyHandling OBJECT-TYPE
        SYNTAX  INTEGER {
                local(1),
                remote(2)
                }
        ACCESS  read-write
        STATUS  mandatory
        DESCRIPTION
                "The value of this object indicates the handling of
                the videotext keyboard 'connexion/fin' key. The
                authorized values are 'local' (.....), 'remote'
                (....). The default value is 'local'."
        ::= { fclAsynAutoVdxKeyTranslationEntry 5 }


    fclAsynAutoTransClearHangUp OBJECT-TYPE
        SYNTAX  INTEGER {
                off(1),
                on(2)
                }
        ACCESS  read-write
        STATUS  mandatory
        DESCRIPTION
                "The value of this object indicates whether the
                local communication is hang up (case PSTN link)
                when a clear packet is received or not. The
                default value is 'off'."
        ::= { fclAsynAutoVdxKeyTranslationEntry 6 }


    fclAsynMnemonic OBJECT IDENTIFIER ::= { fclAsynchronousAccessLogPort 21 }


    fclAsynMnemonicTable OBJECT-TYPE
        SYNTAX  SEQUENCE OF FclAsynMnemonicEntry
        ACCESS  not-accessible
        STATUS  mandatory
        DESCRIPTION
                "This table contains mnemonics that permit to
                associate names to remote peer. For each name this
                table defines the addres of the called remote peer
                and the different parameters of the call
                processing."
        ::= { fclAsynMnemonic 1 }


    fclAsynMnemonicEntry OBJECT-TYPE
        SYNTAX  FclAsynMnemonicEntry
        ACCESS  not-accessible
        STATUS  mandatory
        DESCRIPTION
                "An entry of fclAsynMnemonicTable."
        INDEX   { fclAsynMneMnemonicId }
        ::= { fclAsynMnemonicTable 1 }


        FclAsynMnemonicEntry ::=
                SEQUENCE {
                    fclAsynMneMnemonicId
                        INTEGER,
                    fclAsynMneStatus
                        INTEGER,
                    fclAsynMneName
                        DisplayString,
                    fclAsynMneCalledAddr
                        OCTET STRING,
                    fclAsynMneFacility
                        INTEGER,
                    fclAsynMneFacThroughputClass
                        INTEGER,
                    fclAsynMneCallUserDataAscii
                        DisplayString,
                    fclAsynMneCallUserDataHexa
                        OCTET STRING
                }


    fclAsynMneMnemonicId OBJECT-TYPE
        SYNTAX  INTEGER (0..99)
        ACCESS  read-only
        STATUS  mandatory
        DESCRIPTION
                "The value of this object identifies one and only
                one mnemonic (this value is used as index of this
                table instead of the mnemonic name to make the
                SNMP managers handle correctly this table). The
                possible values are : '0..99'. If it is unused,
                the value of this parameter is '255'."
        ::= { fclAsynMnemonicEntry 1 }


    fclAsynMneStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclAsynMnemonicEntry 2 }


    fclAsynMneName OBJECT-TYPE
        SYNTAX  DisplayString (SIZE(0..6))
        ACCESS  read-write
        STATUS  mandatory
        DESCRIPTION
                "The value of this object is the mnemonic name. The
                value may contain up to 6 characters. The default
                value is an empty string."
        ::= { fclAsynMnemonicEntry 3 }


    fclAsynMneCalledAddr OBJECT-TYPE
        SYNTAX  OCTET STRING (SIZE(8))
        ACCESS  read-write
        STATUS  mandatory
        DESCRIPTION
                "The value of this object is the X121 address of
                the called remote peer. This value is the called
                address specified in the call packet sent from
                this logical port. The value may contain up to 15
                digits (digits 0..9). The value must be completed
                with 'F' digits for a total of 16 digits. The
                equipment configurator does not need final
                completion. The default value is 'FF FF FF FF FF
                FF FF FF' meaning 'empty value' (blank value on
                the equipment configurator)."
        ::= { fclAsynMnemonicEntry 5 }


    fclAsynMneFacility OBJECT-TYPE
        SYNTAX  INTEGER {
                none(1),
                reverseCharging(2),
                cug(3),
                reverseCharging-cug(4),
                throughputClass(5)
                }
        ACCESS  read-write
        STATUS  mandatory
        DESCRIPTION
                "The value of this object indicates the facilities
                set in the call packet. The authorized values are
                'none' (no facility), 'reverseCharging' (code
                '0101'), 'cug' (code '0300'),
                'reverseCharging-cug' (code '01010300'),
                'throughputClass' (code '02xx' where 'x' is the
                throughput class code defined by
                fclAsynMneFacThroughputClass). The default value
                is 'none'."
        ::= { fclAsynMnemonicEntry 6 }


    fclAsynMneFacThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the throughput
                class facility set in the call packet when the
                object fclAsynMneFacility is set to
                'throughputClass'. The authorized values, in bits
                per second, are 75 (code '3'), 150 (code '4'), 300
                (code '5'), 600 (code '6'), 1200 (code '7'), 2400
                (code '8'), 4800 (code '9'), 9600 (code 'A'),
                19200 (code 'B'), 48000 (code 'C'), 64000 (code
                'D'), 128000 (code 'E'), 192000 (code 'F'). The
                default value is 'none'."
        ::= { fclAsynMnemonicEntry 7 }


    fclAsynMneCallUserDataAscii OBJECT-TYPE
        SYNTAX  DisplayString (SIZE(0..12))
        ACCESS  read-write
        STATUS  mandatory
        DESCRIPTION
                "The value of this object is the call user data
                specified in DisplayString format. When both
                objects fclAsynMneCallUserDataAscii and
                fclAsynMneCallUserDataAscii are not empty the
                first one is ignored. The value may contain up to
                12 characters. The default value is an empty
                string."
        ::= { fclAsynMnemonicEntry 10 }


    fclAsynMneCallUserDataHexa OBJECT-TYPE
        SYNTAX  OCTET STRING (SIZE(13))
        ACCESS  read-write
        STATUS  mandatory
        DESCRIPTION
                "The value of this object is the call user data
                specified in OCTET STRING format. When both
                objects fclAsynMneCallUserDataAscii and
                fclAsynMneCallUserDataAscii are not empty the
                first one is ignored. 13 bytes from 00 to FF must
                be specified. The first byte contains the number
                of following useful bytes. The trailing bytes must
                be set to 'FF'. The equipment configurator does
                not need this final completion. The default value
                is 'empty' (first byte set to '00')."
        ::= { fclAsynMnemonicEntry 11 }


    fclAsynMneVdxKeyTranslationTable OBJECT-TYPE
        SYNTAX  SEQUENCE OF FclAsynMneVdxKeyTranslationEntry
        ACCESS  not-accessible
        STATUS  mandatory
        DESCRIPTION
                "This table contains mnemonics that permit to
                associate names to remote peer. This table
                describes how the videotext keyboard function keys
                are translated."
        ::= { fclAsynMnemonic 2 }


    fclAsynMneVdxKeyTranslationEntry OBJECT-TYPE
        SYNTAX  FclAsynMneVdxKeyTranslationEntry
        ACCESS  not-accessible
        STATUS  mandatory
        DESCRIPTION
                "An entry of fclAsynMneVdxKeyTranslationTable."
        INDEX   { fclAsynMneTransMnemonicId }
        ::= { fclAsynMneVdxKeyTranslationTable 1 }


        FclAsynMneVdxKeyTranslationEntry ::=
                SEQUENCE {
                    fclAsynMneTransMnemonicId
                        INTEGER,
                    fclAsynMneTransName
                        DisplayString,
                    fclAsynMneTransTranscoding
                        INTEGER,
                    fclAsynMneTransProfile
                        INTEGER,
                    fclAsynMneTransAutoTermMode
                        INTEGER,
                    fclAsynMneTransCFKeyHandling
                        INTEGER,
                    fclAsynMneTransClearHangUp
                        INTEGER
                }


    fclAsynMneTransMnemonicId OBJECT-TYPE
        SYNTAX  INTEGER (0..99)
        ACCESS  read-only
        STATUS  mandatory
        DESCRIPTION
                "The value of this object identifies one and only
                one mnemonic (this value is used as index of this
                table instead of the mnemonic name to make the
                SNMP managers handle correctly this table). The
                possible values are : '0..99. If it is unused, the
                value of this parameter is '255'."
        ::= { fclAsynMneVdxKeyTranslationEntry 1 }


    fclAsynMneTransName OBJECT-TYPE
        SYNTAX  DisplayString (SIZE(0..6))
        ACCESS  read-only
        STATUS  mandatory
        DESCRIPTION
                "The value of this object is the mnemonic name."
        ::= { fclAsynMneVdxKeyTranslationEntry 2 }


    fclAsynMneTransTranscoding OBJECT-TYPE
        SYNTAX  INTEGER {
                no(1),
                yes(2)
                }
        ACCESS  read-write
        STATUS  mandatory
        DESCRIPTION
                "The value of this object indicates whether the
                videotext keyboard function keys are transcoded or
                not. The default value is 'off'."
        ::= { fclAsynMneVdxKeyTranslationEntry 3 }


    fclAsynMneTransProfile OBJECT-TYPE
        SYNTAX  INTEGER {
                p1(1),
                p2(2)
                }
        ACCESS  read-write
        STATUS  mandatory
        DESCRIPTION
                "The value of this object is the X3 profile number
                used during the transfert. The authorized values
                are 'p1' (profile number 1), 'p2' (profile number
                2). The default value is 'p1'."
        ::= { fclAsynMneVdxKeyTranslationEntry 4 }


    fclAsynMneTransAutoTermMode OBJECT-TYPE
        SYNTAX  INTEGER {
                off(1),
                on(2)
                }
        ACCESS  read-write
        STATUS  mandatory
        DESCRIPTION
                "The value of this object indicates whether the
                automatic changeover to data communication
                standard during data transfert is enabled or not.
                The default value is 'off'."
        ::= { fclAsynMneVdxKeyTranslationEntry 5 }


    fclAsynMneTransCFKeyHandling OBJECT-TYPE
        SYNTAX  INTEGER {
                local(1),
                remote(2)
                }
        ACCESS  read-write
        STATUS  mandatory
        DESCRIPTION
                "The value of this object indicates the handling of
                the videotext keyboard 'connexion/fin' key. The
                authorized values are 'local' (.....), 'remote'
                (....). The default value is 'local'."
        ::= { fclAsynMneVdxKeyTranslationEntry 6 }


    fclAsynMneTransClearHangUp OBJECT-TYPE
        SYNTAX  INTEGER {
                off(1),
                on(2)
                }
        ACCESS  read-write
        STATUS  mandatory
        DESCRIPTION
                "The value of this object indicates whether the
                local communication is hang up (case PSTN link)
                when a clear packet is received or not. The
                default value is 'off'."
        ::= { fclAsynMneVdxKeyTranslationEntry 7 }


    fclAsynPstnRemotePeerTable OBJECT-TYPE
        SYNTAX  SEQUENCE OF FclAsynPstnRemotePeerEntry
        ACCESS  not-accessible
        STATUS  mandatory
        DESCRIPTION
                "This table contains the remote peers to call by
                Public Switched Telephone Network way."
        ::= { fclAsynchronousAccessLogPort 25 }


    fclAsynPstnRemotePeerEntry OBJECT-TYPE
        SYNTAX  FclAsynPstnRemotePeerEntry
        ACCESS  not-accessible
        STATUS  mandatory
        DESCRIPTION
                "An entry of fclAsynPstnRemotePeerTable."
        INDEX   { fclAsynPstnRemX121Addr }
        ::= { fclAsynPstnRemotePeerTable 1 }


        FclAsynPstnRemotePeerEntry ::=
                SEQUENCE {
                    fclAsynPstnRemX121Addr
                        OCTET STRING,
                    fclAsynPstnRemStatus
                        INTEGER,
                    fclAsynPstnRemPstnNumber
                        OCTET STRING
                }


    fclAsynPstnRemX121Addr OBJECT-TYPE
        SYNTAX  OCTET STRING (SIZE(8))
        ACCESS  read-only
        STATUS  mandatory
        DESCRIPTION
                "The value of this object is the X121 address of
                the called remote peer. The value may contain up
                to 15 digits (digits 0..9, B, D).

                The digits 'B', 'D' (respectively characters '*',
                '?' on the equipment configurator) have special
                meanings :

                   'B' matches any address. When used it must be
                        the only digit specified (with final
                        completion as explained below).

                   'D' matches any single digit.

                The value must be completed with 'F' digits for a
                total of 16 digits. The equipment configurator
                does not need final completion. The default value
                is 'FF FF FF FF FF FF FF FF' meaning 'empty value'
                (blank value on the equipment configurator)."
        ::= { fclAsynPstnRemotePeerEntry 1 }


    fclAsynPstnRemStatus OBJECT-TYPE
        SYNTAX  INTEGER {
                valid(1),
                invalid(2)
                }
        ACCESS  read-write
        STATUS  mandatory
        DESCRIPTION
                "Status"
        ::= { fclAsynPstnRemotePeerEntry 2 }


    fclAsynPstnRemPstnNumber OBJECT-TYPE
        SYNTAX  OCTET STRING (SIZE(14))
        ACCESS  read-write
        STATUS  mandatory
        DESCRIPTION
                "The value of this object is the PSTN address of
                the called remote peer. The value may contain up
                to 28 digits (digits 0..E).

                The digits 'A', 'B', 'C', 'D', 'E' (respectively
                characters 'W', ',', 'P', 'T', '!' on the
                equipment configurator) have special meanings :
                   'A' means 'attente de tonalite',
                   'B' means 'pause of 2 seconds',
                   'C' means 'numerotation decimale',
                   'D' means 'numerotation multifrequence',
                   'E' means 'raccrocher 0.5 second'.

                The value must be completed with 'F' digits for a
                total of 28 digits. The equipment configurator
                does not need final completion. The default value
                is 'FF FF FF FF FF FF FF FF' meaning 'empty value'
                (blank value on the equipment configurator)."
        ::= { fclAsynPstnRemotePeerEntry 3 }


    fclAsynNetUserTable OBJECT-TYPE
        SYNTAX  SEQUENCE OF FclAsynNetUserEntry
        ACCESS  not-accessible
        STATUS  mandatory
        DESCRIPTION
                "This table contains user identifications."
        ::= { fclAsynchronousAccessLogPort 26 }


    fclAsynNetUserEntry OBJECT-TYPE
        SYNTAX  FclAsynNetUserEntry
        ACCESS  not-accessible
        STATUS  mandatory
        DESCRIPTION
                "An entry of fclAsynNetUserTable."
        INDEX   { fclAsynNetUserId }
        ::= { fclAsynNetUserTable 1 }


        FclAsynNetUserEntry ::=
                SEQUENCE {
                    fclAsynNetUserId
                        INTEGER,
                    fclAsynNetStatus
                        INTEGER,
                    fclAsynNetNui
                        DisplayString,
                    fclAsynNetNua
                        INTEGER
                }


    fclAsynNetUserId OBJECT-TYPE
        SYNTAX  INTEGER (0..254)
        ACCESS  read-only
        STATUS  mandatory
        DESCRIPTION
                "The value of this object identifies one and only
                one user (this value is used as index of this
                table instead of the NUI to make the SNMP managers
                handle correctly this table). The possible values
                are : '0..254'. If it is unused, the value of this
                parameter is '255'."
        ::= { fclAsynNetUserEntry 1 }


    fclAsynNetStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclAsynNetUserEntry 2 }


    fclAsynNetNui OBJECT-TYPE
        SYNTAX  DisplayString (SIZE(0..6))
        ACCESS  read-write
        STATUS  mandatory
        DESCRIPTION
                "The value of this object is the NUI (Network User
                Identifier). The authorized values are all the
                alphabetical characters strings on 6 characters.
                The default value is the empty string."
        ::= { fclAsynNetUserEntry 3 }


    fclAsynNetNua OBJECT-TYPE
        SYNTAX  INTEGER (0..9999)
        ACCESS  read-write
        STATUS  mandatory
        DESCRIPTION
                "The value of this object is the NUA (Network User
                Access). The authorized values are '0..9999'. If
                it is unused, the value is '65535'. The default
                value is '65535'."
        ::= { fclAsynNetUserEntry 4 }


    fclFrameRelayAccessLogPort OBJECT IDENTIFIER ::= { fcLogicalPorts 13 }


    fclFraLogPortTable OBJECT-TYPE
        SYNTAX  SEQUENCE OF FclFraLogPortEntry
        ACCESS  not-accessible
        STATUS  mandatory
        DESCRIPTION
                "This table defines the general parameters of Frame
                Relay Access logical ports. These FRA logical
                ports are used when X25 Virtual Channel must be
                established between local FR PVC (Frame Relay
                Permanent Virtual Circuit) end points and remote
                FR PVC end points through a X25 network. They are
                not adapted to cross a Frame Relay network (see FR
                CE logical ports in this case)."
        ::= { fclFrameRelayAccessLogPort 1 }


    fclFraLogPortEntry OBJECT-TYPE
        SYNTAX  FclFraLogPortEntry
        ACCESS  not-accessible
        STATUS  mandatory
        DESCRIPTION
                "An entry of fclFraLogPortTable."
        INDEX   { fclFraLpLogPortId }
        ::= { fclFraLogPortTable 1 }


        FclFraLogPortEntry ::=
                SEQUENCE {
                    fclFraLpLogPortId
                        INTEGER,
                    fclFraLpInterfaceId
                        INTEGER,
                    fclFraLpLmi
                        INTEGER,
                    fclFraLpGroupingThreshold
                        INTEGER,
                    fclFraLpFecnBecnThreshold
                        INTEGER,
                    fclFraLpDeDiscardThreshold
                        INTEGER,
                    fclFraLpAllDiscardThreshold
                        INTEGER,
                    fclFraLpX25InterframeFlagCount
                        INTEGER,
                    fclFraLpInactivityCheckDelay
                        INTEGER,
                    fclFraLpCompression
                        INTEGER,
                    fclFraLpCompressNegotiation
                        INTEGER,
                    fclFraLpCompressScrambling
                        INTEGER,
                    fclFraLpCompressMultiPacketsTimer
                        INTEGER,
                    fclFraLpReliableVc
                        INTEGER
                }


    fclFraLpLogPortId OBJECT-TYPE
        SYNTAX  INTEGER (0..181)
        ACCESS  read-only
        STATUS  mandatory
        DESCRIPTION
                "The value of this object identifies one and only
                one Frame Relay Access logical port. The possible
                values are : '0..131'. If it is unused, the value
                of this parameter is '255'. The default value is
                '255'."
        ::= { fclFraLogPortEntry 1 }


    fclFraLpInterfaceId OBJECT-TYPE
        SYNTAX  INTEGER (0..35)
        ACCESS  read-write
        STATUS  mandatory
        DESCRIPTION
                "The value of this object identifies the line
                interface used by this FRA logical port. The
                possible values are : '0..35'. If it is unused,
                the value of this parameter is '255'. The default
                value is '255'."
        ::= { fclFraLogPortEntry 2 }


    fclFraLpLmi OBJECT-TYPE
        SYNTAX  INTEGER {
                off(1),
                lmiUni(2),
                lmiNui(3)
                }
        ACCESS  read-write
        STATUS  mandatory
        DESCRIPTION
                "The value of this object defines which kind of
                signalling is used on this FRA logical port. The
                possible values are 'off' (no signalling), lmiUni
                (Link Management Interface - User to Network
                Interface : the equipment performs user-side
                procedures), lmiNui (Link Management Interface -
                Network to User Interface : the equipment performs
                network-side procedures). The default value is
                '255'."
        ::= { fclFraLogPortEntry 3 }


    fclFraLpGroupingThreshold OBJECT-TYPE
        SYNTAX  INTEGER (1..97)
        ACCESS  read-write
        STATUS  mandatory
        DESCRIPTION
                "The value of this object is the input resource
                threshold over which several input frames coming
                from a FR PVC end point are grouped in a single
                X25 packet to cross the X25 network. The enabling
                of this grouping is PVC end point specific (see
                fclFraPvcEncapsulation). The possible values are :
                '1..97'. The thresholds must be set as following :
                fclFraLpGroupingThreshold <
                fclFraLpFecnBecnThreshold <
                fclFraLpDeDiscardThreshold <
                fclFraLpAllDiscardThreshold. The default value is
                '1'."
        ::= { fclFraLogPortEntry 5 }


    fclFraLpFecnBecnThreshold OBJECT-TYPE
        SYNTAX  INTEGER (2..98)
        ACCESS  read-write
        STATUS  mandatory
        DESCRIPTION
                "The value of this object is the input resource
                threshold over which bits FECN (Forward Explicit
                Congestion Notification) of input frames and BECN
                (Backward Explicit Congestion Notification) of
                output frames are set to 1. The possible values
                are : '2..98'. The thresholds must be set as
                following : fclFraLpGroupingThreshold <
                fclFraLpFecnBecnThreshold <
                fclFraLpDeDiscardThreshold <
                fclFraLpAllDiscardThreshold. The default value is
                '10'."
        ::= { fclFraLogPortEntry 6 }


    fclFraLpDeDiscardThreshold OBJECT-TYPE
        SYNTAX  INTEGER (3..99)
        ACCESS  read-write
        STATUS  mandatory
        DESCRIPTION
                "The value of this object is the input resource
                threshold over which input frames with bit DE
                (Discard Eligible) set to 1 are discarded (i.e. :
                not sent accross the X25 network). The possible
                values are : '3..99'. The thresholds must be set
                as following : fclFraLpGroupingThreshold <
                fclFraLpFecnBecnThreshold <
                fclFraLpDeDiscardThreshold <
                fclFraLpAllDiscardThreshold. The default value is
                '15'."
        ::= { fclFraLogPortEntry 7 }


    fclFraLpAllDiscardThreshold OBJECT-TYPE
        SYNTAX  INTEGER (4..100)
        ACCESS  read-write
        STATUS  mandatory
        DESCRIPTION
                "The value of this object is the input resource
                threshold over which all input frames are
                discarded (i.e. : not sent accross the X25
                network). The possible values are : '4..100'. The
                thresholds must be set as following :
                fclFraLpGroupingThreshold <
                fclFraLpFecnBecnThreshold <
                fclFraLpDeDiscardThreshold <
                fclFraLpAllDiscardThreshold. The default value is
                '20'."
        ::= { fclFraLogPortEntry 8 }


    fclFraLpX25InterframeFlagCount OBJECT-TYPE
        SYNTAX  INTEGER (1..15)
        ACCESS  read-write
        STATUS  mandatory
        DESCRIPTION
                "The value of this object is the number of
                interframe flags (it concerns the framing aspects
                of link access procedures of X25 and not the fact
                to put several frames coming from a FR PVC end
                point in a single X25 packet). The possible values
                are : '1..15'. The default value is '1'."
        ::= { fclFraLogPortEntry 9 }


    fclFraLpInactivityCheckDelay OBJECT-TYPE
        SYNTAX  INTEGER (0..254)
        ACCESS  read-write
        STATUS  mandatory
        DESCRIPTION
                "The value of this object is the inactivity check
                delay in minutes.............. The possible values
                are : '0..254'. The value '0' disables this
                clearing mechanism. The default value is '0'."
        ::= { fclFraLogPortEntry 10 }


    fclFraLpCompression OBJECT-TYPE
        SYNTAX  INTEGER {
                off(1),
                networkToSubscriber(2),
                subscriberToNetwork(3),
                bothway(4)
                }
        ACCESS  read-write
        STATUS  mandatory
        DESCRIPTION
                "The value of this object indicates the compression
                enabling for each direction. The authorized values
                are :
                   off : no compression,
                   networkToSubscriber : compression of the flow
                        from the remote peer to the equipment,
                   subscriberToNetwork : compression of the flow
                        from the equipment to the remote peer,
                   bothway : compression of the two flows from and
                        to the equipment.
                The default value is 'off'."
        ::= { fclFraLogPortEntry 20 }


    fclFraLpCompressNegotiation OBJECT-TYPE
        SYNTAX  INTEGER {
                off(1),
                onOptionalCompression(2),
                onMandatoryCompression(3)
                }
        ACCESS  read-write
        STATUS  mandatory
        DESCRIPTION
                "The value of this object indicates whether the
                compression facility is negociated or not and, if
                negociated, the optional/obligatory status. The
                authorized values are :
                   off' :no negociation,
                   onOptionalCompression : negociation but
                        compression is optional,
                   onMandatoryCompression : negociation and
                        compression is mandatory.
                The default value is 'off'."
        ::= { fclFraLogPortEntry 21 }


    fclFraLpCompressScrambling OBJECT-TYPE
        SYNTAX  INTEGER {
                off(1),
                on(2)
                }
        ACCESS  read-write
        STATUS  mandatory
        DESCRIPTION
                "The value of this object indicates, when the
                compression is active, whether the scrambling is
                enabled or not. The default value is 'off'."
        ::= { fclFraLogPortEntry 22 }


    fclFraLpCompressMultiPacketsTimer OBJECT-TYPE
        SYNTAX  INTEGER (0..1500)
        ACCESS  read-write
        STATUS  mandatory
        DESCRIPTION
                "The value of this object defines the maximum
                waiting time, in milliseconds by steps of 100
                milliseconds , which, if there is not another
                packet to compress, the packet of compressed
                packets is sent beyond (this permits to reduce the
                number of packets transmitted to the remote peer).
                The authorized values are '0..1500'. '0' means no
                packets grouping (i. e. : each packet is
                individually compressed and sent). The default
                value is '0'."
        ::= { fclFraLogPortEntry 23 }


    fclFraLpReliableVc OBJECT-TYPE
        SYNTAX  INTEGER {
                off(1),
                clear(3),
                subscribe(2),
                check(4)
                }
        ACCESS  read-write
        STATUS  mandatory
        DESCRIPTION
                "The value of this object is used to enable the
                Reliable Virtual Circuit service. The authorized
                values are :
                   off : no RVC, the VCs are considered as normal
                        VCs, no particular processing,
                   clear : RVCs are not allowed for the
                        subscriber, each attempt to establish a
                        RVC provokes a clear of the connection,
                   subscribe : all calls transmitted by the
                        subscriber establish RVCs, it is also
                        possible to receive calls with RVC option,
                   check :
                     for a link to a subscriber : when a call with
                        RVC option is received, a RVC is
                        established
                     for a link to a network : the RVC option is
                        ignored when it is present in a call sent
                        by a local subscriber, the connection is
                        cleared when the RVC option is present in
                        a call sent by the network.
                The default value is 'off'."
        ::= { fclFraLogPortEntry 24 }


    fclFraLmiTable OBJECT-TYPE
        SYNTAX  SEQUENCE OF FclFraLmiEntry
        ACCESS  not-accessible
        STATUS  mandatory
        DESCRIPTION
                "This table defines the LMI (Link Management
                Interface) parameters of Frame Relay Access
                logical ports with LMI signalling."
        ::= { fclFrameRelayAccessLogPort 2 }


    fclFraLmiEntry OBJECT-TYPE
        SYNTAX  FclFraLmiEntry
        ACCESS  not-accessible
        STATUS  mandatory
        DESCRIPTION
                "An entry of fclFraLmiTable."
        INDEX   { fclFraLmiLogPortId }
        ::= { fclFraLmiTable 1 }


        FclFraLmiEntry ::=
                SEQUENCE {
                    fclFraLmiLogPortId
                        INTEGER,
                    fclFraLmiDlci
                        INTEGER,
                    fclFraLmiLmiStandard
                        INTEGER,
                    fclFraLmiAccessibilityCondition
                        INTEGER,
                    fclFraLmiN391FullStatusPollCount
                        INTEGER,
                    fclFraLmiN392ErrorThreshold
                        INTEGER,
                    fclFraLmiN393MonitoredEventCount
                        INTEGER,
                    fclFraLmiT391LinkIntegPollTimer
                        INTEGER,
                    fclFraLmiT392PollingVerifTimer
                        INTEGER
                }


    fclFraLmiLogPortId OBJECT-TYPE
        SYNTAX  INTEGER (0..181)
        ACCESS  read-only
        STATUS  mandatory
        DESCRIPTION
                "The value of this object identifies one and only
                one Frame Relay Access logical port with LMI (Link
                Management Interface) signalling. The possible
                values are : '0..131'. If it is unused, the value
                of this parameter is '255'. The default value is
                '255'."
        ::= { fclFraLmiEntry 1 }


    fclFraLmiDlci OBJECT-TYPE
        SYNTAX  INTEGER {
                dlci0(1),
                dlci1023(2)
                }
        ACCESS  read-write
        STATUS  mandatory
        DESCRIPTION
                "The value of this object is the DLCI Data Link
                Connection Identifier of the Frame Relay PVC
                (Permanent Virtual Circuit) used by LMI to
                exchange management datas with the facing peer.
                The possible values are '0' or '1023'. The default
                value is '0'."
        ::= { fclFraLmiEntry 2 }


    fclFraLmiLmiStandard OBJECT-TYPE
        SYNTAX  INTEGER {
                ansiT1-617d(1),
                itutQ933a(2)
                }
        ACCESS  read-write
        STATUS  mandatory
        DESCRIPTION
                "The value of this object defines which standard is
                used. The possible values are 'ansiT1-617d' (ANSI
                T1.617 Annex D) or 'itutQ933a' (ITU-T Q.933 Annex
                A). The default value is 'ansiT1-617d'."
        ::= { fclFraLmiEntry 3 }


    fclFraLmiAccessibilityCondition OBJECT-TYPE
        SYNTAX  INTEGER {
                fast(1),
                n393(2)
                }
        ACCESS  read-write
        STATUS  mandatory
        DESCRIPTION
                "The value of this object defines calculation mode
                of the 'up' operational status of the logical
                port. The operational state may be deducted using
                the N393 mechanism (value 'n393') or, more
                rapidly, withoutis using this mechanism (value
                'fast'). The default value is 'fast'."
        ::= { fclFraLmiEntry 4 }


    fclFraLmiN391FullStatusPollCount OBJECT-TYPE
        SYNTAX  INTEGER (1..254)
        ACCESS  read-write
        STATUS  mandatory
        DESCRIPTION
                "The value of this object identifies the user-side
                N391 full status polling cycle value for this
                logical port. This the number of status enquiry
                intervals that pass before issuance of full status
                enquiry message. If the logical port is not
                performing user-side procedures, then this value
                is meaningless. The authorized values are
                '1..254'. The default value is '6'."
        ::= { fclFraLmiEntry 5 }


    fclFraLmiN392ErrorThreshold OBJECT-TYPE
        SYNTAX  INTEGER (1..10)
        ACCESS  read-write
        STATUS  mandatory
        DESCRIPTION
                "The value of this object identifies the user-side
                or network-side N392 error threshold value for
                this logical port. This is the maximum number of
                unanswered Status Enquiries the equipment shall
                accept before declaring the logical port down. The
                authorized values are '1..10. The default value is
                '3'."
        ::= { fclFraLmiEntry 6 }


    fclFraLmiN393MonitoredEventCount OBJECT-TYPE
        SYNTAX  INTEGER (1..10)
        ACCESS  read-write
        STATUS  mandatory
        DESCRIPTION
                "The value of this object identifies the user-side
                or network-side N393 monitored events count value
                for this logical port. This is the number of
                status polling intervals over which the error
                threshold is counted. For example if within
                'MonitoredEvents' number of events the equipment
                receives 'ErrorThreshold' number of errors, the
                logical port is marked as down. The authorized
                values are '1..10. The default value is '4'."
        ::= { fclFraLmiEntry 7 }


    fclFraLmiT391LinkIntegPollTimer OBJECT-TYPE
        SYNTAX  INTEGER (5..30)
        ACCESS  read-write
        STATUS  mandatory
        DESCRIPTION
                "The value of this object identifies the user-side
                T391 link integrity verification polling timer
                value for this logical port. This is the number of
                seconds between successive status enquiry
                messages. If the logical port is not performing
                user-side procedures, then this value is
                meaningless. The authorized values are '5..30'.
                The default value is '10'."
        ::= { fclFraLmiEntry 8 }


    fclFraLmiT392PollingVerifTimer OBJECT-TYPE
        SYNTAX  INTEGER (5..30)
        ACCESS  read-write
        STATUS  mandatory
        DESCRIPTION
                "The value of this object identifies the
                network-side T392 polling verification timer value
                (nT2 for LMI) for this logical port. This value is
                expressed in seconds. If the logical port is not
                performing network-side procedures, then this
                value is meaningless. The authorized values are
                '5..30'. The default value is '15'"
        ::= { fclFraLmiEntry 9 }


    fclFraPvcEndPointTable OBJECT-TYPE
        SYNTAX  SEQUENCE OF FclFraPvcEndPointEntry
        ACCESS  not-accessible
        STATUS  mandatory
        DESCRIPTION
                "This table defines the Frame Relay PVC
                (Permananent Virtual Circuit) end points on Frame
                Relay Access logical ports. For each PVC end point
                this table defines the addres of the called remote
                peer and the different parameters of the call
                processing."
        ::= { fclFrameRelayAccessLogPort 3 }


    fclFraPvcEndPointEntry OBJECT-TYPE
        SYNTAX  FclFraPvcEndPointEntry
        ACCESS  not-accessible
        STATUS  mandatory
        DESCRIPTION
                "An entry of fclFraPvcEndPointTable."
        INDEX   { fclFraPvcLogPortId,
                  fclFraPvcDlci }
        ::= { fclFraPvcEndPointTable 1 }


        FclFraPvcEndPointEntry ::=
                SEQUENCE {
                    fclFraPvcLogPortId
                        INTEGER,
                    fclFraPvcDlci
                        INTEGER,
                    fclFraPvcStatus
                        INTEGER,
                    fclFraPvcCalledAddr
                        OCTET STRING,
                    fclFraPvcSubscriberNumber
                        INTEGER,
                    fclFraPvcCallDirection
                        INTEGER,
                    fclFraPvcEncapsulation
                        INTEGER,
                    fclFraPvcMinRecallTimer
                        INTEGER,
                    fclFraPvcInactivityTimer
                        INTEGER
                }


    fclFraPvcLogPortId OBJECT-TYPE
        SYNTAX  INTEGER (0..181)
        ACCESS  read-only
        STATUS  mandatory
        DESCRIPTION
                "The value of this object identifies one and only
                one Frame Relay Access logical port. This is the
                logical port this PVC (Permanent Virtual Circuit)
                end point is layered onto. The possible values are
                : '0..131'. If it is unused, the value of this
                parameter is '255'. The default value is '255'."
        ::= { fclFraPvcEndPointEntry 1 }


    fclFraPvcDlci OBJECT-TYPE
        SYNTAX  INTEGER (16..991)
        ACCESS  read-only
        STATUS  mandatory
        DESCRIPTION
                "The value of this object is equal to the DLCI
                (Data Link Connection Identifier) value for this
                PVC (Permanent Virtual Circuit) end point. The
                possible values are : '0..1023. If it is unused,
                the value of this parameter is '65535'. The
                default value is '65535'."
        ::= { fclFraPvcEndPointEntry 2 }


    fclFraPvcStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclFraPvcEndPointEntry 3 }


    fclFraPvcCalledAddr OBJECT-TYPE
        SYNTAX  OCTET STRING (SIZE(8))
        ACCESS  read-write
        STATUS  mandatory
        DESCRIPTION
                "The value of this object is the X121 address of
                the called remote peer PVC end point. This value
                is the called address specified in the call packet
                sent from this PVC end point. The value may
                contain up to 15 digits (digits 0..9). The value
                must be completed with 'F' digits for a total of
                16 digits. The equipment configurator does not
                need final completion. The default value is 'FF FF
                FF FF FF FF FF FF' meaning 'empty value' (blank
                value on the equipment configurator)."
        ::= { fclFraPvcEndPointEntry 5 }


    fclFraPvcSubscriberNumber OBJECT-TYPE
        SYNTAX  INTEGER (0..9999)
        ACCESS  read-write
        STATUS  mandatory
        DESCRIPTION
                "The value of this object is the SB number added to
                the DNICZO of the equipment to make the calling
                address in a call sent from this PVC end point.
                The value must contain 4 digits (digits 0..9). The
                default value is 'FF FF'."
        ::= { fclFraPvcEndPointEntry 6 }


    fclFraPvcCallDirection OBJECT-TYPE
        SYNTAX  INTEGER {
                calling(1),
                called(2),
                auto(3)
                }
        ACCESS  read-write
        STATUS  mandatory
        DESCRIPTION
                "The value of this object defines the mode used to
                establish the X25 VC between this PVC end point
                and the remote one on the other side of the X25
                network. The authorized values are 'calling' (the
                caller is this PVC end point), 'called' (the
                caller is the remote PVC end point), 'auto'
                (automatic choise between 'calling' and 'called').
                The default value is 'auto'."
        ::= { fclFraPvcEndPointEntry 7 }


    fclFraPvcEncapsulation OBJECT-TYPE
        SYNTAX  INTEGER {
                none(1),
                fastSelect(2),
                fastSelect-frHeader(3),
                fastSelect-frHeader-grouping(4)
                }
        ACCESS  read-write
        STATUS  mandatory
        DESCRIPTION
                "The value of this object defines how FR frames are
                transported in the X25 VC between this PVC end
                point and the remote one on the other side of the
                X25 network. The authorized values are 'none'
                (each FR frame is put in one X25 packet without
                any particular treatment), 'fastSelect' (Fast
                select is requested in the call packet),
                'fastSelect-frHeader' (Fast select is requested in
                the call packet, the FR header is also
                transported), 'fastSelect-frHeader-grouping' (Fast
                select is requested in the call packet, the FR
                header is also transported, several FR frames may
                be grouped in only one X25 packet). The default
                value is 'none'."
        ::= { fclFraPvcEndPointEntry 8 }


    fclFraPvcMinRecallTimer OBJECT-TYPE
        SYNTAX  INTEGER (0..990)
        ACCESS  read-write
        STATUS  mandatory
        DESCRIPTION
                "The value of this object specifies the minimum
                recall time (in seconds) between two successive
                calls. The authorized values are '0..990' by step
                of 10. The default value is '0'."
        ::= { fclFraPvcEndPointEntry 10 }


    fclFraPvcInactivityTimer OBJECT-TYPE
        SYNTAX  INTEGER (0..2540)
        ACCESS  read-write
        STATUS  mandatory
        DESCRIPTION
                "The value of this object is the inactivity time in
                seconds.............. The possible values are :
                '0..2540'. This clearing mechanism is enabled or
                disabled on the logical port (see
                fclFraLpInactivityCheckDelay). The default value
                is '30'."
        ::= { fclFraPvcEndPointEntry 11 }


    fclHdlcAccessLogPort OBJECT IDENTIFIER ::= { fcLogicalPorts 14 }


    fclHdlcLogPortTable OBJECT-TYPE
        SYNTAX  SEQUENCE OF FclHdlcLogPortEntry
        ACCESS  not-accessible
        STATUS  mandatory
        DESCRIPTION
                "This table defines the general parameters of HDLC
                (High-level Data Link Control) access logical
                ports."
        ::= { fclHdlcAccessLogPort 1 }


    fclHdlcLogPortEntry OBJECT-TYPE
        SYNTAX  FclHdlcLogPortEntry
        ACCESS  not-accessible
        STATUS  mandatory
        DESCRIPTION
                "An entry of fclHdlcLogPortTable."
        INDEX   { fclHdlcLpLogPortId }
        ::= { fclHdlcLogPortTable 1 }


        FclHdlcLogPortEntry ::=
                SEQUENCE {
                    fclHdlcLpLogPortId
                        INTEGER,
                    fclHdlcLpInterfaceId
                        INTEGER,
                    fclHdlcLpCrcTransport
                        INTEGER,
                    fclHdlcLpGroupingThreshold
                        INTEGER,
                    fclHdlcLpAllDiscardThreshold
                        INTEGER,
                    fclHdlcLpX25InterframeFlagCount
                        INTEGER,
                    fclHdlcLpInactivityCheckDelay
                        INTEGER,
                    fclHdlcLpCompression
                        INTEGER,
                    fclHdlcLpCompressNegotiation
                        INTEGER,
                    fclHdlcLpCompressScrambling
                        INTEGER,
                    fclHdlcLpCompressMultiPacketsTimer
                        INTEGER,
                    fclHdlcLpReliableVc
                        INTEGER,
                    fclHdlcLpCos
                        INTEGER,
                    fclHdlcLpCir
                        INTEGER,
                    fclHdlcLpMinCir
                        INTEGER
                }


    fclHdlcLpLogPortId OBJECT-TYPE
        SYNTAX  INTEGER (0..181)
        ACCESS  read-only
        STATUS  mandatory
        DESCRIPTION
                "The value of this object identifies one and only
                one HDLC (High-level Data Link Control) access
                logical port. The possible values are : '0..131'.
                If it is unused, the value of this parameter is
                '255'. The default value is '255'."
        ::= { fclHdlcLogPortEntry 1 }


    fclHdlcLpInterfaceId OBJECT-TYPE
        SYNTAX  INTEGER (0..181)
        ACCESS  read-write
        STATUS  mandatory
        DESCRIPTION
                "The value of this object identifies the line
                interface used by this HDLC logical port. The
                possible values are : '0..35'. If it is unused,
                the value of this parameter is '255'. The default
                value is '255'."
        ::= { fclHdlcLogPortEntry 2 }


    fclHdlcLpCrcTransport OBJECT-TYPE
        SYNTAX  INTEGER {
                off(2),
                on(1)
                }
        ACCESS  read-write
        STATUS  mandatory
        DESCRIPTION
                "The value of this object indicates whether the CRC
                (Cyclic Redundancy Check) is transported or not.
                The default value is 'off'."
        ::= { fclHdlcLogPortEntry 3 }


    fclHdlcLpGroupingThreshold OBJECT-TYPE
        SYNTAX  INTEGER (1..97)
        ACCESS  read-write
        STATUS  mandatory
        DESCRIPTION
                "The value of this object is the input resource
                threshold over which several input frames coming
                from this HDLC logical port are grouped in a
                single X25 packet. See fclHdlcAutoEncapsulation to
                enable this grouping. The possible values are :
                '1..97'. The thresholds must be set as following :
                fclHdlcLpGroupingThreshold <
                fclHdlcLpAllDiscardThreshold. The default value is
                '1'."
        ::= { fclHdlcLogPortEntry 5 }


    fclHdlcLpAllDiscardThreshold OBJECT-TYPE
        SYNTAX  INTEGER (4..100)
        ACCESS  read-write
        STATUS  mandatory
        DESCRIPTION
                "The value of this object is the input resource
                threshold over which all input frames are
                discarded (i.e. : not sent accross the network).
                The possible values are : '4..100'. The thresholds
                must be set as following :
                fclHdlcLpGroupingThreshold <
                fclHdlcLpAllDiscardThreshold. The default value is
                '20'."
        ::= { fclHdlcLogPortEntry 8 }


    fclHdlcLpX25InterframeFlagCount OBJECT-TYPE
        SYNTAX  INTEGER (1..15)
        ACCESS  read-write
        STATUS  mandatory
        DESCRIPTION
                "The value of this object is the number of
                interframe flags (it concerns the framing aspects
                of link access procedures of X25 and not the fact
                to put several frames coming from this HDLC
                logical port in a single X25 packet). The possible
                values are : '1..15'. The default value is '1'."
        ::= { fclHdlcLogPortEntry 9 }


    fclHdlcLpInactivityCheckDelay OBJECT-TYPE
        SYNTAX  INTEGER (0..254)
        ACCESS  read-write
        STATUS  mandatory
        DESCRIPTION
                "The value of this object is the inactivity check
                delay in minutes.............. The possible values
                are : '0..254'. The value '0' disables this
                clearing mechanism. The default value is '0'."
        ::= { fclHdlcLogPortEntry 10 }


    fclHdlcLpCompression OBJECT-TYPE
        SYNTAX  INTEGER {
                off(1),
                networkToSubscriber(2),
                subscriberToNetwork(3),
                bothway(4)
                }
        ACCESS  read-write
        STATUS  mandatory
        DESCRIPTION
                "The value of this object indicates the compression
                enabling for each direction. The authorized values
                are :
                   off : no compression,
                   networkToSubscriber : compression of the flow
                        from the remote peer to the equipment,
                   subscriberToNetwork : compression of the flow
                        from the equipment to the remote peer,
                   bothway : compression of the two flows from and
                        to the equipment.
                The default value is 'off'."
        ::= { fclHdlcLogPortEntry 20 }


    fclHdlcLpCompressNegotiation OBJECT-TYPE
        SYNTAX  INTEGER {
                off(1),
                onOptionalCompression(2),
                onMandatoryCompression(3)
                }
        ACCESS  read-write
        STATUS  mandatory
        DESCRIPTION
                "The value of this object indicates whether the
                compression facility is negociated or not and, if
                negociated, the optional/obligatory status. The
                authorized values are :
                   off' :no negociation,
                   onOptionalCompression : negociation but
                        compression is optional,
                   onMandatoryCompression : negociation and
                        compression is mandatory.
                The default value is 'off'."
        ::= { fclHdlcLogPortEntry 21 }


    fclHdlcLpCompressScrambling OBJECT-TYPE
        SYNTAX  INTEGER {
                off(1),
                on(2)
                }
        ACCESS  read-write
        STATUS  mandatory
        DESCRIPTION
                "The value of this object indicates, when the
                compression is active, whether the scrambling is
                enabled or not. The default value is 'off'."
        ::= { fclHdlcLogPortEntry 22 }


    fclHdlcLpCompressMultiPacketsTimer OBJECT-TYPE
        SYNTAX  INTEGER (0..1500)
        ACCESS  read-write
        STATUS  mandatory
        DESCRIPTION
                "The value of this object defines the maximum
                waiting time, in milliseconds by steps of 100
                milliseconds , which, if there is not another
                packet to compress, the packet of compressed
                packets is sent beyond (this permits to reduce the
                number of packets transmitted to the remote peer).
                The authorized values are '0..1500'. '0' means no
                packets grouping (i. e. : each packet is
                individually compressed and sent). The default
                value is '0'."
        ::= { fclHdlcLogPortEntry 23 }


    fclHdlcLpReliableVc OBJECT-TYPE
        SYNTAX  INTEGER {
                off(1),
                clear(3),
                subscribe(2),
                check(4)
                }
        ACCESS  read-write
        STATUS  mandatory
        DESCRIPTION
                "The value of this object is used to enable the
                Reliable Virtual Circuit service. The authorized
                values are :
                   off : no RVC, the VCs are considered as normal
                        VCs, no particular processing,
                   clear : RVCs are not allowed for the
                        subscriber, each attempt to establish a
                        RVC provokes a clear of the connection,
                   subscribe : all calls transmitted by the
                        subscriber establish RVCs, it is also
                        possible to receive calls with RVC option,
                   check :
                     for a link to a subscriber : when a call with
                        RVC option is received, a RVC is
                        established
                     for a link to a network : the RVC option is
                        ignored when it is present in a call sent
                        by a local subscriber, the connection is
                        cleared when the RVC option is present in
                        a call sent by the network.
                The default value is 'off'."
        ::= { fclHdlcLogPortEntry 24 }


    fclHdlcLpCos OBJECT-TYPE
        SYNTAX  INTEGER {
                ubr(3),
                vbr-rt(2),
                vbr(1)
                }
        ACCESS  read-write
        STATUS  mandatory
        DESCRIPTION
                "COS"
        ::= { fclHdlcLogPortEntry 30 }


    fclHdlcLpCir OBJECT-TYPE
        SYNTAX  INTEGER (600..2048000)
        ACCESS  read-write
        STATUS  mandatory
        DESCRIPTION
                "Entrant CIR"
        ::= { fclHdlcLogPortEntry 31 }


    fclHdlcLpMinCir OBJECT-TYPE
        SYNTAX  INTEGER (0..2048000)
        ACCESS  read-write
        STATUS  mandatory
        DESCRIPTION
                "Entrant CIR mini"
        ::= { fclHdlcLogPortEntry 32 }


    fclHdlcAutoCallTable OBJECT-TYPE
        SYNTAX  SEQUENCE OF FclHdlcAutoCallEntry
        ACCESS  not-accessible
        STATUS  mandatory
        DESCRIPTION
                "This table contains the HDLC logical ports for
                which a call is automatically sent when the
                operational state of this LP becomes 'up'. For
                each LP this table defines the addres of the
                called remote peer and the different parameters of
                the call processing."
        ::= { fclHdlcAccessLogPort 2 }


    fclHdlcAutoCallEntry OBJECT-TYPE
        SYNTAX  FclHdlcAutoCallEntry
        ACCESS  not-accessible
        STATUS  mandatory
        DESCRIPTION
                "An entry of fclHdlcAutoCallTable."
        INDEX   { fclHdlcAutoLogPortId }
        ::= { fclHdlcAutoCallTable 1 }


        FclHdlcAutoCallEntry ::=
                SEQUENCE {
                    fclHdlcAutoLogPortId
                        INTEGER,
                    fclHdlcAutoCalledAddr
                        OCTET STRING,
                    fclHdlcAutoSubscriberNumber
                        INTEGER,
                    fclHdlcAutoCallDirection
                        INTEGER,
                    fclHdlcAutoEncapsulation
                        INTEGER,
                    fclHdlcAutoMinRecallTimer
                        INTEGER,
                    fclHdlcAutoInactivityTimer
                        INTEGER
                }


    fclHdlcAutoLogPortId OBJECT-TYPE
        SYNTAX  INTEGER (0..181)
        ACCESS  read-only
        STATUS  mandatory
        DESCRIPTION
                "The value of this object identifies one and only
                one HDLC logical port. The possible values are :
                '0..131'. If it is unused, the value of this
                parameter is '255'."
        ::= { fclHdlcAutoCallEntry 1 }


    fclHdlcAutoCalledAddr OBJECT-TYPE
        SYNTAX  OCTET STRING (SIZE(8))
        ACCESS  read-write
        STATUS  mandatory
        DESCRIPTION
                "The value of this object is the X121 address of
                the called remote peer. This value is the called
                address specified in the call packet sent from
                this logical port. The value may contain up to 15
                digits (digits 0..9). The value must be completed
                with 'F' digits for a total of 16 digits. The
                equipment configurator does not need final
                completion. The default value is 'FF FF FF FF FF
                FF FF FF' meaning 'empty value' (blank value on
                the equipment configurator)."
        ::= { fclHdlcAutoCallEntry 5 }


    fclHdlcAutoSubscriberNumber OBJECT-TYPE
        SYNTAX  INTEGER (0..99)
        ACCESS  read-write
        STATUS  mandatory
        DESCRIPTION
                "The value of this object is the SB number added to
                the DNICZO of the equipment to make the calling
                address in a call sent from this HDLC logical
                port. The value must contain 2 digits (digits
                0..9). The default value is 'FF FF'."
        ::= { fclHdlcAutoCallEntry 6 }


    fclHdlcAutoCallDirection OBJECT-TYPE
        SYNTAX  INTEGER {
                calling(1),
                called(2),
                auto(3)
                }
        ACCESS  read-write
        STATUS  mandatory
        DESCRIPTION
                "The value of this object defines the mode used to
                establish the X25 VC between this HDLC logical
                port and the remote one on the other side of the
                network. The authorized values are 'calling' (the
                caller is this HDLC logical port), 'called' (the
                caller is this remote HDLC logical port), 'auto'
                (automatic choise between 'calling' and 'called').
                The default value is 'auto'."
        ::= { fclHdlcAutoCallEntry 7 }


    fclHdlcAutoEncapsulation OBJECT-TYPE
        SYNTAX  INTEGER {
                none(1),
                fastSelect(2),
                fastSelect-grouping(4)
                }
        ACCESS  read-write
        STATUS  mandatory
        DESCRIPTION
                "The value of this object defines how HDLC frames
                are transported in the X25 VC between this HDLC
                logical port and the remote one on the other side
                of the network. The authorized values are 'none'
                (each FR frame is put in one packet without any
                particular treatment), 'fastSelect' (Fast select
                is requested in the call packet),
                'fastSelect-frHeader' (Fast select is requested in
                the call packet, the FR header is also
                transported), 'fastSelect-frHeader-grouping' (Fast
                select is requested in the call packet, the FR
                header is also transported, several FR frames may
                be grouped in only one packet). The default value
                is 'none'."
        ::= { fclHdlcAutoCallEntry 8 }


    fclHdlcAutoMinRecallTimer OBJECT-TYPE
        SYNTAX  INTEGER (0..990)
        ACCESS  read-write
        STATUS  mandatory
        DESCRIPTION
                "The value of this object specifies the minimum
                recall time (in seconds) between two successive
                calls. The authorized values are '0..990' by step
                of 10. The default value is '0'."
        ::= { fclHdlcAutoCallEntry 10 }


    fclHdlcAutoInactivityTimer OBJECT-TYPE
        SYNTAX  INTEGER (0..2540)
        ACCESS  read-write
        STATUS  mandatory
        DESCRIPTION
                "The value of this object is the inactivity time in
                seconds.............. The possible values are :
                '0..2540'. See fclHdlcLpInactivityCheckDelay to
                enable or disable this clearing. The default value
                is '30'."
        ::= { fclHdlcAutoCallEntry 11 }


    fclSdlcLogPort OBJECT IDENTIFIER ::= { fcLogicalPorts 15 }


    fclSdlcLogPortTable OBJECT-TYPE
        SYNTAX  SEQUENCE OF FclSdlcLogPortEntry
        ACCESS  not-accessible
        STATUS  mandatory
        DESCRIPTION
                "This table defines the general parameters of SDLC
                (Synchronous Data Link Control) access logical
                ports. These SDLC logical ports are used in SNA
                (Systems Network Architecture) to cross X25 or
                Frame Relay networks."
        ::= { fclSdlcLogPort 1 }


    fclSdlcLogPortEntry OBJECT-TYPE
        SYNTAX  FclSdlcLogPortEntry
        ACCESS  not-accessible
        STATUS  mandatory
        DESCRIPTION
                "An entry of fclSdlcLogPortTable."
        INDEX   { fclSdlcLpLogPortId }
        ::= { fclSdlcLogPortTable 1 }


        FclSdlcLogPortEntry ::=
                SEQUENCE {
                    fclSdlcLpLogPortId
                        INTEGER,
                    fclSdlcLpInterfaceId
                        INTEGER,
                    fclSdlcLpPhysicalUnitType
                        INTEGER,
                    fclSdlcLpSubscriberNumber
                        OCTET STRING,
                    fclSdlcLpBitEncoding
                        INTEGER,
                    fclSdlcLpUnknownPackets
                        INTEGER,
                    fclSdlcLpLogicalLinkProtocol
                        INTEGER,
                    fclSdlcLpPacketSize
                        INTEGER,
                    fclSdlcLpWindowSize
                        INTEGER,
                    fclSdlcLpCompression
                        INTEGER,
                    fclSdlcLpCompressNegotiation
                        INTEGER,
                    fclSdlcLpCompressScrambling
                        INTEGER,
                    fclSdlcLpCompressMultiPacketsTimer
                        INTEGER,
                    fclSdlcLpReliableVc
                        INTEGER,
                    fclSdlcLpCos
                        INTEGER,
                    fclSdlcLpCir
                        INTEGER,
                    fclSdlcLpMinCir
                        INTEGER,
                    fclSdlcLpBe
                        INTEGER
                }


    fclSdlcLpLogPortId OBJECT-TYPE
        SYNTAX  INTEGER (0..181)
        ACCESS  read-only
        STATUS  mandatory
        DESCRIPTION
                "The value of this object identifies one and only
                one SDLC (Synchronous Data Link Control) access
                logical port in SNA (Systems Network
                Architecture). The possible values are : '0..131'.
                If it is unused, the value of this parameter is
                '255'. The default value is '255'."
        ::= { fclSdlcLogPortEntry 1 }


    fclSdlcLpInterfaceId OBJECT-TYPE
        SYNTAX  INTEGER (0..35)
        ACCESS  read-write
        STATUS  mandatory
        DESCRIPTION
                "The value of this object identifies the line
                interface used by this SDLC logical port. The
                possible values are : '0..35'. If it is unused,
                the value of this parameter is '255'. The default
                value is '255'."
        ::= { fclSdlcLogPortEntry 2 }


    fclSdlcLpPhysicalUnitType OBJECT-TYPE
        SYNTAX  INTEGER {
                primary(18),
                secondary(17)
                }
        ACCESS  read-write
        STATUS  mandatory
        DESCRIPTION
                "The value of this object indicates the type of the
                physical unit(s) which are in front of this SDLC
                logical port. The PU may be 'primary' or
                'secondary'. Primary PUs poll secondary Pus in a
                predetermined order and then secondaries transmit
                if they have outgoing data. The equipment acts as
                a primary PU in front of secondaries PU and, on
                the other side, it acts as secondaries PU in front
                of a primary PU.
                The default value is 'secondary' (so the equipment
                acts as primary PU)."
        ::= { fclSdlcLogPortEntry 3 }


    fclSdlcLpSubscriberNumber OBJECT-TYPE
        SYNTAX  OCTET STRING (SIZE(1))
        ACCESS  read-write
        STATUS  mandatory
        DESCRIPTION
                "The value of this object is the SB number added to
                the DNICZO of the equipment to make the calling
                address in a call sent from this logical port. The
                value must contain 2 digits (digits 0..9). The
                default value is 'FF'."
        ::= { fclSdlcLogPortEntry 4 }


    fclSdlcLpBitEncoding OBJECT-TYPE
        SYNTAX  INTEGER {
                nrz(1),
                nrzInverse(2)
                }
        ACCESS  read-write
        STATUS  mandatory
        DESCRIPTION
                "The value of this object indicates whether the
                coding format is NRZ (Non Return to Zero) or NRZI
                (Non Return to Zero Inverted) The default value is
                'nrz'."
        ::= { fclSdlcLogPortEntry 5 }


    fclSdlcLpUnknownPackets OBJECT-TYPE
        SYNTAX  INTEGER {
                clear(1),
                delete(2)
                }
        ACCESS  read-write
        STATUS  mandatory
        DESCRIPTION
                "The value of this object indicates, when the
                equipment receives an unknown packet on this
                logical port, whether it clears the WAN connection
                or it deletes this packet (i.e. it does not
                transmit this packet over the network). The
                default value is 'nrz'."
        ::= { fclSdlcLogPortEntry 6 }


    fclSdlcLpLogicalLinkProtocol OBJECT-TYPE
        SYNTAX  INTEGER {
                qllc(1),
                psh(2)
                }
        ACCESS  read-write
        STATUS  mandatory
        DESCRIPTION
                "The value of this object indicates which transport
                protocol is used over the network. QLLC (...) or
                PSH (...) may be used. The default value is 'qllc'."
        ::= { fclSdlcLogPortEntry 7 }


    fclSdlcLpPacketSize OBJECT-TYPE
        SYNTAX  INTEGER {
                s16(4),
                s32(5),
                s64(6),
                s128(7),
                s256(8),
                s512(9),
                s1024(10),
                s2048(11),
                s4096(12)
                }
        ACCESS  read-write
        STATUS  mandatory
        DESCRIPTION
                "The value of this object indicates the packet size
                used across the network. When PSH is used as
                transport protocol the packet size must be 128 or
                256 octets. The default value is 128 octets."
        ::= { fclSdlcLogPortEntry 8 }


    fclSdlcLpWindowSize OBJECT-TYPE
        SYNTAX  INTEGER (1..7)
        ACCESS  read-write
        STATUS  mandatory
        DESCRIPTION
                "The value of this object indicates the window size
                used across the network. The authorized values are
                '1..7'. The default value is '7'."
        ::= { fclSdlcLogPortEntry 9 }


    fclSdlcLpCompression OBJECT-TYPE
        SYNTAX  INTEGER {
                off(1),
                networkToSubscriber(2),
                subscriberToNetwork(3),
                bothway(4)
                }
        ACCESS  read-write
        STATUS  mandatory
        DESCRIPTION
                "The value of this object indicates the compression
                enabling for each direction. The authorized values
                are :
                   off : no compression,
                   networkToSubscriber : compression of the flow
                        from the remote peer to the equipment,
                   subscriberToNetwork : compression of the flow
                        from the equipment to the remote peer,
                   bothway : compression of the two flows from and
                        to the equipment.
                The default value is 'off'."
        ::= { fclSdlcLogPortEntry 20 }


    fclSdlcLpCompressNegotiation OBJECT-TYPE
        SYNTAX  INTEGER {
                off(1),
                onOptionalCompression(2),
                onMandatoryCompression(3)
                }
        ACCESS  read-write
        STATUS  mandatory
        DESCRIPTION
                "The value of this object indicates whether the
                compression facility is negociated or not and, if
                negociated, the optional/obligatory status. The
                authorized values are :
                   off' :no negociation,
                   onOptionalCompression : negociation but
                        compression is optional,
                   onMandatoryCompression : negociation and
                        compression is mandatory.
                The default value is 'off'."
        ::= { fclSdlcLogPortEntry 21 }


    fclSdlcLpCompressScrambling OBJECT-TYPE
        SYNTAX  INTEGER {
                off(1),
                on(2)
                }
        ACCESS  read-write
        STATUS  mandatory
        DESCRIPTION
                "The value of this object indicates, when the
                compression is active, whether the scrambling is
                enabled or not. The default value is 'off'."
        ::= { fclSdlcLogPortEntry 22 }


    fclSdlcLpCompressMultiPacketsTimer OBJECT-TYPE
        SYNTAX  INTEGER (0..1500)
        ACCESS  read-write
        STATUS  mandatory
        DESCRIPTION
                "The value of this object defines the maximum
                waiting time, in milliseconds by steps of 100
                milliseconds , which, if there is not another
                packet to compress, the packet of compressed
                packets is sent beyond (this permits to reduce the
                number of packets transmitted to the remote peer).
                The authorized values are '0..1500'. '0' means no
                packets grouping (i. e. : each packet is
                individually compressed and sent). The default
                value is '0'."
        ::= { fclSdlcLogPortEntry 23 }


    fclSdlcLpReliableVc OBJECT-TYPE
        SYNTAX  INTEGER {
                off(1),
                clear(3),
                subscribe(2),
                check(4)
                }
        ACCESS  read-write
        STATUS  mandatory
        DESCRIPTION
                "The value of this object is used to enable the
                Reliable Virtual Circuit service. The authorized
                values are :
                   off : no RVC, the VCs are considered as normal
                        VCs, no particular processing,
                   clear : RVCs are not allowed for the
                        subscriber, each attempt to establish a
                        RVC provokes a clear of the connection,
                   subscribe : all calls transmitted by the
                        subscriber establish RVCs, it is also
                        possible to receive calls with RVC option,
                   check :
                     for a link to a subscriber : when a call with
                        RVC option is received, a RVC is
                        established
                     for a link to a network : the RVC option is
                        ignored when it is present in a call sent
                        by a local subscriber, the connection is
                        cleared when the RVC option is present in
                        a call sent by the network.
                The default value is 'off'."
        ::= { fclSdlcLogPortEntry 24 }


    fclSdlcLpCos OBJECT-TYPE
        SYNTAX  INTEGER {
                ubr(3),
                vbr(1)
                }
        ACCESS  read-write
        STATUS  mandatory
        DESCRIPTION
                "COS"
        ::= { fclSdlcLogPortEntry 30 }


    fclSdlcLpCir OBJECT-TYPE
        SYNTAX  INTEGER (600..2048000)
        ACCESS  read-write
        STATUS  mandatory
        DESCRIPTION
                "Entrant CIR"
        ::= { fclSdlcLogPortEntry 31 }


    fclSdlcLpMinCir OBJECT-TYPE
        SYNTAX  INTEGER (0..2048000)
        ACCESS  read-write
        STATUS  mandatory
        DESCRIPTION
                "Entrant CIR mini"
        ::= { fclSdlcLogPortEntry 32 }


    fclSdlcLpBe OBJECT-TYPE
        SYNTAX  INTEGER (0..2048000)
        ACCESS  read-write
        STATUS  mandatory
        DESCRIPTION
                "Entrant BE"
        ::= { fclSdlcLogPortEntry 33 }


    fclSdlcPrimaryPuLogPort OBJECT IDENTIFIER ::= { fclSdlcLogPort 2 }


    fclSdlcPriLogPortTable OBJECT-TYPE
        SYNTAX  SEQUENCE OF FclSdlcPriLogPortEntry
        ACCESS  not-accessible
        STATUS  mandatory
        DESCRIPTION
                "This table defines the parameters of SDLC access
                logical ports which are in front of primaries
                Physical Units."
        ::= { fclSdlcPrimaryPuLogPort 1 }


    fclSdlcPriLogPortEntry OBJECT-TYPE
        SYNTAX  FclSdlcPriLogPortEntry
        ACCESS  not-accessible
        STATUS  mandatory
        DESCRIPTION
                "An entry of fclSdlcPriLogPortTable."
        INDEX   { fclSdlcPriLpLogPortId }
        ::= { fclSdlcPriLogPortTable 1 }


        FclSdlcPriLogPortEntry ::=
                SEQUENCE {
                    fclSdlcPriLpLogPortId
                        INTEGER,
                    fclSdlcPriLpLinkType
                        INTEGER,
                    fclSdlcPriLpRemPuIdentification
                        INTEGER,
                    fclSdlcPriLpPollingGroupResponse
                        INTEGER,
                    fclSdlcPriLpPollingGroupAddress
                        OCTET STRING
                }


    fclSdlcPriLpLogPortId OBJECT-TYPE
        SYNTAX  INTEGER (0..181)
        ACCESS  read-only
        STATUS  mandatory
        DESCRIPTION
                "The value of this object identifies one and only
                one SDLC access logical port which is in front of
                primaries Physical Units. The possible values are
                : '0..131'. If it is unused, the value of this
                parameter is '255'. The default value is '255'."
        ::= { fclSdlcPriLogPortEntry 1 }


    fclSdlcPriLpLinkType OBJECT-TYPE
        SYNTAX  INTEGER {
                pu4-pu4(25),
                pu4-pu21(20),
                pu4-pu20(16),
                pu21-pu21(22),
                nixd-pu20(27),
                rwsi-pu20(30)
                }
        ACCESS  read-write
        STATUS  mandatory
        DESCRIPTION
                "The value of this object indicates which kind of
                link is estblished over the network. In this
                description the primary PU in front of this
                logical port is said 'local', the secondary PU on
                the other side of the network is said 'remote'.
                The values are expressed with the format
                'local-remote' :
                   pu4-pu4 : PU 4 to PU 4,
                   pu4-pu21 PU 4 to PU 2.1,
                   pu4-pu20 : PU 4 to PU 2.0,
                   pu21-pu21 : PU 2.1 to PU 2.1,
                   nixd-pu20 : Nixdorf PU to PU 2.0,
                   rwsi-pu20 : RWSI to PU 2.0.
                The default value is 'pu4-pu20'."
        ::= { fclSdlcPriLogPortEntry 2 }


    fclSdlcPriLpRemPuIdentification OBJECT-TYPE
        SYNTAX  INTEGER {
                proprietary(1),
                calledAddr(2)
                }
        ACCESS  read-write
        STATUS  mandatory
        DESCRIPTION
                "The value of this object indicates whether the
                remote secondary PU is identified by a proprietary
                way or by using the called address field of call
                packets.
                The default value is 'proprietary'."
        ::= { fclSdlcPriLogPortEntry 3 }


    fclSdlcPriLpPollingGroupResponse OBJECT-TYPE
        SYNTAX  INTEGER {
                off(1),
                on(2)
                }
        ACCESS  read-write
        STATUS  mandatory
        DESCRIPTION
                "The value of this object indicates whether the
                equipment answers to the polling group when this
                feature is used by the local primary PU as a
                normal secondary PU should do. The address used by
                this polling group is defined in
                fclSdlcPriLpPollingGroupAddress.
                The default value is 'off'."
        ::= { fclSdlcPriLogPortEntry 4 }


    fclSdlcPriLpPollingGroupAddress OBJECT-TYPE
        SYNTAX  OCTET STRING (SIZE(1))
        ACCESS  read-write
        STATUS  mandatory
        DESCRIPTION
                "The value of this object defines the address used
                by the polling group (if the equipment must answer
                according to fclSdlcPriLpPollingGroupResponse).
                The value must contain 2 digits (digits 0..F).
                The default value is 'FF'."
        ::= { fclSdlcPriLogPortEntry 5 }


    fclSdlcPriClusterTable OBJECT-TYPE
        SYNTAX  SEQUENCE OF FclSdlcPriClusterEntry
        ACCESS  not-accessible
        STATUS  mandatory
        DESCRIPTION
                ""
        ::= { fclSdlcPrimaryPuLogPort 2 }


    fclSdlcPriClusterEntry OBJECT-TYPE
        SYNTAX  FclSdlcPriClusterEntry
        ACCESS  not-accessible
        STATUS  mandatory
        DESCRIPTION
                "An entry of fclSdlcPriClusterTable."
        INDEX   { fclSdlcPriClusterLogPortId,
                  fclSdlcPriClusterAddress }
        ::= { fclSdlcPriClusterTable 1 }


        FclSdlcPriClusterEntry ::=
                SEQUENCE {
                    fclSdlcPriClusterLogPortId
                        INTEGER,
                    fclSdlcPriClusterAddress
                        OCTET STRING,
                    fclSdlcPriClusterStatus
                        INTEGER,
                    fclSdlcPriClusterRemPu2CalledAddr
                        OCTET STRING
                }


    fclSdlcPriClusterLogPortId OBJECT-TYPE
        SYNTAX  INTEGER (0..181)
        ACCESS  read-only
        STATUS  mandatory
        DESCRIPTION
                "LP Id"
        ::= { fclSdlcPriClusterEntry 1 }


    fclSdlcPriClusterAddress OBJECT-TYPE
        SYNTAX  OCTET STRING (SIZE(1))
        ACCESS  read-only
        STATUS  mandatory
        DESCRIPTION
                "Adresse du cluster"
        ::= { fclSdlcPriClusterEntry 2 }


    fclSdlcPriClusterStatus OBJECT-TYPE
        SYNTAX  INTEGER {
                valid(1),
                invalid(2)
                }
        ACCESS  read-write
        STATUS  mandatory
        DESCRIPTION
                "Status"
        ::= { fclSdlcPriClusterEntry 3 }


    fclSdlcPriClusterRemPu2CalledAddr OBJECT-TYPE
        SYNTAX  OCTET STRING (SIZE(8))
        ACCESS  read-write
        STATUS  mandatory
        DESCRIPTION
                "Adresse X121 si identification PU2 distant par
                adresse appelee"
        ::= { fclSdlcPriClusterEntry 5 }


    fclSdlcSecondaryPuLogPort OBJECT IDENTIFIER ::= { fclSdlcLogPort 3 }


    fclSdlcSecLogPortTable OBJECT-TYPE
        SYNTAX  SEQUENCE OF FclSdlcSecLogPortEntry
        ACCESS  not-accessible
        STATUS  mandatory
        DESCRIPTION
                ""
        ::= { fclSdlcSecondaryPuLogPort 1 }


    fclSdlcSecLogPortEntry OBJECT-TYPE
        SYNTAX  FclSdlcSecLogPortEntry
        ACCESS  not-accessible
        STATUS  mandatory
        DESCRIPTION
                "An entry of fclSdlcSecLogPortTable."
        INDEX   { fclSdlcSecLpLogPortId }
        ::= { fclSdlcSecLogPortTable 1 }


        FclSdlcSecLogPortEntry ::=
                SEQUENCE {
                    fclSdlcSecLpLogPortId
                        INTEGER,
                    fclSdlcSecLpLinkType
                        INTEGER,
                    fclSdlcSecLpRemPuIdentification
                        INTEGER,
                    fclSdlcSecLpT1AcknowledgeTimer
                        INTEGER,
                    fclSdlcSecLpN2RetryCount
                        INTEGER,
                    fclSdlcSecLpCallRetryCount
                        INTEGER,
                    fclSdlcSecLpPollingTimer
                        INTEGER,
                    fclSdlcSecLpPollingMaxCount
                        INTEGER
                }


    fclSdlcSecLpLogPortId OBJECT-TYPE
        SYNTAX  INTEGER (0..181)
        ACCESS  read-only
        STATUS  mandatory
        DESCRIPTION
                "The value of this object identifies one and only
                one SDLC access logical port which is in front of
                primaries Physical Units. The possible values are
                : '0..131'. If it is unused, the value of this
                parameter is '255'. The default value is '255'."
        ::= { fclSdlcSecLogPortEntry 1 }


    fclSdlcSecLpLinkType OBJECT-TYPE
        SYNTAX  INTEGER {
                pu4-pu4(26),
                pu21-pu4(21),
                pu21-pu21(23),
                pu20-pu4(17),
                pu20-nixd(28),
                pu20-rwsi(31),
                terminal-pu4(34)
                }
        ACCESS  read-write
        STATUS  mandatory
        DESCRIPTION
                "The value of this object indicates which kind of
                link is estblished over the network. In this
                description the secondary PU in front of this
                logical port is said 'local', the primary PU on
                the other side of the network is said 'remote'.
                The values are expressed with the format
                'local-remote' :
                   pu4-pu4 : PU 4 to PU 4,
                   pu21-pu4 PU 2.1 to PU 4,
                   pu21-pu21 : PU 2.1 to PU 2.1,
                   pu20-pu4 : PU 2.0 to PU 4,
                   pu20-nixd : PU 2.0 to Nixdorf PU,
                   pu20-rwsi : PU 2.0 to RWSI.
                   terminal to pu4.
                The default value is 'pu20-pu4'."
        ::= { fclSdlcSecLogPortEntry 2 }


    fclSdlcSecLpRemPuIdentification OBJECT-TYPE
        SYNTAX  INTEGER {
                proprietary(1),
                calledAddr(2)
                }
        ACCESS  read-write
        STATUS  mandatory
        DESCRIPTION
                "The value of this object indicates whether the
                remote secondary PU is identified by a proprietary
                way or by using the called address field of call
                packets.
                The default value is 'proprietary'."
        ::= { fclSdlcSecLogPortEntry 3 }


    fclSdlcSecLpT1AcknowledgeTimer OBJECT-TYPE
        SYNTAX  INTEGER (200..25000)
        ACCESS  read-write
        STATUS  mandatory
        DESCRIPTION
                "T1 Reply timer. A SDLC link-station uses T1 to
                detect a failure to receive a required
                acknowlegment or response. T1 runs when there are
                acknowlegments outstanding, it is reset when
                acknowlegments are received."
        ::= { fclSdlcSecLogPortEntry 4 }


    fclSdlcSecLpN2RetryCount OBJECT-TYPE
        SYNTAX  INTEGER (2..250)
        ACCESS  read-write
        STATUS  mandatory
        DESCRIPTION
                "The maximum number of transmissions. If the reply
                timer expires for whatever reason, an S-frame with
                poll bit set is sent to sollicit  a response from
                remote SDLC link-station. If there is still no
                response after N2 retry, the link is deemed to be
                inoperative."
        ::= { fclSdlcSecLogPortEntry 5 }


    fclSdlcSecLpCallRetryCount OBJECT-TYPE
        SYNTAX  INTEGER (0..99)
        ACCESS  read-write
        STATUS  mandatory
        DESCRIPTION
                "The maximum number of calls. If the call confirm
                is not received, the network layer will repeat a
                call packet. If there is still no response after n
                calls, the network layer will then start a slow
                call."
        ::= { fclSdlcSecLogPortEntry 6 }


    fclSdlcSecLpPollingTimer OBJECT-TYPE
        SYNTAX  INTEGER (0..12800)
        ACCESS  read-write
        STATUS  mandatory
        DESCRIPTION
                "Timer between two polling of all stations in a
                list."
        ::= { fclSdlcSecLogPortEntry 10 }


    fclSdlcSecLpPollingMaxCount OBJECT-TYPE
        SYNTAX  INTEGER (1..255)
        ACCESS  read-write
        STATUS  mandatory
        DESCRIPTION
                "Number of polling counts before to poll the
                station with SNRM"
        ::= { fclSdlcSecLogPortEntry 11 }


    fclSdlcSecClusterTable OBJECT-TYPE
        SYNTAX  SEQUENCE OF FclSdlcSecClusterEntry
        ACCESS  not-accessible
        STATUS  mandatory
        DESCRIPTION
                ""
        ::= { fclSdlcSecondaryPuLogPort 2 }


    fclSdlcSecClusterEntry OBJECT-TYPE
        SYNTAX  FclSdlcSecClusterEntry
        ACCESS  not-accessible
        STATUS  mandatory
        DESCRIPTION
                "An entry of fclSdlcSecClusterTable."
        INDEX   { fclSdlcSecClusterLogPortId,
                  fclSdlcSecClusterAddress }
        ::= { fclSdlcSecClusterTable 1 }


        FclSdlcSecClusterEntry ::=
                SEQUENCE {
                    fclSdlcSecClusterLogPortId
                        INTEGER,
                    fclSdlcSecClusterAddress
                        OCTET STRING,
                    fclSdlcSecClusterStatus
                        INTEGER,
                    fclSdlcSecClusterCalledAddr
                        OCTET STRING,
                    fclSdlcSecClusterFacility
                        INTEGER,
                    fclSdlcSecClusterFacThroughputClass
                        INTEGER,
                    fclSdlcSecClusterMinRecallTimer
                        INTEGER,
                    fclSdlcSecClusterRemPvcLogChannel
                        INTEGER,
                    fclSdlcSecClusterXidStringResponse
                        OCTET STRING,
                    fclSdlcSecClusterCos
                        INTEGER,
                    fclSdlcSecClusterCir
                        INTEGER,
                    fclSdlcSecClusterCirmin
                        INTEGER,
                    fclSdlcSecClusterBc
                        INTEGER,
                    fclSdlcSecClusterBe
                        INTEGER
                }


    fclSdlcSecClusterLogPortId OBJECT-TYPE
        SYNTAX  INTEGER (0..181)
        ACCESS  read-only
        STATUS  mandatory
        DESCRIPTION
                "The value of this object identifies one and only
                one SDLC access logical port which is in front of
                primaries Physical Units. The possible values are
                : '0..131'. If it is unused, the value of this
                parameter is '255'. The default value is '255'."
        ::= { fclSdlcSecClusterEntry 1 }


    fclSdlcSecClusterAddress OBJECT-TYPE
        SYNTAX  OCTET STRING (SIZE(1))
        ACCESS  read-only
        STATUS  mandatory
        DESCRIPTION
                "This is the poll address of the controller. You
                must make sure this address matches the one
                assignedto the attached controller. Range is '01
                to FF'"
        ::= { fclSdlcSecClusterEntry 2 }


    fclSdlcSecClusterStatus OBJECT-TYPE
        SYNTAX  INTEGER {
                valid(1),
                invalid(2)
                }
        ACCESS  read-write
        STATUS  mandatory
        DESCRIPTION
                "Status"
        ::= { fclSdlcSecClusterEntry 3 }


    fclSdlcSecClusterCalledAddr OBJECT-TYPE
        SYNTAX  OCTET STRING (SIZE(8))
        ACCESS  read-write
        STATUS  mandatory
        DESCRIPTION
                "Called X121 address. X121 Address of the
                corresponding Hpad element."
        ::= { fclSdlcSecClusterEntry 5 }


    fclSdlcSecClusterFacility OBJECT-TYPE
        SYNTAX  INTEGER {
                none(1),
                reverseCharging(2),
                cug(3),
                reverseCharging-cug(4),
                throughputClass(5)
                }
        ACCESS  read-write
        STATUS  mandatory
        DESCRIPTION
                "The value of this object indicates the X25 call
                packet facility. The possible values are :
                   none : no facility in the call packet,
                   reverseCharging : Reverse Charging,
                   cug : Closed User Group,
                   reverseCharging -cug : Closed User Group,
                        Reverse Charging.
                The default value is 'none'."
        ::= { fclSdlcSecClusterEntry 6 }


    fclSdlcSecClusterFacThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "Throughput Class"
        ::= { fclSdlcSecClusterEntry 7 }


    fclSdlcSecClusterMinRecallTimer OBJECT-TYPE
        SYNTAX  INTEGER (0..990)
        ACCESS  read-write
        STATUS  mandatory
        DESCRIPTION
                "Slow call timer"
        ::= { fclSdlcSecClusterEntry 10 }


    fclSdlcSecClusterRemPvcLogChannel OBJECT-TYPE
        SYNTAX  INTEGER (0..250)
        ACCESS  read-write
        STATUS  mandatory
        DESCRIPTION
                "PVC number"
        ::= { fclSdlcSecClusterEntry 11 }


    fclSdlcSecClusterXidStringResponse OBJECT-TYPE
        SYNTAX  OCTET STRING (SIZE(6))
        ACCESS  read-write
        STATUS  mandatory
        DESCRIPTION
                "This field enables you to assign a PU XID. The
                unit uses XID's to establish and negociate PU
                application session. If the PU cannot respond to
                an XID request from the Host, the unit uses this
                assigned XID value."
        ::= { fclSdlcSecClusterEntry 12 }


    fclSdlcSecClusterCos OBJECT-TYPE
        SYNTAX  INTEGER {
                ubr(3),
                vbr(1),
                vbr-rt(2)
                }
        ACCESS  read-write
        STATUS  mandatory
        DESCRIPTION
                "COS Class Of  Service VBR"
        ::= { fclSdlcSecClusterEntry 20 }


    fclSdlcSecClusterCir OBJECT-TYPE
        SYNTAX  INTEGER (0..2048000)
        ACCESS  read-write
        STATUS  mandatory
        DESCRIPTION
                "CIR Committed information Rate is the maximum
                number of bits per seconds which an end station
                can transmit into the network . This is the access
                rate of the user-network interface and it is
                limited by the line speed of the user-network
                connection and established by subscription."
        ::= { fclSdlcSecClusterEntry 21 }


    fclSdlcSecClusterCirmin OBJECT-TYPE
        SYNTAX  INTEGER (0..2048000)
        ACCESS  read-write
        STATUS  mandatory
        DESCRIPTION
                "CIRmin If the end station is informed about the
                congestion of the network, this is the minimum CIR
                that the end station can transmit into the network."
        ::= { fclSdlcSecClusterEntry 22 }


    fclSdlcSecClusterBc OBJECT-TYPE
        SYNTAX  INTEGER (0..2048000)
        ACCESS  read-write
        STATUS  mandatory
        DESCRIPTION
                "Bc The Committed Burst Size is a measure for the
                volume of data for which the network will garantee
                message delivery under normal conditions. It is
                measured during the committed rate measurement
                interval (Tc)."
        ::= { fclSdlcSecClusterEntry 23 }


    fclSdlcSecClusterBe OBJECT-TYPE
        SYNTAX  INTEGER (0..2048000)
        ACCESS  read-write
        STATUS  mandatory
        DESCRIPTION
                "Be The Excess Burst Size is the maximum amount of
                uncommitted data in access of Bc that the network
                will attemp to deliver during a time interval
                (Tc). End stations are allowed to transmit data in
                excess of the committed burst rate."
        ::= { fclSdlcSecClusterEntry 24 }


    fclVipLogPort OBJECT IDENTIFIER ::= { fcLogicalPorts 16 }


    fclVipLogPortTable OBJECT-TYPE
        SYNTAX  SEQUENCE OF FclVipLogPortEntry
        ACCESS  not-accessible
        STATUS  mandatory
        DESCRIPTION
                "This table defines the general parameters of VIP
                (Visual Information Projection) access logical
                ports. These VIP logical ports are used in
                HONEYWELL -BULL systems to cross X25 or Frame
                Relay networks"
        ::= { fclVipLogPort 1 }


    fclVipLogPortEntry OBJECT-TYPE
        SYNTAX  FclVipLogPortEntry
        ACCESS  not-accessible
        STATUS  mandatory
        DESCRIPTION
                "An entry of fclVipLogPortTable."
        INDEX   { fclVipLpLogPortId }
        ::= { fclVipLogPortTable 1 }


        FclVipLogPortEntry ::=
                SEQUENCE {
                    fclVipLpLogPortId
                        INTEGER,
                    fclVipLpInterfaceId
                        INTEGER,
                    fclVipLpEmulationType
                        INTEGER,
                    fclVipLpResponseSurveyPollingTimer
                        INTEGER,
                    fclVipLpScreenRetryTimer
                        INTEGER,
                    fclVipLpPrinterRetryTimer
                        INTEGER,
                    fclVipLpMessageRetryNumber
                        INTEGER,
                    fclVipLpPrinterMessagesManagement
                        INTEGER
                }


    fclVipLpLogPortId OBJECT-TYPE
        SYNTAX  INTEGER (0..181)
        ACCESS  read-only
        STATUS  mandatory
        DESCRIPTION
                "The value of this object identifies one and only
                one VIP(Visual Information Projection) access
                logical port in BULL network architecture. The
                possible values are : '0..131'. If it is unused,
                the value of this parameter is '255'. The default
                value is '255'."
        ::= { fclVipLogPortEntry 1 }


    fclVipLpInterfaceId OBJECT-TYPE
        SYNTAX  INTEGER (0..35)
        ACCESS  read-write
        STATUS  mandatory
        DESCRIPTION
                "The value of this object identifies the line
                interface used by this VIP logical port. The
                possible values are : '0..35'. If it is unused,
                the value of this parameter is '255'. The default
                value is '255'."
        ::= { fclVipLogPortEntry 2 }


    fclVipLpEmulationType OBJECT-TYPE
        SYNTAX  INTEGER {
                tpad(50),
                hpad(51)
                }
        ACCESS  read-write
        STATUS  mandatory
        DESCRIPTION
                "The value of this object indicates the type of
                unit which are in front of this VIP logical port.
                The unit may be 'Host' or 'Cluster'. Host units
                poll cluster units in a predetermined order and
                then clusters transmit if they have outgoing data.
                The COMPAC equipment acts as a Cluster in front of
                a host(HPAD emulation) and, on the other side, it
                acts as a host in front of a cluster(TPAD
                emulation). The TPAD always originates the link
                circuit request .The HPAD is waiting for  the link
                circuit indication.
                The default value is 'HPAD'(so the equipment acts
                as Cluster)."
        ::= { fclVipLogPortEntry 3 }


    fclVipLpResponseSurveyPollingTimer OBJECT-TYPE
        SYNTAX  INTEGER (100..25000)
        ACCESS  read-write
        STATUS  mandatory
        DESCRIPTION
                "Supervision line watchdog. If this timeout
                matures, the line is considered as beeing out of
                order.
                The default value is 300ms."
        ::= { fclVipLogPortEntry 8 }


    fclVipLpScreenRetryTimer OBJECT-TYPE
        SYNTAX  INTEGER (10..2500)
        ACCESS  read-write
        STATUS  mandatory
        DESCRIPTION
                "Value of screen message transmission Time Out.
                The default value is '10' s"
        ::= { fclVipLogPortEntry 9 }


    fclVipLpPrinterRetryTimer OBJECT-TYPE
        SYNTAX  INTEGER (10..2500)
        ACCESS  read-write
        STATUS  mandatory
        DESCRIPTION
                "Value of  printer message retransmission Time Out.
                The default value is '70' s"
        ::= { fclVipLogPortEntry 10 }


    fclVipLpMessageRetryNumber OBJECT-TYPE
        SYNTAX  INTEGER (1..7)
        ACCESS  read-write
        STATUS  mandatory
        DESCRIPTION
                "Number of message retransmissions.
                The default value is '5'."
        ::= { fclVipLogPortEntry 11 }


    fclVipLpPrinterMessagesManagement OBJECT-TYPE
        SYNTAX  INTEGER {
                local(1),
                transparent(2)
                }
        ACCESS  read-write
        STATUS  mandatory
        DESCRIPTION
                "'Local management' or 'transparency'of  printer
                messages.
                Local management 
                   It is the standard functionning. When a printer
                        message is received from the HOST , it is
                        not immediateley aknowledged by the COMPAC
                        HPAD.It will be acknowledged when the 
                        fclVipLpHosPrinterRetryTimer time out
                        elapses.
                Transparency.
                   It is an end to end aknowlegement, the printer
                        aknowlege  is conveyed through the
                        network(transparency).
                The default value is 'local management'."
        ::= { fclVipLogPortEntry 12 }


    fclVipHostPadLogPort OBJECT IDENTIFIER ::= { fclVipLogPort 2 }


    fclVipHosLogPortTable OBJECT-TYPE
        SYNTAX  SEQUENCE OF FclVipHosLogPortEntry
        ACCESS  not-accessible
        STATUS  mandatory
        DESCRIPTION
                "This table defines the parameters of VIP access
                logical ports which are in front of Host Units"
        ::= { fclVipHostPadLogPort 1 }


    fclVipHosLogPortEntry OBJECT-TYPE
        SYNTAX  FclVipHosLogPortEntry
        ACCESS  not-accessible
        STATUS  mandatory
        DESCRIPTION
                "An entry of fclVipHosLogPortTable."
        INDEX   { fclVipHosLpLogPortId }
        ::= { fclVipHosLogPortTable 1 }


        FclVipHosLogPortEntry ::=
                SEQUENCE {
                    fclVipHosLpLogPortId
                        INTEGER,
                    fclVipHosLpWaitTimeOutForPrinter
                        INTEGER,
                    fclVipHosLpRepAEot
                        INTEGER,
                    fclVipHosLpFtbcc
                        INTEGER
                }


    fclVipHosLpLogPortId OBJECT-TYPE
        SYNTAX  INTEGER (0..181)
        ACCESS  read-only
        STATUS  mandatory
        DESCRIPTION
                "The value of this object identifies one and only
                one VIP access logical port which is in front of 
                a HOST. The possible values are : '0..131'. If it
                is unused, the value of this parameter is '255'. 
                The default value is '255'."
        ::= { fclVipHosLogPortEntry 1 }


    fclVipHosLpWaitTimeOutForPrinter OBJECT-TYPE
        SYNTAX  INTEGER (100..12800)
        ACCESS  read-write
        STATUS  mandatory
        DESCRIPTION
                "Value of  inter-polling  time-out for printer.
                The default value is '300' ms."
        ::= { fclVipHosLogPortEntry 2 }


    fclVipHosLpRepAEot OBJECT-TYPE
        SYNTAX  INTEGER {
                no(1),
                yes(2)
                }
        ACCESS  read-write
        STATUS  mandatory
        DESCRIPTION
                "EOT response or not from the HPAD on polls of the
                HOST and in case the virtual circuit with the TPAD
                has not been established.
                The default value is 'EOT response on the polls'."
        ::= { fclVipHosLogPortEntry 5 }


    fclVipHosLpFtbcc OBJECT-TYPE
        SYNTAX  INTEGER {
                no(1),
                yes(2)
                }
        ACCESS  read-write
        STATUS  mandatory
        DESCRIPTION
                "Special treatment or not  for the 'PENQ (printer
                Enquiry)sequence'(seen with customer FTBCC ITALY).
                The default value is 'no special treatement'."
        ::= { fclVipHosLogPortEntry 6 }


    fclVipHosElementTable OBJECT-TYPE
        SYNTAX  SEQUENCE OF FclVipHosElementEntry
        ACCESS  not-accessible
        STATUS  mandatory
        DESCRIPTION
                ""
        ::= { fclVipHostPadLogPort 2 }


    fclVipHosElementEntry OBJECT-TYPE
        SYNTAX  FclVipHosElementEntry
        ACCESS  not-accessible
        STATUS  mandatory
        DESCRIPTION
                "An entry of fclVipHosElementTable."
        INDEX   { fclVipHosElementId }
        ::= { fclVipHosElementTable 1 }


        FclVipHosElementEntry ::=
                SEQUENCE {
                    fclVipHosElementId
                        INTEGER,
                    fclVipHosElemStatus
                        INTEGER,
                    fclVipHosElemLogPortId
                        INTEGER,
                    fclVipHosElemType
                        INTEGER,
                    fclVipHosElemAddress
                        INTEGER
                }


    fclVipHosElementId OBJECT-TYPE
        SYNTAX  INTEGER (1..200)
        ACCESS  read-only
        STATUS  mandatory
        DESCRIPTION
                "Ident Element. The value of this object identifies
                one identificable addressable entity.
                The possible values are : '0..200'."
        ::= { fclVipHosElementEntry 1 }


    fclVipHosElemStatus OBJECT-TYPE
        SYNTAX  INTEGER {
                valid(1),
                invalid(2)
                }
        ACCESS  read-write
        STATUS  mandatory
        DESCRIPTION
                "Status."
        ::= { fclVipHosElementEntry 2 }


    fclVipHosElemLogPortId OBJECT-TYPE
        SYNTAX  INTEGER (0..181)
        ACCESS  read-write
        STATUS  mandatory
        DESCRIPTION
                "LpId. Logical Port Identifier."
        ::= { fclVipHosElementEntry 3 }


    fclVipHosElemType OBJECT-TYPE
        SYNTAX  INTEGER {
                cluster(1),
                isolatedstation(2)
                }
        ACCESS  read-write
        STATUS  mandatory
        DESCRIPTION
                "Element Type. Cluster or Isolated Station."
        ::= { fclVipHosElementEntry 4 }


    fclVipHosElemAddress OBJECT-TYPE
        SYNTAX  INTEGER (0..31)
        ACCESS  read-write
        STATUS  mandatory
        DESCRIPTION
                "Element Address. Vip Address of The  Entity
                Between '0' and '31'."
        ::= { fclVipHosElementEntry 5 }


    fclVipHosStationTable OBJECT-TYPE
        SYNTAX  SEQUENCE OF FclVipHosStationEntry
        ACCESS  not-accessible
        STATUS  mandatory
        DESCRIPTION
                ""
        ::= { fclVipHostPadLogPort 3 }


    fclVipHosStationEntry OBJECT-TYPE
        SYNTAX  FclVipHosStationEntry
        ACCESS  not-accessible
        STATUS  mandatory
        DESCRIPTION
                "An entry of fclVipHosStationTable."
        INDEX   { fclVipHosStatElementId,
                  fclVipHosStatStationAddress }
        ::= { fclVipHosStationTable 1 }


        FclVipHosStationEntry ::=
                SEQUENCE {
                    fclVipHosStatElementId
                        INTEGER,
                    fclVipHosStatStationAddress
                        INTEGER,
                    fclVipHosStatStatus
                        INTEGER
                }


    fclVipHosStatElementId OBJECT-TYPE
        SYNTAX  INTEGER (1..200)
        ACCESS  read-only
        STATUS  mandatory
        DESCRIPTION
                "Ident Element.The value of this object identifies
                one identificable addressable entity.
                The possible values are : '0..200'."
        ::= { fclVipHosStationEntry 1 }


    fclVipHosStatStationAddress OBJECT-TYPE
        SYNTAX  INTEGER (0..31)
        ACCESS  read-only
        STATUS  mandatory
        DESCRIPTION
                "Station Address. Vip Address of  the cluster
                defined in the previous table (case when element
                type=Cluster)."
        ::= { fclVipHosStationEntry 2 }


    fclVipHosStatStatus OBJECT-TYPE
        SYNTAX  INTEGER {
                valid(1),
                invalid(2)
                }
        ACCESS  read-write
        STATUS  mandatory
        DESCRIPTION
                "Status."
        ::= { fclVipHosStationEntry 3 }


    fclVipClusterLogPort OBJECT IDENTIFIER ::= { fclVipLogPort 3 }


    fclVipCluLogPortTable OBJECT-TYPE
        SYNTAX  SEQUENCE OF FclVipCluLogPortEntry
        ACCESS  not-accessible
        STATUS  mandatory
        DESCRIPTION
                "This table defines the parameters of VIP access
                logical ports which are in front of Cluster Units"
        ::= { fclVipClusterLogPort 1 }


    fclVipCluLogPortEntry OBJECT-TYPE
        SYNTAX  FclVipCluLogPortEntry
        ACCESS  not-accessible
        STATUS  mandatory
        DESCRIPTION
                "An entry of fclVipCluLogPortTable."
        INDEX   { fclVipCluLpLogPortId }
        ::= { fclVipCluLogPortTable 1 }


        FclVipCluLogPortEntry ::=
                SEQUENCE {
                    fclVipCluLpLogPortId
                        INTEGER,
                    fclVipCluLpPollingTimer
                        INTEGER,
                    fclVipCluLpFailedPollingMaxNumber
                        INTEGER,
                    fclVipCluLpPollingTypeAfterSelect
                        INTEGER,
                    fclVipCluLpScreenKeepTimer
                        INTEGER
                }


    fclVipCluLpLogPortId OBJECT-TYPE
        SYNTAX  INTEGER (0..181)
        ACCESS  read-only
        STATUS  mandatory
        DESCRIPTION
                "The value of this object identifies one and only
                one VIP access logical port which is in front of 
                a HOST. The possible values are : '0..131'. If it
                is unused, the value of this parameter is '255'. 
                The default value is '255'."
        ::= { fclVipCluLogPortEntry 1 }


    fclVipCluLpPollingTimer OBJECT-TYPE
        SYNTAX  INTEGER (100..12800)
        ACCESS  read-write
        STATUS  mandatory
        DESCRIPTION
                "Value of interpolling wait time-out
                (retransmission of polling frame on expiry of time
                out)."
        ::= { fclVipCluLogPortEntry 2 }


    fclVipCluLpFailedPollingMaxNumber OBJECT-TYPE
        SYNTAX  INTEGER (1..250)
        ACCESS  read-write
        STATUS  mandatory
        DESCRIPTION
                "Maximum number of unanswered polls
                The default value is '6'."
        ::= { fclVipCluLogPortEntry 3 }


    fclVipCluLpPollingTypeAfterSelect OBJECT-TYPE
        SYNTAX  INTEGER {
                stationPoll(1),
                clusterPoll(2)
                }
        ACCESS  read-write
        STATUS  mandatory
        DESCRIPTION
                "Polling Type after select
                Station polling. After a select the Tpad sends a
                station poll in order to directly receive from it
                an immediate aknowledgement .
                Cluster polling. After a select , the Tpad sends a
                cluster select. Although less efficient  it is
                sometimes used in certain configurations. 
                The default value is 'station poll'."
        ::= { fclVipCluLogPortEntry 8 }


    fclVipCluLpScreenKeepTimer OBJECT-TYPE
        SYNTAX  INTEGER (0..2550)
        ACCESS  read-write
        STATUS  mandatory
        DESCRIPTION
                "Screen message Blocking
                Duration of the blocking of the screen flow .After
                reception of a screen message , transmitted by a
                VIP station ,the message flow from that station  
                to the screen is blocked .The station is released
                when a screen message is received from the Host or
                when the protection time-out expires.
                The default value is no blocking."
        ::= { fclVipCluLogPortEntry 9 }


    fclVipCluElementTable OBJECT-TYPE
        SYNTAX  SEQUENCE OF FclVipCluElementEntry
        ACCESS  not-accessible
        STATUS  mandatory
        DESCRIPTION
                ""
        ::= { fclVipClusterLogPort 2 }


    fclVipCluElementEntry OBJECT-TYPE
        SYNTAX  FclVipCluElementEntry
        ACCESS  not-accessible
        STATUS  mandatory
        DESCRIPTION
                "An entry of fclVipCluElementTable."
        INDEX   { fclVipCluElementId }
        ::= { fclVipCluElementTable 1 }


        FclVipCluElementEntry ::=
                SEQUENCE {
                    fclVipCluElementId
                        INTEGER,
                    fclVipCluElemStatus
                        INTEGER,
                    fclVipCluElemLogPortId
                        INTEGER,
                    fclVipCluElemType
                        INTEGER,
                    fclVipCluElemAddress
                        INTEGER,
                    fclVipCluElemCalledAddr
                        OCTET STRING,
                    fclVipCluElemMinRecallTimer
                        INTEGER
                }


    fclVipCluElementId OBJECT-TYPE
        SYNTAX  INTEGER (1..200)
        ACCESS  read-only
        STATUS  mandatory
        DESCRIPTION
                "LP Id"
        ::= { fclVipCluElementEntry 1 }


    fclVipCluElemStatus OBJECT-TYPE
        SYNTAX  INTEGER {
                valid(1),
                invalid(2)
                }
        ACCESS  read-write
        STATUS  mandatory
        DESCRIPTION
                "Status."
        ::= { fclVipCluElementEntry 2 }


    fclVipCluElemLogPortId OBJECT-TYPE
        SYNTAX  INTEGER (0..181)
        ACCESS  read-write
        STATUS  mandatory
        DESCRIPTION
                "LpId. Logical Port Identifier"
        ::= { fclVipCluElementEntry 3 }


    fclVipCluElemType OBJECT-TYPE
        SYNTAX  INTEGER {
                cluster(1),
                isolatedstation(2)
                }
        ACCESS  read-write
        STATUS  mandatory
        DESCRIPTION
                "Element Type. Cluster or Isolated Station."
        ::= { fclVipCluElementEntry 4 }


    fclVipCluElemAddress OBJECT-TYPE
        SYNTAX  INTEGER (0..31)
        ACCESS  read-write
        STATUS  mandatory
        DESCRIPTION
                "Element Address. Vip Adress of the Entity between
                '0' and '31'."
        ::= { fclVipCluElementEntry 5 }


    fclVipCluElemCalledAddr OBJECT-TYPE
        SYNTAX  OCTET STRING (SIZE(8))
        ACCESS  read-write
        STATUS  mandatory
        DESCRIPTION
                "Called X121 address. X121 Address of the
                corresponding Hpad element."
        ::= { fclVipCluElementEntry 10 }


    fclVipCluElemMinRecallTimer OBJECT-TYPE
        SYNTAX  INTEGER (0..990)
        ACCESS  read-write
        STATUS  mandatory
        DESCRIPTION
                "Call Retransmission timing value. If a call fails,
                this timer is started. When it matures, an other
                call is made."
        ::= { fclVipCluElementEntry 11 }


    fclVipCluStationTable OBJECT-TYPE
        SYNTAX  SEQUENCE OF FclVipCluStationEntry
        ACCESS  not-accessible
        STATUS  mandatory
        DESCRIPTION
                ""
        ::= { fclVipClusterLogPort 3 }


    fclVipCluStationEntry OBJECT-TYPE
        SYNTAX  FclVipCluStationEntry
        ACCESS  not-accessible
        STATUS  mandatory
        DESCRIPTION
                "An entry of fclVipCluStationTable."
        INDEX   { fclVipCluStatElementId,
                  fclVipCluStatStationAddress }
        ::= { fclVipCluStationTable 1 }


        FclVipCluStationEntry ::=
                SEQUENCE {
                    fclVipCluStatElementId
                        INTEGER,
                    fclVipCluStatStationAddress
                        INTEGER,
                    fclVipCluStatStatus
                        INTEGER
                }


    fclVipCluStatElementId OBJECT-TYPE
        SYNTAX  INTEGER (1..200)
        ACCESS  read-only
        STATUS  mandatory
        DESCRIPTION
                "Ident Element. The value of this objetc identifies
                one identifiable and addressable entity.
                The possible values are : '0..200'."
        ::= { fclVipCluStationEntry 1 }


    fclVipCluStatStationAddress OBJECT-TYPE
        SYNTAX  INTEGER (0..31)
        ACCESS  read-only
        STATUS  mandatory
        DESCRIPTION
                "Station Address. Vip adress of the cluster defined
                in the  previuos table (case when element
                type=cluster)."
        ::= { fclVipCluStationEntry 2 }


    fclVipCluStatStatus OBJECT-TYPE
        SYNTAX  INTEGER {
                valid(1),
                invalid(2)
                }
        ACCESS  read-write
        STATUS  mandatory
        DESCRIPTION
                "Status."
        ::= { fclVipCluStationEntry 3 }


    fclBsc3270LogPort OBJECT IDENTIFIER ::= { fcLogicalPorts 17 }


    fclB3270LogPortTable OBJECT-TYPE
        SYNTAX  SEQUENCE OF FclB3270LogPortEntry
        ACCESS  not-accessible
        STATUS  mandatory
        DESCRIPTION
                ""
        ::= { fclBsc3270LogPort 1 }


    fclB3270LogPortEntry OBJECT-TYPE
        SYNTAX  FclB3270LogPortEntry
        ACCESS  not-accessible
        STATUS  mandatory
        DESCRIPTION
                "An entry of fclB3270LogPortTable."
        INDEX   { fclB3270LpLogPortId }
        ::= { fclB3270LogPortTable 1 }


        FclB3270LogPortEntry ::=
                SEQUENCE {
                    fclB3270LpLogPortId
                        INTEGER,
                    fclB3270LpInterfaceId
                        INTEGER,
                    fclB3270LpEmulationType
                        INTEGER,
                    fclB3270LpCodingParityType
                        INTEGER,
                    fclB3270LpNoAnswerWatchDog
                        INTEGER,
                    fclB3270LpMessageRetryNumber
                        INTEGER
                }


    fclB3270LpLogPortId OBJECT-TYPE
        SYNTAX  INTEGER (0..181)
        ACCESS  read-only
        STATUS  mandatory
        DESCRIPTION
                "LP Id"
        ::= { fclB3270LogPortEntry 1 }


    fclB3270LpInterfaceId OBJECT-TYPE
        SYNTAX  INTEGER (0..35)
        ACCESS  read-write
        STATUS  mandatory
        DESCRIPTION
                "IF Id (type ligne)"
        ::= { fclB3270LogPortEntry 2 }


    fclB3270LpEmulationType OBJECT-TYPE
        SYNTAX  INTEGER {
                tpad(60),
                hpad(61)
                }
        ACCESS  read-write
        STATUS  mandatory
        DESCRIPTION
                "Type d'emulation"
        ::= { fclB3270LogPortEntry 3 }


    fclB3270LpCodingParityType OBJECT-TYPE
        SYNTAX  INTEGER {
                ebcdic(1),
                asciioddparity(2)
                }
        ACCESS  read-write
        STATUS  mandatory
        DESCRIPTION
                "Type de codage parite"
        ::= { fclB3270LogPortEntry 4 }


    fclB3270LpNoAnswerWatchDog OBJECT-TYPE
        SYNTAX  INTEGER (100..25000)
        ACCESS  read-write
        STATUS  mandatory
        DESCRIPTION
                "Temporisation de non reponse"
        ::= { fclB3270LogPortEntry 5 }


    fclB3270LpMessageRetryNumber OBJECT-TYPE
        SYNTAX  INTEGER (1..20)
        ACCESS  read-write
        STATUS  mandatory
        DESCRIPTION
                "Nombre de reemission de message"
        ::= { fclB3270LogPortEntry 6 }


    fclB3270HostPadLogPort OBJECT IDENTIFIER ::= { fclBsc3270LogPort 2 }


    fclB3270HosLogPortTable OBJECT-TYPE
        SYNTAX  SEQUENCE OF FclB3270HosLogPortEntry
        ACCESS  not-accessible
        STATUS  mandatory
        DESCRIPTION
                ""
        ::= { fclB3270HostPadLogPort 1 }


    fclB3270HosLogPortEntry OBJECT-TYPE
        SYNTAX  FclB3270HosLogPortEntry
        ACCESS  not-accessible
        STATUS  mandatory
        DESCRIPTION
                "An entry of fclB3270HosLogPortTable."
        INDEX   { fclB3270HosLpLogPortId }
        ::= { fclB3270HosLogPortTable 1 }


        FclB3270HosLogPortEntry ::=
                SEQUENCE {
                    fclB3270HosLpLogPortId
                        INTEGER,
                    fclB3270HosLpLineWatchDog
                        INTEGER,
                    fclB3270HosLpWackTransmission
                        INTEGER,
                    fclB3270HosLpAnswerToPolling
                        INTEGER
                }


    fclB3270HosLpLogPortId OBJECT-TYPE
        SYNTAX  INTEGER (0..181)
        ACCESS  read-only
        STATUS  mandatory
        DESCRIPTION
                "LP Id"
        ::= { fclB3270HosLogPortEntry 1 }


    fclB3270HosLpLineWatchDog OBJECT-TYPE
        SYNTAX  INTEGER (10..2500)
        ACCESS  read-write
        STATUS  mandatory
        DESCRIPTION
                "Tempo de surveillance de ligne"
        ::= { fclB3270HosLogPortEntry 2 }


    fclB3270HosLpWackTransmission OBJECT-TYPE
        SYNTAX  INTEGER {
                no(1),
                yes(2)
                }
        ACCESS  read-write
        STATUS  mandatory
        DESCRIPTION
                "Emission WACK"
        ::= { fclB3270HosLogPortEntry 3 }


    fclB3270HosLpAnswerToPolling OBJECT-TYPE
        SYNTAX  INTEGER {
                always(1),
                onlinkup(2)
                }
        ACCESS  read-write
        STATUS  mandatory
        DESCRIPTION
                "Reponse au poll systematique"
        ::= { fclB3270HosLogPortEntry 4 }


    fclB3270HosClusterTable OBJECT-TYPE
        SYNTAX  SEQUENCE OF FclB3270HosClusterEntry
        ACCESS  not-accessible
        STATUS  mandatory
        DESCRIPTION
                ""
        ::= { fclB3270HostPadLogPort 2 }


    fclB3270HosClusterEntry OBJECT-TYPE
        SYNTAX  FclB3270HosClusterEntry
        ACCESS  not-accessible
        STATUS  mandatory
        DESCRIPTION
                "An entry of fclB3270HosClusterTable."
        INDEX   { fclB3270HosClusterLogPortId,
                  fclB3270HosClusterCluAdd,
                  fclB3270HosClusterStaAdd }
        ::= { fclB3270HosClusterTable 1 }


        FclB3270HosClusterEntry ::=
                SEQUENCE {
                    fclB3270HosClusterLogPortId
                        INTEGER,
                    fclB3270HosClusterCluAdd
                        INTEGER,
                    fclB3270HosClusterStaAdd
                        INTEGER,
                    fclB3270HosClusterStatus
                        INTEGER
                }


    fclB3270HosClusterLogPortId OBJECT-TYPE
        SYNTAX  INTEGER (0..181)
        ACCESS  read-only
        STATUS  mandatory
        DESCRIPTION
                "LP Id"
        ::= { fclB3270HosClusterEntry 1 }


    fclB3270HosClusterCluAdd OBJECT-TYPE
        SYNTAX  INTEGER (0..31)
        ACCESS  read-only
        STATUS  mandatory
        DESCRIPTION
                "Adresse du cluster"
        ::= { fclB3270HosClusterEntry 2 }


    fclB3270HosClusterStaAdd OBJECT-TYPE
        SYNTAX  INTEGER (0..31)
        ACCESS  read-write
        STATUS  mandatory
        DESCRIPTION
                "Adresse station"
        ::= { fclB3270HosClusterEntry 3 }


    fclB3270HosClusterStatus OBJECT-TYPE
        SYNTAX  INTEGER {
                valid(1),
                invalid(2)
                }
        ACCESS  read-write
        STATUS  mandatory
        DESCRIPTION
                "Status"
        ::= { fclB3270HosClusterEntry 4 }


    fclB3270ClusterLogPort OBJECT IDENTIFIER ::= { fclBsc3270LogPort 3 }


    fclB3270CluLogPortTable OBJECT-TYPE
        SYNTAX  SEQUENCE OF FclB3270CluLogPortEntry
        ACCESS  not-accessible
        STATUS  mandatory
        DESCRIPTION
                ""
        ::= { fclB3270ClusterLogPort 1 }


    fclB3270CluLogPortEntry OBJECT-TYPE
        SYNTAX  FclB3270CluLogPortEntry
        ACCESS  not-accessible
        STATUS  mandatory
        DESCRIPTION
                "An entry of fclB3270CluLogPortTable."
        INDEX   { fclB3270CluLpLogPortId }
        ::= { fclB3270CluLogPortTable 1 }


        FclB3270CluLogPortEntry ::=
                SEQUENCE {
                    fclB3270CluLpLogPortId
                        INTEGER,
                    fclB3270CluLpPollingTimer
                        INTEGER,
                    fclB3270CluLpMaxNumberOfUnwPolls
                        INTEGER,
                    fclB3270CluLpReconnectionType
                        INTEGER
                }


    fclB3270CluLpLogPortId OBJECT-TYPE
        SYNTAX  INTEGER (0..181)
        ACCESS  read-only
        STATUS  mandatory
        DESCRIPTION
                "LP Id"
        ::= { fclB3270CluLogPortEntry 1 }


    fclB3270CluLpPollingTimer OBJECT-TYPE
        SYNTAX  INTEGER (100..25000)
        ACCESS  read-write
        STATUS  mandatory
        DESCRIPTION
                "Temporisation d'interpolling"
        ::= { fclB3270CluLogPortEntry 10 }


    fclB3270CluLpMaxNumberOfUnwPolls OBJECT-TYPE
        SYNTAX  INTEGER (1..20)
        ACCESS  read-write
        STATUS  mandatory
        DESCRIPTION
                "Nombre maximum de non reponse au polling"
        ::= { fclB3270CluLogPortEntry 11 }


    fclB3270CluLpReconnectionType OBJECT-TYPE
        SYNTAX  INTEGER {
                automatic(1),
                ondata(2)
                }
        ACCESS  read-write
        STATUS  mandatory
        DESCRIPTION
                "Type de reconnexion "
        ::= { fclB3270CluLogPortEntry 12 }


    fclB3270CluClusterTable OBJECT-TYPE
        SYNTAX  SEQUENCE OF FclB3270CluClusterEntry
        ACCESS  not-accessible
        STATUS  mandatory
        DESCRIPTION
                ""
        ::= { fclB3270ClusterLogPort 2 }


    fclB3270CluClusterEntry OBJECT-TYPE
        SYNTAX  FclB3270CluClusterEntry
        ACCESS  not-accessible
        STATUS  mandatory
        DESCRIPTION
                "An entry of fclB3270CluClusterTable."
        INDEX   { fclB3270CluClusterLogPortId,
                  fclB3270CluClusterCluAdd,
                  fclB3270CluClusterStaAdd }
        ::= { fclB3270CluClusterTable 1 }


        FclB3270CluClusterEntry ::=
                SEQUENCE {
                    fclB3270CluClusterLogPortId
                        INTEGER,
                    fclB3270CluClusterCluAdd
                        INTEGER,
                    fclB3270CluClusterStaAdd
                        INTEGER,
                    fclB3270CluClusterStatus
                        INTEGER
                }


    fclB3270CluClusterLogPortId OBJECT-TYPE
        SYNTAX  INTEGER (0..181)
        ACCESS  read-only
        STATUS  mandatory
        DESCRIPTION
                "LP Id"
        ::= { fclB3270CluClusterEntry 1 }


    fclB3270CluClusterCluAdd OBJECT-TYPE
        SYNTAX  INTEGER (0..31)
        ACCESS  read-only
        STATUS  mandatory
        DESCRIPTION
                "Adresse du cluster"
        ::= { fclB3270CluClusterEntry 2 }


    fclB3270CluClusterStaAdd OBJECT-TYPE
        SYNTAX  INTEGER (0..31)
        ACCESS  read-write
        STATUS  mandatory
        DESCRIPTION
                "Adresse station"
        ::= { fclB3270CluClusterEntry 3 }


    fclB3270CluClusterStatus OBJECT-TYPE
        SYNTAX  INTEGER {
                valid(1),
                invalid(2)
                }
        ACCESS  read-write
        STATUS  mandatory
        DESCRIPTION
                "Status"
        ::= { fclB3270CluClusterEntry 4 }


    fclB3270CluCallTable OBJECT-TYPE
        SYNTAX  SEQUENCE OF FclB3270CluCallEntry
        ACCESS  not-accessible
        STATUS  mandatory
        DESCRIPTION
                ""
        ::= { fclB3270ClusterLogPort 3 }


    fclB3270CluCallEntry OBJECT-TYPE
        SYNTAX  FclB3270CluCallEntry
        ACCESS  not-accessible
        STATUS  mandatory
        DESCRIPTION
                "An entry of fclB3270CluCallTable."
        INDEX   { fclB3270CluCallLogPortId,
                  fclB3270CluCallCluAdd }
        ::= { fclB3270CluCallTable 1 }


        FclB3270CluCallEntry ::=
                SEQUENCE {
                    fclB3270CluCallLogPortId
                        INTEGER,
                    fclB3270CluCallCluAdd
                        INTEGER,
                    fclB3270CluCallStatus
                        INTEGER,
                    fclB3270CluCallCallAddr
                        OCTET STRING,
                    fclB3270CluCallMinRecallTimer
                        INTEGER
                }


    fclB3270CluCallLogPortId OBJECT-TYPE
        SYNTAX  INTEGER (0..181)
        ACCESS  read-only
        STATUS  mandatory
        DESCRIPTION
                "LP Id"
        ::= { fclB3270CluCallEntry 1 }


    fclB3270CluCallCluAdd OBJECT-TYPE
        SYNTAX  INTEGER (0..31)
        ACCESS  read-only
        STATUS  mandatory
        DESCRIPTION
                "Adresse du cluster"
        ::= { fclB3270CluCallEntry 2 }


    fclB3270CluCallStatus OBJECT-TYPE
        SYNTAX  INTEGER {
                valid(1),
                invalid(2)
                }
        ACCESS  read-write
        STATUS  mandatory
        DESCRIPTION
                "Status"
        ::= { fclB3270CluCallEntry 3 }


    fclB3270CluCallCallAddr OBJECT-TYPE
        SYNTAX  OCTET STRING (SIZE(8))
        ACCESS  read-write
        STATUS  mandatory
        DESCRIPTION
                "Adresse X121 appelee"
        ::= { fclB3270CluCallEntry 5 }


    fclB3270CluCallMinRecallTimer OBJECT-TYPE
        SYNTAX  INTEGER (0..990)
        ACCESS  read-write
        STATUS  mandatory
        DESCRIPTION
                "Tempo de retransmission d'appel"
        ::= { fclB3270CluCallEntry 10 }


    fclBscX780LogPort OBJECT IDENTIFIER ::= { fcLogicalPorts 18 }


    fclBX780LogPortTable OBJECT-TYPE
        SYNTAX  SEQUENCE OF FclBX780LogPortEntry
        ACCESS  not-accessible
        STATUS  mandatory
        DESCRIPTION
                ""
        ::= { fclBscX780LogPort 1 }


    fclBX780LogPortEntry OBJECT-TYPE
        SYNTAX  FclBX780LogPortEntry
        ACCESS  not-accessible
        STATUS  mandatory
        DESCRIPTION
                "An entry of fclBX780LogPortTable."
        INDEX   { fclBX780LpLogPortId }
        ::= { fclBX780LogPortTable 1 }


        FclBX780LogPortEntry ::=
                SEQUENCE {
                    fclBX780LpLogPortId
                        INTEGER,
                    fclBX780LpInterfaceId
                        INTEGER,
                    fclBX780LpProtocolType
                        INTEGER,
                    fclBX780LpCallDirection
                        INTEGER,
                    fclBX780LpDeconnectTimer
                        INTEGER,
                    fclBX780LpSurveyTimer
                        INTEGER,
                    fclBX780LpCodingParityType
                        INTEGER,
                    fclBX780LpEquipementType
                        INTEGER,
                    fclBX780LpENQRetransTimer
                        INTEGER,
                    fclBX780LpAuthorAnswerTimer
                        INTEGER,
                    fclBX780LpNoAnswerWatchDog
                        INTEGER,
                    fclBX780LpMessageRetryNumber
                        INTEGER
                }


    fclBX780LpLogPortId OBJECT-TYPE
        SYNTAX  INTEGER (0..181)
        ACCESS  read-only
        STATUS  mandatory
        DESCRIPTION
                "LP Id"
        ::= { fclBX780LogPortEntry 1 }


    fclBX780LpInterfaceId OBJECT-TYPE
        SYNTAX  INTEGER (0..35)
        ACCESS  read-write
        STATUS  mandatory
        DESCRIPTION
                "IF Id (type ligne)"
        ::= { fclBX780LogPortEntry 2 }


    fclBX780LpProtocolType OBJECT-TYPE
        SYNTAX  INTEGER {
                bsc2780(1),
                bsc3780(2),
                bsc3780onPSTN(3)
                }
        ACCESS  read-write
        STATUS  mandatory
        DESCRIPTION
                "Type de BSC"
        ::= { fclBX780LogPortEntry 3 }


    fclBX780LpCallDirection OBJECT-TYPE
        SYNTAX  INTEGER {
                calling(1),
                called(2)
                }
        ACCESS  read-write
        STATUS  mandatory
        DESCRIPTION
                "Mode d'appel"
        ::= { fclBX780LogPortEntry 4 }


    fclBX780LpDeconnectTimer OBJECT-TYPE
        SYNTAX  INTEGER (0..2500)
        ACCESS  read-write
        STATUS  mandatory
        DESCRIPTION
                "Tempo de deconnexion"
        ::= { fclBX780LogPortEntry 5 }


    fclBX780LpSurveyTimer OBJECT-TYPE
        SYNTAX  INTEGER (0..2500)
        ACCESS  read-write
        STATUS  mandatory
        DESCRIPTION
                "Tempo de surveillance"
        ::= { fclBX780LogPortEntry 6 }


    fclBX780LpCodingParityType OBJECT-TYPE
        SYNTAX  INTEGER {
                ebcdic(1),
                asciioddparity(2)
                }
        ACCESS  read-write
        STATUS  mandatory
        DESCRIPTION
                "Type de codage parite"
        ::= { fclBX780LogPortEntry 7 }


    fclBX780LpEquipementType OBJECT-TYPE
        SYNTAX  INTEGER {
                term-term(1),
                term-cpu(2),
                cpu-cpu(3),
                cpu-term(4)
                }
        ACCESS  read-write
        STATUS  mandatory
        DESCRIPTION
                "Type de couple"
        ::= { fclBX780LogPortEntry 8 }


    fclBX780LpENQRetransTimer OBJECT-TYPE
        SYNTAX  INTEGER (100..25000)
        ACCESS  read-write
        STATUS  mandatory
        DESCRIPTION
                "Tempo de retransmission du ENQ"
        ::= { fclBX780LogPortEntry 9 }


    fclBX780LpAuthorAnswerTimer OBJECT-TYPE
        SYNTAX  INTEGER (100..25000)
        ACCESS  read-write
        STATUS  mandatory
        DESCRIPTION
                "Tempo  de  reponse   auteur"
        ::= { fclBX780LogPortEntry 10 }


    fclBX780LpNoAnswerWatchDog OBJECT-TYPE
        SYNTAX  INTEGER (100..25000)
        ACCESS  read-write
        STATUS  mandatory
        DESCRIPTION
                "Temporisation de non reponse"
        ::= { fclBX780LogPortEntry 11 }


    fclBX780LpMessageRetryNumber OBJECT-TYPE
        SYNTAX  INTEGER (1..20)
        ACCESS  read-write
        STATUS  mandatory
        DESCRIPTION
                "Nombre de reemission de message"
        ::= { fclBX780LogPortEntry 12 }


    fclBX780ConnectionTable OBJECT-TYPE
        SYNTAX  SEQUENCE OF FclBX780ConnectionEntry
        ACCESS  not-accessible
        STATUS  mandatory
        DESCRIPTION
                ""
        ::= { fclBscX780LogPort 2 }


    fclBX780ConnectionEntry OBJECT-TYPE
        SYNTAX  FclBX780ConnectionEntry
        ACCESS  not-accessible
        STATUS  mandatory
        DESCRIPTION
                "An entry of fclBX780ConnectionTable."
        INDEX   { fclBX780ConnLogPortId }
        ::= { fclBX780ConnectionTable 1 }


        FclBX780ConnectionEntry ::=
                SEQUENCE {
                    fclBX780ConnLogPortId
                        INTEGER,
                    fclBX780ConnCalledAddr
                        OCTET STRING,
                    fclBX780ConnMinimumRecallTimer
                        INTEGER
                }


    fclBX780ConnLogPortId OBJECT-TYPE
        SYNTAX  INTEGER (0..181)
        ACCESS  read-only
        STATUS  mandatory
        DESCRIPTION
                "LP Id"
        ::= { fclBX780ConnectionEntry 1 }


    fclBX780ConnCalledAddr OBJECT-TYPE
        SYNTAX  OCTET STRING (SIZE(8))
        ACCESS  read-write
        STATUS  mandatory
        DESCRIPTION
                "WAN adresse appelee"
        ::= { fclBX780ConnectionEntry 2 }


    fclBX780ConnMinimumRecallTimer OBJECT-TYPE
        SYNTAX  INTEGER (0..990)
        ACCESS  read-write
        STATUS  mandatory
        DESCRIPTION
                "Tempo de retransmission d'appel"
        ::= { fclBX780ConnectionEntry 3 }


    fclBX780IdentTable OBJECT-TYPE
        SYNTAX  SEQUENCE OF FclBX780IdentEntry
        ACCESS  not-accessible
        STATUS  mandatory
        DESCRIPTION
                ""
        ::= { fclBscX780LogPort 3 }


    fclBX780IdentEntry OBJECT-TYPE
        SYNTAX  FclBX780IdentEntry
        ACCESS  not-accessible
        STATUS  mandatory
        DESCRIPTION
                "An entry of fclBX780IdentTable."
        INDEX   { fclBX780IdentLogPortId,
                  fclBX780IdentTermId }
        ::= { fclBX780IdentTable 1 }


        FclBX780IdentEntry ::=
                SEQUENCE {
                    fclBX780IdentLogPortId
                        INTEGER,
                    fclBX780IdentTermId
                        OCTET STRING,
                    fclBX780IdentStatus
                        INTEGER
                }


    fclBX780IdentLogPortId OBJECT-TYPE
        SYNTAX  INTEGER (0..181)
        ACCESS  read-only
        STATUS  mandatory
        DESCRIPTION
                "LP Id"
        ::= { fclBX780IdentEntry 1 }


    fclBX780IdentTermId OBJECT-TYPE
        SYNTAX  OCTET STRING (SIZE(4))
        ACCESS  read-only
        STATUS  mandatory
        DESCRIPTION
                "Ident du terminal"
        ::= { fclBX780IdentEntry 2 }


    fclBX780IdentStatus OBJECT-TYPE
        SYNTAX  INTEGER {
                valid(1),
                invalid(2)
                }
        ACCESS  read-write
        STATUS  mandatory
        DESCRIPTION
                "Status"
        ::= { fclBX780IdentEntry 3 }


    fclBscSctLogPort OBJECT IDENTIFIER ::= { fcLogicalPorts 19 }


    fclBSctLogPortTable OBJECT-TYPE
        SYNTAX  SEQUENCE OF FclBSctLogPortEntry
        ACCESS  not-accessible
        STATUS  mandatory
        DESCRIPTION
                ""
        ::= { fclBscSctLogPort 1 }


    fclBSctLogPortEntry OBJECT-TYPE
        SYNTAX  FclBSctLogPortEntry
        ACCESS  not-accessible
        STATUS  mandatory
        DESCRIPTION
                "An entry of fclBSctLogPortTable."
        INDEX   { fclBSctLpLogPortId }
        ::= { fclBSctLogPortTable 1 }


        FclBSctLogPortEntry ::=
                SEQUENCE {
                    fclBSctLpLogPortId
                        INTEGER,
                    fclBSctLpInterfaceId
                        INTEGER,
                    fclBSctLpLinkType
                        INTEGER,
                    fclBSctLpNumberOfSYN
                        INTEGER,
                    fclBSctLpSignalEnvelope
                        INTEGER,
                    fclBSctLpCodingParityType
                        INTEGER,
                    fclBSctLpMaxFrameNumberIn
                        INTEGER,
                    fclBSctLpUnderrunManagement
                        INTEGER,
                    fclBSctLpOnePadSuppressed
                        INTEGER
                }


    fclBSctLpLogPortId OBJECT-TYPE
        SYNTAX  INTEGER (0..181)
        ACCESS  read-only
        STATUS  mandatory
        DESCRIPTION
                "LP Id"
        ::= { fclBSctLogPortEntry 1 }


    fclBSctLpInterfaceId OBJECT-TYPE
        SYNTAX  INTEGER (0..35)
        ACCESS  read-write
        STATUS  mandatory
        DESCRIPTION
                "IF Id (type ligne)"
        ::= { fclBSctLogPortEntry 2 }


    fclBSctLpLinkType OBJECT-TYPE
        SYNTAX  INTEGER {
                dte(1),
                dce(2),
                tpc(3)
                }
        ACCESS  read-write
        STATUS  mandatory
        DESCRIPTION
                "Type de liaison"
        ::= { fclBSctLogPortEntry 3 }


    fclBSctLpNumberOfSYN OBJECT-TYPE
        SYNTAX  INTEGER {
                trans-of-2-SYN(2),
                trans-of-4-SYN(4)
                }
        ACCESS  read-write
        STATUS  mandatory
        DESCRIPTION
                "Nombre  de  SYN avant la trame"
        ::= { fclBSctLogPortEntry 4 }


    fclBSctLpSignalEnvelope OBJECT-TYPE
        SYNTAX  INTEGER {
                off(1),
                on(2)
                }
        ACCESS  read-write
        STATUS  mandatory
        DESCRIPTION
                "Enveloppe de trame"
        ::= { fclBSctLogPortEntry 5 }


    fclBSctLpCodingParityType OBJECT-TYPE
        SYNTAX  INTEGER {
                ebcdic(1),
                asciioddparity(2)
                }
        ACCESS  read-write
        STATUS  mandatory
        DESCRIPTION
                "Type de codage parite"
        ::= { fclBSctLogPortEntry 6 }


    fclBSctLpMaxFrameNumberIn OBJECT-TYPE
        SYNTAX  INTEGER (0..254)
        ACCESS  read-write
        STATUS  mandatory
        DESCRIPTION
                "Nombre de trame acceptee en entree"
        ::= { fclBSctLogPortEntry 7 }


    fclBSctLpUnderrunManagement OBJECT-TYPE
        SYNTAX  INTEGER {
                off(1),
                on(2)
                }
        ACCESS  read-write
        STATUS  mandatory
        DESCRIPTION
                "Gestion    de   l    underrun"
        ::= { fclBSctLogPortEntry 8 }


    fclBSctLpOnePadSuppressed OBJECT-TYPE
        SYNTAX  INTEGER {
                off(1),
                on(2)
                }
        ACCESS  read-write
        STATUS  mandatory
        DESCRIPTION
                "Suppression d un pad"
        ::= { fclBSctLogPortEntry 9 }


    fclBSctConnectionTable OBJECT-TYPE
        SYNTAX  SEQUENCE OF FclBSctConnectionEntry
        ACCESS  not-accessible
        STATUS  mandatory
        DESCRIPTION
                ""
        ::= { fclBscSctLogPort 2 }


    fclBSctConnectionEntry OBJECT-TYPE
        SYNTAX  FclBSctConnectionEntry
        ACCESS  not-accessible
        STATUS  mandatory
        DESCRIPTION
                "An entry of fclBSctConnectionTable."
        INDEX   { fclBSctConnLogPortId }
        ::= { fclBSctConnectionTable 1 }


        FclBSctConnectionEntry ::=
                SEQUENCE {
                    fclBSctConnLogPortId
                        INTEGER,
                    fclBSctConnCalledAddr
                        OCTET STRING,
                    fclBSctConnCallDirection
                        INTEGER,
                    fclBSctConnSubscriberNumber
                        INTEGER,
                    fclBSctConnMinimumRecallTimer
                        INTEGER
                }


    fclBSctConnLogPortId OBJECT-TYPE
        SYNTAX  INTEGER (0..181)
        ACCESS  read-only
        STATUS  mandatory
        DESCRIPTION
                "LP Id"
        ::= { fclBSctConnectionEntry 1 }


    fclBSctConnCalledAddr OBJECT-TYPE
        SYNTAX  OCTET STRING (SIZE(8))
        ACCESS  read-write
        STATUS  mandatory
        DESCRIPTION
                "WAN adresse appele"
        ::= { fclBSctConnectionEntry 2 }


    fclBSctConnCallDirection OBJECT-TYPE
        SYNTAX  INTEGER {
                calling(1),
                called(2),
                auto(3),
                datagram(4)
                }
        ACCESS  read-write
        STATUS  mandatory
        DESCRIPTION
                "Mode d appel"
        ::= { fclBSctConnectionEntry 3 }


    fclBSctConnSubscriberNumber OBJECT-TYPE
        SYNTAX  INTEGER (0..9999)
        ACCESS  read-write
        STATUS  mandatory
        DESCRIPTION
                "Numero d'abonne"
        ::= { fclBSctConnectionEntry 4 }


    fclBSctConnMinimumRecallTimer OBJECT-TYPE
        SYNTAX  INTEGER (0..990)
        ACCESS  read-write
        STATUS  mandatory
        DESCRIPTION
                "Tempo de retransmission d'appel"
        ::= { fclBSctConnectionEntry 5 }


    fclBSctProtocolDefinition1Table OBJECT-TYPE
        SYNTAX  SEQUENCE OF FclBSctProtocolDefinition1Entry
        ACCESS  not-accessible
        STATUS  mandatory
        DESCRIPTION
                ""
        ::= { fclBscSctLogPort 3 }


    fclBSctProtocolDefinition1Entry OBJECT-TYPE
        SYNTAX  FclBSctProtocolDefinition1Entry
        ACCESS  not-accessible
        STATUS  mandatory
        DESCRIPTION
                "An entry of fclBSctProtocolDefinition1Table."
        INDEX   { fclBSctProtDef1LogPortId }
        ::= { fclBSctProtocolDefinition1Table 1 }


        FclBSctProtocolDefinition1Entry ::=
                SEQUENCE {
                    fclBSctProtDef1LogPortId
                        INTEGER,
                    fclBSctProtDef1PermanentDelimiter1
                        INTEGER,
                    fclBSctProtDef1PermanentDelimiter2
                        INTEGER,
                    fclBSctProtDef1PermanentDelimiter3
                        INTEGER,
                    fclBSctProtDef1PermanentDelimiter4
                        INTEGER,
                    fclBSctProtDef1PermanentDelimiter5
                        INTEGER,
                    fclBSctProtDef1StartFrameDelimiter1
                        INTEGER,
                    fclBSctProtDef1StartFrameDelimiter2
                        INTEGER,
                    fclBSctProtDef1StartFrameDelimiter3
                        INTEGER,
                    fclBSctProtDef1NbCharInhibited
                        INTEGER,
                    fclBSctProtDef1StFrDelimiterInhib1
                        INTEGER,
                    fclBSctProtDef1StFrDelimiterInhib2
                        INTEGER
                }


    fclBSctProtDef1LogPortId OBJECT-TYPE
        SYNTAX  INTEGER (0..181)
        ACCESS  read-only
        STATUS  mandatory
        DESCRIPTION
                "LP Id"
        ::= { fclBSctProtocolDefinition1Entry 1 }


    fclBSctProtDef1PermanentDelimiter1 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "1 e Delimiteur Permanent"
        ::= { fclBSctProtocolDefinition1Entry 2 }


    fclBSctProtDef1PermanentDelimiter2 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "2 e Delimiteur Permanent"
        ::= { fclBSctProtocolDefinition1Entry 3 }


    fclBSctProtDef1PermanentDelimiter3 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "3 e Delimiteur Permanent"
        ::= { fclBSctProtocolDefinition1Entry 4 }


    fclBSctProtDef1PermanentDelimiter4 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "4 e Delimiteur Permanent"
        ::= { fclBSctProtocolDefinition1Entry 5 }


    fclBSctProtDef1PermanentDelimiter5 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "5 e Delimiteur Permanent"
        ::= { fclBSctProtocolDefinition1Entry 6 }


    fclBSctProtDef1StartFrameDelimiter1 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "1 e delimiteur de debut de trame"
        ::= { fclBSctProtocolDefinition1Entry 7 }


    fclBSctProtDef1StartFrameDelimiter2 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "2 e delimiteur de debut de trame"
        ::= { fclBSctProtocolDefinition1Entry 8 }


    fclBSctProtDef1StartFrameDelimiter3 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "3 e delimiteur de debut de trame"
        ::= { fclBSctProtocolDefinition1Entry 9 }


    fclBSctProtDef1NbCharInhibited OBJECT-TYPE
        SYNTAX  INTEGER (0..10)
        ACCESS  read-write
        STATUS  mandatory
        DESCRIPTION
                "nombre de caracteres a iniber"
        ::= { fclBSctProtocolDefinition1Entry 10 }


    fclBSctProtDef1StFrDelimiterInhib1 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "1 e delimiteur de debut de trame avec inibition"
        ::= { fclBSctProtocolDefinition1Entry 11 }


    fclBSctProtDef1StFrDelimiterInhib2 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "2 e delimiteur de debut de trame avec inibition"
        ::= { fclBSctProtocolDefinition1Entry 12 }


    fclBSctProtocolDefinition2Table OBJECT-TYPE
        SYNTAX  SEQUENCE OF FclBSctProtocolDefinition2Entry
        ACCESS  not-accessible
        STATUS  mandatory
        DESCRIPTION
                ""
        ::= { fclBscSctLogPort 4 }


    fclBSctProtocolDefinition2Entry OBJECT-TYPE
        SYNTAX  FclBSctProtocolDefinition2Entry
        ACCESS  not-accessible
        STATUS  mandatory
        DESCRIPTION
                "An entry of fclBSctProtocolDefinition2Table."
        INDEX   { fclBSctProtDef2LogPortId }
        ::= { fclBSctProtocolDefinition2Table 1 }


        FclBSctProtocolDefinition2Entry ::=
                SEQUENCE {
                    fclBSctProtDef2LogPortId
                        INTEGER,
                    fclBSctProtDef2DataFrameTerminator1
                        INTEGER,
                    fclBSctProtDef2DataFrameTerminator2
                        INTEGER,
                    fclBSctProtDef2DataFrameTerminator3
                        INTEGER,
                    fclBSctProtDef2ControlFrameTerminator1
                        INTEGER,
                    fclBSctProtDef2ControlFrameTerminator2
                        INTEGER,
                    fclBSctProtDef2ACK0
                        INTEGER,
                    fclBSctProtDef2ACK1
                        INTEGER,
                    fclBSctProtDef2WACK
                        INTEGER,
                    fclBSctProtDef2RVI
                        INTEGER,
                    fclBSctProtDef2WABT
                        INTEGER
                }


    fclBSctProtDef2LogPortId OBJECT-TYPE
        SYNTAX  INTEGER (0..181)
        ACCESS  read-only
        STATUS  mandatory
        DESCRIPTION
                "LP Id"
        ::= { fclBSctProtocolDefinition2Entry 1 }


    fclBSctProtDef2DataFrameTerminator1 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "1 e Terminateur de trame de donnees"
        ::= { fclBSctProtocolDefinition2Entry 2 }


    fclBSctProtDef2DataFrameTerminator2 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "2 e Terminateur de trame de donnees"
        ::= { fclBSctProtocolDefinition2Entry 3 }


    fclBSctProtDef2DataFrameTerminator3 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "3 e Terminateur de trame de donnees"
        ::= { fclBSctProtocolDefinition2Entry 4 }


    fclBSctProtDef2ControlFrameTerminator1 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "1 e Terminateur de trame de controle"
        ::= { fclBSctProtocolDefinition2Entry 5 }


    fclBSctProtDef2ControlFrameTerminator2 OBJECT-TYPE
        SYNTAX  INTEGER {
                none(1),
                enq(2),
                nak(3),
                eot(4),
                stx(5),
                soh(6),
                etx(7),
                etb(8),
                pad(9),
                ack(10),
                dle(11),
                esc(12),
                bel(13)
                }
        ACCESS  read-write
        STATUS  mandatory
        DESCRIPTION
                "2 e Terminateur de trame de controle"
        ::= { fclBSctProtocolDefinition2Entry 6 }


    fclBSctProtDef2ACK0 OBJECT-TYPE
        SYNTAX  INTEGER {
                no(1),
                yes(2)
                }
        ACCESS  read-write
        STATUS  mandatory
        DESCRIPTION
                "ACK0"
        ::= { fclBSctProtocolDefinition2Entry 7 }


    fclBSctProtDef2ACK1 OBJECT-TYPE
        SYNTAX  INTEGER {
                no(1),
                yes(2)
                }
        ACCESS  read-write
        STATUS  mandatory
        DESCRIPTION
                "ACK1"
        ::= { fclBSctProtocolDefinition2Entry 8 }


    fclBSctProtDef2WACK OBJECT-TYPE
        SYNTAX  INTEGER {
                no(1),
                yes(2)
                }
        ACCESS  read-write
        STATUS  mandatory
        DESCRIPTION
                "WACK"
        ::= { fclBSctProtocolDefinition2Entry 9 }


    fclBSctProtDef2RVI OBJECT-TYPE
        SYNTAX  INTEGER {
                no(1),
                yes(2)
                }
        ACCESS  read-write
        STATUS  mandatory
        DESCRIPTION
                "RVI"
        ::= { fclBSctProtocolDefinition2Entry 10 }


    fclBSctProtDef2WABT OBJECT-TYPE
        SYNTAX  INTEGER {
                no(1),
                yes(2)
                }
        ACCESS  read-write
        STATUS  mandatory
        DESCRIPTION
                "WABT"
        ::= { fclBSctProtocolDefinition2Entry 11 }


    fclX25SlpAccess OBJECT IDENTIFIER ::= { fcLogicalPorts 20 }


    fclX25SlpAccessTable OBJECT-TYPE
        SYNTAX  SEQUENCE OF FclX25SlpAccessEntry
        ACCESS  not-accessible
        STATUS  mandatory
        DESCRIPTION
                "This table defines the general parameters of X25
                SLP (Single Link Protocol) access logical ports."
        ::= { fclX25SlpAccess 1 }


    fclX25SlpAccessEntry OBJECT-TYPE
        SYNTAX  FclX25SlpAccessEntry
        ACCESS  not-accessible
        STATUS  mandatory
        DESCRIPTION
                "An entry of fclX25SlpAccessTable."
        INDEX   { fclX25AccLogPortId }
        ::= { fclX25SlpAccessTable 1 }


        FclX25SlpAccessEntry ::=
                SEQUENCE {
                    fclX25AccLogPortId
                        INTEGER,
                    fclX25AccInterfaceId
                        INTEGER,
                    fclX25AccConnectionType
                        INTEGER,
                    fclX25AccSubscriberNumber
                        OCTET STRING,
                    fclX25AccPdnLinkAddress
                        OCTET STRING,
                    fclX25AccX25AccessConfigId
                        INTEGER,
                    fclX25AccIsdnBackupEnabling
                        INTEGER,
                    fclX25AccPstnBackupEnabling
                        INTEGER
                }


    fclX25AccLogPortId OBJECT-TYPE
        SYNTAX  INTEGER (0..181)
        ACCESS  read-only
        STATUS  mandatory
        DESCRIPTION
                "The value of this object identifies one and only
                one X25 SLP (Single Link Protocol) access logical
                port. The possible values are : '0..131'. If it is
                unused, the value of this parameter is '255'. The
                default value is '255'."
        ::= { fclX25SlpAccessEntry 1 }


    fclX25AccInterfaceId OBJECT-TYPE
        SYNTAX  INTEGER (0..35)
        ACCESS  read-write
        STATUS  mandatory
        DESCRIPTION
                "The value of this object identifies the line
                interface used by this X25 access logical port.
                The possible values are : '0..35'. If it is
                unused, the value of this parameter is '255'. The
                default value is '255'."
        ::= { fclX25SlpAccessEntry 2 }


    fclX25AccConnectionType OBJECT-TYPE
        SYNTAX  INTEGER {
                subscriber(1),
                publicNetwork(2)
                }
        ACCESS  read-write
        STATUS  mandatory
        DESCRIPTION
                "The value of this object indicates which is the
                system connected to this X25 access logical port.
                The possible values are :
                   subscriber : this X25 access logical port
                        logical port is facing to a X25
                        subscriber, fclX25AccSubscriberNumber is
                        used, fclX25AccPdnLinkAddress is not used,
                   publicNetwork : this logical port is facing to
                        a X25 Public Data Network,
                        fclX25AccSubscriberNumber is not used,
                        fclX25AccPdnLinkAddress is used.
                The default  value is 'subscriber'."
        ::= { fclX25SlpAccessEntry 3 }


    fclX25AccSubscriberNumber OBJECT-TYPE
        SYNTAX  OCTET STRING (SIZE(1))
        ACCESS  read-write
        STATUS  mandatory
        DESCRIPTION
                "The value of this object is the SB number added to
                the DNICZO of the equipment to make the calling
                address in a call sent from this X25 access
                logical port (if fclX25AccConnectionType is set to
                'subscriber'). The value must contain 2 digits
                (digits 0..9). The default value is 'FF'."
        ::= { fclX25SlpAccessEntry 4 }


    fclX25AccPdnLinkAddress OBJECT-TYPE
        SYNTAX  OCTET STRING (SIZE(8))
        ACCESS  read-write
        STATUS  mandatory
        DESCRIPTION
                "The value of this object is the X121 address of
                the equipment on the connected network (if
                fclX25AccConnectionType is set to
                'publicNetwork'). The value may contain up to 15
                digits (digits 0..9). The value must be completed
                with 'F' digits for a total of 16 digits. The
                equipment configurator does not need final
                completion. The default value is 'FF FF FF FF FF
                FF FF FF' meaning 'empty value' (blank value on
                the equipment configurator)."
        ::= { fclX25SlpAccessEntry 5 }


    fclX25AccX25AccessConfigId OBJECT-TYPE
        SYNTAX  INTEGER (0..199)
        ACCESS  read-write
        STATUS  mandatory
        DESCRIPTION
                "The value of this object identifies the X25 access
                configuration used by this X25 access logical
                port. This X25 access configuration must be
                present in fclX25ConfigAccessTable. The possible
                values are : '0..199. If it is unused, the value
                of this parameter is '255'."
        ::= { fclX25SlpAccessEntry 6 }


    fclX25AccIsdnBackupEnabling OBJECT-TYPE
        SYNTAX  INTEGER {
                off(1),
                onWhileActivity(2),
                onWhileLpDown(3),
                onWhileExcessTraffic(7)
                }
        ACCESS  read-write
        STATUS  mandatory
        DESCRIPTION
                "Secours RNIS"
        ::= { fclX25SlpAccessEntry 7 }


    fclX25AccPstnBackupEnabling OBJECT-TYPE
        SYNTAX  INTEGER {
                off(1),
                onWhileActivity(2),
                onWhileLpDown(3),
                onWhileExcessTraffic(7)
                }
        ACCESS  read-write
        STATUS  mandatory
        DESCRIPTION
                "Secours RTC"
        ::= { fclX25SlpAccessEntry 8 }


    fclX25AccPrivateNetTable OBJECT-TYPE
        SYNTAX  SEQUENCE OF FclX25AccPrivateNetEntry
        ACCESS  not-accessible
        STATUS  mandatory
        DESCRIPTION
                "This table defines the X25 access logical ports
                for which some X25 call packet fields are saved in
                X25 facility field. The restoration of these field
                takes place on the other side of the network in a
                symetric X25 SLP access logical port."
        ::= { fclX25SlpAccess 2 }


    fclX25AccPrivateNetEntry OBJECT-TYPE
        SYNTAX  FclX25AccPrivateNetEntry
        ACCESS  not-accessible
        STATUS  mandatory
        DESCRIPTION
                "An entry of fclX25AccPrivateNetTable."
        INDEX   { fclX25AccPrivLogPortId }
        ::= { fclX25AccPrivateNetTable 1 }


        FclX25AccPrivateNetEntry ::=
                SEQUENCE {
                    fclX25AccPrivLogPortId
                        INTEGER,
                    fclX25AccPrivX25FieldsSave
                        INTEGER,
                    fclX25AccPrivX25FieldsChanges
                        OCTET STRING
                }


    fclX25AccPrivLogPortId OBJECT-TYPE
        SYNTAX  INTEGER (0..181)
        ACCESS  read-only
        STATUS  mandatory
        DESCRIPTION
                "The value of this object identifies one and only
                one X25 access logical port.The possible values
                are : '0..131'. If it is unused, the value of this
                parameter is '255'. The default value is '255'."
        ::= { fclX25AccPrivateNetEntry 1 }


    fclX25AccPrivX25FieldsSave OBJECT-TYPE
        SYNTAX  INTEGER {
                off(1),
                addr(4),
                addrCug(8),
                addrCugRc(16)
                }
        ACCESS  read-write
        STATUS  mandatory
        DESCRIPTION
                "The value of this object indicates which X25 call
                packet fields are saved in X25 facility field for
                this X25 access logical port. The save operation
                is made on X25 call packets sent over the network
                and the restore operation is made on X25 packets
                received from the network. The possible values are
                :
                   off : no save/restore procedure,
                   addr : called and calling addresses,
                   addrCug : called and calling addresses, Closed
                        User Group,
                   addrCugRc : called and calling addresses,
                        Closed User Group, Reverse Charging.
                The default value is 'off'."
        ::= { fclX25AccPrivateNetEntry 2 }


    fclX25AccPrivX25FieldsChanges OBJECT-TYPE
        SYNTAX  OCTET STRING (SIZE(25))
        ACCESS  read-write
        STATUS  mandatory
        DESCRIPTION
                "The value of this object describes X25 fields
                modifications. The syntaxe is
                <Modification>[value]. There are 3 possible
                modifications :
                   BF : adds a facility at output,
                   DA : deletes caller's address at input,
                   CE : changes called party address.

                Example : DA CE 90 40 21 80 BF 70 10 00,
                   DA deletes the calling address,
                   CE 90 40 21 80 changes the called address to
                        90402180,
                   BF 70 10 00 adds the facility 701000 at output
                        of switch.

                25 bytes from 00 to FF must be specified. The
                first byte contains the number of following useful
                bytes. The trailing bytes must be set to 'FF'. The
                equipment configurator does not need this final
                completion.
                The default value is 'empty' (first byte set to
                '00')."
        ::= { fclX25AccPrivateNetEntry 3 }


    fclX25AccPermanentVcTable OBJECT-TYPE
        SYNTAX  SEQUENCE OF FclX25AccPermanentVcEntry
        ACCESS  not-accessible
        STATUS  mandatory
        DESCRIPTION
                "This table defines the X25 PVC (Permananent
                Virtual Circuits) on X25 Access logical ports. For
                each PVC this table defines the addres of the
                called remote peer and the different parameters of
                the call processing."
        ::= { fclX25SlpAccess 3 }


    fclX25AccPermanentVcEntry OBJECT-TYPE
        SYNTAX  FclX25AccPermanentVcEntry
        ACCESS  not-accessible
        STATUS  mandatory
        DESCRIPTION
                "An entry of fclX25AccPermanentVcTable."
        INDEX   { fclX25AccPvcLogPortId,
                  fclX25AccPvcLocalLogChannel }
        ::= { fclX25AccPermanentVcTable 1 }


        FclX25AccPermanentVcEntry ::=
                SEQUENCE {
                    fclX25AccPvcLogPortId
                        INTEGER,
                    fclX25AccPvcLocalLogChannel
                        INTEGER,
                    fclX25AccPvcStatus
                        INTEGER,
                    fclX25AccPvcCalledAddr
                        OCTET STRING,
                    fclX25AccPvcRemoteLogChannel
                        INTEGER,
                    fclX25AccPvcMinimumRecallTimer
                        INTEGER,
                    fclX25AccPvcCallDirection
                        INTEGER,
                    fclX25AccPvcFacility
                        INTEGER,
                    fclX25AccPvcFacThroughputClass
                        INTEGER
                }


    fclX25AccPvcLogPortId OBJECT-TYPE
        SYNTAX  INTEGER (0..181)
        ACCESS  read-only
        STATUS  mandatory
        DESCRIPTION
                "The value of this object identifies one and only
                one X25 Access logical port. This is the logical
                port this PVC (Permanent Virtual Circuit) is
                layered onto. The possible values are : '0..131'.
                If it is unused, the value of this parameter is
                '255'. The default value is '255'."
        ::= { fclX25AccPermanentVcEntry 1 }


    fclX25AccPvcLocalLogChannel OBJECT-TYPE
        SYNTAX  INTEGER (0..250)
        ACCESS  read-only
        STATUS  mandatory
        DESCRIPTION
                "The value of this object is equal to the logical
                channel value for this PVC. The possible values
                are '0..250'. The default value is '255'."
        ::= { fclX25AccPermanentVcEntry 2 }


    fclX25AccPvcStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25AccPermanentVcEntry 3 }


    fclX25AccPvcCalledAddr OBJECT-TYPE
        SYNTAX  OCTET STRING (SIZE(8))
        ACCESS  read-write
        STATUS  mandatory
        DESCRIPTION
                "The value of this object is the X121 address of
                the called remote peer PVC. This value is the
                called address specified in the call packet sent
                from this PVC. The value may contain up to 15
                digits (digits 0..9). The value must be completed
                with 'F' digits for a total of 16 digits. The
                equipment configurator does not need final
                completion. The default value is 'FF FF FF FF FF
                FF FF FF' meaning 'empty value' (blank value on
                the equipment configurator)."
        ::= { fclX25AccPermanentVcEntry 4 }


    fclX25AccPvcRemoteLogChannel OBJECT-TYPE
        SYNTAX  INTEGER (0..250)
        ACCESS  read-write
        STATUS  mandatory
        DESCRIPTION
                "The value of this object is equal to the logical
                channel value for the remote peer PVC. The
                possible values are '0..250'. The default value is
                '255'."
        ::= { fclX25AccPermanentVcEntry 5 }


    fclX25AccPvcMinimumRecallTimer OBJECT-TYPE
        SYNTAX  INTEGER (0..990)
        ACCESS  read-write
        STATUS  mandatory
        DESCRIPTION
                "The value of this object specifies the minimum
                recall time (in seconds) between two successive
                calls. The authorized values are '0..990' by step
                of 10. The default value is '0'."
        ::= { fclX25AccPermanentVcEntry 6 }


    fclX25AccPvcCallDirection OBJECT-TYPE
        SYNTAX  INTEGER {
                calling(1),
                called(2),
                auto(3)
                }
        ACCESS  read-write
        STATUS  mandatory
        DESCRIPTION
                "The value of this object defines the mode used to
                establish the X25 VC between this PVC and the
                remote one on the other side of the network. The
                authorized values are 'calling' (the caller is
                this PVC), 'called' (the caller is the remote
                PVC), 'auto' (automatic choise between 'calling'
                and 'called'). The default value is 'auto'."
        ::= { fclX25AccPermanentVcEntry 7 }


    fclX25AccPvcFacility OBJECT-TYPE
        SYNTAX  INTEGER {
                none(1),
                throughputClass(2)
                }
        ACCESS  read-write
        STATUS  mandatory
        DESCRIPTION
                "Facilites"
        ::= { fclX25AccPermanentVcEntry 8 }


    fclX25AccPvcFacThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "Classe de debit eventuelle"
        ::= { fclX25AccPermanentVcEntry 9 }


    fclX25AccSwitchOverTable OBJECT-TYPE
        SYNTAX  SEQUENCE OF FclX25AccSwitchOverEntry
        ACCESS  not-accessible
        STATUS  mandatory
        DESCRIPTION
                ""
        ::= { fclX25SlpAccess 4 }


    fclX25AccSwitchOverEntry OBJECT-TYPE
        SYNTAX  FclX25AccSwitchOverEntry
        ACCESS  not-accessible
        STATUS  mandatory
        DESCRIPTION
                "An entry of fclX25AccSwitchOverTable."
        INDEX   { fclX25AccSwLogPortId }
        ::= { fclX25AccSwitchOverTable 1 }


        FclX25AccSwitchOverEntry ::=
                SEQUENCE {
                    fclX25AccSwLogPortId
                        INTEGER,
                    fclX25AccSwMeasureCount
                        INTEGER,
                    fclX25AccSwSwitchThreshold
                        INTEGER,
                    fclX25AccSwSwitchBackThreshold
                        INTEGER
                }


    fclX25AccSwLogPortId OBJECT-TYPE
        SYNTAX  INTEGER (0..181)
        ACCESS  read-only
        STATUS  mandatory
        DESCRIPTION
                "LP id"
        ::= { fclX25AccSwitchOverEntry 1 }


    fclX25AccSwMeasureCount OBJECT-TYPE
        SYNTAX  INTEGER (0..249)
        ACCESS  read-write
        STATUS  mandatory
        DESCRIPTION
                "Nombre de mesures avant basculement"
        ::= { fclX25AccSwitchOverEntry 2 }


    fclX25AccSwSwitchThreshold OBJECT-TYPE
        SYNTAX  INTEGER (0..100)
        ACCESS  read-write
        STATUS  mandatory
        DESCRIPTION
                "Seuil haut (en pourcentage)"
        ::= { fclX25AccSwitchOverEntry 3 }


    fclX25AccSwSwitchBackThreshold OBJECT-TYPE
        SYNTAX  INTEGER (0..100)
        ACCESS  read-write
        STATUS  mandatory
        DESCRIPTION
                "Seuil bas (en pourcentage)"
        ::= { fclX25AccSwitchOverEntry 4 }


    fclX25AccIsdnBackupTable OBJECT-TYPE
        SYNTAX  SEQUENCE OF FclX25AccIsdnBackupEntry
        ACCESS  not-accessible
        STATUS  mandatory
        DESCRIPTION
                ""
        ::= { fclX25SlpAccess 5 }


    fclX25AccIsdnBackupEntry OBJECT-TYPE
        SYNTAX  FclX25AccIsdnBackupEntry
        ACCESS  not-accessible
        STATUS  mandatory
        DESCRIPTION
                "An entry of fclX25AccIsdnBackupTable."
        INDEX   { fclX25AccIsdnBackLogPortId,
                  fclX25AccIsdnBackIsdnInterfaceId }
        ::= { fclX25AccIsdnBackupTable 1 }


        FclX25AccIsdnBackupEntry ::=
                SEQUENCE {
                    fclX25AccIsdnBackLogPortId
                        INTEGER,
                    fclX25AccIsdnBackIsdnInterfaceId
                        INTEGER,
                    fclX25AccIsdnBackStatus
                        INTEGER
                }


    fclX25AccIsdnBackLogPortId OBJECT-TYPE
        SYNTAX  INTEGER (0..181)
        ACCESS  read-only
        STATUS  mandatory
        DESCRIPTION
                "LP id"
        ::= { fclX25AccIsdnBackupEntry 1 }


    fclX25AccIsdnBackIsdnInterfaceId OBJECT-TYPE
        SYNTAX  INTEGER (0..35)
        ACCESS  read-only
        STATUS  mandatory
        DESCRIPTION
                "IF id (type RNIS)"
        ::= { fclX25AccIsdnBackupEntry 2 }


    fclX25AccIsdnBackStatus OBJECT-TYPE
        SYNTAX  INTEGER {
                valid(1),
                invalid(2)
                }
        ACCESS  read-write
        STATUS  mandatory
        DESCRIPTION
                "Status"
        ::= { fclX25AccIsdnBackupEntry 3 }


    fclX25AccIsdnRemotePeerTable OBJECT-TYPE
        SYNTAX  SEQUENCE OF FclX25AccIsdnRemotePeerEntry
        ACCESS  not-accessible
        STATUS  mandatory
        DESCRIPTION
                ""
        ::= { fclX25SlpAccess 6 }


    fclX25AccIsdnRemotePeerEntry OBJECT-TYPE
        SYNTAX  FclX25AccIsdnRemotePeerEntry
        ACCESS  not-accessible
        STATUS  mandatory
        DESCRIPTION
                "An entry of fclX25AccIsdnRemotePeerTable."
        INDEX   { fclX25AccIsdnRemLogPortId,
                  fclX25AccIsdnRemIsdnInterfaceId }
        ::= { fclX25AccIsdnRemotePeerTable 1 }


        FclX25AccIsdnRemotePeerEntry ::=
                SEQUENCE {
                    fclX25AccIsdnRemLogPortId
                        INTEGER,
                    fclX25AccIsdnRemIsdnInterfaceId
                        INTEGER,
                    fclX25AccIsdnRemStatus
                        INTEGER,
                    fclX25AccIsdnRemX25AccessConfigId
                        INTEGER,
                    fclX25AccIsdnRemPriority
                        INTEGER,
                    fclX25AccIsdnRemCallRetryCount
                        INTEGER
                }


    fclX25AccIsdnRemLogPortId OBJECT-TYPE
        SYNTAX  INTEGER (0..181)
        ACCESS  read-only
        STATUS  mandatory
        DESCRIPTION
                "LP id"
        ::= { fclX25AccIsdnRemotePeerEntry 1 }


    fclX25AccIsdnRemIsdnInterfaceId OBJECT-TYPE
        SYNTAX  INTEGER (0..35)
        ACCESS  read-only
        STATUS  mandatory
        DESCRIPTION
                "Interface RNIS distante id"
        ::= { fclX25AccIsdnRemotePeerEntry 2 }


    fclX25AccIsdnRemStatus OBJECT-TYPE
        SYNTAX  INTEGER {
                valid(1),
                invalid(2)
                }
        ACCESS  read-write
        STATUS  mandatory
        DESCRIPTION
                "Status"
        ::= { fclX25AccIsdnRemotePeerEntry 3 }


    fclX25AccIsdnRemX25AccessConfigId OBJECT-TYPE
        SYNTAX  INTEGER (0..199)
        ACCESS  read-write
        STATUS  mandatory
        DESCRIPTION
                "Configuration X25 acces id"
        ::= { fclX25AccIsdnRemotePeerEntry 4 }


    fclX25AccIsdnRemPriority OBJECT-TYPE
        SYNTAX  INTEGER (0..15)
        ACCESS  read-write
        STATUS  mandatory
        DESCRIPTION
                "Priorite"
        ::= { fclX25AccIsdnRemotePeerEntry 5 }


    fclX25AccIsdnRemCallRetryCount OBJECT-TYPE
        SYNTAX  INTEGER (1..15)
        ACCESS  read-write
        STATUS  mandatory
        DESCRIPTION
                "Nb de tentatives appel"
        ::= { fclX25AccIsdnRemotePeerEntry 6 }


    fclX25AccPstnBackupTable OBJECT-TYPE
        SYNTAX  SEQUENCE OF FclX25AccPstnBackupEntry
        ACCESS  not-accessible
        STATUS  mandatory
        DESCRIPTION
                ""
        ::= { fclX25SlpAccess 7 }


    fclX25AccPstnBackupEntry OBJECT-TYPE
        SYNTAX  FclX25AccPstnBackupEntry
        ACCESS  not-accessible
        STATUS  mandatory
        DESCRIPTION
                "An entry of fclX25AccPstnBackupTable."
        INDEX   { fclX25AccPstnBackLogPortId }
        ::= { fclX25AccPstnBackupTable 1 }


        FclX25AccPstnBackupEntry ::=
                SEQUENCE {
                    fclX25AccPstnBackLogPortId
                        INTEGER,
                    fclX25AccPstnBackStatus
                        INTEGER,
                    fclX25AccPstnBackInterfaceId
                        INTEGER,
                    fclX25AccPstnBackPstnNumber
                        OCTET STRING,
                    fclX25AccPstnBackX25AccessConfigId
                        INTEGER
                }


    fclX25AccPstnBackLogPortId OBJECT-TYPE
        SYNTAX  INTEGER (0..181)
        ACCESS  read-only
        STATUS  mandatory
        DESCRIPTION
                "LP id"
        ::= { fclX25AccPstnBackupEntry 1 }


    fclX25AccPstnBackStatus OBJECT-TYPE
        SYNTAX  INTEGER {
                valid(1),
                invalid(2)
                }
        ACCESS  read-write
        STATUS  mandatory
        DESCRIPTION
                "Status"
        ::= { fclX25AccPstnBackupEntry 2 }


    fclX25AccPstnBackInterfaceId OBJECT-TYPE
        SYNTAX  INTEGER (0..35)
        ACCESS  read-write
        STATUS  mandatory
        DESCRIPTION
                "IF id (type ligne)"
        ::= { fclX25AccPstnBackupEntry 3 }


    fclX25AccPstnBackPstnNumber OBJECT-TYPE
        SYNTAX  OCTET STRING (SIZE(14))
        ACCESS  read-write
        STATUS  mandatory
        DESCRIPTION
                "Numero RTC"
        ::= { fclX25AccPstnBackupEntry 4 }


    fclX25AccPstnBackX25AccessConfigId OBJECT-TYPE
        SYNTAX  INTEGER (0..199)
        ACCESS  read-write
        STATUS  mandatory
        DESCRIPTION
                "Configuration X25 acces id"
        ::= { fclX25AccPstnBackupEntry 5 }


    fclX25InDIsdn OBJECT IDENTIFIER ::= { fcLogicalPorts 21 }


    fclX25InDIsdnTable OBJECT-TYPE
        SYNTAX  SEQUENCE OF FclX25InDIsdnEntry
        ACCESS  not-accessible
        STATUS  mandatory
        DESCRIPTION
                "This table defines the general parameters of X25
                SLP (Single Link Protocol) in ISDN D channel
                access logical ports."
        ::= { fclX25InDIsdn 1 }


    fclX25InDIsdnEntry OBJECT-TYPE
        SYNTAX  FclX25InDIsdnEntry
        ACCESS  not-accessible
        STATUS  mandatory
        DESCRIPTION
                "An entry of fclX25InDIsdnTable."
        INDEX   { fclX25InDLogPortId }
        ::= { fclX25InDIsdnTable 1 }


        FclX25InDIsdnEntry ::=
                SEQUENCE {
                    fclX25InDLogPortId
                        INTEGER,
                    fclX25InDIsdnInterfaceId
                        INTEGER,
                    fclX25InDTei
                        INTEGER,
                    fclX25InDBackupEnabling
                        INTEGER,
                    fclX25InDConnectionType
                        INTEGER,
                    fclX25InDSubscriberNumber
                        OCTET STRING,
                    fclX25InDPdnLinkAddress
                        OCTET STRING,
                    fclX25InDX25AccessConfigId
                        INTEGER,
                    fclX25InDInactivityTimer
                        INTEGER,
                    fclX25InDActiveLinkAtBootTime
                        INTEGER
                }


    fclX25InDLogPortId OBJECT-TYPE
        SYNTAX  INTEGER (0..181)
        ACCESS  read-only
        STATUS  mandatory
        DESCRIPTION
                "The value of this object identifies one and only
                one X25 in ISDN D Channel logical port. The
                possible values are : '0..131'. If it is unused,
                the value of this parameter is '255'. The default
                value is '255'."
        ::= { fclX25InDIsdnEntry 1 }


    fclX25InDIsdnInterfaceId OBJECT-TYPE
        SYNTAX  INTEGER (0..35)
        ACCESS  read-write
        STATUS  mandatory
        DESCRIPTION
                "The value of this object identifies the ISDN Basic
                Rate Interface used by this X25 in ISDN-D logical
                port. The possible values are : '0..35'. If it is
                unused, the value of this parameter is '255'. The
                default value is '255'."
        ::= { fclX25InDIsdnEntry 2 }


    fclX25InDTei OBJECT-TYPE
        SYNTAX  INTEGER (1..63)
        ACCESS  read-write
        STATUS  mandatory
        DESCRIPTION
                "The value of this object defines the TEI (Terminal
                Endpoint Identifier) used by this X25 in ISDN-D
                logical port. The authorized values are '1..63'.
                The default value is '255'."
        ::= { fclX25InDIsdnEntry 3 }


    fclX25InDBackupEnabling OBJECT-TYPE
        SYNTAX  INTEGER {
                off(1),
                onWhileActivity(2),
                onWhileLpDown(3),
                onWhileExcessTraffic(7)
                }
        ACCESS  read-write
        STATUS  mandatory
        DESCRIPTION
                "The value of this object defines how this X25 in
                ISDN-D logical port may be backuped by an ISDN-B
                channel.

                 The possible values are :

                   off : backup is never enabled,

                   onWhileActivity : when the logical port is
                        DOWN, backup is enabled on reception of a
                        new call and remains active while at least
                        one X25 VC is using this way. When no VC
                        is active, the backup is disabled and the
                        next VC will be established on the logical
                        port (if it is UP obviously).

                   onWhileLpDown : when the logical port is DOWN,
                        backup is enabled on reception of a new
                        call and remains active while the logical
                        port is DOWN. The backup is disabled
                        (meaning clearing of all VCs using this
                        way) when the logical port comes back UP
                        and the next VC will be established on the
                        logical port.

                   onWhileExcessTraffic : when the traffic
                        overtakes the fclX25InDSwSwitchThreshold
                        value the logical port state is marked
                        DOWN (meaning clearing of all VCs), backup
                        is enabled on reception of a new call and
                        remains active while the traffic is
                        overtaking the
                        fclX25InDSwSwitchBackThreshold value. When
                        the traffic does not overtake any more the
                        fclX25InDSwSwitchBackThreshold value, the
                        logical port is marked UP and the backup
                        is disabled (meaning clearing of all VCs
                        using this way) so the next VC will be
                        established on the logical port.

                        This Switch Over mechanism permits to
                        transmit temporay excess traffic which
                        could not be transmitted on the ISDN-D
                        Channel because of an insufficient
                        bandwith (16 kbit/s against 64 kbits/s for
                        an ISDN-B Channel).

                The default value is 'off'."
        ::= { fclX25InDIsdnEntry 4 }


    fclX25InDConnectionType OBJECT-TYPE
        SYNTAX  INTEGER {
                subscriber(1),
                publicNetwork(2)
                }
        ACCESS  read-write
        STATUS  mandatory
        DESCRIPTION
                "The value of this object indicates which is the
                system connected to this X25 in ISDN-D logical
                port. The possible values are :
                   subscriber : this X25 ISDN-D logical port
                        logical port is facing to a X25
                        subscriber, fclX25InDSubscriberNumber is
                        used, fclX25InDPdnLinkAddress is not used,
                   publicNetwork : this logical port is facing to
                        a X25 Public Data Network,
                        fclX25InDSubscriberNumber is not used,
                        fclX25InDPdnLinkAddress is used.
                The default value is 'subscriber'."
        ::= { fclX25InDIsdnEntry 5 }


    fclX25InDSubscriberNumber OBJECT-TYPE
        SYNTAX  OCTET STRING (SIZE(1))
        ACCESS  read-write
        STATUS  mandatory
        DESCRIPTION
                "The value of this object is the SB number added to
                the DNICZO of the equipment to make the calling
                address in a call sent from this X25 in ISDN-D
                logical port (if fclX25InDConnectionType is set to
                'subscriber'). The value must contain 2 digits
                (digits 0..9). The default value is 'FF'."
        ::= { fclX25InDIsdnEntry 6 }


    fclX25InDPdnLinkAddress OBJECT-TYPE
        SYNTAX  OCTET STRING (SIZE(8))
        ACCESS  read-write
        STATUS  mandatory
        DESCRIPTION
                "The value of this object is the X121 address of
                the equipment on the connected network (if
                fclX25InDConnectionType is set to
                'publicNetwork'). The value may contain up to 15
                digits (digits 0..9). The value must be completed
                with 'F' digits for a total of 16 digits. The
                equipment configurator does not need final
                completion. The default value is 'FF FF FF FF FF
                FF FF FF' meaning 'empty value' (blank value on
                the equipment configurator)."
        ::= { fclX25InDIsdnEntry 7 }


    fclX25InDX25AccessConfigId OBJECT-TYPE
        SYNTAX  INTEGER (0..199)
        ACCESS  read-write
        STATUS  mandatory
        DESCRIPTION
                "The value of this object identifies the X25 access
                configuration used by this X25 in ISDN-D logical
                port. This X25 access configuration must be
                present in fclX25ConfigAccessTable. The possible
                values are : '0..199. If it is unused, the value
                of this parameter is '255'."
        ::= { fclX25InDIsdnEntry 8 }


    fclX25InDInactivityTimer OBJECT-TYPE
        SYNTAX  INTEGER (0..250)
        ACCESS  read-write
        STATUS  mandatory
        DESCRIPTION
                "The value of this object defines the delay in
                seconds between the clearing of the last X25 VC
                using this ISDN-D logical port and the clearing of
                the ISDN connection. The authorized values are
                '0..250'. The default value is '0'."
        ::= { fclX25InDIsdnEntry 9 }


    fclX25InDActiveLinkAtBootTime OBJECT-TYPE
        SYNTAX  INTEGER {
                off(1),
                on(2)
                }
        ACCESS  read-write
        STATUS  mandatory
        DESCRIPTION
                "The value of this object indicates whether the
                equipment, when it has just started, must
                establish the ISDN connection or not. The default
                value is 'off'."
        ::= { fclX25InDIsdnEntry 10 }


    fclX25InDSwitchOverTable OBJECT-TYPE
        SYNTAX  SEQUENCE OF FclX25InDSwitchOverEntry
        ACCESS  not-accessible
        STATUS  mandatory
        DESCRIPTION
                "This table defines the switch over parameters of
                X25 in ISDN D channel access logical ports using
                the switch over mechanism."
        ::= { fclX25InDIsdn 2 }


    fclX25InDSwitchOverEntry OBJECT-TYPE
        SYNTAX  FclX25InDSwitchOverEntry
        ACCESS  not-accessible
        STATUS  mandatory
        DESCRIPTION
                "An entry of fclX25InDSwitchOverTable."
        INDEX   { fclX25InDSwLogPortId }
        ::= { fclX25InDSwitchOverTable 1 }


        FclX25InDSwitchOverEntry ::=
                SEQUENCE {
                    fclX25InDSwLogPortId
                        INTEGER,
                    fclX25InDSwMeasureCount
                        INTEGER,
                    fclX25InDSwSwitchThreshold
                        INTEGER,
                    fclX25InDSwSwitchBackThreshold
                        INTEGER
                }


    fclX25InDSwLogPortId OBJECT-TYPE
        SYNTAX  INTEGER (0..181)
        ACCESS  read-only
        STATUS  mandatory
        DESCRIPTION
                "The value of this object identifies one and only
                one X25 in ISDN D Channel logical port using the
                switch over mechanism (fclX25InDBackupEnabling set
                to 'onWhileExcessTraffic'). The possible values
                are : '0..131'. If it is unused, the value of this
                parameter is '255'. The default value is '255'."
        ::= { fclX25InDSwitchOverEntry 1 }


    fclX25InDSwMeasureCount OBJECT-TYPE
        SYNTAX  INTEGER (0..249)
        ACCESS  read-write
        STATUS  mandatory
        DESCRIPTION
                "The value of this object is the number of traffic
                measures before switching. The measure duration is
                defined by fcwLoadAndTrafficSummingPeriod. The
                authorized values are '0..249'. The default value
                is '2'."
        ::= { fclX25InDSwitchOverEntry 2 }


    fclX25InDSwSwitchThreshold OBJECT-TYPE
        SYNTAX  INTEGER (0..100)
        ACCESS  read-write
        STATUS  mandatory
        DESCRIPTION
                "The value of this object indicates the traffic
                threshold (in percents of bandwith of the main
                link of logical port) over which the switch over
                mechanism is enabled. The authorized values are
                '0..100'. The default value is '80'."
        ::= { fclX25InDSwitchOverEntry 3 }


    fclX25InDSwSwitchBackThreshold OBJECT-TYPE
        SYNTAX  INTEGER (0..100)
        ACCESS  read-write
        STATUS  mandatory
        DESCRIPTION
                "The value of this object indicates the traffic
                threshold (in percents of bandwith of the main
                link of logical port) under which the switch over
                mechanism is disabled. The authorized values are
                '0..100'. The default value is '60'."
        ::= { fclX25InDSwitchOverEntry 4 }


    fclX25InDIsdnBackupTable OBJECT-TYPE
        SYNTAX  SEQUENCE OF FclX25InDIsdnBackupEntry
        ACCESS  not-accessible
        STATUS  mandatory
        DESCRIPTION
                "This table defines which ISDN Basic Rate Interface
                may be used by each X25 in ISDN D channel access
                logical port when enabling backup on ISDN
                B-Channels."
        ::= { fclX25InDIsdn 3 }


    fclX25InDIsdnBackupEntry OBJECT-TYPE
        SYNTAX  FclX25InDIsdnBackupEntry
        ACCESS  not-accessible
        STATUS  mandatory
        DESCRIPTION
                "An entry of fclX25InDIsdnBackupTable."
        INDEX   { fclX25InDIsdnBackLogPortId,
                  fclX25InDIsdnBackIsdnInterfaceId }
        ::= { fclX25InDIsdnBackupTable 1 }


        FclX25InDIsdnBackupEntry ::=
                SEQUENCE {
                    fclX25InDIsdnBackLogPortId
                        INTEGER,
                    fclX25InDIsdnBackIsdnInterfaceId
                        INTEGER,
                    fclX25InDIsdnBackStatus
                        INTEGER
                }


    fclX25InDIsdnBackLogPortId OBJECT-TYPE
        SYNTAX  INTEGER (0..181)
        ACCESS  read-only
        STATUS  mandatory
        DESCRIPTION
                "The value of this object identifies one and only
                one X25 in ISDN D channel access logical port. One
                X25 X25 in ISDN D channel logical port may use
                backup with one or several ISDN Basic Rate
                Interfaces. The possible values are : '0..131'. If
                it is unused, the value of this parameter is
                '255'. The default value is '255'."
        ::= { fclX25InDIsdnBackupEntry 1 }


    fclX25InDIsdnBackIsdnInterfaceId OBJECT-TYPE
        SYNTAX  INTEGER (0..35)
        ACCESS  read-only
        STATUS  mandatory
        DESCRIPTION
                "The value of this object identifies one ISDN Basic
                Rate Interface used by the X25 in ISDN D channel
                access logical port defined by
                fclX25InDIsdnBackLogPortId. The possible values
                are : '0..35'. If it is unused, the value of this
                parameter is '255'. The default value is '255'."
        ::= { fclX25InDIsdnBackupEntry 2 }


    fclX25InDIsdnBackStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25InDIsdnBackupEntry 3 }


    fclX25InDIsdnRemotePeerTable OBJECT-TYPE
        SYNTAX  SEQUENCE OF FclX25InDIsdnRemotePeerEntry
        ACCESS  not-accessible
        STATUS  mandatory
        DESCRIPTION
                "This table defines the ISDN remote systems which
                may be connected to the equipment using the backup
                mechanism of X25 in ISDN D channel access logical
                ports ."
        ::= { fclX25InDIsdn 4 }


    fclX25InDIsdnRemotePeerEntry OBJECT-TYPE
        SYNTAX  FclX25InDIsdnRemotePeerEntry
        ACCESS  not-accessible
        STATUS  mandatory
        DESCRIPTION
                "An entry of fclX25InDIsdnRemotePeerTable."
        INDEX   { fclX25InDIsdnRemLogPortId,
                  fclX25InDIsdnRemIsdnInterfaceId }
        ::= { fclX25InDIsdnRemotePeerTable 1 }


        FclX25InDIsdnRemotePeerEntry ::=
                SEQUENCE {
                    fclX25InDIsdnRemLogPortId
                        INTEGER,
                    fclX25InDIsdnRemIsdnInterfaceId
                        INTEGER,
                    fclX25InDIsdnRemStatus
                        INTEGER,
                    fclX25InDIsdnRemConnectionType
                        INTEGER,
                    fclX25InDIsdnRemSubscriberNumber
                        OCTET STRING,
                    fclX25InDIsdnRemPdnLinkAddress
                        OCTET STRING,
                    fclX25InDIsdnRemX25AccConfigId
                        INTEGER,
                    fclX25InDIsdnRemPriority
                        INTEGER,
                    fclX25InDIsdnRemCallRetryCount
                        INTEGER
                }


    fclX25InDIsdnRemLogPortId OBJECT-TYPE
        SYNTAX  INTEGER (0..181)
        ACCESS  read-only
        STATUS  mandatory
        DESCRIPTION
                "The value of this object identifies one and only
                one X25 in ISDN D channel access logical port. One
                X25 in ISDN D channel logical port may use backup
                mechanism with one or several ISDN remote systems
                (these ISDN systems can be on different
                equipments). The possible values are : '0..131'.
                If it is unused, the value of this parameter is
                '255'. The default value is '255'."
        ::= { fclX25InDIsdnRemotePeerEntry 1 }


    fclX25InDIsdnRemIsdnInterfaceId OBJECT-TYPE
        SYNTAX  INTEGER (0..249)
        ACCESS  read-only
        STATUS  mandatory
        DESCRIPTION
                "The value of this object identifies one and only
                one ISDN remote system. This ISDN remote system
                must exist in fclIsdnRemotePeerTable. There may be
                several ISDN remote system for only one X25 in
                ISDN D channel logical port (these ISDN systems
                can be on different equipments). The possible
                values are : '0..249'. If it is unused, the value
                of this parameter is '255'."
        ::= { fclX25InDIsdnRemotePeerEntry 2 }


    fclX25InDIsdnRemStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25InDIsdnRemotePeerEntry 3 }


    fclX25InDIsdnRemConnectionType OBJECT-TYPE
        SYNTAX  INTEGER {
                subscriber(1),
                publicNetwork(2)
                }
        ACCESS  read-write
        STATUS  mandatory
        DESCRIPTION
                "The value of this object indicates which is the
                system connected by the backup mechanism to this
                X25 in ISDN-D logical port. The possible values
                are :
                   subscriber : this X25 ISDN-D logical port
                        logical port is facing to a X25
                        subscriber,
                        fclX25InDIsdnRemSubscriberNumber is used,
                        fclX25InDIsdnRemPdnLinkAddress is not
                        used,
                   publicNetwork : this logical port is facing to
                        a X25 Public Data Network,
                        fclX25InDIsdnRemSubscriberNumber is not
                        used, fclX25InDIsdnRemPdnLinkAddress is
                        used.
                The default value is 'subscriber'."
        ::= { fclX25InDIsdnRemotePeerEntry 4 }


    fclX25InDIsdnRemSubscriberNumber OBJECT-TYPE
        SYNTAX  OCTET STRING (SIZE(1))
        ACCESS  read-write
        STATUS  mandatory
        DESCRIPTION
                "The value of this object is the SB number added to
                the DNICZO of the equipment to make the calling
                address in a call sent from this X25 in ISDN-D
                logical port by the backup mechanism (if
                fclX25InDIsdnRemConnectionType is set to
                'subscriber'). The value must contain 2 digits
                (digits 0..9). The default value is 'FF'."
        ::= { fclX25InDIsdnRemotePeerEntry 5 }


    fclX25InDIsdnRemPdnLinkAddress OBJECT-TYPE
        SYNTAX  OCTET STRING (SIZE(8))
        ACCESS  read-write
        STATUS  mandatory
        DESCRIPTION
                "The value of this object is the X121 address of
                the equipment on the connected network (if
                fclX25InDIsdnRemConnectionType is set to
                'publicNetwork'). The value may contain up to 15
                digits (digits 0..9). The value must be completed
                with 'F' digits for a total of 16 digits. The
                equipment configurator does not need final
                completion. The default value is 'FF FF FF FF FF
                FF FF FF' meaning 'empty value' (blank value on
                the equipment configurator)."
        ::= { fclX25InDIsdnRemotePeerEntry 6 }


    fclX25InDIsdnRemX25AccConfigId OBJECT-TYPE
        SYNTAX  INTEGER (0..199)
        ACCESS  read-write
        STATUS  mandatory
        DESCRIPTION
                "The value of this object identifies the X25 access
                configuration used by this X25 in ISDN-D logical
                port.  backup link. This X25 access configuration
                must be present in fclX25ConfigAccessTable. The
                possible values are : '0..199. If it is unused,
                the value of this parameter is '255'."
        ::= { fclX25InDIsdnRemotePeerEntry 7 }


    fclX25InDIsdnRemPriority OBJECT-TYPE
        SYNTAX  INTEGER (0..15)
        ACCESS  read-write
        STATUS  mandatory
        DESCRIPTION
                "The value of this object indicates, when there is
                several ISDN remote system for only one X25 in
                ISDN D channel logical port, in which order the
                equipment will try to call these several ISDN
                remote system to establish an ISDN B Channel. When
                a try to one ISDN remote system fails the
                equipment continues, in the increasing order of
                this parameter, with the following in the list
                until the end of the list. The possible values are
                : '0..15'. The default value is '0' (meaning
                'first of the list')."
        ::= { fclX25InDIsdnRemotePeerEntry 8 }


    fclX25InDIsdnRemCallRetryCount OBJECT-TYPE
        SYNTAX  INTEGER (1..15)
        ACCESS  read-write
        STATUS  mandatory
        DESCRIPTION
                "The value of this object indicates how many times
                the equipment will try to call this particular
                ISDN remote system to establish an ISDN B Channel.
                The possible values are : '1..15'. The default
                value is '1'."
        ::= { fclX25InDIsdnRemotePeerEntry 9 }


    fclX25InBIsdn OBJECT IDENTIFIER ::= { fcLogicalPorts 22 }


    fclX25InBIsdnTable OBJECT-TYPE
        SYNTAX  SEQUENCE OF FclX25InBIsdnEntry
        ACCESS  not-accessible
        STATUS  mandatory
        DESCRIPTION
                "This table defines the general parameters of X25
                SLP (Single Link Protocol) in ISDN B channel
                logical ports."
        ::= { fclX25InBIsdn 1 }


    fclX25InBIsdnEntry OBJECT-TYPE
        SYNTAX  FclX25InBIsdnEntry
        ACCESS  not-accessible
        STATUS  mandatory
        DESCRIPTION
                "An entry of fclX25InBIsdnTable."
        INDEX   { fclX25InBLogPortId }
        ::= { fclX25InBIsdnTable 1 }


        FclX25InBIsdnEntry ::=
                SEQUENCE {
                    fclX25InBLogPortId
                        INTEGER,
                    fclX25InBIsdnInterfaceId
                        INTEGER
                }


    fclX25InBLogPortId OBJECT-TYPE
        SYNTAX  INTEGER (0..181)
        ACCESS  read-only
        STATUS  mandatory
        DESCRIPTION
                "The value of this object identifies one and only
                one X25 in ISDN B Channel logical port. The
                possible values are : '0..131'. If it is unused,
                the value of this parameter is '255'. The default
                value is '255'."
        ::= { fclX25InBIsdnEntry 1 }


    fclX25InBIsdnInterfaceId OBJECT-TYPE
        SYNTAX  INTEGER (0..35)
        ACCESS  read-write
        STATUS  mandatory
        DESCRIPTION
                "The value of this object identifies the ISDN Basic
                Rate Interface used by this X25 in ISDN-B logical
                port. The possible values are : '0..35'. If it is
                unused, the value of this parameter is '255'. The
                default value is '255'."
        ::= { fclX25InBIsdnEntry 2 }


    fclX25InBRemotePeerTable OBJECT-TYPE
        SYNTAX  SEQUENCE OF FclX25InBRemotePeerEntry
        ACCESS  not-accessible
        STATUS  mandatory
        DESCRIPTION
                "This table defines the ISDN remote systems which
                may be connected to the equipment using an X25 in
                ISDN B channel logical ports ."
        ::= { fclX25InBIsdn 2 }


    fclX25InBRemotePeerEntry OBJECT-TYPE
        SYNTAX  FclX25InBRemotePeerEntry
        ACCESS  not-accessible
        STATUS  mandatory
        DESCRIPTION
                "An entry of fclX25InBRemotePeerTable."
        INDEX   { fclX25InBRemX121Addr,
                  fclX25InBRemPeerId }
        ::= { fclX25InBRemotePeerTable 1 }


        FclX25InBRemotePeerEntry ::=
                SEQUENCE {
                    fclX25InBRemX121Addr
                        OCTET STRING,
                    fclX25InBRemPeerId
                        INTEGER,
                    fclX25InBRemStatus
                        INTEGER,
                    fclX25InBRemConnectionType
                        INTEGER,
                    fclX25InBRemSubscriberNumber
                        OCTET STRING,
                    fclX25InBRemPdnLinkAddress
                        OCTET STRING,
                    fclX25InBRemX25ConfigId
                        INTEGER,
                    fclX25InBRemPriority
                        INTEGER,
                    fclX25InBRemCallRetryCount
                        INTEGER,
                    fclX25InBRemLinkCheckPeriod
                        INTEGER,
                    fclX25InBRemCheckPeriodCount
                        INTEGER
                }


    fclX25InBRemX121Addr OBJECT-TYPE
        SYNTAX  OCTET STRING (SIZE(8))
        ACCESS  read-only
        STATUS  mandatory
        DESCRIPTION
                "The value of this object is the X121 address of
                one or several ISDN remote systems. The value may
                contain up to 15 digits (digits 0..9, A,B,D).

                The digits 'A', 'B', 'D' (respectively characters
                ':', '*', '?' on the equipment configurator) have
                special meanings :

                   'A' is a separator used to defines which digits
                        of this X121 address are added to the
                        value of fcfIsdnRemIsdnNumber
                        corresponding to fclX25InBRemPeerId to
                        make the complete ISDN address. When used
                        there must be exactly two separators to
                        mark the beginning and the end of the
                        digits selection.

                   'B' matches any address. When used it must be
                        the only digit specified (with final
                        completion as explained below).

                   'D' matches any single digit.

                The value must be completed with 'F' digits for a
                total of 16 digits. The equipment configurator
                does not need final completion. The default value
                is 'FF FF FF FF FF FF FF FF' meaning 'empty value'
                (blank value on the equipment configurator)."
        ::= { fclX25InBRemotePeerEntry 1 }


    fclX25InBRemPeerId OBJECT-TYPE
        SYNTAX  INTEGER (0..999)
        ACCESS  read-only
        STATUS  mandatory
        DESCRIPTION
                "The value of this object identifies one and only
                one ISDN remote system. This ISDN remote system
                must exist in fclIsdnRemotePeerTable. There may be
                several ISDN remote system for only one X121
                address. The possible values are : '0..249' in
                releases before 4.2, '0..999' after. If it is
                unused, the value of this parameter is '255' or
                '65535'."
        ::= { fclX25InBRemotePeerEntry 2 }


    fclX25InBRemStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25InBRemotePeerEntry 3 }


    fclX25InBRemConnectionType OBJECT-TYPE
        SYNTAX  INTEGER {
                subscriber(1),
                publicNetwork(2),
                interNode(3)
                }
        ACCESS  read-write
        STATUS  mandatory
        DESCRIPTION
                "The value of this object indicates which is the
                ISDN remote system connected to one of the X25 in
                ISDN-B logical port. The possible values are :
                   subscriber : this X25 ISDN-B logical port
                        logical port is facing to a X25
                        subscriber, fclX25InBRemSubscriberNumber
                        is used, fclX25InBRemPdnLinkAddress is not
                        used,
                   publicNetwork : this logical port is facing to
                        a X25 Public Data Network,
                        fclX25InBRemSubscriberNumber is not used,
                        fclX25InBRemPdnLinkAddress is used.
                   interNode : this logical port is used as
                        inter-node ling (i.e. inside an X25
                        network),
                fclX25InBRemSubscriberNumber is not used,
                fclX25InBRemPdnLinkAddress is not used.
                The default value is 'subscriber'."
        ::= { fclX25InBRemotePeerEntry 4 }


    fclX25InBRemSubscriberNumber OBJECT-TYPE
        SYNTAX  OCTET STRING (SIZE(1))
        ACCESS  read-write
        STATUS  mandatory
        DESCRIPTION
                "The value of this object is the SB number added to
                the DNICZO of the equipment to make the calling
                address in a call sent to this ISDN remote system
                (if fclX25InBRemConnectionType is set to
                'subscriber'). The value must contain 2 digits
                (digits 0..9). The default value is 'FF'."
        ::= { fclX25InBRemotePeerEntry 5 }


    fclX25InBRemPdnLinkAddress OBJECT-TYPE
        SYNTAX  OCTET STRING (SIZE(8))
        ACCESS  read-write
        STATUS  mandatory
        DESCRIPTION
                "The value of this object is the X121 address of
                the equipment on the connected network (if
                fclX25InBRemConnectionType is set to
                'publicNetwork'). The value may contain up to 15
                digits (digits 0..9). The value must be completed
                with 'F' digits for a total of 16 digits. The
                equipment configurator does not need final
                completion. The default value is 'FF FF FF FF FF
                FF FF FF' meaning 'empty value' (blank value on
                the equipment configurator)."
        ::= { fclX25InBRemotePeerEntry 6 }


    fclX25InBRemX25ConfigId OBJECT-TYPE
        SYNTAX  INTEGER (0..199)
        ACCESS  read-write
        STATUS  mandatory
        DESCRIPTION
                "The value of this object identifies the X25
                configuration used to establish the X25 VC towards
                the ISDN remote system. This X25 configuration
                must be present in fclX25ConfigAccessTable (case
                X25 access configuration if
                fclX25InBRemConnectionType is set to 'subscriber'
                or 'publicNetwork') or in
                fclX25ConfigInterNodeTable (case X25 inter-node
                configuration if fclX25InBRemConnectionType is set
                to 'interNode'). The possible values are :
                '0..199'. If it is unused, the value of this
                parameter is '255'."
        ::= { fclX25InBRemotePeerEntry 7 }


    fclX25InBRemPriority OBJECT-TYPE
        SYNTAX  INTEGER (0..15)
        ACCESS  read-write
        STATUS  mandatory
        DESCRIPTION
                "The value of this object indicates, when there is
                several ISDN remote system for only one X121
                address, in which order the equipment will try to
                call these several ISDN remote system to establish
                an ISDN B Channel. When a try to one ISDN remote
                system fails the equipment continues, in the
                increasing order of this parameter, with the
                following in the list until the end of the list.
                The possible values are : '0..15'. The default
                value is '0' (meaning 'first of the list')."
        ::= { fclX25InBRemotePeerEntry 8 }


    fclX25InBRemCallRetryCount OBJECT-TYPE
        SYNTAX  INTEGER (1..15)
        ACCESS  read-write
        STATUS  mandatory
        DESCRIPTION
                "The value of this object indicates how many times
                the equipment will try to call this particular
                ISDN remote system to establish an ISDN B Channel.
                The possible values are : '1..15'. The default
                value is '1'."
        ::= { fclX25InBRemotePeerEntry 9 }


    fclX25InBRemLinkCheckPeriod OBJECT-TYPE
        SYNTAX  INTEGER (200..50800)
        ACCESS  read-write
        STATUS  mandatory
        DESCRIPTION
                "The value of this object is the scanning time (in
                milliseconds) to detect the B-Channel state. The
                authorized values are '2000..50800' by steps of
                200 msec. The default value is '200'."
        ::= { fclX25InBRemotePeerEntry 10 }


    fclX25InBRemCheckPeriodCount OBJECT-TYPE
        SYNTAX  INTEGER (1..250)
        ACCESS  read-write
        STATUS  mandatory
        DESCRIPTION
                "The value of this object is the number of periods
                of 'fclX25InBRemLinkCheckPeriod' milliseconds
                before declaring the state of the B-Channel. The
                authorized values are '1..250'. The default value
                is '3'."
        ::= { fclX25InBRemotePeerEntry 11 }


    fclX25InPstn OBJECT IDENTIFIER ::= { fcLogicalPorts 23 }


    fclX25InPstnTable OBJECT-TYPE
        SYNTAX  SEQUENCE OF FclX25InPstnEntry
        ACCESS  not-accessible
        STATUS  mandatory
        DESCRIPTION
                "This table defines the general parameters of X25
                SLP (Single Link Protocol) in PSTN (Public
                Switched Telephone Network) link inter-node
                logical ports."
        ::= { fclX25InPstn 1 }


    fclX25InPstnEntry OBJECT-TYPE
        SYNTAX  FclX25InPstnEntry
        ACCESS  not-accessible
        STATUS  mandatory
        DESCRIPTION
                "An entry of fclX25InPstnTable."
        INDEX   { fclX25PstnLogPortId }
        ::= { fclX25InPstnTable 1 }


        FclX25InPstnEntry ::=
                SEQUENCE {
                    fclX25PstnLogPortId
                        INTEGER,
                    fclX25PstnInterfaceId
                        INTEGER,
                    fclX25PstnX25InterNodeConfigId
                        INTEGER
                }


    fclX25PstnLogPortId OBJECT-TYPE
        SYNTAX  INTEGER (0..181)
        ACCESS  read-only
        STATUS  mandatory
        DESCRIPTION
                "The value of this object identifies one and only
                one X25 in PSTN link logical port. The possible
                values are : '0..131'. If it is unused, the value
                of this parameter is '255'. The default value is
                '255'."
        ::= { fclX25InPstnEntry 1 }


    fclX25PstnInterfaceId OBJECT-TYPE
        SYNTAX  INTEGER (0..35)
        ACCESS  read-write
        STATUS  mandatory
        DESCRIPTION
                "The value of this object identifies the line
                interface used by this X25 in PSTN logical port.
                The possible values are : '0..35'. If it is
                unused, the value of this parameter is '255'. The
                default value is '255'."
        ::= { fclX25InPstnEntry 2 }


    fclX25PstnX25InterNodeConfigId OBJECT-TYPE
        SYNTAX  INTEGER (0..199)
        ACCESS  read-write
        STATUS  mandatory
        DESCRIPTION
                "The value of this object identifies the X25
                inter-node configuration used to establish the X25
                VC towards the PSTN remote system. This X25
                inter-node configuration must be present in
                fclX25ConfigInterNodeTable. The possible values
                are : '0..199'. If it is unused, the value of this
                parameter is '255'. The default value is '255'."
        ::= { fclX25InPstnEntry 3 }


    fclX25PstnRemotePeerTable OBJECT-TYPE
        SYNTAX  SEQUENCE OF FclX25PstnRemotePeerEntry
        ACCESS  not-accessible
        STATUS  mandatory
        DESCRIPTION
                "This table defines the PSTN remote systems which
                may be called by the equipment using a X25 in PSTN
                link logical ports ."
        ::= { fclX25InPstn 2 }


    fclX25PstnRemotePeerEntry OBJECT-TYPE
        SYNTAX  FclX25PstnRemotePeerEntry
        ACCESS  not-accessible
        STATUS  mandatory
        DESCRIPTION
                "An entry of fclX25PstnRemotePeerTable."
        INDEX   { fclX25PstnRemX121Addr }
        ::= { fclX25PstnRemotePeerTable 1 }


        FclX25PstnRemotePeerEntry ::=
                SEQUENCE {
                    fclX25PstnRemX121Addr
                        OCTET STRING,
                    fclX25PstnRemStatus
                        INTEGER,
                    fclX25PstnRemPstnNumber
                        OCTET STRING
                }


    fclX25PstnRemX121Addr OBJECT-TYPE
        SYNTAX  OCTET STRING (SIZE(8))
        ACCESS  read-only
        STATUS  mandatory
        DESCRIPTION
                "The value of this object is the X121 address of
                one PSTN remote system. The value may contain up
                to 15 digits (digits 0..9, B, D).

                The digits 'B', 'D' (respectively characters '*',
                '?' on the equipment configurator) have special
                meanings :

                   'B' matches any address. When used it must be
                        the only digit specified (with final
                        completion as explained below).

                   'D' matches any single digit.

                The value must be completed with 'F' digits for a
                total of 16 digits. The equipment configurator
                does not need final completion. The default value
                is 'FF FF FF FF FF FF FF FF' meaning 'empty value'
                (blank value on the equipment configurator)."
        ::= { fclX25PstnRemotePeerEntry 1 }


    fclX25PstnRemStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25PstnRemotePeerEntry 2 }


    fclX25PstnRemPstnNumber OBJECT-TYPE
        SYNTAX  OCTET STRING (SIZE(14))
        ACCESS  read-write
        STATUS  mandatory
        DESCRIPTION
                "The value of this object is the PSTN address of
                this PSTN remote system. The value may contain up
                to 28 digits (digits 0..E).

                The digits 'A', 'B', 'C', 'D', 'E' (respectively
                characters 'W', ',', 'P', 'T', '!' on the
                equipment configurator) have special meanings :
                   'A' means 'attente de tonalite',
                   'B' means 'pause of 2 seconds',
                   'C' means 'numerotation decimale',
                   'D' means 'numerotation multifrequence',
                   'E' means 'raccrocher 0.5 second'.

                The value must be completed with 'F' digits for a
                total of 28 digits. The equipment configurator
                does not need final completion. The default value
                is 'FF FF FF FF FF FF FF FF' meaning 'empty value'
                (blank value on the equipment configurator)."
        ::= { fclX25PstnRemotePeerEntry 3 }


    fclX25SlpInterNode OBJECT IDENTIFIER ::= { fcLogicalPorts 24 }


    fclX25SlpInterNodeTable OBJECT-TYPE
        SYNTAX  SEQUENCE OF FclX25SlpInterNodeEntry
        ACCESS  not-accessible
        STATUS  mandatory
        DESCRIPTION
                "This table defines the general parameters of X25
                SLP (Single Link Protocol) inter-node logical
                ports."
        ::= { fclX25SlpInterNode 1 }


    fclX25SlpInterNodeEntry OBJECT-TYPE
        SYNTAX  FclX25SlpInterNodeEntry
        ACCESS  not-accessible
        STATUS  mandatory
        DESCRIPTION
                "An entry of fclX25SlpInterNodeTable."
        INDEX   { fclX25SlpLogPortId }
        ::= { fclX25SlpInterNodeTable 1 }


        FclX25SlpInterNodeEntry ::=
                SEQUENCE {
                    fclX25SlpLogPortId
                        INTEGER,
                    fclX25SlpInterfaceId
                        INTEGER,
                    fclX25SlpIsdnBackupEnabling
                        INTEGER,
                    fclX25SlpPstnBackupEnabling
                        INTEGER,
                    fclX25SlpX25InterNodeConfigId
                        INTEGER,
                    fclX25SlpDARApplicable
                        INTEGER,
                    fclX25SlpBackupTimer
                        INTEGER
                }


    fclX25SlpLogPortId OBJECT-TYPE
        SYNTAX  INTEGER (0..181)
        ACCESS  read-only
        STATUS  mandatory
        DESCRIPTION
                "The value of this object identifies one and only
                one X25 SLP (Single Link Protocol) inter-node
                logical port. The possible values are : '0..131'.
                If it is unused, the value of this parameter is
                '255'. The default value is '255'."
        ::= { fclX25SlpInterNodeEntry 1 }


    fclX25SlpInterfaceId OBJECT-TYPE
        SYNTAX  INTEGER (0..181)
        ACCESS  read-write
        STATUS  mandatory
        DESCRIPTION
                "The value of this object identifies the line
                interface used by this X25 inter-node logical
                port. The possible values are : '0..35'. If it is
                unused, the value of this parameter is '255'. The
                default value is '255'."
        ::= { fclX25SlpInterNodeEntry 2 }


    fclX25SlpIsdnBackupEnabling OBJECT-TYPE
        SYNTAX  INTEGER {
                off(1),
                onWhileActivity(2),
                onWhileLpDown(3),
                onWhileExcessTraffic(7)
                }
        ACCESS  read-write
        STATUS  mandatory
        DESCRIPTION
                "The value of this object defines how this X25
                inter-node logical port may be backuped by an
                ISDN-B channel.

                 The possible values are :

                   off : backup is never enabled,

                   onWhileActivity : when the logical port is
                        DOWN, backup is enabled on reception of a
                        new call and remains active while at least
                        one X25 VC is using this way. When no VC
                        is active, the backup is disabled and the
                        next VC will be established on the logical
                        port (if it is UP obviously).

                   onWhileLpDown : when the logical port is DOWN,
                        backup is enabled on reception of a new
                        call and remains active while the logical
                        port is DOWN. The backup is disabled
                        (meaning clearing of all VCs using this
                        way) when the logical port comes back UP
                        and the next VC will be established on the
                        logical port.

                   onWhileExcessTraffic : when the traffic
                        overtakes the fclX25SlpSwSwitchThreshold
                        value the logical port state is marked
                        DOWN (meaning clearing of all VCs), backup
                        is enabled on reception of a new call and
                        remains active while the traffic is
                        overtaking the
                        fclX25SlpSwSwitchBackThreshold value. When
                        the traffic does not overtake any more the
                        fclX25SlpSwSwitchBackThreshold value, the
                        logical port is marked UP and the backup
                        is disabled (meaning clearing of all VCs
                        using this way) so the next VC will be
                        established on the logical port.

                        This Switch Over mechanism permits to
                        transmit temporay excess traffic which
                        could not be transmitted on the logical
                        port because of an insufficient bandwith
                        on a line interface with a speed
                        (fcfLineSpeed) inferior to 64 kbit/s.

                The default value is 'off'."
        ::= { fclX25SlpInterNodeEntry 3 }


    fclX25SlpPstnBackupEnabling OBJECT-TYPE
        SYNTAX  INTEGER {
                off(1),
                onWhileActivity(2),
                onWhileLpDown(3),
                onWhileExcessTraffic(7)
                }
        ACCESS  read-write
        STATUS  mandatory
        DESCRIPTION
                "The value of this object defines how this X25
                inter-node logical port may be backuped by a PSTN
                (Public Switched Telephone Network) link.

                 The possible values are :

                   off : backup is never enabled,

                   onWhileActivity : when the logical port is
                        DOWN, backup is enabled on reception of a
                        new call and remains active while at least
                        one X25 VC is using this way. When no VC
                        is active, the backup is disabled and the
                        next VC will be established on the logical
                        port (if it is UP obviously).

                   onWhileLpDown : when the logical port is DOWN,
                        backup is enabled on reception of a new
                        call and remains active while the logical
                        port is DOWN. The backup is disabled
                        (meaning clearing of all VCs using this
                        way) when the logical port comes back UP
                        and the next VC will be established on the
                        logical port.

                   onWhileExcessTraffic : when the traffic
                        overtakes the fclX25SlpSwSwitchThreshold
                        value the logical port state is marked
                        DOWN (meaning clearing of all VCs), backup
                        is enabled on reception of a new call and
                        remains active while the traffic is
                        overtaking the
                        fclX25SlpSwSwitchBackThreshold value. When
                        the traffic does not overtake any more the
                        fclX25SlpSwSwitchBackThreshold value, the
                        logical port is marked UP and the backup
                        is disabled (meaning clearing of all VCs
                        using this way) so the next VC will be
                        established on the logical port.

                        This Switch Over mechanism permits to
                        transmit temporay excess traffic which
                        could not be transmitted on the logical
                        port because of an insufficient bandwith
                        on a line interface with a speed
                        (fcfLineSpeed) inferior to the speed of a
                        PSTN link (depending on modem capability).

                The default value is 'off'."
        ::= { fclX25SlpInterNodeEntry 4 }


    fclX25SlpX25InterNodeConfigId OBJECT-TYPE
        SYNTAX  INTEGER (0..199)
        ACCESS  read-write
        STATUS  mandatory
        DESCRIPTION
                "The value of this object identifies the X25
                inter-node configuration used by this X25
                inter-node logical port. This X25 inter-node
                configuration must be present in
                fclX25ConfigInterNodeTable. The possible values
                are : '0..199. If it is unused, the value of this
                parameter is '255'."
        ::= { fclX25SlpInterNodeEntry 5 }


    fclX25SlpDARApplicable OBJECT-TYPE
        SYNTAX  INTEGER {
                no(1),
                yes(2)
                }
        ACCESS  read-write
        STATUS  mandatory
        DESCRIPTION
                "Ligne utilisable par le RAD"
        ::= { fclX25SlpInterNodeEntry 6 }


    fclX25SlpBackupTimer OBJECT-TYPE
        SYNTAX  INTEGER (0..2540)
        ACCESS  read-write
        STATUS  mandatory
        DESCRIPTION
                "Tempo de retour sur LS"
        ::= { fclX25SlpInterNodeEntry 7 }


    fclX25SlpSwitchOverTable OBJECT-TYPE
        SYNTAX  SEQUENCE OF FclX25SlpSwitchOverEntry
        ACCESS  not-accessible
        STATUS  mandatory
        DESCRIPTION
                "This table defines the switch over parameters of
                X25 inter-node logical ports using the switch over
                mechanism."
        ::= { fclX25SlpInterNode 2 }


    fclX25SlpSwitchOverEntry OBJECT-TYPE
        SYNTAX  FclX25SlpSwitchOverEntry
        ACCESS  not-accessible
        STATUS  mandatory
        DESCRIPTION
                "An entry of fclX25SlpSwitchOverTable."
        INDEX   { fclX25SlpSwLogPortId }
        ::= { fclX25SlpSwitchOverTable 1 }


        FclX25SlpSwitchOverEntry ::=
                SEQUENCE {
                    fclX25SlpSwLogPortId
                        INTEGER,
                    fclX25SlpSwMeasureCount
                        INTEGER,
                    fclX25SlpSwSwitchThreshold
                        INTEGER,
                    fclX25SlpSwSwitchBackThreshold
                        INTEGER
                }


    fclX25SlpSwLogPortId OBJECT-TYPE
        SYNTAX  INTEGER (0..181)
        ACCESS  read-only
        STATUS  mandatory
        DESCRIPTION
                "The value of this object identifies one and only
                one X25 inter-node logical port using the switch
                over mechanism (fclX25SlpIsdnBackupEnabling or
                fclX25SlpPstnBackupEnabling set to
                'onWhileExcessTraffic'). The possible values are :
                '0..131'. If it is unused, the value of this
                parameter is '255'. The default value is '255'."
        ::= { fclX25SlpSwitchOverEntry 1 }


    fclX25SlpSwMeasureCount OBJECT-TYPE
        SYNTAX  INTEGER (0..249)
        ACCESS  read-write
        STATUS  mandatory
        DESCRIPTION
                "The value of this object is the number of traffic
                measures before switching. The measure duration is
                defined by fcwLoadAndTrafficSummingPeriod. The
                authorized values are '0..249'. The default value
                is '2'."
        ::= { fclX25SlpSwitchOverEntry 2 }


    fclX25SlpSwSwitchThreshold OBJECT-TYPE
        SYNTAX  INTEGER (0..100)
        ACCESS  read-write
        STATUS  mandatory
        DESCRIPTION
                "The value of this object indicates the traffic
                threshold (in percents of bandwith of the main
                link of logical port) over which the switch over
                mechanism is enabled. The authorized values are
                '0..100'. The default value is '80'."
        ::= { fclX25SlpSwitchOverEntry 3 }


    fclX25SlpSwSwitchBackThreshold OBJECT-TYPE
        SYNTAX  INTEGER (0..100)
        ACCESS  read-write
        STATUS  mandatory
        DESCRIPTION
                "The value of this object indicates the traffic
                threshold (in percents of bandwith of the main
                link of logical port) under which the switch over
                mechanism is disabled. The authorized values are
                '0..100'. The default value is '60'."
        ::= { fclX25SlpSwitchOverEntry 4 }


    fclX25SlpIsdnBackupTable OBJECT-TYPE
        SYNTAX  SEQUENCE OF FclX25SlpIsdnBackupEntry
        ACCESS  not-accessible
        STATUS  mandatory
        DESCRIPTION
                "This table defines which ISDN Basic Rate Interface
                may be used by each X25 inter-node logical port
                when enabling backup on ISDN B-Channels."
        ::= { fclX25SlpInterNode 3 }


    fclX25SlpIsdnBackupEntry OBJECT-TYPE
        SYNTAX  FclX25SlpIsdnBackupEntry
        ACCESS  not-accessible
        STATUS  mandatory
        DESCRIPTION
                "An entry of fclX25SlpIsdnBackupTable."
        INDEX   { fclX25SlpIsdnBackLogPortId,
                  fclX25SlpIsdnBackIsdnInterfaceId }
        ::= { fclX25SlpIsdnBackupTable 1 }


        FclX25SlpIsdnBackupEntry ::=
                SEQUENCE {
                    fclX25SlpIsdnBackLogPortId
                        INTEGER,
                    fclX25SlpIsdnBackIsdnInterfaceId
                        INTEGER,
                    fclX25SlpIsdnBackStatus
                        INTEGER
                }


    fclX25SlpIsdnBackLogPortId OBJECT-TYPE
        SYNTAX  INTEGER (0..181)
        ACCESS  read-only
        STATUS  mandatory
        DESCRIPTION
                "The value of this object identifies one and only
                one X25 SLP (Single Link Protocol) inter-node
                logical port. One X25 inter-node logical port may
                use backup with one or several ISDN Basic Rate
                Interfaces. The possible values are : '0..131'. If
                it is unused, the value of this parameter is
                '255'. The default value is '255'."
        ::= { fclX25SlpIsdnBackupEntry 1 }


    fclX25SlpIsdnBackIsdnInterfaceId OBJECT-TYPE
        SYNTAX  INTEGER (0..35)
        ACCESS  read-only
        STATUS  mandatory
        DESCRIPTION
                "The value of this object identifies one ISDN Basic
                Rate Interface used by the X25 inter-node logical
                port defined by fclX25SlpIsdnBackLogPortId. The
                possible values are : '0..35'. If it is unused,
                the value of this parameter is '255'. The default
                value is '255'."
        ::= { fclX25SlpIsdnBackupEntry 2 }


    fclX25SlpIsdnBackStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25SlpIsdnBackupEntry 3 }


    fclX25SlpIsdnRemotePeerTable OBJECT-TYPE
        SYNTAX  SEQUENCE OF FclX25SlpIsdnRemotePeerEntry
        ACCESS  not-accessible
        STATUS  mandatory
        DESCRIPTION
                "This table defines the ISDN remote systems which
                may be connected to the equipment using the backup
                mechanism of X25 inter-node logical ports."
        ::= { fclX25SlpInterNode 4 }


    fclX25SlpIsdnRemotePeerEntry OBJECT-TYPE
        SYNTAX  FclX25SlpIsdnRemotePeerEntry
        ACCESS  not-accessible
        STATUS  mandatory
        DESCRIPTION
                "An entry of fclX25SlpIsdnRemotePeerTable."
        INDEX   { fclX25SlpIsdnRemLogPortId,
                  fclX25SlpIsdnRemIsdnInterfaceId }
        ::= { fclX25SlpIsdnRemotePeerTable 1 }


        FclX25SlpIsdnRemotePeerEntry ::=
                SEQUENCE {
                    fclX25SlpIsdnRemLogPortId
                        INTEGER,
                    fclX25SlpIsdnRemIsdnInterfaceId
                        INTEGER,
                    fclX25SlpIsdnRemStatus
                        INTEGER,
                    fclX25SlpIsdnRemX25InterNodeConfigId
                        INTEGER,
                    fclX25SlpIsdnRemPriority
                        INTEGER,
                    fclX25SlpIsdnRemCallRetryCount
                        INTEGER
                }


    fclX25SlpIsdnRemLogPortId OBJECT-TYPE
        SYNTAX  INTEGER (0..181)
        ACCESS  read-only
        STATUS  mandatory
        DESCRIPTION
                "The value of this object identifies one and only
                one X25 SLP (Single Link Protocol) inter-node
                logical port. One X25 inter-node logical port may
                use backup mechanism with one or several ISDN
                remote systems (these ISDN systems can be on
                different equipments). The possible values are :
                '0..131'. If it is unused, the value of this
                parameter is '255'. The default value is '255'."
        ::= { fclX25SlpIsdnRemotePeerEntry 1 }


    fclX25SlpIsdnRemIsdnInterfaceId OBJECT-TYPE
        SYNTAX  INTEGER (0..35)
        ACCESS  read-only
        STATUS  mandatory
        DESCRIPTION
                "The value of this object identifies one and only
                one ISDN remote system. This ISDN remote system
                must exist in fclIsdnRemotePeerTable. There may be
                several ISDN remote system for only one X25
                inter-node logical port (these ISDN systems can be
                on different equipments). The possible values are
                : '0..249'. If it is unused, the value of this
                parameter is '255'."
        ::= { fclX25SlpIsdnRemotePeerEntry 2 }


    fclX25SlpIsdnRemStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25SlpIsdnRemotePeerEntry 3 }


    fclX25SlpIsdnRemX25InterNodeConfigId OBJECT-TYPE
        SYNTAX  INTEGER (0..199)
        ACCESS  read-write
        STATUS  mandatory
        DESCRIPTION
                "The value of this object identifies the X25
                inter-node configuration used by this X25
                inter-node logical port backup link. This X25
                inter-node configuration must be present in
                fclX25ConfigInterNodeTable. The possible values
                are : '0..199. If it is unused, the value of this
                parameter is '255'."
        ::= { fclX25SlpIsdnRemotePeerEntry 4 }


    fclX25SlpIsdnRemPriority OBJECT-TYPE
        SYNTAX  INTEGER (0..15)
        ACCESS  read-write
        STATUS  mandatory
        DESCRIPTION
                "The value of this object indicates, when there is
                several ISDN remote system for only one X25
                inter-node logical port, in which order the
                equipment will try to call these several ISDN
                remote system to establish an ISDN B Channel. When
                a try to one ISDN remote system fails the
                equipment continues, in the increasing order of
                this parameter, with the following in the list
                until the end of the list. The possible values are
                : '0..15'. The default value is '0' (meaning
                'first of the list')."
        ::= { fclX25SlpIsdnRemotePeerEntry 5 }


    fclX25SlpIsdnRemCallRetryCount OBJECT-TYPE
        SYNTAX  INTEGER (1..15)
        ACCESS  read-write
        STATUS  mandatory
        DESCRIPTION
                "The value of this object indicates how many times
                the equipment will try to call this particular
                ISDN remote system to establish an ISDN B Channel.
                The possible values are : '1..15'. The default
                value is '1'."
        ::= { fclX25SlpIsdnRemotePeerEntry 6 }


    fclX25SlpPstnBackupTable OBJECT-TYPE
        SYNTAX  SEQUENCE OF FclX25SlpPstnBackupEntry
        ACCESS  not-accessible
        STATUS  mandatory
        DESCRIPTION
                "This table defines which line interface may be
                used by each X25 inter-node logical ports when
                enabling backup mechanism on PSTN links."
        ::= { fclX25SlpInterNode 5 }


    fclX25SlpPstnBackupEntry OBJECT-TYPE
        SYNTAX  FclX25SlpPstnBackupEntry
        ACCESS  not-accessible
        STATUS  mandatory
        DESCRIPTION
                "An entry of fclX25SlpPstnBackupTable."
        INDEX   { fclX25SlpPstnBackLogPortId }
        ::= { fclX25SlpPstnBackupTable 1 }


        FclX25SlpPstnBackupEntry ::=
                SEQUENCE {
                    fclX25SlpPstnBackLogPortId
                        INTEGER,
                    fclX25SlpPstnBackStatus
                        INTEGER,
                    fclX25SlpPstnBackInterfaceId
                        INTEGER,
                    fclX25SlpPstnBackPstnNumber
                        OCTET STRING,
                    fclX25SlpPstnBackX25InterNodeConfigId
                        INTEGER
                }


    fclX25SlpPstnBackLogPortId OBJECT-TYPE
        SYNTAX  INTEGER (0..181)
        ACCESS  read-only
        STATUS  mandatory
        DESCRIPTION
                "The value of this object identifies one and only
                one X25 SLP (Single Link Protocol) inter-node
                logical port. The possible values are : '0..131'.
                If it is unused, the value of this parameter is
                '255'. The default value is '255'."
        ::= { fclX25SlpPstnBackupEntry 1 }


    fclX25SlpPstnBackStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25SlpPstnBackupEntry 2 }


    fclX25SlpPstnBackInterfaceId OBJECT-TYPE
        SYNTAX  INTEGER (0..35)
        ACCESS  read-write
        STATUS  mandatory
        DESCRIPTION
                "The value of this object identifies the line
                interface used by the X25 inter-node logical port
                defined by fclX25SlpPstnBackLogPortId. The
                possible values are : '0..35'. If it is unused,
                the value of this parameter is '255'. The default
                value is '255'."
        ::= { fclX25SlpPstnBackupEntry 3 }


    fclX25SlpPstnBackPstnNumber OBJECT-TYPE
        SYNTAX  OCTET STRING (SIZE(14))
        ACCESS  read-write
        STATUS  mandatory
        DESCRIPTION
                "The value of this object is the PSTN address of
                this PSTN remote system. The value may contain up
                to 28 digits (digits 0..E).

                The digits 'A', 'B', 'C', 'D', 'E' (respectively
                characters 'W', ',', 'P', 'T', '!' on the
                equipment configurator) have special meanings :
                   'A' means 'attente de tonalite',
                   'B' means 'pause of 2 seconds',
                   'C' means 'numerotation decimale',
                   'D' means 'numerotation multifrequence',
                   'E' means 'raccrocher 0.5 second'.

                The value must be completed with 'F' digits for a
                total of 28 digits. The equipment configurator
                does not need final completion. The default value
                is 'FF FF FF FF FF FF FF FF' meaning 'empty value'
                (blank value on the equipment configurator)."
        ::= { fclX25SlpPstnBackupEntry 4 }


    fclX25SlpPstnBackX25InterNodeConfigId OBJECT-TYPE
        SYNTAX  INTEGER (0..199)
        ACCESS  read-write
        STATUS  mandatory
        DESCRIPTION
                "The value of this object identifies the X25
                inter-node configuration used by this X25
                inter-node logical port backup link. This X25
                inter-node configuration must be present in
                fclX25ConfigInterNodeTable. The possible values
                are : '0..199. If it is unused, the value of this
                parameter is '255'."
        ::= { fclX25SlpPstnBackupEntry 5 }


    fclX25Mlp OBJECT IDENTIFIER ::= { fcLogicalPorts 25 }


    fclX25MlpTable OBJECT-TYPE
        SYNTAX  SEQUENCE OF FclX25MlpEntry
        ACCESS  not-accessible
        STATUS  mandatory
        DESCRIPTION
                "This table defines the general parameters of X25
                MLP (Multi-Link Protocol) inter-node logical ports."
        ::= { fclX25Mlp 1 }


    fclX25MlpEntry OBJECT-TYPE
        SYNTAX  FclX25MlpEntry
        ACCESS  not-accessible
        STATUS  mandatory
        DESCRIPTION
                "An entry of fclX25MlpTable."
        INDEX   { fclX25MlpLogPortId }
        ::= { fclX25MlpTable 1 }


        FclX25MlpEntry ::=
                SEQUENCE {
                    fclX25MlpLogPortId
                        INTEGER,
                    fclX25MlpLink1InterfaceId
                        INTEGER,
                    fclX25MlpLink2InterfaceId
                        INTEGER,
                    fclX25MlpLink3InterfaceId
                        INTEGER,
                    fclX25MlpLink4InterfaceId
                        INTEGER,
                    fclX25MlpIsdnOverflow
                        INTEGER,
                    fclX25MlpPstnOverflow
                        INTEGER,
                    fclX25MlpX25InterNodeConfigId
                        INTEGER,
                    fclX25MlpDARApplicable
                        INTEGER
                }


    fclX25MlpLogPortId OBJECT-TYPE
        SYNTAX  INTEGER (0..181)
        ACCESS  read-only
        STATUS  mandatory
        DESCRIPTION
                "The value of this object identifies one and only
                one X25 MLP (Multi-Link Protocol) inter-node
                logical port. The possible values are : '0..131'.
                If it is unused, the value of this parameter is
                '255'. The default value is '255'."
        ::= { fclX25MlpEntry 1 }


    fclX25MlpLink1InterfaceId OBJECT-TYPE
        SYNTAX  INTEGER (0..35)
        ACCESS  read-write
        STATUS  mandatory
        DESCRIPTION
                "The value of this object identifies the first line
                interface used by this X25 MLP logical port. This
                line interface is mandatory. The possible values
                are : '0..35'. If it is unused, the value of this
                parameter is '255'. The default value is '255'."
        ::= { fclX25MlpEntry 2 }


    fclX25MlpLink2InterfaceId OBJECT-TYPE
        SYNTAX  INTEGER (0..35)
        ACCESS  read-write
        STATUS  mandatory
        DESCRIPTION
                "The value of this object identifies the second
                line interface used by this X25 MLP logical port.
                This line interface is optional. The possible
                values are : '0..35'. If it is unused, the value
                of this parameter is '255'. The default value is
                '255'."
        ::= { fclX25MlpEntry 3 }


    fclX25MlpLink3InterfaceId OBJECT-TYPE
        SYNTAX  INTEGER (0..35)
        ACCESS  read-write
        STATUS  mandatory
        DESCRIPTION
                "The value of this object identifies the third line
                interface used by this X25 MLP logical port. This
                line interface is optional. The possible values
                are : '0..35'. If it is unused, the value of this
                parameter is '255'. The default value is '255'."
        ::= { fclX25MlpEntry 4 }


    fclX25MlpLink4InterfaceId OBJECT-TYPE
        SYNTAX  INTEGER (0..35)
        ACCESS  read-write
        STATUS  mandatory
        DESCRIPTION
                "The value of this object identifies the fourth
                line interface used by this X25 MLP logical port.
                This line interface is optional. The possible
                values are : '0..35'. If it is unused, the value
                of this parameter is '255'. The default value is
                '255'."
        ::= { fclX25MlpEntry 5 }


    fclX25MlpIsdnOverflow OBJECT-TYPE
        SYNTAX  INTEGER {
                off(1),
                onSlave(2),
                onMasterWhileActivity(10),
                onMasterWhileExcessTraffic(11)
                }
        ACCESS  read-write
        STATUS  mandatory
        DESCRIPTION
                "The value of this object defines how this X25 MLP
                logical port may use additional ISDN-B channel to
                transmit temporary excess traffic (overflow
                mechanism). When opening or closing additional
                B-Channels the existing VCs are not cleared, so
                this overflow mechanism does not alter the
                communication between the two extremities.

                 The possible values are :

                   off : overflow is never enabled,

                   onSlave : overflow is enabled by the connected
                        equipment,

                   onMasterWhileActivity : when the traffic
                        overtakes the fclX25MlpOvOverflowThreshold
                        value for all the links in use (line
                        interfaces and eventual ISDN B-Channels),
                        a new ISDN B-Channel is open by the
                        equipment and remains active while at
                        least one X25 VC is using this way. When
                        no VC is active, this ISDN B-Channel is
                        closed.

                   onMasterWhileExcessTraffic : when the traffic
                        overtakes the fclX25MlpOvOverflowThreshold
                        value for all the links in use (line
                        interfaces and eventual ISDN B-Channels),
                        a new ISDN B-Channel is open by the
                        equipment and remains active while the
                        traffic is overtaking the
                        fclX25SlpOvOverflowBackThreshold value.
                        When the traffic does not overtake any
                        more the fclX25SlpOvOverflowBackThreshold
                        value, this ISDN B-Channel is closed.

                When one line interface is DOWN its bandwith is
                considered as being 0. So the overflow mechanism
                may be used as a backup mechanism which permits to
                not clear existing VCs.

                The default value is 'off'."
        ::= { fclX25MlpEntry 6 }


    fclX25MlpPstnOverflow OBJECT-TYPE
        SYNTAX  INTEGER {
                off(1),
                onSlave(2),
                onMasterWhileActivity(10),
                onMasterWhileExcessTraffic(11)
                }
        ACCESS  read-write
        STATUS  mandatory
        DESCRIPTION
                "The value of this object defines how this X25 MLP
                logical port may use additional PSTN links to
                transmit temporary excess traffic (overflow
                mechanism). When opening or closing additional
                PSTN links the existing VCs are not cleared, so
                this overflow mechanism does not alter the
                communication between the two extremities.

                 The possible values are :

                   off : overflow is never enabled,

                   onSlave : overflow is enabled by the connected
                        equipment,

                   onMasterWhileActivity : when the traffic
                        overtakes the fclX25MlpOvOverflowThreshold
                        value for all the links in use (line
                        interfaces and eventual PSTN links), a new
                        PSTN link is open by the equipment and
                        remains active while at least one X25 VC
                        is using this way. When no VC is active,
                        this PSTN link is closed.

                   onMasterWhileExcessTraffic : when the traffic
                        overtakes the fclX25MlpOvOverflowThreshold
                        value for all the links in use (line
                        interfaces and eventual PSTN links), a new
                        PSTN link is open by the equipment and
                        remains active while the traffic is
                        overtaking the
                        fclX25SlpOvOverflowBackThreshold value.
                        When the traffic does not overtake any
                        more the fclX25SlpOvOverflowBackThreshold
                        value, this PSTN link is closed.

                When one line interface is DOWN its bandwith is
                considered as being 0. So the overflow mechanism
                may be used as a backup mechanism which permits to
                not clear existing VCs.

                The default value is 'off'."
        ::= { fclX25MlpEntry 7 }


    fclX25MlpX25InterNodeConfigId OBJECT-TYPE
        SYNTAX  INTEGER (0..199)
        ACCESS  read-write
        STATUS  mandatory
        DESCRIPTION
                "The value of this object identifies the X25
                inter-node configuration used by this X25 MLP
                logical port. This X25 inter-node configuration
                must be present in fclX25ConfigInterNodeTable. The
                possible values are : '0..199. If it is unused,
                the value of this parameter is '255'."
        ::= { fclX25MlpEntry 8 }


    fclX25MlpDARApplicable OBJECT-TYPE
        SYNTAX  INTEGER {
                no(1),
                yes(2)
                }
        ACCESS  read-write
        STATUS  mandatory
        DESCRIPTION
                "Ligne utilisable par le RAD"
        ::= { fclX25MlpEntry 9 }


    fclX25MlpParameterTable OBJECT-TYPE
        SYNTAX  SEQUENCE OF FclX25MlpParameterEntry
        ACCESS  not-accessible
        STATUS  mandatory
        DESCRIPTION
                "This table defines the MLP parameters of X25 MLP
                (Multi-Link Protocol) inter-node logical ports."
        ::= { fclX25Mlp 2 }


    fclX25MlpParameterEntry OBJECT-TYPE
        SYNTAX  FclX25MlpParameterEntry
        ACCESS  not-accessible
        STATUS  mandatory
        DESCRIPTION
                "An entry of fclX25MlpParameterTable."
        INDEX   { fclX25MlpParamLogPortId }
        ::= { fclX25MlpParameterTable 1 }


        FclX25MlpParameterEntry ::=
                SEQUENCE {
                    fclX25MlpParamLogPortId
                        INTEGER,
                    fclX25MlpMwMultilinkWindowSize
                        INTEGER,
                    fclX25MlpRxMlpMxWinGuardRegion
                        INTEGER,
                    fclX25MlpMt1LostFrameTimer
                        INTEGER,
                    fclX25MlpMt3ResetConfirmationTimer
                        INTEGER,
                    fclX25MlpMt4DownLinkDetectionTimer
                        INTEGER,
                    fclX25MlpFramesMaxCountByLink
                        INTEGER,
                    fclX25MlpRestartTxAfterResetRx
                        INTEGER,
                    fclX25MlpTns3Level3CheckTimer
                        INTEGER
                }


    fclX25MlpParamLogPortId OBJECT-TYPE
        SYNTAX  INTEGER (0..181)
        ACCESS  read-only
        STATUS  mandatory
        DESCRIPTION
                "The value of this object identifies one and only
                one X25 MLP (Multi-Link Protocol) inter-node
                logical port. The possible values are : '0..131'.
                If it is unused, the value of this parameter is
                '255'. The default value is '255'."
        ::= { fclX25MlpParameterEntry 1 }


    fclX25MlpMwMultilinkWindowSize OBJECT-TYPE
        SYNTAX  INTEGER (1..32)
        ACCESS  read-write
        STATUS  mandatory
        DESCRIPTION
                "The value of this object is the maximum number
                (MW) of sequentially numbered multilink frames
                that the DCE or DTE may transfer which the lowest
                numbered multilink frame which has not yet been
                acknowledged beyond. This parameter shall have the
                same value for both switching points. The
                authorized values are '1..32'. The default value
                is '32'."
        ::= { fclX25MlpParameterEntry 2 }


    fclX25MlpRxMlpMxWinGuardRegion OBJECT-TYPE
        SYNTAX  INTEGER (1..32)
        ACCESS  read-write
        STATUS  mandatory
        DESCRIPTION
                "The value of this object defines a guard region
                (MX) of multilink sequence numbers of fixed size.
                The range of MX shall be large enough for that the
                receiving MLP recognizes the highest numbered
                frame that it may receive after the multilink
                frame loss. The window MX must be smaller than or
                equal to the window MW. The authorized values are
                '1..32'. The default value is '32'."
        ::= { fclX25MlpParameterEntry 3 }


    fclX25MlpMt1LostFrameTimer OBJECT-TYPE
        SYNTAX  INTEGER (1..255)
        ACCESS  read-write
        STATUS  mandatory
        DESCRIPTION
                "The value of this object defines the timer (MT1),
                in seconds, which a transmitted frames is declared
                lost beyond. The authorized values are '1..255'.
                The default value is '22'."
        ::= { fclX25MlpParameterEntry 4 }


    fclX25MlpMt3ResetConfirmationTimer OBJECT-TYPE
        SYNTAX  INTEGER (1..255)
        ACCESS  read-write
        STATUS  mandatory
        DESCRIPTION
                "The value of this object defines the maximum time
                (MT3), in seconds, between a reset request and a
                reset confirmation, which the multilink resetting
                procedure restarts beyond. The authorized values
                are '1..255'. The default value is '10'."
        ::= { fclX25MlpParameterEntry 5 }


    fclX25MlpMt4DownLinkDetectionTimer OBJECT-TYPE
        SYNTAX  INTEGER (0..255)
        ACCESS  read-write
        STATUS  mandatory
        DESCRIPTION
                "The value of this object defines the timer (MT4),
                in seconds, which the line is declared down
                beyond. The line is out if all the lines of the
                MLP group are down. The authorized values are
                '0..255'. The default value is '40'."
        ::= { fclX25MlpParameterEntry 6 }


    fclX25MlpFramesMaxCountByLink OBJECT-TYPE
        SYNTAX  INTEGER (1..255)
        ACCESS  read-write
        STATUS  mandatory
        DESCRIPTION
                "The value of this object is the maximum number of
                transmitted frames on a line. The authorized
                values are '1..255'. The default value is '3'."
        ::= { fclX25MlpParameterEntry 7 }


    fclX25MlpRestartTxAfterResetRx OBJECT-TYPE
        SYNTAX  INTEGER {
                off(1),
                on(2)
                }
        ACCESS  read-write
        STATUS  mandatory
        DESCRIPTION
                "The value of this object indicates if there is
                recovery after MLP reset. The authorized values
                are 'off' or 'on'. The default value is 'on'."
        ::= { fclX25MlpParameterEntry 8 }


    fclX25MlpTns3Level3CheckTimer OBJECT-TYPE
        SYNTAX  INTEGER (0..255)
        ACCESS  read-write
        STATUS  mandatory
        DESCRIPTION
                "The value of this object defines the timer, in
                seconds, between a sending of frames and the
                reception of its acknowledges, which the multilink
                resetting procedure restarts beyond. The
                authorized values are '0..255' by step of 10
                seconds. The default value is '10'."
        ::= { fclX25MlpParameterEntry 9 }


    fclX25MlpOverflowTable OBJECT-TYPE
        SYNTAX  SEQUENCE OF FclX25MlpOverflowEntry
        ACCESS  not-accessible
        STATUS  mandatory
        DESCRIPTION
                "This table defines the overflow parameters of X25
                MLP logical ports enabling the overflow mechanism."
        ::= { fclX25Mlp 3 }


    fclX25MlpOverflowEntry OBJECT-TYPE
        SYNTAX  FclX25MlpOverflowEntry
        ACCESS  not-accessible
        STATUS  mandatory
        DESCRIPTION
                "An entry of fclX25MlpOverflowTable."
        INDEX   { fclX25MlpOvLogPortId }
        ::= { fclX25MlpOverflowTable 1 }


        FclX25MlpOverflowEntry ::=
                SEQUENCE {
                    fclX25MlpOvLogPortId
                        INTEGER,
                    fclX25MlpOvMeasureCount
                        INTEGER,
                    fclX25MlpOvOverflowThreshold
                        INTEGER,
                    fclX25MlpOvOverflowBackThreshold
                        INTEGER
                }


    fclX25MlpOvLogPortId OBJECT-TYPE
        SYNTAX  INTEGER (0..181)
        ACCESS  read-only
        STATUS  mandatory
        DESCRIPTION
                "The value of this object identifies one and only
                one X25 MLP logical port enabling the overflow
                mechanism (fclX25MlpIsdnOverflow or
                fclX25MlpPstnOverflow set to
                'onMasterWhileActivity',
                'onMasterWhileExcessTraffic'). The possible values
                are : '0..131'. If it is unused, the value of this
                parameter is '255'. The default value is '255'."
        ::= { fclX25MlpOverflowEntry 1 }


    fclX25MlpOvMeasureCount OBJECT-TYPE
        SYNTAX  INTEGER (0..249)
        ACCESS  read-write
        STATUS  mandatory
        DESCRIPTION
                "The value of this object is the number of traffic
                measures before opening an additional link. The
                measure duration is defined by
                fcwLoadAndTrafficSummingPeriod. The authorized
                values are '0..249'. The default value is '2'."
        ::= { fclX25MlpOverflowEntry 2 }


    fclX25MlpOvOverflowThreshold OBJECT-TYPE
        SYNTAX  INTEGER (0..100)
        ACCESS  read-write
        STATUS  mandatory
        DESCRIPTION
                "The value of this object indicates the traffic
                threshold (in percents of bandwith of alls the
                link in use by this logical port) over which a new
                link is open. The authorized values are '0..100'.
                The default value is '80'."
        ::= { fclX25MlpOverflowEntry 3 }


    fclX25MlpOvOverflowBackThreshold OBJECT-TYPE
        SYNTAX  INTEGER (0..100)
        ACCESS  read-write
        STATUS  mandatory
        DESCRIPTION
                "The value of this object indicates the traffic
                threshold (in percents of bandwith of alls the
                link in use by this logical port) under which the
                last open link is closed. The authorized values
                are '0..100'. The default value is '60'."
        ::= { fclX25MlpOverflowEntry 4 }


    fclX25MlpIsdnOverflowTable OBJECT-TYPE
        SYNTAX  SEQUENCE OF FclX25MlpIsdnOverflowEntry
        ACCESS  not-accessible
        STATUS  mandatory
        DESCRIPTION
                "This table defines which ISDN Basic Rate Interface
                may be used by each X25 MLP logical ports when
                enabling overflow mechanism on ISDN B-Channels."
        ::= { fclX25Mlp 4 }


    fclX25MlpIsdnOverflowEntry OBJECT-TYPE
        SYNTAX  FclX25MlpIsdnOverflowEntry
        ACCESS  not-accessible
        STATUS  mandatory
        DESCRIPTION
                "An entry of fclX25MlpIsdnOverflowTable."
        INDEX   { fclX25MlpIsdnOverLogPortId,
                  fclX25MlpIsdnOverIsdnInterfaceId }
        ::= { fclX25MlpIsdnOverflowTable 1 }


        FclX25MlpIsdnOverflowEntry ::=
                SEQUENCE {
                    fclX25MlpIsdnOverLogPortId
                        INTEGER,
                    fclX25MlpIsdnOverIsdnInterfaceId
                        INTEGER,
                    fclX25MlpIsdnOverStatus
                        INTEGER,
                    fclX25MlpIsdnOverBChannelCount
                        INTEGER
                }


    fclX25MlpIsdnOverLogPortId OBJECT-TYPE
        SYNTAX  INTEGER (0..181)
        ACCESS  read-only
        STATUS  mandatory
        DESCRIPTION
                "The value of this object identifies one and only
                one X25 MLP (Multi-Link Protocol) inter-node
                logical port. One X25 MLP logical port may use
                overflow mechanism with one or several ISDN Basic
                Rate Interfaces. The possible values are :
                '0..131'. If it is unused, the value of this
                parameter is '255'. The default value is '255'."
        ::= { fclX25MlpIsdnOverflowEntry 1 }


    fclX25MlpIsdnOverIsdnInterfaceId OBJECT-TYPE
        SYNTAX  INTEGER (0..35)
        ACCESS  read-only
        STATUS  mandatory
        DESCRIPTION
                "The value of this object identifies one ISDN Basic
                Rate Interface used by the X25 MLP logical port
                defined by fclX25MlpIsdnOverLogPortId. The
                possible values are : '0..35'. If it is unused,
                the value of this parameter is '255'. The default
                value is '255'."
        ::= { fclX25MlpIsdnOverflowEntry 2 }


    fclX25MlpIsdnOverStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25MlpIsdnOverflowEntry 3 }


    fclX25MlpIsdnOverBChannelCount OBJECT-TYPE
        SYNTAX  INTEGER (1..30)
        ACCESS  read-write
        STATUS  mandatory
        DESCRIPTION
                "The value of this object is the number of B
                channels of this ISDN Basic Rate Interface that
                may be used. The authorized values are '1..30'.
                The default value is '2'."
        ::= { fclX25MlpIsdnOverflowEntry 4 }


    fclX25MlpIsdnRemotePeerTable OBJECT-TYPE
        SYNTAX  SEQUENCE OF FclX25MlpIsdnRemotePeerEntry
        ACCESS  not-accessible
        STATUS  mandatory
        DESCRIPTION
                "This table defines the ISDN remote systems which
                may be connected to the equipment using the
                overflow mechanism of X25 MLP logical ports."
        ::= { fclX25Mlp 5 }


    fclX25MlpIsdnRemotePeerEntry OBJECT-TYPE
        SYNTAX  FclX25MlpIsdnRemotePeerEntry
        ACCESS  not-accessible
        STATUS  mandatory
        DESCRIPTION
                "An entry of fclX25MlpIsdnRemotePeerTable."
        INDEX   { fclX25MlpIsdnRemLogPortId,
                  fclX25MlpIsdnRemPeerId }
        ::= { fclX25MlpIsdnRemotePeerTable 1 }


        FclX25MlpIsdnRemotePeerEntry ::=
                SEQUENCE {
                    fclX25MlpIsdnRemLogPortId
                        INTEGER,
                    fclX25MlpIsdnRemPeerId
                        INTEGER,
                    fclX25MlpIsdnRemStatus
                        INTEGER,
                    fclX25MlpIsdnRemPriority
                        INTEGER,
                    fclX25MlpIsdnRemCallRetryCount
                        INTEGER
                }


    fclX25MlpIsdnRemLogPortId OBJECT-TYPE
        SYNTAX  INTEGER (0..181)
        ACCESS  read-only
        STATUS  mandatory
        DESCRIPTION
                "The value of this object identifies one and only
                one X25 MLP (Multi-Link Protocol) inter-node
                logical port. One X25 MLP logical port may use
                overflow mechanism with one or several ISDN remote
                systems (but all these ISDN systems must be on the
                same equipment to make X25 MLP work correctly).
                The possible values are : '0..131'. If it is
                unused, the value of this parameter is '255'. The
                default value is '255'."
        ::= { fclX25MlpIsdnRemotePeerEntry 1 }


    fclX25MlpIsdnRemPeerId OBJECT-TYPE
        SYNTAX  INTEGER (0..249)
        ACCESS  read-only
        STATUS  mandatory
        DESCRIPTION
                "The value of this object identifies one and only
                one ISDN remote system. This ISDN remote system
                must exist in fclIsdnRemotePeerTable. There may be
                several ISDN remote system for only one X25 MLP
                logical port (but all these ISDN systems must be
                on the same equipment to make X25 MLP work
                correctly). The possible values are : '0..249'. If
                it is unused, the value of this parameter is '255'."
        ::= { fclX25MlpIsdnRemotePeerEntry 2 }


    fclX25MlpIsdnRemStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25MlpIsdnRemotePeerEntry 3 }


    fclX25MlpIsdnRemPriority OBJECT-TYPE
        SYNTAX  INTEGER (0..15)
        ACCESS  read-write
        STATUS  mandatory
        DESCRIPTION
                "The value of this object indicates, when there is
                several ISDN remote system for only one X25 MLP
                logical port, in which order the equipment will
                try to call these several ISDN remote system to
                establish an ISDN B Channel. When a try to one
                ISDN remote system fails the equipment continues,
                in the increasing order of this parameter, with
                the following in the list until the end of the
                list. The possible values are : '0..15'. The
                default value is '0' (meaning 'first of the list')."
        ::= { fclX25MlpIsdnRemotePeerEntry 4 }


    fclX25MlpIsdnRemCallRetryCount OBJECT-TYPE
        SYNTAX  INTEGER (1..15)
        ACCESS  read-write
        STATUS  mandatory
        DESCRIPTION
                "The value of this object indicates how many times
                the equipment will try to call this particular
                ISDN remote system to establish an ISDN B Channel.
                The possible values are : '1..15'. The default
                value is '1'."
        ::= { fclX25MlpIsdnRemotePeerEntry 5 }


    fclX25MlpPstnOverflowTable OBJECT-TYPE
        SYNTAX  SEQUENCE OF FclX25MlpPstnOverflowEntry
        ACCESS  not-accessible
        STATUS  mandatory
        DESCRIPTION
                "This table defines which line interface may be
                used by each X25 MLP logical ports when enabling
                overflow mechanism on PSTN links."
        ::= { fclX25Mlp 6 }


    fclX25MlpPstnOverflowEntry OBJECT-TYPE
        SYNTAX  FclX25MlpPstnOverflowEntry
        ACCESS  not-accessible
        STATUS  mandatory
        DESCRIPTION
                "An entry of fclX25MlpPstnOverflowTable."
        INDEX   { fclX25MlpPstnOvLogPortId }
        ::= { fclX25MlpPstnOverflowTable 1 }


        FclX25MlpPstnOverflowEntry ::=
                SEQUENCE {
                    fclX25MlpPstnOvLogPortId
                        INTEGER,
                    fclX25MlpPstnOvStatus
                        INTEGER,
                    fclX25MlpPstnOvInterfaceId
                        INTEGER,
                    fclX25MlpPstnOvPstnNumber
                        OCTET STRING
                }


    fclX25MlpPstnOvLogPortId OBJECT-TYPE
        SYNTAX  INTEGER (0..181)
        ACCESS  read-only
        STATUS  mandatory
        DESCRIPTION
                "The value of this object identifies one and only
                one X25 MLP (Multi-Link Protocol) inter-node
                logical port. The possible values are : '0..131'.
                If it is unused, the value of this parameter is
                '255'. The default value is '255'."
        ::= { fclX25MlpPstnOverflowEntry 1 }


    fclX25MlpPstnOvStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25MlpPstnOverflowEntry 2 }


    fclX25MlpPstnOvInterfaceId OBJECT-TYPE
        SYNTAX  INTEGER (0..35)
        ACCESS  read-write
        STATUS  mandatory
        DESCRIPTION
                "The value of this object identifies the line
                interface used by the X25 MLP logical port defined
                by fclX25MlpPstnOverLogPortId. The possible values
                are : '0..35'. If it is unused, the value of this
                parameter is '255'. The default value is '255'."
        ::= { fclX25MlpPstnOverflowEntry 3 }


    fclX25MlpPstnOvPstnNumber OBJECT-TYPE
        SYNTAX  OCTET STRING (SIZE(14))
        ACCESS  read-write
        STATUS  mandatory
        DESCRIPTION
                "The value of this object is the PSTN address of
                this PSTN remote system. The value may contain up
                to 28 digits (digits 0..E).

                The digits 'A', 'B', 'C', 'D', 'E' (respectively
                characters 'W', ',', 'P', 'T', '!' on the
                equipment configurator) have special meanings :
                   'A' means 'attente de tonalite',
                   'B' means 'pause of 2 seconds',
                   'C' means 'numerotation decimale',
                   'D' means 'numerotation multifrequence',
                   'E' means 'raccrocher 0.5 second'.

                The value must be completed with 'F' digits for a
                total of 28 digits. The equipment configurator
                does not need final completion. The default value
                is 'FF FF FF FF FF FF FF FF' meaning 'empty value'
                (blank value on the equipment configurator)."
        ::= { fclX25MlpPstnOverflowEntry 4 }


    fclPointToPointProtocol OBJECT IDENTIFIER ::= { fcLogicalPorts 30 }


    fclPppSerialLinkAccess OBJECT IDENTIFIER ::= { fclPointToPointProtocol 1 }


    fclPppSerialLogPortTable OBJECT-TYPE
        SYNTAX  SEQUENCE OF FclPppSerialLogPortEntry
        ACCESS  not-accessible
        STATUS  mandatory
        DESCRIPTION
                ""
        ::= { fclPppSerialLinkAccess 1 }


    fclPppSerialLogPortEntry OBJECT-TYPE
        SYNTAX  FclPppSerialLogPortEntry
        ACCESS  not-accessible
        STATUS  mandatory
        DESCRIPTION
                "An entry of fclPppSerialLogPortTable."
        INDEX   { fclPppSerLpLogPortId }
        ::= { fclPppSerialLogPortTable 1 }


        FclPppSerialLogPortEntry ::=
                SEQUENCE {
                    fclPppSerLpLogPortId
                        INTEGER,
                    fclPppSerLpInterfaceId
                        INTEGER,
                    fclPppSerLpLocalSubscriberNb
                        OCTET STRING,
                    fclPppSerLpConfigId
                        INTEGER,
                    fclPppSerLpCos
                        INTEGER,
                    fclPppSerLpCir
                        INTEGER,
                    fclPppSerLpMinCir
                        INTEGER,
                    fclPppSerLpBe
                        INTEGER
                }


    fclPppSerLpLogPortId OBJECT-TYPE
        SYNTAX  INTEGER (0..181)
        ACCESS  read-only
        STATUS  mandatory
        DESCRIPTION
                "LP id"
        ::= { fclPppSerialLogPortEntry 1 }


    fclPppSerLpInterfaceId OBJECT-TYPE
        SYNTAX  INTEGER (0..181)
        ACCESS  read-write
        STATUS  mandatory
        DESCRIPTION
                "IF id (type ligne)"
        ::= { fclPppSerialLogPortEntry 2 }


    fclPppSerLpLocalSubscriberNb OBJECT-TYPE
        SYNTAX  OCTET STRING (SIZE(1))
        ACCESS  read-write
        STATUS  mandatory
        DESCRIPTION
                "Numero d'abonne"
        ::= { fclPppSerialLogPortEntry 3 }


    fclPppSerLpConfigId OBJECT-TYPE
        SYNTAX  INTEGER (0..199)
        ACCESS  read-write
        STATUS  mandatory
        DESCRIPTION
                "Config PPP id"
        ::= { fclPppSerialLogPortEntry 10 }


    fclPppSerLpCos OBJECT-TYPE
        SYNTAX  INTEGER {
                ubr(3),
                vbr(1)
                }
        ACCESS  read-write
        STATUS  mandatory
        DESCRIPTION
                "COS"
        ::= { fclPppSerialLogPortEntry 20 }


    fclPppSerLpCir OBJECT-TYPE
        SYNTAX  INTEGER (600..2048000)
        ACCESS  read-write
        STATUS  mandatory
        DESCRIPTION
                "Entrant CIR"
        ::= { fclPppSerialLogPortEntry 21 }


    fclPppSerLpMinCir OBJECT-TYPE
        SYNTAX  INTEGER (0..2048000)
        ACCESS  read-write
        STATUS  mandatory
        DESCRIPTION
                "Entrant CIR mini"
        ::= { fclPppSerialLogPortEntry 22 }


    fclPppSerLpBe OBJECT-TYPE
        SYNTAX  INTEGER (0..2048000)
        ACCESS  read-write
        STATUS  mandatory
        DESCRIPTION
                "Entrant BE"
        ::= { fclPppSerialLogPortEntry 23 }


    fclPppSerialAutoCallTable OBJECT-TYPE
        SYNTAX  SEQUENCE OF FclPppSerialAutoCallEntry
        ACCESS  not-accessible
        STATUS  mandatory
        DESCRIPTION
                ""
        ::= { fclPppSerialLinkAccess 2 }


    fclPppSerialAutoCallEntry OBJECT-TYPE
        SYNTAX  FclPppSerialAutoCallEntry
        ACCESS  not-accessible
        STATUS  mandatory
        DESCRIPTION
                "An entry of fclPppSerialAutoCallTable."
        INDEX   { fclPppSerAutoLogPortId }
        ::= { fclPppSerialAutoCallTable 1 }


        FclPppSerialAutoCallEntry ::=
                SEQUENCE {
                    fclPppSerAutoLogPortId
                        INTEGER,
                    fclPppSerAutoStatus
                        INTEGER,
                    fclPppSerAutoRemoteAddress
                        OCTET STRING,
                    fclPppSerAutoMinimumRecallTimer
                        INTEGER,
                    fclPppSerAutoInactivityTimer
                        INTEGER,
                    fclPppSerAutoReliableVc
                        INTEGER,
                    fclPppSerAutoCompression
                        INTEGER,
                    fclPppSerAutoCompressNegotiation
                        INTEGER,
                    fclPppSerAutoCompressScrambling
                        INTEGER,
                    fclPppSerAutoCompressMultiPktTimer
                        INTEGER
                }


    fclPppSerAutoLogPortId OBJECT-TYPE
        SYNTAX  INTEGER (0..181)
        ACCESS  read-only
        STATUS  mandatory
        DESCRIPTION
                "LP id"
        ::= { fclPppSerialAutoCallEntry 1 }


    fclPppSerAutoStatus OBJECT-TYPE
        SYNTAX  INTEGER {
                valid(1),
                invalid(2)
                }
        ACCESS  read-write
        STATUS  mandatory
        DESCRIPTION
                "Status"
        ::= { fclPppSerialAutoCallEntry 2 }


    fclPppSerAutoRemoteAddress OBJECT-TYPE
        SYNTAX  OCTET STRING (SIZE(8))
        ACCESS  read-write
        STATUS  mandatory
        DESCRIPTION
                "Adresse du point vise"
        ::= { fclPppSerialAutoCallEntry 3 }


    fclPppSerAutoMinimumRecallTimer OBJECT-TYPE
        SYNTAX  INTEGER (0..990)
        ACCESS  read-write
        STATUS  mandatory
        DESCRIPTION
                "Tempo de retransmission appel"
        ::= { fclPppSerialAutoCallEntry 7 }


    fclPppSerAutoInactivityTimer OBJECT-TYPE
        SYNTAX  INTEGER (0..2540)
        ACCESS  read-write
        STATUS  mandatory
        DESCRIPTION
                "Duree de silence (Tb)"
        ::= { fclPppSerialAutoCallEntry 8 }


    fclPppSerAutoReliableVc OBJECT-TYPE
        SYNTAX  INTEGER {
                off(3),
                on(2)
                }
        ACCESS  read-write
        STATUS  mandatory
        DESCRIPTION
                "CV fiabilise"
        ::= { fclPppSerialAutoCallEntry 10 }


    fclPppSerAutoCompression OBJECT-TYPE
        SYNTAX  INTEGER {
                off(1),
                networkToSubscriber(2),
                subscriberToNetwork(3),
                bothway(4)
                }
        ACCESS  read-write
        STATUS  mandatory
        DESCRIPTION
                "Compression : abonnement et direction"
        ::= { fclPppSerialAutoCallEntry 11 }


    fclPppSerAutoCompressNegotiation OBJECT-TYPE
        SYNTAX  INTEGER {
                off(1),
                onOptionalCompression(2),
                onMandatoryCompression(3)
                }
        ACCESS  read-write
        STATUS  mandatory
        DESCRIPTION
                "Compression : negociation et caractere"
        ::= { fclPppSerialAutoCallEntry 12 }


    fclPppSerAutoCompressScrambling OBJECT-TYPE
        SYNTAX  INTEGER {
                off(1),
                on(2)
                }
        ACCESS  read-write
        STATUS  mandatory
        DESCRIPTION
                "Compression : brouillage"
        ::= { fclPppSerialAutoCallEntry 13 }


    fclPppSerAutoCompressMultiPktTimer OBJECT-TYPE
        SYNTAX  INTEGER (0..1500)
        ACCESS  read-write
        STATUS  mandatory
        DESCRIPTION
                "Compression : tempo attente multi-paquet msec"
        ::= { fclPppSerialAutoCallEntry 14 }


    fclPppPstnAccess OBJECT IDENTIFIER ::= { fclPointToPointProtocol 2 }


    fclPppPstnLogPortTable OBJECT-TYPE
        SYNTAX  SEQUENCE OF FclPppPstnLogPortEntry
        ACCESS  not-accessible
        STATUS  mandatory
        DESCRIPTION
                ""
        ::= { fclPppPstnAccess 1 }


    fclPppPstnLogPortEntry OBJECT-TYPE
        SYNTAX  FclPppPstnLogPortEntry
        ACCESS  not-accessible
        STATUS  mandatory
        DESCRIPTION
                "An entry of fclPppPstnLogPortTable."
        INDEX   { fclPppPstnLpLogPortId }
        ::= { fclPppPstnLogPortTable 1 }


        FclPppPstnLogPortEntry ::=
                SEQUENCE {
                    fclPppPstnLpLogPortId
                        INTEGER,
                    fclPppPstnLpInterfaceId
                        INTEGER,
                    fclPppPstnLpLocalSubscriberNb
                        OCTET STRING,
                    fclPppPstnLpConfigId
                        INTEGER
                }


    fclPppPstnLpLogPortId OBJECT-TYPE
        SYNTAX  INTEGER (0..181)
        ACCESS  read-only
        STATUS  mandatory
        DESCRIPTION
                "LP id"
        ::= { fclPppPstnLogPortEntry 1 }


    fclPppPstnLpInterfaceId OBJECT-TYPE
        SYNTAX  INTEGER (0..35)
        ACCESS  read-write
        STATUS  mandatory
        DESCRIPTION
                "IF id (de type ligne)"
        ::= { fclPppPstnLogPortEntry 2 }


    fclPppPstnLpLocalSubscriberNb OBJECT-TYPE
        SYNTAX  OCTET STRING (SIZE(1))
        ACCESS  read-write
        STATUS  mandatory
        DESCRIPTION
                "Numero d'abonne"
        ::= { fclPppPstnLogPortEntry 3 }


    fclPppPstnLpConfigId OBJECT-TYPE
        SYNTAX  INTEGER (0..199)
        ACCESS  read-write
        STATUS  mandatory
        DESCRIPTION
                "Config PPP id"
        ::= { fclPppPstnLogPortEntry 10 }


    fclPppPstnRemotePeerTable OBJECT-TYPE
        SYNTAX  SEQUENCE OF FclPppPstnRemotePeerEntry
        ACCESS  not-accessible
        STATUS  mandatory
        DESCRIPTION
                ""
        ::= { fclPppPstnAccess 2 }


    fclPppPstnRemotePeerEntry OBJECT-TYPE
        SYNTAX  FclPppPstnRemotePeerEntry
        ACCESS  not-accessible
        STATUS  mandatory
        DESCRIPTION
                "An entry of fclPppPstnRemotePeerTable."
        INDEX   { fclPppPstnRemX121Addr }
        ::= { fclPppPstnRemotePeerTable 1 }


        FclPppPstnRemotePeerEntry ::=
                SEQUENCE {
                    fclPppPstnRemX121Addr
                        OCTET STRING,
                    fclPppPstnRemStatus
                        INTEGER,
                    fclPppPstnRemPstnNumber
                        OCTET STRING
                }


    fclPppPstnRemX121Addr OBJECT-TYPE
        SYNTAX  OCTET STRING (SIZE(8))
        ACCESS  read-only
        STATUS  mandatory
        DESCRIPTION
                "Adresse X121"
        ::= { fclPppPstnRemotePeerEntry 1 }


    fclPppPstnRemStatus OBJECT-TYPE
        SYNTAX  INTEGER {
                valid(1),
                invalid(2)
                }
        ACCESS  read-write
        STATUS  mandatory
        DESCRIPTION
                "Status"
        ::= { fclPppPstnRemotePeerEntry 2 }


    fclPppPstnRemPstnNumber OBJECT-TYPE
        SYNTAX  OCTET STRING (SIZE(14))
        ACCESS  read-write
        STATUS  mandatory
        DESCRIPTION
                "Numero RTC"
        ::= { fclPppPstnRemotePeerEntry 3 }


    fclPppBIsdnAccess OBJECT IDENTIFIER ::= { fclPointToPointProtocol 3 }


    fclPppBIsdnLogPortTable OBJECT-TYPE
        SYNTAX  SEQUENCE OF FclPppBIsdnLogPortEntry
        ACCESS  not-accessible
        STATUS  mandatory
        DESCRIPTION
                ""
        ::= { fclPppBIsdnAccess 1 }


    fclPppBIsdnLogPortEntry OBJECT-TYPE
        SYNTAX  FclPppBIsdnLogPortEntry
        ACCESS  not-accessible
        STATUS  mandatory
        DESCRIPTION
                "An entry of fclPppBIsdnLogPortTable."
        INDEX   { fclPppBIsdnLpLogPortId }
        ::= { fclPppBIsdnLogPortTable 1 }


        FclPppBIsdnLogPortEntry ::=
                SEQUENCE {
                    fclPppBIsdnLpLogPortId
                        INTEGER,
                    fclPppBIsdnLpIsdnInterfaceId
                        INTEGER
                }


    fclPppBIsdnLpLogPortId OBJECT-TYPE
        SYNTAX  INTEGER (0..181)
        ACCESS  read-only
        STATUS  mandatory
        DESCRIPTION
                "LP id"
        ::= { fclPppBIsdnLogPortEntry 1 }


    fclPppBIsdnLpIsdnInterfaceId OBJECT-TYPE
        SYNTAX  INTEGER (0..35)
        ACCESS  read-write
        STATUS  mandatory
        DESCRIPTION
                "IF id (de type RNIS S0)"
        ::= { fclPppBIsdnLogPortEntry 2 }


    fclPppBIsdnLocalBriTable OBJECT-TYPE
        SYNTAX  SEQUENCE OF FclPppBIsdnLocalBriEntry
        ACCESS  not-accessible
        STATUS  mandatory
        DESCRIPTION
                ""
        ::= { fclPppBIsdnAccess 2 }


    fclPppBIsdnLocalBriEntry OBJECT-TYPE
        SYNTAX  FclPppBIsdnLocalBriEntry
        ACCESS  not-accessible
        STATUS  mandatory
        DESCRIPTION
                "An entry of fclPppBIsdnLocalBriTable."
        INDEX   { fclPppBIsdnBriId }
        ::= { fclPppBIsdnLocalBriTable 1 }


        FclPppBIsdnLocalBriEntry ::=
                SEQUENCE {
                    fclPppBIsdnBriId
                        INTEGER,
                    fclPppBIsdnBriStatus
                        INTEGER,
                    fclPppBIsdnBriLocalSubsNb1
                        OCTET STRING,
                    fclPppBIsdnBriLocalSubsNb2
                        OCTET STRING
                }


    fclPppBIsdnBriId OBJECT-TYPE
        SYNTAX  INTEGER (0..35)
        ACCESS  read-only
        STATUS  mandatory
        DESCRIPTION
                "IF id (de type RNIS S0)"
        ::= { fclPppBIsdnLocalBriEntry 1 }


    fclPppBIsdnBriStatus OBJECT-TYPE
        SYNTAX  INTEGER {
                valid(1),
                invalid(2)
                }
        ACCESS  read-write
        STATUS  mandatory
        DESCRIPTION
                "Status"
        ::= { fclPppBIsdnLocalBriEntry 2 }


    fclPppBIsdnBriLocalSubsNb1 OBJECT-TYPE
        SYNTAX  OCTET STRING (SIZE(1))
        ACCESS  read-write
        STATUS  mandatory
        DESCRIPTION
                "Numero d'abonne 1"
        ::= { fclPppBIsdnLocalBriEntry 3 }


    fclPppBIsdnBriLocalSubsNb2 OBJECT-TYPE
        SYNTAX  OCTET STRING (SIZE(1))
        ACCESS  read-write
        STATUS  mandatory
        DESCRIPTION
                "Numero d'abonne 2"
        ::= { fclPppBIsdnLocalBriEntry 4 }


    fclPppBIsdnRemotePeerTable OBJECT-TYPE
        SYNTAX  SEQUENCE OF FclPppBIsdnRemotePeerEntry
        ACCESS  not-accessible
        STATUS  mandatory
        DESCRIPTION
                ""
        ::= { fclPppBIsdnAccess 3 }


    fclPppBIsdnRemotePeerEntry OBJECT-TYPE
        SYNTAX  FclPppBIsdnRemotePeerEntry
        ACCESS  not-accessible
        STATUS  mandatory
        DESCRIPTION
                "An entry of fclPppBIsdnRemotePeerTable."
        INDEX   { fclPppBIsdnRemX121Addr,
                  fclPppBIsdnRemPeerId }
        ::= { fclPppBIsdnRemotePeerTable 1 }


        FclPppBIsdnRemotePeerEntry ::=
                SEQUENCE {
                    fclPppBIsdnRemX121Addr
                        OCTET STRING,
                    fclPppBIsdnRemPeerId
                        INTEGER,
                    fclPppBIsdnRemStatus
                        INTEGER,
                    fclPppBIsdnRemConfigId
                        INTEGER,
                    fclPppBIsdnRemPriority
                        INTEGER,
                    fclPppBIsdnRemCallRetryCount
                        INTEGER,
                    fclPppBIsdnRemLinkCheckPeriod
                        INTEGER,
                    fclPppBIsdnRemCheckPeriodCount
                        INTEGER
                }


    fclPppBIsdnRemX121Addr OBJECT-TYPE
        SYNTAX  OCTET STRING (SIZE(8))
        ACCESS  read-only
        STATUS  mandatory
        DESCRIPTION
                "Adresse X121"
        ::= { fclPppBIsdnRemotePeerEntry 1 }


    fclPppBIsdnRemPeerId OBJECT-TYPE
        SYNTAX  INTEGER (0..999)
        ACCESS  read-only
        STATUS  mandatory
        DESCRIPTION
                "Interface RNIS distante id"
        ::= { fclPppBIsdnRemotePeerEntry 2 }


    fclPppBIsdnRemStatus OBJECT-TYPE
        SYNTAX  INTEGER {
                valid(1),
                invalid(2)
                }
        ACCESS  read-write
        STATUS  mandatory
        DESCRIPTION
                "Status"
        ::= { fclPppBIsdnRemotePeerEntry 3 }


    fclPppBIsdnRemConfigId OBJECT-TYPE
        SYNTAX  INTEGER (0..199)
        ACCESS  read-write
        STATUS  mandatory
        DESCRIPTION
                "Config PPP id"
        ::= { fclPppBIsdnRemotePeerEntry 4 }


    fclPppBIsdnRemPriority OBJECT-TYPE
        SYNTAX  INTEGER (0..15)
        ACCESS  read-write
        STATUS  mandatory
        DESCRIPTION
                "Priorite"
        ::= { fclPppBIsdnRemotePeerEntry 5 }


    fclPppBIsdnRemCallRetryCount OBJECT-TYPE
        SYNTAX  INTEGER (1..15)
        ACCESS  read-write
        STATUS  mandatory
        DESCRIPTION
                "Nb de tentatives appel"
        ::= { fclPppBIsdnRemotePeerEntry 6 }


    fclPppBIsdnRemLinkCheckPeriod OBJECT-TYPE
        SYNTAX  INTEGER (200..50800)
        ACCESS  read-write
        STATUS  mandatory
        DESCRIPTION
                "Periode de surveillance jonction (msec)"
        ::= { fclPppBIsdnRemotePeerEntry 7 }


    fclPppBIsdnRemCheckPeriodCount OBJECT-TYPE
        SYNTAX  INTEGER (1..250)
        ACCESS  read-write
        STATUS  mandatory
        DESCRIPTION
                "Confirmation au bout de n periodes"
        ::= { fclPppBIsdnRemotePeerEntry 8 }


    fclPppBIsdnLocalPriTable OBJECT-TYPE
        SYNTAX  SEQUENCE OF FclPppBIsdnLocalPriEntry
        ACCESS  not-accessible
        STATUS  mandatory
        DESCRIPTION
                ""
        ::= { fclPppBIsdnAccess 4 }


    fclPppBIsdnLocalPriEntry OBJECT-TYPE
        SYNTAX  FclPppBIsdnLocalPriEntry
        ACCESS  not-accessible
        STATUS  mandatory
        DESCRIPTION
                "An entry of fclPppBIsdnLocalPriTable."
        INDEX   { fclPppBIsdnPriId }
        ::= { fclPppBIsdnLocalPriTable 1 }


        FclPppBIsdnLocalPriEntry ::=
                SEQUENCE {
                    fclPppBIsdnPriId
                        INTEGER,
                    fclPppBIsdnPriStatus
                        INTEGER,
                    fclPppBIsdnPriLocalSubs
                        DisplayString
                }


    fclPppBIsdnPriId OBJECT-TYPE
        SYNTAX  INTEGER (0..35)
        ACCESS  read-only
        STATUS  mandatory
        DESCRIPTION
                "IF id (de type RNIS S2)"
        ::= { fclPppBIsdnLocalPriEntry 1 }


    fclPppBIsdnPriStatus OBJECT-TYPE
        SYNTAX  INTEGER {
                valid(1),
                invalid(2)
                }
        ACCESS  read-write
        STATUS  mandatory
        DESCRIPTION
                "Status"
        ::= { fclPppBIsdnLocalPriEntry 2 }


    fclPppBIsdnPriLocalSubs OBJECT-TYPE
        SYNTAX  DisplayString (SIZE(0..24))
        ACCESS  read-write
        STATUS  mandatory
        DESCRIPTION
                "Numero d'abonne"
        ::= { fclPppBIsdnLocalPriEntry 3 }


    fclPppConfig OBJECT IDENTIFIER ::= { fclPointToPointProtocol 10 }


    fclPppConfigurationsTable OBJECT-TYPE
        SYNTAX  SEQUENCE OF FclPppConfigurationsEntry
        ACCESS  not-accessible
        STATUS  mandatory
        DESCRIPTION
                ""
        ::= { fclPppConfig 10 }


    fclPppConfigurationsEntry OBJECT-TYPE
        SYNTAX  FclPppConfigurationsEntry
        ACCESS  not-accessible
        STATUS  mandatory
        DESCRIPTION
                "An entry of fclPppConfigurationsTable."
        INDEX   { fclPppCfgConfigId }
        ::= { fclPppConfigurationsTable 1 }


        FclPppConfigurationsEntry ::=
                SEQUENCE {
                    fclPppCfgConfigId
                        INTEGER,
                    fclPppCfgStatus
                        INTEGER,
                    fclPppCfgDescription
                        DisplayString,
                    fclPppCfgLcpMagicNumber
                        INTEGER,
                    fclPppCfgLcpLocalMru
                        INTEGER,
                    fclPppCfgLcpLocalMtu
                        INTEGER,
                    fclPppCfgNcpBridge
                        INTEGER,
                    fclPppCfgNcpIp
                        INTEGER,
                    fclPppCfgNcpIpx
                        INTEGER,
                    fclPppCfgNcpClnp
                        INTEGER,
                    fclPppCfgAuthentication
                        INTEGER,
                    fclPppCfgAuthenticationMode
                        INTEGER,
                    fclPppCfgIpAddrAssignment
                        INTEGER
                }


    fclPppCfgConfigId OBJECT-TYPE
        SYNTAX  INTEGER (0..199)
        ACCESS  read-only
        STATUS  mandatory
        DESCRIPTION
                "Config PPP id"
        ::= { fclPppConfigurationsEntry 1 }


    fclPppCfgStatus OBJECT-TYPE
        SYNTAX  INTEGER {
                valid(1),
                invalid(2)
                }
        ACCESS  read-write
        STATUS  mandatory
        DESCRIPTION
                "Status"
        ::= { fclPppConfigurationsEntry 2 }


    fclPppCfgDescription OBJECT-TYPE
        SYNTAX  DisplayString (SIZE(0..32))
        ACCESS  read-write
        STATUS  mandatory
        DESCRIPTION
                "Description"
        ::= { fclPppConfigurationsEntry 3 }


    fclPppCfgLcpMagicNumber OBJECT-TYPE
        SYNTAX  INTEGER {
                off(1),
                on(2)
                }
        ACCESS  read-write
        STATUS  mandatory
        DESCRIPTION
                "LCP Utilisation du Magic Number"
        ::= { fclPppConfigurationsEntry 10 }


    fclPppCfgLcpLocalMru OBJECT-TYPE
        SYNTAX  INTEGER {
                mru100(1),
                mru200(2),
                mru300(3),
                mru400(4),
                mru500(5),
                mru600(6),
                mru700(7),
                mru800(8),
                mru900(9),
                mru1000(10),
                mru1100(11),
                mru1200(12),
                mru1300(13),
                mru1400(14),
                mru1500(15),
                mru1600(16)
                }
        ACCESS  read-write
        STATUS  mandatory
        DESCRIPTION
                "LCP Local Maximum Receive Unit"
        ::= { fclPppConfigurationsEntry 11 }


    fclPppCfgLcpLocalMtu OBJECT-TYPE
        SYNTAX  INTEGER {
                mtu100(1),
                mtu200(2),
                mtu300(3),
                mtu400(4),
                mtu500(5),
                mtu600(6),
                mtu700(7),
                mtu800(8),
                mtu900(9),
                mtu1000(10),
                mtu1100(11),
                mtu1200(12),
                mtu1300(13),
                mtu1400(14),
                mtu1500(15),
                mtu1600(16)
                }
        ACCESS  read-write
        STATUS  mandatory
        DESCRIPTION
                "LCP Local Maximum Transmit Unit"
        ::= { fclPppConfigurationsEntry 12 }


    fclPppCfgNcpBridge OBJECT-TYPE
        SYNTAX  INTEGER {
                off(1),
                on(2)
                }
        ACCESS  read-write
        STATUS  mandatory
        DESCRIPTION
                "Bridge NCP"
        ::= { fclPppConfigurationsEntry 20 }


    fclPppCfgNcpIp OBJECT-TYPE
        SYNTAX  INTEGER {
                off(1),
                on(2)
                }
        ACCESS  read-write
        STATUS  mandatory
        DESCRIPTION
                "IP NCP"
        ::= { fclPppConfigurationsEntry 25 }


    fclPppCfgNcpIpx OBJECT-TYPE
        SYNTAX  INTEGER {
                off(1),
                on(2)
                }
        ACCESS  read-write
        STATUS  mandatory
        DESCRIPTION
                "IPX NCP"
        ::= { fclPppConfigurationsEntry 30 }


    fclPppCfgNcpClnp OBJECT-TYPE
        SYNTAX  INTEGER {
                off(1),
                on(2)
                }
        ACCESS  read-write
        STATUS  mandatory
        DESCRIPTION
                "CLNP NCP"
        ::= { fclPppConfigurationsEntry 35 }


    fclPppCfgAuthentication OBJECT-TYPE
        SYNTAX  INTEGER {
                off(1),
                pap(2),
                chap(3),
                papAndChap(4)
                }
        ACCESS  read-write
        STATUS  mandatory
        DESCRIPTION
                "Option authentification"
        ::= { fclPppConfigurationsEntry 40 }


    fclPppCfgAuthenticationMode OBJECT-TYPE
        SYNTAX  INTEGER {
                master(1),
                slave(2),
                masterAndSlave(3)
                }
        ACCESS  read-write
        STATUS  mandatory
        DESCRIPTION
                "Mode authentification"
        ::= { fclPppConfigurationsEntry 41 }


    fclPppCfgIpAddrAssignment OBJECT-TYPE
        SYNTAX  INTEGER {
                off(1),
                byLocalSubscriber(2),
                byRemotePeer(3)
                }
        ACCESS  read-write
        STATUS  mandatory
        DESCRIPTION
                "Option adresse IP dynamique"
        ::= { fclPppConfigurationsEntry 42 }


    fclPppConfigTimersTable OBJECT-TYPE
        SYNTAX  SEQUENCE OF FclPppConfigTimersEntry
        ACCESS  not-accessible
        STATUS  mandatory
        DESCRIPTION
                ""
        ::= { fclPppConfig 11 }


    fclPppConfigTimersEntry OBJECT-TYPE
        SYNTAX  FclPppConfigTimersEntry
        ACCESS  not-accessible
        STATUS  mandatory
        DESCRIPTION
                "An entry of fclPppConfigTimersTable."
        INDEX   { fclPppCftConfigId }
        ::= { fclPppConfigTimersTable 1 }


        FclPppConfigTimersEntry ::=
                SEQUENCE {
                    fclPppCftConfigId
                        INTEGER,
                    fclPppCftLcpEchoRequestPeriod
                        INTEGER,
                    fclPppCftConnectionTimer
                        INTEGER,
                    fclPppCftRestartTimer
                        INTEGER,
                    fclPppCftConfigureMaxCount
                        INTEGER,
                    fclPppCftTerminateMaxCount
                        INTEGER,
                    fclPppCftFailureMaxCount
                        INTEGER
                }


    fclPppCftConfigId OBJECT-TYPE
        SYNTAX  INTEGER (0..199)
        ACCESS  read-only
        STATUS  mandatory
        DESCRIPTION
                "Config PPP id"
        ::= { fclPppConfigTimersEntry 1 }


    fclPppCftLcpEchoRequestPeriod OBJECT-TYPE
        SYNTAX  INTEGER (1..254)
        ACCESS  read-write
        STATUS  mandatory
        DESCRIPTION
                "Periode d'emission des echo requests LCP"
        ::= { fclPppConfigTimersEntry 10 }


    fclPppCftConnectionTimer OBJECT-TYPE
        SYNTAX  INTEGER (1..254)
        ACCESS  read-write
        STATUS  mandatory
        DESCRIPTION
                "Temporisateur de surveillance"
        ::= { fclPppConfigTimersEntry 20 }


    fclPppCftRestartTimer OBJECT-TYPE
        SYNTAX  INTEGER (1..254)
        ACCESS  read-write
        STATUS  mandatory
        DESCRIPTION
                "Tempo de reemission des messages "
        ::= { fclPppConfigTimersEntry 21 }


    fclPppCftConfigureMaxCount OBJECT-TYPE
        SYNTAX  INTEGER (1..254)
        ACCESS  read-write
        STATUS  mandatory
        DESCRIPTION
                "Nombre max de retransmission des configure request"
        ::= { fclPppConfigTimersEntry 22 }


    fclPppCftTerminateMaxCount OBJECT-TYPE
        SYNTAX  INTEGER (1..254)
        ACCESS  read-write
        STATUS  mandatory
        DESCRIPTION
                "Nombre max de retransmission des terminate request"
        ::= { fclPppConfigTimersEntry 23 }


    fclPppCftFailureMaxCount OBJECT-TYPE
        SYNTAX  INTEGER (1..254)
        ACCESS  read-write
        STATUS  mandatory
        DESCRIPTION
                "Nombre max de retransmission des configure nak"
        ::= { fclPppConfigTimersEntry 24 }


    fclPppConfigAuthentication OBJECT IDENTIFIER ::= { fclPppConfig 20 }


    fclPppCfaLocalIdentifier OBJECT-TYPE
        SYNTAX  DisplayString (SIZE(1..16))
        ACCESS  read-write
        STATUS  mandatory
        DESCRIPTION
                "Identite de l'equipement local"
        ::= { fclPppConfigAuthentication 1 }


    fclPppCfaLocalPassword OBJECT-TYPE
        SYNTAX  DisplayString (SIZE(1..16))
        ACCESS  read-write
        STATUS  mandatory
        DESCRIPTION
                "Mot de passe de l'equipement local"
        ::= { fclPppConfigAuthentication 2 }


    fclPppCfaRemotePeerTable OBJECT-TYPE
        SYNTAX  SEQUENCE OF FclPppCfaRemotePeerEntry
        ACCESS  not-accessible
        STATUS  mandatory
        DESCRIPTION
                ""
        ::= { fclPppConfigAuthentication 10 }


    fclPppCfaRemotePeerEntry OBJECT-TYPE
        SYNTAX  FclPppCfaRemotePeerEntry
        ACCESS  not-accessible
        STATUS  mandatory
        DESCRIPTION
                "An entry of fclPppCfaRemotePeerTable."
        INDEX   { fclPppCfaRemPeerId }
        ::= { fclPppCfaRemotePeerTable 1 }


        FclPppCfaRemotePeerEntry ::=
                SEQUENCE {
                    fclPppCfaRemPeerId
                        INTEGER,
                    fclPppCfaRemStatus
                        INTEGER,
                    fclPppCfaRemIdentifier
                        DisplayString,
                    fclPppCfaRemPassword
                        DisplayString
                }


    fclPppCfaRemPeerId OBJECT-TYPE
        SYNTAX  INTEGER (0..249)
        ACCESS  read-only
        STATUS  mandatory
        DESCRIPTION
                "Distant Id"
        ::= { fclPppCfaRemotePeerEntry 1 }


    fclPppCfaRemStatus OBJECT-TYPE
        SYNTAX  INTEGER {
                valid(1),
                invalid(2)
                }
        ACCESS  read-write
        STATUS  mandatory
        DESCRIPTION
                "Status"
        ::= { fclPppCfaRemotePeerEntry 2 }


    fclPppCfaRemIdentifier OBJECT-TYPE
        SYNTAX  DisplayString (SIZE(1..16))
        ACCESS  read-write
        STATUS  mandatory
        DESCRIPTION
                "Identite de l'equipement distant"
        ::= { fclPppCfaRemotePeerEntry 3 }


    fclPppCfaRemPassword OBJECT-TYPE
        SYNTAX  DisplayString (SIZE(1..16))
        ACCESS  read-write
        STATUS  mandatory
        DESCRIPTION
                "Mot de passe de l'equipement distant"
        ::= { fclPppCfaRemotePeerEntry 4 }


    fclFrameRelay OBJECT IDENTIFIER ::= { fcLogicalPorts 40 }


    fclFrCommunicationEquipment OBJECT IDENTIFIER ::= { fclFrameRelay 1 }


    fclFrCeLogPortTable OBJECT-TYPE
        SYNTAX  SEQUENCE OF FclFrCeLogPortEntry
        ACCESS  not-accessible
        STATUS  mandatory
        DESCRIPTION
                ""
        ::= { fclFrCommunicationEquipment 1 }


    fclFrCeLogPortEntry OBJECT-TYPE
        SYNTAX  FclFrCeLogPortEntry
        ACCESS  not-accessible
        STATUS  mandatory
        DESCRIPTION
                "An entry of fclFrCeLogPortTable."
        INDEX   { fclFrCeLpLogPortId }
        ::= { fclFrCeLogPortTable 1 }


        FclFrCeLogPortEntry ::=
                SEQUENCE {
                    fclFrCeLpLogPortId
                        INTEGER,
                    fclFrCeLpInterfaceId
                        INTEGER,
                    fclFrCeLpLocalAddress
                        OCTET STRING,
                    fclFrCeLpConfigId
                        INTEGER,
                    fclFrCeLpLmi
                        INTEGER
                }


    fclFrCeLpLogPortId OBJECT-TYPE
        SYNTAX  INTEGER (0..181)
        ACCESS  read-only
        STATUS  mandatory
        DESCRIPTION
                "LP Id"
        ::= { fclFrCeLogPortEntry 1 }


    fclFrCeLpInterfaceId OBJECT-TYPE
        SYNTAX  INTEGER (0..181)
        ACCESS  read-write
        STATUS  mandatory
        DESCRIPTION
                "IF Id (type ligne)"
        ::= { fclFrCeLogPortEntry 2 }


    fclFrCeLpLocalAddress OBJECT-TYPE
        SYNTAX  OCTET STRING (SIZE(8))
        ACCESS  read-write
        STATUS  mandatory
        DESCRIPTION
                "Adresse de localisation sur le plan d'adressage du
                routage (Numero d'abonne)"
        ::= { fclFrCeLogPortEntry 5 }


    fclFrCeLpConfigId OBJECT-TYPE
        SYNTAX  INTEGER (0..199)
        ACCESS  read-write
        STATUS  mandatory
        DESCRIPTION
                "Configuration FR-CE"
        ::= { fclFrCeLogPortEntry 10 }


    fclFrCeLpLmi OBJECT-TYPE
        SYNTAX  INTEGER {
                off(1),
                lmiNui(3),
                lmiNni(4)
                }
        ACCESS  read-write
        STATUS  mandatory
        DESCRIPTION
                "LMI"
        ::= { fclFrCeLogPortEntry 11 }


    fclFrCeParGenTable OBJECT-TYPE
        SYNTAX  SEQUENCE OF FclFrCeParGenEntry
        ACCESS  not-accessible
        STATUS  mandatory
        DESCRIPTION
                ""
        ::= { fclFrCommunicationEquipment 2 }


    fclFrCeParGenEntry OBJECT-TYPE
        SYNTAX  FclFrCeParGenEntry
        ACCESS  not-accessible
        STATUS  mandatory
        DESCRIPTION
                "An entry of fclFrCeParGenTable."
        INDEX   { fclFrCeParGenLogPortId }
        ::= { fclFrCeParGenTable 1 }


        FclFrCeParGenEntry ::=
                SEQUENCE {
                    fclFrCeParGenLogPortId
                        INTEGER,
                    fclFrCeParGenDlcSetupAlarmThreshold
                        INTEGER,
                    fclFrCeParGenDlcSetupDiscardThreshold
                        INTEGER,
                    fclFrCeParGenBookingUbrThreshold
                        INTEGER,
                    fclFrCeParGenBookingVbrRtThreshold
                        INTEGER,
                    fclFrCeParGenVoiceMaxTransitDelay
                        INTEGER
                }


    fclFrCeParGenLogPortId OBJECT-TYPE
        SYNTAX  INTEGER (0..181)
        ACCESS  read-only
        STATUS  mandatory
        DESCRIPTION
                "LP Id"
        ::= { fclFrCeParGenEntry 1 }


    fclFrCeParGenDlcSetupAlarmThreshold OBJECT-TYPE
        SYNTAX  INTEGER (0..250)
        ACCESS  read-write
        STATUS  mandatory
        DESCRIPTION
                "A% Seuil alarmique d'acceptation des connexions
                (pourcentage du debit de la ligne)"
        ::= { fclFrCeParGenEntry 30 }


    fclFrCeParGenDlcSetupDiscardThreshold OBJECT-TYPE
        SYNTAX  INTEGER (100..1100)
        ACCESS  read-write
        STATUS  mandatory
        DESCRIPTION
                "R% Seuil de refus d'etablissement des DLC VBR-NRT
                (pourcentage du debit de la ligne : 100 = pas de
                surbooking)"
        ::= { fclFrCeParGenEntry 31 }


    fclFrCeParGenBookingUbrThreshold OBJECT-TYPE
        SYNTAX  INTEGER (0..100)
        ACCESS  read-write
        STATUS  mandatory
        DESCRIPTION
                "U% Bande passante reservee aux reseaux virtuels
                UBR (pourcentage du debit de la ligne)"
        ::= { fclFrCeParGenEntry 32 }


    fclFrCeParGenBookingVbrRtThreshold OBJECT-TYPE
        SYNTAX  INTEGER (0..100)
        ACCESS  read-write
        STATUS  mandatory
        DESCRIPTION
                "V% Bande passante reservee aux COS VBR-RT
                (pourcentage du debit de la ligne)"
        ::= { fclFrCeParGenEntry 33 }


    fclFrCeParGenVoiceMaxTransitDelay OBJECT-TYPE
        SYNTAX  INTEGER (0..250)
        ACCESS  read-write
        STATUS  mandatory
        DESCRIPTION
                "PDN transit delay"
        ::= { fclFrCeParGenEntry 34 }


    fclFrTerminalEquipment OBJECT IDENTIFIER ::= { fclFrameRelay 2 }


    fclFrTeLogPortTable OBJECT-TYPE
        SYNTAX  SEQUENCE OF FclFrTeLogPortEntry
        ACCESS  not-accessible
        STATUS  mandatory
        DESCRIPTION
                ""
        ::= { fclFrTerminalEquipment 1 }


    fclFrTeLogPortEntry OBJECT-TYPE
        SYNTAX  FclFrTeLogPortEntry
        ACCESS  not-accessible
        STATUS  mandatory
        DESCRIPTION
                "An entry of fclFrTeLogPortTable."
        INDEX   { fclFrTeLpLogPortId }
        ::= { fclFrTeLogPortTable 1 }


        FclFrTeLogPortEntry ::=
                SEQUENCE {
                    fclFrTeLpLogPortId
                        INTEGER,
                    fclFrTeLpInterfaceId
                        INTEGER,
                    fclFrTeLpLocalAddress
                        OCTET STRING,
                    fclFrTeLpConfigId
                        INTEGER,
                    fclFrTeLpLmi
                        INTEGER,
                    fclFrTeLpFragmentation
                        INTEGER,
                    fclFrTeLpLinkLayerConsolidation
                        INTEGER,
                    fclFrTeLpLogPortBackupEnabling
                        INTEGER,
                    fclFrTeLpFragFrameSize
                        INTEGER,
                    fclFrTeLpBackupTimer
                        INTEGER
                }


    fclFrTeLpLogPortId OBJECT-TYPE
        SYNTAX  INTEGER (0..181)
        ACCESS  read-only
        STATUS  mandatory
        DESCRIPTION
                "LP Id"
        ::= { fclFrTeLogPortEntry 1 }


    fclFrTeLpInterfaceId OBJECT-TYPE
        SYNTAX  INTEGER (0..181)
        ACCESS  read-write
        STATUS  mandatory
        DESCRIPTION
                "IF Id (type ligne)"
        ::= { fclFrTeLogPortEntry 2 }


    fclFrTeLpLocalAddress OBJECT-TYPE
        SYNTAX  OCTET STRING (SIZE(8))
        ACCESS  read-write
        STATUS  mandatory
        DESCRIPTION
                "Adresse de localisation sur le plan d'adressage du
                routage (Numero d'abonne)"
        ::= { fclFrTeLogPortEntry 5 }


    fclFrTeLpConfigId OBJECT-TYPE
        SYNTAX  INTEGER (0..199)
        ACCESS  read-write
        STATUS  mandatory
        DESCRIPTION
                "Configuration FR-TE"
        ::= { fclFrTeLogPortEntry 10 }


    fclFrTeLpLmi OBJECT-TYPE
        SYNTAX  INTEGER {
                off(1),
                lmiUni(2),
                lmiNni(4)
                }
        ACCESS  read-write
        STATUS  mandatory
        DESCRIPTION
                "LMI"
        ::= { fclFrTeLogPortEntry 11 }


    fclFrTeLpFragmentation OBJECT-TYPE
        SYNTAX  INTEGER {
                off(1),
                optimized(3)
                }
        ACCESS  read-write
        STATUS  mandatory
        DESCRIPTION
                "Segmentation"
        ::= { fclFrTeLogPortEntry 20 }


    fclFrTeLpLinkLayerConsolidation OBJECT-TYPE
        SYNTAX  INTEGER {
                off(1),
                on(2)
                }
        ACCESS  read-write
        STATUS  mandatory
        DESCRIPTION
                "CLLM"
        ::= { fclFrTeLogPortEntry 21 }


    fclFrTeLpLogPortBackupEnabling OBJECT-TYPE
        SYNTAX  INTEGER {
                off(1),
                onWhileActivity(2),
                onWhileDlciDown(3),
                onWhileLpDown(4)
                }
        ACCESS  read-write
        STATUS  mandatory
        DESCRIPTION
                "Secours"
        ::= { fclFrTeLogPortEntry 22 }


    fclFrTeLpFragFrameSize OBJECT-TYPE
        SYNTAX  INTEGER {
                auto(1),
                s128(2),
                s256(3),
                s512(5),
                s1024(9),
                s2048(17),
                s4096(33),
                s8192(65)
                }
        ACCESS  read-write
        STATUS  mandatory
        DESCRIPTION
                "Taille des trames pour la Segmentation"
        ::= { fclFrTeLogPortEntry 23 }


    fclFrTeLpBackupTimer OBJECT-TYPE
        SYNTAX  INTEGER (0..2540)
        ACCESS  read-write
        STATUS  mandatory
        DESCRIPTION
                "Tempo de retour su LS"
        ::= { fclFrTeLogPortEntry 25 }


    fclFrTeParGenTable OBJECT-TYPE
        SYNTAX  SEQUENCE OF FclFrTeParGenEntry
        ACCESS  not-accessible
        STATUS  mandatory
        DESCRIPTION
                ""
        ::= { fclFrTerminalEquipment 4 }


    fclFrTeParGenEntry OBJECT-TYPE
        SYNTAX  FclFrTeParGenEntry
        ACCESS  not-accessible
        STATUS  mandatory
        DESCRIPTION
                "An entry of fclFrTeParGenTable."
        INDEX   { fclFrTeParGenLogPortId }
        ::= { fclFrTeParGenTable 1 }


        FclFrTeParGenEntry ::=
                SEQUENCE {
                    fclFrTeParGenLogPortId
                        INTEGER,
                    fclFrTeParGenDlcSetupAlarmThreshold
                        INTEGER,
                    fclFrTeParGenDlcSetupDiscardThreshold
                        INTEGER,
                    fclFrTeParGenBookingUbrThreshold
                        INTEGER,
                    fclFrTeParGenBookingVbrRtThreshold
                        INTEGER,
                    fclFrTeParGenVoiceMaxTransitDelay
                        INTEGER,
                    fclFrTeParGenDynamicEir
                        INTEGER,
                    fclFrTeParGenPredictionRoundTripDelay
                        INTEGER,
                    fclFrTeParGenNetworkBandwidth
                        INTEGER
                }


    fclFrTeParGenLogPortId OBJECT-TYPE
        SYNTAX  INTEGER (0..181)
        ACCESS  read-only
        STATUS  mandatory
        DESCRIPTION
                "LP Id"
        ::= { fclFrTeParGenEntry 1 }


    fclFrTeParGenDlcSetupAlarmThreshold OBJECT-TYPE
        SYNTAX  INTEGER (0..250)
        ACCESS  read-write
        STATUS  mandatory
        DESCRIPTION
                "A% Seuil alarmique d'acceptation des connexions
                (pourcentage du debit de la ligne)"
        ::= { fclFrTeParGenEntry 30 }


    fclFrTeParGenDlcSetupDiscardThreshold OBJECT-TYPE
        SYNTAX  INTEGER (100..1100)
        ACCESS  read-write
        STATUS  mandatory
        DESCRIPTION
                "R% Seuil de refus d'etablissement des DLC VBR-NRT
                (pourcentage du debit de la ligne : 100 = pas de
                surbooking)"
        ::= { fclFrTeParGenEntry 31 }


    fclFrTeParGenBookingUbrThreshold OBJECT-TYPE
        SYNTAX  INTEGER (0..100)
        ACCESS  read-write
        STATUS  mandatory
        DESCRIPTION
                "U% Bande passante reservee aux reseaux virtuels
                UBR (pourcentage du debit de la ligne)"
        ::= { fclFrTeParGenEntry 32 }


    fclFrTeParGenBookingVbrRtThreshold OBJECT-TYPE
        SYNTAX  INTEGER (0..100)
        ACCESS  read-write
        STATUS  mandatory
        DESCRIPTION
                "V% Bande passante reservee aux COS VBR-RT
                (pourcentage du debit de la ligne)"
        ::= { fclFrTeParGenEntry 33 }


    fclFrTeParGenVoiceMaxTransitDelay OBJECT-TYPE
        SYNTAX  INTEGER (0..250)
        ACCESS  read-write
        STATUS  mandatory
        DESCRIPTION
                "PDN transit delay"
        ::= { fclFrTeParGenEntry 34 }


    fclFrTeParGenDynamicEir OBJECT-TYPE
        SYNTAX  INTEGER {
                off(1),
                on(2)
                }
        ACCESS  read-write
        STATUS  mandatory
        DESCRIPTION
                "The value 'off' of this object means the Burst
                Exceeded object configuration is used in the
                traffic management plan with respect agreement
                traffic. The value 'on' of this object allows the
                whole connection to have a fair share of the line
                bandwidth in the proportion of the Commited
                Information Rate. In this case, the Burst Exceeded
                used in the traffic control is made dynamically
                from the unloaded line in the prorata of the CIR.
                 The default value is 'on'."
        ::= { fclFrTeParGenEntry 35 }


    fclFrTeParGenPredictionRoundTripDelay OBJECT-TYPE
        SYNTAX  INTEGER (0..250)
        ACCESS  read-write
        STATUS  mandatory
        DESCRIPTION
                "Prediction du delai de propagation"
        ::= { fclFrTeParGenEntry 36 }


    fclFrTeParGenNetworkBandwidth OBJECT-TYPE
        SYNTAX  INTEGER (0..34)
        ACCESS  read-write
        STATUS  mandatory
        DESCRIPTION
                "Bande passante du reseau"
        ::= { fclFrTeParGenEntry 37 }


    fclFrTeIsdnBackupTable OBJECT-TYPE
        SYNTAX  SEQUENCE OF FclFrTeIsdnBackupEntry
        ACCESS  not-accessible
        STATUS  mandatory
        DESCRIPTION
                ""
        ::= { fclFrTerminalEquipment 11 }


    fclFrTeIsdnBackupEntry OBJECT-TYPE
        SYNTAX  FclFrTeIsdnBackupEntry
        ACCESS  not-accessible
        STATUS  mandatory
        DESCRIPTION
                "An entry of fclFrTeIsdnBackupTable."
        INDEX   { fclFrTeIsdnBackLogPortId,
                  fclFrTeIsdnBackIsdnInterfaceId }
        ::= { fclFrTeIsdnBackupTable 1 }


        FclFrTeIsdnBackupEntry ::=
                SEQUENCE {
                    fclFrTeIsdnBackLogPortId
                        INTEGER,
                    fclFrTeIsdnBackIsdnInterfaceId
                        INTEGER,
                    fclFrTeIsdnBackStatus
                        INTEGER
                }


    fclFrTeIsdnBackLogPortId OBJECT-TYPE
        SYNTAX  INTEGER (0..181)
        ACCESS  read-only
        STATUS  mandatory
        DESCRIPTION
                "LP Id"
        ::= { fclFrTeIsdnBackupEntry 1 }


    fclFrTeIsdnBackIsdnInterfaceId OBJECT-TYPE
        SYNTAX  INTEGER (0..249)
        ACCESS  read-only
        STATUS  mandatory
        DESCRIPTION
                "Interface RNIS locale id"
        ::= { fclFrTeIsdnBackupEntry 2 }


    fclFrTeIsdnBackStatus OBJECT-TYPE
        SYNTAX  INTEGER {
                valid(1),
                invalid(2)
                }
        ACCESS  read-write
        STATUS  mandatory
        DESCRIPTION
                "Status"
        ::= { fclFrTeIsdnBackupEntry 3 }


    fclFrTeIsdnRemotePeerTable OBJECT-TYPE
        SYNTAX  SEQUENCE OF FclFrTeIsdnRemotePeerEntry
        ACCESS  not-accessible
        STATUS  mandatory
        DESCRIPTION
                ""
        ::= { fclFrTerminalEquipment 12 }


    fclFrTeIsdnRemotePeerEntry OBJECT-TYPE
        SYNTAX  FclFrTeIsdnRemotePeerEntry
        ACCESS  not-accessible
        STATUS  mandatory
        DESCRIPTION
                "An entry of fclFrTeIsdnRemotePeerTable."
        INDEX   { fclFrTeIsdnRemLogPortId,
                  fclFrTeIsdnRemRemotePeerId }
        ::= { fclFrTeIsdnRemotePeerTable 1 }


        FclFrTeIsdnRemotePeerEntry ::=
                SEQUENCE {
                    fclFrTeIsdnRemLogPortId
                        INTEGER,
                    fclFrTeIsdnRemRemotePeerId
                        INTEGER,
                    fclFrTeIsdnRemStatus
                        INTEGER,
                    fclFrTeIsdnRemPriority
                        INTEGER,
                    fclFrTeIsdnRemCallRetryCount
                        INTEGER,
                    fclFrTeIsdnRemProtocol
                        INTEGER,
                    fclFrTeIsdnRemConfigId
                        INTEGER
                }


    fclFrTeIsdnRemLogPortId OBJECT-TYPE
        SYNTAX  INTEGER (0..181)
        ACCESS  read-only
        STATUS  mandatory
        DESCRIPTION
                "LP Id"
        ::= { fclFrTeIsdnRemotePeerEntry 1 }


    fclFrTeIsdnRemRemotePeerId OBJECT-TYPE
        SYNTAX  INTEGER (0..249)
        ACCESS  read-only
        STATUS  mandatory
        DESCRIPTION
                "InterfaceRNIS distante id"
        ::= { fclFrTeIsdnRemotePeerEntry 2 }


    fclFrTeIsdnRemStatus OBJECT-TYPE
        SYNTAX  INTEGER {
                valid(1),
                invalid(2)
                }
        ACCESS  read-write
        STATUS  mandatory
        DESCRIPTION
                "Status"
        ::= { fclFrTeIsdnRemotePeerEntry 3 }


    fclFrTeIsdnRemPriority OBJECT-TYPE
        SYNTAX  INTEGER (0..15)
        ACCESS  read-write
        STATUS  mandatory
        DESCRIPTION
                "Priorite"
        ::= { fclFrTeIsdnRemotePeerEntry 8 }


    fclFrTeIsdnRemCallRetryCount OBJECT-TYPE
        SYNTAX  INTEGER (1..15)
        ACCESS  read-write
        STATUS  mandatory
        DESCRIPTION
                "Nombre de tentatives d'appel"
        ::= { fclFrTeIsdnRemotePeerEntry 9 }


    fclFrTeIsdnRemProtocol OBJECT-TYPE
        SYNTAX  INTEGER {
                frse(1),
                frte(2),
                main-line-protocol(3)
                }
        ACCESS  read-write
        STATUS  mandatory
        DESCRIPTION
                "Type de protocole"
        ::= { fclFrTeIsdnRemotePeerEntry 15 }


    fclFrTeIsdnRemConfigId OBJECT-TYPE
        SYNTAX  INTEGER (0..199)
        ACCESS  read-write
        STATUS  mandatory
        DESCRIPTION
                "Configuration id"
        ::= { fclFrTeIsdnRemotePeerEntry 16 }


    fclFrSwitchEquipment OBJECT IDENTIFIER ::= { fclFrameRelay 3 }


    fclFrSeLogPortTable OBJECT-TYPE
        SYNTAX  SEQUENCE OF FclFrSeLogPortEntry
        ACCESS  not-accessible
        STATUS  mandatory
        DESCRIPTION
                ""
        ::= { fclFrSwitchEquipment 1 }


    fclFrSeLogPortEntry OBJECT-TYPE
        SYNTAX  FclFrSeLogPortEntry
        ACCESS  not-accessible
        STATUS  mandatory
        DESCRIPTION
                "An entry of fclFrSeLogPortTable."
        INDEX   { fclFrSeLpLogPortId }
        ::= { fclFrSeLogPortTable 1 }


        FclFrSeLogPortEntry ::=
                SEQUENCE {
                    fclFrSeLpLogPortId
                        INTEGER,
                    fclFrSeLpInterfaceId
                        INTEGER,
                    fclFrSeLpConfigId
                        INTEGER,
                    fclFrSeLpLogPortBackupEnabling
                        INTEGER,
                    fclFrSeLpBackupTimer
                        INTEGER
                }


    fclFrSeLpLogPortId OBJECT-TYPE
        SYNTAX  INTEGER (0..181)
        ACCESS  read-only
        STATUS  mandatory
        DESCRIPTION
                "LP Id"
        ::= { fclFrSeLogPortEntry 1 }


    fclFrSeLpInterfaceId OBJECT-TYPE
        SYNTAX  INTEGER (0..181)
        ACCESS  read-write
        STATUS  mandatory
        DESCRIPTION
                "IF Id (type ligne)"
        ::= { fclFrSeLogPortEntry 2 }


    fclFrSeLpConfigId OBJECT-TYPE
        SYNTAX  INTEGER (0..199)
        ACCESS  read-write
        STATUS  mandatory
        DESCRIPTION
                "Configuration FR-SE"
        ::= { fclFrSeLogPortEntry 10 }


    fclFrSeLpLogPortBackupEnabling OBJECT-TYPE
        SYNTAX  INTEGER {
                off(1),
                onWhileActivity(2),
                onWhileLpDown(3)
                }
        ACCESS  read-write
        STATUS  mandatory
        DESCRIPTION
                "Secours"
        ::= { fclFrSeLogPortEntry 22 }


    fclFrSeLpBackupTimer OBJECT-TYPE
        SYNTAX  INTEGER (0..2540)
        ACCESS  read-write
        STATUS  mandatory
        DESCRIPTION
                "Tempo de retour sur LS"
        ::= { fclFrSeLogPortEntry 25 }


    fclFrSeIsdnBackupTable OBJECT-TYPE
        SYNTAX  SEQUENCE OF FclFrSeIsdnBackupEntry
        ACCESS  not-accessible
        STATUS  mandatory
        DESCRIPTION
                ""
        ::= { fclFrSwitchEquipment 11 }


    fclFrSeIsdnBackupEntry OBJECT-TYPE
        SYNTAX  FclFrSeIsdnBackupEntry
        ACCESS  not-accessible
        STATUS  mandatory
        DESCRIPTION
                "An entry of fclFrSeIsdnBackupTable."
        INDEX   { fclFrSeIsdnBackLogPortId,
                  fclFrSeIsdnBackIsdnInterfaceId }
        ::= { fclFrSeIsdnBackupTable 1 }


        FclFrSeIsdnBackupEntry ::=
                SEQUENCE {
                    fclFrSeIsdnBackLogPortId
                        INTEGER,
                    fclFrSeIsdnBackIsdnInterfaceId
                        INTEGER,
                    fclFrSeIsdnBackStatus
                        INTEGER
                }


    fclFrSeIsdnBackLogPortId OBJECT-TYPE
        SYNTAX  INTEGER (0..181)
        ACCESS  read-only
        STATUS  mandatory
        DESCRIPTION
                "LP Id"
        ::= { fclFrSeIsdnBackupEntry 1 }


    fclFrSeIsdnBackIsdnInterfaceId OBJECT-TYPE
        SYNTAX  INTEGER (0..249)
        ACCESS  read-only
        STATUS  mandatory
        DESCRIPTION
                "Interface RNIS locale id"
        ::= { fclFrSeIsdnBackupEntry 2 }


    fclFrSeIsdnBackStatus OBJECT-TYPE
        SYNTAX  INTEGER {
                valid(1),
                invalid(2)
                }
        ACCESS  read-write
        STATUS  mandatory
        DESCRIPTION
                "Status"
        ::= { fclFrSeIsdnBackupEntry 3 }


    fclFrSeIsdnRemotePeerTable OBJECT-TYPE
        SYNTAX  SEQUENCE OF FclFrSeIsdnRemotePeerEntry
        ACCESS  not-accessible
        STATUS  mandatory
        DESCRIPTION
                ""
        ::= { fclFrSwitchEquipment 12 }


    fclFrSeIsdnRemotePeerEntry OBJECT-TYPE
        SYNTAX  FclFrSeIsdnRemotePeerEntry
        ACCESS  not-accessible
        STATUS  mandatory
        DESCRIPTION
                "An entry of fclFrSeIsdnRemotePeerTable."
        INDEX   { fclFrSeIsdnRemLogPortId,
                  fclFrSeIsdnRemRemotePeerId }
        ::= { fclFrSeIsdnRemotePeerTable 1 }


        FclFrSeIsdnRemotePeerEntry ::=
                SEQUENCE {
                    fclFrSeIsdnRemLogPortId
                        INTEGER,
                    fclFrSeIsdnRemRemotePeerId
                        INTEGER,
                    fclFrSeIsdnRemStatus
                        INTEGER,
                    fclFrSeIsdnRemConfigId
                        INTEGER,
                    fclFrSeIsdnRemPriority
                        INTEGER,
                    fclFrSeIsdnRemCallRetryCount
                        INTEGER
                }


    fclFrSeIsdnRemLogPortId OBJECT-TYPE
        SYNTAX  INTEGER (0..181)
        ACCESS  read-only
        STATUS  mandatory
        DESCRIPTION
                "LP Id"
        ::= { fclFrSeIsdnRemotePeerEntry 1 }


    fclFrSeIsdnRemRemotePeerId OBJECT-TYPE
        SYNTAX  INTEGER (0..249)
        ACCESS  read-only
        STATUS  mandatory
        DESCRIPTION
                "Interface RNIS distante id"
        ::= { fclFrSeIsdnRemotePeerEntry 2 }


    fclFrSeIsdnRemStatus OBJECT-TYPE
        SYNTAX  INTEGER {
                valid(1),
                invalid(2)
                }
        ACCESS  read-write
        STATUS  mandatory
        DESCRIPTION
                "Status"
        ::= { fclFrSeIsdnRemotePeerEntry 3 }


    fclFrSeIsdnRemConfigId OBJECT-TYPE
        SYNTAX  INTEGER (0..199)
        ACCESS  read-write
        STATUS  mandatory
        DESCRIPTION
                "Configuration FR-SE"
        ::= { fclFrSeIsdnRemotePeerEntry 4 }


    fclFrSeIsdnRemPriority OBJECT-TYPE
        SYNTAX  INTEGER (0..15)
        ACCESS  read-write
        STATUS  mandatory
        DESCRIPTION
                "Priorite"
        ::= { fclFrSeIsdnRemotePeerEntry 8 }


    fclFrSeIsdnRemCallRetryCount OBJECT-TYPE
        SYNTAX  INTEGER (1..15)
        ACCESS  read-write
        STATUS  mandatory
        DESCRIPTION
                "Nombre de tentatives d'appel"
        ::= { fclFrSeIsdnRemotePeerEntry 9 }


    fclFrSeInBIsdn OBJECT IDENTIFIER ::= { fclFrameRelay 13 }


    fclFrSeInBIsdnLogPortTable OBJECT-TYPE
        SYNTAX  SEQUENCE OF FclFrSeInBIsdnLogPortEntry
        ACCESS  not-accessible
        STATUS  mandatory
        DESCRIPTION
                ""
        ::= { fclFrSeInBIsdn 1 }


    fclFrSeInBIsdnLogPortEntry OBJECT-TYPE
        SYNTAX  FclFrSeInBIsdnLogPortEntry
        ACCESS  not-accessible
        STATUS  mandatory
        DESCRIPTION
                "An entry of fclFrSeInBIsdnLogPortTable."
        INDEX   { fclFrSeInBLpLogPortId }
        ::= { fclFrSeInBIsdnLogPortTable 1 }


        FclFrSeInBIsdnLogPortEntry ::=
                SEQUENCE {
                    fclFrSeInBLpLogPortId
                        INTEGER,
                    fclFrSeInBLpIsdnInterfaceId
                        INTEGER
                }


    fclFrSeInBLpLogPortId OBJECT-TYPE
        SYNTAX  INTEGER (0..181)
        ACCESS  read-only
        STATUS  mandatory
        DESCRIPTION
                "LP Id"
        ::= { fclFrSeInBIsdnLogPortEntry 1 }


    fclFrSeInBLpIsdnInterfaceId OBJECT-TYPE
        SYNTAX  INTEGER (0..35)
        ACCESS  read-write
        STATUS  mandatory
        DESCRIPTION
                "IF Id (type RNIS)"
        ::= { fclFrSeInBIsdnLogPortEntry 2 }


    fclFrSeInBRemotePeerTable OBJECT-TYPE
        SYNTAX  SEQUENCE OF FclFrSeInBRemotePeerEntry
        ACCESS  not-accessible
        STATUS  mandatory
        DESCRIPTION
                ""
        ::= { fclFrSeInBIsdn 2 }


    fclFrSeInBRemotePeerEntry OBJECT-TYPE
        SYNTAX  FclFrSeInBRemotePeerEntry
        ACCESS  not-accessible
        STATUS  mandatory
        DESCRIPTION
                "An entry of fclFrSeInBRemotePeerTable."
        INDEX   { fclFrSeInBRemRemoteAddress,
                  fclFrSeInBRemPeerId }
        ::= { fclFrSeInBRemotePeerTable 1 }


        FclFrSeInBRemotePeerEntry ::=
                SEQUENCE {
                    fclFrSeInBRemRemoteAddress
                        OCTET STRING,
                    fclFrSeInBRemPeerId
                        INTEGER,
                    fclFrSeInBRemStatus
                        INTEGER,
                    fclFrSeInBRemPriority
                        INTEGER,
                    fclFrSeInBRemCallRetryCount
                        INTEGER,
                    fclFrSeInBRemConfigId
                        INTEGER
                }


    fclFrSeInBRemRemoteAddress OBJECT-TYPE
        SYNTAX  OCTET STRING (SIZE(8))
        ACCESS  read-only
        STATUS  mandatory
        DESCRIPTION
                "Adresse visee"
        ::= { fclFrSeInBRemotePeerEntry 1 }


    fclFrSeInBRemPeerId OBJECT-TYPE
        SYNTAX  INTEGER (0..999)
        ACCESS  read-only
        STATUS  mandatory
        DESCRIPTION
                "Interface RNIS distante id"
        ::= { fclFrSeInBRemotePeerEntry 2 }


    fclFrSeInBRemStatus OBJECT-TYPE
        SYNTAX  INTEGER {
                valid(1),
                invalid(2)
                }
        ACCESS  read-write
        STATUS  mandatory
        DESCRIPTION
                "Status"
        ::= { fclFrSeInBRemotePeerEntry 3 }


    fclFrSeInBRemPriority OBJECT-TYPE
        SYNTAX  INTEGER (0..15)
        ACCESS  read-write
        STATUS  mandatory
        DESCRIPTION
                "Priorite"
        ::= { fclFrSeInBRemotePeerEntry 8 }


    fclFrSeInBRemCallRetryCount OBJECT-TYPE
        SYNTAX  INTEGER (1..15)
        ACCESS  read-write
        STATUS  mandatory
        DESCRIPTION
                "Nb de tentatives appel"
        ::= { fclFrSeInBRemotePeerEntry 9 }


    fclFrSeInBRemConfigId OBJECT-TYPE
        SYNTAX  INTEGER (0..199)
        ACCESS  read-write
        STATUS  mandatory
        DESCRIPTION
                "Configuration FR-SE"
        ::= { fclFrSeInBRemotePeerEntry 10 }


    fclFrPvcEndPoint OBJECT IDENTIFIER ::= { fclFrameRelay 20 }


    fclFrPvcEndPointTable OBJECT-TYPE
        SYNTAX  SEQUENCE OF FclFrPvcEndPointEntry
        ACCESS  not-accessible
        STATUS  mandatory
        DESCRIPTION
                ""
        ::= { fclFrPvcEndPoint 1 }


    fclFrPvcEndPointEntry OBJECT-TYPE
        SYNTAX  FclFrPvcEndPointEntry
        ACCESS  not-accessible
        STATUS  mandatory
        DESCRIPTION
                "An entry of fclFrPvcEndPointTable."
        INDEX   { fclFrPvcLinkType,
                  fclFrPvcLinkId,
                  fclFrPvcDlci }
        ::= { fclFrPvcEndPointTable 1 }


        FclFrPvcEndPointEntry ::=
                SEQUENCE {
                    fclFrPvcLinkType
                        INTEGER,
                    fclFrPvcLinkId
                        INTEGER,
                    fclFrPvcDlci
                        INTEGER,
                    fclFrPvcStatus
                        INTEGER,
                    fclFrPvcCalledAddress
                        OCTET STRING,
                    fclFrPvcCallDirection
                        INTEGER,
                    fclFrPvcEncapsulation
                        INTEGER,
                    fclFrPvcBackupEnabling
                        INTEGER,
                    fclFrPvcBackupDlci
                        INTEGER,
                    fclFrPvcTrafficManagementStrategy
                        INTEGER,
                    fclFrPvcNetworkTransport
                        INTEGER
                }


    fclFrPvcLinkType OBJECT-TYPE
        SYNTAX  INTEGER {
                logicalPort(1),
                bChannelIsdn(2)
                }
        ACCESS  read-only
        STATUS  mandatory
        DESCRIPTION
                "Type de liaison (=logicalPort en v2.1)"
        ::= { fclFrPvcEndPointEntry 1 }


    fclFrPvcLinkId OBJECT-TYPE
        SYNTAX  INTEGER (0..249)
        ACCESS  read-only
        STATUS  mandatory
        DESCRIPTION
                "Liaison Id (=LogPortId en v2.1)"
        ::= { fclFrPvcEndPointEntry 2 }


    fclFrPvcDlci OBJECT-TYPE
        SYNTAX  INTEGER (16..991)
        ACCESS  read-only
        STATUS  mandatory
        DESCRIPTION
                "DLCI"
        ::= { fclFrPvcEndPointEntry 3 }


    fclFrPvcStatus OBJECT-TYPE
        SYNTAX  INTEGER {
                valid(1),
                invalid(2)
                }
        ACCESS  read-write
        STATUS  mandatory
        DESCRIPTION
                "Status"
        ::= { fclFrPvcEndPointEntry 4 }


    fclFrPvcCalledAddress OBJECT-TYPE
        SYNTAX  OCTET STRING (SIZE(8))
        ACCESS  read-write
        STATUS  mandatory
        DESCRIPTION
                "Adresse distante (non utilisee si encapsulation
                X25)"
        ::= { fclFrPvcEndPointEntry 5 }


    fclFrPvcCallDirection OBJECT-TYPE
        SYNTAX  INTEGER {
                calling(1),
                called(2),
                calledMulti(5),
                auto(3),
                datagram(4)
                }
        ACCESS  read-write
        STATUS  mandatory
        DESCRIPTION
                "Mode d'appel (non utilise si encapsulation X25)"
        ::= { fclFrPvcEndPointEntry 6 }


    fclFrPvcEncapsulation OBJECT-TYPE
        SYNTAX  INTEGER {
                none(1),
                lanProtocols(2),
                x25(3),
                sna(4),
                snaBan(5),
                voice(6)
                }
        ACCESS  read-write
        STATUS  mandatory
        DESCRIPTION
                "Encapsulation"
        ::= { fclFrPvcEndPointEntry 7 }


    fclFrPvcBackupEnabling OBJECT-TYPE
        SYNTAX  INTEGER {
                off(1),
                on(2)
                }
        ACCESS  read-write
        STATUS  mandatory
        DESCRIPTION
                "Terminaison de PVC a secourir"
        ::= { fclFrPvcEndPointEntry 10 }


    fclFrPvcBackupDlci OBJECT-TYPE
        SYNTAX  INTEGER (16..991)
        ACCESS  read-write
        STATUS  mandatory
        DESCRIPTION
                "DLCI de secours"
        ::= { fclFrPvcEndPointEntry 11 }


    fclFrPvcTrafficManagementStrategy OBJECT-TYPE
        SYNTAX  INTEGER {
                discardButNotDelay(1),
                delayButNotDiscard-Bc(3),
                delayButNotDiscard-BcBe(4)
                }
        ACCESS  read-write
        STATUS  mandatory
        DESCRIPTION
                "Traffic management strategy"
        ::= { fclFrPvcEndPointEntry 20 }


    fclFrPvcNetworkTransport OBJECT-TYPE
        SYNTAX  INTEGER {
                transparent(36),
                ansiT1-617-G(32)
                }
        ACCESS  read-write
        STATUS  mandatory
        DESCRIPTION
                "FR Network transport"
        ::= { fclFrPvcEndPointEntry 21 }


    fclFrPvcQualityOfServiceTable OBJECT-TYPE
        SYNTAX  SEQUENCE OF FclFrPvcQualityOfServiceEntry
        ACCESS  not-accessible
        STATUS  mandatory
        DESCRIPTION
                ""
        ::= { fclFrPvcEndPoint 2 }


    fclFrPvcQualityOfServiceEntry OBJECT-TYPE
        SYNTAX  FclFrPvcQualityOfServiceEntry
        ACCESS  not-accessible
        STATUS  mandatory
        DESCRIPTION
                "An entry of fclFrPvcQualityOfServiceTable."
        INDEX   { fclFrPvcQosLinkType,
                  fclFrPvcQosLinkId,
                  fclFrPvcQosDlci }
        ::= { fclFrPvcQualityOfServiceTable 1 }


        FclFrPvcQualityOfServiceEntry ::=
                SEQUENCE {
                    fclFrPvcQosLinkType
                        INTEGER,
                    fclFrPvcQosLinkId
                        INTEGER,
                    fclFrPvcQosDlci
                        INTEGER,
                    fclFrPvcQosCos
                        INTEGER,
                    fclFrPvcQosInBc
                        INTEGER,
                    fclFrPvcQosInBe
                        INTEGER,
                    fclFrPvcQosInCir
                        INTEGER,
                    fclFrPvcQosInMinCir
                        INTEGER,
                    fclFrPvcQosOutBc
                        INTEGER,
                    fclFrPvcQosOutBe
                        INTEGER,
                    fclFrPvcQosOutCir
                        INTEGER,
                    fclFrPvcQosOutMinCir
                        INTEGER
                }


    fclFrPvcQosLinkType OBJECT-TYPE
        SYNTAX  INTEGER {
                logicalPort(1),
                bChannelIsdn(2)
                }
        ACCESS  read-only
        STATUS  mandatory
        DESCRIPTION
                "Type de liaison (=logicalPort en v2.1)"
        ::= { fclFrPvcQualityOfServiceEntry 1 }


    fclFrPvcQosLinkId OBJECT-TYPE
        SYNTAX  INTEGER (0..249)
        ACCESS  read-only
        STATUS  mandatory
        DESCRIPTION
                "Liaison Id (=LogPortId en v2.1)"
        ::= { fclFrPvcQualityOfServiceEntry 2 }


    fclFrPvcQosDlci OBJECT-TYPE
        SYNTAX  INTEGER (16..991)
        ACCESS  read-only
        STATUS  mandatory
        DESCRIPTION
                "DLCI"
        ::= { fclFrPvcQualityOfServiceEntry 3 }


    fclFrPvcQosCos OBJECT-TYPE
        SYNTAX  INTEGER {
                ubr(3),
                vbr(1),
                vbr-rt(2)
                }
        ACCESS  read-write
        STATUS  mandatory
        DESCRIPTION
                "COS"
        ::= { fclFrPvcQualityOfServiceEntry 5 }


    fclFrPvcQosInBc OBJECT-TYPE
        SYNTAX  INTEGER (0..2048000)
        ACCESS  read-write
        STATUS  mandatory
        DESCRIPTION
                "Entrant BC"
        ::= { fclFrPvcQualityOfServiceEntry 11 }


    fclFrPvcQosInBe OBJECT-TYPE
        SYNTAX  INTEGER (0..2048000)
        ACCESS  read-write
        STATUS  mandatory
        DESCRIPTION
                "Entrant BE"
        ::= { fclFrPvcQualityOfServiceEntry 12 }


    fclFrPvcQosInCir OBJECT-TYPE
        SYNTAX  INTEGER (0..2048000)
        ACCESS  read-write
        STATUS  mandatory
        DESCRIPTION
                "Entrant CIR"
        ::= { fclFrPvcQualityOfServiceEntry 13 }


    fclFrPvcQosInMinCir OBJECT-TYPE
        SYNTAX  INTEGER (0..2048000)
        ACCESS  read-write
        STATUS  mandatory
        DESCRIPTION
                "Entrant CIR mini"
        ::= { fclFrPvcQualityOfServiceEntry 14 }


    fclFrPvcQosOutBc OBJECT-TYPE
        SYNTAX  INTEGER (0..2048000)
        ACCESS  read-write
        STATUS  mandatory
        DESCRIPTION
                "Sortant BC"
        ::= { fclFrPvcQualityOfServiceEntry 21 }


    fclFrPvcQosOutBe OBJECT-TYPE
        SYNTAX  INTEGER (0..2048000)
        ACCESS  read-write
        STATUS  mandatory
        DESCRIPTION
                "Sortant BE"
        ::= { fclFrPvcQualityOfServiceEntry 22 }


    fclFrPvcQosOutCir OBJECT-TYPE
        SYNTAX  INTEGER (0..2048000)
        ACCESS  read-write
        STATUS  mandatory
        DESCRIPTION
                "Sortant CIR"
        ::= { fclFrPvcQualityOfServiceEntry 23 }


    fclFrPvcQosOutMinCir OBJECT-TYPE
        SYNTAX  INTEGER (0..2048000)
        ACCESS  read-write
        STATUS  mandatory
        DESCRIPTION
                "Sortant CIR mini"
        ::= { fclFrPvcQualityOfServiceEntry 24 }


    fclFrPvcX25EncapsulationTable OBJECT-TYPE
        SYNTAX  SEQUENCE OF FclFrPvcX25EncapsulationEntry
        ACCESS  not-accessible
        STATUS  mandatory
        DESCRIPTION
                ""
        ::= { fclFrPvcEndPoint 10 }


    fclFrPvcX25EncapsulationEntry OBJECT-TYPE
        SYNTAX  FclFrPvcX25EncapsulationEntry
        ACCESS  not-accessible
        STATUS  mandatory
        DESCRIPTION
                "An entry of fclFrPvcX25EncapsulationTable."
        INDEX   { fclFrPvcX25LinkType,
                  fclFrPvcX25LinkId,
                  fclFrPvcX25Dlci }
        ::= { fclFrPvcX25EncapsulationTable 1 }


        FclFrPvcX25EncapsulationEntry ::=
                SEQUENCE {
                    fclFrPvcX25LinkType
                        INTEGER,
                    fclFrPvcX25LinkId
                        INTEGER,
                    fclFrPvcX25Dlci
                        INTEGER,
                    fclFrPvcX25AssociatedAddress
                        OCTET STRING,
                    fclFrPvcX25InterNodeConfigId
                        INTEGER
                }


    fclFrPvcX25LinkType OBJECT-TYPE
        SYNTAX  INTEGER {
                logicalPort(1),
                bChannelIsdn(2)
                }
        ACCESS  read-only
        STATUS  mandatory
        DESCRIPTION
                "Type de liaison (=logicalPort en v2.1)"
        ::= { fclFrPvcX25EncapsulationEntry 1 }


    fclFrPvcX25LinkId OBJECT-TYPE
        SYNTAX  INTEGER (0..249)
        ACCESS  read-only
        STATUS  mandatory
        DESCRIPTION
                "Liaison Id (=LogPortId en v2.1)"
        ::= { fclFrPvcX25EncapsulationEntry 2 }


    fclFrPvcX25Dlci OBJECT-TYPE
        SYNTAX  INTEGER (16..991)
        ACCESS  read-only
        STATUS  mandatory
        DESCRIPTION
                "DLCI"
        ::= { fclFrPvcX25EncapsulationEntry 3 }


    fclFrPvcX25AssociatedAddress OBJECT-TYPE
        SYNTAX  OCTET STRING (SIZE(8))
        ACCESS  read-write
        STATUS  mandatory
        DESCRIPTION
                "Adresse associee"
        ::= { fclFrPvcX25EncapsulationEntry 5 }


    fclFrPvcX25InterNodeConfigId OBJECT-TYPE
        SYNTAX  INTEGER (0..199)
        ACCESS  read-write
        STATUS  mandatory
        DESCRIPTION
                "Configuration X25"
        ::= { fclFrPvcX25EncapsulationEntry 10 }


    fclFrPvcSnaEncapsulationTable OBJECT-TYPE
        SYNTAX  SEQUENCE OF FclFrPvcSnaEncapsulationEntry
        ACCESS  not-accessible
        STATUS  mandatory
        DESCRIPTION
                ""
        ::= { fclFrPvcEndPoint 11 }


    fclFrPvcSnaEncapsulationEntry OBJECT-TYPE
        SYNTAX  FclFrPvcSnaEncapsulationEntry
        ACCESS  not-accessible
        STATUS  mandatory
        DESCRIPTION
                "An entry of fclFrPvcSnaEncapsulationTable."
        INDEX   { fclFrPvcSnaLinkType,
                  fclFrPvcSnaLinkId,
                  fclFrPvcSnaDlci }
        ::= { fclFrPvcSnaEncapsulationTable 1 }


        FclFrPvcSnaEncapsulationEntry ::=
                SEQUENCE {
                    fclFrPvcSnaLinkType
                        INTEGER,
                    fclFrPvcSnaLinkId
                        INTEGER,
                    fclFrPvcSnaDlci
                        INTEGER,
                    fclFrPvcSnaConnTestEnabling
                        INTEGER,
                    fclFrPvcSnaLevel3Pid
                        INTEGER,
                    fclFrPvcSnaDestinationSap
                        OCTET STRING,
                    fclFrPvcSnaSourceSap
                        OCTET STRING,
                    fclFrPvcSnaT1ReplyTimer
                        INTEGER,
                    fclFrPvcSnaN2RetryCount
                        INTEGER,
                    fclFrPvcSnaT2ReceiverAckTimer
                        INTEGER,
                    fclFrPvcSnaN3AcknowledgedCount
                        INTEGER,
                    fclFrPvcSnaNwIncrementAckCount
                        INTEGER,
                    fclFrPvcSnaTwTransmitWinSize
                        INTEGER,
                    fclFrPvcSnaRwReceiveWinSize
                        INTEGER
                }


    fclFrPvcSnaLinkType OBJECT-TYPE
        SYNTAX  INTEGER {
                logicalPort(1),
                bChannelIsdn(2)
                }
        ACCESS  read-only
        STATUS  mandatory
        DESCRIPTION
                "Type de liaison (=logicalPort en v2.1)"
        ::= { fclFrPvcSnaEncapsulationEntry 1 }


    fclFrPvcSnaLinkId OBJECT-TYPE
        SYNTAX  INTEGER (0..249)
        ACCESS  read-only
        STATUS  mandatory
        DESCRIPTION
                "Liaison Id (=LogPortId en v2.1)"
        ::= { fclFrPvcSnaEncapsulationEntry 2 }


    fclFrPvcSnaDlci OBJECT-TYPE
        SYNTAX  INTEGER (16..991)
        ACCESS  read-only
        STATUS  mandatory
        DESCRIPTION
                "DLCI"
        ::= { fclFrPvcSnaEncapsulationEntry 3 }


    fclFrPvcSnaConnTestEnabling OBJECT-TYPE
        SYNTAX  INTEGER {
                off(1),
                on(2)
                }
        ACCESS  read-write
        STATUS  mandatory
        DESCRIPTION
                "Initiative d'etablissement de connexion par une
                trame test"
        ::= { fclFrPvcSnaEncapsulationEntry 5 }


    fclFrPvcSnaLevel3Pid OBJECT-TYPE
        SYNTAX  INTEGER {
                subArea(1),
                peripheral(2),
                appn(3)
                }
        ACCESS  read-write
        STATUS  mandatory
        DESCRIPTION
                "L3 PID"
        ::= { fclFrPvcSnaEncapsulationEntry 10 }


    fclFrPvcSnaDestinationSap OBJECT-TYPE
        SYNTAX  OCTET STRING (SIZE(1))
        ACCESS  read-write
        STATUS  mandatory
        DESCRIPTION
                "DSAP"
        ::= { fclFrPvcSnaEncapsulationEntry 11 }


    fclFrPvcSnaSourceSap OBJECT-TYPE
        SYNTAX  OCTET STRING (SIZE(1))
        ACCESS  read-write
        STATUS  mandatory
        DESCRIPTION
                "SSAP"
        ::= { fclFrPvcSnaEncapsulationEntry 12 }


    fclFrPvcSnaT1ReplyTimer OBJECT-TYPE
        SYNTAX  INTEGER (100..25000)
        ACCESS  read-write
        STATUS  mandatory
        DESCRIPTION
                "Timer T1 attente une trame U"
        ::= { fclFrPvcSnaEncapsulationEntry 20 }


    fclFrPvcSnaN2RetryCount OBJECT-TYPE
        SYNTAX  INTEGER (1..20)
        ACCESS  read-write
        STATUS  mandatory
        DESCRIPTION
                "N2 Nombre maximum de retransmissions"
        ::= { fclFrPvcSnaEncapsulationEntry 21 }


    fclFrPvcSnaT2ReceiverAckTimer OBJECT-TYPE
        SYNTAX  INTEGER (100..15000)
        ACCESS  read-write
        STATUS  mandatory
        DESCRIPTION
                "Timer T2 acquittement des trames I"
        ::= { fclFrPvcSnaEncapsulationEntry 22 }


    fclFrPvcSnaN3AcknowledgedCount OBJECT-TYPE
        SYNTAX  INTEGER (1..20)
        ACCESS  read-write
        STATUS  mandatory
        DESCRIPTION
                "N3 Nombre de trames ok avant acquittement"
        ::= { fclFrPvcSnaEncapsulationEntry 23 }


    fclFrPvcSnaNwIncrementAckCount OBJECT-TYPE
        SYNTAX  INTEGER (1..127)
        ACCESS  read-write
        STATUS  mandatory
        DESCRIPTION
                "NW congestion : nombre de trames ok avant
                incrementer la fenetre de travail"
        ::= { fclFrPvcSnaEncapsulationEntry 24 }


    fclFrPvcSnaTwTransmitWinSize OBJECT-TYPE
        SYNTAX  INTEGER (1..127)
        ACCESS  read-write
        STATUS  mandatory
        DESCRIPTION
                "TW Fenetre en emission"
        ::= { fclFrPvcSnaEncapsulationEntry 25 }


    fclFrPvcSnaRwReceiveWinSize OBJECT-TYPE
        SYNTAX  INTEGER (1..127)
        ACCESS  read-write
        STATUS  mandatory
        DESCRIPTION
                "RW fenetre reception"
        ::= { fclFrPvcSnaEncapsulationEntry 26 }


    fclFrSnaBan OBJECT IDENTIFIER ::= { fclFrPvcEndPoint 12 }


    fclFrNbStationDlci OBJECT IDENTIFIER ::= { fclFrSnaBan 1 }


    fclFrNbStationByDlci OBJECT-TYPE
        SYNTAX  INTEGER {
                nb0(1),
                nb16(2),
                nb32(3),
                nb64(4),
                nb128(5)
                }
        ACCESS  read-write
        STATUS  mandatory
        DESCRIPTION
                "Nombre de stations par DLCI BAN Frontal"
        ::= { fclFrNbStationDlci 1 }


    fclFrPvcSnaBanEncapsulationTable OBJECT-TYPE
        SYNTAX  SEQUENCE OF FclFrPvcSnaBanEncapsulationEntry
        ACCESS  not-accessible
        STATUS  mandatory
        DESCRIPTION
                ""
        ::= { fclFrSnaBan 10 }


    fclFrPvcSnaBanEncapsulationEntry OBJECT-TYPE
        SYNTAX  FclFrPvcSnaBanEncapsulationEntry
        ACCESS  not-accessible
        STATUS  mandatory
        DESCRIPTION
                "An entry of fclFrPvcSnaBanEncapsulationTable."
        INDEX   { fclFrPvcSnaBanLinkType,
                  fclFrPvcSnaBanLinkId,
                  fclFrPvcSnaBanDlci }
        ::= { fclFrPvcSnaBanEncapsulationTable 1 }


        FclFrPvcSnaBanEncapsulationEntry ::=
                SEQUENCE {
                    fclFrPvcSnaBanLinkType
                        INTEGER,
                    fclFrPvcSnaBanLinkId
                        INTEGER,
                    fclFrPvcSnaBanDlci
                        INTEGER,
                    fclFrPvcSnaBanPuId
                        INTEGER,
                    fclFrPvcSnaBanConnTestEnabling
                        INTEGER,
                    fclFrPvcSnaBanLink
                        INTEGER,
                    fclFrPvcSnaBanT1ReplyTimer
                        INTEGER,
                    fclFrPvcSnaBanN2RetryCount
                        INTEGER,
                    fclFrPvcSnaBanT2ReceiverAckTimer
                        INTEGER,
                    fclFrPvcSnaBanN3AcknowledgedCount
                        INTEGER,
                    fclFrPvcSnaBanNwIncrementAckCount
                        INTEGER,
                    fclFrPvcSnaBanTwTransmitWinSize
                        INTEGER,
                    fclFrPvcSnaBanRwReceiveWinSize
                        INTEGER,
                    fclFrPvcSnaBanMinRecallTimer
                        INTEGER
                }


    fclFrPvcSnaBanLinkType OBJECT-TYPE
        SYNTAX  INTEGER {
                logicalPort(1),
                bChannelIsdn(2)
                }
        ACCESS  read-only
        STATUS  mandatory
        DESCRIPTION
                "Type de liaison (=logicalPort en v2.1)"
        ::= { fclFrPvcSnaBanEncapsulationEntry 1 }


    fclFrPvcSnaBanLinkId OBJECT-TYPE
        SYNTAX  INTEGER (0..249)
        ACCESS  read-only
        STATUS  mandatory
        DESCRIPTION
                "Liaison Id (=LogPortId en v2.1)"
        ::= { fclFrPvcSnaBanEncapsulationEntry 2 }


    fclFrPvcSnaBanDlci OBJECT-TYPE
        SYNTAX  INTEGER (16..991)
        ACCESS  read-only
        STATUS  mandatory
        DESCRIPTION
                "DLCI"
        ::= { fclFrPvcSnaBanEncapsulationEntry 3 }


    fclFrPvcSnaBanPuId OBJECT-TYPE
        SYNTAX  INTEGER (0..1999)
        ACCESS  read-write
        STATUS  mandatory
        DESCRIPTION
                "Pu id"
        ::= { fclFrPvcSnaBanEncapsulationEntry 10 }


    fclFrPvcSnaBanConnTestEnabling OBJECT-TYPE
        SYNTAX  INTEGER {
                off(1),
                on(2)
                }
        ACCESS  read-write
        STATUS  mandatory
        DESCRIPTION
                "Initiative d'etablissement de connexion par une
                trame test"
        ::= { fclFrPvcSnaBanEncapsulationEntry 11 }


    fclFrPvcSnaBanLink OBJECT-TYPE
        SYNTAX  INTEGER {
                frontal(1),
                remote(2),
                auto(3)
                }
        ACCESS  read-write
        STATUS  mandatory
        DESCRIPTION
                "Type de ligne"
        ::= { fclFrPvcSnaBanEncapsulationEntry 12 }


    fclFrPvcSnaBanT1ReplyTimer OBJECT-TYPE
        SYNTAX  INTEGER (100..25000)
        ACCESS  read-write
        STATUS  mandatory
        DESCRIPTION
                "Timer T1 attente une trame U"
        ::= { fclFrPvcSnaBanEncapsulationEntry 20 }


    fclFrPvcSnaBanN2RetryCount OBJECT-TYPE
        SYNTAX  INTEGER (1..20)
        ACCESS  read-write
        STATUS  mandatory
        DESCRIPTION
                "N2 Nombre maximum de retransmissions"
        ::= { fclFrPvcSnaBanEncapsulationEntry 21 }


    fclFrPvcSnaBanT2ReceiverAckTimer OBJECT-TYPE
        SYNTAX  INTEGER (100..15000)
        ACCESS  read-write
        STATUS  mandatory
        DESCRIPTION
                "Timer T2 acquittement des trames I"
        ::= { fclFrPvcSnaBanEncapsulationEntry 22 }


    fclFrPvcSnaBanN3AcknowledgedCount OBJECT-TYPE
        SYNTAX  INTEGER (1..20)
        ACCESS  read-write
        STATUS  mandatory
        DESCRIPTION
                "N3 Nombre de trames ok avant acquittement"
        ::= { fclFrPvcSnaBanEncapsulationEntry 23 }


    fclFrPvcSnaBanNwIncrementAckCount OBJECT-TYPE
        SYNTAX  INTEGER (0..127)
        ACCESS  read-write
        STATUS  mandatory
        DESCRIPTION
                "NW congestion : nombre de trames ok avant
                incrementer la fenetre de travail"
        ::= { fclFrPvcSnaBanEncapsulationEntry 24 }


    fclFrPvcSnaBanTwTransmitWinSize OBJECT-TYPE
        SYNTAX  INTEGER (1..127)
        ACCESS  read-write
        STATUS  mandatory
        DESCRIPTION
                "TW Fenetre en emission"
        ::= { fclFrPvcSnaBanEncapsulationEntry 25 }


    fclFrPvcSnaBanRwReceiveWinSize OBJECT-TYPE
        SYNTAX  INTEGER (1..127)
        ACCESS  read-write
        STATUS  mandatory
        DESCRIPTION
                "RW fenetre reception"
        ::= { fclFrPvcSnaBanEncapsulationEntry 26 }


    fclFrPvcSnaBanMinRecallTimer OBJECT-TYPE
        SYNTAX  INTEGER (0..990)
        ACCESS  read-write
        STATUS  mandatory
        DESCRIPTION
                "Minimum recall timer "
        ::= { fclFrPvcSnaBanEncapsulationEntry 27 }


    fclFrPvcSpecific OBJECT IDENTIFIER ::= { fclFrameRelay 25 }


    fclFrPvcTunEndPointTable OBJECT-TYPE
        SYNTAX  SEQUENCE OF FclFrPvcTunEndPointEntry
        ACCESS  not-accessible
        STATUS  mandatory
        DESCRIPTION
                ""
        ::= { fclFrPvcSpecific 1 }


    fclFrPvcTunEndPointEntry OBJECT-TYPE
        SYNTAX  FclFrPvcTunEndPointEntry
        ACCESS  not-accessible
        STATUS  mandatory
        DESCRIPTION
                "An entry of fclFrPvcTunEndPointTable."
        INDEX   { fclFrPvcTunLinkType,
                  fclFrPvcTunLinkId,
                  fclFrPvcTunDlci }
        ::= { fclFrPvcTunEndPointTable 1 }


        FclFrPvcTunEndPointEntry ::=
                SEQUENCE {
                    fclFrPvcTunLinkType
                        INTEGER,
                    fclFrPvcTunLinkId
                        INTEGER,
                    fclFrPvcTunDlci
                        INTEGER,
                    fclFrPvcTunStatus
                        INTEGER,
                    fclFrPvcTunInCir
                        INTEGER,
                    fclFrPvcTunOutCir
                        INTEGER,
                    fclFrPvcTunBackupEnabling
                        INTEGER,
                    fclFrPvcTunBackupDlci
                        INTEGER,
                    fclFrPvcTunAssociatedAddress
                        OCTET STRING,
                    fclFrPvcTunFrseConfiguration
                        INTEGER
                }


    fclFrPvcTunLinkType OBJECT-TYPE
        SYNTAX  INTEGER {
                logicalPort(1),
                bChannelIsdn(2)
                }
        ACCESS  read-only
        STATUS  mandatory
        DESCRIPTION
                "Type de liaison (=logicalPort en v2.1)"
        ::= { fclFrPvcTunEndPointEntry 1 }


    fclFrPvcTunLinkId OBJECT-TYPE
        SYNTAX  INTEGER (0..249)
        ACCESS  read-only
        STATUS  mandatory
        DESCRIPTION
                "Liaison Id (=LogPortId en v2.1)"
        ::= { fclFrPvcTunEndPointEntry 2 }


    fclFrPvcTunDlci OBJECT-TYPE
        SYNTAX  INTEGER (16..991)
        ACCESS  read-only
        STATUS  mandatory
        DESCRIPTION
                "DLCI"
        ::= { fclFrPvcTunEndPointEntry 3 }


    fclFrPvcTunStatus OBJECT-TYPE
        SYNTAX  INTEGER {
                valid(1),
                invalid(2)
                }
        ACCESS  read-write
        STATUS  mandatory
        DESCRIPTION
                "Status"
        ::= { fclFrPvcTunEndPointEntry 4 }


    fclFrPvcTunInCir OBJECT-TYPE
        SYNTAX  INTEGER (0..2048000)
        ACCESS  read-write
        STATUS  mandatory
        DESCRIPTION
                "Entrant CIR"
        ::= { fclFrPvcTunEndPointEntry 5 }


    fclFrPvcTunOutCir OBJECT-TYPE
        SYNTAX  INTEGER (0..2048000)
        ACCESS  read-write
        STATUS  mandatory
        DESCRIPTION
                "Sortant CIR"
        ::= { fclFrPvcTunEndPointEntry 6 }


    fclFrPvcTunBackupEnabling OBJECT-TYPE
        SYNTAX  INTEGER {
                off(1),
                on(2)
                }
        ACCESS  read-write
        STATUS  mandatory
        DESCRIPTION
                "Terminaison de PVC a secourir"
        ::= { fclFrPvcTunEndPointEntry 10 }


    fclFrPvcTunBackupDlci OBJECT-TYPE
        SYNTAX  INTEGER (16..991)
        ACCESS  read-write
        STATUS  mandatory
        DESCRIPTION
                "DLCI de secours"
        ::= { fclFrPvcTunEndPointEntry 11 }


    fclFrPvcTunAssociatedAddress OBJECT-TYPE
        SYNTAX  OCTET STRING (SIZE(8))
        ACCESS  read-write
        STATUS  mandatory
        DESCRIPTION
                "Adresse associee"
        ::= { fclFrPvcTunEndPointEntry 15 }


    fclFrPvcTunFrseConfiguration OBJECT-TYPE
        SYNTAX  INTEGER (0..199)
        ACCESS  read-write
        STATUS  mandatory
        DESCRIPTION
                "Configuration FRSE"
        ::= { fclFrPvcTunEndPointEntry 20 }


    fclFrameRelayBackup OBJECT IDENTIFIER ::= { fclFrameRelay 27 }


    fclFrBackupTable OBJECT-TYPE
        SYNTAX  SEQUENCE OF FclFrBackupEntry
        ACCESS  not-accessible
        STATUS  mandatory
        DESCRIPTION
                ""
        ::= { fclFrameRelayBackup 1 }


    fclFrBackupEntry OBJECT-TYPE
        SYNTAX  FclFrBackupEntry
        ACCESS  not-accessible
        STATUS  mandatory
        DESCRIPTION
                "An entry of fclFrBackupTable."
        INDEX   { fclFrMainLPId,
                  fclFrMainDlci,
                  fclFrBackupLPId,
                  fclFrBackupDlci }
        ::= { fclFrBackupTable 1 }


        FclFrBackupEntry ::=
                SEQUENCE {
                    fclFrMainLPId
                        INTEGER,
                    fclFrMainDlci
                        INTEGER,
                    fclFrBackupLPId
                        INTEGER,
                    fclFrBackupDlci
                        INTEGER,
                    fclFrBackupStatus
                        INTEGER
                }


    fclFrMainLPId OBJECT-TYPE
        SYNTAX  INTEGER (0..99)
        ACCESS  read-only
        STATUS  mandatory
        DESCRIPTION
                "LP principale"
        ::= { fclFrBackupEntry 1 }


    fclFrMainDlci OBJECT-TYPE
        SYNTAX  INTEGER (0..1023)
        ACCESS  read-only
        STATUS  mandatory
        DESCRIPTION
                "DLCI principal"
        ::= { fclFrBackupEntry 2 }


    fclFrBackupLPId OBJECT-TYPE
        SYNTAX  INTEGER (0..99)
        ACCESS  read-only
        STATUS  mandatory
        DESCRIPTION
                "LP secours"
        ::= { fclFrBackupEntry 3 }


    fclFrBackupDlci OBJECT-TYPE
        SYNTAX  INTEGER (0..1023)
        ACCESS  read-only
        STATUS  mandatory
        DESCRIPTION
                "DLCI secours"
        ::= { fclFrBackupEntry 4 }


    fclFrBackupStatus OBJECT-TYPE
        SYNTAX  INTEGER {
                valid(1),
                invalid(2)
                }
        ACCESS  read-write
        STATUS  mandatory
        DESCRIPTION
                "Status"
        ::= { fclFrBackupEntry 5 }


    fclFrConfigurationCeTe OBJECT IDENTIFIER ::= { fclFrameRelay 30 }


    fclFrConfigCeTeTable OBJECT-TYPE
        SYNTAX  SEQUENCE OF FclFrConfigCeTeEntry
        ACCESS  not-accessible
        STATUS  mandatory
        DESCRIPTION
                ""
        ::= { fclFrConfigurationCeTe 1 }


    fclFrConfigCeTeEntry OBJECT-TYPE
        SYNTAX  FclFrConfigCeTeEntry
        ACCESS  not-accessible
        STATUS  mandatory
        DESCRIPTION
                "An entry of fclFrConfigCeTeTable."
        INDEX   { fclFrCfcConfigId }
        ::= { fclFrConfigCeTeTable 1 }


        FclFrConfigCeTeEntry ::=
                SEQUENCE {
                    fclFrCfcConfigId
                        INTEGER,
                    fclFrCfcStatus
                        INTEGER,
                    fclFrCfcDescription
                        DisplayString,
                    fclFrCfcProfileId
                        INTEGER,
                    fclFrCfcModificationCount
                        INTEGER
                }


    fclFrCfcConfigId OBJECT-TYPE
        SYNTAX  INTEGER (0..199)
        ACCESS  read-only
        STATUS  mandatory
        DESCRIPTION
                "Configuration id"
        ::= { fclFrConfigCeTeEntry 1 }


    fclFrCfcStatus OBJECT-TYPE
        SYNTAX  INTEGER {
                valid(1),
                invalid(2)
                }
        ACCESS  read-write
        STATUS  mandatory
        DESCRIPTION
                "Status"
        ::= { fclFrConfigCeTeEntry 2 }


    fclFrCfcDescription OBJECT-TYPE
        SYNTAX  DisplayString (SIZE(0..32))
        ACCESS  read-write
        STATUS  mandatory
        DESCRIPTION
                "Description"
        ::= { fclFrConfigCeTeEntry 3 }


    fclFrCfcProfileId OBJECT-TYPE
        SYNTAX  INTEGER (0..199)
        ACCESS  read-write
        STATUS  mandatory
        DESCRIPTION
                "The value of this object is the profile number
                used to automatically valorize all the FR
                parameters in an entry of the two tables which
                composes FR-CE or FR-TE configurations (see
                fclFrCfcConfigId).

                The possible values are :
                   84 FRTE interface,
                   85 FRCE interface,

                If it is unused, the value of this parameter is
                '255'.
                The default value is '85' (meaning that default
                values of FR parameters are those pre-defined in
                profile number 85)."
        ::= { fclFrConfigCeTeEntry 4 }


    fclFrCfcModificationCount OBJECT-TYPE
        SYNTAX  INTEGER (0..255)
        ACCESS  read-only
        STATUS  mandatory
        DESCRIPTION
                "Nombre de parametres modifies par rapport au profil"
        ::= { fclFrConfigCeTeEntry 5 }


    fclFrCfcGeneralParameterTable OBJECT-TYPE
        SYNTAX  SEQUENCE OF FclFrCfcGeneralParameterEntry
        ACCESS  not-accessible
        STATUS  mandatory
        DESCRIPTION
                ""
        ::= { fclFrConfigurationCeTe 10 }


    fclFrCfcGeneralParameterEntry OBJECT-TYPE
        SYNTAX  FclFrCfcGeneralParameterEntry
        ACCESS  not-accessible
        STATUS  mandatory
        DESCRIPTION
                "An entry of fclFrCfcGeneralParameterTable."
        INDEX   { fclFrCfcGenConfigId }
        ::= { fclFrCfcGeneralParameterTable 1 }


        FclFrCfcGeneralParameterEntry ::=
                SEQUENCE {
                    fclFrCfcGenConfigId
                        INTEGER,
                    fclFrCfcGenMinimumRecallTimer
                        INTEGER,
                    fclFrCfcGenInactivityCheckDelay
                        INTEGER,
                    fclFrCfcGenInactivityTimer
                        INTEGER,
                    fclFrCfcGenUnuseTimer
                        INTEGER,
                    fclFrCfcGenSVC
                        INTEGER
                }


    fclFrCfcGenConfigId OBJECT-TYPE
        SYNTAX  INTEGER (0..199)
        ACCESS  read-only
        STATUS  mandatory
        DESCRIPTION
                "Configuration id"
        ::= { fclFrCfcGeneralParameterEntry 1 }


    fclFrCfcGenMinimumRecallTimer OBJECT-TYPE
        SYNTAX  INTEGER (0..2540)
        ACCESS  read-write
        STATUS  mandatory
        DESCRIPTION
                "Tempo de slow call (Tsc) en secondes"
        ::= { fclFrCfcGeneralParameterEntry 20 }


    fclFrCfcGenInactivityCheckDelay OBJECT-TYPE
        SYNTAX  INTEGER (0..254)
        ACCESS  read-write
        STATUS  mandatory
        DESCRIPTION
                "Inactivity check delay (Ta) en minutes"
        ::= { fclFrCfcGeneralParameterEntry 21 }


    fclFrCfcGenInactivityTimer OBJECT-TYPE
        SYNTAX  INTEGER (0..2540)
        ACCESS  read-write
        STATUS  mandatory
        DESCRIPTION
                "Inactivity timer (Tb) en secondes"
        ::= { fclFrCfcGeneralParameterEntry 22 }


    fclFrCfcGenUnuseTimer OBJECT-TYPE
        SYNTAX  INTEGER (0..2550)
        ACCESS  read-write
        STATUS  mandatory
        DESCRIPTION
                "Tempo 0 CV en secondes (0 = pas de surveillance)"
        ::= { fclFrCfcGeneralParameterEntry 23 }


    fclFrCfcGenSVC OBJECT-TYPE
        SYNTAX  INTEGER {
                yes(1),
                no(2)
                }
        ACCESS  read-write
        STATUS  mandatory
        DESCRIPTION
                "SVC"
        ::= { fclFrCfcGeneralParameterEntry 24 }


    fclFrCfcSignallingParameterTable OBJECT-TYPE
        SYNTAX  SEQUENCE OF FclFrCfcSignallingParameterEntry
        ACCESS  not-accessible
        STATUS  mandatory
        DESCRIPTION
                ""
        ::= { fclFrConfigurationCeTe 15 }


    fclFrCfcSignallingParameterEntry OBJECT-TYPE
        SYNTAX  FclFrCfcSignallingParameterEntry
        ACCESS  not-accessible
        STATUS  mandatory
        DESCRIPTION
                "An entry of fclFrCfcSignallingParameterTable."
        INDEX   { fclFrCfcSigConfigId }
        ::= { fclFrCfcSignallingParameterTable 1 }


        FclFrCfcSignallingParameterEntry ::=
                SEQUENCE {
                    fclFrCfcSigConfigId
                        INTEGER,
                    fclFrCfcSigOuputTimeout
                        INTEGER,
                    fclFrCfcSigSignalOutputWinSize
                        INTEGER,
                    fclFrCfcSigN200RetransMaxCount
                        INTEGER,
                    fclFrCfcSigT200RetransTimer
                        INTEGER,
                    fclFrCfcSigT203InactivityTimer
                        INTEGER,
                    fclFrCfcSigT303SetupResponseTimer
                        INTEGER,
                    fclFrCfcSigT305DisconnectResponseTimer
                        INTEGER,
                    fclFrCfcSigT308ReleaseResponseTimer
                        INTEGER,
                    fclFrCfcSigT310CallProceedingTimer
                        INTEGER,
                    fclFrCfcSigT316RestartAcknowledgeTimer
                        INTEGER,
                    fclFrCfcSigConversionAimedPoint
                        INTEGER
                }


    fclFrCfcSigConfigId OBJECT-TYPE
        SYNTAX  INTEGER (0..199)
        ACCESS  read-only
        STATUS  mandatory
        DESCRIPTION
                "Configuration id"
        ::= { fclFrCfcSignallingParameterEntry 1 }


    fclFrCfcSigOuputTimeout OBJECT-TYPE
        SYNTAX  INTEGER (0..51000)
        ACCESS  read-write
        STATUS  mandatory
        DESCRIPTION
                "Tempo de surveillance de ligne en emission en
                millisecondes"
        ::= { fclFrCfcSignallingParameterEntry 2 }


    fclFrCfcSigSignalOutputWinSize OBJECT-TYPE
        SYNTAX  INTEGER (1..7)
        ACCESS  read-write
        STATUS  mandatory
        DESCRIPTION
                "Fenetre d'emission DLCI de signalisation"
        ::= { fclFrCfcSignallingParameterEntry 3 }


    fclFrCfcSigN200RetransMaxCount OBJECT-TYPE
        SYNTAX  INTEGER (1..255)
        ACCESS  read-write
        STATUS  mandatory
        DESCRIPTION
                "N 200 : Nombre de repetition trames"
        ::= { fclFrCfcSignallingParameterEntry 5 }


    fclFrCfcSigT200RetransTimer OBJECT-TYPE
        SYNTAX  INTEGER (0..25500)
        ACCESS  read-write
        STATUS  mandatory
        DESCRIPTION
                "T 200 : Tempo de retransmission en millisecondes"
        ::= { fclFrCfcSignallingParameterEntry 6 }


    fclFrCfcSigT203InactivityTimer OBJECT-TYPE
        SYNTAX  INTEGER (0..255)
        ACCESS  read-write
        STATUS  mandatory
        DESCRIPTION
                "T 203 : Polling RR en secondes"
        ::= { fclFrCfcSignallingParameterEntry 7 }


    fclFrCfcSigT303SetupResponseTimer OBJECT-TYPE
        SYNTAX  INTEGER (1..255)
        ACCESS  read-write
        STATUS  mandatory
        DESCRIPTION
                "T 303 : Tempo attente de reponse a un
                etablissement sortant en secondes"
        ::= { fclFrCfcSignallingParameterEntry 11 }


    fclFrCfcSigT305DisconnectResponseTimer OBJECT-TYPE
        SYNTAX  INTEGER (1..255)
        ACCESS  read-write
        STATUS  mandatory
        DESCRIPTION
                "T 305 : Tempo attente de reponse a une demande de
                deconnexion en secondes"
        ::= { fclFrCfcSignallingParameterEntry 12 }


    fclFrCfcSigT308ReleaseResponseTimer OBJECT-TYPE
        SYNTAX  INTEGER (1..255)
        ACCESS  read-write
        STATUS  mandatory
        DESCRIPTION
                "T 308 : Tempo attente de reponse a une demande de
                liberation en secondes"
        ::= { fclFrCfcSignallingParameterEntry 13 }


    fclFrCfcSigT310CallProceedingTimer OBJECT-TYPE
        SYNTAX  INTEGER (1..255)
        ACCESS  read-write
        STATUS  mandatory
        DESCRIPTION
                "T 310 : Tempo entre un appel recu et une alerte ou
                une connexion en secondes"
        ::= { fclFrCfcSignallingParameterEntry 15 }


    fclFrCfcSigT316RestartAcknowledgeTimer OBJECT-TYPE
        SYNTAX  INTEGER (0..255)
        ACCESS  read-write
        STATUS  mandatory
        DESCRIPTION
                "T 316 : Tempo de reponse au RESTART en secondes (0
                = pas de RESTART)"
        ::= { fclFrCfcSignallingParameterEntry 17 }


    fclFrCfcSigConversionAimedPoint OBJECT-TYPE
        SYNTAX  INTEGER {
                off(1),
                on(2)
                }
        ACCESS  read-write
        STATUS  mandatory
        DESCRIPTION
                "Conversion adresse : point vise"
        ::= { fclFrCfcSignallingParameterEntry 10 }


    fclFrCfcEiCodingTable OBJECT-TYPE
        SYNTAX  SEQUENCE OF FclFrCfcEiCodingEntry
        ACCESS  not-accessible
        STATUS  mandatory
        DESCRIPTION
                ""
        ::= { fclFrConfigurationCeTe 16 }


    fclFrCfcEiCodingEntry OBJECT-TYPE
        SYNTAX  FclFrCfcEiCodingEntry
        ACCESS  not-accessible
        STATUS  mandatory
        DESCRIPTION
                "An entry of fclFrCfcEiCodingTable."
        INDEX   { fclFrCfcEiCodConfigId }
        ::= { fclFrCfcEiCodingTable 1 }


        FclFrCfcEiCodingEntry ::=
                SEQUENCE {
                    fclFrCfcEiCodConfigId
                        INTEGER,
                    fclFrCfcEiCodCalledTypNum
                        INTEGER,
                    fclFrCfcEiCodCalledNumPlanId
                        INTEGER,
                    fclFrCfcEiCodCallingTypNum
                        INTEGER,
                    fclFrCfcEiCodCallingNumPlanId
                        INTEGER
                }


    fclFrCfcEiCodConfigId OBJECT-TYPE
        SYNTAX  INTEGER (0..199)
        ACCESS  read-only
        STATUS  mandatory
        DESCRIPTION
                "Configuration id"
        ::= { fclFrCfcEiCodingEntry 1 }


    fclFrCfcEiCodCalledTypNum OBJECT-TYPE
        SYNTAX  INTEGER {
                unknown(1),
                international-number(2),
                national-number(3),
                complementary-address(4),
                network-specific(5)
                }
        ACCESS  read-write
        STATUS  mandatory
        DESCRIPTION
                "Called Type of number"
        ::= { fclFrCfcEiCodingEntry 2 }


    fclFrCfcEiCodCalledNumPlanId OBJECT-TYPE
        SYNTAX  INTEGER {
                unknown(1),
                e164(2),
                x121(3),
                private-num-plan(9)
                }
        ACCESS  read-write
        STATUS  mandatory
        DESCRIPTION
                "Called Numbering plan identification"
        ::= { fclFrCfcEiCodingEntry 3 }


    fclFrCfcEiCodCallingTypNum OBJECT-TYPE
        SYNTAX  INTEGER {
                unknown(1),
                international-number(2),
                national-number(3),
                complementary-address(4),
                network-specific(5)
                }
        ACCESS  read-write
        STATUS  mandatory
        DESCRIPTION
                "Calling Type of number"
        ::= { fclFrCfcEiCodingEntry 4 }


    fclFrCfcEiCodCallingNumPlanId OBJECT-TYPE
        SYNTAX  INTEGER {
                unknown(1),
                e164(2),
                x121(3),
                private-num-plan(9)
                }
        ACCESS  read-write
        STATUS  mandatory
        DESCRIPTION
                "Calling Numbering plan identification"
        ::= { fclFrCfcEiCodingEntry 5 }


    fclFrCfcLmiParameterTable OBJECT-TYPE
        SYNTAX  SEQUENCE OF FclFrCfcLmiParameterEntry
        ACCESS  not-accessible
        STATUS  mandatory
        DESCRIPTION
                ""
        ::= { fclFrConfigurationCeTe 21 }


    fclFrCfcLmiParameterEntry OBJECT-TYPE
        SYNTAX  FclFrCfcLmiParameterEntry
        ACCESS  not-accessible
        STATUS  mandatory
        DESCRIPTION
                "An entry of fclFrCfcLmiParameterTable."
        INDEX   { fclFrCfcLmiConfigId }
        ::= { fclFrCfcLmiParameterTable 1 }


        FclFrCfcLmiParameterEntry ::=
                SEQUENCE {
                    fclFrCfcLmiConfigId
                        INTEGER,
                    fclFrCfcLmiDlci
                        INTEGER,
                    fclFrCfcLmiStandard
                        INTEGER,
                    fclFrCfcLmiAccessibilityCondition
                        INTEGER,
                    fclFrCfcLmiN391FullStatusPollCount
                        INTEGER,
                    fclFrCfcLmiN392ErrorThreshold
                        INTEGER,
                    fclFrCfcLmiN393MonitoredEventCount
                        INTEGER,
                    fclFrCfcLmiT391LinkIntegPollTimer
                        INTEGER,
                    fclFrCfcLmiT392PollingVerifTimer
                        INTEGER,
                    fclFrCfcLmiAsynchronousStatusReport
                        INTEGER
                }


    fclFrCfcLmiConfigId OBJECT-TYPE
        SYNTAX  INTEGER (0..199)
        ACCESS  read-only
        STATUS  mandatory
        DESCRIPTION
                "Configuration id"
        ::= { fclFrCfcLmiParameterEntry 1 }


    fclFrCfcLmiDlci OBJECT-TYPE
        SYNTAX  INTEGER {
                dlci0(1),
                dlci1023(2)
                }
        ACCESS  read-write
        STATUS  mandatory
        DESCRIPTION
                "DLCI utilise"
        ::= { fclFrCfcLmiParameterEntry 2 }


    fclFrCfcLmiStandard OBJECT-TYPE
        SYNTAX  INTEGER {
                ansiT1-617d(1),
                itutQ933a(2)
                }
        ACCESS  read-write
        STATUS  mandatory
        DESCRIPTION
                "Standard LMI"
        ::= { fclFrCfcLmiParameterEntry 3 }


    fclFrCfcLmiAccessibilityCondition OBJECT-TYPE
        SYNTAX  INTEGER {
                fast(1),
                n393(2)
                }
        ACCESS  read-write
        STATUS  mandatory
        DESCRIPTION
                "Critere de disponibilite"
        ::= { fclFrCfcLmiParameterEntry 4 }


    fclFrCfcLmiN391FullStatusPollCount OBJECT-TYPE
        SYNTAX  INTEGER (1..254)
        ACCESS  read-write
        STATUS  mandatory
        DESCRIPTION
                "N 391 (User) Cycle interrogation prealable"
        ::= { fclFrCfcLmiParameterEntry 5 }


    fclFrCfcLmiN392ErrorThreshold OBJECT-TYPE
        SYNTAX  INTEGER (1..10)
        ACCESS  read-write
        STATUS  mandatory
        DESCRIPTION
                "N 392 (User/Net) Seuil erreur"
        ::= { fclFrCfcLmiParameterEntry 6 }


    fclFrCfcLmiN393MonitoredEventCount OBJECT-TYPE
        SYNTAX  INTEGER (1..10)
        ACCESS  read-write
        STATUS  mandatory
        DESCRIPTION
                "N393 (User/Net) Compteur des evenements controles"
        ::= { fclFrCfcLmiParameterEntry 7 }


    fclFrCfcLmiT391LinkIntegPollTimer OBJECT-TYPE
        SYNTAX  INTEGER (5..30)
        ACCESS  read-write
        STATUS  mandatory
        DESCRIPTION
                "T 391 (User) Tempo de polling status"
        ::= { fclFrCfcLmiParameterEntry 8 }


    fclFrCfcLmiT392PollingVerifTimer OBJECT-TYPE
        SYNTAX  INTEGER (5..30)
        ACCESS  read-write
        STATUS  mandatory
        DESCRIPTION
                "T 392 (Net) Tempo attente de la demande etat"
        ::= { fclFrCfcLmiParameterEntry 9 }


    fclFrCfcLmiAsynchronousStatusReport OBJECT-TYPE
        SYNTAX  INTEGER {
                off(1),
                on(2)
                }
        ACCESS  read-write
        STATUS  mandatory
        DESCRIPTION
                "Envoi du status asynchrone"
        ::= { fclFrCfcLmiParameterEntry 10 }


    fclFrConfigurationSe OBJECT IDENTIFIER ::= { fclFrameRelay 40 }


    fclFrConfigSeTable OBJECT-TYPE
        SYNTAX  SEQUENCE OF FclFrConfigSeEntry
        ACCESS  not-accessible
        STATUS  mandatory
        DESCRIPTION
                ""
        ::= { fclFrConfigurationSe 1 }


    fclFrConfigSeEntry OBJECT-TYPE
        SYNTAX  FclFrConfigSeEntry
        ACCESS  not-accessible
        STATUS  mandatory
        DESCRIPTION
                "An entry of fclFrConfigSeTable."
        INDEX   { fclFrCfsConfigId }
        ::= { fclFrConfigSeTable 1 }


        FclFrConfigSeEntry ::=
                SEQUENCE {
                    fclFrCfsConfigId
                        INTEGER,
                    fclFrCfsStatus
                        INTEGER,
                    fclFrCfsDescription
                        DisplayString,
                    fclFrCfsProfileId
                        INTEGER,
                    fclFrCfsModificationCount
                        INTEGER
                }


    fclFrCfsConfigId OBJECT-TYPE
        SYNTAX  INTEGER (0..199)
        ACCESS  read-only
        STATUS  mandatory
        DESCRIPTION
                "Configuration id"
        ::= { fclFrConfigSeEntry 1 }


    fclFrCfsStatus OBJECT-TYPE
        SYNTAX  INTEGER {
                valid(1),
                invalid(2)
                }
        ACCESS  read-write
        STATUS  mandatory
        DESCRIPTION
                "Status"
        ::= { fclFrConfigSeEntry 2 }


    fclFrCfsDescription OBJECT-TYPE
        SYNTAX  DisplayString (SIZE(0..32))
        ACCESS  read-write
        STATUS  mandatory
        DESCRIPTION
                "Description"
        ::= { fclFrConfigSeEntry 3 }


    fclFrCfsProfileId OBJECT-TYPE
        SYNTAX  INTEGER (0..199)
        ACCESS  read-write
        STATUS  mandatory
        DESCRIPTION
                "The value of this object is the profile number
                used to automatically valorize all the FR
                parameters in an entry of the two tables which
                composes FR-SE configurations (see
                fclFrCfsConfigId).

                The possible values are :
                   80 FRSE interface.

                If it is unused, the value of this parameter is
                '255'.
                The default value is '80' (meaning that default
                values of FR parameters are those pre-defined in
                profile number 80)."
        ::= { fclFrConfigSeEntry 4 }


    fclFrCfsModificationCount OBJECT-TYPE
        SYNTAX  INTEGER (0..255)
        ACCESS  read-only
        STATUS  mandatory
        DESCRIPTION
                "Nombre de parametres modifies par rapport au profil"
        ::= { fclFrConfigSeEntry 5 }


    fclFrCfsGeneralParameterTable OBJECT-TYPE
        SYNTAX  SEQUENCE OF FclFrCfsGeneralParameterEntry
        ACCESS  not-accessible
        STATUS  mandatory
        DESCRIPTION
                ""
        ::= { fclFrConfigurationSe 10 }


    fclFrCfsGeneralParameterEntry OBJECT-TYPE
        SYNTAX  FclFrCfsGeneralParameterEntry
        ACCESS  not-accessible
        STATUS  mandatory
        DESCRIPTION
                "An entry of fclFrCfsGeneralParameterTable."
        INDEX   { fclFrCfsGenConfigId }
        ::= { fclFrCfsGeneralParameterTable 1 }


        FclFrCfsGeneralParameterEntry ::=
                SEQUENCE {
                    fclFrCfsGenConfigId
                        INTEGER,
                    fclFrCfsGenCallReturnTransmission
                        INTEGER,
                    fclFrCfsGenUnuseTimer
                        INTEGER,
                    fclFrCfsGenDlcSetupAlarmThreshold
                        INTEGER,
                    fclFrCfsGenDlcSetupDiscardThreshold
                        INTEGER,
                    fclFrCfsGenBookingUbrThreshold
                        INTEGER,
                    fclFrCfsGenBookingVbrRtThreshold
                        INTEGER,
                    fclFrCfsGenBehavior
                        INTEGER,
                    fclFrCfsGenDynamicEir
                        INTEGER,
                    fclFrCfsGenPredictionRoundTripDelay
                        INTEGER,
                    fclFrCfsGenNetworkBandwidth
                        INTEGER
                }


    fclFrCfsGenConfigId OBJECT-TYPE
        SYNTAX  INTEGER (0..199)
        ACCESS  read-only
        STATUS  mandatory
        DESCRIPTION
                "Configuration id"
        ::= { fclFrCfsGeneralParameterEntry 1 }


    fclFrCfsGenCallReturnTransmission OBJECT-TYPE
        SYNTAX  INTEGER {
                off(1),
                onIfFailed(3),
                onIfFailedOrBusy(4)
                }
        ACCESS  read-write
        STATUS  mandatory
        DESCRIPTION
                "Retour d'appel"
        ::= { fclFrCfsGeneralParameterEntry 15 }


    fclFrCfsGenUnuseTimer OBJECT-TYPE
        SYNTAX  INTEGER (0..2550)
        ACCESS  read-write
        STATUS  mandatory
        DESCRIPTION
                "Tempo 0 CV en secondes (0 = pas de surveillance)"
        ::= { fclFrCfsGeneralParameterEntry 20 }


    fclFrCfsGenDlcSetupAlarmThreshold OBJECT-TYPE
        SYNTAX  INTEGER (0..250)
        ACCESS  read-write
        STATUS  mandatory
        DESCRIPTION
                "A% Seuil alarmique d'acceptation des connexions
                (pourcentage du debit de la ligne)"
        ::= { fclFrCfsGeneralParameterEntry 30 }


    fclFrCfsGenDlcSetupDiscardThreshold OBJECT-TYPE
        SYNTAX  INTEGER (100..1100)
        ACCESS  read-write
        STATUS  mandatory
        DESCRIPTION
                "R% Seuil de refus d'etablissement des DLC VBR-NRT
                (pourcentage du debit de la ligne : 100 = pas de
                surbooking)"
        ::= { fclFrCfsGeneralParameterEntry 31 }


    fclFrCfsGenBookingUbrThreshold OBJECT-TYPE
        SYNTAX  INTEGER (0..100)
        ACCESS  read-write
        STATUS  mandatory
        DESCRIPTION
                "U% Bande passante reservee aux reseaux virtuels
                UBR (pourcentage du debit de la ligne)"
        ::= { fclFrCfsGeneralParameterEntry 32 }


    fclFrCfsGenBookingVbrRtThreshold OBJECT-TYPE
        SYNTAX  INTEGER (0..100)
        ACCESS  read-write
        STATUS  mandatory
        DESCRIPTION
                "V% Bande passante reservee aux COS VBR-RT
                (pourcentage du debit de la ligne)"
        ::= { fclFrCfsGeneralParameterEntry 33 }


    fclFrCfsGenBehavior OBJECT-TYPE
        SYNTAX  INTEGER {
                normal(1),
                svc-endpoint(2)
                }
        ACCESS  read-write
        STATUS  mandatory
        DESCRIPTION
                "Type de comportement"
        ::= { fclFrCfsGeneralParameterEntry 40 }


    fclFrCfsGenDynamicEir OBJECT-TYPE
        SYNTAX  INTEGER {
                off(1),
                on(2)
                }
        ACCESS  read-write
        STATUS  mandatory
        DESCRIPTION
                "The value 'off' of this object means the Burst
                Exceeded object configuration is used in the
                traffic management plan with respect agreement
                traffic. The value 'on' of this object allows the
                whole connection to have a fair share of the line
                bandwidth in the proportion of the Commited
                Information Rate. In this case, the Burst Exceeded
                used in the traffic control is made dynamically
                from the unloaded line in the prorata of the CIR.
                 The default value is 'on'."
        ::= { fclFrCfsGeneralParameterEntry 41 }


    fclFrCfsGenPredictionRoundTripDelay OBJECT-TYPE
        SYNTAX  INTEGER (0..250)
        ACCESS  read-write
        STATUS  mandatory
        DESCRIPTION
                "Prediction du delai de propagation"
        ::= { fclFrCfsGeneralParameterEntry 42 }


    fclFrCfsGenNetworkBandwidth OBJECT-TYPE
        SYNTAX  INTEGER (0..34)
        ACCESS  read-write
        STATUS  mandatory
        DESCRIPTION
                "Bande passante du reseau"
        ::= { fclFrCfsGeneralParameterEntry 43 }


    fclFrCfsSignallingTable OBJECT-TYPE
        SYNTAX  SEQUENCE OF FclFrCfsSignallingEntry
        ACCESS  not-accessible
        STATUS  mandatory
        DESCRIPTION
                ""
        ::= { fclFrConfigurationSe 20 }


    fclFrCfsSignallingEntry OBJECT-TYPE
        SYNTAX  FclFrCfsSignallingEntry
        ACCESS  not-accessible
        STATUS  mandatory
        DESCRIPTION
                "An entry of fclFrCfsSignallingTable."
        INDEX   { fclFrCfsSigConfigId }
        ::= { fclFrCfsSignallingTable 1 }


        FclFrCfsSignallingEntry ::=
                SEQUENCE {
                    fclFrCfsSigConfigId
                        INTEGER,
                    fclFrCfsSigOuputTimeout
                        INTEGER,
                    fclFrCfsSigSignalOutputWinSize
                        INTEGER,
                    fclFrCfsSigN200RetransMaxCount
                        INTEGER,
                    fclFrCfsSigT200RetransTimer
                        INTEGER,
                    fclFrCfsSigT203InactivityTimer
                        INTEGER,
                    fclFrCfsSigT303SetupResponseTimer
                        INTEGER,
                    fclFrCfsSigT305DisconnectResponseTimer
                        INTEGER,
                    fclFrCfsSigT308ReleaseResponseTimer
                        INTEGER,
                    fclFrCfsSigT310CallProceedingTimer
                        INTEGER,
                    fclFrCfsSigT316RestartAcknowledgeTimer
                        INTEGER
                }


    fclFrCfsSigConfigId OBJECT-TYPE
        SYNTAX  INTEGER (0..199)
        ACCESS  read-only
        STATUS  mandatory
        DESCRIPTION
                "Configuration id"
        ::= { fclFrCfsSignallingEntry 1 }


    fclFrCfsSigOuputTimeout OBJECT-TYPE
        SYNTAX  INTEGER (0..51000)
        ACCESS  read-write
        STATUS  mandatory
        DESCRIPTION
                "Tempo de surveillance de ligne en emission en
                millisecondes"
        ::= { fclFrCfsSignallingEntry 2 }


    fclFrCfsSigSignalOutputWinSize OBJECT-TYPE
        SYNTAX  INTEGER (1..7)
        ACCESS  read-write
        STATUS  mandatory
        DESCRIPTION
                "Fenetre d'emission DLCI de signalisation"
        ::= { fclFrCfsSignallingEntry 3 }


    fclFrCfsSigN200RetransMaxCount OBJECT-TYPE
        SYNTAX  INTEGER (1..255)
        ACCESS  read-write
        STATUS  mandatory
        DESCRIPTION
                "N 200 : Nombre de repetition trames"
        ::= { fclFrCfsSignallingEntry 5 }


    fclFrCfsSigT200RetransTimer OBJECT-TYPE
        SYNTAX  INTEGER (0..25500)
        ACCESS  read-write
        STATUS  mandatory
        DESCRIPTION
                "T 200 : Tempo de retransmission en millisecondes"
        ::= { fclFrCfsSignallingEntry 6 }


    fclFrCfsSigT203InactivityTimer OBJECT-TYPE
        SYNTAX  INTEGER (0..255)
        ACCESS  read-write
        STATUS  mandatory
        DESCRIPTION
                "T 203 : Polling RR en secondes"
        ::= { fclFrCfsSignallingEntry 7 }


    fclFrCfsSigT303SetupResponseTimer OBJECT-TYPE
        SYNTAX  INTEGER (1..255)
        ACCESS  read-write
        STATUS  mandatory
        DESCRIPTION
                "T 303 : Tempo attente de reponse a un
                etablissement sortant en secondes"
        ::= { fclFrCfsSignallingEntry 11 }


    fclFrCfsSigT305DisconnectResponseTimer OBJECT-TYPE
        SYNTAX  INTEGER (1..255)
        ACCESS  read-write
        STATUS  mandatory
        DESCRIPTION
                "T 305 : Tempo attente de reponse a une demande de
                deconnexion en secondes"
        ::= { fclFrCfsSignallingEntry 12 }


    fclFrCfsSigT308ReleaseResponseTimer OBJECT-TYPE
        SYNTAX  INTEGER (1..255)
        ACCESS  read-write
        STATUS  mandatory
        DESCRIPTION
                "T 308 : Tempo attente de reponse a une demande de
                liberation en secondes"
        ::= { fclFrCfsSignallingEntry 13 }


    fclFrCfsSigT310CallProceedingTimer OBJECT-TYPE
        SYNTAX  INTEGER (1..255)
        ACCESS  read-write
        STATUS  mandatory
        DESCRIPTION
                "T 310 : Tempo entre un appel recu et une alerte ou
                une connexion en secondes"
        ::= { fclFrCfsSignallingEntry 15 }


    fclFrCfsSigT316RestartAcknowledgeTimer OBJECT-TYPE
        SYNTAX  INTEGER (0..255)
        ACCESS  read-write
        STATUS  mandatory
        DESCRIPTION
                "T 316 : Tempo de reponse au RESTART en secondes (0
                = pas de RESTART)"
        ::= { fclFrCfsSignallingEntry 17 }


    fclInterUnitLink OBJECT IDENTIFIER ::= { fcLogicalPorts 45 }


    fclInterUnitLinkTable OBJECT-TYPE
        SYNTAX  SEQUENCE OF FclInterUnitLinkEntry
        ACCESS  not-accessible
        STATUS  mandatory
        DESCRIPTION
                ""
        ::= { fclInterUnitLink 1 }


    fclInterUnitLinkEntry OBJECT-TYPE
        SYNTAX  FclInterUnitLinkEntry
        ACCESS  not-accessible
        STATUS  mandatory
        DESCRIPTION
                "An entry of fclInterUnitLinkTable."
        INDEX   { fclIulLogPortId }
        ::= { fclInterUnitLinkTable 1 }


        FclInterUnitLinkEntry ::=
                SEQUENCE {
                    fclIulLogPortId
                        INTEGER,
                    fclIulInterfaceId
                        INTEGER,
                    fclIulCallReturnTransmission
                        INTEGER,
                    fclIulConversionAimedPoint
                        INTEGER,
                    fclIulConversionIncomingCall
                        INTEGER,
                    fclIulConversionOutgoingCall
                        INTEGER,
                    fclIulConversionAddressCheck
                        INTEGER
                }


    fclIulLogPortId OBJECT-TYPE
        SYNTAX  INTEGER (36..41)
        ACCESS  read-only
        STATUS  mandatory
        DESCRIPTION
                "LP id"
        ::= { fclInterUnitLinkEntry 1 }


    fclIulInterfaceId OBJECT-TYPE
        SYNTAX  INTEGER (36..41)
        ACCESS  read-write
        STATUS  mandatory
        DESCRIPTION
                "IF id (type LIU)"
        ::= { fclInterUnitLinkEntry 2 }


    fclIulCallReturnTransmission OBJECT-TYPE
        SYNTAX  INTEGER {
                off(1),
                on(3)
                }
        ACCESS  read-write
        STATUS  mandatory
        DESCRIPTION
                "Autorisation retour d'appel"
        ::= { fclInterUnitLinkEntry 5 }


    fclIulConversionAimedPoint OBJECT-TYPE
        SYNTAX  INTEGER {
                off(1),
                on(2)
                }
        ACCESS  read-write
        STATUS  mandatory
        DESCRIPTION
                "Conversion adresse : point vise"
        ::= { fclInterUnitLinkEntry 10 }


    fclIulConversionIncomingCall OBJECT-TYPE
        SYNTAX  INTEGER {
                off(1),
                callingAddress(2),
                calledAddress(3),
                callingAddressAndCalledAddress(4)
                }
        ACCESS  read-write
        STATUS  mandatory
        DESCRIPTION
                "Conversion d'adresse sur appel entrant"
        ::= { fclInterUnitLinkEntry 11 }


    fclIulConversionOutgoingCall OBJECT-TYPE
        SYNTAX  INTEGER {
                off(1),
                callingAddress(2),
                calledAddress(3),
                callingAddressAndCalledAddress(4)
                }
        ACCESS  read-write
        STATUS  mandatory
        DESCRIPTION
                "Conversion adresse sur appel sortant"
        ::= { fclInterUnitLinkEntry 12 }


    fclIulConversionAddressCheck OBJECT-TYPE
        SYNTAX  INTEGER {
                off(1),
                onIncomingCall(2),
                onOutgoingCall(3),
                onIncomingCallAndOutgoingCall(4)
                }
        ACCESS  read-write
        STATUS  mandatory
        DESCRIPTION
                "Conversion adresse : controle de la presence dans
                les tables de conversion"
        ::= { fclInterUnitLinkEntry 13 }


    fclX25Configurations OBJECT IDENTIFIER ::= { fcLogicalPorts 50 }


    fclX25ConfigAccess OBJECT IDENTIFIER ::= { fclX25Configurations 1 }


    fclX25ConfigAccessTable OBJECT-TYPE
        SYNTAX  SEQUENCE OF FclX25ConfigAccessEntry
        ACCESS  not-accessible
        STATUS  mandatory
        DESCRIPTION
                "This table contains the X25 access configurations
                used by X25 access links."
        ::= { fclX25ConfigAccess 1 }


    fclX25ConfigAccessEntry OBJECT-TYPE
        SYNTAX  FclX25ConfigAccessEntry
        ACCESS  not-accessible
        STATUS  mandatory
        DESCRIPTION
                "An entry of fclX25ConfigAccessTable."
        INDEX   { fclX25CfaConfigId }
        ::= { fclX25ConfigAccessTable 1 }


        FclX25ConfigAccessEntry ::=
                SEQUENCE {
                    fclX25CfaConfigId
                        INTEGER,
                    fclX25CfaStatus
                        INTEGER,
                    fclX25CfaDescription
                        DisplayString,
                    fclX25CfaProfileId
                        INTEGER,
                    fclX25CfaModificationCount
                        INTEGER
                }


    fclX25CfaConfigId OBJECT-TYPE
        SYNTAX  INTEGER (0..199)
        ACCESS  read-only
        STATUS  mandatory
        DESCRIPTION
                "The value of this object identifies one and only
                one X25 access configuration. This configuration
                may be referenced by fclX25AccX25AccessConfigId,
                fclX25InDX25AccessConfigId,
                fclX25InDIsdnRemX25AccConfigId or
                fclX25InBRemX25ConfigId.
                The possible values are : '0..199. If it is
                unused, the value of this parameter is '255'.
                The X25 access configuration parameters are
                described in :
                   fclX25CfaDataLinkNetworkTable : data link and
                        network levels,
                   fclX25CfaFacilityTable : facility level,
                   fclX25CfaNegotiatedFacilityTable : facility
                        level (negotiaitions),
                   fclX25CfaSignallingTable : signalling level,
                   fclX25CfaServiceTable : services level.
                When creating a new configuration each parameter
                takes its default value. Setting a profile allows
                the user to fill all the parameters with values
                pre-defined in this profile but each one may also
                be individually modified."
        ::= { fclX25ConfigAccessEntry 1 }


    fclX25CfaStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25ConfigAccessEntry 2 }


    fclX25CfaDescription OBJECT-TYPE
        SYNTAX  DisplayString (SIZE(0..32))
        ACCESS  read-write
        STATUS  mandatory
        DESCRIPTION
                "The value of this object stores a text description
                of the X25 access configuration elaborated by the
                user. This description may contains from 0 to 32
                characters. The default value is 'Subscriber with
                facilities'."
        ::= { fclX25ConfigAccessEntry 3 }


    fclX25CfaProfileId OBJECT-TYPE
        SYNTAX  INTEGER (0..199)
        ACCESS  read-write
        STATUS  mandatory
        DESCRIPTION
                "The value of this object is the profile number
                used to automatically valorize all the X25
                parameters in an entry of the five tables which
                composes X25 access configurations (see
                fclX25CfaConfigId).

                The possible values are :
                   00 Public network with facilities,
                   01 Subscribers without facilities,
                   02 Subscribers with facilities,
                   03 PSTN,
                   19 PSTN VX.32 (TRANSPAC),

                If it is unused, the value of this parameter is
                '255'.
                The default value is '2' (meaning that default
                values of X25 parameters are those pre-defined in
                profile number 02)."
        ::= { fclX25ConfigAccessEntry 4 }


    fclX25CfaModificationCount OBJECT-TYPE
        SYNTAX  INTEGER (0..255)
        ACCESS  read-only
        STATUS  mandatory
        DESCRIPTION
                "The value of this object indicates how many X25
                parameters have not the value defined in the
                profile specified by fclX25CfaProfileId (i.e how
                many individual modifications)."
        ::= { fclX25ConfigAccessEntry 5 }


    fclX25CfaDataLinkNetworkTable OBJECT-TYPE
        SYNTAX  SEQUENCE OF FclX25CfaDataLinkNetworkEntry
        ACCESS  not-accessible
        STATUS  mandatory
        DESCRIPTION
                "This table contains the data link and network
                levels parameters of X25 access configurations."
        ::= { fclX25ConfigAccess 10 }


    fclX25CfaDataLinkNetworkEntry OBJECT-TYPE
        SYNTAX  FclX25CfaDataLinkNetworkEntry
        ACCESS  not-accessible
        STATUS  mandatory
        DESCRIPTION
                "An entry of fclX25CfaDataLinkNetworkTable."
        INDEX   { fclX25CfaDlnConfigId }
        ::= { fclX25CfaDataLinkNetworkTable 1 }


        FclX25CfaDataLinkNetworkEntry ::=
                SEQUENCE {
                    fclX25CfaDlnConfigId
                        INTEGER,
                    fclX25CfaDlnStationType
                        INTEGER,
                    fclX25CfaDlnNetworkType
                        INTEGER,
                    fclX25CfaDlnN2RetryCount
                        INTEGER,
                    fclX25CfaDlnT1AcknowledgeTimer
                        INTEGER,
                    fclX25CfaDlnT2AcknwledgeDelayTimer
                        INTEGER,
                    fclX25CfaDlnKWindowSize
                        INTEGER,
                    fclX25CfaDlnEachPacketAcknowledgement
                        INTEGER,
                    fclX25CfaDlnLowestIncomingChannel
                        INTEGER,
                    fclX25CfaDlnIncomingChannelCount
                        INTEGER,
                    fclX25CfaDlnLowestTwoWayChannel
                        INTEGER,
                    fclX25CfaDlnTwoWayChannelCount
                        INTEGER,
                    fclX25CfaDlnLowestOutgoingChannel
                        INTEGER,
                    fclX25CfaDlnOutgoingChannelCount
                        INTEGER,
                    fclX25CfaDlnOutgoingChannelNumbering
                        INTEGER,
                    fclX25CfaDlnDBitModification
                        INTEGER
                }


    fclX25CfaDlnConfigId OBJECT-TYPE
        SYNTAX  INTEGER (0..199)
        ACCESS  read-only
        STATUS  mandatory
        DESCRIPTION
                "The value of this object identifies one and only
                one X25 access configuration. The possible values
                are : '0..199. If it is unused, the value of this
                parameter is '255'."
        ::= { fclX25CfaDataLinkNetworkEntry 1 }


    fclX25CfaDlnStationType OBJECT-TYPE
        SYNTAX  INTEGER {
                dte(1),
                dce(2)
                }
        ACCESS  read-write
        STATUS  mandatory
        DESCRIPTION
                "The value of this object defines the type of the
                interface at the data link layer (and not at the
                physical layer which is defined in fcfLineType).
                The equipment can acts as a DTE (Data Terminal
                Equipment) or as a DCE (Data Circuit-terminating
                Equipment). The default value is 'dce'."
        ::= { fclX25CfaDataLinkNetworkEntry 2 }


    fclX25CfaDlnNetworkType OBJECT-TYPE
        SYNTAX  INTEGER {
                x25(1),
                transpac(5),
                telenet(9),
                tymnet(13),
                infoSwitch(17),
                datapac(21),
                dn1(25),
                pss(29),
                germanyDatexP(33),
                dcs(37),
                itapac(41),
                austpac(45),
                uninet(53),
                telepac(61),
                iberpac(65),
                datapak(69),
                helpac(73),
                entel(77),
                austriaDatexP(93)
                }
        ACCESS  read-write
        STATUS  mandatory
        DESCRIPTION
                "The value of this parameter defines the type of
                the network which the equipment is working with.
                The authorized values are :
                   x25,
                   'transpac' in France,
                   'telenet' in the USA,
                   'tymnet' in the USA,
                   'infoSwitch' in Canada,
                   'datapac' in Canada,
                   'dn1' in the Netherlands,
                   'pss' in Great Britain,
                   'germanyDatexP' in Germany,
                   'dcs' in Belgium,
                   'itapac' in Italy,
                   'austpac' in Australia,
                   'uninet' in the USA,
                   'telepac' in Switzerland,
                   'iberpac' in Spain,
                   'datapak' in Sweden,
                   'helpac' in Greece,
                   'entel' in Argentina,
                   'austriaDatexP' in Austria.
                The default value is 'transpac'."
        ::= { fclX25CfaDataLinkNetworkEntry 3 }


    fclX25CfaDlnN2RetryCount OBJECT-TYPE
        SYNTAX  INTEGER (2..250)
        ACCESS  read-write
        STATUS  mandatory
        DESCRIPTION
                "The value of this object indicates the maximum
                number (N2) of attempts made by the equipment to
                complete the successfull transmission of a frame.
                The authorized values are '2..250'. The default
                value is '10'."
        ::= { fclX25CfaDataLinkNetworkEntry 5 }


    fclX25CfaDlnT1AcknowledgeTimer OBJECT-TYPE
        SYNTAX  INTEGER (200..25000)
        ACCESS  read-write
        STATUS  mandatory
        DESCRIPTION
                "The value of this object indicates the period
                (T1), in milliseconds, at the end of which
                retransmission of a frame may be initiated. The
                authorized values are '200..25000'. The default
                value is '1600'."
        ::= { fclX25CfaDataLinkNetworkEntry 6 }


    fclX25CfaDlnT2AcknwledgeDelayTimer OBJECT-TYPE
        SYNTAX  INTEGER (100..12700)
        ACCESS  read-write
        STATUS  mandatory
        DESCRIPTION
                "The value of this object indicates the amount of
                time available (T2), in milliseconds, before the
                acknowledging frame must be initiated. This
                parameter must be smaller than T1. The authorized
                values are '100..12700'. The default value is
                '100'."
        ::= { fclX25CfaDataLinkNetworkEntry 7 }


    fclX25CfaDlnKWindowSize OBJECT-TYPE
        SYNTAX  INTEGER (1..127)
        ACCESS  read-write
        STATUS  mandatory
        DESCRIPTION
                "The value of this object indicates the maximum
                number (K) of sequentially numbered I frames that
                the equipment may have outstanding (i.e..
                unacknowledged) at any given time. The authorized
                values are '1..127'. The default value is '4'."
        ::= { fclX25CfaDataLinkNetworkEntry 8 }


    fclX25CfaDlnEachPacketAcknowledgement OBJECT-TYPE
        SYNTAX  INTEGER {
                off(1),
                on(2)
                }
        ACCESS  read-write
        STATUS  mandatory
        DESCRIPTION
                "The value of this object indicates whether each
                frame is acknowledged or not. The default value is
                'off'."
        ::= { fclX25CfaDataLinkNetworkEntry 9 }


    fclX25CfaDlnLowestIncomingChannel OBJECT-TYPE
        SYNTAX  INTEGER (0..4095)
        ACCESS  read-write
        STATUS  mandatory
        DESCRIPTION
                "The value of this object is the Lowest Incoming
                one-way logical Channel (LIC).The authorized
                values are '0..4095'. The default value is '26'."
        ::= { fclX25CfaDataLinkNetworkEntry 10 }


    fclX25CfaDlnIncomingChannelCount OBJECT-TYPE
        SYNTAX  INTEGER (0..4096)
        ACCESS  read-write
        STATUS  mandatory
        DESCRIPTION
                "The value of this object is the Number of Incoming
                one-way logical Channels (NIC). So the Highest
                Incoming one-way logical Channel (HIC) is : HIC =
                LIC + NIC - 1. The authorized values are
                '0..4096'. The default value is '0'."
        ::= { fclX25CfaDataLinkNetworkEntry 11 }


    fclX25CfaDlnLowestTwoWayChannel OBJECT-TYPE
        SYNTAX  INTEGER (0..4095)
        ACCESS  read-write
        STATUS  mandatory
        DESCRIPTION
                "The value of this object is the Lowest Two-way
                logical Channel (LTC). The authorized values are
                '0..4095'. The default value is '1'."
        ::= { fclX25CfaDataLinkNetworkEntry 15 }


    fclX25CfaDlnTwoWayChannelCount OBJECT-TYPE
        SYNTAX  INTEGER (0..4096)
        ACCESS  read-write
        STATUS  mandatory
        DESCRIPTION
                "The value of this object is the Number of Two-way
                logical Channels. So the Highest Two-way logical
                Channel (HTC) is : HTC = LTC + NTC - 1. The
                authorized values are '0..4096'. The default value
                is '25'."
        ::= { fclX25CfaDataLinkNetworkEntry 16 }


    fclX25CfaDlnLowestOutgoingChannel OBJECT-TYPE
        SYNTAX  INTEGER (0..4095)
        ACCESS  read-write
        STATUS  mandatory
        DESCRIPTION
                "The value of this object is the Lowest Outgoing
                one-way logical Channel (LOC). The authorized
                values are '0..4095'. The default value is '1'."
        ::= { fclX25CfaDataLinkNetworkEntry 17 }


    fclX25CfaDlnOutgoingChannelCount OBJECT-TYPE
        SYNTAX  INTEGER (0..4096)
        ACCESS  read-write
        STATUS  mandatory
        DESCRIPTION
                "The value of this object is the Number of Outgoing
                one-way logical Channels (NOC). So the Highest
                Outgoing one-way logical Channel (HOC) is : HOC =
                LOC + NOC - 1. The authorized values are
                '0..4096'. The default value is '0'."
        ::= { fclX25CfaDataLinkNetworkEntry 18 }


    fclX25CfaDlnOutgoingChannelNumbering OBJECT-TYPE
        SYNTAX  INTEGER {
                decremental(1),
                incremental(2)
                }
        ACCESS  read-write
        STATUS  mandatory
        DESCRIPTION
                "The value of this object indicates whether the
                equipment searches for a logical channel from the
                lowest one to the highest one (incremental order)
                or from the highest one to the lowest one
                (decremental order). The default value is
                'incremental'."
        ::= { fclX25CfaDataLinkNetworkEntry 19 }


    fclX25CfaDlnDBitModification OBJECT-TYPE
        SYNTAX  INTEGER {
                off(1),
                clear(2),
                on(3)
                }
        ACCESS  read-write
        STATUS  mandatory
        DESCRIPTION
                "The value of this object indicates how the
                equipment manages the D bit (Delivery Confirmation
                Bit). When it receives a call from a DTE wishing
                to receive an end-to-end acknowledgement of
                delivery the equipment may :
                   ignore this D bit procedure ('off' value), ???
                   indicate clearing ('clear' value),
                   ??? ('on' value),
                The default value is 'on'."
        ::= { fclX25CfaDataLinkNetworkEntry 30 }


    fclX25CfaFacilityTable OBJECT-TYPE
        SYNTAX  SEQUENCE OF FclX25CfaFacilityEntry
        ACCESS  not-accessible
        STATUS  mandatory
        DESCRIPTION
                "This table contains the facility level parameters
                of X25 access configurations (except fast select,
                throughput class, packet size and window size
                which take place in
                fclX25CfaNegotiatedFacilityTable)."
        ::= { fclX25ConfigAccess 20 }


    fclX25CfaFacilityEntry OBJECT-TYPE
        SYNTAX  FclX25CfaFacilityEntry
        ACCESS  not-accessible
        STATUS  mandatory
        DESCRIPTION
                "An entry of fclX25CfaFacilityTable."
        INDEX   { fclX25CfaFacConfigId }
        ::= { fclX25CfaFacilityTable 1 }


        FclX25CfaFacilityEntry ::=
                SEQUENCE {
                    fclX25CfaFacConfigId
                        INTEGER,
                    fclX25CfaFacClosedUserGroup
                        INTEGER,
                    fclX25CfaFacReverseCharging
                        INTEGER,
                    fclX25CfaFacTransitDelay
                        INTEGER,
                    fclX25CfaFacOutputMarkers
                        INTEGER,
                    fclX25CfaFacInputMarkers
                        INTEGER,
                    fclX25CfaFacOutputUnknownFacility
                        INTEGER,
                    fclX25CfaFacInputUnknownFacility
                        INTEGER
                }


    fclX25CfaFacConfigId OBJECT-TYPE
        SYNTAX  INTEGER (0..199)
        ACCESS  read-only
        STATUS  mandatory
        DESCRIPTION
                "The value of this object identifies one and only
                one X25 access configuration. The possible values
                are : '0..199. If it is unused, the value of this
                parameter is '255'."
        ::= { fclX25CfaFacilityEntry 1 }


    fclX25CfaFacClosedUserGroup OBJECT-TYPE
        SYNTAX  INTEGER {
                noCheck(2),
                clear(1),
                subscribe(3),
                subscribeAndRemove(4)
                }
        ACCESS  read-write
        STATUS  mandatory
        DESCRIPTION
                "The value of this object specifies the behaviour
                of the equipment with respect to the Closed User
                Group (CUG) facility. There are 4 possible values
                :
                   noCheck : the CUG is not checked,
                   clear : clearing if the CUG is present in a
                        call packet from a subscriber,
                   subscribe : clearing if the CUG is not present
                        in a call packet from a subcriber,
                   subscribeAndRemove :
                     clearing if the CUG is not present in a call
                        packet from a subcriber,
                     suppression of the CUG in a call packet to a
                        subcriber.
                The default value is 'noCheck'."
        ::= { fclX25CfaFacilityEntry 2 }


    fclX25CfaFacReverseCharging OBJECT-TYPE
        SYNTAX  INTEGER {
                refuse(1),
                accept(2)
                }
        ACCESS  read-write
        STATUS  mandatory
        DESCRIPTION
                "The value of this object specifies the behaviour
                of the equipment with respect to the reverse
                charging facility. If the called subscriber
                doesn't accept the reverse charging, the call is
                not transmitted and a clear is sent. The default
                value is 'refuse'."
        ::= { fclX25CfaFacilityEntry 5 }


    fclX25CfaFacTransitDelay OBJECT-TYPE
        SYNTAX  INTEGER {
                noCheck(1),
                clear(3),
                subscribe(2)
                }
        ACCESS  read-write
        STATUS  mandatory
        DESCRIPTION
                "The value of this object specifies the behaviour
                of the equipment with respect to the transit delay
                facility. The authorized values are :

                noCheck : no checking

                clear : clearing

                subscribe : according to the following table :

                    ~~~~~~~~~~~~~~~~~~~~~~~~~~~~~~~~~~~~~~~~~~~~~
                    |    packet    |from network|from subscriber|
                    |~~~~~~~~~~~~~~|~~~~~~~~~~~~|~~~~~~~~~~~~~~~|
                    |     call     |no checking |  no checking  |
                    |~~~~~~~~~~~~~~|~~~~~~~~~~~~|~~~~~~~~~~~~~~~|
                    |call connected|no checking | clearing (2)  |
                    |~~~~~~~~~~~~~~|~~~~~~~~~~~~|~~~~~~~~~~~~~~~|
                    |     clear    |clearing (1)| clearing (2)  |
                    ~~~~~~~~~~~~~~~~~~~~~~~~~~~~~~~~~~~~~~~~~~~~~
                    (1) : diagnostic = 05 41
                    (2) : diagnostic to local equipment = 03 41,
                          diagnostic to remote equipment = 03 41

                The default value is 'noCheck'."
        ::= { fclX25CfaFacilityEntry 6 }


    fclX25CfaFacOutputMarkers OBJECT-TYPE
        SYNTAX  INTEGER {
                noCheck(1),
                check(2),
                remove(3)
                }
        ACCESS  read-write
        STATUS  mandatory
        DESCRIPTION
                "The value of this object specifies the behaviour
                of the equipment with respect to the outgoing
                facility markers. The authorized values are :

                noCheck : no checking,

                remove : the markers are not transmitted,

                check : according to the following table :

                 ~~~~~~~~~~~~~~~~~~~~~~~~~~~~~~~~~~~~~~~~~~~~~~~~~
                 | packet  |           facility marker           |
                 |         |~~~~~~~~~~~~~~~~~~~~~~~~~~~~~~~~~~~~~~
                 |         |  0000 (1)  |  00FF (2)  |  000F (3) |
                 |~~~~~~~~~|~~~~~~~~~~~~|~~~~~~~~~~~~|~~~~~~~~~~~|
                 |  call   |no checking |clearing (5)|no checking|
                 |~~~~~~~~~|~~~~~~~~~~~~|~~~~~~~~~~~~|~~~~~~~~~~~|
                 |  call   |            |            |           |
                 |connected|clearing (4)|no checking |no checking|
                 |~~~~~~~~~|~~~~~~~~~~~~|~~~~~~~~~~~~|~~~~~~~~~~~|
                 |  clear  |     -      |     -      |no checking|
                 ~~~~~~~~~~~~~~~~~~~~~~~~~~~~~~~~~~~~~~~~~~~~~~~~~
                   (1) : registration codes,
                         non-x25 facilities provided by the
                            network in case of intranetwork calls,
                         non-x25 facilities provided by the
                            network to which the calling DTE is
                            connected in case of internetwork
                            calls
                   (2) : non-x25 facilities provided by the
                            network to which the calling DTE is
                            connected in case of intranetwork
                            calls
                   (3) : CCITT-specified DTE facilities
                   (4) : diagnostic to local equipment = 03 42,
                         diagnostic to remote equipment = 11 42
                   (5) : diagnostic to local equipment = 03 42

                The default value is 'noCheck'."
        ::= { fclX25CfaFacilityEntry 7 }


    fclX25CfaFacInputMarkers OBJECT-TYPE
        SYNTAX  INTEGER {
                noCheck(1),
                check(2),
                remove(3)
                }
        ACCESS  read-write
        STATUS  mandatory
        DESCRIPTION
                "Marqueurs en reception"
        ::= { fclX25CfaFacilityEntry 8 }


    fclX25CfaFacOutputUnknownFacility OBJECT-TYPE
        SYNTAX  INTEGER {
                noCheck(1),
                clear(3),
                remove(2)
                }
        ACCESS  read-write
        STATUS  mandatory
        DESCRIPTION
                "The value of this object specifies the behaviour
                of the equipment with respect to an outgoing
                unknown facility. The authorized values are :

                noCheck : no checking,

                remove : the unknown facility is not sent,

                clear : clearing.


                The default value is 'noCheck'."
        ::= { fclX25CfaFacilityEntry 10 }


    fclX25CfaFacInputUnknownFacility OBJECT-TYPE
        SYNTAX  INTEGER {
                noCheck(1),
                clear(3),
                remove(2)
                }
        ACCESS  read-write
        STATUS  mandatory
        DESCRIPTION
                "The value of this object specifies the behaviour
                of the equipment with respect to an incoming
                unknown facility. The authorized values are :

                noCheck : no checking,

                remove : the unknown facility is not sent,

                clear : clearing.


                The default value is 'noCheck'."
        ::= { fclX25CfaFacilityEntry 11 }


    fclX25CfaNegotiatedFacilityTable OBJECT-TYPE
        SYNTAX  SEQUENCE OF FclX25CfaNegotiatedFacilityEntry
        ACCESS  not-accessible
        STATUS  mandatory
        DESCRIPTION
                "This table contains the facility level parameters
                of X25 access configurations (except closed user
                group, reverse charging, transit delay, markers,
                unknown facility which take place in
                fclX25CfaFacilityTable)."
        ::= { fclX25ConfigAccess 21 }


    fclX25CfaNegotiatedFacilityEntry OBJECT-TYPE
        SYNTAX  FclX25CfaNegotiatedFacilityEntry
        ACCESS  not-accessible
        STATUS  mandatory
        DESCRIPTION
                "An entry of fclX25CfaNegotiatedFacilityTable."
        INDEX   { fclX25CfaNegConfigId }
        ::= { fclX25CfaNegotiatedFacilityTable 1 }


        FclX25CfaNegotiatedFacilityEntry ::=
                SEQUENCE {
                    fclX25CfaNegConfigId
                        INTEGER,
                    fclX25CfaNegOutputFastSelect
                        INTEGER,
                    fclX25CfaNegInputFastSelect
                        INTEGER,
                    fclX25CfaNegThroughputClass
                        INTEGER,
                    fclX25CfaNegDefOutThroughputClass
                        INTEGER,
                    fclX25CfaNegDefInThroughputClass
                        INTEGER,
                    fclX25CfaNegMaxOutThroughputClass
                        INTEGER,
                    fclX25CfaNegMaxInThroughputClass
                        INTEGER,
                    fclX25CfaNegPacketSize
                        INTEGER,
                    fclX25CfaNegDefOutPacketSize
                        INTEGER,
                    fclX25CfaNegDefInPacketSize
                        INTEGER,
                    fclX25CfaNegMaxOutPacketSize
                        INTEGER,
                    fclX25CfaNegMaxInPacketSize
                        INTEGER,
                    fclX25CfaNegMinOutPacketSize
                        INTEGER,
                    fclX25CfaNegMinInPacketSize
                        INTEGER,
                    fclX25CfaNegWindowSize
                        INTEGER,
                    fclX25CfaNegDefOutWindowSize
                        INTEGER,
                    fclX25CfaNegDefInWindowSize
                        INTEGER,
                    fclX25CfaNegMaxOutWindowSize
                        INTEGER,
                    fclX25CfaNegMaxInWindowSize
                        INTEGER
                }


    fclX25CfaNegConfigId OBJECT-TYPE
        SYNTAX  INTEGER (0..199)
        ACCESS  read-only
        STATUS  mandatory
        DESCRIPTION
                "The value of this object identifies one and only
                one X25 access configuration. The possible values
                are : '0..199. If it is unused, the value of this
                parameter is '255'."
        ::= { fclX25CfaNegotiatedFacilityEntry 1 }


    fclX25CfaNegOutputFastSelect OBJECT-TYPE
        SYNTAX  INTEGER {
                noCheck(3),
                clear(1),
                subscribe(2)
                }
        ACCESS  read-write
        STATUS  mandatory
        DESCRIPTION
                "The value of this object specifies the behaviour
                of the equipment with respect to the fast select
                facility in outgoing call. The authorized values
                are 'noCheck' (no checking), 'clear' (clearing),
                'subscribe'. The default value is 'noCheck'."
        ::= { fclX25CfaNegotiatedFacilityEntry 2 }


    fclX25CfaNegInputFastSelect OBJECT-TYPE
        SYNTAX  INTEGER {
                subscribe(2),
                longUserData(4)
                }
        ACCESS  read-write
        STATUS  mandatory
        DESCRIPTION
                "The value of this object is the maximum size of
                the call user data field in a received call
                request packet not containing the fast select
                facility. The authorized values are 'subscribe'
                (up to 16 bytes) or 'longUserData' (up to 128
                bytes). The default value is 'subscribe'."
        ::= { fclX25CfaNegotiatedFacilityEntry 3 }


    fclX25CfaNegThroughputClass OBJECT-TYPE
        SYNTAX  INTEGER {
                clear(1),
                subscribe(2)
                }
        ACCESS  read-write
        STATUS  mandatory
        DESCRIPTION
                "The value of this object indicates whether the
                subscriber connected to the link has subscribed to
                throughput class negociation facility or not. The
                authorized values are 'clear' (not subscriber) or
                'subscribe'. The default value is 'subscribe'."
        ::= { fclX25CfaNegotiatedFacilityEntry 10 }


    fclX25CfaNegDefOutThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the default
                throughput class in transmit direction (equipment
                to remote peer). The default value is 4800 bits
                per second."
        ::= { fclX25CfaNegotiatedFacilityEntry 11 }


    fclX25CfaNegDefInThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the default
                throughput class in receive direction (remote peer
                to equipment). The default value is 4800 bits per
                second."
        ::= { fclX25CfaNegotiatedFacilityEntry 12 }


    fclX25CfaNegMaxOutThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the maximum
                throughput class in transmit direction (equipment
                to remote peer). The default value is 4800 bits
                per second."
        ::= { fclX25CfaNegotiatedFacilityEntry 13 }


    fclX25CfaNegMaxInThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the maximum
                throughput class in receive direction (equipment
                to remote peer). The default value is 4800 bits
                per second."
        ::= { fclX25CfaNegotiatedFacilityEntry 14 }


    fclX25CfaNegPacketSize OBJECT-TYPE
        SYNTAX  INTEGER {
                clear(1),
                subscribe(2)
                }
        ACCESS  read-write
        STATUS  mandatory
        DESCRIPTION
                "The value of this object indicates whether the
                subscriber connected to the link has subscribed to
                packet size negociation facility or not. The
                authorized values are 'clear' (not subscriber) or
                'subscribe'. The default value is 'subscribe'."
        ::= { fclX25CfaNegotiatedFacilityEntry 20 }


    fclX25CfaNegDefOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the default
                packet size in transmit direction (equipment to
                remote peer). The default value is 128 octets."
        ::= { fclX25CfaNegotiatedFacilityEntry 21 }


    fclX25CfaNegDefInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the default
                packet size in receive direction (remote peer to
                equipment). The default value is 128 octets."
        ::= { fclX25CfaNegotiatedFacilityEntry 22 }


    fclX25CfaNegMaxOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the maximum
                packet size in transmit direction (equipment to
                remote peer). The default value is 256 octets."
        ::= { fclX25CfaNegotiatedFacilityEntry 23 }


    fclX25CfaNegMaxInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the maximum
                packet size in receive direction (remote peer to
                equipment). The default value is 256 octets."
        ::= { fclX25CfaNegotiatedFacilityEntry 24 }


    fclX25CfaNegMinOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the minimum
                packet size in transmit direction (equipment to
                remote peer). The default value is 32 octets."
        ::= { fclX25CfaNegotiatedFacilityEntry 25 }


    fclX25CfaNegMinInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the minimum
                packet size in receive direction (remote peer to
                equipment). The default value is 32 octets."
        ::= { fclX25CfaNegotiatedFacilityEntry 26 }


    fclX25CfaNegWindowSize OBJECT-TYPE
        SYNTAX  INTEGER {
                clear(1),
                subscribe(2)
                }
        ACCESS  read-write
        STATUS  mandatory
        DESCRIPTION
                "The value of this object indicates whether the
                subscriber connected to the link has subscribed to
                the negociation of the transmit window size
                facility or not. The authorized values are 'clear'
                (not subscriber) or 'subscribe'. The default value
                is 'subscribe'."
        ::= { fclX25CfaNegotiatedFacilityEntry 30 }


    fclX25CfaNegDefOutWindowSize OBJECT-TYPE
        SYNTAX  INTEGER (1..7)
        ACCESS  read-write
        STATUS  mandatory
        DESCRIPTION
                "The value of this object indicates the default
                window size in transmit direction (equipment to
                remote peer). The authorized values are '1..7'.
                The default value is '2'."
        ::= { fclX25CfaNegotiatedFacilityEntry 31 }


    fclX25CfaNegDefInWindowSize OBJECT-TYPE
        SYNTAX  INTEGER (1..7)
        ACCESS  read-write
        STATUS  mandatory
        DESCRIPTION
                "The value of this object indicates the default
                window size in receive direction (remote peer to
                equipment). The authorized values are '1..7'. The
                default value is '4'."
        ::= { fclX25CfaNegotiatedFacilityEntry 32 }


    fclX25CfaNegMaxOutWindowSize OBJECT-TYPE
        SYNTAX  INTEGER (1..7)
        ACCESS  read-write
        STATUS  mandatory
        DESCRIPTION
                "The value of this object indicates the maximum
                window size in transmit direction (equipment to
                remote peer). The authorized values are '1..7'.
                The default value is '4'."
        ::= { fclX25CfaNegotiatedFacilityEntry 33 }


    fclX25CfaNegMaxInWindowSize OBJECT-TYPE
        SYNTAX  INTEGER (1..7)
        ACCESS  read-write
        STATUS  mandatory
        DESCRIPTION
                "The value of this object indicates the maximum
                window size in receive direction (remote peer to
                equipment). The authorized values are '1..7'. The
                default value is '4'."
        ::= { fclX25CfaNegotiatedFacilityEntry 34 }


    fclX25CfaSignallingTable OBJECT-TYPE
        SYNTAX  SEQUENCE OF FclX25CfaSignallingEntry
        ACCESS  not-accessible
        STATUS  mandatory
        DESCRIPTION
                "This table contains the signalling level
                parameters of X25 access configurations."
        ::= { fclX25ConfigAccess 30 }


    fclX25CfaSignallingEntry OBJECT-TYPE
        SYNTAX  FclX25CfaSignallingEntry
        ACCESS  not-accessible
        STATUS  mandatory
        DESCRIPTION
                "An entry of fclX25CfaSignallingTable."
        INDEX   { fclX25CfaSigConfigId }
        ::= { fclX25CfaSignallingTable 1 }


        FclX25CfaSignallingEntry ::=
                SEQUENCE {
                    fclX25CfaSigConfigId
                        INTEGER,
                    fclX25CfaSigType
                        INTEGER,
                    fclX25CfaSigPacketAddressCount
                        INTEGER,
                    fclX25CfaSigSubAddressTransmission
                        INTEGER,
                    fclX25CfaSigPdnIndicator
                        INTEGER,
                    fclX25CfaSigConversionAimedPoint
                        INTEGER,
                    fclX25CfaSigConversionIncomingCall
                        INTEGER,
                    fclX25CfaSigConversionOutgoingCall
                        INTEGER,
                    fclX25CfaSigConversionAddressCheck
                        INTEGER,
                    fclX25CfaSigConvMultiCalledAddrInCall
                        INTEGER,
                    fclX25CfaSigConvMultiCallingAddrInCall
                        INTEGER,
                    fclX25CfaSigConvMultiCalledAddrOutCall
                        INTEGER,
                    fclX25CfaSigConvMultiCallingAddrOutCall
                        INTEGER,
                    fclX25CfaSigOutPacketCauseField
                        INTEGER,
                    fclX25CfaSigInPacketCauseField
                        INTEGER,
                    fclX25CfaSigT11CallResponseTimer
                        INTEGER,
                    fclX25CfaSigCallAcceptedFormat
                        INTEGER,
                    fclX25CfaSigClearFormat
                        INTEGER
                }


    fclX25CfaSigConfigId OBJECT-TYPE
        SYNTAX  INTEGER (0..199)
        ACCESS  read-only
        STATUS  mandatory
        DESCRIPTION
                "The value of this object identifies one and only
                one X25 access configuration. The possible values
                are : '0..199. If it is unused, the value of this
                parameter is '255'."
        ::= { fclX25CfaSignallingEntry 1 }


    fclX25CfaSigType OBJECT-TYPE
        SYNTAX  INTEGER {
                x25Network(1),
                x25Subscriber(2),
                x75(3)
                }
        ACCESS  read-write
        STATUS  mandatory
        DESCRIPTION
                "The value of this object defines the signalling
                processing behaviour over the connected line. The
                authorized values are 'x25Network',
                'x25Subscriber', 'x75'. The default value is
                'x25Subscriber'."
        ::= { fclX25CfaSignallingEntry 2 }


    fclX25CfaSigPacketAddressCount OBJECT-TYPE
        SYNTAX  INTEGER (1..2)
        ACCESS  read-write
        STATUS  mandatory
        DESCRIPTION
                "The value of this object is the number of
                addresses in call request packets sent or
                received. The authorized values are '1..2'. The
                '1' value indicates that one of two addressing
                fields (calling address for packets from
                subscriber, called address for packets to
                subscriber) contains only the suffix (after DNIC
                ZO AB). The '2' value indicates that both
                addressing fields of each of the two types of call
                request packet (calling, called) contain the
                complete addresses. If fclX25CfaSigType is set to
                'x25Network', the value of this object must be
                '2'. The default value is '1'."
        ::= { fclX25CfaSignallingEntry 3 }


    fclX25CfaSigSubAddressTransmission OBJECT-TYPE
        SYNTAX  INTEGER {
                off(1),
                on(2)
                }
        ACCESS  read-write
        STATUS  mandatory
        DESCRIPTION
                "The value of this object indicates whether the
                sub-address of the called address field of the
                call request packet received on a PDNL (Public
                Data Network Link) is retransmitted on the
                outgoing line or not. The default value is 'off'."
        ::= { fclX25CfaSignallingEntry 4 }


    fclX25CfaSigPdnIndicator OBJECT-TYPE
        SYNTAX  INTEGER {
                off(1),
                pdnWithoutAddressTransmission(2),
                pdnWithAddressTransmission(5),
                dedicatedLaPoste(3),
                dedicatedTranspac(4)
                }
        ACCESS  read-write
        STATUS  mandatory
        DESCRIPTION
                "The value of this object specifies the behaviour
                of the equipment with respect to a PDNL (Public
                Data Network Link). The authorized values are :
                   off : it is not a PDNL,
                   pdnWithoutAddressTransmission : for a PDNL with
                        address transport,
                   pdnWithAddressTransmission : for a PDNL with
                        address packing,
                   dedicatedLaPoste : for Muse network,
                   dedicatedTranspac : for Transpac network.
                The default value is 'off'."
        ::= { fclX25CfaSignallingEntry 5 }


    fclX25CfaSigConversionAimedPoint OBJECT-TYPE
        SYNTAX  INTEGER {
                off(1),
                on(2)
                }
        ACCESS  read-write
        STATUS  mandatory
        DESCRIPTION
                "The value of this object indicates whether the
                'aimed point' address conversion is enabled or
                not. This conversion consists in making the
                routing process work not with the called address
                from the call packet but with a substituted
                address according to the address conversion table
                (see fcwAddrConvIncomingCallTable). Therefore this
                reduces the number of entries of the routing
                tables if several called addresses are converted
                to same 'aimed point' address. The default value
                is 'off'."
        ::= { fclX25CfaSignallingEntry 10 }


    fclX25CfaSigConversionIncomingCall OBJECT-TYPE
        SYNTAX  INTEGER {
                off(1),
                callingAddress(2),
                calledAddress(3),
                callingAddressAndCalledAddress(4)
                }
        ACCESS  read-write
        STATUS  mandatory
        DESCRIPTION
                "The value of this object indicates which address
                field are converted on an incoming call. The
                authorized values are :
                   off : no address field conversion,
                   callingAddress : conversion of the calling
                        address field according to the contains of
                        fcwAddrConvIncomingCallTable,
                   calledAddress : conversion of the called
                        address field according to the contains of
                        fcwAddrConvIncomingCallTable,
                   callingAddressAndCalledAddress : conversion of
                        the calling and called address fields
                        according to the contains of
                        fcwAddrConvIncomingCallTable.
                The default value is 'off'."
        ::= { fclX25CfaSignallingEntry 11 }


    fclX25CfaSigConversionOutgoingCall OBJECT-TYPE
        SYNTAX  INTEGER {
                off(1),
                callingAddress(2),
                calledAddress(3),
                callingAddressAndCalledAddress(4)
                }
        ACCESS  read-write
        STATUS  mandatory
        DESCRIPTION
                "The value of this object indicates which address
                field are converted on an outgoing call. The
                authorized values are :
                   off : no address field conversion,
                   callingAddress : conversion of the calling
                        address field according to the contains of
                        fcwAddrConvOutgoingCallTable,
                   calledAddress : conversion of the called
                        address field according to the contains of
                        fcwAddrConvOutgoingCallTable,
                   callingAddressAndCalledAddress : conversion of
                        the calling and called address fields
                        according to the contains of
                        fcwAddrConvOutgoingCallTable.
                The default value is 'off'."
        ::= { fclX25CfaSignallingEntry 12 }


    fclX25CfaSigConversionAddressCheck OBJECT-TYPE
        SYNTAX  INTEGER {
                off(1),
                onIncomingCall(2),
                onOutgoingCall(3),
                onIncomingCallAndOutgoingCall(4)
                }
        ACCESS  read-write
        STATUS  mandatory
        DESCRIPTION
                "The value of this object indicates the behaviour
                of the equipment when a requested address
                conversion can not be made because the address is
                not found in the address conversion tables
                (fcwAddrConvIncomingCallTable or
                fcwAddrConvOutgoingCallTable). In this case the
                call will be cleared when 'checking' is enabled.
                The authorized values are :
                   off : no checking,
                   onIncomingCall : checking on incoming calls,
                   onOutgoingCall : checking on outgoing calls,
                   onIcomingCallAndOutgoingCall : checking on
                        incoming and outgoing calls.
                   The default value is 'off'."
        ::= { fclX25CfaSignallingEntry 13 }


    fclX25CfaSigConvMultiCalledAddrInCall OBJECT-TYPE
        SYNTAX  INTEGER (1..99)
        ACCESS  read-write
        STATUS  mandatory
        DESCRIPTION
                "Numero d'identification pour conversion d'adresse
                d'appele multi-criteres en entree"
        ::= { fclX25CfaSignallingEntry 14 }


    fclX25CfaSigConvMultiCallingAddrInCall OBJECT-TYPE
        SYNTAX  INTEGER (1..99)
        ACCESS  read-write
        STATUS  mandatory
        DESCRIPTION
                "Numero d'identification pour conversion d'adresse
                d'appelant multi-criteres en entree"
        ::= { fclX25CfaSignallingEntry 15 }


    fclX25CfaSigConvMultiCalledAddrOutCall OBJECT-TYPE
        SYNTAX  INTEGER (1..99)
        ACCESS  read-write
        STATUS  mandatory
        DESCRIPTION
                "Numero d'identification pour conversion d'adresse
                d'appele multi-criteres en sortie"
        ::= { fclX25CfaSignallingEntry 16 }


    fclX25CfaSigConvMultiCallingAddrOutCall OBJECT-TYPE
        SYNTAX  INTEGER (1..99)
        ACCESS  read-write
        STATUS  mandatory
        DESCRIPTION
                "Numero d'identification pour conversion d'adresse
                d'appelant multi-criteres en sortie"
        ::= { fclX25CfaSignallingEntry 17 }


    fclX25CfaSigOutPacketCauseField OBJECT-TYPE
        SYNTAX  INTEGER {
                noModify(1),
                setToZero(2)
                }
        ACCESS  read-write
        STATUS  mandatory
        DESCRIPTION
                "The value of this object describes which operation
                the equipment makes on the cause field of reset,
                clear, and restart request and indication outgoing
                packets. The authorized values are :
                   noModify : no operation,
                   setToZero : the cause field is set to 0
                        (meaning 'DTE originated').
                The default value is 'noModify'."
        ::= { fclX25CfaSignallingEntry 20 }


    fclX25CfaSigInPacketCauseField OBJECT-TYPE
        SYNTAX  INTEGER {
                noModify(1),
                setToZero(2),
                setToZeroIfLowerThan128(3),
                modify(4)
                }
        ACCESS  read-write
        STATUS  mandatory
        DESCRIPTION
                "The value of this object describes which operation
                the equipment makes on the cause field of reset,
                clear, and restart request and indication incoming
                packets. The authorized values are :
                   noModify : no operation,
                   setToZero : the cause field is set to 'DTE
                        originated'.
                   setToZeroIfLowerThan128 : the cause field is
                        set to 'DTE originated' only if the bit 8
                        is 0 (i.e. if the bits 7 to 1 are those
                        included by the remote DTE).
                   modify : if the cause field is 'Invalid
                        facility request' or 'Local procedure
                        error' then it is changed to 'Network
                        congestion' else no operation.
                The default value is 'noModify'."
        ::= { fclX25CfaSignallingEntry 21 }


    fclX25CfaSigT11CallResponseTimer OBJECT-TYPE
        SYNTAX  INTEGER (10..2500)
        ACCESS  read-write
        STATUS  mandatory
        DESCRIPTION
                "The value of this object is the maximum time (in
                seconds) the equipment will wait for a response to
                a call request packet sent on the link. A clear
                packet is sent if there is no response after this
                time. The authorized values are '10..2500' by step
                of 10. The default value is '200'."
        ::= { fclX25CfaSignallingEntry 22 }


    fclX25CfaSigCallAcceptedFormat OBJECT-TYPE
        SYNTAX  INTEGER {
                noFacilitiesNoAddresses(3),
                facilitiesNoAddresses(2),
                facilitiesNotCheckedAddresses(4),
                facilitiesCheckedAddresses(1)
                }
        ACCESS  read-write
        STATUS  mandatory
        DESCRIPTION
                "The value of this object defines the format of an
                outgoing call connected packet. The authorized
                values are :
                   noFacilitiesNoAddresses : no facility length
                        and facility fields, calling and called
                        DTE address lengths set to 0,
                   facilitiesNoAddresses : facility length and
                        facility fields, calling and called DTE
                        address lengths set to 0,
                   facilitiesNoCheckedAdresses : facility length
                        and facility fields, calling and called
                        DTE address lengths different from 0,
                        addresses are not checked (???),
                   facilitiesCheckedAddresses : facility length
                        and facility fields, calling and called
                        DTE address lengths different from 0,
                        addresses are checked (???),
                The default value is 'noFacilitiesNoAddresses'."
        ::= { fclX25CfaSignallingEntry 25 }


    fclX25CfaSigClearFormat OBJECT-TYPE
        SYNTAX  INTEGER {
                noFacilitiesNoAddresses(3),
                facilitiesNoAddresses(2),
                facilitiesNotCheckedAddresses(4),
                facilitiesCheckedAddresses(1)
                }
        ACCESS  read-write
        STATUS  mandatory
        DESCRIPTION
                "The value of this object defines the format of an
                outgoing call connected packet. The authorized
                values are :
                   noFacilitiesNoAddresses : no facility length
                        and facility fields, calling and called
                        DTE address lengths set to 0,
                   facilitiesNoAddresses : facility length and
                        facility fields, calling and called DTE
                        address lengths set to 0,
                   facilitiesNoCheckedAdresses : facility length
                        and facility fields, calling and called
                        DTE address lengths different from 0,
                        addresses are not checked (???),
                   facilitiesCheckedAddresses : facility length
                        and facility fields, calling and called
                        DTE address lengths different from 0,
                        addresses are checked (???),
                The default value is 'noFacilitiesNoAddresses'."
        ::= { fclX25CfaSignallingEntry 26 }


    fclX25CfaServiceTable OBJECT-TYPE
        SYNTAX  SEQUENCE OF FclX25CfaServiceEntry
        ACCESS  not-accessible
        STATUS  mandatory
        DESCRIPTION
                "This table contains the services level parameters
                of X25 access configurations."
        ::= { fclX25ConfigAccess 40 }


    fclX25CfaServiceEntry OBJECT-TYPE
        SYNTAX  FclX25CfaServiceEntry
        ACCESS  not-accessible
        STATUS  mandatory
        DESCRIPTION
                "An entry of fclX25CfaServiceTable."
        INDEX   { fclX25CfaSerConfigId }
        ::= { fclX25CfaServiceTable 1 }


        FclX25CfaServiceEntry ::=
                SEQUENCE {
                    fclX25CfaSerConfigId
                        INTEGER,
                    fclX25CfaSerReliableVc
                        INTEGER,
                    fclX25CfaSerCharging
                        INTEGER,
                    fclX25CfaSerX29Reselection
                        INTEGER,
                    fclX25CfaSerRemoteExclusiveLink
                        INTEGER,
                    fclX25CfaSerStatLoadAndTraffic
                        INTEGER,
                    fclX25CfaSerStatSignalling
                        INTEGER,
                    fclX25CfaSerStatTotalizer
                        INTEGER,
                    fclX25CfaSerStatCompression
                        INTEGER,
                    fclX25CfaSerCompression
                        INTEGER,
                    fclX25CfaSerCompressNegotiation
                        INTEGER,
                    fclX25CfaSerCompressScrambling
                        INTEGER,
                    fclX25CfaSerCompressMultiPacketsTimer
                        INTEGER,
                    fclX25CfaSerCos
                        INTEGER,
                    fclX25CfaSerCir
                        INTEGER,
                    fclX25CfaSerMinCir
                        INTEGER,
                    fclX25CfaSerBe
                        INTEGER
                }


    fclX25CfaSerConfigId OBJECT-TYPE
        SYNTAX  INTEGER (0..199)
        ACCESS  read-only
        STATUS  mandatory
        DESCRIPTION
                "The value of this object identifies one and only
                one X25 access configuration. The possible values
                are : '0..199. If it is unused, the value of this
                parameter is '255'."
        ::= { fclX25CfaServiceEntry 1 }


    fclX25CfaSerReliableVc OBJECT-TYPE
        SYNTAX  INTEGER {
                off(1),
                clear(3),
                subscribe(2),
                check(4)
                }
        ACCESS  read-write
        STATUS  mandatory
        DESCRIPTION
                "The value of this object is used to enable the
                Reliable Virtual Circuit service. The authorized
                values are :
                   off : no RVC, the VCs are considered as normal
                        VCs, no particular processing,
                   clear : RVCs are not allowed for the
                        subscriber, each attempt to establish a
                        RVC provokes a clear of the connection,
                   subscribe : all calls transmitted by the
                        subscriber establish RVCs, it is also
                        possible to receive calls with RVC option,
                   check :
                     for a link to a subscriber : when a call with
                        RVC option is received, a RVC is
                        established
                     for a link to a network : the RVC option is
                        ignored when it is present in a call sent
                        by a local subscriber, the connection is
                        cleared when the RVC option is present in
                        a call sent by the network.
                The default value is 'off'."
        ::= { fclX25CfaServiceEntry 2 }


    fclX25CfaSerCharging OBJECT-TYPE
        SYNTAX  INTEGER {
                off(1),
                overall(2),
                detailed(3)
                }
        ACCESS  read-write
        STATUS  mandatory
        DESCRIPTION
                "The value of this object is used to enable the
                charging service. The authorized values are :
                   off : no charging,
                   overall : charging (a charging ticket is made
                        of informations from all the lines of the
                        equipment),
                   detailed : charging (a charging ticket is made
                        of informations from one virtual circuit),
                The default value is 'off'."
        ::= { fclX25CfaServiceEntry 3 }


    fclX25CfaSerX29Reselection OBJECT-TYPE
        SYNTAX  INTEGER {
                off(1),
                on(2)
                }
        ACCESS  read-write
        STATUS  mandatory
        DESCRIPTION
                "The value of this object indicates whether the
                subscriber connected to the link has subscribed to
                X29 reselection or not. The default value is 'off'."
        ::= { fclX25CfaServiceEntry 4 }


    fclX25CfaSerRemoteExclusiveLink OBJECT-TYPE
        SYNTAX  INTEGER {
                no(1),
                yes(2)
                }
        ACCESS  read-write
        STATUS  mandatory
        DESCRIPTION
                "The value of this object indicates whether this
                link is the only way to join the facing equipment
                (exclusive link = yes, the equipment answers to a
                call packet with a clear packet) or there is
                another way to join it (exclusive link = no, the
                equipment answers to a call packet with a 'call
                return' packet, to make the previous equipments
                search for another route). The default value is
                'off'."
        ::= { fclX25CfaServiceEntry 5 }


    fclX25CfaSerStatLoadAndTraffic OBJECT-TYPE
        SYNTAX  INTEGER {
                off(1),
                on(2)
                }
        ACCESS  read-write
        STATUS  mandatory
        DESCRIPTION
                "The value of this object indicates whether, for
                this link, the load and traffic informations
                recording of the statistics management function is
                enabled or not. The default value is 'off'."
        ::= { fclX25CfaServiceEntry 10 }


    fclX25CfaSerStatSignalling OBJECT-TYPE
        SYNTAX  INTEGER {
                off(1),
                on(2)
                }
        ACCESS  read-write
        STATUS  mandatory
        DESCRIPTION
                "The value of this object indicates whether, for
                this link, the signalling informations recording
                of the statistics management function is enabled
                or not. The default value is 'off'."
        ::= { fclX25CfaServiceEntry 11 }


    fclX25CfaSerStatTotalizer OBJECT-TYPE
        SYNTAX  INTEGER {
                off(1),
                on(2)
                }
        ACCESS  read-write
        STATUS  mandatory
        DESCRIPTION
                "The value of this object indicates whether, for
                this link, the frames counting informations
                recording of the statistics management function is
                enabled or not. The default value is 'off'."
        ::= { fclX25CfaServiceEntry 12 }


    fclX25CfaSerStatCompression OBJECT-TYPE
        SYNTAX  INTEGER {
                off(1),
                on(2)
                }
        ACCESS  read-write
        STATUS  mandatory
        DESCRIPTION
                "The value of this object indicates whether, for
                this link, the compression informations recording
                of the statistics management function is enabled
                or not. The default value is 'off'."
        ::= { fclX25CfaServiceEntry 13 }


    fclX25CfaSerCompression OBJECT-TYPE
        SYNTAX  INTEGER {
                off(1),
                networkToSubscriber(2),
                subscriberToNetwork(3),
                bothway(4)
                }
        ACCESS  read-write
        STATUS  mandatory
        DESCRIPTION
                "The value of this object indicates the compression
                enabling for each direction. The authorized values
                are :
                   off : no compression,
                   networkToSubscriber : compression of the flow
                        from the remote peer to the equipment,
                   subscriberToNetwork : compression of the flow
                        from the equipment to the remote peer,
                   bothway : compression of the two flows from and
                        to the equipment.
                The default value is 'off'."
        ::= { fclX25CfaServiceEntry 20 }


    fclX25CfaSerCompressNegotiation OBJECT-TYPE
        SYNTAX  INTEGER {
                off(1),
                onOptionalCompression(2),
                onMandatoryCompression(3)
                }
        ACCESS  read-write
        STATUS  mandatory
        DESCRIPTION
                "The value of this object indicates whether the
                compression facility is negociated or not and, if
                negociated, the optional/obligatory status. The
                authorized values are :
                   off' :no negociation,
                   onOptionalCompression : negociation but
                        compression is optional,
                   onMandatoryCompression : negociation and
                        compression is mandatory.
                The default value is 'off'."
        ::= { fclX25CfaServiceEntry 21 }


    fclX25CfaSerCompressScrambling OBJECT-TYPE
        SYNTAX  INTEGER {
                off(1),
                on(2)
                }
        ACCESS  read-write
        STATUS  mandatory
        DESCRIPTION
                "The value of this object indicates, when the
                compression is active, whether the scrambling is
                enabled or not. The default value is 'off'."
        ::= { fclX25CfaServiceEntry 22 }


    fclX25CfaSerCompressMultiPacketsTimer OBJECT-TYPE
        SYNTAX  INTEGER (0..1500)
        ACCESS  read-write
        STATUS  mandatory
        DESCRIPTION
                "The value of this object defines the maximum
                waiting time, in milliseconds by steps of 100
                milliseconds , which, if there is not another
                packet to compress, the packet of compressed
                packets is sent beyond (this permits to reduce the
                number of packets transmitted to the remote peer).
                The authorized values are '0..1500'. '0' means no
                packets grouping (i. e. : each packet is
                individually compressed and sent). The default
                value is '0'."
        ::= { fclX25CfaServiceEntry 23 }


    fclX25CfaSerCos OBJECT-TYPE
        SYNTAX  INTEGER {
                ubr(3),
                vbr(1)
                }
        ACCESS  read-write
        STATUS  mandatory
        DESCRIPTION
                "COS"
        ::= { fclX25CfaServiceEntry 30 }


    fclX25CfaSerCir OBJECT-TYPE
        SYNTAX  INTEGER (600..2048000)
        ACCESS  read-write
        STATUS  mandatory
        DESCRIPTION
                "Entrant CIR"
        ::= { fclX25CfaServiceEntry 31 }


    fclX25CfaSerMinCir OBJECT-TYPE
        SYNTAX  INTEGER (0..2048000)
        ACCESS  read-write
        STATUS  mandatory
        DESCRIPTION
                "Entrant CIR mini"
        ::= { fclX25CfaServiceEntry 32 }


    fclX25CfaSerBe OBJECT-TYPE
        SYNTAX  INTEGER (0..2048000)
        ACCESS  read-write
        STATUS  mandatory
        DESCRIPTION
                "Entrant BE"
        ::= { fclX25CfaServiceEntry 33 }


    fclX25CfaPackingAddresses OBJECT IDENTIFIER ::= { fclX25ConfigAccess 50 }


    fclX25CfaPackOutSubAddressCheck OBJECT-TYPE
        SYNTAX  INTEGER {
                off(1),
                on(2)
                }
        ACCESS  read-write
        STATUS  mandatory
        DESCRIPTION
                "The value of this object indicates whether the
                packing mechanism (see fclX25CfaPackingTable) is
                enabled for the outgoing call packets or not. The
                default value is 'on'."
        ::= { fclX25CfaPackingAddresses 1 }


    fclX25CfaPackOutSubAddressSize OBJECT-TYPE
        SYNTAX  INTEGER (1..4)
        ACCESS  read-write
        STATUS  mandatory
        DESCRIPTION
                "The value of this object defines the length of the
                substituted sub-address used by the packing
                mechanism (see fclX25CfaPackSubAddress). The
                authorized values are '1..4'. The default value is
                '2'."
        ::= { fclX25CfaPackingAddresses 2 }


    fclX25CfaPackPdnCallingSubAddress OBJECT-TYPE
        SYNTAX  INTEGER {
                pack(1),
                remove(2)
                }
        ACCESS  read-write
        STATUS  mandatory
        DESCRIPTION
                "The value of this object indicates, when using the
                packing mechanism, whether the calling address is
                packed or is removed (i.e. there is no calling
                sub-address). The default value is 'remove'."
        ::= { fclX25CfaPackingAddresses 3 }


    fclX25CfaPackingTable OBJECT-TYPE
        SYNTAX  SEQUENCE OF FclX25CfaPackingEntry
        ACCESS  not-accessible
        STATUS  mandatory
        DESCRIPTION
                "This table defines the association between the ZO
                SB part of the DNIC ZO SB address and the
                substituted sub-address (i.e. the 'packed ZO SB').
                This substitution is enabled on a link when
                fclX25CfaSigPdnIndicator is set to
                'pdnWithAddressTransmission'."
        ::= { fclX25CfaPackingAddresses 4 }


    fclX25CfaPackingEntry OBJECT-TYPE
        SYNTAX  FclX25CfaPackingEntry
        ACCESS  not-accessible
        STATUS  mandatory
        DESCRIPTION
                "An entry of fclX25CfaPackingTable."
        INDEX   { fclX25CfaPackPrivateZoSb }
        ::= { fclX25CfaPackingTable 1 }


        FclX25CfaPackingEntry ::=
                SEQUENCE {
                    fclX25CfaPackPrivateZoSb
                        OCTET STRING,
                    fclX25CfaPackStatus
                        INTEGER,
                    fclX25CfaPackSubAddress
                        OCTET STRING
                }


    fclX25CfaPackPrivateZoSb OBJECT-TYPE
        SYNTAX  OCTET STRING (SIZE(2))
        ACCESS  read-only
        STATUS  mandatory
        DESCRIPTION
                "The value of this object is the ZO SB part of the
                DNIC ZO SB address which is replaced by the
                sub-address defined in fclX25CfaPackSubAddress.
                The value may contain up to 4 digits (digits
                0..9). The value must be completed with 'F' digits
                for a total of 4 digits. The equipment
                configurator does not need final completion. The
                default value is 'FF FF' meaning 'empty value'
                (blank value on the equipment configurator)."
        ::= { fclX25CfaPackingEntry 1 }


    fclX25CfaPackStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25CfaPackingEntry 2 }


    fclX25CfaPackSubAddress OBJECT-TYPE
        SYNTAX  OCTET STRING (SIZE(2))
        ACCESS  read-write
        STATUS  mandatory
        DESCRIPTION
                "The value of this object is the substituted
                sub-address (i.e. the 'packed ZO SB') which
                replaces the ZO SB part of the DNIC ZO SB address
                defined in fclX25CfaPackPrivateZoSb. The value may
                contain up to 'fclX25CfaPackOutSubAddressSize'
                digits (digits 0..9). The value must be completed
                with 'F' digits for a total of 4 digits. The
                equipment configurator does not need final
                completion. The default value is 'FF FF' meaning
                'empty value' (blank value on the equipment
                configurator)."
        ::= { fclX25CfaPackingEntry 3 }


    fclX25CfaClosedUserGroupTable OBJECT-TYPE
        SYNTAX  SEQUENCE OF FclX25CfaClosedUserGroupEntry
        ACCESS  not-accessible
        STATUS  mandatory
        DESCRIPTION
                "This table defines the Closed User Groups to which
                belong the subscribers. This table is used on a
                link when fclX25CfaFacClosedUserGroup is set to
                'subscribe' or 'subscribeAndRemove'."
        ::= { fclX25ConfigAccess 51 }


    fclX25CfaClosedUserGroupEntry OBJECT-TYPE
        SYNTAX  FclX25CfaClosedUserGroupEntry
        ACCESS  not-accessible
        STATUS  mandatory
        DESCRIPTION
                "An entry of fclX25CfaClosedUserGroupTable."
        INDEX   { fclX25CfaCugLogPortId,
                  fclX25CfaCugClosedUserGroupId }
        ::= { fclX25CfaClosedUserGroupTable 1 }


        FclX25CfaClosedUserGroupEntry ::=
                SEQUENCE {
                    fclX25CfaCugLogPortId
                        INTEGER,
                    fclX25CfaCugClosedUserGroupId
                        INTEGER,
                    fclX25CfaCugStatus
                        INTEGER,
                    fclX25CfaCugChecking
                        INTEGER,
                    fclX25CfaCugClosedUserGroupExt
                        INTEGER
                }


    fclX25CfaCugLogPortId OBJECT-TYPE
        SYNTAX  INTEGER (0..181)
        ACCESS  read-only
        STATUS  mandatory
        DESCRIPTION
                "The value of this object identifies one and only
                one access logical port. There may up to 28 CUG
                for only one logical port. The possible values are
                : '0..131'. If it is unused, the value of this
                parameter is '255'. The default value is '255'."
        ::= { fclX25CfaClosedUserGroupEntry 1 }


    fclX25CfaCugClosedUserGroupId OBJECT-TYPE
        SYNTAX  INTEGER (0..99)
        ACCESS  read-only
        STATUS  mandatory
        DESCRIPTION
                "This value defines one CUG associated to the
                logical port defined in fclX25CfaCugLogPortId. The
                possible values are : '0..99. If it is unused, the
                value of this parameter is '255'. The default
                value is '255'."
        ::= { fclX25CfaClosedUserGroupEntry 2 }


    fclX25CfaCugStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25CfaClosedUserGroupEntry 3 }


    fclX25CfaCugChecking OBJECT-TYPE
        SYNTAX  INTEGER {
                onIncomingCall(2),
                onOutgoingCall(3),
                onIncomingCallAndOutgoingCall(1)
                }
        ACCESS  read-write
        STATUS  mandatory
        DESCRIPTION
                "The value of this object defines on which call the
                equipment checks this CUG. The default values is
                'onIncomingCallAndOutgoingCall'."
        ::= { fclX25CfaClosedUserGroupEntry 4 }


    fclX25CfaCugClosedUserGroupExt OBJECT-TYPE
        SYNTAX  INTEGER (0..99)
        ACCESS  read-write
        STATUS  mandatory
        DESCRIPTION
                "GFU externe"
        ::= { fclX25CfaClosedUserGroupEntry 5 }


    fclX25ConfigInterNode OBJECT IDENTIFIER ::= { fclX25Configurations 10 }


    fclX25ConfigInterNodeTable OBJECT-TYPE
        SYNTAX  SEQUENCE OF FclX25ConfigInterNodeEntry
        ACCESS  not-accessible
        STATUS  mandatory
        DESCRIPTION
                "This table contains the X25 inter-node
                configurations used by X25 inter-node links."
        ::= { fclX25ConfigInterNode 1 }


    fclX25ConfigInterNodeEntry OBJECT-TYPE
        SYNTAX  FclX25ConfigInterNodeEntry
        ACCESS  not-accessible
        STATUS  mandatory
        DESCRIPTION
                "An entry of fclX25ConfigInterNodeTable."
        INDEX   { fclX25CfnConfigId }
        ::= { fclX25ConfigInterNodeTable 1 }


        FclX25ConfigInterNodeEntry ::=
                SEQUENCE {
                    fclX25CfnConfigId
                        INTEGER,
                    fclX25CfnStatus
                        INTEGER,
                    fclX25CfnDescription
                        DisplayString,
                    fclX25CfnProfileId
                        INTEGER,
                    fclX25CfnModificationCount
                        INTEGER
                }


    fclX25CfnConfigId OBJECT-TYPE
        SYNTAX  INTEGER (0..199)
        ACCESS  read-only
        STATUS  mandatory
        DESCRIPTION
                "The value of this object identifies one and only
                one X25 inter-node configuration. This
                configuration may be referenced by
                fclX25InBRemX25ConfigId,
                fclX25PstnX25InterNodeConfigId,
                fclX25SlpX25InterNodeConfigId,
                fclX25SlpIsdnRemX25InterNodeConfigId,
                fclX25SlpPstnBackX25InterNodeConfigId,
                fclX25MlpX25InterNodeConfigId or
                fclFrPvcX25InterNodeConfigId.
                The possible values are : '0..199. If it is
                unused, the value of this parameter is '255'.
                The X25 inter-node configuration parameters are
                described in :
                   fclX25CfnaDataLinkNetworkTable : data link and
                        network levels,
                   fclX25CfnNegotiatedFacilityTable : facility
                        level,
                   fclX25CfnSignallingTable : signalling level,
                   fclX25CfnServiceTable : services level.
                When creating a new configuration each parameter
                takes its default value. Setting a profile allows
                the user to fill all the parameters with values
                pre-defined in this profile but each one may also
                be individually modified."
        ::= { fclX25ConfigInterNodeEntry 1 }


    fclX25CfnStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fclX25ConfigInterNodeEntry 2 }


    fclX25CfnDescription OBJECT-TYPE
        SYNTAX  DisplayString (SIZE(0..32))
        ACCESS  read-write
        STATUS  mandatory
        DESCRIPTION
                "The value of this object stores a text description
                of the X25 inter-node configuration elaborated by
                the user. This description may contains from 0 to
                32 characters. The default value is 'DTE
                inter-node'."
        ::= { fclX25ConfigInterNodeEntry 3 }


    fclX25CfnProfileId OBJECT-TYPE
        SYNTAX  INTEGER (0..199)
        ACCESS  read-write
        STATUS  mandatory
        DESCRIPTION
                "The value of this object is the profile number
                used to automatically valorize all the X25
                parameters in an entry of the four tables which
                composes X25 inter-node configurations (see
                fclX25CfnConfigId).

                The possible values are :
                   04 DTE inter-node,
                   05 DCE inter-node,
                   20 DTE PSTN back-up auto modem,
                   21 DCE PSTN back-up auto modem,
                   24 Inter-node (TRANSPAC),
                   24 Inter-node (TRANSPAC),
                   40 DTE PSTN back-up V.25bis modem,
                   1 DCE PSTN back-up V.25bis modem,
                   74 DTE inter-node X.75 physical,
                   75 DCE inter-node X.75 physical,
                   86 DTE FR network (p transac),
                   87 DCE FR network (p transac),
                   88 DTE FR Network (no priority),
                   89 DCE FR Network (no priority),

                If it is unused, the value of this parameter is
                '255'.
                The default value is '4' (meaning that default
                values of X25 parameters are those pre-defined in
                profile number 04)."
        ::= { fclX25ConfigInterNodeEntry 4 }


    fclX25CfnModificationCount OBJECT-TYPE
        SYNTAX  INTEGER (0..255)
        ACCESS  read-only
        STATUS  mandatory
        DESCRIPTION
                "The value of this object indicates how many X25
                parameters have not the value defined in the
                profile specified by fclX25CfnProfileId (i.e how
                many individual modifications)."
        ::= { fclX25ConfigInterNodeEntry 5 }


    fclX25CfnDataLinkNetworkTable OBJECT-TYPE
        SYNTAX  SEQUENCE OF FclX25CfnDataLinkNetworkEntry
        ACCESS  not-accessible
        STATUS  mandatory
        DESCRIPTION
                "This table contains the data link and network
                levels parameters of X25 inter-node configurations."
        ::= { fclX25ConfigInterNode 10 }


    fclX25CfnDataLinkNetworkEntry OBJECT-TYPE
        SYNTAX  FclX25CfnDataLinkNetworkEntry
        ACCESS  not-accessible
        STATUS  mandatory
        DESCRIPTION
                "An entry of fclX25CfnDataLinkNetworkTable."
        INDEX   { fclX25CfnDlnConfigId }
        ::= { fclX25CfnDataLinkNetworkTable 1 }


        FclX25CfnDataLinkNetworkEntry ::=
                SEQUENCE {
                    fclX25CfnDlnConfigId
                        INTEGER,
                    fclX25CfnDlnStationType
                        INTEGER,
                    fclX25CfnDlnN2RetryCount
                        INTEGER,
                    fclX25CfnDlnT1AcknowledgeTimer
                        INTEGER,
                    fclX25CfnDlnT2AcknowledgeDelayTimer
                        INTEGER,
                    fclX25CfnDlnKWindowSize
                        INTEGER,
                    fclX25CfnDlnEachPacketAcknowledgement
                        INTEGER,
                    fclX25CfnDlnLowestIncomingChannel
                        INTEGER,
                    fclX25CfnDlnIncomingChannelCount
                        INTEGER,
                    fclX25CfnDlnLowestTwoWayChannel
                        INTEGER,
                    fclX25CfnDlnTwoWayChannelCount
                        INTEGER,
                    fclX25CfnDlnLowestOutgoingChannel
                        INTEGER,
                    fclX25CfnDlnOutgoingChannelCount
                        INTEGER,
                    fclX25CfnDlnOutgoingChannelNumbering
                        INTEGER,
                    fclX25CfnDlnDBitModification
                        INTEGER
                }


    fclX25CfnDlnConfigId OBJECT-TYPE
        SYNTAX  INTEGER (0..199)
        ACCESS  read-only
        STATUS  mandatory
        DESCRIPTION
                "The value of this object identifies one and only
                one X25 inter-node configuration. The possible
                values are : '0..199. If it is unused, the value
                of this parameter is '255'."
        ::= { fclX25CfnDataLinkNetworkEntry 1 }


    fclX25CfnDlnStationType OBJECT-TYPE
        SYNTAX  INTEGER {
                dte(1),
                dce(2)
                }
        ACCESS  read-write
        STATUS  mandatory
        DESCRIPTION
                "The value of this object defines the type of the
                interface at the data link layer (and not at the
                physical layer which is defined in fcfLineType).
                The equipment can acts as a DTE (Data Terminal
                Equipment) or as a DCE (Data Circuit-terminating
                Equipment). The default value is 'dce'."
        ::= { fclX25CfnDataLinkNetworkEntry 2 }


    fclX25CfnDlnN2RetryCount OBJECT-TYPE
        SYNTAX  INTEGER (2..250)
        ACCESS  read-write
        STATUS  mandatory
        DESCRIPTION
                "The value of this object indicates the maximum
                number (N2) of attempts made by the equipment to
                complete the successfull transmission of a frame.
                The authorized values are '2..250'. The default
                value is '10'."
        ::= { fclX25CfnDataLinkNetworkEntry 5 }


    fclX25CfnDlnT1AcknowledgeTimer OBJECT-TYPE
        SYNTAX  INTEGER (200..25000)
        ACCESS  read-write
        STATUS  mandatory
        DESCRIPTION
                "The value of this object indicates the period
                (T1), in milliseconds, at the end of which
                retransmission of a frame may be initiated. The
                authorized values are '200..25000'. The default
                value is '800'."
        ::= { fclX25CfnDataLinkNetworkEntry 6 }


    fclX25CfnDlnT2AcknowledgeDelayTimer OBJECT-TYPE
        SYNTAX  INTEGER (100..12700)
        ACCESS  read-write
        STATUS  mandatory
        DESCRIPTION
                "The value of this object indicates the amount of
                time available (T2), in milliseconds, before the
                acknowledging frame must be initiated. This
                parameter must be smaller than T1. The authorized
                values are '100..12700'. The default value is
                '400'."
        ::= { fclX25CfnDataLinkNetworkEntry 7 }


    fclX25CfnDlnKWindowSize OBJECT-TYPE
        SYNTAX  INTEGER (1..127)
        ACCESS  read-write
        STATUS  mandatory
        DESCRIPTION
                "The value of this object indicates the maximum
                number (K) of sequentially numbered I frames that
                the equipment may have outstanding (i.e..
                unacknowledged) at any given time. The authorized
                values are '1..127'. The default value is '7'."
        ::= { fclX25CfnDataLinkNetworkEntry 8 }


    fclX25CfnDlnEachPacketAcknowledgement OBJECT-TYPE
        SYNTAX  INTEGER {
                off(1),
                on(2)
                }
        ACCESS  read-write
        STATUS  mandatory
        DESCRIPTION
                "The value of this object indicates whether each
                frame is acknowledged or not. The default value is
                'off'."
        ::= { fclX25CfnDataLinkNetworkEntry 9 }


    fclX25CfnDlnLowestIncomingChannel OBJECT-TYPE
        SYNTAX  INTEGER (0..4095)
        ACCESS  read-write
        STATUS  mandatory
        DESCRIPTION
                "The value of this object is the Lowest Incoming
                one-way logical Channel (LIC).The authorized
                values are '0..4095'. The default value is '0'."
        ::= { fclX25CfnDataLinkNetworkEntry 10 }


    fclX25CfnDlnIncomingChannelCount OBJECT-TYPE
        SYNTAX  INTEGER (0..4096)
        ACCESS  read-write
        STATUS  mandatory
        DESCRIPTION
                "The value of this object is the Number of Incoming
                one-way logical Channels (NIC). So the Highest
                Incoming one-way logical Channel (HIC) is : HIC =
                LIC + NIC - 1. The authorized values are
                '0..4096'. The default value is '0'."
        ::= { fclX25CfnDataLinkNetworkEntry 11 }


    fclX25CfnDlnLowestTwoWayChannel OBJECT-TYPE
        SYNTAX  INTEGER (0..4095)
        ACCESS  read-write
        STATUS  mandatory
        DESCRIPTION
                "The value of this object is the Lowest Two-way
                logical Channel (LTC). The authorized values are
                '0..4095'. The default value is '0'."
        ::= { fclX25CfnDataLinkNetworkEntry 15 }


    fclX25CfnDlnTwoWayChannelCount OBJECT-TYPE
        SYNTAX  INTEGER (0..4096)
        ACCESS  read-write
        STATUS  mandatory
        DESCRIPTION
                "The value of this object is the Number of Two-way
                logical Channels. So the Highest Two-way logical
                Channel (HTC) is : HTC = LTC + NTC - 1. The
                authorized values are '0..4096'. The default value
                is '20'."
        ::= { fclX25CfnDataLinkNetworkEntry 16 }


    fclX25CfnDlnLowestOutgoingChannel OBJECT-TYPE
        SYNTAX  INTEGER (0..4095)
        ACCESS  read-write
        STATUS  mandatory
        DESCRIPTION
                "The value of this object is the Lowest Outgoing
                one-way logical Channel (LOC). The authorized
                values are '0..4095'. The default value is '20'."
        ::= { fclX25CfnDataLinkNetworkEntry 17 }


    fclX25CfnDlnOutgoingChannelCount OBJECT-TYPE
        SYNTAX  INTEGER (0..4096)
        ACCESS  read-write
        STATUS  mandatory
        DESCRIPTION
                "The value of this object is the Number of Outgoing
                one-way logical Channels (NOC). So the Highest
                Outgoing one-way logical Channel (HOC) is : HOC =
                LOC + NOC - 1. The authorized values are
                '0..4096'. The default value is '0'."
        ::= { fclX25CfnDataLinkNetworkEntry 18 }


    fclX25CfnDlnOutgoingChannelNumbering OBJECT-TYPE
        SYNTAX  INTEGER {
                decremental(1),
                incremental(2)
                }
        ACCESS  read-write
        STATUS  mandatory
        DESCRIPTION
                "The value of this object indicates whether the
                equipment searches for a logical channel from the
                lowest one to the highest one (incremental order)
                or from the highest one to the lowest one
                (decremental order). The default value is
                'decremental'."
        ::= { fclX25CfnDataLinkNetworkEntry 19 }


    fclX25CfnDlnDBitModification OBJECT-TYPE
        SYNTAX  INTEGER {
                off(1),
                clear(2),
                on(3)
                }
        ACCESS  read-write
        STATUS  mandatory
        DESCRIPTION
                "The value of this object indicates how the
                equipment manages the D bit (Delivery Confirmation
                Bit). When it receives a call from a DTE wishing
                to receive an end-to-end acknowledgement of
                delivery the equipment may :
                   ignore this D bit procedure ('off' value), ???
                   indicate clearing ('clear' value),
                   ??? ('on' value),
                The default value is 'off'."
        ::= { fclX25CfnDataLinkNetworkEntry 30 }


    fclX25CfnNegotiatedFacilityTable OBJECT-TYPE
        SYNTAX  SEQUENCE OF FclX25CfnNegotiatedFacilityEntry
        ACCESS  not-accessible
        STATUS  mandatory
        DESCRIPTION
                "This table contains the facility level parameters
                of X25 inter-node configurations."
        ::= { fclX25ConfigInterNode 11 }


    fclX25CfnNegotiatedFacilityEntry OBJECT-TYPE
        SYNTAX  FclX25CfnNegotiatedFacilityEntry
        ACCESS  not-accessible
        STATUS  mandatory
        DESCRIPTION
                "An entry of fclX25CfnNegotiatedFacilityTable."
        INDEX   { fclX25CfnNegConfigId }
        ::= { fclX25CfnNegotiatedFacilityTable 1 }


        FclX25CfnNegotiatedFacilityEntry ::=
                SEQUENCE {
                    fclX25CfnNegConfigId
                        INTEGER,
                    fclX25CfnNegOutputFastSelect
                        INTEGER,
                    fclX25CfnNegInputFastSelect
                        INTEGER,
                    fclX25CfnNegThroughputClass
                        INTEGER,
                    fclX25CfnNegDefOutThroughputClass
                        INTEGER,
                    fclX25CfnNegDefInThroughputClass
                        INTEGER,
                    fclX25CfnNegMaxOutThroughputClass
                        INTEGER,
                    fclX25CfnNegMaxInThroughputClass
                        INTEGER,
                    fclX25CfnNegPacketSize
                        INTEGER,
                    fclX25CfnNegDefOutPacketSize
                        INTEGER,
                    fclX25CfnNegDefInPacketSize
                        INTEGER,
                    fclX25CfnNegMaxOutPacketSize
                        INTEGER,
                    fclX25CfnNegMaxInPacketSize
                        INTEGER,
                    fclX25CfnNegMinOutPacketSize
                        INTEGER,
                    fclX25CfnNegMinInPacketSize
                        INTEGER,
                    fclX25CfnNegWindowSize
                        INTEGER,
                    fclX25CfnNegDefOutWindowSize
                        INTEGER,
                    fclX25CfnNegDefInWindowSize
                        INTEGER,
                    fclX25CfnNegMaxOutWindowSize
                        INTEGER,
                    fclX25CfnNegMaxInWindowSize
                        INTEGER
                }


    fclX25CfnNegConfigId OBJECT-TYPE
        SYNTAX  INTEGER (0..199)
        ACCESS  read-only
        STATUS  mandatory
        DESCRIPTION
                "The value of this object identifies one and only
                one X25 inter-node configuration. The possible
                values are : '0..199. If it is unused, the value
                of this parameter is '255'."
        ::= { fclX25CfnNegotiatedFacilityEntry 1 }


    fclX25CfnNegOutputFastSelect OBJECT-TYPE
        SYNTAX  INTEGER {
                noCheck(3),
                clear(1),
                subscribe(2)
                }
        ACCESS  read-write
        STATUS  mandatory
        DESCRIPTION
                "The value of this object specifies the behaviour
                of the equipment with respect to the fast select
                facility in outgoing call. The authorized values
                are 'noCheck' (no checking), 'clear' (clearing),
                'subscribe'. The default value is 'noCheck'."
        ::= { fclX25CfnNegotiatedFacilityEntry 2 }


    fclX25CfnNegInputFastSelect OBJECT-TYPE
        SYNTAX  INTEGER {
                subscribe(2),
                longUserData(4)
                }
        ACCESS  read-write
        STATUS  mandatory
        DESCRIPTION
                "The value of this object is the maximum size of
                the call user data field in a received call
                request packet not containing the fast select
                facility. The authorized values are 'subscribe'
                (up to 16 bytes) or 'longUserData' (up to 128
                bytes). The default value is 'subscribe'."
        ::= { fclX25CfnNegotiatedFacilityEntry 3 }


    fclX25CfnNegThroughputClass OBJECT-TYPE
        SYNTAX  INTEGER {
                clear(1),
                subscribe(2)
                }
        ACCESS  read-write
        STATUS  mandatory
        DESCRIPTION
                "The value of this object indicates whether the
                subscriber connected to the link has subscribed to
                throughput class negociation facility or not. The
                authorized values are 'clear' (not subscriber) or
                'subscribe'. The default value is 'subscribe'."
        ::= { fclX25CfnNegotiatedFacilityEntry 10 }


    fclX25CfnNegDefOutThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the default
                throughput class in transmit direction (equipment
                to remote peer). The default value is 9600 bits
                per second."
        ::= { fclX25CfnNegotiatedFacilityEntry 11 }


    fclX25CfnNegDefInThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the default
                throughput class in receive direction (remote peer
                to equipment). The default value is 9600 bits per
                second."
        ::= { fclX25CfnNegotiatedFacilityEntry 12 }


    fclX25CfnNegMaxOutThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the maximum
                throughput class in transmit direction (equipment
                to remote peer). The default value is 9600 bits
                per second."
        ::= { fclX25CfnNegotiatedFacilityEntry 13 }


    fclX25CfnNegMaxInThroughputClass OBJECT-TYPE
        SYNTAX  INTEGER {
                t75(3),
                t150(4),
                t300(5),
                t600(6),
                t1200(7),
                t2400(8),
                t4800(9),
                t9600(10),
                t19200(11),
                t48000(12),
                t64000(13),
                t128000(14),
                t192000(15)
                }
        ACCESS  read-write
        STATUS  mandatory
        DESCRIPTION
                "The value of this object indicates the maximum
                throughput class in receive direction (equipment
                to remote peer). The default value is 9600 bits
                per second."
        ::= { fclX25CfnNegotiatedFacilityEntry 14 }


    fclX25CfnNegPacketSize OBJECT-TYPE
        SYNTAX  INTEGER {
                clear(1),
                subscribe(2)
                }
        ACCESS  read-write
        STATUS  mandatory
        DESCRIPTION
                "The value of this object indicates whether the
                subscriber connected to the link has subscribed to
                packet size negociation facility or not. The
                authorized values are 'clear' (not subscriber) or
                'subscribe'. The default value is 'subscribe'."
        ::= { fclX25CfnNegotiatedFacilityEntry 20 }


    fclX25CfnNegDefOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the default
                packet size in transmit direction (equipment to
                remote peer). The default value is 128 octets."
        ::= { fclX25CfnNegotiatedFacilityEntry 21 }


    fclX25CfnNegDefInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the default
                packet size in receive direction (remote peer to
                equipment). The default value is 128 octets."
        ::= { fclX25CfnNegotiatedFacilityEntry 22 }


    fclX25CfnNegMaxOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the maximum
                packet size in transmit direction (equipment to
                remote peer). The default value is 256 octets."
        ::= { fclX25CfnNegotiatedFacilityEntry 23 }


    fclX25CfnNegMaxInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the maximum
                packet size in receive direction (remote peer to
                equipment). The default value is 256 octets."
        ::= { fclX25CfnNegotiatedFacilityEntry 24 }


    fclX25CfnNegMinOutPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the minimum
                packet size in transmit direction (equipment to
                remote peer). The default value is 16 octets."
        ::= { fclX25CfnNegotiatedFacilityEntry 25 }


    fclX25CfnNegMinInPacketSize OBJECT-TYPE
        SYNTAX  INTEGER {
                s16(4),
                s32(5),
                s64(6),
                s128(7),
                s256(8),
                s512(9),
                s1024(10),
                s2048(11),
                s4096(12),
                s8192(13)
                }
        ACCESS  read-write
        STATUS  mandatory
        DESCRIPTION
                "The value of this object indicates the minimum
                packet size in receive direction (remote peer to
                equipment). The default value is 16 octets."
        ::= { fclX25CfnNegotiatedFacilityEntry 26 }


    fclX25CfnNegWindowSize OBJECT-TYPE
        SYNTAX  INTEGER {
                clear(1),
                subscribe(2)
                }
        ACCESS  read-write
        STATUS  mandatory
        DESCRIPTION
                "The value of this object indicates whether the
                subscriber connected to the link has subscribed to
                the negociation of the transmit window size
                facility or not. The authorized values are 'clear'
                (not subscriber) or 'subscribe'. The default value
                is 'subscribe'."
        ::= { fclX25CfnNegotiatedFacilityEntry 30 }


    fclX25CfnNegDefOutWindowSize OBJECT-TYPE
        SYNTAX  INTEGER (1..7)
        ACCESS  read-write
        STATUS  mandatory
        DESCRIPTION
                "The value of this object indicates the default
                window size in transmit direction (equipment to
                remote peer). The authorized values are '1..7'.
                The default value is '3'."
        ::= { fclX25CfnNegotiatedFacilityEntry 31 }


    fclX25CfnNegDefInWindowSize OBJECT-TYPE
        SYNTAX  INTEGER (1..7)
        ACCESS  read-write
        STATUS  mandatory
        DESCRIPTION
                "The value of this object indicates the default
                window size in receive direction (remote peer to
                equipment). The authorized values are '1..7'. The
                default value is '3'."
        ::= { fclX25CfnNegotiatedFacilityEntry 32 }


    fclX25CfnNegMaxOutWindowSize OBJECT-TYPE
        SYNTAX  INTEGER (1..7)
        ACCESS  read-write
        STATUS  mandatory
        DESCRIPTION
                "The value of this object indicates the maximum
                window size in transmit direction (equipment to
                remote peer). The authorized values are '1..7'.
                The default value is '4'."
        ::= { fclX25CfnNegotiatedFacilityEntry 33 }


    fclX25CfnNegMaxInWindowSize OBJECT-TYPE
        SYNTAX  INTEGER (1..7)
        ACCESS  read-write
        STATUS  mandatory
        DESCRIPTION
                "The value of this object indicates the maximum
                window size in receive direction (remote peer to
                equipment). The authorized values are '1..7'. The
                default value is '4'."
        ::= { fclX25CfnNegotiatedFacilityEntry 34 }


    fclX25CfnSignallingTable OBJECT-TYPE
        SYNTAX  SEQUENCE OF FclX25CfnSignallingEntry
        ACCESS  not-accessible
        STATUS  mandatory
        DESCRIPTION
                "This table contains the signalling level
                parameters of X25 inter-node configurations."
        ::= { fclX25ConfigInterNode 30 }


    fclX25CfnSignallingEntry OBJECT-TYPE
        SYNTAX  FclX25CfnSignallingEntry
        ACCESS  not-accessible
        STATUS  mandatory
        DESCRIPTION
                "An entry of fclX25CfnSignallingTable."
        INDEX   { fclX25CfnSigConfigId }
        ::= { fclX25CfnSignallingTable 1 }


        FclX25CfnSignallingEntry ::=
                SEQUENCE {
                    fclX25CfnSigConfigId
                        INTEGER,
                    fclX25CfnSigSubAddressTransmission
                        INTEGER,
                    fclX25CfnSigConversionAimedPoint
                        INTEGER,
                    fclX25CfnSigConversionIncomingCall
                        INTEGER,
                    fclX25CfnSigConversionOutgoingCall
                        INTEGER,
                    fclX25CfnSigConversionAddressCheck
                        INTEGER,
                    fclX25CfnSigConvMultiCalledAddrInCall
                        INTEGER,
                    fclX25CfnSigConvMultiCallingAddrInCall
                        INTEGER,
                    fclX25CfnSigConvMultiCalledAddrOutCall
                        INTEGER,
                    fclX25CfnSigConvMultiCallingAddrOutCall
                        INTEGER,
                    fclX25CfnSigT11CallResponseTimer
                        INTEGER,
                    fclX25CfnSigCallAcceptedFormat
                        INTEGER
                }


    fclX25CfnSigConfigId OBJECT-TYPE
        SYNTAX  INTEGER (0..199)
        ACCESS  read-only
        STATUS  mandatory
        DESCRIPTION
                "The value of this object identifies one and only
                one X25 inter-node configuration. The possible
                values are : '0..199. If it is unused, the value
                of this parameter is '255'."
        ::= { fclX25CfnSignallingEntry 1 }


    fclX25CfnSigSubAddressTransmission OBJECT-TYPE
        SYNTAX  INTEGER {
                off(1),
                on(2)
                }
        ACCESS  read-write
        STATUS  mandatory
        DESCRIPTION
                "The value of this object indicates whether the
                sub-address of the called address field of the
                call request packet received on a PDNL (Public
                Data Network Link) is retransmitted on the
                outgoing line or not. The default value is 'off'."
        ::= { fclX25CfnSignallingEntry 4 }


    fclX25CfnSigConversionAimedPoint OBJECT-TYPE
        SYNTAX  INTEGER {
                off(1),
                on(2)
                }
        ACCESS  read-write
        STATUS  mandatory
        DESCRIPTION
                "The value of this object indicates whether the
                'aimed point' address conversion is enabled or
                not. This conversion consists in making the
                routing process work not with the called address
                from the call packet but with a substituted
                address according to the address conversion table
                (see fcwAddrConvIncomingCallTable). Therefore this
                reduces the number of entries of the routing
                tables if several called addresses are converted
                to same 'aimed point' address. The default value
                is 'off'."
        ::= { fclX25CfnSignallingEntry 10 }


    fclX25CfnSigConversionIncomingCall OBJECT-TYPE
        SYNTAX  INTEGER {
                off(1),
                callingAddress(2),
                calledAddress(3),
                callingAddressAndCalledAddress(4)
                }
        ACCESS  read-write
        STATUS  mandatory
        DESCRIPTION
                "The value of this object indicates which address
                field are converted on an incoming call. The
                authorized values are :
                   off : no address field conversion,
                   callingAddress : conversion of the calling
                        address field according to the contains of
                        fcwAddrConvIncomingCallTable,
                   calledAddress : conversion of the called
                        address field according to the contains of
                        fcwAddrConvIncomingCallTable,
                   callingAddressAndCalledAddress : conversion of
                        the calling and called address fields
                        according to the contains of
                        fcwAddrConvIncomingCallTable.
                The default value is 'off'."
        ::= { fclX25CfnSignallingEntry 11 }


    fclX25CfnSigConversionOutgoingCall OBJECT-TYPE
        SYNTAX  INTEGER {
                off(1),
                callingAddress(2),
                calledAddress(3),
                callingAddressAndCalledAddress(4)
                }
        ACCESS  read-write
        STATUS  mandatory
        DESCRIPTION
                "The value of this object indicates which address
                field are converted on an outgoing call. The
                authorized values are :
                   off : no address field conversion,
                   callingAddress : conversion of the calling
                        address field according to the contains of
                        fcwAddrConvOutgoingCallTable,
                   calledAddress : conversion of the called
                        address field according to the contains of
                        fcwAddrConvOutgoingCallTable,
                   callingAddressAndCalledAddress : conversion of
                        the calling and called address fields
                        according to the contains of
                        fcwAddrConvOutgoingCallTable.
                The default value is 'off'."
        ::= { fclX25CfnSignallingEntry 12 }


    fclX25CfnSigConversionAddressCheck OBJECT-TYPE
        SYNTAX  INTEGER {
                off(1),
                onIncomingCall(2),
                onOutgoingCall(3),
                onIncomingCallAndOutgoingCall(4)
                }
        ACCESS  read-write
        STATUS  mandatory
        DESCRIPTION
                "The value of this object indicates the behaviour
                of the equipment when a requested address
                conversion can not be made because the address is
                not found in the address conversion tables
                (fcwAddrConvIncomingCallTable or
                fcwAddrConvOutgoingCallTable). In this case the
                call will be cleared when 'checking' is enabled.
                The authorized values are :
                   off : no checking,
                   onIncomingCall : checking on incoming calls,
                   onOutgoingCall : checking on outgoing calls,
                   onIcomingCallAndOutgoingCall : checking on
                        incoming and outgoing calls.
                   The default value is 'off'."
        ::= { fclX25CfnSignallingEntry 13 }


    fclX25CfnSigConvMultiCalledAddrInCall OBJECT-TYPE
        SYNTAX  INTEGER (1..99)
        ACCESS  read-write
        STATUS  mandatory
        DESCRIPTION
                "Numero d'identification pour conversion d'adresse
                d'appele multi-criteres en entree"
        ::= { fclX25CfnSignallingEntry 14 }


    fclX25CfnSigConvMultiCallingAddrInCall OBJECT-TYPE
        SYNTAX  INTEGER (1..99)
        ACCESS  read-write
        STATUS  mandatory
        DESCRIPTION
                "Numero d'identification pour conversion d'adresse
                d'appelant multi-criteres en entree"
        ::= { fclX25CfnSignallingEntry 15 }


    fclX25CfnSigConvMultiCalledAddrOutCall OBJECT-TYPE
        SYNTAX  INTEGER (1..99)
        ACCESS  read-write
        STATUS  mandatory
        DESCRIPTION
                "Numero d'identification pour conversion d'adresse
                d'appele multi-criteres en sortie"
        ::= { fclX25CfnSignallingEntry 16 }


    fclX25CfnSigConvMultiCallingAddrOutCall OBJECT-TYPE
        SYNTAX  INTEGER (1..99)
        ACCESS  read-write
        STATUS  mandatory
        DESCRIPTION
                "Numero d'identification pour conversion d'adresse
                d'appelant multi-criteres en sortie"
        ::= { fclX25CfnSignallingEntry 17 }


    fclX25CfnSigT11CallResponseTimer OBJECT-TYPE
        SYNTAX  INTEGER (10..2500)
        ACCESS  read-write
        STATUS  mandatory
        DESCRIPTION
                "The value of this object is the maximum time (in
                seconds) the equipment will wait for a response to
                a call request packet sent on the link. A clear
                packet is sent if there is no response after this
                time. The authorized values are '10..2500' by step
                of 10. The default value is '200'."
        ::= { fclX25CfnSignallingEntry 22 }


    fclX25CfnSigCallAcceptedFormat OBJECT-TYPE
        SYNTAX  INTEGER {
                noFacilitiesNoAddresses(3),
                facilitiesNoAddresses(2),
                facilitiesNotCheckedAddresses(4),
                facilitiesCheckedAddresses(1)
                }
        ACCESS  read-write
        STATUS  mandatory
        DESCRIPTION
                "The value of this object defines the format of an
                outgoing call connected packet. The authorized
                values are :
                   noFacilitiesNoAddresses : no facility length
                        and facility fields, calling and called
                        DTE address lengths set to 0,
                   facilitiesNoAddresses : facility length and
                        facility fields, calling and called DTE
                        address lengths set to 0,
                   facilitiesNoCheckedAdresses : facility length
                        and facility fields, calling and called
                        DTE address lengths different from 0,
                        addresses are not checked (???),
                   facilitiesCheckedAddresses : facility length
                        and facility fields, calling and called
                        DTE address lengths different from 0,
                        addresses are checked (???),
                The default value is 'noFacilitiesNoAddresses'."
        ::= { fclX25CfnSignallingEntry 25 }


    fclX25CfnServiceTable OBJECT-TYPE
        SYNTAX  SEQUENCE OF FclX25CfnServiceEntry
        ACCESS  not-accessible
        STATUS  mandatory
        DESCRIPTION
                "This table contains the services level parameters
                of X25 inter-node configurations."
        ::= { fclX25ConfigInterNode 40 }


    fclX25CfnServiceEntry OBJECT-TYPE
        SYNTAX  FclX25CfnServiceEntry
        ACCESS  not-accessible
        STATUS  mandatory
        DESCRIPTION
                "An entry of fclX25CfnServiceTable."
        INDEX   { fclX25CfnSerConfigId }
        ::= { fclX25CfnServiceTable 1 }


        FclX25CfnServiceEntry ::=
                SEQUENCE {
                    fclX25CfnSerConfigId
                        INTEGER,
                    fclX25CfnSerReliableVc
                        INTEGER,
                    fclX25CfnSerCharging
                        INTEGER,
                    fclX25CfnSerX29Reselection
                        INTEGER,
                    fclX25CfnSerRemoteExclusiveLink
                        INTEGER,
                    fclX25CfnSerCallReturnTransmission
                        INTEGER,
                    fclX25CfnSerStatLoadAndTraffic
                        INTEGER,
                    fclX25CfnSerStatSignalling
                        INTEGER,
                    fclX25CfnSerStatTotalizer
                        INTEGER,
                    fclX25CfnSerStatCompression
                        INTEGER
                }


    fclX25CfnSerConfigId OBJECT-TYPE
        SYNTAX  INTEGER (0..199)
        ACCESS  read-only
        STATUS  mandatory
        DESCRIPTION
                "The value of this object identifies one and only
                one X25 inter-node configuration. The possible
                values are : '0..199. If it is unused, the value
                of this parameter is '255'."
        ::= { fclX25CfnServiceEntry 1 }


    fclX25CfnSerReliableVc OBJECT-TYPE
        SYNTAX  INTEGER {
                off(1),
                clear(3),
                subscribe(2),
                check(4)
                }
        ACCESS  read-write
        STATUS  mandatory
        DESCRIPTION
                "The value of this object is used to enable the
                Reliable Virtual Circuit service. The authorized
                values are :
                   off : no RVC, the VCs are considered as normal
                        VCs, no particular processing,
                   clear : RVCs are not allowed for the
                        subscriber, each attempt to establish a
                        RVC provokes a clear of the connection,
                   subscribe : all calls transmitted by the
                        subscriber establish RVCs, it is also
                        possible to receive calls with RVC option,
                   check :
                     for a link to a subscriber : when a call with
                        RVC option is received, a RVC is
                        established
                     for a link to a network : the RVC option is
                        ignored when it is present in a call sent
                        by a local subscriber, the connection is
                        cleared when the RVC option is present in
                        a call sent by the network.
                The default value is 'off'."
        ::= { fclX25CfnServiceEntry 2 }


    fclX25CfnSerCharging OBJECT-TYPE
        SYNTAX  INTEGER {
                off(1),
                overall(2),
                detailed(3)
                }
        ACCESS  read-write
        STATUS  mandatory
        DESCRIPTION
                "The value of this object is used to enable the
                charging service. The authorized values are :
                   off : no charging,
                   overall : charging (a charging ticket is made
                        of informations from all the lines of the
                        equipment),
                   detailed : charging (a charging ticket is made
                        of informations from one virtual circuit),
                The default value is 'off'."
        ::= { fclX25CfnServiceEntry 3 }


    fclX25CfnSerX29Reselection OBJECT-TYPE
        SYNTAX  INTEGER {
                off(1),
                on(2)
                }
        ACCESS  read-write
        STATUS  mandatory
        DESCRIPTION
                "The value of this object indicates whether the
                subscriber connected to the link has subscribed to
                X29 reselection or not. The default value is 'off'."
        ::= { fclX25CfnServiceEntry 4 }


    fclX25CfnSerRemoteExclusiveLink OBJECT-TYPE
        SYNTAX  INTEGER {
                no(1),
                yes(2)
                }
        ACCESS  read-write
        STATUS  mandatory
        DESCRIPTION
                "The value of this object indicates whether this
                link is the only way to join the facing equipment
                (exclusive link = yes, the equipment answers to a
                call packet with a clear packet) or there is
                another way to join it (exclusive link = no, the
                equipment answers to a call packet with a 'call
                return' packet, to make the previous equipments
                search for another route). The default value is
                'off'."
        ::= { fclX25CfnServiceEntry 5 }


    fclX25CfnSerCallReturnTransmission OBJECT-TYPE
        SYNTAX  INTEGER {
                off(1),
                on(3)
                }
        ACCESS  read-write
        STATUS  mandatory
        DESCRIPTION
                "The value of this object indicates whether the
                'call return' packet may be sent on this link or
                not. The 'call return' packet, sent to the
                previous equipment, makes this equipments search
                for another route to join the called DTE. The
                defaut value is 'on'."
        ::= { fclX25CfnServiceEntry 6 }


    fclX25CfnSerStatLoadAndTraffic OBJECT-TYPE
        SYNTAX  INTEGER {
                off(1),
                on(2)
                }
        ACCESS  read-write
        STATUS  mandatory
        DESCRIPTION
                "The value of this object indicates whether, for
                this link, the load and traffic informations
                recording of the statistics management function is
                enabled or not. The default value is 'off'."
        ::= { fclX25CfnServiceEntry 10 }


    fclX25CfnSerStatSignalling OBJECT-TYPE
        SYNTAX  INTEGER {
                off(1),
                on(2)
                }
        ACCESS  read-write
        STATUS  mandatory
        DESCRIPTION
                "The value of this object indicates whether, for
                this link, the signalling informations recording
                of the statistics management function is enabled
                or not. The default value is 'off'."
        ::= { fclX25CfnServiceEntry 11 }


    fclX25CfnSerStatTotalizer OBJECT-TYPE
        SYNTAX  INTEGER {
                off(1),
                on(2)
                }
        ACCESS  read-write
        STATUS  mandatory
        DESCRIPTION
                "The value of this object indicates whether, for
                this link, the frames counting informations
                recording of the statistics management function is
                enabled or not. The default value is 'off'."
        ::= { fclX25CfnServiceEntry 12 }


    fclX25CfnSerStatCompression OBJECT-TYPE
        SYNTAX  INTEGER {
                off(1),
                on(2)
                }
        ACCESS  read-write
        STATUS  mandatory
        DESCRIPTION
                "The value of this object indicates whether, for
                this link, the compression informations recording
                of the statistics management function is enabled
                or not. The default value is 'off'."
        ::= { fclX25CfnServiceEntry 13 }


    fclX25ConfigMiscellaneous OBJECT IDENTIFIER ::= { fclX25Configurations 30 }


    fclX25CfmDiagnosticCodeField OBJECT-TYPE
        SYNTAX  INTEGER {
                privateCoding(2),
                publicCoding(1),
                x75Coding(3)
                }
        ACCESS  read-write
        STATUS  mandatory
        DESCRIPTION
                "The value of this object indicates how the
                diagnostic field is encoded. The default value is
                'privateCoding'."
        ::= { fclX25ConfigMiscellaneous 1 }


    fclX25CfmTransmitFlowControl OBJECT-TYPE
        SYNTAX  INTEGER {
                standard(1),
                dedicatedTranspac(2)
                }
        ACCESS  read-write
        STATUS  mandatory
        DESCRIPTION
                "The value of this object indicates whether the
                flow control is made according to the standard or
                according to fclX25CfmTransmitFlowControlTable
                (this way is used by TRANSPAC). The default value
                is 'standard'."
        ::= { fclX25ConfigMiscellaneous 2 }


    fclX25CfmAddress14DigitsTruncation OBJECT-TYPE
        SYNTAX  INTEGER {
                off(1),
                on(2)
                }
        ACCESS  read-write
        STATUS  mandatory
        DESCRIPTION
                "The value of this object indicates whether the
                addresses are truncated to 14 digits or not. The
                default value is 'off'."
        ::= { fclX25ConfigMiscellaneous 3 }


    fclX25CfmTransmitFlowControlTable OBJECT-TYPE
        SYNTAX  SEQUENCE OF FclX25CfmTransmitFlowControlEntry
        ACCESS  not-accessible
        STATUS  mandatory
        DESCRIPTION
                "This table defines non standard flow control. This
                table is used if fclX25CfmTransmitFlowControl is
                set to 'dedicatedTranspac'."
        ::= { fclX25ConfigMiscellaneous 20 }


    fclX25CfmTransmitFlowControlEntry OBJECT-TYPE
        SYNTAX  FclX25CfmTransmitFlowControlEntry
        ACCESS  not-accessible
        STATUS  mandatory
        DESCRIPTION
                "An entry of fclX25CfmTransmitFlowControlTable."
        INDEX   { fclX25CfmFlowCtrlPacketSize }
        ::= { fclX25CfmTransmitFlowControlTable 1 }


        FclX25CfmTransmitFlowControlEntry ::=
                SEQUENCE {
                    fclX25CfmFlowCtrlPacketSize
                        INTEGER,
                    fclX25CfmFlowCtrlMaxWindowSize
                        INTEGER
                }


    fclX25CfmFlowCtrlPacketSize OBJECT-TYPE
        SYNTAX  INTEGER {
                s16(4),
                s32(5),
                s64(6),
                s128(7),
                s256(8),
                s512(9),
                s1024(10),
                s2048(11),
                s4096(12),
                s8192(13)
                }
        ACCESS  read-only
        STATUS  mandatory
        DESCRIPTION
                "The value of this object defines a packet size."
        ::= { fclX25CfmTransmitFlowControlEntry 1 }


    fclX25CfmFlowCtrlMaxWindowSize OBJECT-TYPE
        SYNTAX  INTEGER (1..7)
        ACCESS  read-write
        STATUS  mandatory
        DESCRIPTION
                "The value of this object defines the maximum
                window size used for this packet size."
        ::= { fclX25CfmTransmitFlowControlEntry 2 }


    fcWanSwitch OBJECT IDENTIFIER ::= { frxConfig 25 }


    fcwDnicZoAddress OBJECT-TYPE
        SYNTAX  OCTET STRING (SIZE(3))
        ACCESS  read-write
        STATUS  mandatory
        DESCRIPTION
                "The value of this object is the address of the
                equipment. This address , with a DNIC ZO format as
                explained below, must have 6 digits (0..9). The
                default value is '900000'.


                Address format :

                   Eight digits (0..9) of X121 format are used as
                      the network address numbering plan. This
                      numbering plan has a hierarchical structure
                      :

                      4 digits define the Data Network Identifier
                         Code (DNIC) : DNIC identifies the region
                         to which belongs the equipment,
                      2 digits define the zone (ZO) : ZO
                         identifies the equipment inside the
                         region,
                      2 digits define the subscriber (SB) : SB
                         identifies a subscriber of the equipment.

                   Therefore each subscriber is completely
                      identified by its address of the form DNIC
                      ZO SB and each equipment by its address of
                      the form DNIC ZO."
        ::= { fcWanSwitch 1 }


    fcwMaxActiveCommunications OBJECT-TYPE
        SYNTAX  INTEGER (256..4064)
        ACCESS  read-write
        STATUS  mandatory
        DESCRIPTION
                "The value of this object defines the maximum
                number of the simultaneous active communications.
                The authorized values are '32..2048'. The default
                value is '512'."
        ::= { fcWanSwitch 10 }


    fcwDataPacketsDiscardThreshold OBJECT-TYPE
        SYNTAX  INTEGER (10..99)
        ACCESS  read-write
        STATUS  mandatory
        DESCRIPTION
                "The value of this object defines the busy memory
                threshold, in percentage of the total memory
                resources, beyond which the equipment discards the
                X25 data packets. The authorized values are
                '10..99'. The default value is '98'."
        ::= { fcWanSwitch 20 }


    fcwDataPacketsAcceptThreshold OBJECT-TYPE
        SYNTAX  INTEGER (10..99)
        ACCESS  read-write
        STATUS  mandatory
        DESCRIPTION
                "The value of this object defines the busy memory
                threshold, in percentage of the total memory
                resources, under which the equipment does not
                discard any more the X25 data packets. The
                authorized values are '10..99'. The default value
                is '98'."
        ::= { fcWanSwitch 21 }


    fcwCallPacketsDiscardThreshold OBJECT-TYPE
        SYNTAX  INTEGER (10..99)
        ACCESS  read-write
        STATUS  mandatory
        DESCRIPTION
                "The value of this object defines the busy memory
                threshold, in percentage of the total memory
                resources, beyond which the equipment discards the
                X25 call packets. The authorized values are
                '10..99'. The default value is '95'."
        ::= { fcWanSwitch 22 }


    fcwCallPacketsAcceptThreshold OBJECT-TYPE
        SYNTAX  INTEGER (10..99)
        ACCESS  read-write
        STATUS  mandatory
        DESCRIPTION
                "The value of this object defines the busy memory
                threshold, in percentage of the total memory
                resources, under which the equipment does not
                discard any more the X25 call packets. The
                authorized values are '10..99'. The default value
                is '90'."
        ::= { fcWanSwitch 23 }


    fcwLocalCommunications OBJECT-TYPE
        SYNTAX  INTEGER {
                denied(1),
                permitted(2)
                }
        ACCESS  read-write
        STATUS  mandatory
        DESCRIPTION
                "The value of this object defines whether the local
                communications (i.e. between two subscribers to
                this equipment) are authorized or not. For
                instance, these communications are denied when it
                is neccessary to re-route them to a billing
                equipment. The route used in this case is defined
                by fcwLocalIncomingCallsRouteId.
                The default value is 'permitted'."
        ::= { fcWanSwitch 30 }


    fcwLocalIncomingCallsRouteId OBJECT-TYPE
        SYNTAX  INTEGER (0..199)
        ACCESS  read-write
        STATUS  mandatory
        DESCRIPTION
                "The value of this object defines the route used by
                the local incoming call packets when the local
                communications are forbidden
                (fcwLocalCommunications set to 'denied'). This
                route must exist in fcwRouteTable. The authorized
                values are '0..199'. The default value is '255'."
        ::= { fcWanSwitch 31 }


    fcwLoadAndTrafficSummingPeriod OBJECT-TYPE
        SYNTAX  INTEGER (10..2500)
        ACCESS  read-write
        STATUS  mandatory
        DESCRIPTION
                "The value of this object is the period, in
                seconds, during which load and traffic quantity is
                summed and used by the switch over or overflow
                mechanisms. The authorized values are '10..2500'
                by step of 10. The default value is '20'."
        ::= { fcWanSwitch 40 }


    fcwLoadAndTrafficEventsTimer OBJECT-TYPE
        SYNTAX  INTEGER (10..2500)
        ACCESS  read-write
        STATUS  mandatory
        DESCRIPTION
                "The value of this object defines the time, in
                seconds, between two load and traffic event
                generations. These event are generated by the
                switch over or overflow mechanisms when a
                threshold is crossed. The authorized values are
                '10..2500' by step of 10. The default value is
                '20'."
        ::= { fcWanSwitch 41 }


    fcwFrameRelay OBJECT IDENTIFIER ::= { fcWanSwitch 45 }


    fcwFrDlcStatusChangeTrapEnabling OBJECT-TYPE
        SYNTAX  INTEGER {
                off(1),
                on(2)
                }
        ACCESS  read-write
        STATUS  mandatory
        DESCRIPTION
                "Emission du TRAP 'changement d'etat d'une
                terminaison PVC' defini en RFC1315"
        ::= { fcwFrameRelay 5 }


    fcwFrAnnexeGInternalStacksMaxCount OBJECT-TYPE
        SYNTAX  INTEGER (0..2000)
        ACCESS  read-write
        STATUS  mandatory
        DESCRIPTION
                "Nb max d'instances FRI disponible"
        ::= { fcwFrameRelay 6 }


    fcwFrEndPointMaxCount OBJECT-TYPE
        SYNTAX  INTEGER (0..5000)
        ACCESS  read-write
        STATUS  mandatory
        DESCRIPTION
                "Nb max de terminaisons FR simultanees (SVC ou PVC)"
        ::= { fcwFrameRelay 10 }


    fcwFrFrameAcceptCpuThreshold OBJECT-TYPE
        SYNTAX  INTEGER (0..100)
        ACCESS  read-write
        STATUS  mandatory
        DESCRIPTION
                "Seuil : CPU autorisee pour l'acceptation des trames"
        ::= { fcwFrameRelay 20 }


    fcwFrFrameAcceptMemoryThreshold OBJECT-TYPE
        SYNTAX  INTEGER (0..100)
        ACCESS  read-write
        STATUS  mandatory
        DESCRIPTION
                "Seuil : Memoire autorisee pour l'acceptation des
                trames"
        ::= { fcwFrameRelay 21 }


    fcwFrDlcSetupAlarmThreshold OBJECT-TYPE
        SYNTAX  INTEGER (0..250)
        ACCESS  read-write
        STATUS  mandatory
        DESCRIPTION
                "Seuil : A% seuil alarmique d'acceptation de
                connexions FR en terme de ressources"
        ::= { fcwFrameRelay 22 }


    fcwFrDlcSetupDiscardThreshold OBJECT-TYPE
        SYNTAX  INTEGER (100..350)
        ACCESS  read-write
        STATUS  mandatory
        DESCRIPTION
                "R% Seuil de refus d'etablissement des DLC VBR-NRT
                (pourcentage des ressources : 100 = pas de
                surbooking)"
        ::= { fcwFrameRelay 23 }


    fcwFrVoiceFrameSize OBJECT-TYPE
        SYNTAX  INTEGER (0..250)
        ACCESS  read-write
        STATUS  mandatory
        DESCRIPTION
                "Longueur trames voix"
        ::= { fcwFrameRelay 40 }


    fcwFrVoiceMaxTransitDelay OBJECT-TYPE
        SYNTAX  INTEGER (0..250)
        ACCESS  read-write
        STATUS  mandatory
        DESCRIPTION
                "Temps de transit maximum de bout en bout des
                communications de type voix en millisecondes"
        ::= { fcwFrameRelay 41 }


    fcwFrCongestionCheckTimer OBJECT-TYPE
        SYNTAX  INTEGER (200..4000)
        ACCESS  read-write
        STATUS  mandatory
        DESCRIPTION
                "Tempo de surveillance de la congestion du reseau
                FR (milisecondes)"
        ::= { fcwFrameRelay 50 }


    fcwFrCongestionCount OBJECT-TYPE
        SYNTAX  INTEGER (10..255)
        ACCESS  read-write
        STATUS  mandatory
        DESCRIPTION
                "Critere de decongestion du reseau FR"
        ::= { fcwFrameRelay 51 }


    fcwFrCirTimer OBJECT-TYPE
        SYNTAX  INTEGER (20..400)
        ACCESS  read-write
        STATUS  mandatory
        DESCRIPTION
                "Tempo echantillonage CIR (millisecondes)"
        ::= { fcwFrameRelay 52 }


    fcwFrEventOutput OBJECT-TYPE
        SYNTAX  INTEGER {
                none(1),
                oneOutOf16(3),
                oneOutOf64(4),
                oneOutOf256(5),
                all(2)
                }
        ACCESS  read-write
        STATUS  mandatory
        DESCRIPTION
                "Filtrage des EVR"
        ::= { fcwFrameRelay 53 }


    fcwFrSlowingDownThreshold OBJECT-TYPE
        SYNTAX  INTEGER (0..250)
        ACCESS  read-write
        STATUS  mandatory
        DESCRIPTION
                "S0 seuil de ralentissement du trafic sans
                positionner de bits de congestion (0 = pas de
                ralentissement)"
        ::= { fcwFrameRelay 54 }


    fcwFrFecnBecnOfDeFramesThreshold OBJECT-TYPE
        SYNTAX  INTEGER (0..250)
        ACCESS  read-write
        STATUS  mandatory
        DESCRIPTION
                "S1 seuil de positionnement des bits FECN BECN sur
                les trames DE (0 = calcule en fct de la vitesse de
                la ligne)"
        ::= { fcwFrameRelay 55 }


    fcwFrFecnBecnOfAllFramesThreshold OBJECT-TYPE
        SYNTAX  INTEGER (0..250)
        ACCESS  read-write
        STATUS  mandatory
        DESCRIPTION
                "S2 seuil de positionnement des bits FECN BECN sur
                toutes les trames (0 = calcule en fct de la
                vitesse de la ligne)"
        ::= { fcwFrameRelay 56 }


    fcwFrDeFramesDiscardThreshold OBJECT-TYPE
        SYNTAX  INTEGER (0..250)
        ACCESS  read-write
        STATUS  mandatory
        DESCRIPTION
                "S3 seuil de rejet des trames DE (0 = calcule en
                fct de la vitesse de la ligne)"
        ::= { fcwFrameRelay 57 }


    fcwFrAllFramesDiscardThreshold OBJECT-TYPE
        SYNTAX  INTEGER (0..250)
        ACCESS  read-write
        STATUS  mandatory
        DESCRIPTION
                "S4 seuil de rejet de toutes les trames (0 =
                calcule en fct de la vitesse de la ligne)"
        ::= { fcwFrameRelay 58 }


    fcwAddressConversion OBJECT IDENTIFIER ::= { fcWanSwitch 48 }


    fcwAddrConvIncomingCallTable OBJECT-TYPE
        SYNTAX  SEQUENCE OF FcwAddrConvIncomingCallEntry
        ACCESS  not-accessible
        STATUS  mandatory
        DESCRIPTION
                "This table defines, for the incoming call packets,
                the association between an X121 address pattern to
                be converted and the substituted address pattern.
                This substitution is used on the logical ports
                when *ConversionAimedPoint is set to 'on',
                *ConversionIncomingCall is not set to 'off' or
                *ConversionAddressCheck is set to 'onIncomingCall'
                or 'onIncomingCallAndOutgoingCall'.

                Two digits have special meanings :

                The digit 'C' ('$' on the equipment configurator)
                   when simultaneously used in the address pattern
                   to be converted AND in the converted address
                   pattern matches any single digit which will be
                   reported in the converted address.

                   Example :
                      fcwConvInExternalAddr  = 1234C6C8FFFFFFF
                      fcwConvInConvertedAddr = 900010CCFFFFFFF

                      1234567890 is converted to 9000105790

                The digit 'D' ('?' on the equipment configurator)
                   when used in the address pattern to be
                   converted matches any single digit which will
                   not be present in the converted address.

                   Example :
                      fcwConvInExternalAddr  = 1234DD78FFFFFFF
                      fcwConvInConvertedAddr = 9000FFFFFFFFFFF

                      1234567890 is converted to 900090,
                      1234007890 is converted to 900090,
                      1234560090 is not converted."
        ::= { fcwAddressConversion 1 }


    fcwAddrConvIncomingCallEntry OBJECT-TYPE
        SYNTAX  FcwAddrConvIncomingCallEntry
        ACCESS  not-accessible
        STATUS  mandatory
        DESCRIPTION
                "An entry of fcwAddrConvIncomingCallTable."
        INDEX   { fcwConvInExternalAddr }
        ::= { fcwAddrConvIncomingCallTable 1 }


        FcwAddrConvIncomingCallEntry ::=
                SEQUENCE {
                    fcwConvInExternalAddr
                        OCTET STRING,
                    fcwConvInStatus
                        INTEGER,
                    fcwConvInConvertedAddr
                        OCTET STRING,
                    fcwConvInOrderNum
                        INTEGER
                }


    fcwConvInExternalAddr OBJECT-TYPE
        SYNTAX  OCTET STRING (SIZE(8))
        ACCESS  read-only
        STATUS  mandatory
        DESCRIPTION
                "The value of this object identifies one and only
                one external address pattern to be converted. The
                value may contain up to 15 digits (digits 0..9,
                special digits C and D). The value must be
                completed with 'F' digits for a total of 16
                digits. The equipment configurator does not need
                final completion. The default value is 'FF FF FF
                FF FF FF FF FF' meaning 'empty value' (blank value
                on the equipment configurator). The conversion
                mechanism is explained in the description of this
                table."
        ::= { fcwAddrConvIncomingCallEntry 1 }


    fcwConvInStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwAddrConvIncomingCallEntry 2 }


    fcwConvInConvertedAddr OBJECT-TYPE
        SYNTAX  OCTET STRING (SIZE(8))
        ACCESS  read-write
        STATUS  mandatory
        DESCRIPTION
                "The value of this object defines the converted
                address pattern. The value may contain up to 15
                digits (digits 0..9, special digit C). The value
                must be completed with 'F' digits for a total of
                16 digits. The equipment configurator does not
                need final completion. The default value is 'FF FF
                FF FF FF FF FF FF' meaning 'empty value' (blank
                value on the equipment configurator). The
                conversion mechanism is explained in the
                description of this table."
        ::= { fcwAddrConvIncomingCallEntry 3 }


    fcwConvInOrderNum OBJECT-TYPE
        SYNTAX  INTEGER (1..255)
        ACCESS  read-write
        STATUS  mandatory
        DESCRIPTION
                "No ordre"
        ::= { fcwAddrConvIncomingCallEntry 4 }


    fcwAddrConvOutgoingCallTable OBJECT-TYPE
        SYNTAX  SEQUENCE OF FcwAddrConvOutgoingCallEntry
        ACCESS  not-accessible
        STATUS  mandatory
        DESCRIPTION
                "This table defines, for the outgoing call packets,
                the association between an X121 address pattern to
                be converted and the substituted address pattern.
                This substitution is used on the logical ports
                when *ConversionOutgoingCall is not set to 'off'
                or *ConversionAddressCheck is set to
                'onOutgoingCall' or
                'onIncomingCallAndOutgoingCall'.

                Two digits have special meanings :

                The digit 'C' ('$' on the equipment configurator)
                   when simultaneously used in the address pattern
                   to be converted AND in the converted address
                   pattern matches any single digit which will be
                   reported in the converted address.

                   Example :
                      fcwConvOutExternalAddr  = 1234C6C8FFFFFFF
                      fcwConvOutConvertedAddr = 900010CCFFFFFFF

                      1234567890 is converted to 9000105790

                The digit 'D' ('?' on the equipment configurator)
                   when used in the address pattern to be
                   converted matches any single digit which will
                   not be present in the converted address.

                   Example :
                      fcwConvOutExternalAddr  = 1234DD78FFFFFFF
                      fcwConvOutConvertedAddr = 9000FFFFFFFFFFF

                      1234567890 is converted to 900090,
                      1234007890 is converted to 900090,
                      1234560090 is not converted."
        ::= { fcwAddressConversion 2 }


    fcwAddrConvOutgoingCallEntry OBJECT-TYPE
        SYNTAX  FcwAddrConvOutgoingCallEntry
        ACCESS  not-accessible
        STATUS  mandatory
        DESCRIPTION
                "An entry of fcwAddrConvOutgoingCallTable."
        INDEX   { fcwConvOutExternalAddr }
        ::= { fcwAddrConvOutgoingCallTable 1 }


        FcwAddrConvOutgoingCallEntry ::=
                SEQUENCE {
                    fcwConvOutExternalAddr
                        OCTET STRING,
                    fcwConvOutStatus
                        INTEGER,
                    fcwConvOutConvertedAddr
                        OCTET STRING,
                    fcwConvOutOrderNum
                        INTEGER
                }


    fcwConvOutExternalAddr OBJECT-TYPE
        SYNTAX  OCTET STRING (SIZE(8))
        ACCESS  read-only
        STATUS  mandatory
        DESCRIPTION
                "The value of this object identifies one and only
                one external address pattern to be converted. The
                value may contain up to 15 digits (digits 0..9,
                special digits C and D). The value must be
                completed with 'F' digits for a total of 16
                digits. The equipment configurator does not need
                final completion. The default value is 'FF FF FF
                FF FF FF FF FF' meaning 'empty value' (blank value
                on the equipment configurator). The conversion
                mechanism is explained in the description of this
                table."
        ::= { fcwAddrConvOutgoingCallEntry 1 }


    fcwConvOutStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwAddrConvOutgoingCallEntry 2 }


    fcwConvOutConvertedAddr OBJECT-TYPE
        SYNTAX  OCTET STRING (SIZE(8))
        ACCESS  read-write
        STATUS  mandatory
        DESCRIPTION
                "The value of this object defines the converted
                address pattern. The value may contain up to 15
                digits (digits 0..9, special digit C). The value
                must be completed with 'F' digits for a total of
                16 digits. The equipment configurator does not
                need final completion. The default value is 'FF FF
                FF FF FF FF FF FF' meaning 'empty value' (blank
                value on the equipment configurator). The
                conversion mechanism is explained in the
                description of this table."
        ::= { fcwAddrConvOutgoingCallEntry 3 }


    fcwConvOutOrderNum OBJECT-TYPE
        SYNTAX  INTEGER (1..255)
        ACCESS  read-write
        STATUS  mandatory
        DESCRIPTION
                "No ordre"
        ::= { fcwAddrConvOutgoingCallEntry 4 }


    fcwAddrConvMultiCriterionInCallTable OBJECT-TYPE
        SYNTAX  SEQUENCE OF FcwAddrConvMultiCriterionInCallEntry
        ACCESS  not-accessible
        STATUS  mandatory
        DESCRIPTION
                ""
        ::= { fcwAddressConversion 3 }


    fcwAddrConvMultiCriterionInCallEntry OBJECT-TYPE
        SYNTAX  FcwAddrConvMultiCriterionInCallEntry
        ACCESS  not-accessible
        STATUS  mandatory
        DESCRIPTION
                "An entry of fcwAddrConvMultiCriterionInCallTable."
        INDEX   { fcwConvMultiInConvID,
                  fcwConvMultiInExternalAddr }
        ::= { fcwAddrConvMultiCriterionInCallTable 1 }


        FcwAddrConvMultiCriterionInCallEntry ::=
                SEQUENCE {
                    fcwConvMultiInConvID
                        OCTET STRING,
                    fcwConvMultiInExternalAddr
                        OCTET STRING,
                    fcwConvMultiInStatus
                        INTEGER,
                    fcwConvMultiInConvertedAddr
                        OCTET STRING,
                    fcwConvMultiInOrderNum
                        INTEGER
                }


    fcwConvMultiInConvID OBJECT-TYPE
        SYNTAX  OCTET STRING (SIZE(1))
        ACCESS  read-only
        STATUS  mandatory
        DESCRIPTION
                "Conversion ID "
        ::= { fcwAddrConvMultiCriterionInCallEntry 1 }


    fcwConvMultiInExternalAddr OBJECT-TYPE
        SYNTAX  OCTET STRING (SIZE(6))
        ACCESS  read-only
        STATUS  mandatory
        DESCRIPTION
                "Prefixe adresse exterieur "
        ::= { fcwAddrConvMultiCriterionInCallEntry 2 }


    fcwConvMultiInStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwAddrConvMultiCriterionInCallEntry 3 }


    fcwConvMultiInConvertedAddr OBJECT-TYPE
        SYNTAX  OCTET STRING (SIZE(6))
        ACCESS  read-write
        STATUS  mandatory
        DESCRIPTION
                "Prefixe converti"
        ::= { fcwAddrConvMultiCriterionInCallEntry 4 }


    fcwConvMultiInOrderNum OBJECT-TYPE
        SYNTAX  INTEGER (1..255)
        ACCESS  read-write
        STATUS  mandatory
        DESCRIPTION
                "No ordre"
        ::= { fcwAddrConvMultiCriterionInCallEntry 5 }


    fcwAddrConvMultiCriterionOutCallTable OBJECT-TYPE
        SYNTAX  SEQUENCE OF FcwAddrConvMultiCriterionOutCallEntry
        ACCESS  not-accessible
        STATUS  mandatory
        DESCRIPTION
                ""
        ::= { fcwAddressConversion 4 }


    fcwAddrConvMultiCriterionOutCallEntry OBJECT-TYPE
        SYNTAX  FcwAddrConvMultiCriterionOutCallEntry
        ACCESS  not-accessible
        STATUS  mandatory
        DESCRIPTION
                "An entry of fcwAddrConvMultiCriterionOutCallTable."
        INDEX   { fcwConvMultiOutConvID,
                  fcwConvMultiOutExternalAddr }
        ::= { fcwAddrConvMultiCriterionOutCallTable 1 }


        FcwAddrConvMultiCriterionOutCallEntry ::=
                SEQUENCE {
                    fcwConvMultiOutConvID
                        OCTET STRING,
                    fcwConvMultiOutExternalAddr
                        OCTET STRING,
                    fcwConvMultiOutStatus
                        INTEGER,
                    fcwConvMultiOutConvertedAddr
                        OCTET STRING,
                    fcwConvMultiOutOrderNum
                        INTEGER
                }


    fcwConvMultiOutConvID OBJECT-TYPE
        SYNTAX  OCTET STRING (SIZE(1))
        ACCESS  read-only
        STATUS  mandatory
        DESCRIPTION
                "Conversion ID "
        ::= { fcwAddrConvMultiCriterionOutCallEntry 1 }


    fcwConvMultiOutExternalAddr OBJECT-TYPE
        SYNTAX  OCTET STRING (SIZE(6))
        ACCESS  read-only
        STATUS  mandatory
        DESCRIPTION
                "Prefixe adresse exterieur"
        ::= { fcwAddrConvMultiCriterionOutCallEntry 2 }


    fcwConvMultiOutStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwAddrConvMultiCriterionOutCallEntry 3 }


    fcwConvMultiOutConvertedAddr OBJECT-TYPE
        SYNTAX  OCTET STRING (SIZE(6))
        ACCESS  read-write
        STATUS  mandatory
        DESCRIPTION
                "Prefixe converti"
        ::= { fcwAddrConvMultiCriterionOutCallEntry 4 }


    fcwConvMultiOutOrderNum OBJECT-TYPE
        SYNTAX  INTEGER (1..255)
        ACCESS  read-write
        STATUS  mandatory
        DESCRIPTION
                "No ordre"
        ::= { fcwAddrConvMultiCriterionOutCallEntry 5 }


    fcwAddrConvCondOutgoingCallTable OBJECT-TYPE
        SYNTAX  SEQUENCE OF FcwAddrConvCondOutgoingCallEntry
        ACCESS  not-accessible
        STATUS  mandatory
        DESCRIPTION
                ""
        ::= { fcwAddressConversion 5 }


    fcwAddrConvCondOutgoingCallEntry OBJECT-TYPE
        SYNTAX  FcwAddrConvCondOutgoingCallEntry
        ACCESS  not-accessible
        STATUS  mandatory
        DESCRIPTION
                "An entry of fcwAddrConvCondOutgoingCallTable."
        INDEX   { fcwConvCondOutExternalAddr,
                  fcwConvCondOutTryOn }
        ::= { fcwAddrConvCondOutgoingCallTable 1 }


        FcwAddrConvCondOutgoingCallEntry ::=
                SEQUENCE {
                    fcwConvCondOutExternalAddr
                        OCTET STRING,
                    fcwConvCondOutTryOn
                        INTEGER,
                    fcwConvCondOutStatus
                        INTEGER,
                    fcwConvCondOutConvertedAddr
                        OCTET STRING
                }


    fcwConvCondOutExternalAddr OBJECT-TYPE
        SYNTAX  OCTET STRING (SIZE(6))
        ACCESS  read-only
        STATUS  mandatory
        DESCRIPTION
                "The value of this object identifies one and only
                one external address pattern to be converted. The
                value may contain up to 12 digits (digits 0..9,
                special digits C and D). The equipment
                configurator does not need final completion. The
                default value is 'FF FF FF FF FF FF' meaning
                'empty value' (blank value on the equipment
                configurator). The conversion mechanism is
                explained in the description of
                fcwAddrConvOutgoingCallTable."
        ::= { fcwAddrConvCondOutgoingCallEntry 1 }


    fcwConvCondOutTryOn OBJECT-TYPE
        SYNTAX  INTEGER {
                normalClear1(1),
                backup(2),
                all(3)
                }
        ACCESS  read-only
        STATUS  mandatory
        DESCRIPTION
                "The value of this object defines which kind of LP
                in the route table the entry is associated with  :
                   all : this conversion is for both primary LP
                        with routing type normalClear1, and
                        associated backup LP,
                   normalClear1 : this conversion is only for
                        primary LP with routing type normalClear1,
                   backup : this conversion is only for backups of
                        primary LP with routing type normalClear1,

                The default value is 'all'."
        ::= { fcwAddrConvCondOutgoingCallEntry 2 }


    fcwConvCondOutStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwAddrConvCondOutgoingCallEntry 3 }


    fcwConvCondOutConvertedAddr OBJECT-TYPE
        SYNTAX  OCTET STRING (SIZE(6))
        ACCESS  read-write
        STATUS  mandatory
        DESCRIPTION
                "The value of this object defines the converted
                address pattern. The value may contain up to 12
                digits (digits 0..9, special digit C). The
                equipment configurator does not need final
                completion. The default value is 'FF FF FF FF FF'
                meaning 'empty value' (blank value on the
                equipment configurator The conversion mechanism is
                explained in the description of
                fcwAddrConvOutgoingCallTable."
        ::= { fcwAddrConvCondOutgoingCallEntry 4 }


    fcwRouteTable OBJECT-TYPE
        SYNTAX  SEQUENCE OF FcwRouteEntry
        ACCESS  not-accessible
        STATUS  mandatory
        DESCRIPTION
                "This table defines the routes which may be used by
                the call packets according to the routing tables.
                One route is composed of one or more logical
                ports. Most of times each logical port has only
                one channel and it is not necessary to indicates
                the channel identifier."
        ::= { fcWanSwitch 50 }


    fcwRouteEntry OBJECT-TYPE
        SYNTAX  FcwRouteEntry
        ACCESS  not-accessible
        STATUS  mandatory
        DESCRIPTION
                "An entry of fcwRouteTable."
        INDEX   { fcwRoutRouteId,
                  fcwRoutLogPortId,
                  fcwRoutChannelId }
        ::= { fcwRouteTable 1 }


        FcwRouteEntry ::=
                SEQUENCE {
                    fcwRoutRouteId
                        INTEGER,
                    fcwRoutLogPortId
                        INTEGER,
                    fcwRoutChannelId
                        INTEGER,
                    fcwRoutStatus
                        INTEGER,
                    fcwRoutType
                        INTEGER
                }


    fcwRoutRouteId OBJECT-TYPE
        SYNTAX  INTEGER (0..199)
        ACCESS  read-only
        STATUS  mandatory
        DESCRIPTION
                "The value of this object identifies one and only
                one route. One route may be composed of one or
                several logical ports. The possible values are :
                '0..199'. If it is unused, the value of this
                parameter is '255'. The default value is '255'."
        ::= { fcwRouteEntry 1 }


    fcwRoutLogPortId OBJECT-TYPE
        SYNTAX  INTEGER (0..181)
        ACCESS  read-only
        STATUS  mandatory
        DESCRIPTION
                "The value of this object identifies one of the
                logical ports which compose the route defined by
                fcwRoutRouteId. The possible values are :
                '0..131'. If it is unused, the value of this
                parameter is '255'. The default value is '255'."
        ::= { fcwRouteEntry 2 }


    fcwRoutChannelId OBJECT-TYPE
        SYNTAX  INTEGER (0..1023)
        ACCESS  read-only
        STATUS  mandatory
        DESCRIPTION
                "The value of this object identifies one of the
                channels available on the logical port defined by
                fcwRoutLogPortId. Most of times each logical port
                has only one channel and it is not necessary to
                indicates this channel identifier.

                In some very particular cases a logical port may
                have several channels and the equipment is not
                able to choose the right one. So the channel
                identifier must be indicated.

                This happens, for instance, with a Frame Relay
                logical port which has several Permanent Virtual
                Circuit end points and when it is impossible to
                find which one must be used : the corresponding
                DLCI (Data Link Connection Identifier) must be
                indicated in fcwRoutChannelId.

                   The possible values are : '0..1023'. If it is
                        unused, the value of this parameter is
                        '65535'. The default value is '65535'."
        ::= { fcwRouteEntry 3 }


    fcwRoutStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwRouteEntry 4 }


    fcwRoutType OBJECT-TYPE
        SYNTAX  INTEGER {
                normal(1),
                normalPriorityModule(2),
                backup1(3),
                backup2(4),
                backup3(5),
                backup4(6),
                backup5(7),
                dynamic(8),
                backupDynamic(9),
                normalClear1(10)
                }
        ACCESS  read-write
        STATUS  mandatory
        DESCRIPTION
                "The value of this object indicates how the
                equipment will try to use this logical port (or
                this couple [logical port, channel]) which
                composes this route.

                The following combinations are possible :

                ~~~~~~~~~~~~~~~~~~~~~~~~~~~~~~~~~~~~~~~~~~~~~~~~~~
                |Route|LP|Type|       Routing description        |
                |~~~~~|~~|~~~~|~~~~~~~~~~~~~~~~~~~~~~~~~~~~~~~~~~|
                |  1  | 1| n  | -> on one LP                     |
                |~~~~~|~~|~~~~|~~~~~~~~~~~~~~~~~~~~~~~~~~~~~~~~~~|
                |  2  | 1| n  | -> 1 : on one main LP            |
                |  2  | 2| b1 | \                                |
                |  2  | 3| b1 |  > 2 : on three equal            |
                |  2  | 4| b1 | /      priority backup LPs       |
                |~~~~~|~~|~~~~|~~~~~~~~~~~~~~~~~~~~~~~~~~~~~~~~~~|
                |  3  | 1| n  | \                                |
                |  3  | 2| n  |  |                               |
                |  3  | 3| n  |  > on five equal priority LPs    |
                |  3  | 4| n  |  |                               |
                |  3  | 5| n  | /                                |
                |~~~~~|~~|~~~~|~~~~~~~~~~~~~~~~~~~~~~~~~~~~~~~~~~|
                |  4  | 1| n  | -> 1 : on one main LP            |
                |  4  | 2| b1 | -> 2 : on one first backup LP    |
                |  4  | 3| b2 | -> 3 : on one second backup LP   |
                |  4  | 4| b3 | -> 4 : on one third backup LP    |
                |~~~~~|~~|~~~~|~~~~~~~~~~~~~~~~~~~~~~~~~~~~~~~~~~|
                |  5  | 1| n  | \      on three equal            |
                |  5  | 2| n  |  > 1 : priority main LPs         |
                |  5  | 3| n  | /                                |
                |  5  | 4| b1 | -> 2 : on one backup LP          |
                |~~~~~|~~|~~~~|~~~~~~~~~~~~~~~~~~~~~~~~~~~~~~~~~~|
                |  8  | 1| nM |   each module of the equipment   |
                |  8  | 2| b1 | considers its own LPs as having  |
                |  8  |11| b2 |    a higher priority than the    |
                |  8  | 3| b3 |     LPs of the other modules     |
                |  8  |21| b4 |           (see below)            |
                |  8  |12| b5 |                                  |
                |~~~~~|~~|~~~~|~~~~~~~~~~~~~~~~~~~~~~~~~~~~~~~~~~|
                |  9  | 1| nC | -> 1 : on one main LP            |
                |~~~~~|~~|~~~~|~~~~~~~~~~~~~~~~~~~~~~~~~~~~~~~~~~|
                |  10 | 1| nC | -> 1 : on one main LP            |
                |  10 | 2| b1 | -> 2 : on one first backup LP    |
                |  10 | 3| b2 | -> 3 : on one second backup LP   |
                |  10 | 4| b3 | -> 4 : on one third backup LP    |
                ~~~~~~~~~~~~~~~~~~~~~~~~~~~~~~~~~~~~~~~~~~~~~~~~~~
                Types : n : normal, nM : normalPriorityModule, b1
                   : backup1, b2 : backup2, b3 : backup3, b4 :
                   backup4, b5 : backup5, dynamic, backupDynamic,
                   nC : normalClear1.

                Interpretation of the route 8 : In this example
                   let us suppose that LP 1, 2 and 3 belongs to
                   the module 0, 11 and 12 to the module 1, and 21
                   to the module 2. The route 8 becomes :

                        on the module 0 :
                             LP   :  1   2   3  11  21  12
                             Type :  n  b1  b2  b3  b4  b5

                        on the module 1 :
                             LP   : 11  12   1   2   3  21
                             Type :  n  b1  b2  b3  b4  b5

                        on the module 2 :
                             LP   : 21   1   2  11   3  12
                             Type :  n  b1  b2  b3  b4  b5

                Interpretation of the route 9 : there must be at
                   least 1 valid entry with try on = normalClear1
                   (or all) in the Clear cause/diagnostic table.
                   The address is converted according to that
                   entry.
                Interpretation of the route 10 : there must be at
                   least 1 valid entry with try on = normalClear1
                   and 1 with try on = backup (or 1 with all) in
                   the Clear cause/diagnostic table. The address
                   is converted according to that entry.

                The default value is 'normal'."
        ::= { fcwRouteEntry 5 }


    fcwDnicRoutingTable OBJECT-TYPE
        SYNTAX  SEQUENCE OF FcwDnicRoutingEntry
        ACCESS  not-accessible
        STATUS  mandatory
        DESCRIPTION
                "This table is the call packets routing table for
                the Data Network Identifier Code (DNIC) part of
                the X121 called address."
        ::= { fcWanSwitch 60 }


    fcwDnicRoutingEntry OBJECT-TYPE
        SYNTAX  FcwDnicRoutingEntry
        ACCESS  not-accessible
        STATUS  mandatory
        DESCRIPTION
                "An entry of fcwDnicRoutingTable."
        INDEX   { fcwDnicDataNetworkIdentifierCode,
                  fcwDnicRouteId }
        ::= { fcwDnicRoutingTable 1 }


        FcwDnicRoutingEntry ::=
                SEQUENCE {
                    fcwDnicDataNetworkIdentifierCode
                        OCTET STRING,
                    fcwDnicRouteId
                        INTEGER,
                    fcwDnicStatus
                        INTEGER
                }


    fcwDnicDataNetworkIdentifierCode OBJECT-TYPE
        SYNTAX  OCTET STRING (SIZE(2))
        ACCESS  read-only
        STATUS  mandatory
        DESCRIPTION
                "The value of this object is the Data Network
                Identifier Code (DNIC) part of the X121 called
                address from the call packet to be routed. This
                address , with a DNIC format as explained below,
                may contain up to 4 digits (0..9, B).

                The digit 'B' (character '*' on the equipment
                configurator) have special meaning :

                   'B' matches any address. When used it must be
                        the only digit specified (with final
                        completion as explained below). The
                        associated route is used only if the
                        equipment does not find another
                        possibility in this table.

                   There must be only one route for each specified
                        address but partial addresses are
                        accepted.

                   Example : If route 1 is specified for DNIC
                        '1234', route 2 for DNIC '12' and route 3
                        for DNIC 'B', call packets to DNIC 1234
                        are routed on the route 1, call packets to
                        DNIC 12xx (xx different from 34) are
                        routed on the route 2 and all others are
                        routed on the route 3.

                The value must be completed with 'F' digits for a
                total of 4 digits. The equipment configurator does
                not need final completion. The default value is
                'FF FF' meaning 'empty value' (blank value on the
                equipment configurator).


                Address format :

                   Eight digits (0..9) of X121 format are used as
                      the network address numbering plan. This
                      numbering plan has a hierarchical structure
                      :

                      4 digits define the Data Network Identifier
                         Code (DNIC) : DNIC identifies the region
                         to which belongs the equipment,
                      2 digits define the zone (ZO) : ZO
                         identifies the equipment inside the
                         region,
                      2 digits define the subscriber (SB) : SB
                         identifies a subscriber of the equipment.

                   Therefore each subscriber is completely
                      identified by its address of the form DNIC
                      ZO SB and each equipment by its address of
                      the form DNIC ZO."
        ::= { fcwDnicRoutingEntry 1 }


    fcwDnicRouteId OBJECT-TYPE
        SYNTAX  INTEGER (0..199)
        ACCESS  read-only
        STATUS  mandatory
        DESCRIPTION
                "The value of this object defines the route
                associated to this address. This route must exist
                in fcwRouteTable. The authorized values are
                '0..199'. The default value is '255'."
        ::= { fcwDnicRoutingEntry 2 }


    fcwDnicStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwDnicRoutingEntry 3 }


    fcwZoRoutingTable OBJECT-TYPE
        SYNTAX  SEQUENCE OF FcwZoRoutingEntry
        ACCESS  not-accessible
        STATUS  mandatory
        DESCRIPTION
                "This table is the call packets routing table for
                the Zone (ZO) part of the X121 called address."
        ::= { fcWanSwitch 61 }


    fcwZoRoutingEntry OBJECT-TYPE
        SYNTAX  FcwZoRoutingEntry
        ACCESS  not-accessible
        STATUS  mandatory
        DESCRIPTION
                "An entry of fcwZoRoutingTable."
        INDEX   { fcwZoZone,
                  fcwZoRouteId }
        ::= { fcwZoRoutingTable 1 }


        FcwZoRoutingEntry ::=
                SEQUENCE {
                    fcwZoZone
                        OCTET STRING,
                    fcwZoRouteId
                        INTEGER,
                    fcwZoStatus
                        INTEGER
                }


    fcwZoZone OBJECT-TYPE
        SYNTAX  OCTET STRING (SIZE(1))
        ACCESS  read-only
        STATUS  mandatory
        DESCRIPTION
                "The value of this object is the Zone (ZO) part of
                the X121 called address from the call packet to be
                routed. This address , with a ZO format as
                explained below, must contains 2 digits (0..9, B).

                The digit 'B' (character '*' on the equipment
                configurator) have special meaning :

                   'B' matches any address. When used it must be
                        the only digit specified (with final
                        completion as explained below). The
                        associated route is used only if the
                        equipment does not find another
                        possibility in this table.

                   There must be only one route for each specified
                        address.

                   Example : If route 1 is specified for ZO '12',
                        route 2 for ZO 'B', call packets to ZO 12
                        are routed on the route 1 and all others
                        are routed on the route 2.

                The value must be completed with 'F' digits for a
                total of 2 digits (here only if the digit 'B' is
                used). The equipment configurator does not need
                final completion. The default value is 'FF'
                meaning 'empty value' (blank value on the
                equipment configurator).


                Address format :

                   Eight digits (0..9) of X121 format are used as
                      the network address numbering plan. This
                      numbering plan has a hierarchical structure
                      :

                      4 digits define the Data Network Identifier
                         Code (DNIC) : DNIC identifies the region
                         to which belongs the equipment,
                      2 digits define the zone (ZO) : ZO
                         identifies the equipment inside the
                         region,
                      2 digits define the subscriber (SB) : SB
                         identifies a subscriber of the equipment.

                   Therefore each subscriber is completely
                      identified by its address of the form DNIC
                      ZO SB and each equipment by its address of
                      the form DNIC ZO."
        ::= { fcwZoRoutingEntry 1 }


    fcwZoRouteId OBJECT-TYPE
        SYNTAX  INTEGER (0..199)
        ACCESS  read-only
        STATUS  mandatory
        DESCRIPTION
                "The value of this object defines the route
                associated to this address. This route must exist
                in fcwRouteTable. The authorized values are
                '0..199'. The default value is '255'."
        ::= { fcwZoRoutingEntry 2 }


    fcwZoStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwZoRoutingEntry 3 }


    fcwSbRoutingTable OBJECT-TYPE
        SYNTAX  SEQUENCE OF FcwSbRoutingEntry
        ACCESS  not-accessible
        STATUS  mandatory
        DESCRIPTION
                "This table is the call packets routing table for
                the Subscriber (SB) part of the X121 called
                address."
        ::= { fcWanSwitch 62 }


    fcwSbRoutingEntry OBJECT-TYPE
        SYNTAX  FcwSbRoutingEntry
        ACCESS  not-accessible
        STATUS  mandatory
        DESCRIPTION
                "An entry of fcwSbRoutingTable."
        INDEX   { fcwSbSubscriberNumber,
                  fcwSbRouteId }
        ::= { fcwSbRoutingTable 1 }


        FcwSbRoutingEntry ::=
                SEQUENCE {
                    fcwSbSubscriberNumber
                        OCTET STRING,
                    fcwSbRouteId
                        INTEGER,
                    fcwSbStatus
                        INTEGER
                }


    fcwSbSubscriberNumber OBJECT-TYPE
        SYNTAX  OCTET STRING (SIZE(1))
        ACCESS  read-only
        STATUS  mandatory
        DESCRIPTION
                "The value of this object is the Subscriber (SB)
                part of the X121 called address from the call
                packet to be routed. This address , with a SB
                format as explained below, must contains 2 digits
                (0..9, B).

                The digit 'B' (character '*' on the equipment
                configurator) have special meaning :

                   'B' matches any address. When used it must be
                        the only digit specified (with final
                        completion as explained below). The
                        associated route is used only if the
                        equipment does not find another
                        possibility in this table.

                   There must be only one route for each specified
                        address.

                   Example : If route 1 is specified for SB '12',
                        route 2 for SB 'B', call packets to SB 12
                        are routed on the route 1 and all others
                        are routed on the route 2.

                The value must be completed with 'F' digits for a
                total of 2 digits (here only if the digit 'B' is
                used). The equipment configurator does not need
                final completion. The default value is 'FF'
                meaning 'empty value' (blank value on the
                equipment configurator).


                Address format :

                   Eight digits (0..9) of X121 format are used as
                      the network address numbering plan. This
                      numbering plan has a hierarchical structure
                      :

                      4 digits define the Data Network Identifier
                         Code (DNIC) : DNIC identifies the region
                         to which belongs the equipment,
                      2 digits define the zone (ZO) : ZO
                         identifies the equipment inside the
                         region,
                      2 digits define the subscriber (SB) : SB
                         identifies a subscriber of the equipment.

                   Therefore each subscriber is completely
                      identified by its address of the form DNIC
                      ZO SB and each equipment by its address of
                      the form DNIC ZO."
        ::= { fcwSbRoutingEntry 1 }


    fcwSbRouteId OBJECT-TYPE
        SYNTAX  INTEGER (0..199)
        ACCESS  read-only
        STATUS  mandatory
        DESCRIPTION
                "The value of this object defines the route
                associated to this address. This route must exist
                in fcwRouteTable. The authorized values are
                '0..199'. The default value is '255'."
        ::= { fcwSbRoutingEntry 2 }


    fcwSbStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwSbRoutingEntry 3 }


    fcwServices OBJECT IDENTIFIER ::= { fcWanSwitch 70 }


    fcwSerCompression OBJECT IDENTIFIER ::= { fcwServices 1 }


    fcwSCompModule0CompressedVcCount OBJECT-TYPE
        SYNTAX  INTEGER (0..2048)
        ACCESS  read-write
        STATUS  mandatory
        DESCRIPTION
                "The value of this object defines the maximum
                number of virtual circuits which may be
                simultaneously compressed by the module 0 of the
                equipment. The compression of virtual circuits may
                be enabled at the logical port level. The
                authorized values are '0..2048'. The default value
                is '0'."
        ::= { fcwSerCompression 1 }


    fcwSCompModule1CompressedVcCount OBJECT-TYPE
        SYNTAX  INTEGER (0..2048)
        ACCESS  read-write
        STATUS  mandatory
        DESCRIPTION
                "The value of this object defines the maximum
                number of the virtual channels that may be
                simultaneously compressed by the module 0 of the
                equipment. The authorized values are '0..2048'.
                The default value is '1'."
        ::= { fcwSerCompression 2 }


    fcwSCompModule2CompressedVcCount OBJECT-TYPE
        SYNTAX  INTEGER (0..2048)
        ACCESS  read-write
        STATUS  mandatory
        DESCRIPTION
                "The value of this object defines the maximum
                number of the virtual channels that may be
                simultaneously compressed by the module 0 of the
                equipment. The authorized values are '0..2048'.
                The default value is '2'."
        ::= { fcwSerCompression 3 }


    fcwSCompAlgorithmSelection OBJECT-TYPE
        SYNTAX  INTEGER {
                auto(1),
                v9Compatible(2),
                v10Compatible(3)
                }
        ACCESS  read-write
        STATUS  mandatory
        DESCRIPTION
                "The value of this object which compression
                algorithm is used by the equipment. It can use an
                algorithm compatible to which one used on
                equipment with version 9 software or version 10
                software. It can also choise the right one
                automatically. The default value is 'auto'."
        ::= { fcwSerCompression 4 }


    fcwSerReliableVirtualCircuits OBJECT IDENTIFIER ::= { fcwServices 2 }


    fcwSRvcReliableVcCount OBJECT-TYPE
        SYNTAX  INTEGER (0..255)
        ACCESS  read-write
        STATUS  mandatory
        DESCRIPTION
                "The value of this object defines the maximum
                number of simultaneously reliable virtual circuits
                in the equipment. The reliable virtual circuits
                may be enabled at the logical port level. The
                authorized values are '0..255. The default value
                is '20'."
        ::= { fcwSerReliableVirtualCircuits 1 }


    fcwSRvcFirstDataPacketTimer OBJECT-TYPE
        SYNTAX  INTEGER (1..254)
        ACCESS  read-write
        STATUS  mandatory
        DESCRIPTION
                "The value of this object is the waiting time
                between the call connected packet and the first
                data packet which there is clearing beyond. This
                parameter is pertinent only if the fast select
                facility is used. The authorized values are
                '1..254'. The default value is '12'."
        ::= { fcwSerReliableVirtualCircuits 2 }


    fcwSRvcRestoreOutgoingCallRetryCount OBJECT-TYPE
        SYNTAX  INTEGER (1..254)
        ACCESS  read-write
        STATUS  mandatory
        DESCRIPTION
                "The value of this object indicates how many times
                the equipment will try to send a call packet to
                restore the virtual circuit wich has been
                unintentionnaly cleared. The possible values are :
                '1..254'. The default value is '10'."
        ::= { fcwSerReliableVirtualCircuits 3 }


    fcwSRvcRestoreMinimumRecallTimer OBJECT-TYPE
        SYNTAX  INTEGER (1..254)
        ACCESS  read-write
        STATUS  mandatory
        DESCRIPTION
                "The value of this object specifies the minimum
                recall time (in seconds) between two successive
                calls. The authorized values are '1..254'. The
                default value is '20'."
        ::= { fcwSerReliableVirtualCircuits 4 }


    fcwSRvcRestoreIncomingCallTimer OBJECT-TYPE
        SYNTAX  INTEGER (10..2540)
        ACCESS  read-write
        STATUS  mandatory
        DESCRIPTION
                "The value of this object is the time between a new
                connection request and the reception of the
                corresponding call connected packet which there is
                clearing beyond. The authorized values are
                '10..2540'. The default value is '120'."
        ::= { fcwSerReliableVirtualCircuits 5 }


    fcwSRvcRestoreOutgoingCallDelay OBJECT-TYPE
        SYNTAX  INTEGER (10..2540)
        ACCESS  read-write
        STATUS  mandatory
        DESCRIPTION
                "When it is not possible to restore the network
                connection, the standard forces to not use the
                called reference number during the value of this
                object. The authorized values are '10..2540'. The
                default value is '120'."
        ::= { fcwSerReliableVirtualCircuits 6 }


    fcwSRvcKWindowSize OBJECT-TYPE
        SYNTAX  INTEGER (1..127)
        ACCESS  read-write
        STATUS  mandatory
        DESCRIPTION
                "The value of this object indicates the maximum
                number (K) of sequentially numbered I frames that
                the equipment may have outstanding (i.e..
                unacknowledged) at any given time. The authorized
                values are '1..127'. The default value is '10'."
        ::= { fcwSerReliableVirtualCircuits 7 }


    fcwSRvcFastSelectUse OBJECT-TYPE
        SYNTAX  INTEGER {
                off(1),
                on(2)
                }
        ACCESS  read-write
        STATUS  mandatory
        DESCRIPTION
                "The value of this object specifies whether the
                equipment uses the fast select facility or not.
                The default value is 'onk'."
        ::= { fcwSerReliableVirtualCircuits 8 }


    fcwSRvcOutputMarkers OBJECT-TYPE
        SYNTAX  INTEGER {
                noCheck(1),
                check(2),
                remove(3)
                }
        ACCESS  read-write
        STATUS  mandatory
        DESCRIPTION
                "The value of this object specifies the behaviour
                of the equipment with respect to the outgoing
                facility markers. The authorized values are :

                noCheck : no checking,

                remove : the markers are not transmitted,

                check : according to the following table :

                 ~~~~~~~~~~~~~~~~~~~~~~~~~~~~~~~~~~~~~~~~~~~~~~~~~
                 | packet  |           facility marker           |
                 |         |~~~~~~~~~~~~~~~~~~~~~~~~~~~~~~~~~~~~~~
                 |         |  0000 (1)  |  00FF (2)  |  000F (3) |
                 |~~~~~~~~~|~~~~~~~~~~~~|~~~~~~~~~~~~|~~~~~~~~~~~|
                 |  call   |no checking |clearing (5)|no checking|
                 |~~~~~~~~~|~~~~~~~~~~~~|~~~~~~~~~~~~|~~~~~~~~~~~|
                 |  call   |            |            |           |
                 |connected|clearing (4)|no checking |no checking|
                 |~~~~~~~~~|~~~~~~~~~~~~|~~~~~~~~~~~~|~~~~~~~~~~~|
                 |  clear  |     -      |     -      |no checking|
                 ~~~~~~~~~~~~~~~~~~~~~~~~~~~~~~~~~~~~~~~~~~~~~~~~~
                   (1) : registration codes,
                         non-x25 facilities provided by the
                            network in case of intranetwork calls,
                         non-x25 facilities provided by the
                            network to which the calling DTE is
                            connected in case of internetwork
                            calls
                   (2) : non-x25 facilities provided by the
                            network to which the calling DTE is
                            connected in case of intranetwork
                            calls
                   (3) : CCITT-specified DTE facilities
                   (4) : diagnostic to local equipment = 03 42,
                         diagnostic to remote equipment = 11 42
                   (5) : diagnostic to local equipment = 03 42

                The default value is 'noCheck'."
        ::= { fcwSerReliableVirtualCircuits 9 }


    fcwSRvcConversionAimedPoint OBJECT-TYPE
        SYNTAX  INTEGER {
                off(1),
                on(2)
                }
        ACCESS  read-write
        STATUS  mandatory
        DESCRIPTION
                "The value of this object indicates whether the
                'aimed point' address conversion is enabled or
                not. This conversion consists in making the
                routing process work not with the called address
                from the call packet but with a substituted
                address according to the address conversion table
                (see fcwAddrConvIncomingCallTable). Therefore this
                reduces the number of entries of the routing
                tables if several called addresses are converted
                to same 'aimed point' address. The default value
                is 'off'."
        ::= { fcwSerReliableVirtualCircuits 10 }


    fcwSRvcConversionIncomingCall OBJECT-TYPE
        SYNTAX  INTEGER {
                off(1),
                callingAddress(2),
                calledAddress(3),
                callingAddressAndCalledAddress(4)
                }
        ACCESS  read-write
        STATUS  mandatory
        DESCRIPTION
                "The value of this object indicates which address
                field are converted on an incoming call. The
                authorized values are :
                   off : no address field conversion,
                   callingAddress : conversion of the calling
                        address field according to the contains of
                        fcwAddrConvIncomingCallTable,
                   calledAddress : conversion of the called
                        address field according to the contains of
                        fcwAddrConvIncomingCallTable,
                   callingAddressAndCalledAddress : conversion of
                        the calling and called address fields
                        according to the contains of
                        fcwAddrConvIncomingCallTable.
                The default value is 'off'."
        ::= { fcwSerReliableVirtualCircuits 11 }


    fcwSRvcConversionOutgoingCall OBJECT-TYPE
        SYNTAX  INTEGER {
                off(1),
                callingAddress(2),
                calledAddress(3),
                callingAddressAndCalledAddress(4)
                }
        ACCESS  read-write
        STATUS  mandatory
        DESCRIPTION
                "The value of this object indicates which address
                field are converted on an outgoing call. The
                authorized values are :
                   off : no address field conversion,
                   callingAddress : conversion of the calling
                        address field according to the contains of
                        fcwAddrConvOutgoingCallTable,
                   calledAddress : conversion of the called
                        address field according to the contains of
                        fcwAddrConvOutgoingCallTable,
                   callingAddressAndCalledAddress : conversion of
                        the calling and called address fields
                        according to the contains of
                        fcwAddrConvOutgoingCallTable.
                The default value is 'off'."
        ::= { fcwSerReliableVirtualCircuits 12 }


    fcwSRvcConversionAddressCheck OBJECT-TYPE
        SYNTAX  INTEGER {
                off(1),
                onIncomingCall(2),
                onOutgoingCall(3),
                onIncomingCallAndOutgoingCall(4)
                }
        ACCESS  read-write
        STATUS  mandatory
        DESCRIPTION
                "The value of this object indicates the behaviour
                of the equipment when a requested address
                conversion can not be made because the address is
                not found in the address conversion tables
                (fcwAddrConvIncomingCallTable or
                fcwAddrConvOutgoingCallTable). In this case the
                call will be cleared when 'checking' is enabled.
                The authorized values are :
                   off : no checking,
                   onIncomingCall : checking on incoming calls,
                   onOutgoingCall : checking on outgoing calls,
                   onIcomingCallAndOutgoingCall : checking on
                        incoming and outgoing calls.
                   The default value is 'off'."
        ::= { fcwSerReliableVirtualCircuits 13 }


    fcwSerReselectionX29 OBJECT IDENTIFIER ::= { fcwServices 3 }


    fcwSResLogChannelCount OBJECT-TYPE
        SYNTAX  INTEGER (0..255)
        ACCESS  read-write
        STATUS  mandatory
        DESCRIPTION
                "The value of this object is the number of logical
                Channels. The authorized values are '0..255. The
                default value is '200'."
        ::= { fcwSerReselectionX29 1 }


    fcwSResProtocolIdentifierTransmission OBJECT-TYPE
        SYNTAX  INTEGER {
                off(1),
                on(2)
                }
        ACCESS  read-write
        STATUS  mandatory
        DESCRIPTION
                "The value of this object indicates whether the
                protocol identifier is transmitted or not. The
                default value is 'off'."
        ::= { fcwSerReselectionX29 2 }


    fcwSResConversionAimedPoint OBJECT-TYPE
        SYNTAX  INTEGER {
                off(1),
                on(2)
                }
        ACCESS  read-write
        STATUS  mandatory
        DESCRIPTION
                "The value of this object indicates whether the
                'aimed point' address conversion is enabled or
                not. This conversion consists in making the
                routing process work not with the called address
                from the call packet but with a substituted
                address according to the address conversion table
                (see fcwAddrConvIncomingCallTable). Therefore this
                reduces the number of entries of the routing
                tables if several called addresses are converted
                to same 'aimed point' address. The default value
                is 'off'."
        ::= { fcwSerReselectionX29 10 }


    fcwSResConversionIncomingCall OBJECT-TYPE
        SYNTAX  INTEGER {
                off(1),
                callingAddress(2),
                calledAddress(3),
                callingAddressAndCalledAddress(4)
                }
        ACCESS  read-write
        STATUS  mandatory
        DESCRIPTION
                "The value of this object indicates which address
                field are converted on an incoming call. The
                authorized values are :
                   off : no address field conversion,
                   callingAddress : conversion of the calling
                        address field according to the contains of
                        fcwAddrConvIncomingCallTable,
                   calledAddress : conversion of the called
                        address field according to the contains of
                        fcwAddrConvIncomingCallTable,
                   callingAddressAndCalledAddress : conversion of
                        the calling and called address fields
                        according to the contains of
                        fcwAddrConvIncomingCallTable.
                The default value is 'off'."
        ::= { fcwSerReselectionX29 11 }


    fcwSResConversionOutgoingCall OBJECT-TYPE
        SYNTAX  INTEGER {
                off(1),
                callingAddress(2),
                calledAddress(3),
                callingAddressAndCalledAddress(4)
                }
        ACCESS  read-write
        STATUS  mandatory
        DESCRIPTION
                "The value of this object indicates which address
                field are converted on an outgoing call. The
                authorized values are :
                   off : no address field conversion,
                   callingAddress : conversion of the calling
                        address field according to the contains of
                        fcwAddrConvOutgoingCallTable,
                   calledAddress : conversion of the called
                        address field according to the contains of
                        fcwAddrConvOutgoingCallTable,
                   callingAddressAndCalledAddress : conversion of
                        the calling and called address fields
                        according to the contains of
                        fcwAddrConvOutgoingCallTable.
                The default value is 'off'."
        ::= { fcwSerReselectionX29 12 }


    fcwSResConversionAddressCheck OBJECT-TYPE
        SYNTAX  INTEGER {
                off(1),
                onIncomingCall(2),
                onOutgoingCall(3),
                onIncomingCallAndOutgoingCall(4)
                }
        ACCESS  read-write
        STATUS  mandatory
        DESCRIPTION
                "The value of this object indicates the behaviour
                of the equipment when a requested address
                conversion can not be made because the address is
                not found in the address conversion tables
                (fcwAddrConvIncomingCallTable or
                fcwAddrConvOutgoingCallTable). In this case the
                call will be cleared when 'checking' is enabled.
                The authorized values are :
                   off : no checking,
                   onIncomingCall : checking on incoming calls,
                   onOutgoingCall : checking on outgoing calls,
                   onIcomingCallAndOutgoingCall : checking on
                        incoming and outgoing calls.
                   The default value is 'off'."
        ::= { fcwSerReselectionX29 13 }


    fcwSerDynamicRouting OBJECT IDENTIFIER ::= { fcwServices 4 }


    fcwSDynDynamicRouting OBJECT-TYPE
        SYNTAX  INTEGER {
                off(1),
                on(3)
                }
        ACCESS  read-write
        STATUS  mandatory
        DESCRIPTION
                "Mode de fonctionnement RAD"
        ::= { fcwSerDynamicRouting 1 }


    fcwSDynPassword OBJECT-TYPE
        SYNTAX  DisplayString (SIZE(0..6))
        ACCESS  read-write
        STATUS  mandatory
        DESCRIPTION
                "Mode de passe fonction d'exploitation RAD"
        ::= { fcwSerDynamicRouting 2 }


    fcwSDynNeighborMaxCount OBJECT-TYPE
        SYNTAX  INTEGER (1..250)
        ACCESS  read-write
        STATUS  mandatory
        DESCRIPTION
                "Nb max de LSPDU memorisees"
        ::= { fcwSerDynamicRouting 3 }


    fcwSDynLspAgingTimer OBJECT-TYPE
        SYNTAX  INTEGER (10..2500)
        ACCESS  read-write
        STATUS  mandatory
        DESCRIPTION
                "Duree de stockage d'un LSPDU"
        ::= { fcwSerDynamicRouting 4 }


    fcwSDynLspRetransRequestTimer OBJECT-TYPE
        SYNTAX  INTEGER (10..2500)
        ACCESS  read-write
        STATUS  mandatory
        DESCRIPTION
                "Duree de stockage minimum declanchant une demande
                de mise a jour d'un LSPDU "
        ::= { fcwSerDynamicRouting 5 }


    fcwSDynLspRetransmissionTimer OBJECT-TYPE
        SYNTAX  INTEGER (10..2500)
        ACCESS  read-write
        STATUS  mandatory
        DESCRIPTION
                "Periode de diffusion de la topologie"
        ::= { fcwSerDynamicRouting 6 }


    fcwSDynRouteCalculationTimer OBJECT-TYPE
        SYNTAX  INTEGER (10..2500)
        ACCESS  read-write
        STATUS  mandatory
        DESCRIPTION
                "Periode de calcul des routes"
        ::= { fcwSerDynamicRouting 7 }


    fcwSDynRouteCalculLockingTimer OBJECT-TYPE
        SYNTAX  INTEGER (10..2500)
        ACCESS  read-write
        STATUS  mandatory
        DESCRIPTION
                "Duree de verrouillage du calcul des routes"
        ::= { fcwSerDynamicRouting 8 }


    fcwSerClearAnalysisTable OBJECT-TYPE
        SYNTAX  SEQUENCE OF FcwSerClearAnalysisEntry
        ACCESS  not-accessible
        STATUS  mandatory
        DESCRIPTION
                ""
        ::= { fcwServices 5 }


    fcwSerClearAnalysisEntry OBJECT-TYPE
        SYNTAX  FcwSerClearAnalysisEntry
        ACCESS  not-accessible
        STATUS  mandatory
        DESCRIPTION
                "An entry of fcwSerClearAnalysisTable."
        INDEX   { fcwSClearAnalysId }
        ::= { fcwSerClearAnalysisTable 1 }


        FcwSerClearAnalysisEntry ::=
                SEQUENCE {
                    fcwSClearAnalysId
                        INTEGER,
                    fcwSClearAnalysStatus
                        INTEGER,
                    fcwSClearAnalysCause
                        DisplayString,
                    fcwSClearAnalysDiag
                        DisplayString
                }


    fcwSClearAnalysId OBJECT-TYPE
        SYNTAX  INTEGER (0..17)
        ACCESS  read-only
        STATUS  mandatory
        DESCRIPTION
                "The value of this object identifies one and only
                one entry in the table (index)"
        ::= { fcwSerClearAnalysisEntry 1 }


    fcwSClearAnalysStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fcwSerClearAnalysisEntry 2 }


    fcwSClearAnalysCause OBJECT-TYPE
        SYNTAX  DisplayString (SIZE(0..2))
        ACCESS  read-write
        STATUS  mandatory
        DESCRIPTION
                "The value of this object indicates which cause(s)
                is taken into account in case of clear indication.
                Possible values are : 
                   00..FF
                   TT (all DTE clear indications)
                   TC (all DCE clear indications)
                   * (any clearing cause)"
        ::= { fcwSerClearAnalysisEntry 3 }


    fcwSClearAnalysDiag OBJECT-TYPE
        SYNTAX  DisplayString (SIZE(0..2))
        ACCESS  read-write
        STATUS  mandatory
        DESCRIPTION
                "The value of this object indicates which
                diagnostic is taken into account in case of clear
                indication.
                Possible values are :
                   00..FF
                   * (any clearing diagnostic)"
        ::= { fcwSerClearAnalysisEntry 4 }


    fcwSerQOSX25 OBJECT IDENTIFIER ::= { fcwServices 10 }


    fcwSQOSX25Table OBJECT-TYPE
        SYNTAX  SEQUENCE OF FcwSQOSX25Entry
        ACCESS  not-accessible
        STATUS  mandatory
        DESCRIPTION
                ""
        ::= { fcwSerQOSX25 1 }


    fcwSQOSX25Entry OBJECT-TYPE
        SYNTAX  FcwSQOSX25Entry
        ACCESS  not-accessible
        STATUS  mandatory
        DESCRIPTION
                "An entry of fcwSQOSX25Table."
        INDEX   { fcwSQOSX25CalledAddress,
                  fcwSQOSX25CallingAddress,
                  fcwSQOSX25CUDProfileId }
        ::= { fcwSQOSX25Table 1 }


        FcwSQOSX25Entry ::=
                SEQUENCE {
                    fcwSQOSX25CalledAddress
                        OCTET STRING,
                    fcwSQOSX25CallingAddress
                        OCTET STRING,
                    fcwSQOSX25CUDProfileId
                        INTEGER,
                    fcwSQOSX25Status
                        INTEGER,
                    fcwSQOSX25PriorityLevel
                        INTEGER,
                    fcwSQOSX25QOSProfileId
                        INTEGER,
                    fcwSQOSX25Cos
                        INTEGER,
                    fcwSQOSX25TrafficManagementStrategy
                        INTEGER
                }


    fcwSQOSX25CalledAddress OBJECT-TYPE
        SYNTAX  OCTET STRING (SIZE(8))
        ACCESS  read-only
        STATUS  mandatory
        DESCRIPTION
                "Called Address"
        ::= { fcwSQOSX25Entry 1 }


    fcwSQOSX25CallingAddress OBJECT-TYPE
        SYNTAX  OCTET STRING (SIZE(8))
        ACCESS  read-only
        STATUS  mandatory
        DESCRIPTION
                "Calling Address"
        ::= { fcwSQOSX25Entry 2 }


    fcwSQOSX25CUDProfileId OBJECT-TYPE
        SYNTAX  INTEGER (1..100)
        ACCESS  read-only
        STATUS  mandatory
        DESCRIPTION
                "CUD Profile Id"
        ::= { fcwSQOSX25Entry 3 }


    fcwSQOSX25Status OBJECT-TYPE
        SYNTAX  INTEGER {
                valid(1),
                invalid(2)
                }
        ACCESS  read-write
        STATUS  mandatory
        DESCRIPTION
                "Status"
        ::= { fcwSQOSX25Entry 4 }


    fcwSQOSX25PriorityLevel OBJECT-TYPE
        SYNTAX  INTEGER (1..10)
        ACCESS  read-write
        STATUS  mandatory
        DESCRIPTION
                "Priority Level"
        ::= { fcwSQOSX25Entry 5 }


    fcwSQOSX25QOSProfileId OBJECT-TYPE
        SYNTAX  INTEGER (1..100)
        ACCESS  read-write
        STATUS  mandatory
        DESCRIPTION
                "QOS Profile Id"
        ::= { fcwSQOSX25Entry 6 }


    fcwSQOSX25Cos OBJECT-TYPE
        SYNTAX  INTEGER {
                ubr(3),
                vbr(1),
                vbr-rt(2)
                }
        ACCESS  read-write
        STATUS  mandatory
        DESCRIPTION
                "COS"
        ::= { fcwSQOSX25Entry 7 }


    fcwSQOSX25TrafficManagementStrategy OBJECT-TYPE
        SYNTAX  INTEGER {
                discardButNotDelay(1),
                delayButNotDiscard-Bc(3),
                delayButNotDiscard-BcBe(4)
                }
        ACCESS  read-write
        STATUS  mandatory
        DESCRIPTION
                "Traffic Management Strategy"
        ::= { fcwSQOSX25Entry 8 }


    fcwSCUDProfilesTable OBJECT-TYPE
        SYNTAX  SEQUENCE OF FcwSCUDProfilesEntry
        ACCESS  not-accessible
        STATUS  mandatory
        DESCRIPTION
                ""
        ::= { fcwSerQOSX25 2 }


    fcwSCUDProfilesEntry OBJECT-TYPE
        SYNTAX  FcwSCUDProfilesEntry
        ACCESS  not-accessible
        STATUS  mandatory
        DESCRIPTION
                "An entry of fcwSCUDProfilesTable."
        INDEX   { fcwSCUDProfilesId }
        ::= { fcwSCUDProfilesTable 1 }


        FcwSCUDProfilesEntry ::=
                SEQUENCE {
                    fcwSCUDProfilesId
                        INTEGER,
                    fcwSCUDProfilesStatus
                        INTEGER,
                    fcwSCUDProfilesCUD
                        OCTET STRING
                }


    fcwSCUDProfilesId OBJECT-TYPE
        SYNTAX  INTEGER (1..100)
        ACCESS  read-only
        STATUS  mandatory
        DESCRIPTION
                "CUD Profile Id"
        ::= { fcwSCUDProfilesEntry 1 }


    fcwSCUDProfilesStatus OBJECT-TYPE
        SYNTAX  INTEGER {
                valid(1),
                invalid(2)
                }
        ACCESS  read-write
        STATUS  mandatory
        DESCRIPTION
                "Status"
        ::= { fcwSCUDProfilesEntry 2 }


    fcwSCUDProfilesCUD OBJECT-TYPE
        SYNTAX  OCTET STRING (SIZE(13))
        ACCESS  read-write
        STATUS  mandatory
        DESCRIPTION
                "Donnees d'appel hexa CUD"
        ::= { fcwSCUDProfilesEntry 3 }


    fcwSQOSProfilesTable OBJECT-TYPE
        SYNTAX  SEQUENCE OF FcwSQOSProfilesEntry
        ACCESS  not-accessible
        STATUS  mandatory
        DESCRIPTION
                ""
        ::= { fcwSerQOSX25 3 }


    fcwSQOSProfilesEntry OBJECT-TYPE
        SYNTAX  FcwSQOSProfilesEntry
        ACCESS  not-accessible
        STATUS  mandatory
        DESCRIPTION
                "An entry of fcwSQOSProfilesTable."
        INDEX   { fcwSQOSProfilesId }
        ::= { fcwSQOSProfilesTable 1 }


        FcwSQOSProfilesEntry ::=
                SEQUENCE {
                    fcwSQOSProfilesId
                        INTEGER,
                    fcwSQOSProfilesStatus
                        INTEGER,
                    fcwSQOSProfilesCIR
                        INTEGER,
                    fcwSQOSProfilesCIRmin
                        INTEGER,
                    fcwSQOSProfilesBc
                        INTEGER,
                    fcwSQOSProfilesBe
                        INTEGER
                }


    fcwSQOSProfilesId OBJECT-TYPE
        SYNTAX  INTEGER (1..100)
        ACCESS  read-only
        STATUS  mandatory
        DESCRIPTION
                "QOS Profile Id"
        ::= { fcwSQOSProfilesEntry 1 }


    fcwSQOSProfilesStatus OBJECT-TYPE
        SYNTAX  INTEGER {
                valid(1),
                invalid(2)
                }
        ACCESS  read-write
        STATUS  mandatory
        DESCRIPTION
                "Status"
        ::= { fcwSQOSProfilesEntry 2 }


    fcwSQOSProfilesCIR OBJECT-TYPE
        SYNTAX  INTEGER (0..2048000)
        ACCESS  read-write
        STATUS  mandatory
        DESCRIPTION
                "CIR"
        ::= { fcwSQOSProfilesEntry 3 }


    fcwSQOSProfilesCIRmin OBJECT-TYPE
        SYNTAX  INTEGER (0..2048000)
        ACCESS  read-write
        STATUS  mandatory
        DESCRIPTION
                "CIRmin"
        ::= { fcwSQOSProfilesEntry 4 }


    fcwSQOSProfilesBc OBJECT-TYPE
        SYNTAX  INTEGER (0..2048000)
        ACCESS  read-write
        STATUS  mandatory
        DESCRIPTION
                "Bc"
        ::= { fcwSQOSProfilesEntry 5 }


    fcwSQOSProfilesBe OBJECT-TYPE
        SYNTAX  INTEGER (0..2048000)
        ACCESS  read-write
        STATUS  mandatory
        DESCRIPTION
                "Be"
        ::= { fcwSQOSProfilesEntry 6 }


    fcVirtualPorts OBJECT IDENTIFIER ::= { frxConfig 30 }


    fcvVirtualPortTable OBJECT-TYPE
        SYNTAX  SEQUENCE OF FcvVirtualPortEntry
        ACCESS  not-accessible
        STATUS  mandatory
        DESCRIPTION
                "This table defines the virtual ports.

                Through a virtual port the bridge and the IP, IPX
                and CLNP routers can communicate with bridges and
                routers taking place inside a particular virtual
                network. These communications may use a Local Area
                Network (LAN), namely the virtual network matches
                the LAN, or Wide Area Networks (WAN), namely the
                virtual network matches a group of remote bridges
                or routers.

                Each module of the equipment has its own virtual
                ports. The module 0 can enable bridge forwarding,
                IP (Internet Protocol) routing, IPX (Internetwork
                Packet eXchange : Novell protocol) routing and
                CLNP (ConnectionLess Network Protocol) routing.
                The modules 1 and 2 can only act as IP host. So
                each of these two modules needs one remote VP when
                its SNMP agent must exchange SNMP datas with an
                SNMP manager.

                Set any writable object(s) of this table to valid
                value(s) with a new index value to create an entry
                (the objects of the entry not present in this SET
                REQUEST will take their default values). Set
                fcvVpStatus to 'invalid' to delete an entry."
        ::= { fcVirtualPorts 1 }


    fcvVirtualPortEntry OBJECT-TYPE
        SYNTAX  FcvVirtualPortEntry
        ACCESS  not-accessible
        STATUS  mandatory
        DESCRIPTION
                "An entry of fcvVirtualPortTable."
        INDEX   { fcvVpVirtualPortId }
        ::= { fcvVirtualPortTable 1 }


        FcvVirtualPortEntry ::=
                SEQUENCE {
                    fcvVpVirtualPortId
                        INTEGER,
                    fcvVpStatus
                        INTEGER,
                    fcvVpType
                        INTEGER,
                    fcvVpModuleId
                        INTEGER
                }


    fcvVpVirtualPortId OBJECT-TYPE
        SYNTAX  INTEGER (0..11)
        ACCESS  read-only
        STATUS  mandatory
        DESCRIPTION
                "The value of this object identifies one and only
                one virtual port. Through a virtual port the
                bridge and the IP, IPX and CLNP routers can
                communicate with bridges and routers taking place
                inside a particular virtual network. These
                communications may use a Local Area Network (LAN),
                namely the virtual network matches the LAN, or
                Wide Area Networks (WAN), namely the virtual
                network matches a group of remote bridges or
                routers.

                This is a decimal integer in the range 0 to 11."
        ::= { fcvVirtualPortEntry 1 }


    fcvVpStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcvVirtualPortEntry 2 }


    fcvVpType OBJECT-TYPE
        SYNTAX  INTEGER {
                local(1),
                remote(2)
                }
        ACCESS  read-write
        STATUS  mandatory
        DESCRIPTION
                "The value of this object indicates whether this
                virtual port is: 
                   local : the virtual network is a Local Area
                        Network (LAN),
                   or remote : the virtual network is a group of
                        remote equipments which may be reached
                        through Wide Area Networks (WAN).

                The default value is 'remote'."
        ::= { fcvVirtualPortEntry 3 }


    fcvVpModuleId OBJECT-TYPE
        SYNTAX  INTEGER (0..2)
        ACCESS  read-write
        STATUS  mandatory
        DESCRIPTION
                "The value of this object indicates the module of
                the equipment to which this virtual port belongs
                to.

                Each module of the equipment has its own virtual
                ports. The module 0 can enable bridge forwarding,
                IP (Internet Protocol) routing, IPX (Internetwork
                Packet eXchange : Novell protocol) routing and
                CLNP (ConnectionLess Network Protocol) routing.
                The modules 1 and 2 can only act as IP host. So
                each of these two modules needs one remote VP when
                its SNMP agent must exchange SNMP datas with an
                SNMP manager.

                This is a decimal integer in the range 0 to 2.
                The default value is '0'."
        ::= { fcvVirtualPortEntry 4 }


    fcvLocalVirtualPorts OBJECT IDENTIFIER ::= { fcVirtualPorts 10 }


    fcvLocalVirtualPortTable OBJECT-TYPE
        SYNTAX  SEQUENCE OF FcvLocalVirtualPortEntry
        ACCESS  not-accessible
        STATUS  mandatory
        DESCRIPTION
                "This table defines the characteristics of the
                local virtual ports.

                It is not possible to add or delete an entry of
                this table (each entry corresponds, in
                fcvVirtualPortTable, to one instance of fcvVpType
                equal to 'local')."
        ::= { fcvLocalVirtualPorts 1 }


    fcvLocalVirtualPortEntry OBJECT-TYPE
        SYNTAX  FcvLocalVirtualPortEntry
        ACCESS  not-accessible
        STATUS  mandatory
        DESCRIPTION
                "An entry of fcvLocalVirtualPortTable."
        INDEX   { fcvLvpVirtualPortId }
        ::= { fcvLocalVirtualPortTable 1 }


        FcvLocalVirtualPortEntry ::=
                SEQUENCE {
                    fcvLvpVirtualPortId
                        INTEGER,
                    fcvLvpLogicalPortId
                        INTEGER
                }


    fcvLvpVirtualPortId OBJECT-TYPE
        SYNTAX  INTEGER (0..11)
        ACCESS  read-only
        STATUS  mandatory
        DESCRIPTION
                "The value of this object identifies one and only
                one local virtual port. Each local virtual port
                corresponds, in fcvVirtualPortTable, to one
                instance of fcvVpType equal to 'local'.

                This is a decimal integer in the range 0 to 11."
        ::= { fcvLocalVirtualPortEntry 1 }


    fcvLvpLogicalPortId OBJECT-TYPE
        SYNTAX  INTEGER (0..181)
        ACCESS  read-write
        STATUS  mandatory
        DESCRIPTION
                "The value of this object indicates the logical
                port to which this local virtual port is
                associated. This logical port must exist in
                fclEthernetTable.

                This is a decimal integer in the range 0 to 131.
                The default value is '255' meaning 'empty value'
                (blank value on the equipment configurator)."
        ::= { fcvLocalVirtualPortEntry 2 }


    fcvLvpFiltering OBJECT IDENTIFIER ::= { fcvLocalVirtualPorts 10 }


    fcvLvpFltConditionTable OBJECT-TYPE
        SYNTAX  SEQUENCE OF FcvLvpFltConditionEntry
        ACCESS  not-accessible
        STATUS  mandatory
        DESCRIPTION
                "This table defines the conditions which may be
                used to make filters in fcvLvpFltFilterTable.

                Set any writable object(s) of this table to valid
                value(s) with a new index value to create an entry
                (the objects of the entry not present in this SET
                REQUEST will take their default values). Set
                fcvLvpFltCondStatus to 'invalid' to delete an
                entry."
        ::= { fcvLvpFiltering 1 }


    fcvLvpFltConditionEntry OBJECT-TYPE
        SYNTAX  FcvLvpFltConditionEntry
        ACCESS  not-accessible
        STATUS  mandatory
        DESCRIPTION
                "An entry of fcvLvpFltConditionTable."
        INDEX   { fcvLvpFltCondConditionId }
        ::= { fcvLvpFltConditionTable 1 }


        FcvLvpFltConditionEntry ::=
                SEQUENCE {
                    fcvLvpFltCondConditionId
                        INTEGER,
                    fcvLvpFltCondStatus
                        INTEGER,
                    fcvLvpFltCondOffset
                        INTEGER,
                    fcvLvpFltCondMask
                        OCTET STRING,
                    fcvLvpFltCondValue
                        OCTET STRING
                }


    fcvLvpFltCondConditionId OBJECT-TYPE
        SYNTAX  INTEGER (0..99)
        ACCESS  read-only
        STATUS  mandatory
        DESCRIPTION
                "The value of this object identifies one and only
                one condition. This condition identifier is used
                in fcvFltFilterTable to make filters.

                This is a decimal integer in the range 0 to 99."
        ::= { fcvLvpFltConditionEntry 1 }


    fcvLvpFltCondStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcvLvpFltConditionEntry 2 }


    fcvLvpFltCondOffset OBJECT-TYPE
        SYNTAX  INTEGER (0..1513)
        ACCESS  read-write
        STATUS  mandatory
        DESCRIPTION
                "The value of this object selects the four bytes as
                of which are applied the mask defined by
                fcvLvpFltCondMask and the value defined by
                fcvLvpFltCondValue.

                   Examples :
                      Offset at MAC level :
                         Destination MAC address (6 bytes): 0
                         Source MAC address (6 bytes) : 6
                         PID field (2 bytes) : 12
                      Offset at IP level with Ethernet
                      encapsulation :
                         Protocol (1 byte): 23
                         Source IP address (4 bytes): 26
                         Destination IP address (4 bytes): 30

                This is a decimal integer in the range 0 to 1513.
                The default value is '0'."
        ::= { fcvLvpFltConditionEntry 3 }


    fcvLvpFltCondMask OBJECT-TYPE
        SYNTAX  OCTET STRING (SIZE(4))
        ACCESS  read-write
        STATUS  mandatory
        DESCRIPTION
                "The value of this object defines the mask
                indicating the bits of the four bytes selected by
                fcvLvpFltCondOffset which are to be compared with
                the bits of the four bytes defined by
                fcvLvpFltCondValue.
                This is a four-bytes octet string with 8 digits in
                the range 0 to F,
                The default value is 'FF FF FF FF'."
        ::= { fcvLvpFltConditionEntry 4 }


    fcvLvpFltCondValue OBJECT-TYPE
        SYNTAX  OCTET STRING (SIZE(4))
        ACCESS  read-write
        STATUS  mandatory
        DESCRIPTION
                "The value of this object defines the values of the
                bits with which are compared, according to the
                mask defined by fcvLvpFltCondMask, the bits of the
                four bytes selected by fcvLvpFltCondOffset.
                This is a four-bytes octet string with 8 digits in
                the range 0 to F,
                The default value is 'FF FF FF FF'."
        ::= { fcvLvpFltConditionEntry 5 }


    fcvLvpFltFilterTable OBJECT-TYPE
        SYNTAX  SEQUENCE OF FcvLvpFltFilterEntry
        ACCESS  not-accessible
        STATUS  mandatory
        DESCRIPTION
                "This table defines the filters which may be used
                in the filtering table (fcvLvpFltFilteringTable).
                One filter is a combination of up to three
                conditions from fcvLvpFltConditionTable.

                Set any writable object(s) of this table to valid
                value(s) with a new index value to create an entry
                (the objects of the entry not present in this SET
                REQUEST will take their default values). Set
                fcvLvpFltFilterStatus to 'invalid' to delete an
                entry."
        ::= { fcvLvpFiltering 2 }


    fcvLvpFltFilterEntry OBJECT-TYPE
        SYNTAX  FcvLvpFltFilterEntry
        ACCESS  not-accessible
        STATUS  mandatory
        DESCRIPTION
                "An entry of fcvLvpFltFilterTable."
        INDEX   { fcvLvpFltFilterId }
        ::= { fcvLvpFltFilterTable 1 }


        FcvLvpFltFilterEntry ::=
                SEQUENCE {
                    fcvLvpFltFilterId
                        INTEGER,
                    fcvLvpFltFilterStatus
                        INTEGER,
                    fcvLvpFltFilterCondition1Id
                        INTEGER,
                    fcvLvpFltFilterCondition2Id
                        INTEGER,
                    fcvLvpFltFilterCondition3Id
                        INTEGER
                }


    fcvLvpFltFilterId OBJECT-TYPE
        SYNTAX  INTEGER (0..199)
        ACCESS  read-only
        STATUS  mandatory
        DESCRIPTION
                "The value of this object identifies one and only
                one filter. This filter is a combination of one,
                two or three conditions defined in
                fcvLvpFltConditionTable. A filter selects the
                received frames which simultaneously verify those
                of the three conditions which are actually used
                for this filter.

                When several filters are simultaneously used on
                the same virtual port, the equipment analyses them
                in the incremental order of this filter identifier
                until whether the current frame is selected by one
                of these filters or all of them are analysed. So
                the numbering order must be done with a particular
                attention.

                This is a decimal integer in the range 0 to 199."
        ::= { fcvLvpFltFilterEntry 1 }


    fcvLvpFltFilterStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcvLvpFltFilterEntry 2 }


    fcvLvpFltFilterCondition1Id OBJECT-TYPE
        SYNTAX  INTEGER (0..199)
        ACCESS  read-write
        STATUS  mandatory
        DESCRIPTION
                "The value of this object specifies a first
                condition used by this filter. This condition must
                exist in fcvLvpFltConditionTable.

                Important : by convention, the condition
                identifier increased by 100 allows the opposite
                condition to be applied : the received frames not
                verifying this condition are then selected..

                This is a decimal integer in the range 0 to 199.
                The default value is '255' meaning 'empty value'
                (blank value on the equipment configurator)."
        ::= { fcvLvpFltFilterEntry 3 }


    fcvLvpFltFilterCondition2Id OBJECT-TYPE
        SYNTAX  INTEGER (0..199)
        ACCESS  read-write
        STATUS  mandatory
        DESCRIPTION
                "The value of this object specifies a second
                condition used by this filter. This condition must
                exist in fcvLvpFltConditionTable.

                Important : by convention, the condition
                identifier increased by 100 allows the opposite
                condition to be applied : the received frames not
                verifying this condition are then selected..

                This is a decimal integer in the range 0 to 199.
                The default value is '255' meaning 'empty value'
                (blank value on the equipment configurator)."
        ::= { fcvLvpFltFilterEntry 4 }


    fcvLvpFltFilterCondition3Id OBJECT-TYPE
        SYNTAX  INTEGER (0..199)
        ACCESS  read-write
        STATUS  mandatory
        DESCRIPTION
                "The value of this object specifies a third
                condition used by this filter. This condition must
                exist in fcvLvpFltConditionTable.

                Important : by convention, the condition
                identifier increased by 100 allows the opposite
                condition to be applied : the received frames not
                verifying this condition are then selected..

                This is a decimal integer in the range 0 to 199.
                The default value is '255' meaning 'empty value'
                (blank value on the equipment configurator)."
        ::= { fcvLvpFltFilterEntry 5 }


    fcvLvpFltFilteringTable OBJECT-TYPE
        SYNTAX  SEQUENCE OF FcvLvpFltFilteringEntry
        ACCESS  not-accessible
        STATUS  mandatory
        DESCRIPTION
                "This table is the filtering table. It defines
                which filters are used by each virtual port to
                select the frames to which is applied the
                reject/accept decision. By default, if no filter
                has been configured or if the frame is not
                selected by any filter, it is accepted.

                Set any writable object(s) of this table to valid
                value(s) with a new index value to create an entry
                (the objects of the entry not present in this SET
                REQUEST will take their default values). Set
                fcvLvpFltFilteringStatus to 'invalid' to delete an
                entry."
        ::= { fcvLvpFiltering 3 }


    fcvLvpFltFilteringEntry OBJECT-TYPE
        SYNTAX  FcvLvpFltFilteringEntry
        ACCESS  not-accessible
        STATUS  mandatory
        DESCRIPTION
                "An entry of fcvLvpFltFilteringTable."
        INDEX   { fcvLvpFltFilteringVirtualPortId,
                  fcvLvpFltFilteringFilterId }
        ::= { fcvLvpFltFilteringTable 1 }


        FcvLvpFltFilteringEntry ::=
                SEQUENCE {
                    fcvLvpFltFilteringVirtualPortId
                        INTEGER,
                    fcvLvpFltFilteringFilterId
                        INTEGER,
                    fcvLvpFltFilteringStatus
                        INTEGER,
                    fcvLvpFltFilteringType
                        INTEGER
                }


    fcvLvpFltFilteringVirtualPortId OBJECT-TYPE
        SYNTAX  INTEGER (0..11)
        ACCESS  read-only
        STATUS  mandatory
        DESCRIPTION
                "The value of this object identifies one and only
                one local virtual port. This local virtual port
                must exist in fcvLocalVirtualPortTable.

                Each local virtual port may use several filters :
                the equipment analyses them in the incremental
                order of the filter identifier until whether the
                current frame is selected by one of these filters
                or all of them are analysed.

                This is a decimal integer in the range 0 to 11."
        ::= { fcvLvpFltFilteringEntry 1 }


    fcvLvpFltFilteringFilterId OBJECT-TYPE
        SYNTAX  INTEGER (0..200)
        ACCESS  read-only
        STATUS  mandatory
        DESCRIPTION
                "The value of this object identifies one filter
                used by this local virtual port. This filter must
                exist in fcvFltFilterTable.

                When several filters are simultaneously used on
                the same virtual port, the equipment analyses them
                in the incremental order of this filter
                identifier. So the numbering order must be done
                with a particular attention.

                Important : , the value 200 designates a special
                filter grouping all the frames received by this VP
                which were not selected by the other filters
                applied to this VP. This special filter is the
                last analysed filter for this VP.

                This filtering process concerns all the traffic
                received on one of the IP, IPX or CNLP routers or
                bridge whereas the filtering described in
                fciFlowTable is made only at the IP level.

                This is a decimal integer in the range 0 to 200."
        ::= { fcvLvpFltFilteringEntry 2 }


    fcvLvpFltFilteringStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcvLvpFltFilteringEntry 3 }


    fcvLvpFltFilteringType OBJECT-TYPE
        SYNTAX  INTEGER {
                deny(1),
                permit(2)
                }
        ACCESS  read-write
        STATUS  mandatory
        DESCRIPTION
                "The value of this object specifies whether the
                frames selected by the filter are rejected or
                accepted :
                   deny : the frames selected by the filter are
                        rejected, therefore the frames not
                        selected are accepted,
                   permit : the frames selected by the filter are
                        accepted, therefore the frames not
                        selected are rejected.

                The default value is 'deny'."
        ::= { fcvLvpFltFilteringEntry 4 }


    fcvRemoteVirtualPorts OBJECT IDENTIFIER ::= { fcVirtualPorts 20 }


    fcvRvpCompression OBJECT-TYPE
        SYNTAX  INTEGER {
                off(1),
                networkToSubscriber(2),
                subscriberToNetwork(3),
                bothway(4)
                }
        ACCESS  read-write
        STATUS  mandatory
        DESCRIPTION
                "For all the connections described in
                fcvRvpConnectionTable, the value of this object
                indicates the compression enabling for each
                direction :
                   off : compression is disabled,
                   networkToSubscriber : compression is enabled
                        for the flow from the remote peer to the
                        equipment,
                   subscriberToNetwork : compression is enabled
                        for the flow from the equipment to the
                        remote peer,
                   bothway : compression is enabled for the two
                        flows from and to the equipment.

                The default value is 'off'."
        ::= { fcvRemoteVirtualPorts 1 }


    fcvRvpCompressNegotiation OBJECT-TYPE
        SYNTAX  INTEGER {
                off(1),
                onOptionalCompression(2),
                onMandatoryCompression(3)
                }
        ACCESS  read-write
        STATUS  mandatory
        DESCRIPTION
                "The value of this object indicates, when the
                compression is active, whether the compression
                facility is negociated or not and, if negociated,
                the optional/mandatory status :
                   off : negociation is disabled,
                   onOptionalCompression : negociation is enabled
                        and compression is optional,
                   onMandatoryCompression : negociation is enabled
                        and compression is mandatory.

                The default value is 'off'."
        ::= { fcvRemoteVirtualPorts 2 }


    fcvRvpCompressScrambling OBJECT-TYPE
        SYNTAX  INTEGER {
                off(1),
                on(2)
                }
        ACCESS  read-write
        STATUS  mandatory
        DESCRIPTION
                "The value of this object indicates, when the
                compression is active, whether the scrambling is
                enabled or not. @
                The default value is 'off'."
        ::= { fcvRemoteVirtualPorts 3 }


    fcvRvpCompressMultiPacketsTimer OBJECT-TYPE
        SYNTAX  INTEGER (0..1500)
        ACCESS  read-write
        STATUS  mandatory
        DESCRIPTION
                "The value of this object is the multi-packets
                timer in milliseconds. When the compression is
                active, the multi-packets function is specified in
                order to reduce the number of single packets
                (i.e., without 'More Data mark' = bit M set to 0)
                transmitted to the remote peer by grouping several
                packets in an only one compressed output packet.

                The value 0 disables this function (i.e., each
                single packet is individually compressed and
                sent). So to enable this function this timer must
                be different from 0 on both the local equipment
                and the remote peer (even when the compression
                direction is set to 'subscriberToNetwork' or
                'subscriberToNetwork').

                This timer starts when the equipment begins to
                fill a new compressed output packet and it is
                normally stopped when this packet is sent. When
                this timer runs out the equipment sends this
                compressed packet even if it is not full.

                This is a decimal integer in the range 0 to 1500
                by step of 100.
                The default value is '0'."
        ::= { fcvRemoteVirtualPorts 4 }


    fcvRvpReliableVirtualCircuit OBJECT-TYPE
        SYNTAX  INTEGER {
                off(1),
                on(2)
                }
        ACCESS  read-write
        STATUS  mandatory
        DESCRIPTION
                "For all the connections described in
                fcvRvpConnectionTable, the value of this object
                indicates whether the Reliable Virtual Circuit
                (RVC) service is enabled or not :
                   off : no RVC, the VCs are considered as normal
                        VCs, no particular processing,
                   on : all calls transmitted by the subscriber
                        establish RVCs, it is also possible to
                        receive calls with RVC option.

                The default value is 'off'."
        ::= { fcvRemoteVirtualPorts 5 }


    fcvRvpBe OBJECT-TYPE
        SYNTAX  INTEGER (0..2048000)
        ACCESS  read-write
        STATUS  mandatory
        DESCRIPTION
                "Entrant BE"
        ::= { fcvRemoteVirtualPorts 6 }


    fcvRvpConversionAimedPoint OBJECT-TYPE
        SYNTAX  INTEGER {
                off(1),
                on(2)
                }
        ACCESS  read-write
        STATUS  mandatory
        DESCRIPTION
                "Conversion adresse : point vise"
        ::= { fcvRemoteVirtualPorts 7 }


    fcvRvpConversionIncomingCall OBJECT-TYPE
        SYNTAX  INTEGER {
                off(1),
                callingAddress(2),
                calledAddress(3),
                callingAddressAndCalledAddress(4)
                }
        ACCESS  read-write
        STATUS  mandatory
        DESCRIPTION
                "Conversion d'adresse sur appel entrant"
        ::= { fcvRemoteVirtualPorts 8 }


    fcvRvpConversionOutgoingCall OBJECT-TYPE
        SYNTAX  INTEGER {
                off(1),
                callingAddress(2),
                calledAddress(3),
                callingAddressAndCalledAddress(4)
                }
        ACCESS  read-write
        STATUS  mandatory
        DESCRIPTION
                "Conversion adresse sur appel sortant"
        ::= { fcvRemoteVirtualPorts 9 }


    fcvRvpConversionAddressCheck OBJECT-TYPE
        SYNTAX  INTEGER {
                off(1),
                onIncomingCall(2),
                onOutgoingCall(3),
                onIncomingCallAndOutgoingCall(4)
                }
        ACCESS  read-write
        STATUS  mandatory
        DESCRIPTION
                "Conversion adresse : controle de la presence dans
                les tables de conversion"
        ::= { fcvRemoteVirtualPorts 10 }


    fcvRvpConvMultiCalledAddrInCall OBJECT-TYPE
        SYNTAX  INTEGER (1..99)
        ACCESS  read-write
        STATUS  mandatory
        DESCRIPTION
                "Numero d'identification pour conversion d'adresse
                d'appele multi-criteres en entree"
        ::= { fcvRemoteVirtualPorts 11 }


    fcvRvpConvMultiCallingAddrInCall OBJECT-TYPE
        SYNTAX  INTEGER (1..99)
        ACCESS  read-write
        STATUS  mandatory
        DESCRIPTION
                "Numero d'identification pour conversion d'adresse
                d'appelant multi-criteres en entree"
        ::= { fcvRemoteVirtualPorts 12 }


    fcvRvpConvMultiCalledAddrOutCall OBJECT-TYPE
        SYNTAX  INTEGER (1..99)
        ACCESS  read-write
        STATUS  mandatory
        DESCRIPTION
                "Numero d'identification pour conversion d'adresse
                d'appele multi-criteres en sortie"
        ::= { fcvRemoteVirtualPorts 13 }


    fcvRvpConvMultiCallingAddrOutCall OBJECT-TYPE
        SYNTAX  INTEGER (1..99)
        ACCESS  read-write
        STATUS  mandatory
        DESCRIPTION
                "Numero d'identification pour conversion d'adresse
                d'appelant multi-criteres en sortie"
        ::= { fcvRemoteVirtualPorts 14 }


    fcvRvpCallAcceptwithReverseCharging OBJECT-TYPE
        SYNTAX  INTEGER {
                no(1),
                yes(2)
                }
        ACCESS  read-write
        STATUS  mandatory
        DESCRIPTION
                "Acceptation appel avec TAD"
        ::= { fcvRemoteVirtualPorts 15 }


    fcvRvpCos OBJECT-TYPE
        SYNTAX  INTEGER {
                ubr(3),
                vbr(1)
                }
        ACCESS  read-write
        STATUS  mandatory
        DESCRIPTION
                "For all the connections described in
                fcvRvpConnectionTable, the value of this object
                indicates the Class Of Service (COS) desired on a
                Frame Relay network. This object is meaningless if
                the call is established on another transport
                network.
                   ubr : undefined bit rate,
                   vbr : variable bit rate.

                The default value is 'ubr'."
        ::= { fcvRemoteVirtualPorts 20 }


    fcvRvpCir OBJECT-TYPE
        SYNTAX  INTEGER (600..2048000)
        ACCESS  read-write
        STATUS  mandatory
        DESCRIPTION
                "For all the connections described in
                fcvRvpConnectionTable, the value of this object
                indicates the Committed Infomation Rate (CIR) in
                bits per second desired on a Frame Relay network.
                This object is meaningless if the call is
                established on another transport network.

                The CIR is the subscriber data rate that the Frame
                Relay network commits to deliver under normal
                network conditions.

                This is a decimal integer in the range 600 to
                2048000. Only the following values are valid :

                   ~~~~~~~~~~~~~~~~~~~~~~~~~~~~~~~~~~~~~~~~~~~~~~
                   |  # |  value  |  # |  value  |  # |  value  |
                   ~~~~~~~~~~~~~~~~~~~~~~~~~~~~~~~~~~~~~~~~~~~~~~
                   |  0 |       0 | 17 |  144000 | 33 | 1152000 |
                   |  2 |     600 | 18 |  192000 | 34 | 1216000 |
                   |  3 |    1200 | 19 |  256000 | 35 | 1280000 |
                   |  4 |    2400 | 20 |  320000 | 36 | 1344000 |
                   |  5 |    4800 | 21 |  384000 | 37 | 1408000 |
                   |  6 |    9600 | 22 |  448000 | 38 | 1472000 |
                   |  7 |   14400 | 23 |  512000 | 39 | 1536000 |
                   |  8 |   19200 | 24 |  576000 | 40 | 1600000 |
                   |  9 |   32000 | 25 |  640000 | 41 | 1664000 |
                   | 10 |   38400 | 26 |  704000 | 42 | 1728000 |
                   | 11 |   48000 | 27 |  768000 | 43 | 1792000 |
                   | 12 |   56000 | 28 |  832000 | 44 | 1856000 |
                   | 13 |   64000 | 29 |  896000 | 45 | 1920000 |
                   | 14 |   72000 | 30 |  960000 | 46 | 1984000 |
                   | 15 |   96000 | 31 | 1024000 | 47 | 2048000 |
                   | 16 |  128000 | 32 | 1088000 |    |         |
                   ~~~~~~~~~~~~~~~~~~~~~~~~~~~~~~~~~~~~~~~~~~~~~~

                The default value is '4294967295' meaning 'empty
                value' (blank value on the equipment configurator)."
        ::= { fcvRemoteVirtualPorts 21 }


    fcvRvpMinCir OBJECT-TYPE
        SYNTAX  INTEGER (0..2048000)
        ACCESS  read-write
        STATUS  mandatory
        DESCRIPTION
                "For all the connections described in
                fcvRvpConnectionTable, the value of this object
                indicates the minimum Committed Infomation Rate
                (CIR) in bits per second desired on a Frame Relay
                network. This object is meaningless if the call is
                established on another transport network.

                This is a decimal integer in the range 600 to
                2048000. Only the following values are valid :

                   ~~~~~~~~~~~~~~~~~~~~~~~~~~~~~~~~~~~~~~~~~~~~~~
                   |  # |  value  |  # |  value  |  # |  value  |
                   ~~~~~~~~~~~~~~~~~~~~~~~~~~~~~~~~~~~~~~~~~~~~~~
                   |  0 |       0 | 17 |  144000 | 33 | 1152000 |
                   |  2 |     600 | 18 |  192000 | 34 | 1216000 |
                   |  3 |    1200 | 19 |  256000 | 35 | 1280000 |
                   |  4 |    2400 | 20 |  320000 | 36 | 1344000 |
                   |  5 |    4800 | 21 |  384000 | 37 | 1408000 |
                   |  6 |    9600 | 22 |  448000 | 38 | 1472000 |
                   |  7 |   14400 | 23 |  512000 | 39 | 1536000 |
                   |  8 |   19200 | 24 |  576000 | 40 | 1600000 |
                   |  9 |   32000 | 25 |  640000 | 41 | 1664000 |
                   | 10 |   38400 | 26 |  704000 | 42 | 1728000 |
                   | 11 |   48000 | 27 |  768000 | 43 | 1792000 |
                   | 12 |   56000 | 28 |  832000 | 44 | 1856000 |
                   | 13 |   64000 | 29 |  896000 | 45 | 1920000 |
                   | 14 |   72000 | 30 |  960000 | 46 | 1984000 |
                   | 15 |   96000 | 31 | 1024000 | 47 | 2048000 |
                   | 16 |  128000 | 32 | 1088000 |    |         |
                   ~~~~~~~~~~~~~~~~~~~~~~~~~~~~~~~~~~~~~~~~~~~~~~

                The default value is '4294967295' meaning 'empty
                value' (blank value on the equipment configurator)."
        ::= { fcvRemoteVirtualPorts 22 }


    fcvRvpConnectionTable OBJECT-TYPE
        SYNTAX  SEQUENCE OF FcvRvpConnectionEntry
        ACCESS  not-accessible
        STATUS  mandatory
        DESCRIPTION
                "This table defines the connections to each remote
                bridge or router on WAN virtual networks. Each
                connection is attached to one remote virtual port
                of a module of the equipment.

                Set any writable object(s) of this table to valid
                value(s) with a new index value to create an entry
                (the objects of the entry not present in this SET
                REQUEST will take their default values). Set
                fcvRvpConnStatus to 'invalid' to delete an entry."
        ::= { fcvRemoteVirtualPorts 23 }


    fcvRvpConnectionEntry OBJECT-TYPE
        SYNTAX  FcvRvpConnectionEntry
        ACCESS  not-accessible
        STATUS  mandatory
        DESCRIPTION
                "An entry of fcvRvpConnectionTable."
        INDEX   { fcvRvpConnRemoteAddress,
                  fcvRvpConnEncapsulation,
                  fcvRvpConnConnectionId }
        ::= { fcvRvpConnectionTable 1 }


        FcvRvpConnectionEntry ::=
                SEQUENCE {
                    fcvRvpConnRemoteAddress
                        OCTET STRING,
                    fcvRvpConnEncapsulation
                        INTEGER,
                    fcvRvpConnConnectionId
                        INTEGER,
                    fcvRvpConnStatus
                        INTEGER,
                    fcvRvpConnFlowTypeMask
                        INTEGER,
                    fcvRvpConnModule0VpId
                        INTEGER,
                    fcvRvpConnModule1VpId
                        INTEGER,
                    fcvRvpConnModule2VpId
                        INTEGER,
                    fcvRvpConnCallDirection
                        INTEGER,
                    fcvRvpConnGrouping
                        INTEGER,
                    fcvRvpConnMinimumRecallTimer
                        INTEGER,
                    fcvRvpConnInactivityTimer
                        INTEGER,
                    fcvRvpConnCir
                        INTEGER,
                    fcvRvpConnCos
                        INTEGER,
                    fcvRvpConnBe
                        INTEGER
                }


    fcvRvpConnRemoteAddress OBJECT-TYPE
        SYNTAX  OCTET STRING (SIZE(8))
        ACCESS  read-only
        STATUS  mandatory
        DESCRIPTION
                "The value of this object is the X121 address of
                the called remote bridge or router. This value is
                the called address specified in the call packet
                sent from this module.

                Several connections using different encapsulations
                may be established with the same remote equipment.
                But when multiplexing is used it must be the only
                encapsulation used with this particular remote
                equipment.

                This is a eight-bytes octet string with :
                   up to 15 digits in the range 0 to 9,
                   mandatory 'F' digits to pad the value until a
                        total of 16 digits (the equipment
                        configurator does not need this final
                        padding)."
        ::= { fcvRvpConnectionEntry 1 }


    fcvRvpConnEncapsulation OBJECT-TYPE
        SYNTAX  INTEGER {
                multiplexing(1),
                bridge(10),
                bridgeSpecific(11),
                ip(20),
                ipx(30),
                ipxSpecific(31),
                clnp(40)
                }
        ACCESS  read-only
        STATUS  mandatory
        DESCRIPTION
                "The value of this object indicates the protocol(s)
                to be transferred on the connection :
                   multiplexing : all protocols may be transported
                        on this connection and it must be the only
                        encapsulation specified for this X121
                        address,
                   bridge : bridge protocol,
                   bridgeSpecific : bridge specific protocol,
                   ip : internet protocol,
                   ipx : internetwork packet exchange protocol,
                   ipxSpecific : specific internetwork packet
                        exchange protocol,
                   clnp : connectionless network protocol."
        ::= { fcvRvpConnectionEntry 2 }


    fcvRvpConnConnectionId OBJECT-TYPE
        SYNTAX  INTEGER (1..255)
        ACCESS  read-only
        STATUS  mandatory
        DESCRIPTION
                "When several connections are established with the
                same encapsulation for the same remote equipment,
                the value of this object identifies this
                particular connection. This connection identifier
                must also be configured on the remote equipment.
                When only one connection is established with the
                same encapsulation for the same remote equipment,
                the value of this object is '255' (blank value on
                the equipment configurator) meaning 'unused'.

                This is a decimal integer in the range 1 to 8 or
                equal to 255."
        ::= { fcvRvpConnectionEntry 3 }


    fcvRvpConnStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcvRvpConnectionEntry 4 }


    fcvRvpConnFlowTypeMask OBJECT-TYPE
        SYNTAX  INTEGER (1..255)
        ACCESS  read-write
        STATUS  mandatory
        DESCRIPTION
                "The value of this object is a mask specifying the
                families (defined by fciFlowType) which have to
                transit via this connection.

                   Example : let us suppose that fciFlowTable
                        defines the content of families 2, 8, 16,
                        32 and 64 and this connection is set up to
                        process families 8, 16 and 32. The mask
                        therefore takes on value : 8 + 16 + 32 =
                        56.

                If two connections to the same address with the
                same encapsulation select the same family, the
                family will be oriented towards the first of these
                connections (increasing order of the connection
                identifiers).

                By convention, the value 255 selects, out of all
                the flows directed towards a WAN address, not only
                all the specified flows (i.e., defined in
                fciFlowTable) but also the unspecified flows
                (i.e., not defined in fciFlowTable). This is the
                default value to be used when flow separation is
                not being used.

                This is a decimal integer in the range 1 to 255.
                The default value is '255'."
        ::= { fcvRvpConnectionEntry 5 }


    fcvRvpConnModule0VpId OBJECT-TYPE
        SYNTAX  INTEGER (0..11)
        ACCESS  read-write
        STATUS  mandatory
        DESCRIPTION
                "The value of this object indicates the virtual
                port used by the Bridge and Router functions of
                the module 0 to communicate with the remote
                equipment. This VP must exist in
                fcvVirtualPortTable and must be a remote VP.

                When this connection is not processed by the
                module 0 this value is set to '255' (blank value
                on the equipment configurator).

                This is a decimal integer in the range 0 to 11.
                The default value is '255'."
        ::= { fcvRvpConnectionEntry 10 }


    fcvRvpConnModule1VpId OBJECT-TYPE
        SYNTAX  INTEGER (0..11)
        ACCESS  read-write
        STATUS  mandatory
        DESCRIPTION
                "The value of this object indicates the virtual
                port used by the Bridge and Router functions of
                the module 1 to communicate with the remote
                equipment. This VP must exist in
                fcvVirtualPortTable and must be a remote VP.

                When this connection is not processed by the
                module 1 this value is set to '255' (blank value
                on the equipment configurator).

                This is a decimal integer in the range 0 to 11.
                The default value is '255'."
        ::= { fcvRvpConnectionEntry 11 }


    fcvRvpConnModule2VpId OBJECT-TYPE
        SYNTAX  INTEGER (0..11)
        ACCESS  read-write
        STATUS  mandatory
        DESCRIPTION
                "The value of this object indicates the virtual
                port used by the Bridge and Router functions of
                the module 2 to communicate with the remote
                equipment. This VP must exist in
                fcvVirtualPortTable and must be a remote VP.

                When this connection is not processed by the
                module 2 this value is set to '255' (blank value
                on the equipment configurator).

                This is a decimal integer in the range 0 to 11.
                The default value is '255'."
        ::= { fcvRvpConnectionEntry 12 }


    fcvRvpConnCallDirection OBJECT-TYPE
        SYNTAX  INTEGER {
                calling(1),
                called(2),
                auto(3),
                datagram(4)
                }
        ACCESS  read-write
        STATUS  mandatory
        DESCRIPTION
                "The value of this object defines the mode used to
                establish this connection. The authorized values
                are :
                   calling : the caller is this equipment (at
                        initialization time),
                   called : the caller is the remote this
                        equipment (at initialization time),
                   auto : automatic choise between 'calling' and
                        'called' (at initialization time with call
                        collision processing),
                   datagram : the caller is this equipment or the
                        remote one (at any time) depending on
                        which of them is the first one that wishes
                        send datas.

                The default value is 'datagram'."
        ::= { fcvRvpConnectionEntry 20 }


    fcvRvpConnGrouping OBJECT-TYPE
        SYNTAX  INTEGER {
                off(1),
                on(2)
                }
        ACCESS  read-write
        STATUS  mandatory
        DESCRIPTION
                "The value of this object indicates whether the
                frame grouping/separation service (according to a
                specific proprietary encapsulation) is enabled or
                not. It requires the configuration of the fast
                select facility accross the WAN network.

                The frame grouping option is compatible only with
                the bridgeSpecific and ip encapsulations (see
                fcvRvpConnEncapsulation).

                The default value is 'off'."
        ::= { fcvRvpConnectionEntry 21 }


    fcvRvpConnMinimumRecallTimer OBJECT-TYPE
        SYNTAX  INTEGER (0..990)
        ACCESS  read-write
        STATUS  mandatory
        DESCRIPTION
                "The value of this object is the minimum recall
                timer in seconds. This timer starts when the
                equipment initiates the call and it is normally
                stopped when this call is successfull. When this
                timer runs out the equipment initiates a new call.

                This is a decimal integer in the range 0 to 990 by
                step of 10.
                The default value is '100'."
        ::= { fcvRvpConnectionEntry 22 }


    fcvRvpConnInactivityTimer OBJECT-TYPE
        SYNTAX  INTEGER (0..2540)
        ACCESS  read-write
        STATUS  mandatory
        DESCRIPTION
                "The value of this object is the inactivity timer
                in seconds. This timer starts one minute after the
                call is successfull. When this timer runs out, if
                there was traffic on this call during this period,
                this timer is re-started otherwise this call is
                cleared.

                This is a decimal integer in the range 0 to 2540
                by step of 10.
                The default value is '30'."
        ::= { fcvRvpConnectionEntry 23 }


    fcvRvpConnCir OBJECT-TYPE
        SYNTAX  INTEGER (600..2048000)
        ACCESS  read-write
        STATUS  mandatory
        DESCRIPTION
                "The value of this object indicates, for this
                connection, the Committed Infomation Rate (CIR) in
                bits per second desired on a Frame Relay network.
                This object is meaningless if the call is
                established on another transport network.

                The CIR is the subscriber data rate that the Frame
                Relay network commits to deliver under normal
                network conditions.

                This is a decimal integer in the range 600 to
                2048000. Only the following values are valid :

                   ~~~~~~~~~~~~~~~~~~~~~~~~~~~~~~~~~~~~~~~~~~~~~~
                   |  # |  value  |  # |  value  |  # |  value  |
                   ~~~~~~~~~~~~~~~~~~~~~~~~~~~~~~~~~~~~~~~~~~~~~~
                   |  0 |       0 | 17 |  144000 | 33 | 1152000 |
                   |  2 |     600 | 18 |  192000 | 34 | 1216000 |
                   |  3 |    1200 | 19 |  256000 | 35 | 1280000 |
                   |  4 |    2400 | 20 |  320000 | 36 | 1344000 |
                   |  5 |    4800 | 21 |  384000 | 37 | 1408000 |
                   |  6 |    9600 | 22 |  448000 | 38 | 1472000 |
                   |  7 |   14400 | 23 |  512000 | 39 | 1536000 |
                   |  8 |   19200 | 24 |  576000 | 40 | 1600000 |
                   |  9 |   32000 | 25 |  640000 | 41 | 1664000 |
                   | 10 |   38400 | 26 |  704000 | 42 | 1728000 |
                   | 11 |   48000 | 27 |  768000 | 43 | 1792000 |
                   | 12 |   56000 | 28 |  832000 | 44 | 1856000 |
                   | 13 |   64000 | 29 |  896000 | 45 | 1920000 |
                   | 14 |   72000 | 30 |  960000 | 46 | 1984000 |
                   | 15 |   96000 | 31 | 1024000 | 47 | 2048000 |
                   | 16 |  128000 | 32 | 1088000 |    |         |
                   ~~~~~~~~~~~~~~~~~~~~~~~~~~~~~~~~~~~~~~~~~~~~~~

                The default value is '4294967295' meaning 'empty
                value' (blank value on the equipment
                configurator).
                "
        ::= { fcvRvpConnectionEntry 24 }


    fcvRvpConnCos OBJECT-TYPE
        SYNTAX  INTEGER {
                ubr(3),
                global(4),
                vbr(1),
                vbr-rt(2)
                }
        ACCESS  read-write
        STATUS  mandatory
        DESCRIPTION
                "Requested Class of Service for this connection,
                the Cos can be configured more globally."
        ::= { fcvRvpConnectionEntry 25 }


    fcvRvpConnBe OBJECT-TYPE
        SYNTAX  INTEGER (0..2048000)
        ACCESS  read-write
        STATUS  mandatory
        DESCRIPTION
                "Be"
        ::= { fcvRvpConnectionEntry 26 }


    fcSna OBJECT IDENTIFIER ::= { frxConfig 32 }


    fcsnaLocalVirtualPort OBJECT IDENTIFIER ::= { fcSna 1 }


    fcsnaLvpLocalLanPuTable OBJECT-TYPE
        SYNTAX  SEQUENCE OF FcsnaLvpLocalLanPuEntry
        ACCESS  not-accessible
        STATUS  mandatory
        DESCRIPTION
                ""
        ::= { fcsnaLocalVirtualPort 1 }


    fcsnaLvpLocalLanPuEntry OBJECT-TYPE
        SYNTAX  FcsnaLvpLocalLanPuEntry
        ACCESS  not-accessible
        STATUS  mandatory
        DESCRIPTION
                "An entry of fcsnaLvpLocalLanPuTable."
        INDEX   { fcsnaLvpLlpVirtualPortId,
                  fcsnaLvpLlpPuId }
        ::= { fcsnaLvpLocalLanPuTable 1 }


        FcsnaLvpLocalLanPuEntry ::=
                SEQUENCE {
                    fcsnaLvpLlpVirtualPortId
                        INTEGER,
                    fcsnaLvpLlpPuId
                        INTEGER,
                    fcsnaLvpLlpStatus
                        INTEGER
                }


    fcsnaLvpLlpVirtualPortId OBJECT-TYPE
        SYNTAX  INTEGER (0..11)
        ACCESS  read-only
        STATUS  mandatory
        DESCRIPTION
                "VP id"
        ::= { fcsnaLvpLocalLanPuEntry 1 }


    fcsnaLvpLlpPuId OBJECT-TYPE
        SYNTAX  INTEGER (0..1999)
        ACCESS  read-only
        STATUS  mandatory
        DESCRIPTION
                "Physical Unit id"
        ::= { fcsnaLvpLocalLanPuEntry 2 }


    fcsnaLvpLlpStatus OBJECT-TYPE
        SYNTAX  INTEGER {
                valid(1),
                invalid(2)
                }
        ACCESS  read-write
        STATUS  mandatory
        DESCRIPTION
                "Status"
        ::= { fcsnaLvpLocalLanPuEntry 3 }


    fcsnaLvpParameters OBJECT IDENTIFIER ::= { fcsnaLocalVirtualPort 10 }


    fcsnaLvpParamLinkType OBJECT-TYPE
        SYNTAX  INTEGER {
                frontal(1),
                remote(2)
                }
        ACCESS  read-write
        STATUS  mandatory
        DESCRIPTION
                "The type of frontal must be connected to a primary
                link-station or negociable link station that will
                become the primary. The type of remote must be
                connected to a secondary link-station or
                negociable link station that will become the
                secondary. 

                The default value is 'frontal'"
        ::= { fcsnaLvpParameters 1 }


    fcsnaLvpParamFrameFormat OBJECT-TYPE
        SYNTAX  INTEGER {
                e802-3(1),
                v2-DIX(2)
                }
        ACCESS  read-write
        STATUS  mandatory
        DESCRIPTION
                "The unit supports IEEE 802.3 and V2 DIX Ethernet
                frame format."
        ::= { fcsnaLvpParameters 2 }


    fcsnaLvpParamLocalTest OBJECT-TYPE
        SYNTAX  INTEGER {
                off(1),
                on(2)
                }
        ACCESS  read-write
        STATUS  mandatory
        DESCRIPTION
                "This feature is used in 'frontal' mode. If this
                feature is set to on, and when the internal
                connection is established, it will send a local
                test frame to the primary link-station."
        ::= { fcsnaLvpParameters 3 }


    fcsnaLvpParamCallDirection OBJECT-TYPE
        SYNTAX  INTEGER {
                called(1),
                calling(2)
                }
        ACCESS  read-write
        STATUS  mandatory
        DESCRIPTION
                "Frontal mode is called. Remote mode is calling."
        ::= { fcsnaLvpParameters 4 }


    fcsnaLvpMacAddressTrans OBJECT-TYPE
        SYNTAX  INTEGER {
                off(1),
                on(2)
                }
        ACCESS  read-write
        STATUS  mandatory
        DESCRIPTION
                "MAC address translation."
        ::= { fcsnaLvpParameters 5 }


    fcsnaLvpParamT1 OBJECT-TYPE
        SYNTAX  INTEGER (100..25000)
        ACCESS  read-write
        STATUS  mandatory
        DESCRIPTION
                "T1 Reply timer. A link-station uses T1 to detect a
                failure to receive a required acknowlegment or
                response. T1 runs when there are acknowlegments
                outstanding, it is reset when acknowlegments are
                received."
        ::= { fcsnaLvpParameters 10 }


    fcsnaLvpParamN2 OBJECT-TYPE
        SYNTAX  INTEGER (1..20)
        ACCESS  read-write
        STATUS  mandatory
        DESCRIPTION
                "The maximum number of transmissions. If the reply
                timer expires for whatever reason, an S-frame with
                poll bit set is sent to sollicit  a response from
                remote link-station. If there is still no response
                after N2 retry, the link is deemed to be
                inoperative."
        ::= { fcsnaLvpParameters 11 }


    fcsnaLvpParamT2 OBJECT-TYPE
        SYNTAX  INTEGER (100..15000)
        ACCESS  read-write
        STATUS  mandatory
        DESCRIPTION
                "Receiver acknowledge timer. The end station uses
                this timer to delay the seding of an acknowlegment
                for a received I-frame LPDU. The link-station
                starts T2 when it receives an I-frame and resets
                it when it sends an acknowlegment. T2 must be less
                than T1."
        ::= { fcsnaLvpParameters 12 }


    fcsnaLvpParamN3 OBJECT-TYPE
        SYNTAX  INTEGER (1..20)
        ACCESS  read-write
        STATUS  mandatory
        DESCRIPTION
                "Number of I-frame LPDU's received before sending
                an acknowledgment."
        ::= { fcsnaLvpParameters 13 }


    fcsnaLvpParamNW OBJECT-TYPE
        SYNTAX  INTEGER (0..127)
        ACCESS  read-write
        STATUS  mandatory
        DESCRIPTION
                "Number of acknowledgments needed to increment Ww."
        ::= { fcsnaLvpParameters 14 }


    fcsnaLvpParamTW OBJECT-TYPE
        SYNTAX  INTEGER (1..127)
        ACCESS  read-write
        STATUS  mandatory
        DESCRIPTION
                "LLC transmit window size. This is maximum number
                of sequentially numbered Iframe that the
                link-station may have outstanding at any given
                time."
        ::= { fcsnaLvpParameters 15 }


    fcsnaLvpParamRW OBJECT-TYPE
        SYNTAX  INTEGER (1..127)
        ACCESS  read-write
        STATUS  mandatory
        DESCRIPTION
                "LLC receive window size. This is the maximum
                number of unacknowlegment sequentially numbered
                I-frame the link-station can receive from the
                remote station."
        ::= { fcsnaLvpParameters 16 }


    fcsnaLvpParamMinRecallTimer OBJECT-TYPE
        SYNTAX  INTEGER (0..990)
        ACCESS  read-write
        STATUS  mandatory
        DESCRIPTION
                "Slow call timer."
        ::= { fcsnaLvpParameters 20 }


    fcsnaLvpParamSubscriberNumber OBJECT-TYPE
        SYNTAX  OCTET STRING (SIZE(1))
        ACCESS  read-write
        STATUS  mandatory
        DESCRIPTION
                "The value of this object is the SB number added to
                the DNICZO of the equipment to make the calling
                address in a call sent from this logical port. The
                value must contain 2 digits (digits 0..9). The
                default value is '22'.
                "
        ::= { fcsnaLvpParameters 21 }


    fcsnaLvpParamReliableVc OBJECT-TYPE
        SYNTAX  INTEGER {
                off(1),
                clear(3),
                subscribe(2),
                check(4)
                }
        ACCESS  read-write
        STATUS  mandatory
        DESCRIPTION
                "The value of this object is used to enable the
                Reliable Virtual Circuit service. The authorized
                values are :
                   off : no RVC, the VCs are considered as normal
                        VCs, no particular processing,
                   clear : RVCs are not allowed for the
                        subscriber, each attempt to establish a
                        RVC provokes a clear of the connection,
                   subscribe : all calls transmitted by the
                        subscriber establish RVCs, it is also
                        possible to receive calls with RVC option,
                   check :
                     for a link to a subscriber : when a call with
                        RVC option is received, a RVC is
                        established
                     for a link to a network : the RVC option is
                        ignored when it is present in a call sent
                        by a local subscriber, the connection is
                        cleared when the RVC option is present in
                        a call sent by the network.
                The default value is 'off'.
                "
        ::= { fcsnaLvpParameters 22 }


    fcsnaLvpParamCompression OBJECT-TYPE
        SYNTAX  INTEGER {
                off(1),
                networkToSubscriber(2),
                subscriberToNetwork(3),
                bothway(4)
                }
        ACCESS  read-write
        STATUS  mandatory
        DESCRIPTION
                "The value of this object indicates the compression
                enabling for each direction. The authorized values
                are :
                   off : no compression,
                   networkToSubscriber : compression of the flow
                        from the remote peer to the equipment,
                   subscriberToNetwork : compression of the flow
                        from the equipment to the remote peer,
                   bothway : compression of the two flows from and
                        to the equipment.
                The default value is 'off'."
        ::= { fcsnaLvpParameters 30 }


    fcsnaLvpParamCompressNegotiation OBJECT-TYPE
        SYNTAX  INTEGER {
                off(1),
                onOptionalCompression(2),
                onMandatoryCompression(3)
                }
        ACCESS  read-write
        STATUS  mandatory
        DESCRIPTION
                "The value of this object indicates whether the
                compression facility is negociated or not and, if
                negociated, the optional/obligatory status. The
                authorized values are :
                   off' :no negociation,
                   onOptionalCompression : negociation but
                        compression is optional,
                   onMandatoryCompression : negociation and
                        compression is mandatory.
                The default value is 'off'."
        ::= { fcsnaLvpParameters 31 }


    fcsnaLvpParamCompressScrambling OBJECT-TYPE
        SYNTAX  INTEGER {
                off(1),
                on(2)
                }
        ACCESS  read-write
        STATUS  mandatory
        DESCRIPTION
                "The value of this object indicates, when the
                compression is active, whether the scrambling is
                enabled or not. The default value is 'off'.
                "
        ::= { fcsnaLvpParameters 32 }


    fcsnaLvpParamCompressMultiPacketsTimer OBJECT-TYPE
        SYNTAX  INTEGER (0..1500)
        ACCESS  read-write
        STATUS  mandatory
        DESCRIPTION
                "The value of this object defines the maximum
                waiting time, in milliseconds by steps of 100
                milliseconds , which, if there is not another
                packet to compress, the packet of compressed
                packets is sent beyond (this permits to reduce the
                number of packets transmitted to the remote peer).
                The authorized values are '0..1500'. '0' means no
                packets grouping (i. e. : each packet is
                individually compressed and sent). The default
                value is '0'.
                "
        ::= { fcsnaLvpParameters 33 }


    fcsnaLvpParamCos OBJECT-TYPE
        SYNTAX  INTEGER {
                ubr(3),
                vbr(1)
                }
        ACCESS  read-write
        STATUS  mandatory
        DESCRIPTION
                "Class Of  Service VBR or UBR."
        ::= { fcsnaLvpParameters 40 }


    fcsnaLvpParamCir OBJECT-TYPE
        SYNTAX  INTEGER (600..2048000)
        ACCESS  read-write
        STATUS  mandatory
        DESCRIPTION
                "Committed information Rate is the maximum number
                of bits per seconds which an end station can
                transmit into the network . This is the access
                rate of the user-network interface and it is
                limited by the line speed of the user-network
                connection and established by subscription."
        ::= { fcsnaLvpParameters 41 }


    fcsnaLvpParamCirMin OBJECT-TYPE
        SYNTAX  INTEGER (0..2048000)
        ACCESS  read-write
        STATUS  mandatory
        DESCRIPTION
                "If the end station is informed about the
                congestion of the network, this is the minimum CIR
                that the end station can transmit into the network."
        ::= { fcsnaLvpParameters 42 }


    fcsnaLvpParamBc OBJECT-TYPE
        SYNTAX  INTEGER (0..2048000)
        ACCESS  read-write
        STATUS  mandatory
        DESCRIPTION
                "The Committed Burst Size is a measure for the
                volume of data for which the network will garantee
                message delivery under normal conditions. It is
                measured during the committed rate measurement
                interval (Tc)."
        ::= { fcsnaLvpParameters 43 }


    fcsnaLvpParamBe OBJECT-TYPE
        SYNTAX  INTEGER (0..2048000)
        ACCESS  read-write
        STATUS  mandatory
        DESCRIPTION
                "The Excess Burst Size is the maximum amount of
                uncommitted data in access of Bc that the network
                will attemp to deliver during a time interval
                (Tc). End stations are allowed to transmit data in
                excess of the committed burst rate."
        ::= { fcsnaLvpParameters 44 }


    fcsnaLvpTrParameters OBJECT IDENTIFIER ::= { fcsnaLocalVirtualPort 20 }


    fcsnaLvpTrParamLinkType OBJECT-TYPE
        SYNTAX  INTEGER {
                frontal(1),
                remote(2)
                }
        ACCESS  read-write
        STATUS  mandatory
        DESCRIPTION
                "frontal must be connected to the a primary
                link-station or negociable link-station that will
                become the primary, remote must be connected to
                the a decondary link-station or negociable
                link-station that will become the secondary"
        ::= { fcsnaLvpTrParameters 1 }


    fcsnaLvpTrParamBroadcastType OBJECT-TYPE
        SYNTAX  INTEGER {
                none(1),
                all-routes(2),
                single-route(3)
                }
        ACCESS  read-write
        STATUS  mandatory
        DESCRIPTION
                "This field defines the type of broadcast test
                frame. The unit sends to a destination to
                determine the best route"
        ::= { fcsnaLvpTrParameters 2 }


    fcsnaLvpTrParamLocalTest OBJECT-TYPE
        SYNTAX  INTEGER {
                off(1),
                on(2)
                }
        ACCESS  read-write
        STATUS  mandatory
        DESCRIPTION
                "This feature is used in 'frontal' mode. If this
                feature is set to on, and when the internal
                connection is established, it will send a local
                test frame to the primary link-station.
                "
        ::= { fcsnaLvpTrParameters 3 }


    fcsnaLvpTrParamCallDirection OBJECT-TYPE
        SYNTAX  INTEGER {
                called(1),
                calling(2)
                }
        ACCESS  read-write
        STATUS  mandatory
        DESCRIPTION
                "Frontal mode is called. Remote mode is calling.
                "
        ::= { fcsnaLvpTrParameters 4 }


    fcsnaLvpTrRingNo OBJECT-TYPE
        SYNTAX  INTEGER (1..4095)
        ACCESS  read-write
        STATUS  mandatory
        DESCRIPTION
                "This field identifies the ring number of the LAN
                to which the unit connects.
                "
        ::= { fcsnaLvpTrParameters 5 }


    fcsnaLvpTrBridgeNo OBJECT-TYPE
        SYNTAX  INTEGER (1..15)
        ACCESS  read-write
        STATUS  mandatory
        DESCRIPTION
                "A unit attached to a Token Ring LAN represents a
                bridge between the physical LAN ring and the
                network's virtual ring.
                "
        ::= { fcsnaLvpTrParameters 6 }


    fcsnaLvpTrMacAddressTrans OBJECT-TYPE
        SYNTAX  INTEGER {
                off(1),
                on(2)
                }
        ACCESS  read-write
        STATUS  mandatory
        DESCRIPTION
                "MAC address translation"
        ::= { fcsnaLvpTrParameters 7 }


    fcsnaLvpTrParamT1 OBJECT-TYPE
        SYNTAX  INTEGER (100..25000)
        ACCESS  read-write
        STATUS  mandatory
        DESCRIPTION
                "T1 Reply timer. A link-station uses T1 to detect a
                failure to receive a required acknowlegment or
                response. T1 runs when there are acknowlegments
                outstanding, it is reset when acknowlegments are
                received.
                "
        ::= { fcsnaLvpTrParameters 10 }


    fcsnaLvpTrParamN2 OBJECT-TYPE
        SYNTAX  INTEGER (1..20)
        ACCESS  read-write
        STATUS  mandatory
        DESCRIPTION
                "The maximum number of transmissions. If the reply
                timer expires for whatever reason, an S-frame with
                poll bit set is sent to sollicit  a response from
                remote link-station. If there is still no response
                after N2 retry, the link is deemed to be
                inoperative.
                "
        ::= { fcsnaLvpTrParameters 11 }


    fcsnaLvpTrParamT2 OBJECT-TYPE
        SYNTAX  INTEGER (100..15000)
        ACCESS  read-write
        STATUS  mandatory
        DESCRIPTION
                "Receiver acknowledge timer. The end station uses
                this timer to delay the seding of an acknowlegment
                for a received I-frame LPDU. The link-station
                starts T2 when it receives an I-frame and resets
                it when it sends an acknowlegment. T2 must be less
                than T1."
        ::= { fcsnaLvpTrParameters 12 }


    fcsnaLvpTrParamN3 OBJECT-TYPE
        SYNTAX  INTEGER (1..20)
        ACCESS  read-write
        STATUS  mandatory
        DESCRIPTION
                "Number of I-frame LPDU's received before sending
                an acknowledgment
                "
        ::= { fcsnaLvpTrParameters 13 }


    fcsnaLvpTrParamNW OBJECT-TYPE
        SYNTAX  INTEGER (0..127)
        ACCESS  read-write
        STATUS  mandatory
        DESCRIPTION
                "Number of acknowledgments needed to increment Ww
                "
        ::= { fcsnaLvpTrParameters 14 }


    fcsnaLvpTrParamTW OBJECT-TYPE
        SYNTAX  INTEGER (1..127)
        ACCESS  read-write
        STATUS  mandatory
        DESCRIPTION
                "LLC transmit window size. This is maximum number
                of sequentially numbered Iframe that the
                link-station may have outstanding at any given
                time.
                "
        ::= { fcsnaLvpTrParameters 15 }


    fcsnaLvpTrParamRW OBJECT-TYPE
        SYNTAX  INTEGER (1..127)
        ACCESS  read-write
        STATUS  mandatory
        DESCRIPTION
                "LLC receive window size. This is the maximum
                number of unacknowlegment sequentially numbered
                I-frame the link-station can receive from the
                remote station.
                "
        ::= { fcsnaLvpTrParameters 16 }


    fcsnaLvpTrParamMinRecallTimer OBJECT-TYPE
        SYNTAX  INTEGER (0..990)
        ACCESS  read-write
        STATUS  mandatory
        DESCRIPTION
                "Slow call timer."
        ::= { fcsnaLvpTrParameters 20 }


    fcsnaLvpTrParamSubscriberNumber OBJECT-TYPE
        SYNTAX  OCTET STRING (SIZE(1))
        ACCESS  read-write
        STATUS  mandatory
        DESCRIPTION
                "The value of this object is the SB number added to
                the DNICZO of the equipment to make the calling
                address in a call sent from this logical port. The
                value must contain 2 digits (digits 0..9). The
                default value is '22'."
        ::= { fcsnaLvpTrParameters 21 }


    fcsnaLvpTrParamReliableVc OBJECT-TYPE
        SYNTAX  INTEGER {
                off(1),
                clear(3),
                subscribe(2),
                check(4)
                }
        ACCESS  read-write
        STATUS  mandatory
        DESCRIPTION
                "The value of this object is used to enable the
                Reliable Virtual Circuit service. The authorized
                values are :
                   off : no RVC, the VCs are considered as normal
                        VCs, no particular processing,
                   clear : RVCs are not allowed for the
                        subscriber, each attempt to establish a
                        RVC provokes a clear of the connection,
                   subscribe : all calls transmitted by the
                        subscriber establish RVCs, it is also
                        possible to receive calls with RVC option,
                   check :
                     for a link to a subscriber : when a call with
                        RVC option is received, a RVC is
                        established
                     for a link to a network : the RVC option is
                        ignored when it is present in a call sent
                        by a local subscriber, the connection is
                        cleared when the RVC option is present in
                        a call sent by the network.
                The default value is 'off'.
                "
        ::= { fcsnaLvpTrParameters 22 }


    fcsnaLvpTrParamCompression OBJECT-TYPE
        SYNTAX  INTEGER {
                off(1),
                networkToSubscriber(2),
                subscriberToNetwork(3),
                bothway(4)
                }
        ACCESS  read-write
        STATUS  mandatory
        DESCRIPTION
                "The value of this object indicates the compression
                enabling for each direction. The authorized values
                are :
                   off : no compression,
                   networkToSubscriber : compression of the flow
                        from the remote peer to the equipment,
                   subscriberToNetwork : compression of the flow
                        from the equipment to the remote peer,
                   bothway : compression of the two flows from and
                        to the equipment.
                The default value is 'off'.
                "
        ::= { fcsnaLvpTrParameters 30 }


    fcsnaLvpTrParamCompressNegotiation OBJECT-TYPE
        SYNTAX  INTEGER {
                off(1),
                onOptionalCompression(2),
                onMandatoryCompression(3)
                }
        ACCESS  read-write
        STATUS  mandatory
        DESCRIPTION
                "The value of this object indicates whether the
                compression facility is negociated or not and, if
                negociated, the optional/obligatory status. The
                authorized values are :
                   off' :no negociation,
                   onOptionalCompression : negociation but
                        compression is optional,
                   onMandatoryCompression : negociation and
                        compression is mandatory.
                The default value is 'off'.
                "
        ::= { fcsnaLvpTrParameters 31 }


    fcsnaLvpTrParamCompressScrambling OBJECT-TYPE
        SYNTAX  INTEGER {
                off(1),
                on(2)
                }
        ACCESS  read-write
        STATUS  mandatory
        DESCRIPTION
                "The value of this object indicates, when the
                compression is active, whether the scrambling is
                enabled or not. The default value is 'off'.
                "
        ::= { fcsnaLvpTrParameters 32 }


    fcsnaLvpTrParamCompressMultiPacketsTimer OBJECT-TYPE
        SYNTAX  INTEGER (0..1500)
        ACCESS  read-write
        STATUS  mandatory
        DESCRIPTION
                "The value of this object defines the maximum
                waiting time, in milliseconds by steps of 100
                milliseconds , which, if there is not another
                packet to compress, the packet of compressed
                packets is sent beyond (this permits to reduce the
                number of packets transmitted to the remote peer).
                The authorized values are '0..1500'. '0' means no
                packets grouping (i. e. : each packet is
                individually compressed and sent). The default
                value is '0'.
                "
        ::= { fcsnaLvpTrParameters 33 }


    fcsnaLvpTrParamCos OBJECT-TYPE
        SYNTAX  INTEGER {
                ubr(3),
                vbr(1)
                }
        ACCESS  read-write
        STATUS  mandatory
        DESCRIPTION
                "Class Of  Service VBR or UBR."
        ::= { fcsnaLvpTrParameters 40 }


    fcsnaLvpTrParamCir OBJECT-TYPE
        SYNTAX  INTEGER (600..2048000)
        ACCESS  read-write
        STATUS  mandatory
        DESCRIPTION
                "Committed information Rate is the maximum number
                of bits per seconds which an end station can
                transmit into the network . This is the access
                rate of the user-network interface and it is
                limited by the line speed of the user-network
                connection and established by subscription."
        ::= { fcsnaLvpTrParameters 41 }


    fcsnaLvpTrParamCirMin OBJECT-TYPE
        SYNTAX  INTEGER (0..2048000)
        ACCESS  read-write
        STATUS  mandatory
        DESCRIPTION
                "If the end station is informed about the
                congestion of the network, this is the minimum CIR
                that the end station can transmit into the
                network.
                "
        ::= { fcsnaLvpTrParameters 42 }


    fcsnaLvpTrParamBc OBJECT-TYPE
        SYNTAX  INTEGER (0..2048000)
        ACCESS  read-write
        STATUS  mandatory
        DESCRIPTION
                "The Committed Burst Size is a measure for the
                volume of data for which the network will garantee
                message delivery under normal conditions. It is
                measured during the committed rate measurement
                interval (Tc).
                "
        ::= { fcsnaLvpTrParameters 43 }


    fcsnaLvpTrParamBe OBJECT-TYPE
        SYNTAX  INTEGER (0..2048000)
        ACCESS  read-write
        STATUS  mandatory
        DESCRIPTION
                "The Excess Burst Size is the maximum amount of
                uncommitted data in access of Bc that the network
                will attemp to deliver during a time interval
                (Tc). End stations are allowed to transmit data in
                excess of the committed burst rate.
                "
        ::= { fcsnaLvpTrParameters 44 }


    fcsnaGeneralParameters OBJECT IDENTIFIER ::= { fcSna 5 }


    fcsnaGpRoutingTable OBJECT-TYPE
        SYNTAX  SEQUENCE OF FcsnaGpRoutingEntry
        ACCESS  not-accessible
        STATUS  mandatory
        DESCRIPTION
                ""
        ::= { fcsnaGeneralParameters 1 }


    fcsnaGpRoutingEntry OBJECT-TYPE
        SYNTAX  FcsnaGpRoutingEntry
        ACCESS  not-accessible
        STATUS  mandatory
        DESCRIPTION
                "An entry of fcsnaGpRoutingTable."
        INDEX   { fcsnaGpRoutClusterPuId,
                  fcsnaGpRoutHostPuId }
        ::= { fcsnaGpRoutingTable 1 }


        FcsnaGpRoutingEntry ::=
                SEQUENCE {
                    fcsnaGpRoutClusterPuId
                        INTEGER,
                    fcsnaGpRoutHostPuId
                        INTEGER,
                    fcsnaGpRoutStatus
                        INTEGER,
                    fcsnaGpRoutDsap
                        OCTET STRING,
                    fcsnaGpRoutSsap
                        OCTET STRING,
                    fcsnaGpRoutCos
                        INTEGER,
                    fcsnaGpRoutCir
                        INTEGER,
                    fcsnaGpRoutCirmin
                        INTEGER,
                    fcsnaGpRoutBc
                        INTEGER,
                    fcsnaGpRoutBe
                        INTEGER
                }


    fcsnaGpRoutClusterPuId OBJECT-TYPE
        SYNTAX  INTEGER (0..999)
        ACCESS  read-only
        STATUS  mandatory
        DESCRIPTION
                "PU id cluster"
        ::= { fcsnaGpRoutingEntry 1 }


    fcsnaGpRoutHostPuId OBJECT-TYPE
        SYNTAX  INTEGER (1000..1999)
        ACCESS  read-only
        STATUS  mandatory
        DESCRIPTION
                "PU id host"
        ::= { fcsnaGpRoutingEntry 2 }


    fcsnaGpRoutStatus OBJECT-TYPE
        SYNTAX  INTEGER {
                valid(1),
                invalid(2)
                }
        ACCESS  read-write
        STATUS  mandatory
        DESCRIPTION
                "Status"
        ::= { fcsnaGpRoutingEntry 3 }


    fcsnaGpRoutDsap OBJECT-TYPE
        SYNTAX  OCTET STRING (SIZE(1))
        ACCESS  read-write
        STATUS  mandatory
        DESCRIPTION
                "DSAP This field defines the service access point
                for the PU session. The unit uses this 
                Address in conjunction withe the MAC address to to
                map the session to its destination.
                If  the PU originates the call, this is the source
                SSAP. If the PU responds the call, this is
                The destionation DSAP."
        ::= { fcsnaGpRoutingEntry 10 }


    fcsnaGpRoutSsap OBJECT-TYPE
        SYNTAX  OCTET STRING (SIZE(1))
        ACCESS  read-write
        STATUS  mandatory
        DESCRIPTION
                "SSAP This field defines the service access point
                for the PU session. The unit uses this 
                Address in conjunction withe the MAC address to to
                map the session to its destination.
                If  the PU originates the call, this is the source
                SSAP. If the PU responds the call, this is
                The destionation DSAP."
        ::= { fcsnaGpRoutingEntry 11 }


    fcsnaGpRoutCos OBJECT-TYPE
        SYNTAX  INTEGER {
                ubr(3),
                vbr(1),
                vbr-rt(2)
                }
        ACCESS  read-write
        STATUS  mandatory
        DESCRIPTION
                "COS Class Of  Service VBR or UBR"
        ::= { fcsnaGpRoutingEntry 20 }


    fcsnaGpRoutCir OBJECT-TYPE
        SYNTAX  INTEGER (0..2048000)
        ACCESS  read-write
        STATUS  mandatory
        DESCRIPTION
                "CIR Committed information Rate is the maximum
                number of bits per seconds which an end station
                can transmit into the network . This is the access
                rate of the user-network interface and it is
                limited by the line speed of the user-network
                connection and established by subscription."
        ::= { fcsnaGpRoutingEntry 21 }


    fcsnaGpRoutCirmin OBJECT-TYPE
        SYNTAX  INTEGER (0..2048000)
        ACCESS  read-write
        STATUS  mandatory
        DESCRIPTION
                "CIRmin If the end station is informed about the
                congestion of the network, this is the minimum CIR
                that the end station can transmit into the network."
        ::= { fcsnaGpRoutingEntry 22 }


    fcsnaGpRoutBc OBJECT-TYPE
        SYNTAX  INTEGER (0..2048000)
        ACCESS  read-write
        STATUS  mandatory
        DESCRIPTION
                "Bc The Committed Burst Size is a measure for the
                volume of data for which the network will garantee
                message delivery under normal conditions. It is
                measured during the committed rate measurement
                interval (Tc)
                "
        ::= { fcsnaGpRoutingEntry 23 }


    fcsnaGpRoutBe OBJECT-TYPE
        SYNTAX  INTEGER (0..2048000)
        ACCESS  read-write
        STATUS  mandatory
        DESCRIPTION
                "Be The Excess Burst Size is the maximum amount of
                uncommitted data in access of Bc that the network
                will attemp to deliver during a time interval
                (Tc). End stations are allowed to transmit data in
                excess of the committed burst rate."
        ::= { fcsnaGpRoutingEntry 24 }


    fcsnaGpRemotePuTable OBJECT-TYPE
        SYNTAX  SEQUENCE OF FcsnaGpRemotePuEntry
        ACCESS  not-accessible
        STATUS  mandatory
        DESCRIPTION
                ""
        ::= { fcsnaGeneralParameters 2 }


    fcsnaGpRemotePuEntry OBJECT-TYPE
        SYNTAX  FcsnaGpRemotePuEntry
        ACCESS  not-accessible
        STATUS  mandatory
        DESCRIPTION
                "An entry of fcsnaGpRemotePuTable."
        INDEX   { fcsnaGpRemPuPuId }
        ::= { fcsnaGpRemotePuTable 1 }


        FcsnaGpRemotePuEntry ::=
                SEQUENCE {
                    fcsnaGpRemPuPuId
                        INTEGER,
                    fcsnaGpRemPuStatus
                        INTEGER,
                    fcsnaGpRemPuProtocol
                        INTEGER
                }


    fcsnaGpRemPuPuId OBJECT-TYPE
        SYNTAX  INTEGER (0..1999)
        ACCESS  read-only
        STATUS  mandatory
        DESCRIPTION
                "Physical Unit id"
        ::= { fcsnaGpRemotePuEntry 1 }


    fcsnaGpRemPuStatus OBJECT-TYPE
        SYNTAX  INTEGER {
                valid(1),
                invalid(2)
                }
        ACCESS  read-write
        STATUS  mandatory
        DESCRIPTION
                "Status"
        ::= { fcsnaGpRemotePuEntry 2 }


    fcsnaGpRemPuProtocol OBJECT-TYPE
        SYNTAX  INTEGER {
                auto(1),
                x25(2),
                sdlc(3),
                frban(4),
                sna-ethernet(5)
                }
        ACCESS  read-write
        STATUS  mandatory
        DESCRIPTION
                "Type de protocole The value of this object allows
                to interworking with an remote 
                Equipement which uses another communication
                protocole as X25/QLLC, SDLC or 
                Lan protocol SNA/LLC2."
        ::= { fcsnaGpRemotePuEntry 3 }


    fcsnaGpSdlcTable OBJECT-TYPE
        SYNTAX  SEQUENCE OF FcsnaGpSdlcEntry
        ACCESS  not-accessible
        STATUS  mandatory
        DESCRIPTION
                ""
        ::= { fcsnaGeneralParameters 3 }


    fcsnaGpSdlcEntry OBJECT-TYPE
        SYNTAX  FcsnaGpSdlcEntry
        ACCESS  not-accessible
        STATUS  mandatory
        DESCRIPTION
                "An entry of fcsnaGpSdlcTable."
        INDEX   { fcsnaGpSdlcPuId }
        ::= { fcsnaGpSdlcTable 1 }


        FcsnaGpSdlcEntry ::=
                SEQUENCE {
                    fcsnaGpSdlcPuId
                        INTEGER,
                    fcsnaGpSdlcStatus
                        INTEGER,
                    fcsnaGpSdlcLp
                        INTEGER,
                    fcsnaGpSdlcCluster
                        OCTET STRING
                }


    fcsnaGpSdlcPuId OBJECT-TYPE
        SYNTAX  INTEGER (0..1999)
        ACCESS  read-only
        STATUS  mandatory
        DESCRIPTION
                "Physical Unit id"
        ::= { fcsnaGpSdlcEntry 1 }


    fcsnaGpSdlcStatus OBJECT-TYPE
        SYNTAX  INTEGER {
                valid(1),
                invalid(2)
                }
        ACCESS  read-write
        STATUS  mandatory
        DESCRIPTION
                "Status"
        ::= { fcsnaGpSdlcEntry 2 }


    fcsnaGpSdlcLp OBJECT-TYPE
        SYNTAX  INTEGER (0..181)
        ACCESS  read-write
        STATUS  mandatory
        DESCRIPTION
                "Logical Port The value of this object identifies
                one and only one SDLC logical port. The possible
                values are : '0..131'. If it is unused, the value
                of this parameter is '255'. The default value is
                '255'."
        ::= { fcsnaGpSdlcEntry 3 }


    fcsnaGpSdlcCluster OBJECT-TYPE
        SYNTAX  OCTET STRING (SIZE(1))
        ACCESS  read-write
        STATUS  mandatory
        DESCRIPTION
                "Cluster This is the address of the PU of the
                controller."
        ::= { fcsnaGpSdlcEntry 4 }


    fcsnaGpX25Table OBJECT-TYPE
        SYNTAX  SEQUENCE OF FcsnaGpX25Entry
        ACCESS  not-accessible
        STATUS  mandatory
        DESCRIPTION
                ""
        ::= { fcsnaGeneralParameters 4 }


    fcsnaGpX25Entry OBJECT-TYPE
        SYNTAX  FcsnaGpX25Entry
        ACCESS  not-accessible
        STATUS  mandatory
        DESCRIPTION
                "An entry of fcsnaGpX25Table."
        INDEX   { fcsnaGpX25PuId }
        ::= { fcsnaGpX25Table 1 }


        FcsnaGpX25Entry ::=
                SEQUENCE {
                    fcsnaGpX25PuId
                        INTEGER,
                    fcsnaGpX25Status
                        INTEGER,
                    fcsnaGpX25Address
                        OCTET STRING
                }


    fcsnaGpX25PuId OBJECT-TYPE
        SYNTAX  INTEGER (0..1999)
        ACCESS  read-only
        STATUS  mandatory
        DESCRIPTION
                "Physical Unit id"
        ::= { fcsnaGpX25Entry 1 }


    fcsnaGpX25Status OBJECT-TYPE
        SYNTAX  INTEGER {
                valid(1),
                invalid(2)
                }
        ACCESS  read-write
        STATUS  mandatory
        DESCRIPTION
                "Status"
        ::= { fcsnaGpX25Entry 2 }


    fcsnaGpX25Address OBJECT-TYPE
        SYNTAX  OCTET STRING (SIZE(8))
        ACCESS  read-write
        STATUS  mandatory
        DESCRIPTION
                "Adresse X121 Called X121 address. X121 Address of
                the corresponding Hpad element"
        ::= { fcsnaGpX25Entry 3 }


    fcsnaGpLanFrTable OBJECT-TYPE
        SYNTAX  SEQUENCE OF FcsnaGpLanFrEntry
        ACCESS  not-accessible
        STATUS  mandatory
        DESCRIPTION
                ""
        ::= { fcsnaGeneralParameters 5 }


    fcsnaGpLanFrEntry OBJECT-TYPE
        SYNTAX  FcsnaGpLanFrEntry
        ACCESS  not-accessible
        STATUS  mandatory
        DESCRIPTION
                "An entry of fcsnaGpLanFrTable."
        INDEX   { fcsnaGpLanFrPuId }
        ::= { fcsnaGpLanFrTable 1 }


        FcsnaGpLanFrEntry ::=
                SEQUENCE {
                    fcsnaGpLanFrPuId
                        INTEGER,
                    fcsnaGpLanFrStatus
                        INTEGER,
                    fcsnaGpLanFrMacAddress
                        OCTET STRING
                }


    fcsnaGpLanFrPuId OBJECT-TYPE
        SYNTAX  INTEGER (0..1999)
        ACCESS  read-only
        STATUS  mandatory
        DESCRIPTION
                "Physical Unit id"
        ::= { fcsnaGpLanFrEntry 1 }


    fcsnaGpLanFrStatus OBJECT-TYPE
        SYNTAX  INTEGER {
                valid(1),
                invalid(2)
                }
        ACCESS  read-write
        STATUS  mandatory
        DESCRIPTION
                "Status"
        ::= { fcsnaGpLanFrEntry 2 }


    fcsnaGpLanFrMacAddress OBJECT-TYPE
        SYNTAX  OCTET STRING (SIZE(6))
        ACCESS  read-write
        STATUS  mandatory
        DESCRIPTION
                "Adresse MAC This parameter defines the PU MAC
                address."
        ::= { fcsnaGpLanFrEntry 3 }


    fcsnaGpMiscellaneousParameters OBJECT IDENTIFIER ::= { fcsnaGeneralParameters 10 }


    fcsnaGpMiscMacAddrLearningMode OBJECT-TYPE
        SYNTAX  INTEGER {
                off(1),
                on(2)
                }
        ACCESS  read-write
        STATUS  mandatory
        DESCRIPTION
                "The value of this object indicates whether
                automatic MAc address learning is enabled or not.

                The default value is 'off'."
        ::= { fcsnaGpMiscellaneousParameters 1 }


    fcBridge OBJECT IDENTIFIER ::= { frxConfig 35 }


    fcbBridging OBJECT-TYPE
        SYNTAX  INTEGER {
                off(1),
                transparentBridge(2),
                transparentBridgeStp(3)
                }
        ACCESS  read-write
        STATUS  mandatory
        DESCRIPTION
                "The value of this object indicates whether the
                bridge forwards data or not, and if it does
                whether the Spanning Tree Protocol (STP) is
                enabled or not.

                The default value is 'off'."
        ::= { fcBridge 1 }


    fcbBridgingBetweenRemoteVp OBJECT-TYPE
        SYNTAX  INTEGER {
                off(1),
                on(2)
                }
        ACCESS  read-write
        STATUS  mandatory
        DESCRIPTION
                "The value of this object indicates whether the
                bridge forwards data between remote virtual ports
                or not. Disabling this possibility prevents from
                making a way between remote equipments on
                different virtual networks which should not
                exchange data.

                BRIDGING BETWEEN REMOTE VP IS NOT IMPLEMENTED IN
                THIS SOFTWARE VERSION.

                The default value is 'off'."
        ::= { fcBridge 2 }


    fcbTransparentBridge OBJECT IDENTIFIER ::= { fcBridge 10 }


    fcbBrdgVirtualPortTable OBJECT-TYPE
        SYNTAX  SEQUENCE OF FcbBrdgVirtualPortEntry
        ACCESS  not-accessible
        STATUS  mandatory
        DESCRIPTION
                "This table defines the virtual ports used by the
                bridge.

                Set any writable object(s) of this table to valid
                value(s) with a new index value to create an entry
                (the objects of the entry not present in this SET
                REQUEST will take their default values). Set
                fcbBrdgVpStatus to 'invalid' to delete an entry."
        ::= { fcbTransparentBridge 1 }


    fcbBrdgVirtualPortEntry OBJECT-TYPE
        SYNTAX  FcbBrdgVirtualPortEntry
        ACCESS  not-accessible
        STATUS  mandatory
        DESCRIPTION
                "An entry of fcbBrdgVirtualPortTable."
        INDEX   { fcbBrdgVpVirtualPortId }
        ::= { fcbBrdgVirtualPortTable 1 }


        FcbBrdgVirtualPortEntry ::=
                SEQUENCE {
                    fcbBrdgVpVirtualPortId
                        INTEGER,
                    fcbBrdgVpStatus
                        INTEGER,
                    fcbBrdgVpAgingTime
                        INTEGER,
                    fcbBrdgVpBroadcasting
                        INTEGER,
                    fcbBrdgVpFcsPreservation
                        INTEGER
                }


    fcbBrdgVpVirtualPortId OBJECT-TYPE
        SYNTAX  INTEGER (0..11)
        ACCESS  read-only
        STATUS  mandatory
        DESCRIPTION
                "The value of this object identifies one and only
                one virtual port. This virtual port must exist in
                fcvVirtualPortTable.

                This is a decimal integer in the range 0 to 11."
        ::= { fcbBrdgVirtualPortEntry 1 }


    fcbBrdgVpStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcbBrdgVirtualPortEntry 2 }


    fcbBrdgVpAgingTime OBJECT-TYPE
        SYNTAX  INTEGER (0..3600)
        ACCESS  read-write
        STATUS  mandatory
        DESCRIPTION
                "The value of this object is the aging time in
                seconds for addresses learnt on this virtual port.

                This is a decimal integer in the range 0 to 3600.
                The default value is '300'."
        ::= { fcbBrdgVirtualPortEntry 4 }


    fcbBrdgVpBroadcasting OBJECT-TYPE
        SYNTAX  INTEGER {
                off(1),
                on(2)
                }
        ACCESS  read-write
        STATUS  mandatory
        DESCRIPTION
                "The value of this object indicates whether
                broadcasting is enabled or not for this virtual
                port. This function may permit to limit the use of
                expansive WAN links.

                The default value is 'off'."
        ::= { fcbBrdgVirtualPortEntry 5 }


    fcbBrdgVpFcsPreservation OBJECT-TYPE
        SYNTAX  INTEGER {
                off(1),
                offTinygram(3),
                on(2)
                }
        ACCESS  read-write
        STATUS  mandatory
        DESCRIPTION
                "The value of this object indicates whether the FCS
                (Frame Check Sequence) of MAC frames is
                transported over the WAN network or not through
                this virtual port. This value is meaningless for
                local virtual ports.

                The default value is 'off'."
        ::= { fcbBrdgVirtualPortEntry 6 }


    fcbBrdgRemoteAddressMappingTable OBJECT-TYPE
        SYNTAX  SEQUENCE OF FcbBrdgRemoteAddressMappingEntry
        ACCESS  not-accessible
        STATUS  mandatory
        DESCRIPTION
                "This table contains the static entries of the
                address translation table. The transparent Bridge
                function learns dynamically the entries of the
                address translation table. Owing to speed
                considerations or the possibility of learning, it
                may be necessary to create static entries in this
                table.

                Set any writable object(s) of this table to valid
                value(s) with a new index value to create an entry
                (the objects of the entry not present in this SET
                REQUEST will take their default values). Set
                fcbBrdgMapStatus to 'invalid' to delete an entry."
        ::= { fcbTransparentBridge 2 }


    fcbBrdgRemoteAddressMappingEntry OBJECT-TYPE
        SYNTAX  FcbBrdgRemoteAddressMappingEntry
        ACCESS  not-accessible
        STATUS  mandatory
        DESCRIPTION
                "An entry of fcbBrdgRemoteAddressMappingTable."
        INDEX   { fcbBrdgMapMacAddress }
        ::= { fcbBrdgRemoteAddressMappingTable 1 }


        FcbBrdgRemoteAddressMappingEntry ::=
                SEQUENCE {
                    fcbBrdgMapMacAddress
                        OCTET STRING,
                    fcbBrdgMapStatus
                        INTEGER,
                    fcbBrdgMapRemoteAddress
                        OCTET STRING
                }


    fcbBrdgMapMacAddress OBJECT-TYPE
        SYNTAX  OCTET STRING (SIZE(6))
        ACCESS  read-only
        STATUS  mandatory
        DESCRIPTION
                "The value of this object is the MAC address of a
                remote station to be reached through WAN networks.

                This is a six-bytes octet string with 12 digits in
                the range 0 to F. Broadcasting (FF FF FF FF FF
                FF), null (00 00 00 00 00 00) and group (bit 0 of
                first byte equal to 1) addresses must not be used."
        ::= { fcbBrdgRemoteAddressMappingEntry 1 }


    fcbBrdgMapStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fcbBrdgRemoteAddressMappingEntry 2 }


    fcbBrdgMapRemoteAddress OBJECT-TYPE
        SYNTAX  OCTET STRING (SIZE(8))
        ACCESS  read-write
        STATUS  mandatory
        DESCRIPTION
                "The value of this object is the X121 address of a
                remote bridge able to reach this remote station.
                This address must exist in fcvRvpConnectionTable.

                This is a eight-bytes octet string with :
                   up to 15 digits in the range 0 to 9,
                   mandatory 'F' digits to pad the value until a
                        total of 16 digits (the equipment
                        configurator does not need this final
                        padding).

                The default value is 'FF FF FF FF FF FF FF FF'
                meaning 'empty value' (blank value on the
                equipment configurator)."
        ::= { fcbBrdgRemoteAddressMappingEntry 3 }


    fcbSpanningTreeProtocol OBJECT IDENTIFIER ::= { fcBridge 20 }


    fcbStpPriority OBJECT-TYPE
        SYNTAX  INTEGER (0..65535)
        ACCESS  read-write
        STATUS  mandatory
        DESCRIPTION
                "The value of this object is the Bridge Priority
                used in association with the MAC address of the
                Ethernet port by the STP algorithm so as to
                determine from among all the possibilities, the
                bridge that will be elected as topology root. The
                lower the value, the higher the bridge priority..

                This is a decimal integer in the range 0 to 65535.
                The default value is '32768'."
        ::= { fcbSpanningTreeProtocol 1 }


    fcbStpMaxAge OBJECT-TYPE
        SYNTAX  INTEGER (600..4000)
        ACCESS  read-write
        STATUS  mandatory
        DESCRIPTION
                "The value of this object is the maximum age, in
                milliseconds, of STP information learned from the
                network on any virtual port before it is
                discarded. This value is used by all bridges when
                this bridge is acting as the root of the spanning
                tree.

                This maximum age is the life duration assigned to
                a Configuration bridge PDU issued at the
                initiative of the bridge. This life duration will
                be decremented by the various bridges crossed and
                will reach zero, causing the deletion of the
                Configuration bridge PDU.

                This is a decimal integer in the range 600 to
                4000.
                The default value is '2000'."
        ::= { fcbSpanningTreeProtocol 2 }


    fcbStpHelloTime OBJECT-TYPE
        SYNTAX  INTEGER (100..1000)
        ACCESS  read-write
        STATUS  mandatory
        DESCRIPTION
                "The value of this object is the hello time, in
                milliseconds. This is the amount of time between
                the transmissions of Configuration bridge PDUs by
                this node on any virtual port when it is the root
                of the spanning tree or trying to become so. This
                value is used by all bridges when this bridge is
                acting as the root.

                This is a decimal integer in the range 100 to
                1000.
                The default value is '200'."
        ::= { fcbSpanningTreeProtocol 3 }


    fcbStpForwardDelay OBJECT-TYPE
        SYNTAX  INTEGER (400..3000)
        ACCESS  read-write
        STATUS  mandatory
        DESCRIPTION
                "The value of this object is the forward delay, in
                milliseconds. This time value controls how fast a
                virtual port changes its spanning state when
                moving towards the Forwarding state. The value
                determines how long the port stays in each of the
                Listening and Learning states, which precede the
                Forwarding state. This value is also used, when a
                topology change has been detected and is underway,
                to age all dynamic entries in the Forwarding
                Database. This value is the value that this bridge
                and all others would start using if/when this
                bridge were to become the root.
                The Forward Delay value corresponds to the time
                during which the bridge that has just been started
                does not provide its service; it waits until the
                STP has established its topology. During this
                period, only the Configuration bridge PDUs are
                bridged, the user frames are not processed and
                this time delay is also used as minimum duration
                of a bridge state.

                This is a decimal integer in the range 400 to
                3000.
                The default value is '1500'."
        ::= { fcbSpanningTreeProtocol 4 }


    fcbStpVirtualPortTable OBJECT-TYPE
        SYNTAX  SEQUENCE OF FcbStpVirtualPortEntry
        ACCESS  not-accessible
        STATUS  mandatory
        DESCRIPTION
                "This table defines the Spanning Tree Protocol
                parameters of virtual ports.

                It is not possible to add or delete an entry of
                this table (each entry corresponds, in
                fcbBrdgVirtualPortTable, to one instance of
                fcbBrdgVpVirtualPortId)."
        ::= { fcbSpanningTreeProtocol 10 }


    fcbStpVirtualPortEntry OBJECT-TYPE
        SYNTAX  FcbStpVirtualPortEntry
        ACCESS  not-accessible
        STATUS  mandatory
        DESCRIPTION
                "An entry of fcbStpVirtualPortTable."
        INDEX   { fcbStpVpVirtualPortId }
        ::= { fcbStpVirtualPortTable 1 }


        FcbStpVirtualPortEntry ::=
                SEQUENCE {
                    fcbStpVpVirtualPortId
                        INTEGER,
                    fcbStpVpPortPriority
                        INTEGER,
                    fcbStpVpPortPathCost
                        INTEGER,
                    fcbStpVpBpduEncapsulation
                        INTEGER
                }


    fcbStpVpVirtualPortId OBJECT-TYPE
        SYNTAX  INTEGER (0..11)
        ACCESS  read-only
        STATUS  mandatory
        DESCRIPTION
                "The value of this object identifies one and only
                one virtual port. Each virtual port corresponds,
                in fcbBrdgVirtualPortTable, to one instance of
                fcbBrdgVpVirtualPortId.

                This is a decimal integer in the range 0 to 11."
        ::= { fcbStpVirtualPortEntry 1 }


    fcbStpVpPortPriority OBJECT-TYPE
        SYNTAX  INTEGER (0..255)
        ACCESS  read-write
        STATUS  mandatory
        DESCRIPTION
                "The value of this object is the priority field
                which is contained in the first (in network byte
                order) octet of the (2 octet long) Port ID. The
                other octet of the Port ID is given by the value
                of fcbStpVpVirtualPortId.

                The port priority is used with its extra cost and
                its MAC address for the STP algorithm in order to
                grade the ports of the bridge in order of
                preference. This concept is used by the STP
                algorithm to elect the root port and to detect a
                loop so as to determine the port to be cut off.

                This is a decimal integer in the range 0 to 255.
                The default value is '128'."
        ::= { fcbStpVirtualPortEntry 2 }


    fcbStpVpPortPathCost OBJECT-TYPE
        SYNTAX  INTEGER (1..65535)
        ACCESS  read-write
        STATUS  mandatory
        DESCRIPTION
                "The value of this object is the contribution of
                this port to the path cost of paths towards the
                spanning tree root which include this port.
                802.1D-1990 recommends that the default value of
                this parameter be in inverse proportion to the
                speed of the attached virtual network.

                The path cost of the port is used jointly with its
                priority and its MAC address by the STP algorithm
                in order to classify the bridge ports in order of
                preference. Thge lower the cost, the better
                preferred is the port. This concept is used by the
                STP algorithm on initialization to elect the root
                port and when a loop is detected in order to
                determine which port is to be cut off.

                This is a decimal integer in the range 1 to 65535.
                The default value is '100'."
        ::= { fcbStpVirtualPortEntry 3 }


    fcbStpVpBpduEncapsulation OBJECT-TYPE
        SYNTAX  INTEGER {
                mac(1),
                bpdu(2)
                }
        ACCESS  read-write
        STATUS  mandatory
        DESCRIPTION
                "The value of this object indicates, for the remote
                virtual ports, how the STP frames are encapsulated
                on the WAN virtual network. This value is
                meaningless for local virtual ports :
                   mac : STP frames are encapsulated in SNAP
                        802.3,
                   bpdu : STP frames are encapsulated in SNAP
                        BPDU.

                The default value is 'mac'."
        ::= { fcbStpVirtualPortEntry 4 }


    fcIpRouter OBJECT IDENTIFIER ::= { frxConfig 36 }


    fciIpRouting OBJECT-TYPE
        SYNTAX  INTEGER {
                off(1),
                on(2)
                }
        ACCESS  read-write
        STATUS  mandatory
        DESCRIPTION
                "The value of this object indicates whether the
                equipment is acting as an IP gateway in respect to
                the forwarding of IP datagrams received by, but
                not addressed to, this entity. IP gateways forward
                IP datagrams. IP hosts do not.

                The default value is 'off'."
        ::= { fcIpRouter 1 }


    fciFastIpRouting OBJECT-TYPE
        SYNTAX  INTEGER {
                off(1),
                on(2)
                }
        ACCESS  read-write
        STATUS  mandatory
        DESCRIPTION
                "The value of this object indicates whether the
                optimized forwarding of IP datagrams is enabled or
                not. This optimization consist in reducing the
                validity checks carried out on each IP datagram.

                The default value is 'off'."
        ::= { fcIpRouter 2 }


    fciIcmpRedirection OBJECT-TYPE
        SYNTAX  INTEGER {
                off(1),
                on(2)
                }
        ACCESS  read-write
        STATUS  mandatory
        DESCRIPTION
                "The value of this object indicates whether the
                ICMP (Internet Control Message Protocol) Redirect
                messages are sent or not.

                The default value is 'off'."
        ::= { fcIpRouter 3 }


    fciSourceRouting OBJECT-TYPE
        SYNTAX  INTEGER {
                off(1),
                on(2)
                }
        ACCESS  read-write
        STATUS  mandatory
        DESCRIPTION
                "The value of this object indicates whether the
                Source Routing information is inserted in the
                forwarded IP datagrams or not.

                The default value is 'off'."
        ::= { fcIpRouter 4 }


    fciVirtualPortTable OBJECT-TYPE
        SYNTAX  SEQUENCE OF FciVirtualPortEntry
        ACCESS  not-accessible
        STATUS  mandatory
        DESCRIPTION
                "This table defines the virtual ports used by the
                IP router.

                Set any writable object(s) of this table to valid
                value(s) with a new index value to create an entry
                (the objects of the entry not present in this SET
                REQUEST will take their default values). Set
                fciVpStatus to 'invalid' to delete an entry."
        ::= { fcIpRouter 10 }


    fciVirtualPortEntry OBJECT-TYPE
        SYNTAX  FciVirtualPortEntry
        ACCESS  not-accessible
        STATUS  mandatory
        DESCRIPTION
                "An entry of fciVirtualPortTable."
        INDEX   { fciVpVirtualPortId }
        ::= { fciVirtualPortTable 1 }


        FciVirtualPortEntry ::=
                SEQUENCE {
                    fciVpVirtualPortId
                        INTEGER,
                    fciVpStatus
                        INTEGER,
                    fciVpIpAddress
                        IpAddress,
                    fciVpNetMask
                        IpAddress,
                    fciVpMtu
                        INTEGER,
                    fciVpProxyArp
                        INTEGER,
                    fciVpInverseArp
                        INTEGER
                }


    fciVpVirtualPortId OBJECT-TYPE
        SYNTAX  INTEGER (0..11)
        ACCESS  read-only
        STATUS  mandatory
        DESCRIPTION
                "The value of this object identifies one and only
                one virtual port. This virtual port must exist in
                fcvVirtualPortTable.

                This is a decimal integer in the range 0 to 11."
        ::= { fciVirtualPortEntry 1 }


    fciVpStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fciVirtualPortEntry 2 }


    fciVpIpAddress OBJECT-TYPE
        SYNTAX  IpAddress
        ACCESS  read-write
        STATUS  mandatory
        DESCRIPTION
                "The value of this object is the IP address
                associated with this virtual port. This IP address
                must be a valid host address.

                The default value is '0.0.0.0'."
        ::= { fciVirtualPortEntry 3 }


    fciVpNetMask OBJECT-TYPE
        SYNTAX  IpAddress
        ACCESS  read-write
        STATUS  mandatory
        DESCRIPTION
                "The value of this object is the subnet mask
                associated with the IP address of this virtual
                port. The value of the mask is an IP address with
                all the network bits set to 1 and all the hosts
                bits set to 0. In the absence of subnets, the mask
                contains 255.0.0.0 for an address of class A,
                255.255.0.0 for class B, 255.255.255.0 for class
                C.

                The default value is '255.255.255.0'."
        ::= { fciVirtualPortEntry 4 }


    fciVpMtu OBJECT-TYPE
        SYNTAX  INTEGER (576..9180)
        ACCESS  read-write
        STATUS  mandatory
        DESCRIPTION
                "The value of this object defines, in octets, the
                largest IP datagram (Maximum Transmit Unit) which
                can be sent/received on this virtual port.

                This is a decimal integer in the range 576 to
                9180.
                The default value is '1500'."
        ::= { fciVirtualPortEntry 5 }


    fciVpProxyArp OBJECT-TYPE
        SYNTAX  INTEGER {
                off(1),
                on(2)
                }
        ACCESS  read-write
        STATUS  mandatory
        DESCRIPTION
                "The value of this object indicates whether the
                proxy-ARP processing is enabled or not.

                The default value is 'off'."
        ::= { fciVirtualPortEntry 6 }


    fciVpInverseArp OBJECT-TYPE
        SYNTAX  INTEGER {
                off(1),
                on(2)
                }
        ACCESS  read-write
        STATUS  mandatory
        DESCRIPTION
                "For all connections without IP address association
                on an IP VP, this parameter activate an InverseARP
                resolution.

                The default value is 'off'."
        ::= { fciVirtualPortEntry 7 }


    fciLocalVirtualPortTable OBJECT-TYPE
        SYNTAX  SEQUENCE OF FciLocalVirtualPortEntry
        ACCESS  not-accessible
        STATUS  mandatory
        DESCRIPTION
                "This table defines the local virtual ports used by
                the IP router.

                Set any writable object(s) of this table to valid
                value(s) with a new index value to create an entry
                (the objects of the entry not present in this SET
                REQUEST will take their default values). Set
                fciLvpStatus to 'invalid' to delete an entry."
        ::= { fcIpRouter 11 }


    fciLocalVirtualPortEntry OBJECT-TYPE
        SYNTAX  FciLocalVirtualPortEntry
        ACCESS  not-accessible
        STATUS  mandatory
        DESCRIPTION
                "An entry of fciLocalVirtualPortTable."
        INDEX   { fciLvpVirtualPortId }
        ::= { fciLocalVirtualPortTable 1 }


        FciLocalVirtualPortEntry ::=
                SEQUENCE {
                    fciLvpVirtualPortId
                        INTEGER,
                    fciLvpStatus
                        INTEGER,
                    fciLvpEncapsulation
                        INTEGER
                }


    fciLvpVirtualPortId OBJECT-TYPE
        SYNTAX  INTEGER (0..11)
        ACCESS  read-only
        STATUS  mandatory
        DESCRIPTION
                "The value of this object identifies one and only
                one local virtual port. This local virtual port
                must exist in fciVirtualPortTable and in
                fcvLocalVirtualPortTable.

                This is a decimal integer in the range 0 to 11."
        ::= { fciLocalVirtualPortEntry 1 }


    fciLvpStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fciLocalVirtualPortEntry 2 }


    fciLvpEncapsulation OBJECT-TYPE
        SYNTAX  INTEGER {
                ethernet(1),
                ieee802-3(2),
                monoRing(3),
                multiArb(4),
                multiSrb(5)
                }
        ACCESS  read-write
        STATUS  mandatory
        DESCRIPTION
                "The value of this object indicates, for this local
                virtual ports, how the IP datagrams are
                encapsulated on the LAN virtual network :
                   ethernet : IP datagrams are encapsulated
                        according to Ethernet V2 standard,
                   ieee802-3 : IP datagrams are encapsulated
                        according to IEEE 802.3 standard.

                The default value is 'ethernet'."
        ::= { fciLocalVirtualPortEntry 3 }


    fciLocalClusterTable OBJECT-TYPE
        SYNTAX  SEQUENCE OF FciLocalClusterEntry
        ACCESS  not-accessible
        STATUS  mandatory
        DESCRIPTION
                ""
        ::= { fcIpRouter 12 }


    fciLocalClusterEntry OBJECT-TYPE
        SYNTAX  FciLocalClusterEntry
        ACCESS  not-accessible
        STATUS  mandatory
        DESCRIPTION
                "An entry of fciLocalClusterTable."
        INDEX   { fciLclVirtualPortId,
                  fciLclClusterNumber }
        ::= { fciLocalClusterTable 1 }


        FciLocalClusterEntry ::=
                SEQUENCE {
                    fciLclVirtualPortId
                        INTEGER,
                    fciLclClusterNumber
                        INTEGER,
                    fciLclStatus
                        INTEGER,
                    fciLclVirtualIpAddress
                        IpAddress,
                    fciLclPriority
                        INTEGER
                }


    fciLclVirtualPortId OBJECT-TYPE
        SYNTAX  INTEGER (0..11)
        ACCESS  read-only
        STATUS  mandatory
        DESCRIPTION
                "VP id"
        ::= { fciLocalClusterEntry 1 }


    fciLclClusterNumber OBJECT-TYPE
        SYNTAX  INTEGER (0..255)
        ACCESS  read-only
        STATUS  mandatory
        DESCRIPTION
                "Cluster number"
        ::= { fciLocalClusterEntry 2 }


    fciLclStatus OBJECT-TYPE
        SYNTAX  INTEGER {
                valid(1),
                invalid(2)
                }
        ACCESS  read-write
        STATUS  mandatory
        DESCRIPTION
                "Status"
        ::= { fciLocalClusterEntry 3 }


    fciLclVirtualIpAddress OBJECT-TYPE
        SYNTAX  IpAddress
        ACCESS  read-write
        STATUS  mandatory
        DESCRIPTION
                "Virtual IP Address"
        ::= { fciLocalClusterEntry 4 }


    fciLclPriority OBJECT-TYPE
        SYNTAX  INTEGER (0..255)
        ACCESS  read-write
        STATUS  mandatory
        DESCRIPTION
                "Priority"
        ::= { fciLocalClusterEntry 5 }


    fciRemoteNetToMediaTable OBJECT-TYPE
        SYNTAX  SEQUENCE OF FciRemoteNetToMediaEntry
        ACCESS  not-accessible
        STATUS  mandatory
        DESCRIPTION
                "This table contains the IP address translations
                used for mapping from IP address to X121 address
                for each IP router reachable through a WAN virtual
                network.

                Set any writable object(s) of this table to valid
                value(s) with a new index value to create an entry
                (the objects of the entry not present in this SET
                REQUEST will take their default values). Set
                fciRemStatus to 'invalid' to delete an entry."
        ::= { fcIpRouter 15 }


    fciRemoteNetToMediaEntry OBJECT-TYPE
        SYNTAX  FciRemoteNetToMediaEntry
        ACCESS  not-accessible
        STATUS  mandatory
        DESCRIPTION
                "An entry of fciRemoteNetToMediaTable."
        INDEX   { fciRemIpAddress }
        ::= { fciRemoteNetToMediaTable 1 }


        FciRemoteNetToMediaEntry ::=
                SEQUENCE {
                    fciRemIpAddress
                        IpAddress,
                    fciRemStatus
                        INTEGER,
                    fciRemRemoteAddress
                        OCTET STRING
                }


    fciRemIpAddress OBJECT-TYPE
        SYNTAX  IpAddress
        ACCESS  read-only
        STATUS  mandatory
        DESCRIPTION
                "The value of this object is the IP address of one
                IP router reachable through a WAN virtual network.
                This IP address must be a valid host address."
        ::= { fciRemoteNetToMediaEntry 1 }


    fciRemStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fciRemoteNetToMediaEntry 2 }


    fciRemRemoteAddress OBJECT-TYPE
        SYNTAX  OCTET STRING (SIZE(8))
        ACCESS  read-write
        STATUS  mandatory
        DESCRIPTION
                "The value of this object is the X121 address of
                the called remote IP router. This address must
                exist in fcvRvpConnectionTable.

                This is a eight-bytes octet string with :
                   up to 15 digits in the range 0 to 9,
                   mandatory 'F' digits to pad the value until a
                        total of 16 digits (the equipment
                        configurator does not need this final
                        padding).

                The default value is 'FF FF FF FF FF FF FF FF'
                meaning 'empty value' (blank value on the
                equipment configurator)."
        ::= { fciRemoteNetToMediaEntry 3 }


    fciNetToMediaTable OBJECT-TYPE
        SYNTAX  SEQUENCE OF FciNetToMediaEntry
        ACCESS  not-accessible
        STATUS  mandatory
        DESCRIPTION
                "ARP (Address Resolution Protocol) is in charge to
                dynamically manage the IP address translations
                used for mapping from IP address to MAC address
                for each IP host or IP router reachable through a
                LAN. This table contains translations which are
                statically added to the dynamic ones.

                Set any writable object(s) of this table to valid
                value(s) with a new index value to create an entry
                (the objects of the entry not present in this SET
                REQUEST will take their default values). Set
                fciNetToMediaStatus to 'invalid' to delete an
                entry."
        ::= { fcIpRouter 16 }


    fciNetToMediaEntry OBJECT-TYPE
        SYNTAX  FciNetToMediaEntry
        ACCESS  not-accessible
        STATUS  mandatory
        DESCRIPTION
                "An entry of fciNetToMediaTable."
        INDEX   { fciNetToMediaIpAddress }
        ::= { fciNetToMediaTable 1 }


        FciNetToMediaEntry ::=
                SEQUENCE {
                    fciNetToMediaIpAddress
                        IpAddress,
                    fciNetToMediaStatus
                        INTEGER,
                    fciNetToMediaMacAddress
                        OCTET STRING
                }


    fciNetToMediaIpAddress OBJECT-TYPE
        SYNTAX  IpAddress
        ACCESS  read-only
        STATUS  mandatory
        DESCRIPTION
                "The value of this object is the IP address of one
                IP host or IP router reachable through a LAN
                virtual network. This IP address must be a valid
                host address."
        ::= { fciNetToMediaEntry 1 }


    fciNetToMediaStatus OBJECT-TYPE
        SYNTAX  INTEGER {
                valid(1),
                invalid(2)
                }
        ACCESS  read-write
        STATUS  mandatory
        DESCRIPTION
                "The value of this object indicates the state of
                the entry of this table. It must be set to
                'invalid' to delete the entry.

                The default value is 'valid'."
        ::= { fciNetToMediaEntry 2 }


    fciNetToMediaMacAddress OBJECT-TYPE
        SYNTAX  OCTET STRING (SIZE(6))
        ACCESS  read-write
        STATUS  mandatory
        DESCRIPTION
                "The value of this object is the MAC address of
                this IP host or IP router.

                This is a six-bytes octet string with 12 digits in
                the range 0 to F. Broadcasting (FF FF FF FF FF
                FF), null (00 00 00 00 00 00) and group (bit 0 of
                first byte equal to 1) addresses must not be used.

                The default value is 'FF FF FF FF FF FF' meaning
                'empty value' (blank value on the equipment
                configurator)."
        ::= { fciNetToMediaEntry 3 }


    fciIpRouteTable OBJECT-TYPE
        SYNTAX  SEQUENCE OF FciIpRouteEntry
        ACCESS  not-accessible
        STATUS  mandatory
        DESCRIPTION
                "RIP (Routing Information Protocol) or EGP
                (External Gateway Protocol) are in charge to
                dynamically manage the routes used by the IP
                router. This table contains routes which are
                statically added to the dynamic ones."
        ::= { fcIpRouter 20 }


    fciIpRouteEntry OBJECT-TYPE
        SYNTAX  FciIpRouteEntry
        ACCESS  not-accessible
        STATUS  mandatory
        DESCRIPTION
                "An entry of fciIpRouteTable."
        INDEX   { fciRouteDest,
                  fciRouteMask }
        ::= { fciIpRouteTable 1 }


        FciIpRouteEntry ::=
                SEQUENCE {
                    fciRouteDest
                        IpAddress,
                    fciRouteMask
                        IpAddress,
                    fciRouteStatus
                        INTEGER,
                    fciRouteNextHop
                        IpAddress,
                    fciRouteMetric
                        INTEGER
                }


    fciRouteDest OBJECT-TYPE
        SYNTAX  IpAddress
        ACCESS  read-only
        STATUS  mandatory
        DESCRIPTION
                "The value of this object is the destination IP
                address of this route. An entry with a value of
                0.0.0.0 is considered a default route. This IP
                address may be a network address (hosts bits set
                to 0) or a host address (at least one hosts bit
                set to 1).
                The default value is '0.0.0.0'."
        ::= { fciIpRouteEntry 1 }


    fciRouteMask OBJECT-TYPE
        SYNTAX  IpAddress
        ACCESS  read-only
        STATUS  mandatory
        DESCRIPTION
                "The value of this object is the subnet mask
                associated with the IP address of this virtual
                port. The value of the mask is an IP address with
                all the network bits set to 1 and all the hosts
                bits set to 0. In the absence of subnets, the mask
                contains 255.0.0.0 for an address of class A,
                255.255.0.0 for class B, 255.255.255.0 for class
                C.
                If the value of fciRouteDest is 0.0.0.0 (a default
                route), then the mask value is also 0.0.0.0.
                The default value is '255.255.255.0'."
        ::= { fciIpRouteEntry 2 }


    fciRouteStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciIpRouteEntry 3 }


    fciRouteNextHop OBJECT-TYPE
        SYNTAX  IpAddress
        ACCESS  read-write
        STATUS  mandatory
        DESCRIPTION
                "The value of this object is the IP address of the
                next hop of this route. This IP address must be a
                valid host address.
                The default value is '0.0.0.0'."
        ::= { fciIpRouteEntry 4 }


    fciRouteMetric OBJECT-TYPE
        SYNTAX  INTEGER (1..15)
        ACCESS  read-write
        STATUS  mandatory
        DESCRIPTION
                "The value of this object is the routing metric for
                this route. The search algorithm is based on
                metrics for choosing between several possible
                routes to reach the destination of an IP datagram.
                In the case of RIP, the metrics indicates the
                number of IP routers through which an IP datagram
                must pass to reach its destination. The algorithm
                chooses preferably the shortest metric route.
                The authorized values are '1..15'. The default
                value is '1'."
        ::= { fciIpRouteEntry 5 }


    fciFlowManagement OBJECT IDENTIFIER ::= { fcIpRouter 30 }


    fciFlowTable OBJECT-TYPE
        SYNTAX  SEQUENCE OF FciFlowEntry
        ACCESS  not-accessible
        STATUS  mandatory
        DESCRIPTION
                "This table defines the flows. A flow is a
                selection of IP datagrams coming from a local
                virtual port (i.e., froma a LAN)."
        ::= { fciFlowManagement 1 }


    fciFlowEntry OBJECT-TYPE
        SYNTAX  FciFlowEntry
        ACCESS  not-accessible
        STATUS  mandatory
        DESCRIPTION
                "An entry of fciFlowTable."
        INDEX   { fciFlowFlowId }
        ::= { fciFlowTable 1 }


        FciFlowEntry ::=
                SEQUENCE {
                    fciFlowFlowId
                        INTEGER,
                    fciFlowStatus
                        INTEGER,
                    fciFlowType
                        INTEGER,
                    fciFlowVpId
                        INTEGER,
                    fciFlowSrcIpAddress
                        IpAddress,
                    fciFlowSrcMask
                        IpAddress,
                    fciFlowDestIpAddress
                        IpAddress,
                    fciFlowDestMask
                        IpAddress,
                    fciFlowProtocol
                        INTEGER,
                    fciFlowPortMin
                        INTEGER,
                    fciFlowPortMax
                        INTEGER,
                    fciFlowLengthMax
                        INTEGER,
                    fciFlowSegmented
                        INTEGER
                }


    fciFlowFlowId OBJECT-TYPE
        SYNTAX  INTEGER (0..199)
        ACCESS  read-only
        STATUS  mandatory
        DESCRIPTION
                "The value of this object identifies one and only
                one flow. A flow is a selection of IP datagrams
                coming from a local virtual port (i.e., froma a
                LAN). Several flows may belong to the same family.

                This flow uses a combination of several conditions
                defined below. A flow selects the received IP
                datagrams which simultaneously verify those of the
                conditions which are meaningful for this flow.

                When several flows are defined for the same VP
                with overlapping conditions, the IP datagram
                belongs to the first (in increasing order of flow
                identifiers) of all the flows that select it. So
                the numbering order must be done with a particular
                attention.

                By convention, if none of the conditions of this
                entry is meaningful, then every IP datagram is
                selected (default flow).

                The authorized values are '0..199'. If it is
                unused, the value is '255'. The default value is
                '255'."
        ::= { fciFlowEntry 1 }


    fciFlowStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciFlowEntry 2 }


    fciFlowType OBJECT-TYPE
        SYNTAX  INTEGER (0..255)
        ACCESS  read-write
        STATUS  mandatory
        DESCRIPTION
                "The value of this object indicates the family to
                which belong any IP datagram selected by the
                conditions defining this flow. Several flows may
                belong to the same family. The transmission of the
                family of IP datagrams over WAN virtual networks
                is defined by fcvRvpConnFlowTypeMask.

                By convention, the family 0 groups together all
                the IP datagrams that the router has to reject
                (filtering at the IP level) whereas the filtering
                described in fcvLvpFltFilteringTable concerns all
                the traffic received on one of the IP, IPX or CNLP
                routers or bridge.

                The authorized values are : 0, 1, 2, 4, 8, 16, 32,
                64 and 128. The default value is '255'."
        ::= { fciFlowEntry 3 }


    fciFlowVpId OBJECT-TYPE
        SYNTAX  INTEGER (0..11)
        ACCESS  read-write
        STATUS  mandatory
        DESCRIPTION
                "The value of this object specifies the virtual
                port for which the flow is defined. Any IP
                datagram received on this VP will go through the
                evaluations of the meaningful conditions defined
                for this flow and it is selected if all these
                comparisons produce positive results."
        ::= { fciFlowEntry 5 }


    fciFlowSrcIpAddress OBJECT-TYPE
        SYNTAX  IpAddress
        ACCESS  read-write
        STATUS  mandatory
        DESCRIPTION
                "The value of this object specifies the value with
                which the source IP address field of all the IP
                datagrams received on this VP is compared. If the
                bits, selected by fciFlowSrcMask, from this value
                are equal to the same bits from the source IP
                address of a IP datagram then this IP datagram is
                selected.

                This condition on source IP address is meaningless
                if fciFlowSrcMask is equal to '0.0.0.0' (no bits
                selected).

                The authorized values are all four bytes integer
                with an IP address notation but this value is not
                necessarily a valid IP address (e.g. 0.0.0.41 or
                255.0.0.0). The default value is '0.0.0.0'."
        ::= { fciFlowEntry 10 }


    fciFlowSrcMask OBJECT-TYPE
        SYNTAX  IpAddress
        ACCESS  read-write
        STATUS  mandatory
        DESCRIPTION
                "The value of this object specifies the bits from
                fciFlowSrcIpAddress which are to be compared with
                the same bits from the source IP address field of
                all the IP datagrams received on this VP.

                This condition on source IP address is meaningless
                if this mask is equal to '0.0.0.0' (no bits
                selected).

                The authorized values are all four bytes integer
                with an IP address notation but this value is not
                necessarily a valid IP address mask (e.g.,
                0,0,0,127 or 0,255,0,0). The default value is
                '0.0.0.0'."
        ::= { fciFlowEntry 11 }


    fciFlowDestIpAddress OBJECT-TYPE
        SYNTAX  IpAddress
        ACCESS  read-write
        STATUS  mandatory
        DESCRIPTION
                "The value of this object specifies the value with
                which the destination IP address field of all the
                IP datagrams received on this VP is compared. If
                the bits, selected by fciFlowDestMask, from this
                value are equal to the same bits from the
                destination IP address of a IP datagram then this
                IP datagram is selected.

                This condition on destination IP address is
                meaningless if fciFlowDestMask is equal to
                '0.0.0.0' (no bits selected).

                The authorized values are all four bytes integer
                with an IP address notation but this value is not
                necessarily a valid IP address (e.g. 0.0.0.41 or
                255.0.0.0). The default value is '0.0.0.0'."
        ::= { fciFlowEntry 12 }


    fciFlowDestMask OBJECT-TYPE
        SYNTAX  IpAddress
        ACCESS  read-write
        STATUS  mandatory
        DESCRIPTION
                "The value of this object specifies the bits from
                fciFlowDestIpAddress which are to be compared with
                the same bits from the destination IP address
                field of all the IP datagrams received on this VP.

                This condition on destination IP address is
                meaningless if this mask is equal to '0.0.0.0' (no
                bits selected).

                The authorized values are all four bytes integer
                with an IP address notation but this value is not
                necessarily a valid IP address mask (e.g.,
                0,0,0,127 or 0,255,0,0). The default value is
                '0.0.0.0'."
        ::= { fciFlowEntry 13 }


    fciFlowProtocol OBJECT-TYPE
        SYNTAX  INTEGER (0..255)
        ACCESS  read-write
        STATUS  mandatory
        DESCRIPTION
                "The value of this object specifies the value with
                which the protocol field of all the IP datagrams
                received on this VP is compared. If these two
                values are equal then the IP datagram is selected.

                This field identifies the protocol transported by
                IP (see PROTOCOL NUMBERS in RFC 1700).  E.g. 1 =
                ICMP, 6 = TCP, 8 = EGP, 17 = UDP ...

                This condition on protocol is meaningless if this
                value is equal to '0'.

                The authorized values are '0..255'. The default
                value is '0'."
        ::= { fciFlowEntry 14 }


    fciFlowPortMin OBJECT-TYPE
        SYNTAX  INTEGER (0..65535)
        ACCESS  read-write
        STATUS  mandatory
        DESCRIPTION
                "The value of this object specifies the minimum
                value with which the source port and destination
                port fields of all the TCP/IP or UDP/IP datagrams
                received on this VP are compared.

                When fciFlowPortMax > fciFlowPortMin > 0, if the
                value of at least one of the two fields from the
                IP datagram is included inside these limits then
                the IP datagram is selected.

                When fciFlowPortMax > 0 and fciFlowPortMin = 0, if
                the value of at least one of the two fields from
                the IP datagram is equal to fciFlowPortMax then
                the IP datagram is selected.

                When fciFlowPortMax = 0 and fciFlowPortMin > 0, if
                the value of at least one of the two fields from
                the IP datagram is equal to fciFlowPortMin then
                the IP datagram is selected.

                When fciFlowPortMax = fciFlowPortMin = 0, this
                condition on ports is meaningless.

                   Examples : (see WELL KNOWN PORT NUMBERS in RFC
                        1700); 21 = ftp, 23 = telnet, 67 = bootp
                        server, 68 = bootp client, 69 = ttfp, 161
                        = snmp, 162 = snmptrap.

                The authorized values are '0..65535'. The default
                value is '0'."
        ::= { fciFlowEntry 15 }


    fciFlowPortMax OBJECT-TYPE
        SYNTAX  INTEGER (0..65535)
        ACCESS  read-write
        STATUS  mandatory
        DESCRIPTION
                "The value of this object specifies the maximum
                value with which the source port and destination
                port fields of all the TCP/IP or UDP/IP datagrams
                received on this VP are compared.

                When fciFlowPortMax > fciFlowPortMin > 0, if the
                value of at least one of the two fields from the
                IP datagram is included inside these limits then
                the IP datagram is selected.

                When fciFlowPortMax > 0 and fciFlowPortMin = 0, if
                the value of at least one of the two fields from
                the IP datagram is equal to fciFlowPortMax then
                the IP datagram is selected.

                When fciFlowPortMax = 0 and fciFlowPortMin > 0, if
                the value of at least one of the two fields from
                the IP datagram is equal to fciFlowPortMin then
                the IP datagram is selected.

                When fciFlowPortMax = fciFlowPortMin = 0, this
                condition on ports is meaningless.

                   Examples : (see WELL KNOWN PORT NUMBERS in RFC
                        1700); 21 = ftp, 23 = telnet, 67 = bootp
                        server, 68 = bootp client, 69 = ttfp, 161
                        = snmp, 162 = snmptrap.

                The authorized values are '0..65535'. The default
                value is '0'."
        ::= { fciFlowEntry 16 }


    fciFlowLengthMax OBJECT-TYPE
        SYNTAX  INTEGER (0..65535)
        ACCESS  read-write
        STATUS  mandatory
        DESCRIPTION
                "The value of this object specifies the value with
                which the length of all the IP datagrams received
                on this VP are compared. If the number of octets
                in the IP datagram is less or equal to this value
                then the IP datagram is selected.

                This condition on length is meaningless if this
                value is equal to '0'.

                The authorized values are '0..65535'. The default
                value is '0'."
        ::= { fciFlowEntry 17 }


    fciFlowSegmented OBJECT-TYPE
        SYNTAX  INTEGER {
                notChecked(1),
                no(2),
                yes(3)
                }
        ACCESS  read-write
        STATUS  mandatory
        DESCRIPTION
                "The value of this object specifies the selection
                of segmented IP datagrams received on this VP :
                   notChecked : This condition on segmentation is
                        meaningless.
                   no  : The IP datagrams not segmented are
                        selected.
                   yes  : The IP datagrams segmented are selected.

                The default value is 'notChecked'."
        ::= { fciFlowEntry 18 }


    fciFlowAddrSubstituteTable OBJECT-TYPE
        SYNTAX  SEQUENCE OF FciFlowAddrSubstituteEntry
        ACCESS  not-accessible
        STATUS  mandatory
        DESCRIPTION
                "This table is used for replacing the IP
                destination address contained in every IP datagram
                belonging to a specific flow by a precise IP
                address. This substitution takes place before the
                frame is examined by the IP routing.

                Therefore, it is possible, for instance, to orient
                the IP/UDP traffic distributed towards a specific
                recipient.."
        ::= { fciFlowManagement 2 }


    fciFlowAddrSubstituteEntry OBJECT-TYPE
        SYNTAX  FciFlowAddrSubstituteEntry
        ACCESS  not-accessible
        STATUS  mandatory
        DESCRIPTION
                "An entry of fciFlowAddrSubstituteTable."
        INDEX   { fciFlowSubstFlowId,
                  fciFlowSubstDestIpAddress }
        ::= { fciFlowAddrSubstituteTable 1 }


        FciFlowAddrSubstituteEntry ::=
                SEQUENCE {
                    fciFlowSubstFlowId
                        INTEGER,
                    fciFlowSubstDestIpAddress
                        IpAddress,
                    fciFlowSubstStatus
                        INTEGER
                }


    fciFlowSubstFlowId OBJECT-TYPE
        SYNTAX  INTEGER (0..199)
        ACCESS  read-only
        STATUS  mandatory
        DESCRIPTION
                "The value of this object identifies one and only
                one flow. A flow is a selection of IP datagrams
                coming from a local virtual port (i.e., froma a
                LAN). It must exist in fciFlowTable.

                The authorized values are '0..199'. If it is
                unused, the value is '255'. The default value is
                '255'."
        ::= { fciFlowAddrSubstituteEntry 1 }


    fciFlowSubstDestIpAddress OBJECT-TYPE
        SYNTAX  IpAddress
        ACCESS  read-only
        STATUS  mandatory
        DESCRIPTION
                "The value of this object is the new destination IP
                address which replaces the existing one in all IP
                datagrams belonging to this flow. This IP address
                must be a broadcasting IP address (hosts bits set
                to 1) or a host address (at least one hosts bit
                set to 1).
                The default value is '0.0.0.0'."
        ::= { fciFlowAddrSubstituteEntry 2 }


    fciFlowSubstStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciFlowAddrSubstituteEntry 3 }


    fciFlowRouteTable OBJECT-TYPE
        SYNTAX  SEQUENCE OF FciFlowRouteEntry
        ACCESS  not-accessible
        STATUS  mandatory
        DESCRIPTION
                "This table contains routes which are statically
                defined for particular flows (this permits to
                bypass the normal IP routing process)."
        ::= { fciFlowManagement 20 }


    fciFlowRouteEntry OBJECT-TYPE
        SYNTAX  FciFlowRouteEntry
        ACCESS  not-accessible
        STATUS  mandatory
        DESCRIPTION
                "An entry of fciFlowRouteTable."
        INDEX   { fciFlowRouteFlowId }
        ::= { fciFlowRouteTable 1 }


        FciFlowRouteEntry ::=
                SEQUENCE {
                    fciFlowRouteFlowId
                        INTEGER,
                    fciFlowRouteStatus
                        INTEGER,
                    fciFlowRouteNextHop
                        IpAddress
                }


    fciFlowRouteFlowId OBJECT-TYPE
        SYNTAX  INTEGER (0..199)
        ACCESS  read-only
        STATUS  mandatory
        DESCRIPTION
                "The value of this object identifies one and only
                one flow. A flow is a selection of IP datagrams
                coming from a local virtual port (i.e., froma a
                LAN). It must exist in fciFlowTable.

                The authorized values are '0..199'. If it is
                unused, the value is '255'. The default value is
                '255'."
        ::= { fciFlowRouteEntry 1 }


    fciFlowRouteStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciFlowRouteEntry 2 }


    fciFlowRouteNextHop OBJECT-TYPE
        SYNTAX  IpAddress
        ACCESS  read-write
        STATUS  mandatory
        DESCRIPTION
                "The value of this object is the IP address of the
                next hop of the route used by this flow. This IP
                address must be a valid host address.
                The default value is '0.0.0.0'."
        ::= { fciFlowRouteEntry 3 }


    fciRip OBJECT IDENTIFIER ::= { fcIpRouter 40 }


    fciRipAdminStatus OBJECT-TYPE
        SYNTAX  INTEGER {
                off(1),
                on(2),
                quiet(3)
                }
        ACCESS  read-write
        STATUS  mandatory
        DESCRIPTION
                "The value of this object indicates whether RIP
                (Routing Information Protocol) is enabled or not :
                   off : RIP is not enabled,
                   on : RIP is enabled in 'active mode (it learns
                        the routes transmitted by the adjacents
                        routers to complete the routing table and
                        itself distributes all or part of the
                        routes contained in the routing table),
                   quiet : RIP is enabled in 'passive mode (it
                        learns the routes transmitted by the
                        adjacents routers to complete the routing
                        table but itself does not distribute
                        anything).
                The default value is 'off'."
        ::= { fciRip 1 }


    fciRipStaticRoutesDistribution OBJECT-TYPE
        SYNTAX  INTEGER {
                off(1),
                on(2)
                }
        ACCESS  read-write
        STATUS  mandatory
        DESCRIPTION
                "The value of this object indicates whether RIP
                distributes static entries of the routing table
                (i.e., those defined in fciIpRouteTable) or not.
                The default value is 'off'."
        ::= { fciRip 2 }


    fciRipEgpRoutesDistribution OBJECT-TYPE
        SYNTAX  INTEGER {
                off(1),
                on(2)
                }
        ACCESS  read-write
        STATUS  mandatory
        DESCRIPTION
                "The value of this object indicates whether RIP
                distributes entries of the routing table learnt by
                EGP (Exterior Gateway Protocol) or not. The
                autonomous systems from which these routing
                informations are distributed are defined in
                fciRipEgpRoutesDistributionTable.
                The default value is 'off'."
        ::= { fciRip 3 }


    fciRipDistributionTimer OBJECT-TYPE
        SYNTAX  INTEGER (30..3600)
        ACCESS  read-write
        STATUS  mandatory
        DESCRIPTION
                "The value of this object indicates the waiting
                time in seconds between two successive
                transmissions of informations from the routing
                table by RIP.
                The authorized values are '30..3600'. The default
                value is '30'."
        ::= { fciRip 4 }


    fciRipPreference OBJECT-TYPE
        SYNTAX  INTEGER (0..255)
        ACCESS  read-write
        STATUS  mandatory
        DESCRIPTION
                " The value of this object controls preference for
                routes learned (imported) by RIP, relative to
                routes to same destination learned by others
                protocols.
                '0' is high preference. '255' is low preference."
        ::= { fciRip 5 }


    fciRipOspfRoutesDistribution OBJECT-TYPE
        SYNTAX  INTEGER {
                off(1),
                on(2)
                }
        ACCESS  read-write
        STATUS  mandatory
        DESCRIPTION
                "The value of this object indicates whether RIP
                distributes entries of the routing table learnt by
                OSPF (Open Shortest Path First) protocol or not.
                The metric used is specified by the field
                fciRipOspfRoutesDistributionMetric."
        ::= { fciRip 6 }


    fciRipOspfRoutesDistributionMetric OBJECT-TYPE
        SYNTAX  INTEGER (0..16)
        ACCESS  read-write
        STATUS  mandatory
        DESCRIPTION
                " The value of this object indicates the metric
                used by RIP when propagating (exporting) routes
                learnt via OSPF.
                "
        ::= { fciRip 7 }


    fciRipStaticRoutesDistributionMetric OBJECT-TYPE
        SYNTAX  INTEGER (0..16)
        ACCESS  read-write
        STATUS  mandatory
        DESCRIPTION
                "The value of this object indicates the metric used
                by RIP when propagating (exporting) static routes.
                "
        ::= { fciRip 8 }


    fciRipVirtualPortTable OBJECT-TYPE
        SYNTAX  SEQUENCE OF FciRipVirtualPortEntry
        ACCESS  not-accessible
        STATUS  mandatory
        DESCRIPTION
                "This table defines the RIP parameters of virtual
                ports. This table is meaningless if there is at
                least one entry in fciRipNeighborTable (in this
                case RIP learns [and/or sends] routing
                informations only from [and/or to] the neighbors
                defined in that table)."
        ::= { fciRip 10 }


    fciRipVirtualPortEntry OBJECT-TYPE
        SYNTAX  FciRipVirtualPortEntry
        ACCESS  not-accessible
        STATUS  mandatory
        DESCRIPTION
                "An entry of fciRipVirtualPortTable."
        INDEX   { fciRipVpVirtualPortId }
        ::= { fciRipVirtualPortTable 1 }


        FciRipVirtualPortEntry ::=
                SEQUENCE {
                    fciRipVpVirtualPortId
                        INTEGER,
                    fciRipVpDistribution
                        INTEGER,
                    fciRipVpMetricOut
                        INTEGER,
                    fciRipVpRipIn
                        INTEGER,
                    fciRipVpMetricIn
                        INTEGER,
                    fciRipVpVersion
                        INTEGER,
                    fciRipVpMulticast
                        INTEGER,
                    fciRipVpAuthType
                        INTEGER,
                    fciRipVpAuthKey
                        DisplayString
                }


    fciRipVpVirtualPortId OBJECT-TYPE
        SYNTAX  INTEGER (0..35)
        ACCESS  read-only
        STATUS  mandatory
        DESCRIPTION
                "The value of this object identifies one and only
                one virtual port.
                The authorized values are '0..199'. If it is
                unused, the value is '255'. The default value is
                '255'."
        ::= { fciRipVirtualPortEntry 1 }


    fciRipVpDistribution OBJECT-TYPE
        SYNTAX  INTEGER {
                off(1),
                on(2)
                }
        ACCESS  read-write
        STATUS  mandatory
        DESCRIPTION
                "The value of this object indicates whether
                performs its information exchanges on the IP
                network attached to this virtual port or not.
                The default value is 'on'."
        ::= { fciRipVirtualPortEntry 2 }


    fciRipVpMetricOut OBJECT-TYPE
        SYNTAX  INTEGER (0..16)
        ACCESS  read-write
        STATUS  mandatory
        DESCRIPTION
                "The RIP output metric of this interface. This
                metric will be added to routes that are send via
                the interface. This parameter can be used to make
                other routers prefer other sources of RIP routes
                over this router."
        ::= { fciRipVirtualPortEntry 3 }


    fciRipVpRipIn OBJECT-TYPE
        SYNTAX  INTEGER {
                off(1),
                on(2)
                }
        ACCESS  read-write
        STATUS  mandatory
        DESCRIPTION
                "The RIP input interface's administrative status.
                The value 'on' denotes that RIP packets received
                on this interface will be accepted. The value
                'off' denotes that no RIP received packets will be
                accepted."
        ::= { fciRipVirtualPortEntry 4 }


    fciRipVpMetricIn OBJECT-TYPE
        SYNTAX  INTEGER (0..16)
        ACCESS  read-write
        STATUS  mandatory
        DESCRIPTION
                "The RIP input metric of this interface. This
                metric will be added to incoming routes before
                they are installed in the routing table. This
                parameter can be used to make this router prefer
                RIP routes learned via the specified interface
                less than RIP routes from other interface."
        ::= { fciRipVirtualPortEntry 5 }


    fciRipVpVersion OBJECT-TYPE
        SYNTAX  INTEGER {
                ripVersion1(1),
                ripVersion2(2)
                }
        ACCESS  read-write
        STATUS  mandatory
        DESCRIPTION
                "The RIP output packets version. The value of  this
                object indicates the version of RIP packets sent
                on the interface. The value 'ripVersion1' implies
                sending RIP updates compliant  with  RFC  1058.
                'ripVersion2' implies sending RIP updates
                compliant with RFC 1388."
        ::= { fciRipVirtualPortEntry 6 }


    fciRipVpMulticast OBJECT-TYPE
        SYNTAX  INTEGER {
                off(1),
                on(2),
                other(3)
                }
        ACCESS  read-write
        STATUS  mandatory
        DESCRIPTION
                "The RIP-2 multicast output interface's
                administrative status. The value 'on' implies
                sending RIP updates using the multicast capability."
        ::= { fciRipVirtualPortEntry 7 }


    fciRipVpAuthType OBJECT-TYPE
        SYNTAX  INTEGER {
                noAuthentication(1),
                simplePassword(2),
                other(3)
                }
        ACCESS  read-write
        STATUS  mandatory
        DESCRIPTION
                "Type of authentication shema used on the interface."
        ::= { fciRipVirtualPortEntry 8 }


    fciRipVpAuthKey OBJECT-TYPE
        SYNTAX  DisplayString (SIZE(0..16))
        ACCESS  read-write
        STATUS  mandatory
        DESCRIPTION
                "The value to be used as the Authentication Key
                whenever the corresponding instance of
                fciRipVpAuthType has the value simplePassword. A
                modification of the corresponding instance of
                fciRipVpAuthType does not modify the
                fciRipVpAuthKey value. If a string shorter than 16
                octets is supplied, it will be left-justified and
                padded to 16 octets, on the right, with nulls
                (0x00). Reading this object always results in an 
                OCTET STRING  of  length zero; authentication may
                not be bypassed by reading the MIB object."
        ::= { fciRipVirtualPortEntry 9 }


    fciRipNeighborTable OBJECT-TYPE
        SYNTAX  SEQUENCE OF FciRipNeighborEntry
        ACCESS  not-accessible
        STATUS  mandatory
        DESCRIPTION
                "This table defines the neighbors (i.e., the
                adjacent routers with RIP enabled) with witch RIP
                exchange routing informations. If this table is
                empty RIP uses fciRipVirtualPortTable."
        ::= { fciRip 20 }


    fciRipNeighborEntry OBJECT-TYPE
        SYNTAX  FciRipNeighborEntry
        ACCESS  not-accessible
        STATUS  mandatory
        DESCRIPTION
                "An entry of fciRipNeighborTable."
        INDEX   { fciRipNeighborIpAddress }
        ::= { fciRipNeighborTable 1 }


        FciRipNeighborEntry ::=
                SEQUENCE {
                    fciRipNeighborIpAddress
                        IpAddress,
                    fciRipNeighborStatus
                        INTEGER,
                    fciRipNeighborOutput
                        INTEGER,
                    fciRipNeighborInput
                        INTEGER,
                    fciRipNeighborBackupGroup
                        INTEGER
                }


    fciRipNeighborIpAddress OBJECT-TYPE
        SYNTAX  IpAddress
        ACCESS  read-only
        STATUS  mandatory
        DESCRIPTION
                "The value of this object is the IP address of a
                neighbor (i.e., an adjacent router with RIP
                enabled). This IP address must be a valid host
                address.
                The default value is '0.0.0.0'."
        ::= { fciRipNeighborEntry 1 }


    fciRipNeighborStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciRipNeighborEntry 2 }


    fciRipNeighborOutput OBJECT-TYPE
        SYNTAX  INTEGER {
                off(1),
                on(2),
                bck(3),
                on1(4),
                bk1(5)
                }
        ACCESS  read-write
        STATUS  mandatory
        DESCRIPTION
                " This flag indicates whether the neighbor is a
                gateway to which RIP will send RIP packets (value
                :  on  or  on V1 ) or not (value :  off ). If the
                value is  bck  or  bck V1 , RIP will send packets
                only if all members of the RIP backup group are
                down.
                The value  on  or  bck  force RIP to send RIP V2
                packets if the RIP output packets version on that
                VP is RIP V2, or to send RIP V1 packets if the RIP
                output packets version on that VP is RIP V1.
                The value  on V1  or  bck V1 , is used when the
                neighbor doesn't support RIP V2, that value force
                RIP to send RIP V1 compatible packets compliant
                with RFC 1388."
        ::= { fciRipNeighborEntry 3 }


    fciRipNeighborInput OBJECT-TYPE
        SYNTAX  INTEGER {
                off(1),
                on(2)
                }
        ACCESS  read-write
        STATUS  mandatory
        DESCRIPTION
                " This flag indicates whether the neighbor is a
                gateway from which RIP will accept RIP packets or
                not.
                "
        ::= { fciRipNeighborEntry 4 }


    fciRipNeighborBackupGroup OBJECT-TYPE
        SYNTAX  INTEGER (1..255)
        ACCESS  read-write
        STATUS  mandatory
        DESCRIPTION
                " This flag indicates the RIP backup group number
                of the neighbor. If the neighbor doesn't belong to
                a group, the value is 255 (default value)."
        ::= { fciRipNeighborEntry 5 }


    fciRipEgpRoutesDistributionTable OBJECT-TYPE
        SYNTAX  SEQUENCE OF FciRipEgpRoutesDistributionEntry
        ACCESS  not-accessible
        STATUS  mandatory
        DESCRIPTION
                "As defined by fciRipEgpRoutesDistribution, when
                RIP distributes entries of the routing table
                learnt by EGP (Exterior Gateway Protocol), this
                table defines which of these entries are to be
                distributed. Only entries learnt from a router of
                an automous system specified in this table are
                distributed by RIP."
        ::= { fciRip 30 }


    fciRipEgpRoutesDistributionEntry OBJECT-TYPE
        SYNTAX  FciRipEgpRoutesDistributionEntry
        ACCESS  not-accessible
        STATUS  mandatory
        DESCRIPTION
                "An entry of fciRipEgpRoutesDistributionTable."
        INDEX   { fciRipEgpRoutesAsNumber }
        ::= { fciRipEgpRoutesDistributionTable 1 }


        FciRipEgpRoutesDistributionEntry ::=
                SEQUENCE {
                    fciRipEgpRoutesAsNumber
                        INTEGER,
                    fciRipEgpRoutesStatus
                        INTEGER,
                    fciRipEgpRoutesMetric
                        INTEGER
                }


    fciRipEgpRoutesAsNumber OBJECT-TYPE
        SYNTAX  INTEGER (1..65534)
        ACCESS  read-only
        STATUS  mandatory
        DESCRIPTION
                "The value of this object identifies an autonomous
                system containing routers delivering the routing
                information that RIP distributes. This AS must
                exist in fciEgpNeighborTable.
                The authorized values are '1..65534'. The default
                value is '0'."
        ::= { fciRipEgpRoutesDistributionEntry 1 }


    fciRipEgpRoutesStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciRipEgpRoutesDistributionEntry 2 }


    fciRipEgpRoutesMetric OBJECT-TYPE
        SYNTAX  INTEGER (1..15)
        ACCESS  read-write
        STATUS  mandatory
        DESCRIPTION
                "The value of this object is the value indicated in
                the transmitted RIP datagrams concerning routing
                information learnt by EGP and coming from this
                autonomous system.
                The authorized values are '1..15'. The default
                value is '1'."
        ::= { fciRipEgpRoutesDistributionEntry 3 }


    fciOspf OBJECT IDENTIFIER ::= { fcIpRouter 41 }


    fciOspfGeneralParameters OBJECT IDENTIFIER ::= { fciOspf 1 }


    fciOspfAdminStatus OBJECT-TYPE
        SYNTAX  INTEGER {
                off(1),
                on(2)
                }
        ACCESS  read-write
        STATUS  mandatory
        DESCRIPTION
                "OSPF administrative status. The administrative
                status of OSPF in the router. The value 'on'
                denotes that the OSPF Process is active on at
                least one interface ; 'off' disables OSPF on all
                interfaces."
        ::= { fciOspfGeneralParameters 1 }


    fciOspfRouterId OBJECT-TYPE
        SYNTAX  IpAddress
        ACCESS  read-write
        STATUS  mandatory
        DESCRIPTION
                "OSPF router Id. A 32-bit integer uniquely
                identifying the router in the autonomous system.
                By convention, to ensure uniqueness, this should
                default to the value of one of the router's IP
                interface addresses."
        ::= { fciOspfGeneralParameters 2 }


    fciOspfRoutesPreference OBJECT-TYPE
        SYNTAX  INTEGER (0..255)
        ACCESS  read-write
        STATUS  mandatory
        DESCRIPTION
                "OSPF routes preference. Specifies the preference
                with which routes learned by OSPF are imported
                into the routing tables."
        ::= { fciOspfGeneralParameters 3 }


    fciOspfAsePreference OBJECT-TYPE
        SYNTAX  INTEGER (0..255)
        ACCESS  read-write
        STATUS  mandatory
        DESCRIPTION
                "OSPF ASE preference. Specifies the preference with
                which routes external to the Autonomous System
                learned by OSPF are imported into the routing
                tables."
        ::= { fciOspfGeneralParameters 4 }


    fciOspfVirtualPortsTable OBJECT-TYPE
        SYNTAX  SEQUENCE OF FciOspfVirtualPortsEntry
        ACCESS  not-accessible
        STATUS  mandatory
        DESCRIPTION
                "OSPF Interface Table. The OSPF Interface Table
                augments the ifTable with OSPF specific
                information. Each OSPF Interface Entry describes
                one interface from the viewpoint of OSPF."
        ::= { fciOspf 10 }


    fciOspfVirtualPortsEntry OBJECT-TYPE
        SYNTAX  FciOspfVirtualPortsEntry
        ACCESS  not-accessible
        STATUS  mandatory
        DESCRIPTION
                "An entry of fciOspfVirtualPortsTable."
        INDEX   { fciOspfVpId }
        ::= { fciOspfVirtualPortsTable 1 }


        FciOspfVirtualPortsEntry ::=
                SEQUENCE {
                    fciOspfVpId
                        INTEGER,
                    fciOspfVpAdminStatus
                        INTEGER,
                    fciOspfVpAreaId
                        IpAddress,
                    fciOspfVpMetric
                        INTEGER,
                    fciOspfVpType
                        INTEGER,
                    fciOspfVpDRPriority
                        INTEGER,
                    fciOspfVpTransitDelay
                        INTEGER,
                    fciOspfVpRetransmitInterval
                        INTEGER,
                    fciOspfVpHelloInterval
                        INTEGER,
                    fciOspfVpRouterDeadInterval
                        INTEGER,
                    fciOspfVpPollInterval
                        INTEGER,
                    fciOspfVpAuthenticationKey
                        DisplayString
                }


    fciOspfVpId OBJECT-TYPE
        SYNTAX  INTEGER (0..35)
        ACCESS  read-only
        STATUS  mandatory
        DESCRIPTION
                "OSPF VP id. The VP id identifying this OSPF
                interface."
        ::= { fciOspfVirtualPortsEntry 1 }


    fciOspfVpAdminStatus OBJECT-TYPE
        SYNTAX  INTEGER {
                off(1),
                on(2)
                }
        ACCESS  read-write
        STATUS  mandatory
        DESCRIPTION
                "OSPF VP administrative status. The OSPF
                interface's administrative status.  The value 'on'
                denotes that neighbor relationships may be formed
                on the interface, and the interface will be
                advertised as an internal route to some area.  The
                value 'off' denotes that the interface is external
                to OSPF. This parameter defaults to the value 'on'."
        ::= { fciOspfVirtualPortsEntry 2 }


    fciOspfVpAreaId OBJECT-TYPE
        SYNTAX  IpAddress
        ACCESS  read-write
        STATUS  mandatory
        DESCRIPTION
                "OSPF VP area id. A 32-bit integer uniquely
                identifying the area to which the interface
                connects.  This parameter defaults to the value
                '0.0.0.0' which is used for the OSPF backbone."
        ::= { fciOspfVirtualPortsEntry 3 }


    fciOspfVpMetric OBJECT-TYPE
        SYNTAX  INTEGER (0..4294967295)
        ACCESS  read-write
        STATUS  mandatory
        DESCRIPTION
                "OSPF VP metric. The metric of using this type of
                service on this interface.  The default value of
                the TOS 0 Metric is 10^8 / ifSpeed. The value FFFF
                is distinguished to mean 'no route via this TOS'."
        ::= { fciOspfVirtualPortsEntry 4 }


    fciOspfVpType OBJECT-TYPE
        SYNTAX  INTEGER {
                broadcast(1),
                nbma(2),
                pointToPoint(3)
                }
        ACCESS  read-write
        STATUS  mandatory
        DESCRIPTION
                "OSPF VP type. The OSPF interface type. By way of a
                default, this field may be intuited from the
                corresponding value of ifType.  Broadcast LANs,
                such as Ethernet and IEEE 802.5, take the value
                'broadcast', X.25, Frame Relay, and similar
                technologies take the value 'nbma', and links that
                are definitively point to point take the value
                'pointToPoint'."
        ::= { fciOspfVirtualPortsEntry 5 }


    fciOspfVpDRPriority OBJECT-TYPE
        SYNTAX  INTEGER (0..255)
        ACCESS  read-write
        STATUS  mandatory
        DESCRIPTION
                "OSPF VP DR priority.  The priority of this
                interface.  Used in multi-access networks, this
                field is used in the designated router election
                algorithm.  The value 0 signifies that the router
                is not eligible to become the designated router on
                this particular network.  In the event of a tie in
                this value, routers will use their router id as a
                tie breaker. This parameter defaults to the value
                '1'."
        ::= { fciOspfVirtualPortsEntry 6 }


    fciOspfVpTransitDelay OBJECT-TYPE
        SYNTAX  INTEGER (0..65535)
        ACCESS  read-write
        STATUS  mandatory
        DESCRIPTION
                "OSPF VP transit delay. The estimated number of
                seconds it takes to transmit a link state update
                packet over this interface. This parameter
                defaults with the value '1'."
        ::= { fciOspfVirtualPortsEntry 7 }


    fciOspfVpRetransmitInterval OBJECT-TYPE
        SYNTAX  INTEGER (0..65535)
        ACCESS  read-write
        STATUS  mandatory
        DESCRIPTION
                "OSPF VP retransmit interval. The number of seconds
                between link-state advertisement retransmissions,
                for adjacencies belonging to this interface.  This
                value is also used when retransmitting database
                description and link-state request packets. This
                parameter defaults to the value '5'. "
        ::= { fciOspfVirtualPortsEntry 8 }


    fciOspfVpHelloInterval OBJECT-TYPE
        SYNTAX  INTEGER (0..255)
        ACCESS  read-write
        STATUS  mandatory
        DESCRIPTION
                "OSPF VP hello interval. The length of time, in
                seconds, between the Hello packets that the router
                sends on the interface.  This value must be the
                same for all routers attached to a common
                network.This parameter defaults with the value
                '10'."
        ::= { fciOspfVirtualPortsEntry 9 }


    fciOspfVpRouterDeadInterval OBJECT-TYPE
        SYNTAX  INTEGER (0..65535)
        ACCESS  read-write
        STATUS  mandatory
        DESCRIPTION
                "OSPF VP router dead interval. The number of
                seconds that a router's Hello packets have not
                been seen before it's neighbors declare the router
                down.  This should be some multiple of the Hello
                interval.  This value must be the same for all
                routers attached to a common network. This
                parameter defaults with the value '40'."
        ::= { fciOspfVirtualPortsEntry 10 }


    fciOspfVpPollInterval OBJECT-TYPE
        SYNTAX  INTEGER (0..255)
        ACCESS  read-write
        STATUS  mandatory
        DESCRIPTION
                "OSPF VP poll interval. The larger time interval,
                in seconds, between the Hello packets sent to an
                inactive non-broadcast multi-access neighbor. This
                parameter defaults with the value '120'."
        ::= { fciOspfVirtualPortsEntry 11 }


    fciOspfVpAuthenticationKey OBJECT-TYPE
        SYNTAX  DisplayString (SIZE(0..8))
        ACCESS  read-write
        STATUS  mandatory
        DESCRIPTION
                "OSPF VP authentication key. The Authentication
                Key.  If the Area's Authentication Type is
                simplePassword, and the key length is shorter than
                8 octets, the agent will left adjust and zero fill
                to 8 octets. When read, ospfIfAuthKey always
                returns an Octet String of length zero. This
                parameter defaults with the value
                '0000000000000000h'."
        ::= { fciOspfVirtualPortsEntry 12 }


    fciOspfNeighborsTable OBJECT-TYPE
        SYNTAX  SEQUENCE OF FciOspfNeighborsEntry
        ACCESS  not-accessible
        STATUS  mandatory
        DESCRIPTION
                "OSPF Neighbors Table. The OSPF Neighbors Table
                describes all neighbors in the locality of the
                subject router. Each entry contains the
                information regarding a single neighbor."
        ::= { fciOspf 20 }


    fciOspfNeighborsEntry OBJECT-TYPE
        SYNTAX  FciOspfNeighborsEntry
        ACCESS  not-accessible
        STATUS  mandatory
        DESCRIPTION
                "An entry of fciOspfNeighborsTable."
        INDEX   { fciOspfNeighborIpAddress }
        ::= { fciOspfNeighborsTable 1 }


        FciOspfNeighborsEntry ::=
                SEQUENCE {
                    fciOspfNeighborIpAddress
                        IpAddress,
                    fciOspfNeighborStatus
                        INTEGER,
                    fciOspfNeighborEligibleStatus
                        INTEGER
                }


    fciOspfNeighborIpAddress OBJECT-TYPE
        SYNTAX  IpAddress
        ACCESS  read-only
        STATUS  mandatory
        DESCRIPTION
                "Neighbor IP address. The IP address of this
                neighbor."
        ::= { fciOspfNeighborsEntry 1 }


    fciOspfNeighborStatus OBJECT-TYPE
        SYNTAX  INTEGER {
                valid(1),
                invalid(2)
                }
        ACCESS  read-write
        STATUS  mandatory
        DESCRIPTION
                "Status. The value of this object indicates the
                state of the entry of this table. The default
                value is 'valid'. It must be set to 'invalid' to
                delete the entry."
        ::= { fciOspfNeighborsEntry 2 }


    fciOspfNeighborEligibleStatus OBJECT-TYPE
        SYNTAX  INTEGER {
                off(1),
                on(2)
                }
        ACCESS  read-write
        STATUS  mandatory
        DESCRIPTION
                "Neighbor eligible status. This parameter indicates
                whether the neighbor is eligible for DR election."
        ::= { fciOspfNeighborsEntry 3 }


    fciOspfAreasTable OBJECT-TYPE
        SYNTAX  SEQUENCE OF FciOspfAreasEntry
        ACCESS  not-accessible
        STATUS  mandatory
        DESCRIPTION
                "The OSPF Area Data Structure contains informations
                regarding the various areas. The interfaces and
                the virtual links are configured as part of these
                areas. Area 0.0.0.0, by definition, is the
                Backbone Area. Each entry describes the configured
                parameters of one of the router's attached areas."
        ::= { fciOspf 30 }


    fciOspfAreasEntry OBJECT-TYPE
        SYNTAX  FciOspfAreasEntry
        ACCESS  not-accessible
        STATUS  mandatory
        DESCRIPTION
                "An entry of fciOspfAreasTable."
        INDEX   { fciOspfAreaId }
        ::= { fciOspfAreasTable 1 }


        FciOspfAreasEntry ::=
                SEQUENCE {
                    fciOspfAreaId
                        IpAddress,
                    fciOspfAreaStatus
                        INTEGER,
                    fciOspfAreaAuthType
                        INTEGER,
                    fciOspfAreaStubStatus
                        INTEGER,
                    fciOspfAreaStubMetric
                        INTEGER
                }


    fciOspfAreaId OBJECT-TYPE
        SYNTAX  IpAddress
        ACCESS  read-only
        STATUS  mandatory
        DESCRIPTION
                "Area id. A 32-bit integer uniquely identifying an
                area. This parameter defaults to the value
                '0.0.0.0' which is used to identify the OSPF
                backbone."
        ::= { fciOspfAreasEntry 1 }


    fciOspfAreaStatus OBJECT-TYPE
        SYNTAX  INTEGER {
                valid(1),
                invalid(2)
                }
        ACCESS  read-write
        STATUS  mandatory
        DESCRIPTION
                "Status. The value of this object indicates the
                state of the entry of this table. The default
                value is 'valid'. It must be set to 'invalid' to
                delete the entry."
        ::= { fciOspfAreasEntry 2 }


    fciOspfAreaAuthType OBJECT-TYPE
        SYNTAX  INTEGER {
                none(1),
                simplePassword(2)
                }
        ACCESS  read-write
        STATUS  mandatory
        DESCRIPTION
                "Area authentication type. The authentication type
                specified for an area. This parameter defaults to
                the 'none' value and can take the value
                'simplePassword' to enable authentication into the
                area."
        ::= { fciOspfAreasEntry 3 }


    fciOspfAreaStubStatus OBJECT-TYPE
        SYNTAX  INTEGER {
                off(1),
                on(2)
                }
        ACCESS  read-write
        STATUS  mandatory
        DESCRIPTION
                "Area stub status. This parameter indicates whether
                the area is a stub area or not."
        ::= { fciOspfAreasEntry 4 }


    fciOspfAreaStubMetric OBJECT-TYPE
        SYNTAX  INTEGER (0..16777215)
        ACCESS  read-write
        STATUS  mandatory
        DESCRIPTION
                "Area stub metric. The OSPF metric associated to
                the stub area."
        ::= { fciOspfAreasEntry 5 }


    fciOspfAreaRangesTable OBJECT-TYPE
        SYNTAX  SEQUENCE OF FciOspfAreaRangesEntry
        ACCESS  not-accessible
        STATUS  mandatory
        DESCRIPTION
                "OSPF Address Range Table. The Address Range Table
                acts as an adjunct to the Area Table ; It
                describes those Address Range Summaries that are
                configured to be propagated from an Area to reduce
                the amount of information about it which is known
                beyond its borders. A range of IP addresses is
                specified by an IP address/IP network mask pair.
                For example, Class B address range of X.X.X.X with
                a network mask of 255.255.0.0 includes all IP
                addresses from X.X.0.0 to X.X.255.255."
        ::= { fciOspf 33 }


    fciOspfAreaRangesEntry OBJECT-TYPE
        SYNTAX  FciOspfAreaRangesEntry
        ACCESS  not-accessible
        STATUS  mandatory
        DESCRIPTION
                "An entry of fciOspfAreaRangesTable."
        INDEX   { fciOspfAreaRangeIpAddress,
                  fciOspfAreaRangeIpMask }
        ::= { fciOspfAreaRangesTable 1 }


        FciOspfAreaRangesEntry ::=
                SEQUENCE {
                    fciOspfAreaRangeIpAddress
                        IpAddress,
                    fciOspfAreaRangeIpMask
                        IpAddress,
                    fciOspfAreaRangeStatus
                        INTEGER,
                    fciOspfAreaRangeAreaId
                        IpAddress,
                    fciOspfAreaRangeRestrict
                        INTEGER
                }


    fciOspfAreaRangeIpAddress OBJECT-TYPE
        SYNTAX  IpAddress
        ACCESS  read-only
        STATUS  mandatory
        DESCRIPTION
                "Area range IP address. The IP Address of the Net
                or Subnet indicated by the range."
        ::= { fciOspfAreaRangesEntry 1 }


    fciOspfAreaRangeIpMask OBJECT-TYPE
        SYNTAX  IpAddress
        ACCESS  read-only
        STATUS  mandatory
        DESCRIPTION
                "Area range IP mask. The Subnet Mask that pertains
                to the Net or Subnet."
        ::= { fciOspfAreaRangesEntry 2 }


    fciOspfAreaRangeStatus OBJECT-TYPE
        SYNTAX  INTEGER {
                valid(1),
                invalid(2)
                }
        ACCESS  read-write
        STATUS  mandatory
        DESCRIPTION
                "Status. The value of this object indicates the
                state of the entry of this table. The default
                value is 'valid'. It must be set to 'invalid' to
                delete the entry."
        ::= { fciOspfAreaRangesEntry 3 }


    fciOspfAreaRangeAreaId OBJECT-TYPE
        SYNTAX  IpAddress
        ACCESS  read-write
        STATUS  mandatory
        DESCRIPTION
                "Area range area id. The Area the Address Range is
                to be found within."
        ::= { fciOspfAreaRangesEntry 4 }


    fciOspfAreaRangeRestrict OBJECT-TYPE
        SYNTAX  INTEGER {
                off(1),
                on(2)
                }
        ACCESS  read-write
        STATUS  mandatory
        DESCRIPTION
                "Restriction. The value 'off' indicates that
                intra-area LSAs that fall within the specified
                range are not advertised into other areas as
                inter-area routes. Instead, the specified range
                are advertised as summary network LSAs. The value
                'on' specifies that the summary network LSAs are
                not advertised."
        ::= { fciOspfAreaRangesEntry 5 }


    fciOspfVirtualLinksTable OBJECT-TYPE
        SYNTAX  SEQUENCE OF FciOspfVirtualLinksEntry
        ACCESS  not-accessible
        STATUS  mandatory
        DESCRIPTION
                "OSPF Virtual Link Table. The Virtual Link Table
                describes the virtual links that the OSPF Process
                is configured to carry on."
        ::= { fciOspf 36 }


    fciOspfVirtualLinksEntry OBJECT-TYPE
        SYNTAX  FciOspfVirtualLinksEntry
        ACCESS  not-accessible
        STATUS  mandatory
        DESCRIPTION
                "An entry of fciOspfVirtualLinksTable."
        INDEX   { fciOspfVlNeighborId,
                  fciOspfVlTransitAreaId }
        ::= { fciOspfVirtualLinksTable 1 }


        FciOspfVirtualLinksEntry ::=
                SEQUENCE {
                    fciOspfVlNeighborId
                        IpAddress,
                    fciOspfVlTransitAreaId
                        IpAddress,
                    fciOspfVlStatus
                        INTEGER,
                    fciOspfVlDRPriority
                        INTEGER,
                    fciOspfVlTransitDelay
                        INTEGER,
                    fciOspfVlRetransmitInterval
                        INTEGER,
                    fciOspfVlHelloInterval
                        INTEGER,
                    fciOspfVlRouterDeadInterval
                        INTEGER,
                    fciOspfVlAuthenticationKey
                        DisplayString
                }


    fciOspfVlNeighborId OBJECT-TYPE
        SYNTAX  IpAddress
        ACCESS  read-only
        STATUS  mandatory
        DESCRIPTION
                "VL neighbor id. The Router ID of the Virtual
                Neighbor."
        ::= { fciOspfVirtualLinksEntry 1 }


    fciOspfVlTransitAreaId OBJECT-TYPE
        SYNTAX  IpAddress
        ACCESS  read-only
        STATUS  mandatory
        DESCRIPTION
                "VL transit area id. The Transit Area that the
                Virtual Link traverses. By definition, this is not
                0.0.0.0."
        ::= { fciOspfVirtualLinksEntry 2 }


    fciOspfVlStatus OBJECT-TYPE
        SYNTAX  INTEGER {
                valid(1),
                invalid(2)
                }
        ACCESS  read-write
        STATUS  mandatory
        DESCRIPTION
                "Status. The value of this object indicates the
                state of the entry of this table. The default
                value is 'valid'. It must be set to 'invalid' to
                delete the entry."
        ::= { fciOspfVirtualLinksEntry 3 }


    fciOspfVlDRPriority OBJECT-TYPE
        SYNTAX  INTEGER (0..255)
        ACCESS  read-write
        STATUS  mandatory
        DESCRIPTION
                "VL DR priority.  The priority of this virtual
                link.  Used in multi-access networks, this field
                is used in the designated router election
                algorithm.  The value 0 signifies that the router
                is not eligible to become the designated router on
                this particular network.  In the event of a tie in
                this value, routers will use their router id as a
                tie breaker. This parameter defaults to the value
                '1'."
        ::= { fciOspfVirtualLinksEntry 4 }


    fciOspfVlTransitDelay OBJECT-TYPE
        SYNTAX  INTEGER (0..65535)
        ACCESS  read-write
        STATUS  mandatory
        DESCRIPTION
                "VL transit delay. The estimated number of seconds
                it takes to transmit a link-state update packet
                over this interface."
        ::= { fciOspfVirtualLinksEntry 5 }


    fciOspfVlRetransmitInterval OBJECT-TYPE
        SYNTAX  INTEGER (0..65535)
        ACCESS  read-write
        STATUS  mandatory
        DESCRIPTION
                "VL retransmit interval. The number of seconds
                between link-state advertisement retransmissions,
                for adjacencies belonging to this interface.  This
                value is also used when retransmitting database
                description and link-state request packets. This
                value should be well over the expected round-trip."
        ::= { fciOspfVirtualLinksEntry 6 }


    fciOspfVlHelloInterval OBJECT-TYPE
        SYNTAX  INTEGER (0..255)
        ACCESS  read-write
        STATUS  mandatory
        DESCRIPTION
                "VL hello interval. The length of time, in seconds,
                between the Hello packets that the router sends on
                the interface.  This value must be the same for
                the virtual neighbor."
        ::= { fciOspfVirtualLinksEntry 7 }


    fciOspfVlRouterDeadInterval OBJECT-TYPE
        SYNTAX  INTEGER (0..65535)
        ACCESS  read-write
        STATUS  mandatory
        DESCRIPTION
                "VL router dead interval. The number of seconds
                that a router's Hello packets have not been seen
                before it's neighbors declare the router down. 
                This should be some multiple of the Hello
                interval.  This value must be the same for the
                virtual neighbor."
        ::= { fciOspfVirtualLinksEntry 8 }


    fciOspfVlAuthenticationKey OBJECT-TYPE
        SYNTAX  DisplayString (SIZE(0..8))
        ACCESS  read-write
        STATUS  mandatory
        DESCRIPTION
                "VL authentication key. If Authentication Type is
                simplePassword, the device will left adjust and
                zero fill to 8 octets. When read, ospfVifAuthKey
                always returns a string of length zero."
        ::= { fciOspfVirtualLinksEntry 9 }


    fciOspfExportingGroup OBJECT IDENTIFIER ::= { fciOspf 40 }


    fciOspfAseExportInterval OBJECT-TYPE
        SYNTAX  INTEGER (1..255)
        ACCESS  read-write
        STATUS  mandatory
        DESCRIPTION
                "ASE flow packets interval. Together with
                fciOspfAseExportLimit, controls the rate at which
                Autonomous System External (ASE) routes are
                imported.  The rate is defined as the ratio of
                fciOspfAseExportLimit and
                fciOspfAseExportInterval, in number of routes per
                second.  By default, ASE routes are imported at
                the rate of 100 ASEs per second."
        ::= { fciOspfExportingGroup 1 }


    fciOspfAseExportLimit OBJECT-TYPE
        SYNTAX  INTEGER (1..255)
        ACCESS  read-write
        STATUS  mandatory
        DESCRIPTION
                "ASE flow packets limit. Together with
                fciOspfAseExportInterval, controls the rate at
                which Autonomous System External (ASE) routes are
                imported.  The rate is defined as the ratio of
                fciOspfAseExportLimit and
                fciOspfAseExportInterval, in number of routes per
                second.  By default, ASE routes are imported at
                the rate of 100 ASEs per second."
        ::= { fciOspfExportingGroup 2 }


    fciOspfAseExportStaticsStatus OBJECT-TYPE
        SYNTAX  INTEGER {
                off(1),
                on(2)
                }
        ACCESS  read-write
        STATUS  mandatory
        DESCRIPTION
                "Statics ASE export status. "
        ::= { fciOspfExportingGroup 3 }


    fciOspfAseExportStaticsMetric OBJECT-TYPE
        SYNTAX  INTEGER (0..16777215)
        ACCESS  read-write
        STATUS  mandatory
        DESCRIPTION
                "Statics ASE export metric. The default metric (or
                cost) used by OSPF when propagating (exporting)
                routes learned via other protocols."
        ::= { fciOspfExportingGroup 4 }


    fciOspfAseExportStaticsTag OBJECT-TYPE
        SYNTAX  INTEGER (0..2147483648)
        ACCESS  read-write
        STATUS  mandatory
        DESCRIPTION
                "Statics ASE export tag. The OSPF tag to be placed
                on all routes exported by OSPF.  Specifies one way
                of generating OSPF tags."
        ::= { fciOspfExportingGroup 5 }


    fciOspfAseExportStaticsType OBJECT-TYPE
        SYNTAX  INTEGER (1..2)
        ACCESS  read-write
        STATUS  mandatory
        DESCRIPTION
                "Statics ASE export type The OSPF external routes
                type used to export static routes. The value '1'
                indicates that the metric of the static routes
                exported are directly comparable with OSPF metric.
                The value '2' indicates the contrary. "
        ::= { fciOspfExportingGroup 6 }


    fciOspfAseExportRipStatus OBJECT-TYPE
        SYNTAX  INTEGER {
                off(1),
                on(2)
                }
        ACCESS  read-write
        STATUS  mandatory
        DESCRIPTION
                "RIP ASE export status. "
        ::= { fciOspfExportingGroup 7 }


    fciOspfAseExportRipMetric OBJECT-TYPE
        SYNTAX  INTEGER (0..16777215)
        ACCESS  read-write
        STATUS  mandatory
        DESCRIPTION
                "RIP ASE export metric. The default metric (or
                cost) used by OSPF when propagating (exporting)
                routes learned via other protocols."
        ::= { fciOspfExportingGroup 8 }


    fciOspfAseExportRipTag OBJECT-TYPE
        SYNTAX  INTEGER (0..2147483648)
        ACCESS  read-write
        STATUS  mandatory
        DESCRIPTION
                "RIP ASE export tag. The OSPF tag to be placed on
                all routes exported by OSPF.  Specifies one way of
                generating OSPF tags."
        ::= { fciOspfExportingGroup 9 }


    fciOspfAseExportRipType OBJECT-TYPE
        SYNTAX  INTEGER (1..2)
        ACCESS  read-write
        STATUS  mandatory
        DESCRIPTION
                "RIP ASE export type The OSPF external routes type
                used to export RIP routes. The value '1' indicates
                that the metric of the static routes exported are
                directly comparable with OSPF metric. The value
                '2' indicates the contrary."
        ::= { fciOspfExportingGroup 10 }


    fciEgp OBJECT IDENTIFIER ::= { fcIpRouter 45 }


    fciEgpAdminStatus OBJECT-TYPE
        SYNTAX  INTEGER {
                off(1),
                on(2)
                }
        ACCESS  read-write
        STATUS  mandatory
        DESCRIPTION
                "The value of this object indicates whether EGP
                (Exterior Gateway Protocol) is enabled or not.
                fciEgpNeighborTable must contain at least one
                entry.
                The default value is 'off'."
        ::= { fciEgp 1 }


    fciEgpAutonomousSystemNumber OBJECT-TYPE
        SYNTAX  INTEGER (1..65534)
        ACCESS  read-write
        STATUS  mandatory
        DESCRIPTION
                "The value of this object defines the autonomous
                system to which belongs this IP router.
                The authorized values are '1..65534'. The default
                value is '1'."
        ::= { fciEgp 2 }


    fciEgpStaticRoutesDistribution OBJECT-TYPE
        SYNTAX  INTEGER {
                off(1),
                on(2)
                }
        ACCESS  read-write
        STATUS  mandatory
        DESCRIPTION
                "The value of this object indicates whether EGP
                distributes static entries of the routing table
                (i.e., those defined in fciIpRouteTable) or not..
                The autonomous systems to which these routing
                informations are distributed are defined in
                fciEgpTargetAsDistributionTable.
                The default value is 'off'."
        ::= { fciEgp 3 }


    fciEgpRipRoutesDistribution OBJECT-TYPE
        SYNTAX  INTEGER {
                off(1),
                on(2)
                }
        ACCESS  read-write
        STATUS  mandatory
        DESCRIPTION
                "The value of this object indicates whether EGP
                distributes entries of the routing table learnt by
                RIP (Routing Information Protocol) or not. The
                autonomous systems to which these routing
                informations are distributed are defined in
                fciEgpTargetAsDistributionTable.
                The default value is 'off'."
        ::= { fciEgp 4 }


    fciEgpMetricDistribution OBJECT-TYPE
        SYNTAX  INTEGER (1..255)
        ACCESS  read-write
        STATUS  mandatory
        DESCRIPTION
                "The value of this object is the value indicated in
                the transmitted EGP datagrams concerning routing
                information learnt by RIP.
                The authorized values are '1..255'. The default
                value is '128'."
        ::= { fciEgp 5 }


    fciEgpNeighborTable OBJECT-TYPE
        SYNTAX  SEQUENCE OF FciEgpNeighborEntry
        ACCESS  not-accessible
        STATUS  mandatory
        DESCRIPTION
                "This table defines the EGP neighbors with witch
                EGP exchanges routing informations."
        ::= { fciEgp 10 }


    fciEgpNeighborEntry OBJECT-TYPE
        SYNTAX  FciEgpNeighborEntry
        ACCESS  not-accessible
        STATUS  mandatory
        DESCRIPTION
                "An entry of fciEgpNeighborTable."
        INDEX   { fciEgpNeighborIpAddress }
        ::= { fciEgpNeighborTable 1 }


        FciEgpNeighborEntry ::=
                SEQUENCE {
                    fciEgpNeighborIpAddress
                        IpAddress,
                    fciEgpNeighborStatus
                        INTEGER,
                    fciEgpNeighborAsNumber
                        INTEGER
                }


    fciEgpNeighborIpAddress OBJECT-TYPE
        SYNTAX  IpAddress
        ACCESS  read-only
        STATUS  mandatory
        DESCRIPTION
                "The value of this object is the IP address of an
                EGP neighbor. This IP address must be a valid host
                address.
                The default value is '0.0.0.0'."
        ::= { fciEgpNeighborEntry 1 }


    fciEgpNeighborStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciEgpNeighborEntry 2 }


    fciEgpNeighborAsNumber OBJECT-TYPE
        SYNTAX  INTEGER (1..65534)
        ACCESS  read-write
        STATUS  mandatory
        DESCRIPTION
                "The value of this object defines the autonomous
                system to which belongs this EGP neighbor.
                The authorized values are '1..65534'. The default
                value is '1'."
        ::= { fciEgpNeighborEntry 3 }


    fciEgpTargetAsDistributionTable OBJECT-TYPE
        SYNTAX  SEQUENCE OF FciEgpTargetAsDistributionEntry
        ACCESS  not-accessible
        STATUS  mandatory
        DESCRIPTION
                "As defined by fciEgpStaticRoutesDistribution and
                fciEgpRipRoutesDistribution, when EGP distributes
                static entries or entries of the routing table
                learnt by RIP (Routing Information Protocol), this
                table defines to which autonomous systems these
                entries are to be distributed. Only neighbors of
                an automous system specified in this table will
                receive these routing informations."
        ::= { fciEgp 15 }


    fciEgpTargetAsDistributionEntry OBJECT-TYPE
        SYNTAX  FciEgpTargetAsDistributionEntry
        ACCESS  not-accessible
        STATUS  mandatory
        DESCRIPTION
                "An entry of fciEgpTargetAsDistributionTable."
        INDEX   { fciEgpTargetAsNumber }
        ::= { fciEgpTargetAsDistributionTable 1 }


        FciEgpTargetAsDistributionEntry ::=
                SEQUENCE {
                    fciEgpTargetAsNumber
                        INTEGER,
                    fciEgpTargetAsStatus
                        INTEGER
                }


    fciEgpTargetAsNumber OBJECT-TYPE
        SYNTAX  INTEGER (1..65534)
        ACCESS  read-only
        STATUS  mandatory
        DESCRIPTION
                "The value of this object identifies an autonomous
                system containing routers to which EGP distributes
                the routing informations. This AS must exist in
                fciEgpNeighborTable.
                The authorized values are '1..65534'. The default
                value is '0'."
        ::= { fciEgpTargetAsDistributionEntry 1 }


    fciEgpTargetAsStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciEgpTargetAsDistributionEntry 2 }


    fciSnmp OBJECT IDENTIFIER ::= { fcIpRouter 50 }


    fciSnmpCommunityStringReadOnly OBJECT-TYPE
        SYNTAX  DisplayString (SIZE(1..14))
        ACCESS  read-write
        STATUS  mandatory
        DESCRIPTION
                "The value of this object is the string which
                identifies the 'public' community. The managers of
                this community have only 'read-only' access rights
                even on the objects with read-write access.
                The SNMP agent of this equipment compares the
                community string of a received GetRequest or
                GetNextRequest to this value to know whether it
                makes a GetResponse or not.
                This value may contain up to 14 printable
                characters. The default value is 'public'."
        ::= { fciSnmp 1 }


    fciSnmpCommunityStringReadWrite OBJECT-TYPE
        SYNTAX  DisplayString (SIZE(1..14))
        ACCESS  read-write
        STATUS  mandatory
        DESCRIPTION
                "The value of this object is the string which
                identifies the 'administrator' community. The
                managers of this community have complete access
                rights (i.e. they have the rights which are
                defined in the MIB).
                The SNMP agent of this equipment compares the
                community string of a received GetRequest,
                GetNextRequest or SetRequest to this value to know
                whether it makes a GetResponse or not.
                This value may contain up to 14 printable
                characters. The default value is 'private'."
        ::= { fciSnmp 2 }


    fciSnmpCommunityStringTrap OBJECT-TYPE
        SYNTAX  DisplayString (SIZE(1..14))
        ACCESS  read-write
        STATUS  mandatory
        DESCRIPTION
                "The value of this object is the string which
                identifies the 'alarm' community. The managers of
                this community may filter the received Traps
                according of this community string.
                The SNMP agent of this equipment sets the
                community string of all the sent Trap to this
                value. It sends traps to the managers defined in
                fciSnmpManagerTable.
                This value may contain up to 14 printable
                characters. The default value is 'private'."
        ::= { fciSnmp 3 }


    fciSnmpAuthenticationFailureTrap OBJECT-TYPE
        SYNTAX  INTEGER {
                off(1),
                on(2)
                }
        ACCESS  read-write
        STATUS  mandatory
        DESCRIPTION
                "The value of this object specifies whether the
                SNMP agent sends the authenticationFailure trap or
                not. When enabled, this trap is sent with each
                reception of an unauthorized SNMP request
                (erroneous community string or manager not
                authorized).
                It can be useful to disable this sending when
                unauthorized SNMP managers polls very often the
                SNMP agent because the quantity of
                authenticationFailure trap is then very important
                and prevents the 'good' manager to show correctly
                the significant traps.
                The default value is 'off'."
        ::= { fciSnmp 5 }


    fciSnmpModule0TrapSourceAddrVpId OBJECT-TYPE
        SYNTAX  INTEGER (0..11)
        ACCESS  read-write
        STATUS  mandatory
        DESCRIPTION
                "The SNMP agent of module 0 indicates, as the
                source address of each TRAP, the IP address
                associated with the virtual port identified by
                this value. This virtual port must exist in
                fciVirtualPortTable.
                The authorized values are '0..199'. The default
                value is '0'."
        ::= { fciSnmp 10 }


    fciSnmpModule1TrapSourceAddrVpId OBJECT-TYPE
        SYNTAX  INTEGER (0..11)
        ACCESS  read-write
        STATUS  mandatory
        DESCRIPTION
                "The SNMP agent of module 1 indicates, as the
                source address of each TRAP, the IP address
                associated with the virtual port identified by
                this value. This virtual port must exist in
                fciVirtualPortTable.
                The authorized values are '0..199'. The default
                value is '255' meaning 'empty value' (blank value
                on the equipment configurator)."
        ::= { fciSnmp 11 }


    fciSnmpModule2TrapSourceAddrVpId OBJECT-TYPE
        SYNTAX  INTEGER (0..11)
        ACCESS  read-write
        STATUS  mandatory
        DESCRIPTION
                "The SNMP agent of module 1 indicates, as the
                source address of each TRAP, the IP address
                associated with the virtual port identified by
                this value. This virtual port must exist in
                fciVirtualPortTable.
                The authorized values are '0..199'. The default
                value is '255' meaning 'empty value' (blank value
                on the equipment configurator)."
        ::= { fciSnmp 12 }


    fciSnmpManagerFiltering OBJECT-TYPE
        SYNTAX  INTEGER {
                off(1),
                on(2)
                }
        ACCESS  read-write
        STATUS  mandatory
        DESCRIPTION
                "The value of this object specifies whether the
                SNMP agent answers to all the SNMP managers or
                only to those defined in fciSnmpManagerTable. When
                set to 'on' the SNMP agent sends an
                authenticationFailure trap (if enabled) each time
                it receives a request from a manager not in the
                table.
                The default value is 'off' (i.e., no filtering :
                access for all managers).."
        ::= { fciSnmp 15 }


    fciSnmpManagerTable OBJECT-TYPE
        SYNTAX  SEQUENCE OF FciSnmpManagerEntry
        ACCESS  not-accessible
        STATUS  mandatory
        DESCRIPTION
                "This table contains the SNMP managers to which
                SNMP traps may be sent. This table is also used to
                define the authorized managers when
                fciSnmpManagerFiltering is set to 'on'."
        ::= { fciSnmp 20 }


    fciSnmpManagerEntry OBJECT-TYPE
        SYNTAX  FciSnmpManagerEntry
        ACCESS  not-accessible
        STATUS  mandatory
        DESCRIPTION
                "An entry of fciSnmpManagerTable."
        INDEX   { fciSnmpManagerIpAddress }
        ::= { fciSnmpManagerTable 1 }


        FciSnmpManagerEntry ::=
                SEQUENCE {
                    fciSnmpManagerIpAddress
                        IpAddress,
                    fciSnmpManagerStatus
                        INTEGER,
                    fciSnmpManagerSendTraps
                        INTEGER,
                    fciSnmpManagerTrapsUdpPort
                        INTEGER
                }


    fciSnmpManagerIpAddress OBJECT-TYPE
        SYNTAX  IpAddress
        ACCESS  read-only
        STATUS  mandatory
        DESCRIPTION
                "The value of this object is the IP address of an
                SNMP manager. This IP address must be a valid host
                address.
                The default value is '0.0.0.0'."
        ::= { fciSnmpManagerEntry 1 }


    fciSnmpManagerStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciSnmpManagerEntry 2 }


    fciSnmpManagerSendTraps OBJECT-TYPE
        SYNTAX  INTEGER {
                off(1),
                on(2)
                }
        ACCESS  read-write
        STATUS  mandatory
        DESCRIPTION
                "The value of this object specifies whether the
                SNMP agent sends the traps to this SNMP manager or
                not.
                The default value is 'on'."
        ::= { fciSnmpManagerEntry 3 }


    fciSnmpManagerTrapsUdpPort OBJECT-TYPE
        SYNTAX  INTEGER (0..65535)
        ACCESS  read-write
        STATUS  mandatory
        DESCRIPTION
                "The value of this object indicates the UDP port to
                which are sent the SNMP traps. This value must be
                the value used by this SNMP manager when it
                listens for SNMP traps.
                The authorized values are '0..65535'. The default
                value is '162'."
        ::= { fciSnmpManagerEntry 4 }


    fciBootP OBJECT IDENTIFIER ::= { fcIpRouter 60 }


    fciBootPClient OBJECT IDENTIFIER ::= { fciBootP 1 }


    fciBootPClientStart OBJECT-TYPE
        SYNTAX  INTEGER {
                no(1),
                yes(2)
                }
        ACCESS  read-write
        STATUS  mandatory
        DESCRIPTION
                "The value of this object identifies start mode of
                equipement.
                The default value is 'no'."
        ::= { fciBootPClient 1 }


    fciBootPClientServer OBJECT-TYPE
        SYNTAX  DisplayString (SIZE(0..64))
        ACCESS  read-write
        STATUS  mandatory
        DESCRIPTION
                "The value of this object identifies server name.
                This value may contain up to 64 printable
                characters. The default value is an empty string."
        ::= { fciBootPClient 2 }


    fciBootPClientBootFile OBJECT-TYPE
        SYNTAX  DisplayString (SIZE(0..64))
        ACCESS  read-write
        STATUS  mandatory
        DESCRIPTION
                "The value of this object identifies generic name
                of bootfile. 
                This value may contain up to 64 printable
                characters. The default value is an empty string."
        ::= { fciBootPClient 3 }


    fciBootPClientBootTime OBJECT-TYPE
        SYNTAX  INTEGER (15..900)
        ACCESS  read-write
        STATUS  mandatory
        DESCRIPTION
                "The value of this object identifies time to wait
                before bootp launching. Time is specified in
                seconds.
                The authorized values are '15..900'. The default
                value is '180'."
        ::= { fciBootPClient 4 }


    fciBootPClientRetransNb OBJECT-TYPE
        SYNTAX  INTEGER (0..10)
        ACCESS  read-write
        STATUS  mandatory
        DESCRIPTION
                "The value of this object identifies numbers of
                retransmissions of bootrequest packet.
                The authorized values are '0..10'. The default
                value is '5'."
        ::= { fciBootPClient 5 }


    fciBootPInterfaceTable OBJECT-TYPE
        SYNTAX  SEQUENCE OF FciBootPInterfaceEntry
        ACCESS  not-accessible
        STATUS  mandatory
        DESCRIPTION
                "This table describes the parameters of BootP
                Virtual Ports. It offers a solution to link many
                servers on the bootp client or relay."
        ::= { fciBootPClient 20 }


    fciBootPInterfaceEntry OBJECT-TYPE
        SYNTAX  FciBootPInterfaceEntry
        ACCESS  not-accessible
        STATUS  mandatory
        DESCRIPTION
                "An entry of fciBootPInterfaceTable."
        INDEX   { fciBootPInterfaceVpId,
                  fciBootPInterfaceIpAddress }
        ::= { fciBootPInterfaceTable 1 }


        FciBootPInterfaceEntry ::=
                SEQUENCE {
                    fciBootPInterfaceVpId
                        INTEGER,
                    fciBootPInterfaceIpAddress
                        IpAddress,
                    fciBootPInterfaceStatus
                        INTEGER,
                    fciBootPInterfaceType
                        INTEGER
                }


    fciBootPInterfaceVpId OBJECT-TYPE
        SYNTAX  INTEGER (0..11)
        ACCESS  read-only
        STATUS  mandatory
        DESCRIPTION
                "The value of this object identifies one virtual
                port.
                The default value is '255'."
        ::= { fciBootPInterfaceEntry 1 }


    fciBootPInterfaceIpAddress OBJECT-TYPE
        SYNTAX  IpAddress
        ACCESS  read-only
        STATUS  mandatory
        DESCRIPTION
                "The value of this object is the IP address
                associated to one bootp interface.
                The default value is '255.255.255.255'."
        ::= { fciBootPInterfaceEntry 2 }


    fciBootPInterfaceStatus OBJECT-TYPE
        SYNTAX  INTEGER {
                valid(1),
                invalid(2)
                }
        ACCESS  read-write
        STATUS  mandatory
        DESCRIPTION
                "The value of this object indicates the state of
                the entry of this table. The default value is
                'valid'. It must be set to 'invalid' to delete the
                entry."
        ::= { fciBootPInterfaceEntry 3 }


    fciBootPInterfaceType OBJECT-TYPE
        SYNTAX  INTEGER {
                client(1),
                relay(2)
                }
        ACCESS  read-write
        STATUS  mandatory
        DESCRIPTION
                "The value of this object indicates the
                fonctionnality of the equipement.
                The authorized values are 'client' or 'relay'. The
                default value is 'client'."
        ::= { fciBootPInterfaceEntry 4 }


    fciTelnet OBJECT IDENTIFIER ::= { fcIpRouter 70 }


    fciTelnetConfiguration OBJECT IDENTIFIER ::= { fciTelnet 1 }


    fciTelnetMaxSession OBJECT-TYPE
        SYNTAX  INTEGER (0..50)
        ACCESS  read-write
        STATUS  mandatory
        DESCRIPTION
                "Maximum number of telnet session that the
                equipment would accept. This number include the
                telnet session issuing from the equipment. 
                The modification of this parameter need a reboot
                of the equipment.
                The default value is 6."
        ::= { fciTelnetConfiguration 1 }


    fciTelnetTimer OBJECT-TYPE
        SYNTAX  INTEGER (0..3600)
        ACCESS  read-write
        STATUS  mandatory
        DESCRIPTION
                "This parameter is global to all connection and set
                the timer that make a session to be disconnected
                if no traffic is send or receive in the telnet
                session.
                The modification of the parameter takes effect
                after a hot reset and is used for new connections
                "
        ::= { fciTelnetConfiguration 2 }


    fciTelnetPwd OBJECT IDENTIFIER ::= { fciTelnet 10 }


    fciTelnetPwdP0 OBJECT-TYPE
        SYNTAX  DisplayString (SIZE(0..16))
        ACCESS  read-write
        STATUS  mandatory
        DESCRIPTION
                "This parameter set the password to access to a
                priority 0 level. All the user set to a priority 0
                level have to uses this password.
                The modification of the parameter takes effect
                after a hot reset and is used for new connections
                The default value is 'root'."
        ::= { fciTelnetPwd 1 }


    fciTelnetPwdP1 OBJECT-TYPE
        SYNTAX  DisplayString (SIZE(0..16))
        ACCESS  read-write
        STATUS  mandatory
        DESCRIPTION
                "This parameter set the password to access to a
                priority 1 level. All the user set to a priority 1
                level have to uses this password.
                The modification of the parameter takes effect
                after a hot reset and is used for new connections
                The default value is 'user'."
        ::= { fciTelnetPwd 2 }


    fciTelnetPwdP2 OBJECT-TYPE
        SYNTAX  DisplayString (SIZE(0..16))
        ACCESS  read-write
        STATUS  mandatory
        DESCRIPTION
                "This parameter set the password to access to a
                priority 2 level. All the user set to a priority 2
                level have to uses this password.
                The modification of the parameter takes effect
                after a hot reset and is used for new connections
                The default value is 'user'."
        ::= { fciTelnetPwd 3 }


    fciTelnetPwdP3 OBJECT-TYPE
        SYNTAX  DisplayString (SIZE(0..16))
        ACCESS  read-write
        STATUS  mandatory
        DESCRIPTION
                "This parameter set the password to access to a
                priority 3 level. All the user set to a priority 3
                level have to uses this password.
                The modification of the parameter takes effect
                after a hot reset and is used for new connections
                The default value is 'user'."
        ::= { fciTelnetPwd 4 }


    fciTelnetPwdP4 OBJECT-TYPE
        SYNTAX  DisplayString (SIZE(0..16))
        ACCESS  read-write
        STATUS  mandatory
        DESCRIPTION
                "This parameter set the password to access to a
                priority 4 level. All the user set to a priority 4
                level have to uses this password.
                The modification of the parameter takes effect
                after a hot reset and is used for new connections
                The default value is 'user'."
        ::= { fciTelnetPwd 5 }


    fciTelnetPwdP5 OBJECT-TYPE
        SYNTAX  DisplayString (SIZE(0..16))
        ACCESS  read-write
        STATUS  mandatory
        DESCRIPTION
                "This parameter set the password to access to a
                priority 5 level. All the user set to a priority 5
                level have to uses this password.
                The modification of the parameter takes effect
                after a hot reset and is used for new connections
                The default value is 'user'."
        ::= { fciTelnetPwd 6 }


    fciTelnetPwdP6 OBJECT-TYPE
        SYNTAX  DisplayString (SIZE(0..16))
        ACCESS  read-write
        STATUS  mandatory
        DESCRIPTION
                "This parameter set the password to access to a
                priority 6 level. All the user set to a priority 6
                level have to uses this password.
                The modification of the parameter takes effect
                after a hot reset and is used for new connections
                The default value is 'user'."
        ::= { fciTelnetPwd 7 }


    fciTelnetPwdP7 OBJECT-TYPE
        SYNTAX  DisplayString (SIZE(0..16))
        ACCESS  read-write
        STATUS  mandatory
        DESCRIPTION
                "This parameter set the password to access to a
                priority 7 level. All the user set to a priority 7
                level have to uses this password.
                The modification of the parameter takes effect
                after a hot reset and is used for new connections
                The default value is 'user'."
        ::= { fciTelnetPwd 8 }


    fciTelnetPwdP8 OBJECT-TYPE
        SYNTAX  DisplayString (SIZE(0..16))
        ACCESS  read-write
        STATUS  mandatory
        DESCRIPTION
                "This parameter set the password to access to a
                priority 8 level. All the user set to a priority 8
                level have to uses this password.
                The modification of the parameter takes effect
                after a hot reset and is used for new connections
                The default value is 'user'."
        ::= { fciTelnetPwd 9 }


    fciTelnetPwdP9 OBJECT-TYPE
        SYNTAX  DisplayString (SIZE(0..16))
        ACCESS  read-write
        STATUS  mandatory
        DESCRIPTION
                "This parameter set the password to access to a
                priority 9 level. All the user set to a priority 9
                level have to uses this password.
                The modification of the parameter takes effect
                after a hot reset and is used for new connections
                The default value is 'user'."
        ::= { fciTelnetPwd 10 }


    fciTelnetUserTable OBJECT-TYPE
        SYNTAX  SEQUENCE OF FciTelnetUserEntry
        ACCESS  not-accessible
        STATUS  mandatory
        DESCRIPTION
                ""
        ::= { fciTelnet 30 }


    fciTelnetUserEntry OBJECT-TYPE
        SYNTAX  FciTelnetUserEntry
        ACCESS  not-accessible
        STATUS  mandatory
        DESCRIPTION
                "An entry of fciTelnetUserTable."
        INDEX   { fciTelnetUserId }
        ::= { fciTelnetUserTable 1 }


        FciTelnetUserEntry ::=
                SEQUENCE {
                    fciTelnetUserId
                        INTEGER,
                    fciTelnetUserStatus
                        INTEGER,
                    fciTelnetUserLogin
                        DisplayString,
                    fciTelnetUserPriority
                        INTEGER
                }


    fciTelnetUserId OBJECT-TYPE
        SYNTAX  INTEGER (0..49)
        ACCESS  read-only
        STATUS  mandatory
        DESCRIPTION
                "This parameter identify the user."
        ::= { fciTelnetUserEntry 1 }


    fciTelnetUserStatus OBJECT-TYPE
        SYNTAX  INTEGER {
                valid(1),
                invalid(2)
                }
        ACCESS  read-write
        STATUS  mandatory
        DESCRIPTION
                "This parameter set the status of the raw"
        ::= { fciTelnetUserEntry 2 }


    fciTelnetUserLogin OBJECT-TYPE
        SYNTAX  DisplayString (SIZE(0..16))
        ACCESS  read-write
        STATUS  mandatory
        DESCRIPTION
                "This parameter set the login identification of the
                user. The password ask to the user would the
                associated priority password.
                The modification of the parameter takes effect
                after a hot reset and is used for new connections."
        ::= { fciTelnetUserEntry 3 }


    fciTelnetUserPriority OBJECT-TYPE
        SYNTAX  INTEGER (0..9)
        ACCESS  read-write
        STATUS  mandatory
        DESCRIPTION
                "This parameter associate a priority level to a
                user. The priority level give access right to
                different service.
                The default value is set to the lower priority
                level.
                The modification of the parameter takes effect
                after a hot reset and is used for new connections."
        ::= { fciTelnetUserEntry 4 }


    fcIpx OBJECT IDENTIFIER ::= { frxConfig 37 }


    fcxInstance OBJECT IDENTIFIER ::= { fcIpx 1 }


    fcxIpxRouting OBJECT-TYPE
        SYNTAX  INTEGER {
                off(1),
                on(2)
                }
        ACCESS  read-write
        STATUS  mandatory
        DESCRIPTION
                "Activation"
        ::= { fcxInstance 1 }


    fcxBasicSysName OBJECT-TYPE
        SYNTAX  DisplayString (SIZE(1..47))
        ACCESS  read-write
        STATUS  mandatory
        DESCRIPTION
                "ipxBasicSysName"
        ::= { fcxInstance 12 }


    fcxAdvSysMaxPathSplits OBJECT-TYPE
        SYNTAX  INTEGER (1..32)
        ACCESS  read-write
        STATUS  mandatory
        DESCRIPTION
                "ipxAdvSysMaxPathSplits"
        ::= { fcxInstance 15 }


    fcxAdvSysMaxHops OBJECT-TYPE
        SYNTAX  INTEGER (2..255)
        ACCESS  read-write
        STATUS  mandatory
        DESCRIPTION
                "ipxAdvSysMaxHops"
        ::= { fcxInstance 16 }


    fcxCircuits OBJECT IDENTIFIER ::= { fcIpx 10 }


    fcxCircuitTable OBJECT-TYPE
        SYNTAX  SEQUENCE OF FcxCircuitEntry
        ACCESS  not-accessible
        STATUS  mandatory
        DESCRIPTION
                ""
        ::= { fcxCircuits 1 }


    fcxCircuitEntry OBJECT-TYPE
        SYNTAX  FcxCircuitEntry
        ACCESS  not-accessible
        STATUS  mandatory
        DESCRIPTION
                "An entry of fcxCircuitTable."
        INDEX   { fcxCircCircuitId }
        ::= { fcxCircuitTable 1 }


        FcxCircuitEntry ::=
                SEQUENCE {
                    fcxCircCircuitId
                        INTEGER,
                    fcxCircStatus
                        INTEGER,
                    fcxCircVirtualPortId
                        INTEGER,
                    fcxCircOperState
                        INTEGER,
                    fcxCircName
                        DisplayString,
                    fcxCircType
                        INTEGER,
                    fcxCircLocalMaxPacketSize
                        INTEGER,
                    fcxCircNetNumber
                        OCTET STRING,
                    fcxCircChecksumEnabling
                        INTEGER
                }


    fcxCircCircuitId OBJECT-TYPE
        SYNTAX  INTEGER (1..199)
        ACCESS  read-only
        STATUS  mandatory
        DESCRIPTION
                "Circuit id"
        ::= { fcxCircuitEntry 1 }


    fcxCircStatus OBJECT-TYPE
        SYNTAX  INTEGER {
                valid(1),
                invalid(2)
                }
        ACCESS  read-write
        STATUS  mandatory
        DESCRIPTION
                "Status"
        ::= { fcxCircuitEntry 2 }


    fcxCircVirtualPortId OBJECT-TYPE
        SYNTAX  INTEGER (0..11)
        ACCESS  read-write
        STATUS  mandatory
        DESCRIPTION
                "VP id"
        ::= { fcxCircuitEntry 3 }


    fcxCircOperState OBJECT-TYPE
        SYNTAX  INTEGER {
                down(1),
                up(2)
                }
        ACCESS  read-write
        STATUS  mandatory
        DESCRIPTION
                "ipxCircOperState"
        ::= { fcxCircuitEntry 10 }


    fcxCircName OBJECT-TYPE
        SYNTAX  DisplayString (SIZE(1..24))
        ACCESS  read-write
        STATUS  mandatory
        DESCRIPTION
                "ipxCircName"
        ::= { fcxCircuitEntry 11 }


    fcxCircType OBJECT-TYPE
        SYNTAX  INTEGER {
                broadcast(2),
                ptToPt(3),
                dynamic(6)
                }
        ACCESS  read-write
        STATUS  mandatory
        DESCRIPTION
                "ipxCircType"
        ::= { fcxCircuitEntry 12 }


    fcxCircLocalMaxPacketSize OBJECT-TYPE
        SYNTAX  INTEGER (512..65535)
        ACCESS  read-write
        STATUS  mandatory
        DESCRIPTION
                "ipxCircLocalMaxPacketSize"
        ::= { fcxCircuitEntry 13 }


    fcxCircNetNumber OBJECT-TYPE
        SYNTAX  OCTET STRING (SIZE(4))
        ACCESS  read-write
        STATUS  mandatory
        DESCRIPTION
                "ipxCircNetNumber"
        ::= { fcxCircuitEntry 14 }


    fcxCircChecksumEnabling OBJECT-TYPE
        SYNTAX  INTEGER {
                off(1),
                on(2)
                }
        ACCESS  read-write
        STATUS  mandatory
        DESCRIPTION
                "Calcul du checksum"
        ::= { fcxCircuitEntry 20 }


    fcxCircuitLocalVpTable OBJECT-TYPE
        SYNTAX  SEQUENCE OF FcxCircuitLocalVpEntry
        ACCESS  not-accessible
        STATUS  mandatory
        DESCRIPTION
                ""
        ::= { fcxCircuits 2 }


    fcxCircuitLocalVpEntry OBJECT-TYPE
        SYNTAX  FcxCircuitLocalVpEntry
        ACCESS  not-accessible
        STATUS  mandatory
        DESCRIPTION
                "An entry of fcxCircuitLocalVpTable."
        INDEX   { fcxCircLvpCircuitId }
        ::= { fcxCircuitLocalVpTable 1 }


        FcxCircuitLocalVpEntry ::=
                SEQUENCE {
                    fcxCircLvpCircuitId
                        INTEGER,
                    fcxCircLvpStatus
                        INTEGER,
                    fcxCircLvpEncapsulation
                        INTEGER
                }


    fcxCircLvpCircuitId OBJECT-TYPE
        SYNTAX  INTEGER (1..199)
        ACCESS  read-only
        STATUS  mandatory
        DESCRIPTION
                "Circuit id"
        ::= { fcxCircuitLocalVpEntry 1 }


    fcxCircLvpStatus OBJECT-TYPE
        SYNTAX  INTEGER {
                valid(1),
                invalid(2)
                }
        ACCESS  read-write
        STATUS  mandatory
        DESCRIPTION
                "Status"
        ::= { fcxCircuitLocalVpEntry 2 }


    fcxCircLvpEncapsulation OBJECT-TYPE
        SYNTAX  INTEGER {
                ethernet(1),
                ether802-3(2),
                ether802-2(3),
                etherSnap(4)
                }
        ACCESS  read-write
        STATUS  mandatory
        DESCRIPTION
                "Encapsulation"
        ::= { fcxCircuitLocalVpEntry 3 }


    fcxCircuitRemoteVpTable OBJECT-TYPE
        SYNTAX  SEQUENCE OF FcxCircuitRemoteVpEntry
        ACCESS  not-accessible
        STATUS  mandatory
        DESCRIPTION
                ""
        ::= { fcxCircuits 3 }


    fcxCircuitRemoteVpEntry OBJECT-TYPE
        SYNTAX  FcxCircuitRemoteVpEntry
        ACCESS  not-accessible
        STATUS  mandatory
        DESCRIPTION
                "An entry of fcxCircuitRemoteVpTable."
        INDEX   { fcxCircRvpCircuitId }
        ::= { fcxCircuitRemoteVpTable 1 }


        FcxCircuitRemoteVpEntry ::=
                SEQUENCE {
                    fcxCircRvpCircuitId
                        INTEGER,
                    fcxCircRvpStatus
                        INTEGER,
                    fcxCircRvpRemoteAddress
                        OCTET STRING,
                    fcxCircRvpLocalNode
                        OCTET STRING
                }


    fcxCircRvpCircuitId OBJECT-TYPE
        SYNTAX  INTEGER (1..199)
        ACCESS  read-only
        STATUS  mandatory
        DESCRIPTION
                "Circuit id"
        ::= { fcxCircuitRemoteVpEntry 1 }


    fcxCircRvpStatus OBJECT-TYPE
        SYNTAX  INTEGER {
                valid(1),
                invalid(2)
                }
        ACCESS  read-write
        STATUS  mandatory
        DESCRIPTION
                "Status"
        ::= { fcxCircuitRemoteVpEntry 2 }


    fcxCircRvpRemoteAddress OBJECT-TYPE
        SYNTAX  OCTET STRING (SIZE(8))
        ACCESS  read-write
        STATUS  mandatory
        DESCRIPTION
                "Adresse WAN"
        ::= { fcxCircuitRemoteVpEntry 3 }


    fcxCircRvpLocalNode OBJECT-TYPE
        SYNTAX  OCTET STRING (SIZE(6))
        ACCESS  read-write
        STATUS  mandatory
        DESCRIPTION
                "Adresse locale"
        ::= { fcxCircuitRemoteVpEntry 4 }


    fcxRouting OBJECT IDENTIFIER ::= { fcIpx 20 }


    fcxRoutInstance OBJECT IDENTIFIER ::= { fcxRouting 1 }


    fcxRoutType20PacketBroadcasting OBJECT-TYPE
        SYNTAX  INTEGER {
                off(1),
                onLanOnly(2),
                on(3)
                }
        ACCESS  read-write
        STATUS  mandatory
        DESCRIPTION
                "Diffusion des paquets IPX de type 20"
        ::= { fcxRoutInstance 10 }


    fcxRoutCircuitTable OBJECT-TYPE
        SYNTAX  SEQUENCE OF FcxRoutCircuitEntry
        ACCESS  not-accessible
        STATUS  mandatory
        DESCRIPTION
                ""
        ::= { fcxRouting 10 }


    fcxRoutCircuitEntry OBJECT-TYPE
        SYNTAX  FcxRoutCircuitEntry
        ACCESS  not-accessible
        STATUS  mandatory
        DESCRIPTION
                "An entry of fcxRoutCircuitTable."
        INDEX   { fcxRoutCircCircuitId }
        ::= { fcxRoutCircuitTable 1 }


        FcxRoutCircuitEntry ::=
                SEQUENCE {
                    fcxRoutCircCircuitId
                        INTEGER,
                    fcxRoutCircNcpSpoofing
                        INTEGER,
                    fcxRoutCircType20PacketBroadcasting
                        INTEGER,
                    fcxRoutCircAddressFiltering
                        INTEGER
                }


    fcxRoutCircCircuitId OBJECT-TYPE
        SYNTAX  INTEGER (1..199)
        ACCESS  read-only
        STATUS  mandatory
        DESCRIPTION
                "Circuit id"
        ::= { fcxRoutCircuitEntry 1 }


    fcxRoutCircNcpSpoofing OBJECT-TYPE
        SYNTAX  INTEGER {
                off(1),
                on(2)
                }
        ACCESS  read-write
        STATUS  mandatory
        DESCRIPTION
                "Netware Core Protocol Spoofing"
        ::= { fcxRoutCircuitEntry 2 }


    fcxRoutCircType20PacketBroadcasting OBJECT-TYPE
        SYNTAX  INTEGER {
                off(1),
                on(2)
                }
        ACCESS  read-write
        STATUS  mandatory
        DESCRIPTION
                "Diffusion des paquets IPX de type 20"
        ::= { fcxRoutCircuitEntry 3 }


    fcxRoutCircAddressFiltering OBJECT-TYPE
        SYNTAX  INTEGER {
                off(1),
                permitted(2),
                denied(3)
                }
        ACCESS  read-write
        STATUS  mandatory
        DESCRIPTION
                "Filtrage sur adresse IPX"
        ::= { fcxRoutCircuitEntry 4 }


    fcxRoutIpxStaticRouteTable OBJECT-TYPE
        SYNTAX  SEQUENCE OF FcxRoutIpxStaticRouteEntry
        ACCESS  not-accessible
        STATUS  mandatory
        DESCRIPTION
                ""
        ::= { fcxRouting 20 }


    fcxRoutIpxStaticRouteEntry OBJECT-TYPE
        SYNTAX  FcxRoutIpxStaticRouteEntry
        ACCESS  not-accessible
        STATUS  mandatory
        DESCRIPTION
                "An entry of fcxRoutIpxStaticRouteTable."
        INDEX   { fcxRoutStaticRouteCircuitId,
                  fcxRoutStaticRouteNetNum }
        ::= { fcxRoutIpxStaticRouteTable 1 }


        FcxRoutIpxStaticRouteEntry ::=
                SEQUENCE {
                    fcxRoutStaticRouteCircuitId
                        INTEGER,
                    fcxRoutStaticRouteNetNum
                        OCTET STRING,
                    fcxRoutStaticRouteStatus
                        INTEGER,
                    fcxRoutStaticRouteTicks
                        INTEGER,
                    fcxRoutStaticRouteHopCount
                        INTEGER
                }


    fcxRoutStaticRouteCircuitId OBJECT-TYPE
        SYNTAX  INTEGER (1..199)
        ACCESS  read-only
        STATUS  mandatory
        DESCRIPTION
                "ipxStaticRouteCircIndex"
        ::= { fcxRoutIpxStaticRouteEntry 1 }


    fcxRoutStaticRouteNetNum OBJECT-TYPE
        SYNTAX  OCTET STRING (SIZE(4))
        ACCESS  read-only
        STATUS  mandatory
        DESCRIPTION
                "ipxStaticRouteNetNum"
        ::= { fcxRoutIpxStaticRouteEntry 2 }


    fcxRoutStaticRouteStatus OBJECT-TYPE
        SYNTAX  INTEGER {
                valid(1),
                invalid(2)
                }
        ACCESS  read-write
        STATUS  mandatory
        DESCRIPTION
                "Status"
        ::= { fcxRoutIpxStaticRouteEntry 3 }


    fcxRoutStaticRouteTicks OBJECT-TYPE
        SYNTAX  INTEGER (1..65535)
        ACCESS  read-write
        STATUS  mandatory
        DESCRIPTION
                "ipxStaticRouteTicks en 1/60eme de seconde"
        ::= { fcxRoutIpxStaticRouteEntry 4 }


    fcxRoutStaticRouteHopCount OBJECT-TYPE
        SYNTAX  INTEGER (1..255)
        ACCESS  read-write
        STATUS  mandatory
        DESCRIPTION
                "ipxStaticRouteHopCount"
        ::= { fcxRoutIpxStaticRouteEntry 5 }


    fcxRoutAddressFilteringTable OBJECT-TYPE
        SYNTAX  SEQUENCE OF FcxRoutAddressFilteringEntry
        ACCESS  not-accessible
        STATUS  mandatory
        DESCRIPTION
                ""
        ::= { fcxRouting 30 }


    fcxRoutAddressFilteringEntry OBJECT-TYPE
        SYNTAX  FcxRoutAddressFilteringEntry
        ACCESS  not-accessible
        STATUS  mandatory
        DESCRIPTION
                "An entry of fcxRoutAddressFilteringTable."
        INDEX   { fcxRoutAddrFltCircuitId,
                  fcxRoutAddrFltFilterId }
        ::= { fcxRoutAddressFilteringTable 1 }


        FcxRoutAddressFilteringEntry ::=
                SEQUENCE {
                    fcxRoutAddrFltCircuitId
                        INTEGER,
                    fcxRoutAddrFltFilterId
                        INTEGER,
                    fcxRoutAddrFltStatus
                        INTEGER,
                    fcxRoutAddrFltFiltering
                        INTEGER,
                    fcxRoutAddrFltField
                        INTEGER,
                    fcxRoutAddrFltMask
                        OCTET STRING,
                    fcxRoutAddrFltValue
                        OCTET STRING
                }


    fcxRoutAddrFltCircuitId OBJECT-TYPE
        SYNTAX  INTEGER (1..199)
        ACCESS  read-only
        STATUS  mandatory
        DESCRIPTION
                "Circuit id"
        ::= { fcxRoutAddressFilteringEntry 1 }


    fcxRoutAddrFltFilterId OBJECT-TYPE
        SYNTAX  INTEGER (0..199)
        ACCESS  read-only
        STATUS  mandatory
        DESCRIPTION
                "Filtre id"
        ::= { fcxRoutAddressFilteringEntry 2 }


    fcxRoutAddrFltStatus OBJECT-TYPE
        SYNTAX  INTEGER {
                valid(1),
                invalid(2)
                }
        ACCESS  read-write
        STATUS  mandatory
        DESCRIPTION
                "Status"
        ::= { fcxRoutAddressFilteringEntry 3 }


    fcxRoutAddrFltFiltering OBJECT-TYPE
        SYNTAX  INTEGER {
                off(1),
                on(2)
                }
        ACCESS  read-write
        STATUS  mandatory
        DESCRIPTION
                "Activation du filtre"
        ::= { fcxRoutAddressFilteringEntry 4 }


    fcxRoutAddrFltField OBJECT-TYPE
        SYNTAX  INTEGER {
                sourceNetAddress(1),
                destNetAddress(2),
                sourceSocket(3),
                destSocket(4)
                }
        ACCESS  read-write
        STATUS  mandatory
        DESCRIPTION
                "Champ"
        ::= { fcxRoutAddressFilteringEntry 5 }


    fcxRoutAddrFltMask OBJECT-TYPE
        SYNTAX  OCTET STRING (SIZE(4))
        ACCESS  read-write
        STATUS  mandatory
        DESCRIPTION
                "Masque"
        ::= { fcxRoutAddressFilteringEntry 6 }


    fcxRoutAddrFltValue OBJECT-TYPE
        SYNTAX  OCTET STRING (SIZE(4))
        ACCESS  read-write
        STATUS  mandatory
        DESCRIPTION
                "Valeur"
        ::= { fcxRoutAddressFilteringEntry 7 }


    fcxRoutingInformationProtocol OBJECT IDENTIFIER ::= { fcIpx 25 }


    fcxRipInstance OBJECT IDENTIFIER ::= { fcxRoutingInformationProtocol 1 }


    fcxRipSysState OBJECT-TYPE
        SYNTAX  INTEGER {
                off(1),
                on(2)
                }
        ACCESS  read-write
        STATUS  mandatory
        DESCRIPTION
                "ripSysState"
        ::= { fcxRipInstance 1 }


    fcxRipInputFiltering OBJECT-TYPE
        SYNTAX  INTEGER {
                off(1),
                permitted(2),
                denied(3)
                }
        ACCESS  read-write
        STATUS  mandatory
        DESCRIPTION
                "Filtrage RIP en entree"
        ::= { fcxRipInstance 2 }


    fcxRipCircuitTable OBJECT-TYPE
        SYNTAX  SEQUENCE OF FcxRipCircuitEntry
        ACCESS  not-accessible
        STATUS  mandatory
        DESCRIPTION
                ""
        ::= { fcxRoutingInformationProtocol 10 }


    fcxRipCircuitEntry OBJECT-TYPE
        SYNTAX  FcxRipCircuitEntry
        ACCESS  not-accessible
        STATUS  mandatory
        DESCRIPTION
                "An entry of fcxRipCircuitTable."
        INDEX   { fcxRipCircCircuitId }
        ::= { fcxRipCircuitTable 1 }


        FcxRipCircuitEntry ::=
                SEQUENCE {
                    fcxRipCircCircuitId
                        INTEGER,
                    fcxRipCircState
                        INTEGER,
                    fcxRipCircPace
                        INTEGER,
                    fcxRipCircUpdate
                        INTEGER,
                    fcxRipCircAgeMultiplier
                        INTEGER,
                    fcxRipCircPacketSize
                        INTEGER,
                    fcxRipCircOutputFiltering
                        INTEGER
                }


    fcxRipCircCircuitId OBJECT-TYPE
        SYNTAX  INTEGER (1..199)
        ACCESS  read-only
        STATUS  mandatory
        DESCRIPTION
                "Circuit id"
        ::= { fcxRipCircuitEntry 1 }


    fcxRipCircState OBJECT-TYPE
        SYNTAX  INTEGER {
                off(1),
                on(2)
                }
        ACCESS  read-write
        STATUS  mandatory
        DESCRIPTION
                "ripCircState"
        ::= { fcxRipCircuitEntry 10 }


    fcxRipCircPace OBJECT-TYPE
        SYNTAX  INTEGER (1..100)
        ACCESS  read-write
        STATUS  mandatory
        DESCRIPTION
                "ripCircPace"
        ::= { fcxRipCircuitEntry 11 }


    fcxRipCircUpdate OBJECT-TYPE
        SYNTAX  INTEGER (0..65535)
        ACCESS  read-write
        STATUS  mandatory
        DESCRIPTION
                "ripCircUpdate"
        ::= { fcxRipCircuitEntry 12 }


    fcxRipCircAgeMultiplier OBJECT-TYPE
        SYNTAX  INTEGER (2..255)
        ACCESS  read-write
        STATUS  mandatory
        DESCRIPTION
                "ripCircAgeMultiplier"
        ::= { fcxRipCircuitEntry 13 }


    fcxRipCircPacketSize OBJECT-TYPE
        SYNTAX  INTEGER (512..65535)
        ACCESS  read-write
        STATUS  mandatory
        DESCRIPTION
                "ripCircPacketSize"
        ::= { fcxRipCircuitEntry 14 }


    fcxRipCircOutputFiltering OBJECT-TYPE
        SYNTAX  INTEGER {
                off(1),
                permitted(2),
                denied(3)
                }
        ACCESS  read-write
        STATUS  mandatory
        DESCRIPTION
                "Filtrage RIP en sortie"
        ::= { fcxRipCircuitEntry 20 }


    fcxRipInputFilteringTable OBJECT-TYPE
        SYNTAX  SEQUENCE OF FcxRipInputFilteringEntry
        ACCESS  not-accessible
        STATUS  mandatory
        DESCRIPTION
                ""
        ::= { fcxRoutingInformationProtocol 11 }


    fcxRipInputFilteringEntry OBJECT-TYPE
        SYNTAX  FcxRipInputFilteringEntry
        ACCESS  not-accessible
        STATUS  mandatory
        DESCRIPTION
                "An entry of fcxRipInputFilteringTable."
        INDEX   { fcxRipInFltFilterId }
        ::= { fcxRipInputFilteringTable 1 }


        FcxRipInputFilteringEntry ::=
                SEQUENCE {
                    fcxRipInFltFilterId
                        INTEGER,
                    fcxRipInFltStatus
                        INTEGER,
                    fcxRipInFltFiltering
                        INTEGER,
                    fcxRipInFltNetAddress
                        OCTET STRING,
                    fcxRipInFltMask
                        OCTET STRING
                }


    fcxRipInFltFilterId OBJECT-TYPE
        SYNTAX  INTEGER (0..199)
        ACCESS  read-only
        STATUS  mandatory
        DESCRIPTION
                "Filtre id"
        ::= { fcxRipInputFilteringEntry 1 }


    fcxRipInFltStatus OBJECT-TYPE
        SYNTAX  INTEGER {
                valid(1),
                invalid(2)
                }
        ACCESS  read-write
        STATUS  mandatory
        DESCRIPTION
                "Status"
        ::= { fcxRipInputFilteringEntry 2 }


    fcxRipInFltFiltering OBJECT-TYPE
        SYNTAX  INTEGER {
                off(1),
                on(2)
                }
        ACCESS  read-write
        STATUS  mandatory
        DESCRIPTION
                "Activation du filtre"
        ::= { fcxRipInputFilteringEntry 3 }


    fcxRipInFltNetAddress OBJECT-TYPE
        SYNTAX  OCTET STRING (SIZE(4))
        ACCESS  read-write
        STATUS  mandatory
        DESCRIPTION
                "Adresse reseau"
        ::= { fcxRipInputFilteringEntry 4 }


    fcxRipInFltMask OBJECT-TYPE
        SYNTAX  OCTET STRING (SIZE(4))
        ACCESS  read-write
        STATUS  mandatory
        DESCRIPTION
                "Masque adresse"
        ::= { fcxRipInputFilteringEntry 5 }


    fcxRipOutputFilteringTable OBJECT-TYPE
        SYNTAX  SEQUENCE OF FcxRipOutputFilteringEntry
        ACCESS  not-accessible
        STATUS  mandatory
        DESCRIPTION
                ""
        ::= { fcxRoutingInformationProtocol 12 }


    fcxRipOutputFilteringEntry OBJECT-TYPE
        SYNTAX  FcxRipOutputFilteringEntry
        ACCESS  not-accessible
        STATUS  mandatory
        DESCRIPTION
                "An entry of fcxRipOutputFilteringTable."
        INDEX   { fcxRipOutFltCircuitId,
                  fcxRipOutFltFilterId }
        ::= { fcxRipOutputFilteringTable 1 }


        FcxRipOutputFilteringEntry ::=
                SEQUENCE {
                    fcxRipOutFltCircuitId
                        INTEGER,
                    fcxRipOutFltFilterId
                        INTEGER,
                    fcxRipOutFltStatus
                        INTEGER,
                    fcxRipOutFltFiltering
                        INTEGER,
                    fcxRipOutFltNetAddress
                        OCTET STRING,
                    fcxRipOutFltMask
                        OCTET STRING
                }


    fcxRipOutFltCircuitId OBJECT-TYPE
        SYNTAX  INTEGER (1..199)
        ACCESS  read-only
        STATUS  mandatory
        DESCRIPTION
                "Circuit id"
        ::= { fcxRipOutputFilteringEntry 1 }


    fcxRipOutFltFilterId OBJECT-TYPE
        SYNTAX  INTEGER (0..199)
        ACCESS  read-only
        STATUS  mandatory
        DESCRIPTION
                "Filtre id"
        ::= { fcxRipOutputFilteringEntry 2 }


    fcxRipOutFltStatus OBJECT-TYPE
        SYNTAX  INTEGER {
                valid(1),
                invalid(2)
                }
        ACCESS  read-write
        STATUS  mandatory
        DESCRIPTION
                "Status"
        ::= { fcxRipOutputFilteringEntry 3 }


    fcxRipOutFltFiltering OBJECT-TYPE
        SYNTAX  INTEGER {
                off(1),
                on(2)
                }
        ACCESS  read-write
        STATUS  mandatory
        DESCRIPTION
                "Activation du filtre"
        ::= { fcxRipOutputFilteringEntry 4 }


    fcxRipOutFltNetAddress OBJECT-TYPE
        SYNTAX  OCTET STRING (SIZE(4))
        ACCESS  read-write
        STATUS  mandatory
        DESCRIPTION
                "Adresse reseau"
        ::= { fcxRipOutputFilteringEntry 5 }


    fcxRipOutFltMask OBJECT-TYPE
        SYNTAX  OCTET STRING (SIZE(4))
        ACCESS  read-write
        STATUS  mandatory
        DESCRIPTION
                "Masque adresse"
        ::= { fcxRipOutputFilteringEntry 6 }


    fcxServices OBJECT IDENTIFIER ::= { fcIpx 30 }


    fcxServInstance OBJECT IDENTIFIER ::= { fcxServices 1 }


    fcxServSapSysState OBJECT-TYPE
        SYNTAX  INTEGER {
                off(1),
                on(2)
                }
        ACCESS  read-write
        STATUS  mandatory
        DESCRIPTION
                "sapSysState"
        ::= { fcxServInstance 1 }


    fcxServSapInputFiltering OBJECT-TYPE
        SYNTAX  INTEGER {
                off(1),
                permitted(2),
                denied(3)
                }
        ACCESS  read-write
        STATUS  mandatory
        DESCRIPTION
                "Filtrage SAP en entree"
        ::= { fcxServInstance 12 }


    fcxServCircuitTable OBJECT-TYPE
        SYNTAX  SEQUENCE OF FcxServCircuitEntry
        ACCESS  not-accessible
        STATUS  mandatory
        DESCRIPTION
                ""
        ::= { fcxServices 10 }


    fcxServCircuitEntry OBJECT-TYPE
        SYNTAX  FcxServCircuitEntry
        ACCESS  not-accessible
        STATUS  mandatory
        DESCRIPTION
                "An entry of fcxServCircuitTable."
        INDEX   { fcxServCircSapCircuitId }
        ::= { fcxServCircuitTable 1 }


        FcxServCircuitEntry ::=
                SEQUENCE {
                    fcxServCircSapCircuitId
                        INTEGER,
                    fcxServCircSapState
                        INTEGER,
                    fcxServCircSapPace
                        INTEGER,
                    fcxServCircSapUpdate
                        INTEGER,
                    fcxServCircSapAgeMultiplier
                        INTEGER,
                    fcxServCircSapPacketSize
                        INTEGER,
                    fcxServCircSapGetNearestServerReply
                        INTEGER,
                    fcxServCircSapOutputFiltering
                        INTEGER
                }


    fcxServCircSapCircuitId OBJECT-TYPE
        SYNTAX  INTEGER (1..199)
        ACCESS  read-only
        STATUS  mandatory
        DESCRIPTION
                "sapCircIndex"
        ::= { fcxServCircuitEntry 1 }


    fcxServCircSapState OBJECT-TYPE
        SYNTAX  INTEGER {
                off(1),
                on(2)
                }
        ACCESS  read-write
        STATUS  mandatory
        DESCRIPTION
                "sapCircState"
        ::= { fcxServCircuitEntry 2 }


    fcxServCircSapPace OBJECT-TYPE
        SYNTAX  INTEGER (1..100)
        ACCESS  read-write
        STATUS  mandatory
        DESCRIPTION
                "sapCircPace"
        ::= { fcxServCircuitEntry 3 }


    fcxServCircSapUpdate OBJECT-TYPE
        SYNTAX  INTEGER (0..65535)
        ACCESS  read-write
        STATUS  mandatory
        DESCRIPTION
                "sapCircUpdate"
        ::= { fcxServCircuitEntry 4 }


    fcxServCircSapAgeMultiplier OBJECT-TYPE
        SYNTAX  INTEGER (2..255)
        ACCESS  read-write
        STATUS  mandatory
        DESCRIPTION
                "sapCircAgeMultiplier"
        ::= { fcxServCircuitEntry 5 }


    fcxServCircSapPacketSize OBJECT-TYPE
        SYNTAX  INTEGER (512..65535)
        ACCESS  read-write
        STATUS  mandatory
        DESCRIPTION
                "sapCircPacketSize"
        ::= { fcxServCircuitEntry 6 }


    fcxServCircSapGetNearestServerReply OBJECT-TYPE
        SYNTAX  INTEGER {
                no(1),
                yes(2)
                }
        ACCESS  read-write
        STATUS  mandatory
        DESCRIPTION
                "sapCircGetNearestServerReply"
        ::= { fcxServCircuitEntry 7 }


    fcxServCircSapOutputFiltering OBJECT-TYPE
        SYNTAX  INTEGER {
                off(1),
                permitted(2),
                denied(3)
                }
        ACCESS  read-write
        STATUS  mandatory
        DESCRIPTION
                "Filtrage SAP en sortie"
        ::= { fcxServCircuitEntry 10 }


    fcxServStaticServiceTable OBJECT-TYPE
        SYNTAX  SEQUENCE OF FcxServStaticServiceEntry
        ACCESS  not-accessible
        STATUS  mandatory
        DESCRIPTION
                ""
        ::= { fcxServices 20 }


    fcxServStaticServiceEntry OBJECT-TYPE
        SYNTAX  FcxServStaticServiceEntry
        ACCESS  not-accessible
        STATUS  mandatory
        DESCRIPTION
                "An entry of fcxServStaticServiceTable."
        INDEX   { fcxServStaticServiceId }
        ::= { fcxServStaticServiceTable 1 }


        FcxServStaticServiceEntry ::=
                SEQUENCE {
                    fcxServStaticServiceId
                        INTEGER,
                    fcxServStaticStatus
                        INTEGER,
                    fcxServStaticCircuitId
                        INTEGER,
                    fcxServStaticName
                        DisplayString,
                    fcxServStaticType
                        OCTET STRING,
                    fcxServStaticNetNum
                        OCTET STRING,
                    fcxServStaticNode
                        OCTET STRING,
                    fcxServStaticSocket
                        OCTET STRING,
                    fcxServStaticHopCount
                        INTEGER
                }


    fcxServStaticServiceId OBJECT-TYPE
        SYNTAX  INTEGER (0..199)
        ACCESS  read-only
        STATUS  mandatory
        DESCRIPTION
                "Service Id"
        ::= { fcxServStaticServiceEntry 1 }


    fcxServStaticStatus OBJECT-TYPE
        SYNTAX  INTEGER {
                valid(1),
                invalid(2)
                }
        ACCESS  read-write
        STATUS  mandatory
        DESCRIPTION
                "Status"
        ::= { fcxServStaticServiceEntry 2 }


    fcxServStaticCircuitId OBJECT-TYPE
        SYNTAX  INTEGER (1..199)
        ACCESS  read-write
        STATUS  mandatory
        DESCRIPTION
                "ipxStaticServCircIndex"
        ::= { fcxServStaticServiceEntry 3 }


    fcxServStaticName OBJECT-TYPE
        SYNTAX  DisplayString (SIZE(1..47))
        ACCESS  read-write
        STATUS  mandatory
        DESCRIPTION
                "ipxStaticServName"
        ::= { fcxServStaticServiceEntry 4 }


    fcxServStaticType OBJECT-TYPE
        SYNTAX  OCTET STRING (SIZE(2))
        ACCESS  read-write
        STATUS  mandatory
        DESCRIPTION
                "ipxStaticServType"
        ::= { fcxServStaticServiceEntry 5 }


    fcxServStaticNetNum OBJECT-TYPE
        SYNTAX  OCTET STRING (SIZE(4))
        ACCESS  read-write
        STATUS  mandatory
        DESCRIPTION
                "ipxStaticServNetNum"
        ::= { fcxServStaticServiceEntry 6 }


    fcxServStaticNode OBJECT-TYPE
        SYNTAX  OCTET STRING (SIZE(6))
        ACCESS  read-write
        STATUS  mandatory
        DESCRIPTION
                "ipxStaticServNode"
        ::= { fcxServStaticServiceEntry 7 }


    fcxServStaticSocket OBJECT-TYPE
        SYNTAX  OCTET STRING (SIZE(2))
        ACCESS  read-write
        STATUS  mandatory
        DESCRIPTION
                "ipxStaticServSocket"
        ::= { fcxServStaticServiceEntry 8 }


    fcxServStaticHopCount OBJECT-TYPE
        SYNTAX  INTEGER (0..255)
        ACCESS  read-write
        STATUS  mandatory
        DESCRIPTION
                "ipxStaticServHopCount"
        ::= { fcxServStaticServiceEntry 9 }


    fcxServSapInputFilteringTable OBJECT-TYPE
        SYNTAX  SEQUENCE OF FcxServSapInputFilteringEntry
        ACCESS  not-accessible
        STATUS  mandatory
        DESCRIPTION
                ""
        ::= { fcxServices 30 }


    fcxServSapInputFilteringEntry OBJECT-TYPE
        SYNTAX  FcxServSapInputFilteringEntry
        ACCESS  not-accessible
        STATUS  mandatory
        DESCRIPTION
                "An entry of fcxServSapInputFilteringTable."
        INDEX   { fcxServSapInFltFilterId }
        ::= { fcxServSapInputFilteringTable 1 }


        FcxServSapInputFilteringEntry ::=
                SEQUENCE {
                    fcxServSapInFltFilterId
                        INTEGER,
                    fcxServSapInFltStatus
                        INTEGER,
                    fcxServSapInFltFiltering
                        INTEGER,
                    fcxServSapInFltCheckedField
                        INTEGER,
                    fcxServSapInFltServiceNameType
                        INTEGER,
                    fcxServSapInFltServiceName
                        DisplayString,
                    fcxServSapInFltServiceType
                        OCTET STRING
                }


    fcxServSapInFltFilterId OBJECT-TYPE
        SYNTAX  INTEGER (0..199)
        ACCESS  read-only
        STATUS  mandatory
        DESCRIPTION
                "Filtre id"
        ::= { fcxServSapInputFilteringEntry 1 }


    fcxServSapInFltStatus OBJECT-TYPE
        SYNTAX  INTEGER {
                valid(1),
                invalid(2)
                }
        ACCESS  read-write
        STATUS  mandatory
        DESCRIPTION
                "Status"
        ::= { fcxServSapInputFilteringEntry 2 }


    fcxServSapInFltFiltering OBJECT-TYPE
        SYNTAX  INTEGER {
                off(1),
                on(2)
                }
        ACCESS  read-write
        STATUS  mandatory
        DESCRIPTION
                "Activation du filtre"
        ::= { fcxServSapInputFilteringEntry 3 }


    fcxServSapInFltCheckedField OBJECT-TYPE
        SYNTAX  INTEGER {
                name(1),
                type(2),
                nameAndType(3)
                }
        ACCESS  read-write
        STATUS  mandatory
        DESCRIPTION
                "Champ evalue"
        ::= { fcxServSapInputFilteringEntry 4 }


    fcxServSapInFltServiceNameType OBJECT-TYPE
        SYNTAX  INTEGER {
                fullName(1),
                beginningPattern(2)
                }
        ACCESS  read-write
        STATUS  mandatory
        DESCRIPTION
                "Type de nom de service"
        ::= { fcxServSapInputFilteringEntry 5 }


    fcxServSapInFltServiceName OBJECT-TYPE
        SYNTAX  DisplayString (SIZE(0..47))
        ACCESS  read-write
        STATUS  mandatory
        DESCRIPTION
                "Nom de service"
        ::= { fcxServSapInputFilteringEntry 6 }


    fcxServSapInFltServiceType OBJECT-TYPE
        SYNTAX  OCTET STRING (SIZE(2))
        ACCESS  read-write
        STATUS  mandatory
        DESCRIPTION
                "Type de service"
        ::= { fcxServSapInputFilteringEntry 7 }


    fcxServSapOutputFilteringTable OBJECT-TYPE
        SYNTAX  SEQUENCE OF FcxServSapOutputFilteringEntry
        ACCESS  not-accessible
        STATUS  mandatory
        DESCRIPTION
                ""
        ::= { fcxServices 31 }


    fcxServSapOutputFilteringEntry OBJECT-TYPE
        SYNTAX  FcxServSapOutputFilteringEntry
        ACCESS  not-accessible
        STATUS  mandatory
        DESCRIPTION
                "An entry of fcxServSapOutputFilteringTable."
        INDEX   { fcxServSapOutFltCircuitId,
                  fcxServSapOutFltFilterId }
        ::= { fcxServSapOutputFilteringTable 1 }


        FcxServSapOutputFilteringEntry ::=
                SEQUENCE {
                    fcxServSapOutFltCircuitId
                        INTEGER,
                    fcxServSapOutFltFilterId
                        INTEGER,
                    fcxServSapOutFltStatus
                        INTEGER,
                    fcxServSapOutFltFiltering
                        INTEGER,
                    fcxServSapOutFltCheckedField
                        INTEGER,
                    fcxServSapOutFltServiceNameType
                        INTEGER,
                    fcxServSapOutFltServiceName
                        DisplayString,
                    fcxServSapOutFltServiceType
                        OCTET STRING
                }


    fcxServSapOutFltCircuitId OBJECT-TYPE
        SYNTAX  INTEGER (1..199)
        ACCESS  read-only
        STATUS  mandatory
        DESCRIPTION
                "Circuit id"
        ::= { fcxServSapOutputFilteringEntry 1 }


    fcxServSapOutFltFilterId OBJECT-TYPE
        SYNTAX  INTEGER (0..199)
        ACCESS  read-only
        STATUS  mandatory
        DESCRIPTION
                "Filtre id"
        ::= { fcxServSapOutputFilteringEntry 2 }


    fcxServSapOutFltStatus OBJECT-TYPE
        SYNTAX  INTEGER {
                valid(1),
                invalid(2)
                }
        ACCESS  read-write
        STATUS  mandatory
        DESCRIPTION
                "Status"
        ::= { fcxServSapOutputFilteringEntry 3 }


    fcxServSapOutFltFiltering OBJECT-TYPE
        SYNTAX  INTEGER {
                off(1),
                on(2)
                }
        ACCESS  read-write
        STATUS  mandatory
        DESCRIPTION
                "Activation du filtre"
        ::= { fcxServSapOutputFilteringEntry 4 }


    fcxServSapOutFltCheckedField OBJECT-TYPE
        SYNTAX  INTEGER {
                name(1),
                type(2),
                nameAndType(3)
                }
        ACCESS  read-write
        STATUS  mandatory
        DESCRIPTION
                "Champ evalue"
        ::= { fcxServSapOutputFilteringEntry 5 }


    fcxServSapOutFltServiceNameType OBJECT-TYPE
        SYNTAX  INTEGER {
                fullName(1),
                beginningPattern(2)
                }
        ACCESS  read-write
        STATUS  mandatory
        DESCRIPTION
                "Type de nom de service"
        ::= { fcxServSapOutputFilteringEntry 6 }


    fcxServSapOutFltServiceName OBJECT-TYPE
        SYNTAX  DisplayString (SIZE(0..47))
        ACCESS  read-write
        STATUS  mandatory
        DESCRIPTION
                "Nom de service"
        ::= { fcxServSapOutputFilteringEntry 7 }


    fcxServSapOutFltServiceType OBJECT-TYPE
        SYNTAX  OCTET STRING (SIZE(2))
        ACCESS  read-write
        STATUS  mandatory
        DESCRIPTION
                "Type de service"
        ::= { fcxServSapOutputFilteringEntry 8 }


    fcClnp OBJECT IDENTIFIER ::= { frxConfig 38 }


    fccClnpRouting OBJECT-TYPE
        SYNTAX  INTEGER {
                off(1),
                on(2)
                }
        ACCESS  read-write
        STATUS  mandatory
        DESCRIPTION
                "AdminStatus"
        ::= { fcClnp 1 }


    fccLocalNetworkEntityTitle OBJECT-TYPE
        SYNTAX  OCTET STRING (SIZE(22))
        ACCESS  read-write
        STATUS  mandatory
        DESCRIPTION
                "LocalNet"
        ::= { fcClnp 2 }


    fccErrorFramesSending OBJECT-TYPE
        SYNTAX  INTEGER {
                off(1),
                on(2)
                }
        ACCESS  read-write
        STATUS  mandatory
        DESCRIPTION
                "ErrorFrames"
        ::= { fcClnp 4 }


    fccVirtualPortTable OBJECT-TYPE
        SYNTAX  SEQUENCE OF FccVirtualPortEntry
        ACCESS  not-accessible
        STATUS  mandatory
        DESCRIPTION
                ""
        ::= { fcClnp 10 }


    fccVirtualPortEntry OBJECT-TYPE
        SYNTAX  FccVirtualPortEntry
        ACCESS  not-accessible
        STATUS  mandatory
        DESCRIPTION
                "An entry of fccVirtualPortTable."
        INDEX   { fccVpVirtualPortId }
        ::= { fccVirtualPortTable 1 }


        FccVirtualPortEntry ::=
                SEQUENCE {
                    fccVpVirtualPortId
                        INTEGER,
                    fccVpStatus
                        INTEGER,
                    fccVpMtu
                        INTEGER
                }


    fccVpVirtualPortId OBJECT-TYPE
        SYNTAX  INTEGER (0..11)
        ACCESS  read-only
        STATUS  mandatory
        DESCRIPTION
                "VP id"
        ::= { fccVirtualPortEntry 1 }


    fccVpStatus OBJECT-TYPE
        SYNTAX  INTEGER {
                valid(1),
                invalid(2)
                }
        ACCESS  read-write
        STATUS  mandatory
        DESCRIPTION
                "Status"
        ::= { fccVirtualPortEntry 2 }


    fccVpMtu OBJECT-TYPE
        SYNTAX  INTEGER (512..1600)
        ACCESS  read-write
        STATUS  mandatory
        DESCRIPTION
                "MTU"
        ::= { fccVirtualPortEntry 4 }


    fccLocalVirtualPortTable OBJECT-TYPE
        SYNTAX  SEQUENCE OF FccLocalVirtualPortEntry
        ACCESS  not-accessible
        STATUS  mandatory
        DESCRIPTION
                ""
        ::= { fcClnp 11 }


    fccLocalVirtualPortEntry OBJECT-TYPE
        SYNTAX  FccLocalVirtualPortEntry
        ACCESS  not-accessible
        STATUS  mandatory
        DESCRIPTION
                "An entry of fccLocalVirtualPortTable."
        INDEX   { fccLvpVirtualPortId }
        ::= { fccLocalVirtualPortTable 1 }


        FccLocalVirtualPortEntry ::=
                SEQUENCE {
                    fccLvpVirtualPortId
                        INTEGER,
                    fccLvpStatus
                        INTEGER,
                    fccLvpEsIsRedirection
                        INTEGER,
                    fccLvpEsIsConfigTimer
                        INTEGER,
                    fccLvpEsIsHoldingTimer
                        INTEGER
                }


    fccLvpVirtualPortId OBJECT-TYPE
        SYNTAX  INTEGER (0..11)
        ACCESS  read-only
        STATUS  mandatory
        DESCRIPTION
                "VP id"
        ::= { fccLocalVirtualPortEntry 1 }


    fccLvpStatus OBJECT-TYPE
        SYNTAX  INTEGER {
                valid(1),
                invalid(2)
                }
        ACCESS  read-write
        STATUS  mandatory
        DESCRIPTION
                "Status"
        ::= { fccLocalVirtualPortEntry 2 }


    fccLvpEsIsRedirection OBJECT-TYPE
        SYNTAX  INTEGER {
                off(1),
                on(2)
                }
        ACCESS  read-write
        STATUS  mandatory
        DESCRIPTION
                "EsIsRedirects"
        ::= { fccLocalVirtualPortEntry 3 }


    fccLvpEsIsConfigTimer OBJECT-TYPE
        SYNTAX  INTEGER (1..3600)
        ACCESS  read-write
        STATUS  mandatory
        DESCRIPTION
                "EsIsConfigTimer"
        ::= { fccLocalVirtualPortEntry 4 }


    fccLvpEsIsHoldingTimer OBJECT-TYPE
        SYNTAX  INTEGER (1..3600)
        ACCESS  read-write
        STATUS  mandatory
        DESCRIPTION
                "EsIsHoldingTimer"
        ::= { fccLocalVirtualPortEntry 5 }


    fccNeighborTable OBJECT-TYPE
        SYNTAX  SEQUENCE OF FccNeighborEntry
        ACCESS  not-accessible
        STATUS  mandatory
        DESCRIPTION
                ""
        ::= { fcClnp 20 }


    fccNeighborEntry OBJECT-TYPE
        SYNTAX  FccNeighborEntry
        ACCESS  not-accessible
        STATUS  mandatory
        DESCRIPTION
                "An entry of fccNeighborTable."
        INDEX   { fccNeighNeighborId }
        ::= { fccNeighborTable 1 }


        FccNeighborEntry ::=
                SEQUENCE {
                    fccNeighNeighborId
                        INTEGER,
                    fccNeighStatus
                        INTEGER,
                    fccNeighType
                        INTEGER,
                    fccNeighVirtualPortId
                        INTEGER,
                    fccNeighClnpAddress
                        OCTET STRING
                }


    fccNeighNeighborId OBJECT-TYPE
        SYNTAX  INTEGER (0..199)
        ACCESS  read-only
        STATUS  mandatory
        DESCRIPTION
                "Neighbor id"
        ::= { fccNeighborEntry 1 }


    fccNeighStatus OBJECT-TYPE
        SYNTAX  INTEGER {
                valid(1),
                invalid(2)
                }
        ACCESS  read-write
        STATUS  mandatory
        DESCRIPTION
                "Status"
        ::= { fccNeighborEntry 2 }


    fccNeighType OBJECT-TYPE
        SYNTAX  INTEGER {
                es(1),
                is(2)
                }
        ACCESS  read-write
        STATUS  mandatory
        DESCRIPTION
                "Type"
        ::= { fccNeighborEntry 3 }


    fccNeighVirtualPortId OBJECT-TYPE
        SYNTAX  INTEGER (0..11)
        ACCESS  read-write
        STATUS  mandatory
        DESCRIPTION
                "VP id"
        ::= { fccNeighborEntry 4 }


    fccNeighClnpAddress OBJECT-TYPE
        SYNTAX  OCTET STRING (SIZE(22))
        ACCESS  read-write
        STATUS  mandatory
        DESCRIPTION
                "Adresse IP-ISO"
        ::= { fccNeighborEntry 5 }


    fccLocalNeighborTable OBJECT-TYPE
        SYNTAX  SEQUENCE OF FccLocalNeighborEntry
        ACCESS  not-accessible
        STATUS  mandatory
        DESCRIPTION
                ""
        ::= { fcClnp 21 }


    fccLocalNeighborEntry OBJECT-TYPE
        SYNTAX  FccLocalNeighborEntry
        ACCESS  not-accessible
        STATUS  mandatory
        DESCRIPTION
                "An entry of fccLocalNeighborTable."
        INDEX   { fccLneighNeighborId }
        ::= { fccLocalNeighborTable 1 }


        FccLocalNeighborEntry ::=
                SEQUENCE {
                    fccLneighNeighborId
                        INTEGER,
                    fccLneighStatus
                        INTEGER,
                    fccLneighMacAddress
                        OCTET STRING
                }


    fccLneighNeighborId OBJECT-TYPE
        SYNTAX  INTEGER (0..199)
        ACCESS  read-only
        STATUS  mandatory
        DESCRIPTION
                "Neighbor id"
        ::= { fccLocalNeighborEntry 1 }


    fccLneighStatus OBJECT-TYPE
        SYNTAX  INTEGER {
                valid(1),
                invalid(2)
                }
        ACCESS  read-write
        STATUS  mandatory
        DESCRIPTION
                "Status"
        ::= { fccLocalNeighborEntry 2 }


    fccLneighMacAddress OBJECT-TYPE
        SYNTAX  OCTET STRING (SIZE(6))
        ACCESS  read-write
        STATUS  mandatory
        DESCRIPTION
                "Adresse MAC"
        ::= { fccLocalNeighborEntry 3 }


    fccRemoteNeighborTable OBJECT-TYPE
        SYNTAX  SEQUENCE OF FccRemoteNeighborEntry
        ACCESS  not-accessible
        STATUS  mandatory
        DESCRIPTION
                ""
        ::= { fcClnp 22 }


    fccRemoteNeighborEntry OBJECT-TYPE
        SYNTAX  FccRemoteNeighborEntry
        ACCESS  not-accessible
        STATUS  mandatory
        DESCRIPTION
                "An entry of fccRemoteNeighborTable."
        INDEX   { fccRneighNeighborId }
        ::= { fccRemoteNeighborTable 1 }


        FccRemoteNeighborEntry ::=
                SEQUENCE {
                    fccRneighNeighborId
                        INTEGER,
                    fccRneighStatus
                        INTEGER,
                    fccRneighRemoteAddress
                        OCTET STRING
                }


    fccRneighNeighborId OBJECT-TYPE
        SYNTAX  INTEGER (0..199)
        ACCESS  read-only
        STATUS  mandatory
        DESCRIPTION
                "Neighbor id"
        ::= { fccRemoteNeighborEntry 1 }


    fccRneighStatus OBJECT-TYPE
        SYNTAX  INTEGER {
                valid(1),
                invalid(2)
                }
        ACCESS  read-write
        STATUS  mandatory
        DESCRIPTION
                "Status"
        ::= { fccRemoteNeighborEntry 2 }


    fccRneighRemoteAddress OBJECT-TYPE
        SYNTAX  OCTET STRING (SIZE(8))
        ACCESS  read-write
        STATUS  mandatory
        DESCRIPTION
                "Adresse WAN"
        ::= { fccRemoteNeighborEntry 3 }


    fccClnpRouteTable OBJECT-TYPE
        SYNTAX  SEQUENCE OF FccClnpRouteEntry
        ACCESS  not-accessible
        STATUS  mandatory
        DESCRIPTION
                ""
        ::= { fcClnp 30 }


    fccClnpRouteEntry OBJECT-TYPE
        SYNTAX  FccClnpRouteEntry
        ACCESS  not-accessible
        STATUS  mandatory
        DESCRIPTION
                "An entry of fccClnpRouteTable."
        INDEX   { fccRoutRouteId }
        ::= { fccClnpRouteTable 1 }


        FccClnpRouteEntry ::=
                SEQUENCE {
                    fccRoutRouteId
                        INTEGER,
                    fccRoutStatus
                        INTEGER,
                    fccRoutDestClnpAddress
                        OCTET STRING,
                    fccRoutNextHopNeighborId
                        INTEGER
                }


    fccRoutRouteId OBJECT-TYPE
        SYNTAX  INTEGER (0..199)
        ACCESS  read-only
        STATUS  mandatory
        DESCRIPTION
                "Route id"
        ::= { fccClnpRouteEntry 1 }


    fccRoutStatus OBJECT-TYPE
        SYNTAX  INTEGER {
                valid(1),
                invalid(2)
                }
        ACCESS  read-write
        STATUS  mandatory
        DESCRIPTION
                "Status"
        ::= { fccClnpRouteEntry 2 }


    fccRoutDestClnpAddress OBJECT-TYPE
        SYNTAX  OCTET STRING (SIZE(22))
        ACCESS  read-write
        STATUS  mandatory
        DESCRIPTION
                "Adresse IP-ISO destination"
        ::= { fccClnpRouteEntry 3 }


    fccRoutNextHopNeighborId OBJECT-TYPE
        SYNTAX  INTEGER (0..199)
        ACCESS  read-write
        STATUS  mandatory
        DESCRIPTION
                "Next Hop neighbor id"
        ::= { fccClnpRouteEntry 5 }



    fmEvents OBJECT IDENTIFIER ::= { frxManagement 5 }


    fmeTroubleReport OBJECT IDENTIFIER ::= { fmEvents 1 }


    fmeTrblEventType OBJECT-TYPE
        SYNTAX  INTEGER {
                startAfterUnintentionalCrash(1),
                startAfterDeliberateCrash(2),
                startAfterHardwareResetOrStartUp(3)
                }
        ACCESS  read-only
        STATUS  mandatory
        DESCRIPTION
                "The value of this object is the cause of the
                system starting."
        ::= { fmeTroubleReport 1 }


    fmeTroubleReportInfoTable OBJECT-TYPE
        SYNTAX  SEQUENCE OF FmeTroubleReportInfoEntry
        ACCESS  not-accessible
        STATUS  mandatory
        DESCRIPTION
                "This table contains the additional information
                about the trouble report. It's the fatal error
                zone : the snapshot of the memory and registers
                when there is a trouble. It contains the registers
                state, the system stack ..."
        ::= { fmeTroubleReport 2 }


    fmeTroubleReportInfoEntry OBJECT-TYPE
        SYNTAX  FmeTroubleReportInfoEntry
        ACCESS  not-accessible
        STATUS  mandatory
        DESCRIPTION
                "An entry of fmeTroubleReportInfoTable."
        INDEX   { fmeTrblInfoIndex }
        ::= { fmeTroubleReportInfoTable 1 }


        FmeTroubleReportInfoEntry ::=
                SEQUENCE {
                    fmeTrblInfoIndex
                        INTEGER,
                    fmeTrblInfoData
                        DisplayString
                }


    fmeTrblInfoIndex OBJECT-TYPE
        SYNTAX  INTEGER (1..194)
        ACCESS  read-only
        STATUS  mandatory
        DESCRIPTION
                "The value of this object identifies one and only
                one element of the trouble report."
        ::= { fmeTroubleReportInfoEntry 1 }


    fmeTrblInfoData OBJECT-TYPE
        SYNTAX  DisplayString (SIZE(0..16))
        ACCESS  read-only
        STATUS  mandatory
        DESCRIPTION
                "The value of this object is the data of this
                element of the trouble report."
        ::= { fmeTroubleReportInfoEntry 2 }


    fmeFamilyTable OBJECT-TYPE
        SYNTAX  SEQUENCE OF FmeFamilyEntry
        ACCESS  not-accessible
        STATUS  mandatory
        DESCRIPTION
                "This table contains general information about the
                families of the outstanding events. For one
                family, the maximum number of stored events is 6,
                but all the families can store simultaneously at
                most 3 events. So, the maximum number can
                fluctuate following the busy memory. When one
                event is added to the list of one family, the
                oldest event is kept in memory, and the event is
                added at the end of the list, with the possibility
                of a rotation of the stored events if there is no
                free memory."
        ::= { fmEvents 2 }


    fmeFamilyEntry OBJECT-TYPE
        SYNTAX  FmeFamilyEntry
        ACCESS  not-accessible
        STATUS  mandatory
        DESCRIPTION
                "An entry of fmeFamilyTable."
        INDEX   { fmeFamFamilyId }
        ::= { fmeFamilyTable 1 }


        FmeFamilyEntry ::=
                SEQUENCE {
                    fmeFamFamilyId
                        INTEGER,
                    fmeFamStoredEventsCount
                        INTEGER,
                    fmeFamStoredEventsCommand
                        INTEGER
                }


    fmeFamFamilyId OBJECT-TYPE
        SYNTAX  INTEGER {
                troubleReport-00(1),
                management-01(2),
                synchronousSignalling-02(3),
                x25SynchronousProcedure-03(4),
                synchronousLink-04(5),
                linePhysicalLevel-05(6),
                asynchronousProtocolLevel-06(7),
                asynchronousCommandSyntax-07(8),
                asynchronousSemanticLevel-08(9),
                sdlcProcedure-09(10),
                vipProcedure-0A(11),
                tvipFradBscProcedure-0B(12),
                dlcBscProcedure-0C(13),
                mlp-0D(14),
                pstnProcedure-0E(15),
                securizedVcEsv-0F(16),
                securizedVcN4-10(17),
                securizedVcIr-11(18),
                isdnDChannelProcedure-12(19),
                x29Rerouting-13(20),
                ethernetBridgeAndIpRouterFunctions-14(21),
                dlcMtrFrad-15(22),
                compressionProcedure-16(23),
                dlmFunction-17(24),
                configurationFunction-18(25),
                lmiFunction-19(26),
                ppp-1A(27),
                frameRelaySna-1B(28),
                tokenRing-1C(29)
                }
        ACCESS  read-only
        STATUS  mandatory
        DESCRIPTION
                "The value of this object identifies one and only
                one family."
        ::= { fmeFamilyEntry 1 }


    fmeFamStoredEventsCount OBJECT-TYPE
        SYNTAX  INTEGER (1..6)
        ACCESS  read-only
        STATUS  mandatory
        DESCRIPTION
                "The value of this object how many events are
                stored for this family."
        ::= { fmeFamilyEntry 2 }


    fmeFamStoredEventsCommand OBJECT-TYPE
        SYNTAX  INTEGER {
                ready(1),
                delete(2)
                }
        ACCESS  read-write
        STATUS  mandatory
        DESCRIPTION
                "The value of this object permits, when it is set
                to 'delete', to destroy the stored events of this
                family. The equipment answers always with the
                value 'ready' to a GetRequest on this object."
        ::= { fmeFamilyEntry 3 }


    fmeEventTable OBJECT-TYPE
        SYNTAX  SEQUENCE OF FmeEventEntry
        ACCESS  not-accessible
        STATUS  mandatory
        DESCRIPTION
                "This table contains the stored outstanding events."
        ::= { fmEvents 3 }


    fmeEventEntry OBJECT-TYPE
        SYNTAX  FmeEventEntry
        ACCESS  not-accessible
        STATUS  mandatory
        DESCRIPTION
                "An entry of fmeEventTable."
        INDEX   { fmeEvtFamilyId,
                  fmeEvtEventIndex }
        ::= { fmeEventTable 1 }


        FmeEventEntry ::=
                SEQUENCE {
                    fmeEvtFamilyId
                        INTEGER,
                    fmeEvtEventIndex
                        INTEGER,
                    fmeEvtEventType
                        OCTET STRING,
                    fmeEvtTime
                        TimeTicks,
                    fmeEvtLineId
                        INTEGER,
                    fmeEvtData
                        DisplayString
                }


    fmeEvtFamilyId OBJECT-TYPE
        SYNTAX  INTEGER {
                troubleReport-00(1),
                management-01(2),
                synchronousSignalling-02(3),
                x25SynchronousProcedure-03(4),
                synchronousLink-04(5),
                linePhysicalLevel-05(6),
                asynchronousProtocolLevel-06(7),
                asynchronousCommandSyntax-07(8),
                asynchronousSemanticLevel-08(9),
                sdlcProcedure-09(10),
                vipProcedure-0A(11),
                tvipFradBscProcedure-0B(12),
                dlcBscProcedure-0C(13),
                mlp-0D(14),
                pstnProcedure-0E(15),
                securizedVcEsv-0F(16),
                securizedVcN4-10(17),
                securizedVcIr-11(18),
                isdnDChannelProcedure-12(19),
                x29Rerouting-13(20),
                ethernetBridgeAndIpRouterFunctions-14(21),
                dlcMtrFrad-15(22),
                compressionProcedure-16(23),
                dlmFunction-17(24),
                configurationFunction-18(25),
                lmiFunction-19(26),
                ppp-1A(27),
                frameRelaySna-1B(28),
                tokenRing-1C(29)
                }
        ACCESS  read-only
        STATUS  mandatory
        DESCRIPTION
                "The value of this object identifies one and only
                one family. This is the family this outstanding
                event belongs to."
        ::= { fmeEventEntry 1 }


    fmeEvtEventIndex OBJECT-TYPE
        SYNTAX  INTEGER (1..6)
        ACCESS  read-only
        STATUS  mandatory
        DESCRIPTION
                "The value of this object identifies one and only
                one outstanding event of this familty."
        ::= { fmeEventEntry 2 }


    fmeEvtEventType OBJECT-TYPE
        SYNTAX  OCTET STRING (SIZE(1))
        ACCESS  read-only
        STATUS  mandatory
        DESCRIPTION
                "The value of this object is the event type. See
                the management function manual for more
                information on the description of the events."
        ::= { fmeEventEntry 3 }


    fmeEvtTime OBJECT-TYPE
        SYNTAX  TimeTicks
        ACCESS  read-only
        STATUS  mandatory
        DESCRIPTION
                "The value of this object is the value of sysUpTime
                when this event was stored."
        ::= { fmeEventEntry 4 }


    fmeEvtLineId OBJECT-TYPE
        SYNTAX  INTEGER (0..255)
        ACCESS  read-only
        STATUS  mandatory
        DESCRIPTION
                "The value of this object is the identifier of the
                line where this event takes place. The value '255'
                means 'general' (i.e., not a particular line)."
        ::= { fmeEventEntry 5 }


    fmeEvtData OBJECT-TYPE
        SYNTAX  DisplayString (SIZE(0..80))
        ACCESS  read-only
        STATUS  mandatory
        DESCRIPTION
                "The value of this object contains additional data
                for this event."
        ::= { fmeEventEntry 6 }


    fmeTrapInfo OBJECT IDENTIFIER ::= { fmEvents 4 }


    fmeTrapLineId OBJECT-TYPE
        SYNTAX  INTEGER (0..255)
        ACCESS  read-only
        STATUS  mandatory
        DESCRIPTION
                "The value of this object is the identifier of the
                line where the event takes place. The value '255'
                means 'general' (i.e., not a particular line).

                This object is only used in a Trap PDU and is not
                accessible by GET requests."
        ::= { fmeTrapInfo 1 }


    fmeTrapFamilyId OBJECT-TYPE
        SYNTAX  INTEGER {
                troubleReport-00(1),
                management-01(2),
                synchronousSignalling-02(3),
                x25SynchronousProcedure-03(4),
                synchronousLink-04(5),
                linePhysicalLevel-05(6),
                asynchronousProtocolLevel-06(7),
                asynchronousCommandSyntax-07(8),
                asynchronousSemanticLevel-08(9),
                sdlcProcedure-09(10),
                vipProcedure-0A(11),
                tvipFradBscProcedure-0B(12),
                dlcBscProcedure-0C(13),
                mlp-0D(14),
                pstnProcedure-0E(15),
                securizedVcEsv-0F(16),
                securizedVcN4-10(17),
                securizedVcIr-11(18),
                isdnDChannelProcedure-12(19),
                x29Rerouting-13(20),
                ethernetBridgeAndIpRouterFunctions-14(21),
                dlcMtrFrad-15(22),
                compressionProcedure-16(23),
                dlmFunction-17(24),
                configurationFunction-18(25),
                lmiFunction-19(26),
                ppp-1A(27),
                frameRelaySna-1B(28)
                }
        ACCESS  read-only
        STATUS  mandatory
        DESCRIPTION
                "The value of this object identifies one and only
                one family. This is the family the outstanding
                event belongs to.

                This object is only used in a Trap PDU and is not
                accessible by GET requests."
        ::= { fmeTrapInfo 2 }


    fmeTrapEventType OBJECT-TYPE
        SYNTAX  INTEGER (0..255)
        ACCESS  read-only
        STATUS  mandatory
        DESCRIPTION
                "The value of this object is the event type. See
                the management function manual for more
                information on the description of the events.

                This object is only used in a Trap PDU and is not
                accessible by GET requests."
        ::= { fmeTrapInfo 3 }


    fmeTrapEventData OBJECT-TYPE
        SYNTAX  DisplayString (SIZE(0..80))
        ACCESS  read-only
        STATUS  mandatory
        DESCRIPTION
                "The value of this object contains additional data
                for the event.

                This object is only used in a Trap PDU and is not
                accessible by GET requests."
        ::= { fmeTrapInfo 4 }


    fmStat OBJECT IDENTIFIER ::= { frxManagement 10 }


    fmStatControl OBJECT IDENTIFIER ::= { fmStat 1 }


    fmsCtrlStatus OBJECT-TYPE
        SYNTAX  INTEGER {
                inProgress(1),
                notInProgress(2)
                }
        ACCESS  read-only
        STATUS  mandatory
        DESCRIPTION
                "The value of this object indicates the processing
                state of the statistics. The value 'notInProgress'
                indicates that there is only a SNMP access at the
                management function. The value 'InProgress'
                indicates that there is an access to the
                management function which is not a SNMP access."
        ::= { fmStatControl 1 }


    fmsCtrlSumming OBJECT-TYPE
        SYNTAX  INTEGER {
                infinite(1),
                notInfinite(2)
                }
        ACCESS  read-write
        STATUS  mandatory
        DESCRIPTION
                "The value of this object is the summing mode of
                the statistics. The value 'infinite' indicates
                that the statistics are calculated since the last
                counters reset. With the value 'notInfinite', the
                statistics are calculated on the configurable
                period, which there is an automatic counters reset
                beyond. The default value is 'notInfinite'."
        ::= { fmStatControl 2 }


    fmsCtrlCountersCommand OBJECT-TYPE
        SYNTAX  INTEGER {
                ready(1),
                reset(2)
                }
        ACCESS  read-write
        STATUS  mandatory
        DESCRIPTION
                "The value of this object permits, when it is set
                to 'reset', to re-initialize all the counters
                except those in fmStatEthOutputTrafficTable,
                fmStatEthInputTrafficTable and
                fmStatEthManagementTable. The equipment answers
                always with the value 'ready' to a GetRequest on
                this object."
        ::= { fmStatControl 3 }


    fmsCtrlResetTime OBJECT-TYPE
        SYNTAX  TimeTicks
        ACCESS  read-only
        STATUS  mandatory
        DESCRIPTION
                "The value of this object is the value of sysUpTime
                when the counters were re-initialized by a 'reset'
                command (see fmsCtrlCountersCommand)."
        ::= { fmStatControl 4 }


    fmStatGlobal OBJECT IDENTIFIER ::= { fmStat 10 }


    fmsGlobInitBuffCount OBJECT-TYPE
        SYNTAX  Gauge
        ACCESS  read-only
        STATUS  mandatory
        DESCRIPTION
                "The value of this object is the total number of
                the buffers created when initializing."
        ::= { fmStatGlobal 1 }


    fmsGlobFreeBuffCount OBJECT-TYPE
        SYNTAX  Gauge
        ACCESS  read-only
        STATUS  mandatory
        DESCRIPTION
                "The value of this object is the total number of
                the free buffers."
        ::= { fmStatGlobal 2 }


    fmsGlobCpuA OBJECT-TYPE
        SYNTAX  Gauge
        ACCESS  read-only
        STATUS  mandatory
        DESCRIPTION
                "The value of this object is the maximum instant
                load of the CPU A on all the modules."
        ::= { fmStatGlobal 3 }


    fmsGlobCpuB OBJECT-TYPE
        SYNTAX  Gauge
        ACCESS  read-only
        STATUS  mandatory
        DESCRIPTION
                "The value of this object is the maximum instant
                load of the CPU B on all the modules."
        ::= { fmStatGlobal 4 }


    fmsGlobVcInUseCount OBJECT-TYPE
        SYNTAX  Gauge
        ACCESS  read-only
        STATUS  mandatory
        DESCRIPTION
                "The value of this object is the number of the
                virtual circuits established."
        ::= { fmStatGlobal 5 }


    fmsGlobGeneratorsInUseCount OBJECT-TYPE
        SYNTAX  Gauge
        ACCESS  read-only
        STATUS  mandatory
        DESCRIPTION
                "The value of this object is the number of the busy
                traffic generators."
        ::= { fmStatGlobal 6 }


    fmsGlobCompressOctetGain OBJECT-TYPE
        SYNTAX  Gauge
        ACCESS  read-only
        STATUS  mandatory
        DESCRIPTION
                "The value of this object is the total gain, in
                volume (in bytes), generated by the
                compression/scrambling function."
        ::= { fmStatGlobal 7 }


    fmsGlobCompressBillGain OBJECT-TYPE
        SYNTAX  Gauge
        ACCESS  read-only
        STATUS  mandatory
        DESCRIPTION
                "The value of this object is the total gain, in
                billing (in segments), generated by the
                compression/scrambling function."
        ::= { fmStatGlobal 8 }


    fmsGlobLanCpu OBJECT-TYPE
        SYNTAX  Counter
        ACCESS  read-only
        STATUS  mandatory
        DESCRIPTION
                "The value of this object is the transputer CPU
                load."
        ::= { fmStatGlobal 9 }


    fmsGlobCongCpuLostBlocks OBJECT-TYPE
        SYNTAX  Counter
        ACCESS  read-only
        STATUS  mandatory
        DESCRIPTION
                "Nb de blocs de 0 a N octets rejetes sur congestion
                CPU (N = 160 en v2.1)"
        ::= { fmStatGlobal 10 }


    fmsGlobCongRamLostBlocks OBJECT-TYPE
        SYNTAX  Counter
        ACCESS  read-only
        STATUS  mandatory
        DESCRIPTION
                "Nb de blocs de 0 a N octets rejetes sur congestion
                memoire (N = 160 en v2.1)"
        ::= { fmStatGlobal 11 }


    fmStatInputTraffic OBJECT IDENTIFIER ::= { fmStat 11 }


    fmsInputDataPktsCounter OBJECT-TYPE
        SYNTAX  Counter
        ACCESS  read-only
        STATUS  mandatory
        DESCRIPTION
                "The value of this object is the total number of
                the data packets received by the internal switch
                from the beginning of the collection period."
        ::= { fmStatInputTraffic 1 }


    fmsInputDataBytesCounter OBJECT-TYPE
        SYNTAX  Counter
        ACCESS  read-only
        STATUS  mandatory
        DESCRIPTION
                "The value of this object is the total number of
                the data bytes received by the internal switch
                from the beginning of the collection period."
        ::= { fmStatInputTraffic 2 }


    fmsInputIntrPktsCounter OBJECT-TYPE
        SYNTAX  Counter
        ACCESS  read-only
        STATUS  mandatory
        DESCRIPTION
                "The value of this object is the total number of
                the interrupt packets received by the internal
                switch from the beginning of the collection period."
        ::= { fmStatInputTraffic 3 }


    fmsInputReinitPktsCounter OBJECT-TYPE
        SYNTAX  Counter
        ACCESS  read-only
        STATUS  mandatory
        DESCRIPTION
                "The value of this object is the total number of
                the reset packets received by the internal switch
                from the beginning of the collection period."
        ::= { fmStatInputTraffic 4 }


    fmsInputCallPktsCounter OBJECT-TYPE
        SYNTAX  Counter
        ACCESS  read-only
        STATUS  mandatory
        DESCRIPTION
                "The value of this object is the total number of
                the call packets received by the internal switch
                from the beginning of the collection period."
        ::= { fmStatInputTraffic 5 }


    fmsInputCallConfPktsCounter OBJECT-TYPE
        SYNTAX  Counter
        ACCESS  read-only
        STATUS  mandatory
        DESCRIPTION
                "The value of this object is the total number of
                the call confirmation received and successfully
                processed by the internal switch from the
                beginning of the collection period. This object is
                therefore the number of the virtual circuits
                established from the beginning of the collection
                period."
        ::= { fmStatInputTraffic 6 }


    fmStatLineTable OBJECT-TYPE
        SYNTAX  SEQUENCE OF FmStatLineEntry
        ACCESS  not-accessible
        STATUS  mandatory
        DESCRIPTION
                "This table contains the information about the
                statistics by line."
        ::= { fmStat 12 }


    fmStatLineEntry OBJECT-TYPE
        SYNTAX  FmStatLineEntry
        ACCESS  not-accessible
        STATUS  mandatory
        DESCRIPTION
                "An entry of fmStatLineTable."
        INDEX   { fmsLineId }
        ::= { fmStatLineTable 1 }


        FmStatLineEntry ::=
                SEQUENCE {
                    fmsLineId
                        INTEGER,
                    fmsLineState
                        INTEGER,
                    fmsLineLcInUseCount
                        Gauge,
                    fmsLineReinitsCounter
                        Counter,
                    fmsLineIncidentsCounter
                        INTEGER,
                    fmsLineInputOctetsCounter
                        Counter,
                    fmsLineOutputOctetsCounter
                        Counter,
                    fmsLineType
                        INTEGER,
                    fmsLineTestState
                        INTEGER
                }


    fmsLineId OBJECT-TYPE
        SYNTAX  INTEGER (0..55)
        ACCESS  read-only
        STATUS  mandatory
        DESCRIPTION
                "The value of this object is the one line
                identifier."
        ::= { fmStatLineEntry 1 }


    fmsLineState OBJECT-TYPE
        SYNTAX  INTEGER {
                down(2),
                disconnectedByDiag(3),
                layer1Up(1),
                layer2Up(4),
                layer3Up(5)
                }
        ACCESS  read-only
        STATUS  mandatory
        DESCRIPTION
                "The value of this object is the state of this line."
        ::= { fmStatLineEntry 2 }


    fmsLineLcInUseCount OBJECT-TYPE
        SYNTAX  Gauge
        ACCESS  read-only
        STATUS  mandatory
        DESCRIPTION
                "The value of this object is the total number of
                the busy logical channels."
        ::= { fmStatLineEntry 3 }


    fmsLineReinitsCounter OBJECT-TYPE
        SYNTAX  Counter
        ACCESS  read-only
        STATUS  mandatory
        DESCRIPTION
                "The value of this object is the total number of
                the resets of this line from the beginning of the
                collection period."
        ::= { fmStatLineEntry 4 }


    fmsLineIncidentsCounter OBJECT-TYPE
        SYNTAX  INTEGER (0..255)
        ACCESS  read-only
        STATUS  mandatory
        DESCRIPTION
                "The value of this object is the total number of
                the incidents of this line from the beginning of
                the collection period."
        ::= { fmStatLineEntry 5 }


    fmsLineInputOctetsCounter OBJECT-TYPE
        SYNTAX  Counter
        ACCESS  read-only
        STATUS  mandatory
        DESCRIPTION
                "The value of this object is the total number of
                the bytes received over this line from the
                beginning of the collection period."
        ::= { fmStatLineEntry 6 }


    fmsLineOutputOctetsCounter OBJECT-TYPE
        SYNTAX  Counter
        ACCESS  read-only
        STATUS  mandatory
        DESCRIPTION
                "The value of this object is the total number of
                bytes sent over this line from the beginning of
                the collection period."
        ::= { fmStatLineEntry 7 }


    fmsLineType OBJECT-TYPE
        SYNTAX  INTEGER {
                x25Synchronous(1),
                asynchronous(2),
                asynchronousSdlc(4),
                synchronousVipCharacter(6),
                synchronousBscTransparentCharacter(7),
                characterSynchronousBsc3270Or2780-3780(8),
                isdnDChannel(14),
                isdnBChannelWithSignalling(15),
                isdnBChannelWithoutSignalling(16),
                isdnDChannelWithPll(17),
                frameRelayTypeTransit(19),
                hdlc(20),
                frameRelaySubscriber(21),
                lanConnection(23),
                lanIpRouter(27),
                lanBridgeOrIpRouter(28),
                asynchronousX28(30),
                synchronousPpp(39),
                asynchronousPpp(40),
                moduleLink(50),
                unitLink(51)
                }
        ACCESS  read-only
        STATUS  mandatory
        DESCRIPTION
                "The value of this object indicates the type of
                this line."
        ::= { fmStatLineEntry 20 }


    fmsLineTestState OBJECT-TYPE
        SYNTAX  INTEGER {
                off(1),
                on(2)
                }
        ACCESS  read-only
        STATUS  mandatory
        DESCRIPTION
                "The value of this object indicates the test state
                of this line."
        ::= { fmStatLineEntry 21 }


    fmStatSignalTable OBJECT-TYPE
        SYNTAX  SEQUENCE OF FmStatSignalEntry
        ACCESS  not-accessible
        STATUS  mandatory
        DESCRIPTION
                "This table contains the information about the
                lines signals."
        ::= { fmStat 13 }


    fmStatSignalEntry OBJECT-TYPE
        SYNTAX  FmStatSignalEntry
        ACCESS  not-accessible
        STATUS  mandatory
        DESCRIPTION
                "An entry of fmStatSignalTable."
        INDEX   { fmsSigPhysPortId }
        ::= { fmStatSignalTable 1 }


        FmStatSignalEntry ::=
                SEQUENCE {
                    fmsSigPhysPortId
                        INTEGER,
                    fmsSigState
                        INTEGER,
                    fmsSigDceOrDte
                        INTEGER,
                    fmsSig105
                        INTEGER,
                    fmsSig106
                        INTEGER,
                    fmsSig107
                        INTEGER,
                    fmsSig108
                        INTEGER,
                    fmsSig109
                        INTEGER,
                    fmsSig111
                        INTEGER,
                    fmsSig125
                        INTEGER,
                    fmsSig140
                        INTEGER,
                    fmsSig141
                        INTEGER,
                    fmsSig142
                        INTEGER,
                    fmsSigSyn
                        INTEGER
                }


    fmsSigPhysPortId OBJECT-TYPE
        SYNTAX  INTEGER (0..35)
        ACCESS  read-only
        STATUS  mandatory
        DESCRIPTION
                "The value of this object is the one physical line
                identifier."
        ::= { fmStatSignalEntry 1 }


    fmsSigState OBJECT-TYPE
        SYNTAX  INTEGER {
                down(1),
                up(2)
                }
        ACCESS  read-only
        STATUS  mandatory
        DESCRIPTION
                "The value of this object indictates the state of
                this line."
        ::= { fmStatSignalEntry 2 }


    fmsSigDceOrDte OBJECT-TYPE
        SYNTAX  INTEGER {
                dce(1),
                dte(2)
                }
        ACCESS  read-only
        STATUS  mandatory
        DESCRIPTION
                "The value of this object indicates whether the
                equipment is DTE or DCE for this line."
        ::= { fmStatSignalEntry 3 }


    fmsSig105 OBJECT-TYPE
        SYNTAX  INTEGER {
                off(1),
                on(2)
                }
        ACCESS  read-only
        STATUS  mandatory
        DESCRIPTION
                "The value of this object indicates the state of
                the signal 105 on this line."
        ::= { fmStatSignalEntry 4 }


    fmsSig106 OBJECT-TYPE
        SYNTAX  INTEGER {
                off(1),
                on(2)
                }
        ACCESS  read-only
        STATUS  mandatory
        DESCRIPTION
                "The value of this object indicates the state of
                the signal 106 on this line."
        ::= { fmStatSignalEntry 5 }


    fmsSig107 OBJECT-TYPE
        SYNTAX  INTEGER {
                off(1),
                on(2)
                }
        ACCESS  read-only
        STATUS  mandatory
        DESCRIPTION
                "The value of this object indicates the state of
                the signal 107 on this line."
        ::= { fmStatSignalEntry 6 }


    fmsSig108 OBJECT-TYPE
        SYNTAX  INTEGER {
                off(1),
                on(2)
                }
        ACCESS  read-only
        STATUS  mandatory
        DESCRIPTION
                "The value of this object indicates the state of
                the signal 108 on this line."
        ::= { fmStatSignalEntry 7 }


    fmsSig109 OBJECT-TYPE
        SYNTAX  INTEGER {
                off(1),
                on(2)
                }
        ACCESS  read-only
        STATUS  mandatory
        DESCRIPTION
                "The value of this object indicates the state of
                the signal 109 on this line."
        ::= { fmStatSignalEntry 8 }


    fmsSig111 OBJECT-TYPE
        SYNTAX  INTEGER {
                off(1),
                on(2)
                }
        ACCESS  read-only
        STATUS  mandatory
        DESCRIPTION
                "The value of this object indicates the state of
                the signal 111 on this line."
        ::= { fmStatSignalEntry 9 }


    fmsSig125 OBJECT-TYPE
        SYNTAX  INTEGER {
                off(1),
                on(2)
                }
        ACCESS  read-only
        STATUS  mandatory
        DESCRIPTION
                "The value of this object indicates the state of
                the signal 125 on this line."
        ::= { fmStatSignalEntry 10 }


    fmsSig140 OBJECT-TYPE
        SYNTAX  INTEGER {
                off(1),
                on(2)
                }
        ACCESS  read-only
        STATUS  mandatory
        DESCRIPTION
                "The value of this object indicates the state of
                the signal 140 on this line."
        ::= { fmStatSignalEntry 11 }


    fmsSig141 OBJECT-TYPE
        SYNTAX  INTEGER {
                off(1),
                on(2)
                }
        ACCESS  read-only
        STATUS  mandatory
        DESCRIPTION
                "The value of this object indicates the state of
                the signal 141 on this line."
        ::= { fmStatSignalEntry 12 }


    fmsSig142 OBJECT-TYPE
        SYNTAX  INTEGER {
                off(1),
                on(2)
                }
        ACCESS  read-only
        STATUS  mandatory
        DESCRIPTION
                "The value of this object indicates the state of
                the signal 142 on this line."
        ::= { fmStatSignalEntry 13 }


    fmsSigSyn OBJECT-TYPE
        SYNTAX  INTEGER {
                undefined(1),
                off(2),
                on(3)
                }
        ACCESS  read-only
        STATUS  mandatory
        DESCRIPTION
                "The value of this object indicates the state of
                the signal SYN on this line."
        ::= { fmStatSignalEntry 14 }


    fmStatLinesSummary OBJECT IDENTIFIER ::= { fmStat 15 }


    fmsLinesSummState OBJECT-TYPE
        SYNTAX  OCTET STRING (SIZE(0..80))
        ACCESS  read-only
        STATUS  mandatory
        DESCRIPTION
                "This object indicates the state of each line of
                the equipment with the following format,. each
                line using three octets (i.e., 24 bits) :
                   bit 0 : physical level (0 = down, 1 = up),
                   bit 1: level 3 (0 = down, 1 = up),
                   bits 2 to 8 : protocol (1 = X25 synchronous, 2
                        = asynchronous, 4 = asynchronous SDLC, 6 =
                        asynchronous VIP character, 7 = BSC
                        Transparent character, 8 = asynchronous on
                        BSC 3270 or 2780/3780, 14 = ISDN D-Channel
                        with or without PLL, 15 = ISDN B-Channel
                        with signalling, 16 = ISDN B-Channel
                        without signalling, 19 = Frame Relay
                        transit or FR-TE, 20 = HDLC-T, 21 = Frame
                        Relay subscriber, FRA, 23 = Ethernet, 30 =
                        asynchronous X28+),
                   bits 9 to 20 : number of active logical
                        channels (0 to 4095),
                   bits 20 to 23 : unused."
        ::= { fmStatLinesSummary 1 }


    fmStatStateTable OBJECT-TYPE
        SYNTAX  SEQUENCE OF FmStatStateEntry
        ACCESS  not-accessible
        STATUS  mandatory
        DESCRIPTION
                "This table contains the information about the type
                and the state of the lines."
        ::= { fmStat 20 }


    fmStatStateEntry OBJECT-TYPE
        SYNTAX  FmStatStateEntry
        ACCESS  not-accessible
        STATUS  mandatory
        DESCRIPTION
                "An entry of fmStatStateTable."
        INDEX   { fmsStateLine }
        ::= { fmStatStateTable 1 }


        FmStatStateEntry ::=
                SEQUENCE {
                    fmsStateLine
                        INTEGER,
                    fmsStateLineType
                        INTEGER,
                    fmsStateOsiState
                        INTEGER,
                    fmsStateTestState
                        INTEGER,
                    fmsStateMlpTrunkMainLine
                        INTEGER,
                    fmsStateMlpTrunkNumber
                        INTEGER,
                    fmsStateMlpTrunkState
                        INTEGER
                }


    fmsStateLine OBJECT-TYPE
        SYNTAX  INTEGER (0..55)
        ACCESS  read-only
        STATUS  mandatory
        DESCRIPTION
                "The value of this object is the one line
                identifier."
        ::= { fmStatStateEntry 1 }


    fmsStateLineType OBJECT-TYPE
        SYNTAX  INTEGER {
                x25Synchronous(1),
                asynchronous(2),
                asynchronousSdlc(4),
                synchronousVipCharacter(6),
                synchronousBscTransparentCharacter(7),
                characterSynchronousBsc3270Or2780-3780(8),
                isdnDChannel(14),
                isdnBChannelWithSignalling(15),
                isdnBChannelWithoutSignalling(16),
                isdnDChannelWithPll(17),
                frameRelayTypeTransit(19),
                hdlc(20),
                frameRelaySubscriber(21),
                lanConnection(23),
                lanIpRouter(27),
                lanBridgeOrIpRouter(28),
                asynchronousX28(30),
                synchronousPpp(39),
                asynchronousPpp(40),
                moduleLink(50),
                unitLink(51)
                }
        ACCESS  read-only
        STATUS  mandatory
        DESCRIPTION
                "The value of this object indicates the type of
                this line."
        ::= { fmStatStateEntry 2 }


    fmsStateOsiState OBJECT-TYPE
        SYNTAX  INTEGER {
                down(1),
                layer1Up(2),
                layer2Up(3),
                layer3Up(4)
                }
        ACCESS  read-only
        STATUS  mandatory
        DESCRIPTION
                "The value of this object indicates the state and
                the ISO layer of this line. If this line is up,
                the value indicated is the ISO layer."
        ::= { fmStatStateEntry 3 }


    fmsStateTestState OBJECT-TYPE
        SYNTAX  INTEGER {
                notUnderTest(1),
                lineDisconnectedByTelemaintenance(2),
                underTest(3)
                }
        ACCESS  read-only
        STATUS  mandatory
        DESCRIPTION
                "The value of this object indicates the test state
                of this line."
        ::= { fmStatStateEntry 4 }


    fmsStateMlpTrunkMainLine OBJECT-TYPE
        SYNTAX  INTEGER {
                no(1),
                yes(2)
                }
        ACCESS  read-only
        STATUS  mandatory
        DESCRIPTION
                "The value of this object indicates if this line is
                the main line of a MLP trunk."
        ::= { fmStatStateEntry 5 }


    fmsStateMlpTrunkNumber OBJECT-TYPE
        SYNTAX  INTEGER (0..255)
        ACCESS  read-only
        STATUS  mandatory
        DESCRIPTION
                "The value of this object is the identifier of the
                MLP trunk."
        ::= { fmStatStateEntry 6 }


    fmsStateMlpTrunkState OBJECT-TYPE
        SYNTAX  INTEGER {
                down(1),
                up(2)
                }
        ACCESS  read-only
        STATUS  mandatory
        DESCRIPTION
                "The value of this object is the MLP trunk state."
        ::= { fmStatStateEntry 7 }


    fmStatMlpTable OBJECT-TYPE
        SYNTAX  SEQUENCE OF FmStatMlpEntry
        ACCESS  not-accessible
        STATUS  mandatory
        DESCRIPTION
                "This table contains the information about the MLP
                trunks."
        ::= { fmStat 30 }


    fmStatMlpEntry OBJECT-TYPE
        SYNTAX  FmStatMlpEntry
        ACCESS  not-accessible
        STATUS  mandatory
        DESCRIPTION
                "An entry of fmStatMlpTable."
        INDEX   { fmsMlpTrunkNumber,
                  fmsMlpLineId }
        ::= { fmStatMlpTable 1 }


        FmStatMlpEntry ::=
                SEQUENCE {
                    fmsMlpTrunkNumber
                        INTEGER,
                    fmsMlpLineId
                        INTEGER,
                    fmsMlpLineType
                        INTEGER
                }


    fmsMlpTrunkNumber OBJECT-TYPE
        SYNTAX  INTEGER (0..255)
        ACCESS  read-only
        STATUS  mandatory
        DESCRIPTION
                "The value of this object is the identifier of the
                MLP trunk."
        ::= { fmStatMlpEntry 1 }


    fmsMlpLineId OBJECT-TYPE
        SYNTAX  INTEGER (0..35)
        ACCESS  read-only
        STATUS  mandatory
        DESCRIPTION
                "The value of this object is the one line
                identifier."
        ::= { fmStatMlpEntry 2 }


    fmsMlpLineType OBJECT-TYPE
        SYNTAX  INTEGER {
                mainDown(1),
                mainUp(2),
                secondaryDown(3),
                secondaryUp(4)
                }
        ACCESS  read-only
        STATUS  mandatory
        DESCRIPTION
                "The value of this object indicates if this line is
                the main line of this MLP trunk."
        ::= { fmStatMlpEntry 3 }


    fmStatEthernet OBJECT IDENTIFIER ::= { fmStat 40 }


    fmStatEthernetTable OBJECT-TYPE
        SYNTAX  SEQUENCE OF FmStatEthernetEntry
        ACCESS  not-accessible
        STATUS  mandatory
        DESCRIPTION
                "This table contains the general information about
                the Ethernet physical ports."
        ::= { fmStatEthernet 1 }


    fmStatEthernetEntry OBJECT-TYPE
        SYNTAX  FmStatEthernetEntry
        ACCESS  not-accessible
        STATUS  mandatory
        DESCRIPTION
                "An entry of fmStatEthernetTable."
        INDEX   { fmsEthLineId }
        ::= { fmStatEthernetTable 1 }


        FmStatEthernetEntry ::=
                SEQUENCE {
                    fmsEthLineId
                        INTEGER,
                    fmsEthPhysAddr
                        OCTET STRING,
                    fmsEthOperStatus
                        INTEGER,
                    fmsEthInterface
                        INTEGER,
                    fmsEthAutoPortSelection
                        INTEGER,
                    fmsEthPolarityCorrection
                        INTEGER,
                    fmsEthPolarityInversion
                        INTEGER,
                    fmsEthLinkIntegrity
                        INTEGER,
                    fmsEthTestLoopback
                        INTEGER,
                    fmsEthJabber
                        INTEGER,
                    fmsEthTestMode
                        INTEGER,
                    fmsEthTdrState
                        INTEGER,
                    fmsEthTdrLoc
                        INTEGER,
                    fmsEthUpTime
                        TimeTicks
                }


    fmsEthLineId OBJECT-TYPE
        SYNTAX  INTEGER (0..35)
        ACCESS  read-only
        STATUS  mandatory
        DESCRIPTION
                "The value of this object is the identifier of one
                physical port."
        ::= { fmStatEthernetEntry 1 }


    fmsEthPhysAddr OBJECT-TYPE
        SYNTAX  OCTET STRING (SIZE(6))
        ACCESS  read-only
        STATUS  mandatory
        DESCRIPTION
                "The value of this object is the MAC address of the
                equipment."
        ::= { fmStatEthernetEntry 2 }


    fmsEthOperStatus OBJECT-TYPE
        SYNTAX  INTEGER {
                down(1),
                up(2)
                }
        ACCESS  read-only
        STATUS  mandatory
        DESCRIPTION
                "The value of this object is the state of the LAN
                function."
        ::= { fmStatEthernetEntry 3 }


    fmsEthInterface OBJECT-TYPE
        SYNTAX  INTEGER {
                ethernet10base5(1),
                ethernet10BaseT(2),
                ethernetAuto(3)
                }
        ACCESS  read-only
        STATUS  mandatory
        DESCRIPTION
                "The value of this object is the ethernet connector
                type."
        ::= { fmStatEthernetEntry 4 }


    fmsEthAutoPortSelection OBJECT-TYPE
        SYNTAX  INTEGER {
                off(1),
                on(2)
                }
        ACCESS  read-only
        STATUS  mandatory
        DESCRIPTION
                "The value of this object indicates whether the
                selection of the LAN port is automatic or not."
        ::= { fmStatEthernetEntry 20 }


    fmsEthPolarityCorrection OBJECT-TYPE
        SYNTAX  INTEGER {
                off(1),
                on(2)
                }
        ACCESS  read-only
        STATUS  mandatory
        DESCRIPTION
                "The value of this object indicates the state of
                the polarity spontaneous correction."
        ::= { fmStatEthernetEntry 21 }


    fmsEthPolarityInversion OBJECT-TYPE
        SYNTAX  INTEGER {
                no(1),
                yes(2)
                }
        ACCESS  read-only
        STATUS  mandatory
        DESCRIPTION
                "The value of this object indicates if there is
                inversion of the polarity."
        ::= { fmStatEthernetEntry 22 }


    fmsEthLinkIntegrity OBJECT-TYPE
        SYNTAX  INTEGER {
                off(1),
                down(2),
                up(3)
                }
        ACCESS  read-only
        STATUS  mandatory
        DESCRIPTION
                "The value of this object indicates the state of
                the link integrity function."
        ::= { fmStatEthernetEntry 23 }


    fmsEthTestLoopback OBJECT-TYPE
        SYNTAX  INTEGER {
                off(1),
                on(2)
                }
        ACCESS  read-only
        STATUS  mandatory
        DESCRIPTION
                "The value of this object indicates if the loopback
                test is used."
        ::= { fmStatEthernetEntry 24 }


    fmsEthJabber OBJECT-TYPE
        SYNTAX  INTEGER {
                off(1),
                on(2)
                }
        ACCESS  read-only
        STATUS  mandatory
        DESCRIPTION
                "The value of this object is the state of the bus
                taking time control function (Jabber)."
        ::= { fmStatEthernetEntry 25 }


    fmsEthTestMode OBJECT-TYPE
        SYNTAX  INTEGER {
                off(1),
                continousSending(2),
                standby(3)
                }
        ACCESS  read-only
        STATUS  mandatory
        DESCRIPTION
                "The value of this object is the mode of the test.
                The value 'continousSending' indicates that frames
                are sent continously during the test. The value
                'standby' indicates that no frames are sent during
                the test."
        ::= { fmStatEthernetEntry 26 }


    fmsEthTdrState OBJECT-TYPE
        SYNTAX  INTEGER {
                ok(1),
                transceiverProblem(2),
                openCircuit(3),
                shortCircuit(4)
                }
        ACCESS  read-only
        STATUS  mandatory
        DESCRIPTION
                "The value of this object (Time Domain
                Reflectometry) indicates the problem type of the
                connectors system."
        ::= { fmStatEthernetEntry 27 }


    fmsEthTdrLoc OBJECT-TYPE
        SYNTAX  INTEGER (0..2047)
        ACCESS  read-only
        STATUS  mandatory
        DESCRIPTION
                "The value of this object (Time Domain
                Reflectometry) indicates the tracing of connectors
                system problem. The value '2047' is not
                significant."
        ::= { fmStatEthernetEntry 28 }


    fmsEthUpTime OBJECT-TYPE
        SYNTAX  TimeTicks
        ACCESS  read-only
        STATUS  mandatory
        DESCRIPTION
                "The value of this object is the time elapsing
                since the last start-up of the LAN interface. When
                the equipment starts, the value of this object is
                0."
        ::= { fmStatEthernetEntry 29 }


    fmStatEthInputTrafficTable OBJECT-TYPE
        SYNTAX  SEQUENCE OF FmStatEthInputTrafficEntry
        ACCESS  not-accessible
        STATUS  mandatory
        DESCRIPTION
                "This table contains the information about the
                statistics, in reception, of a LAN line. The
                values of all this counters are not reseted by the
                command 'reset' of fmsCtrlCountersCommand."
        ::= { fmStatEthernet 2 }


    fmStatEthInputTrafficEntry OBJECT-TYPE
        SYNTAX  FmStatEthInputTrafficEntry
        ACCESS  not-accessible
        STATUS  mandatory
        DESCRIPTION
                "An entry of fmStatEthInputTrafficTable."
        INDEX   { fmsEthInLineId }
        ::= { fmStatEthInputTrafficTable 1 }


        FmStatEthInputTrafficEntry ::=
                SEQUENCE {
                    fmsEthInLineId
                        INTEGER,
                    fmsEthInOctetsCounter
                        Counter,
                    fmsEthInPktsCounter
                        Counter,
                    fmsEthInNoErrCounter
                        Counter,
                    fmsEthInUcastPktsCounter
                        Counter,
                    fmsEthInAlignmentErrorsCounter
                        Counter,
                    fmsEthInFCSErrorsCounter
                        Counter,
                    fmsEthInPktsTooLongsCounter
                        Counter,
                    fmsEthInPktsTooShortsCounter
                        Counter,
                    fmsEthInErrOutOfResourcesCounter
                        Counter,
                    fmsEthInErrDmaOverrunCounter
                        Counter,
                    fmsEthInErrCollCounter
                        Counter,
                    fmsEthInErrOverFlowCounter
                        Counter
                }


    fmsEthInLineId OBJECT-TYPE
        SYNTAX  INTEGER (0..35)
        ACCESS  read-only
        STATUS  mandatory
        DESCRIPTION
                "The value of this object is the one line
                identifier."
        ::= { fmStatEthInputTrafficEntry 1 }


    fmsEthInOctetsCounter OBJECT-TYPE
        SYNTAX  Counter
        ACCESS  read-only
        STATUS  mandatory
        DESCRIPTION
                "The value of this object is the number of the
                bytes received over this line."
        ::= { fmStatEthInputTrafficEntry 2 }


    fmsEthInPktsCounter OBJECT-TYPE
        SYNTAX  Counter
        ACCESS  read-only
        STATUS  mandatory
        DESCRIPTION
                "The value of this object is the number of the
                frames received over this line."
        ::= { fmStatEthInputTrafficEntry 3 }


    fmsEthInNoErrCounter OBJECT-TYPE
        SYNTAX  Counter
        ACCESS  read-only
        STATUS  mandatory
        DESCRIPTION
                "The value of this object is the number of the
                frames received with no error over this line."
        ::= { fmStatEthInputTrafficEntry 4 }


    fmsEthInUcastPktsCounter OBJECT-TYPE
        SYNTAX  Counter
        ACCESS  read-only
        STATUS  mandatory
        DESCRIPTION
                "The value of this object is the number of the
                frames received over this line and correctly sent
                to the upper layer."
        ::= { fmStatEthInputTrafficEntry 5 }


    fmsEthInAlignmentErrorsCounter OBJECT-TYPE
        SYNTAX  Counter
        ACCESS  read-only
        STATUS  mandatory
        DESCRIPTION
                "The value of this object is the number of the
                frames received with an error of alignment (number
                of bits not multiple of 8) over this line."
        ::= { fmStatEthInputTrafficEntry 20 }


    fmsEthInFCSErrorsCounter OBJECT-TYPE
        SYNTAX  Counter
        ACCESS  read-only
        STATUS  mandatory
        DESCRIPTION
                "The value of this object is the number of the
                frames received with an error of CRC over this
                line."
        ::= { fmStatEthInputTrafficEntry 21 }


    fmsEthInPktsTooLongsCounter OBJECT-TYPE
        SYNTAX  Counter
        ACCESS  read-only
        STATUS  mandatory
        DESCRIPTION
                "The value of this object is the number of the
                frames received with a length too long over this
                line."
        ::= { fmStatEthInputTrafficEntry 22 }


    fmsEthInPktsTooShortsCounter OBJECT-TYPE
        SYNTAX  Counter
        ACCESS  read-only
        STATUS  mandatory
        DESCRIPTION
                "The value of this object is the number of the
                frames received with a length too short over this
                line."
        ::= { fmStatEthInputTrafficEntry 23 }


    fmsEthInErrOutOfResourcesCounter OBJECT-TYPE
        SYNTAX  Counter
        ACCESS  read-only
        STATUS  mandatory
        DESCRIPTION
                "The value of this object is the number of the
                frames received with an error of resources too
                short over this line."
        ::= { fmStatEthInputTrafficEntry 24 }


    fmsEthInErrDmaOverrunCounter OBJECT-TYPE
        SYNTAX  Counter
        ACCESS  read-only
        STATUS  mandatory
        DESCRIPTION
                "The value of this object is the number of the
                frames received with the error 'DMA overrun' (no
                reply when expected by the memory bus to a DMA
                cycle) over this line."
        ::= { fmStatEthInputTrafficEntry 25 }


    fmsEthInErrCollCounter OBJECT-TYPE
        SYNTAX  Counter
        ACCESS  read-only
        STATUS  mandatory
        DESCRIPTION
                "The value of this object is the number of the
                frames received with the error 'receive collision'
                (frames received but invalided because of a
                collision detection during the reception) over
                this line."
        ::= { fmStatEthInputTrafficEntry 26 }


    fmsEthInErrOverFlowCounter OBJECT-TYPE
        SYNTAX  Counter
        ACCESS  read-only
        STATUS  mandatory
        DESCRIPTION
                "The value of this object is the number of the
                frames received over this line and not sent to the
                upper layer because of the resources overflow."
        ::= { fmStatEthInputTrafficEntry 27 }


    fmStatEthOutputTrafficTable OBJECT-TYPE
        SYNTAX  SEQUENCE OF FmStatEthOutputTrafficEntry
        ACCESS  not-accessible
        STATUS  mandatory
        DESCRIPTION
                "This table contains the information about the
                statistics, in sending, of one LAN line. The
                values of all this counters are not reseted by the
                command 'reset' of fmsCtrlCountersCommand."
        ::= { fmStatEthernet 3 }


    fmStatEthOutputTrafficEntry OBJECT-TYPE
        SYNTAX  FmStatEthOutputTrafficEntry
        ACCESS  not-accessible
        STATUS  mandatory
        DESCRIPTION
                "An entry of fmStatEthOutputTrafficTable."
        INDEX   { fmsEthOutLineId }
        ::= { fmStatEthOutputTrafficTable 1 }


        FmStatEthOutputTrafficEntry ::=
                SEQUENCE {
                    fmsEthOutLineId
                        INTEGER,
                    fmsEthOutOctetsCounter
                        Counter,
                    fmsEthOutPktsCounter
                        Counter,
                    fmsEthOutNoErrCounter
                        Counter,
                    fmsEthOutSingleCollisionFramesCounter
                        Counter,
                    fmsEthOutMultipleCollisionFramesCounter
                        Counter,
                    fmsEthOutDeferredTransmissionsCounter
                        Counter,
                    fmsEthOutSQETestErrorsCounter
                        Counter,
                    fmsEthOutLateCollisionsCounter
                        Counter,
                    fmsEthOutExcessiveCollisionsCounter
                        Counter,
                    fmsEthOutCarrierSenseErrorsCounter
                        Counter,
                    fmsEthOutErrExcdDelayCounter
                        Counter,
                    fmsEthOutErrCtsLossCounter
                        Counter,
                    fmsEthOutErrDmaUnderrunCounter
                        Counter
                }


    fmsEthOutLineId OBJECT-TYPE
        SYNTAX  INTEGER (0..35)
        ACCESS  read-only
        STATUS  mandatory
        DESCRIPTION
                "The value of this object is the one line
                identifier."
        ::= { fmStatEthOutputTrafficEntry 1 }


    fmsEthOutOctetsCounter OBJECT-TYPE
        SYNTAX  Counter
        ACCESS  read-only
        STATUS  mandatory
        DESCRIPTION
                "The value of this object is the number of the
                bytes sent over this line."
        ::= { fmStatEthOutputTrafficEntry 2 }


    fmsEthOutPktsCounter OBJECT-TYPE
        SYNTAX  Counter
        ACCESS  read-only
        STATUS  mandatory
        DESCRIPTION
                "The value of this object is the number of the
                frames sent over this line."
        ::= { fmStatEthOutputTrafficEntry 3 }


    fmsEthOutNoErrCounter OBJECT-TYPE
        SYNTAX  Counter
        ACCESS  read-only
        STATUS  mandatory
        DESCRIPTION
                "The value of this object is the number of the
                frames sent without error over this line."
        ::= { fmStatEthOutputTrafficEntry 4 }


    fmsEthOutSingleCollisionFramesCounter OBJECT-TYPE
        SYNTAX  Counter
        ACCESS  read-only
        STATUS  mandatory
        DESCRIPTION
                "The value of this object is the number of the
                frames sent after one collision over this line."
        ::= { fmStatEthOutputTrafficEntry 5 }


    fmsEthOutMultipleCollisionFramesCounter OBJECT-TYPE
        SYNTAX  Counter
        ACCESS  read-only
        STATUS  mandatory
        DESCRIPTION
                "The value of this object is the number of the
                frames sent after two collisions or more over this
                line."
        ::= { fmStatEthOutputTrafficEntry 6 }


    fmsEthOutDeferredTransmissionsCounter OBJECT-TYPE
        SYNTAX  Counter
        ACCESS  read-only
        STATUS  mandatory
        DESCRIPTION
                "The value of this object is the number of the
                frames sent late over this line because the
                ethernet bus is busy."
        ::= { fmStatEthOutputTrafficEntry 7 }


    fmsEthOutSQETestErrorsCounter OBJECT-TYPE
        SYNTAX  Counter
        ACCESS  read-only
        STATUS  mandatory
        DESCRIPTION
                "The value of this object is the number of the
                frames sent with error of no heartbeat over this
                line. The heartbeat function of the ethernet
                transmitter is used to indicate to the LAN driver
                the status of its collision detector. If following
                a transmission, the transmitter does not send the
                SQE signal of the heartbeat function to the
                equipment, then the frame is considered to be sent
                with 'no heartbeat' error."
        ::= { fmStatEthOutputTrafficEntry 20 }


    fmsEthOutLateCollisionsCounter OBJECT-TYPE
        SYNTAX  Counter
        ACCESS  read-only
        STATUS  mandatory
        DESCRIPTION
                "The value of this object is the number of the
                frames not sent because of the error 'late
                collision' (collision detection after the end of
                the slot time) over this line."
        ::= { fmStatEthOutputTrafficEntry 21 }


    fmsEthOutExcessiveCollisionsCounter OBJECT-TYPE
        SYNTAX  Counter
        ACCESS  read-only
        STATUS  mandatory
        DESCRIPTION
                "The value of this object is the number of the
                frames not sent because of the collisions
                detections at all the attempts over this line."
        ::= { fmStatEthOutputTrafficEntry 22 }


    fmsEthOutCarrierSenseErrorsCounter OBJECT-TYPE
        SYNTAX  Counter
        ACCESS  read-only
        STATUS  mandatory
        DESCRIPTION
                "The value of this object is the number of the
                frames not sent because of the error 'no carrier
                sense' over this line."
        ::= { fmStatEthOutputTrafficEntry 23 }


    fmsEthOutErrExcdDelayCounter OBJECT-TYPE
        SYNTAX  Counter
        ACCESS  read-only
        STATUS  mandatory
        DESCRIPTION
                "The value of this object is the number of the
                frames not sent over this line because the bus is
                busy during a long time."
        ::= { fmStatEthOutputTrafficEntry 24 }


    fmsEthOutErrCtsLossCounter OBJECT-TYPE
        SYNTAX  Counter
        ACCESS  read-only
        STATUS  mandatory
        DESCRIPTION
                "The value of this object is the number of the
                frames not sent over this line because of the loss
                of the CTS (Clear To Send) signal."
        ::= { fmStatEthOutputTrafficEntry 25 }


    fmsEthOutErrDmaUnderrunCounter OBJECT-TYPE
        SYNTAX  Counter
        ACCESS  read-only
        STATUS  mandatory
        DESCRIPTION
                "The value of this object is the number of the
                frames not sent over this line because of the
                error 'DMA underrun' (no reply when expected by
                the memory bus to a DMA cycle)."
        ::= { fmStatEthOutputTrafficEntry 26 }


    fmStatEthManagementTable OBJECT-TYPE
        SYNTAX  SEQUENCE OF FmStatEthManagementEntry
        ACCESS  not-accessible
        STATUS  mandatory
        DESCRIPTION
                "This table contains the information about the
                monitoring, the reset and the filtering for each
                port. The values of all this counters are not
                reseted by the command 'reset' of
                fmsCtrlCountersCommand."
        ::= { fmStatEthernet 4 }


    fmStatEthManagementEntry OBJECT-TYPE
        SYNTAX  FmStatEthManagementEntry
        ACCESS  not-accessible
        STATUS  mandatory
        DESCRIPTION
                "An entry of fmStatEthManagementTable."
        INDEX   { fmsEthManLineId }
        ::= { fmStatEthManagementTable 1 }


        FmStatEthManagementEntry ::=
                SEQUENCE {
                    fmsEthManLineId
                        INTEGER,
                    fmsEthManSupervisionOkCounter
                        Counter,
                    fmsEthManSupervisionNokCounter
                        Counter,
                    fmsEthManInputResetCounter
                        Counter,
                    fmsEthManFilterPermitCounter
                        Counter,
                    fmsEthManFilterDenyCounter
                        Counter
                }


    fmsEthManLineId OBJECT-TYPE
        SYNTAX  INTEGER (0..35)
        ACCESS  read-only
        STATUS  mandatory
        DESCRIPTION
                "The value of this object is the one line
                identifier."
        ::= { fmStatEthManagementEntry 1 }


    fmsEthManSupervisionOkCounter OBJECT-TYPE
        SYNTAX  Counter
        ACCESS  read-only
        STATUS  mandatory
        DESCRIPTION
                "The value of this object is the number of the OK
                supervision frames over this line."
        ::= { fmStatEthManagementEntry 2 }


    fmsEthManSupervisionNokCounter OBJECT-TYPE
        SYNTAX  Counter
        ACCESS  read-only
        STATUS  mandatory
        DESCRIPTION
                "The value of this object is the number of the not
                OK supervision frames over this line."
        ::= { fmStatEthManagementEntry 3 }


    fmsEthManInputResetCounter OBJECT-TYPE
        SYNTAX  Counter
        ACCESS  read-only
        STATUS  mandatory
        DESCRIPTION
                "The value of this object is the number of the
                reception resets over this line."
        ::= { fmStatEthManagementEntry 4 }


    fmsEthManFilterPermitCounter OBJECT-TYPE
        SYNTAX  Counter
        ACCESS  read-only
        STATUS  mandatory
        DESCRIPTION
                "The value of this object is the number of the
                frames accepted by the bridge filtering over this
                line."
        ::= { fmStatEthManagementEntry 5 }


    fmsEthManFilterDenyCounter OBJECT-TYPE
        SYNTAX  Counter
        ACCESS  read-only
        STATUS  mandatory
        DESCRIPTION
                "The value of this object is the number of the
                frames refused by the bridge filtering over this
                line."
        ::= { fmStatEthManagementEntry 6 }


    fmStatWanConnectionsTable OBJECT-TYPE
        SYNTAX  SEQUENCE OF FmStatWanConnectionsEntry
        ACCESS  not-accessible
        STATUS  mandatory
        DESCRIPTION
                "This table contains the information about the WAN
                connections."
        ::= { fmStat 45 }


    fmStatWanConnectionsEntry OBJECT-TYPE
        SYNTAX  FmStatWanConnectionsEntry
        ACCESS  not-accessible
        STATUS  mandatory
        DESCRIPTION
                "An entry of fmStatWanConnectionsTable."
        INDEX   { fmsWanConnId }
        ::= { fmStatWanConnectionsTable 1 }


        FmStatWanConnectionsEntry ::=
                SEQUENCE {
                    fmsWanConnId
                        INTEGER,
                    fmsWanConnRemoteAddr
                        OCTET STRING,
                    fmsWanConnEncapsulation
                        INTEGER,
                    fmsWanConnStatus
                        INTEGER,
                    fmsWanConnGrouping
                        INTEGER,
                    fmsWanConnLocalSbNumber
                        INTEGER,
                    fmsWanConnInPktsCounter
                        Counter,
                    fmsWanConnInErrPktsCounter
                        Counter,
                    fmsWanConnInOctetsCounter
                        Counter,
                    fmsWanConnOutPktsCounter
                        Counter,
                    fmsWanConnOutOctetsCounter
                        Counter
                }


    fmsWanConnId OBJECT-TYPE
        SYNTAX  INTEGER (0..255)
        ACCESS  read-only
        STATUS  mandatory
        DESCRIPTION
                "The value of this object is the one SLL (Switched
                Logical Link) identifier."
        ::= { fmStatWanConnectionsEntry 1 }


    fmsWanConnRemoteAddr OBJECT-TYPE
        SYNTAX  OCTET STRING (SIZE(8))
        ACCESS  read-only
        STATUS  mandatory
        DESCRIPTION
                "The value of this object is the X121 address of
                the remote equipment."
        ::= { fmStatWanConnectionsEntry 2 }


    fmsWanConnEncapsulation OBJECT-TYPE
        SYNTAX  INTEGER {
                rilBridge(9),
                ip(20)
                }
        ACCESS  read-only
        STATUS  mandatory
        DESCRIPTION
                "The value of this object indicates the
                encapsulation type over this SLL (Switched Logical
                Link)."
        ::= { fmStatWanConnectionsEntry 3 }


    fmsWanConnStatus OBJECT-TYPE
        SYNTAX  INTEGER {
                down(1),
                up(2)
                }
        ACCESS  read-only
        STATUS  mandatory
        DESCRIPTION
                "The value of this object is the state of this SLL
                (Switched Logical Link)."
        ::= { fmStatWanConnectionsEntry 5 }


    fmsWanConnGrouping OBJECT-TYPE
        SYNTAX  INTEGER {
                off(1),
                multiFrames(3),
                grouping(2)
                }
        ACCESS  read-only
        STATUS  mandatory
        DESCRIPTION
                "The value of this object indicates if the grouping
                function is used over this SLL (Switched Logical
                Link)."
        ::= { fmStatWanConnectionsEntry 6 }


    fmsWanConnLocalSbNumber OBJECT-TYPE
        SYNTAX  INTEGER (0..99)
        ACCESS  read-only
        STATUS  mandatory
        DESCRIPTION
                "The value of this object is the subscriber local
                number AB (in the DNIC ZO AB plan) of the LAN
                coupling function."
        ::= { fmStatWanConnectionsEntry 7 }


    fmsWanConnInPktsCounter OBJECT-TYPE
        SYNTAX  Counter
        ACCESS  read-only
        STATUS  mandatory
        DESCRIPTION
                "The value of this object is the number of frames
                received over this SLL (Switched Logical Link)."
        ::= { fmStatWanConnectionsEntry 20 }


    fmsWanConnInErrPktsCounter OBJECT-TYPE
        SYNTAX  Counter
        ACCESS  read-only
        STATUS  mandatory
        DESCRIPTION
                "The value of this object is the number of frames
                lost because they are erroneous over this SLL
                (Switched Logical Link)."
        ::= { fmStatWanConnectionsEntry 21 }


    fmsWanConnInOctetsCounter OBJECT-TYPE
        SYNTAX  Counter
        ACCESS  read-only
        STATUS  mandatory
        DESCRIPTION
                "The value of this object is the number of bytes
                received over this SLL (Switched Logical Link)."
        ::= { fmStatWanConnectionsEntry 22 }


    fmsWanConnOutPktsCounter OBJECT-TYPE
        SYNTAX  Counter
        ACCESS  read-only
        STATUS  mandatory
        DESCRIPTION
                "The value of this object is the number of frames
                sent over this SLL (Switched Logical Link)."
        ::= { fmStatWanConnectionsEntry 30 }


    fmsWanConnOutOctetsCounter OBJECT-TYPE
        SYNTAX  Counter
        ACCESS  read-only
        STATUS  mandatory
        DESCRIPTION
                "The value of this object is the number of bytes
                sent over this SLL (Switched Logical Link)."
        ::= { fmStatWanConnectionsEntry 31 }


    fmStatRemoteVirtualPorts OBJECT IDENTIFIER ::= { fmStat 46 }


    fmStatRvpConnectionsTable OBJECT-TYPE
        SYNTAX  SEQUENCE OF FmStatRvpConnectionsEntry
        ACCESS  not-accessible
        STATUS  mandatory
        DESCRIPTION
                "This table contains the information about the
                remote virtual ports."
        ::= { fmStatRemoteVirtualPorts 1 }


    fmStatRvpConnectionsEntry OBJECT-TYPE
        SYNTAX  FmStatRvpConnectionsEntry
        ACCESS  not-accessible
        STATUS  mandatory
        DESCRIPTION
                "An entry of fmStatRvpConnectionsTable."
        INDEX   { fmsRvpConnRemoteAddr,
                  fmsRvpConnEncapsulation,
                  fmsRvpConnId }
        ::= { fmStatRvpConnectionsTable 1 }


        FmStatRvpConnectionsEntry ::=
                SEQUENCE {
                    fmsRvpConnRemoteAddr
                        OCTET STRING,
                    fmsRvpConnEncapsulation
                        INTEGER,
                    fmsRvpConnId
                        INTEGER,
                    fmsRvpConnStatus
                        INTEGER,
                    fmsRvpConnGrouping
                        INTEGER,
                    fmsRvpConnLocalSbNumber
                        INTEGER,
                    fmsRvpConnInPktsCounter
                        Counter,
                    fmsRvpConnInErrPktsCounter
                        Counter,
                    fmsRvpConnInOctetsCounter
                        Counter,
                    fmsRvpConnOutPktsCounter
                        Counter,
                    fmsRvpConnOutOctetsCounter
                        Counter
                }


    fmsRvpConnRemoteAddr OBJECT-TYPE
        SYNTAX  OCTET STRING (SIZE(8))
        ACCESS  read-only
        STATUS  mandatory
        DESCRIPTION
                "The value of this object is the X121 address of
                the remote equipment."
        ::= { fmStatRvpConnectionsEntry 2 }


    fmsRvpConnEncapsulation OBJECT-TYPE
        SYNTAX  INTEGER {
                multiplexing(1),
                bridge(10),
                bridgeSpecific(11),
                ip(20),
                ipx(30),
                ipxSpecific(31),
                clnp(40)
                }
        ACCESS  read-only
        STATUS  mandatory
        DESCRIPTION
                "The value of this object indicates the
                encapsulation type."
        ::= { fmStatRvpConnectionsEntry 3 }


    fmsRvpConnId OBJECT-TYPE
        SYNTAX  INTEGER (0..255)
        ACCESS  read-only
        STATUS  mandatory
        DESCRIPTION
                "The value of this object is the one connection
                identifier."
        ::= { fmStatRvpConnectionsEntry 4 }


    fmsRvpConnStatus OBJECT-TYPE
        SYNTAX  INTEGER {
                down(1),
                up(2)
                }
        ACCESS  read-only
        STATUS  mandatory
        DESCRIPTION
                "The value of this object is the state of this
                connection."
        ::= { fmStatRvpConnectionsEntry 5 }


    fmsRvpConnGrouping OBJECT-TYPE
        SYNTAX  INTEGER {
                off(1),
                on(2)
                }
        ACCESS  read-only
        STATUS  mandatory
        DESCRIPTION
                "The value of this object indicates if the grouping
                function is used."
        ::= { fmStatRvpConnectionsEntry 6 }


    fmsRvpConnLocalSbNumber OBJECT-TYPE
        SYNTAX  INTEGER (0..99)
        ACCESS  read-only
        STATUS  mandatory
        DESCRIPTION
                "The value of this object is the subscriber local
                number AB (in the DNIC ZO AB plan) of this
                connection."
        ::= { fmStatRvpConnectionsEntry 7 }


    fmsRvpConnInPktsCounter OBJECT-TYPE
        SYNTAX  Counter
        ACCESS  read-only
        STATUS  mandatory
        DESCRIPTION
                "The value of this object is the number of frames
                received over this connection."
        ::= { fmStatRvpConnectionsEntry 20 }


    fmsRvpConnInErrPktsCounter OBJECT-TYPE
        SYNTAX  Counter
        ACCESS  read-only
        STATUS  mandatory
        DESCRIPTION
                "The value of this object is the number of frames
                lost because they are erroneous over this
                connection."
        ::= { fmStatRvpConnectionsEntry 21 }


    fmsRvpConnInOctetsCounter OBJECT-TYPE
        SYNTAX  Counter
        ACCESS  read-only
        STATUS  mandatory
        DESCRIPTION
                "The value of this object is the number of bytes
                received over this connection."
        ::= { fmStatRvpConnectionsEntry 22 }


    fmsRvpConnOutPktsCounter OBJECT-TYPE
        SYNTAX  Counter
        ACCESS  read-only
        STATUS  mandatory
        DESCRIPTION
                "The value of this object is the number of frames
                sent over this connection."
        ::= { fmStatRvpConnectionsEntry 30 }


    fmsRvpConnOutOctetsCounter OBJECT-TYPE
        SYNTAX  Counter
        ACCESS  read-only
        STATUS  mandatory
        DESCRIPTION
                "The value of this object is the number of bytes
                sent over this connection."
        ::= { fmStatRvpConnectionsEntry 31 }


    fmStatBridge OBJECT IDENTIFIER ::= { fmStat 50 }


    fmsBridgeState OBJECT-TYPE
        SYNTAX  INTEGER {
                off(1),
                transparentBridge(2)
                }
        ACCESS  read-only
        STATUS  mandatory
        DESCRIPTION
                "The value of this object is the state of the
                bridging function."
        ::= { fmStatBridge 1 }


    fmStatBrdgTraffic OBJECT IDENTIFIER ::= { fmStatBridge 18 }


    fmsBrdgTrafInPktsCounter OBJECT-TYPE
        SYNTAX  Counter
        ACCESS  read-only
        STATUS  mandatory
        DESCRIPTION
                "The value of this object is the number of the
                frames received by the bridge."
        ::= { fmStatBrdgTraffic 1 }


    fmsBrdgTrafOutPktsCounter OBJECT-TYPE
        SYNTAX  Counter
        ACCESS  read-only
        STATUS  mandatory
        DESCRIPTION
                "The value of this object is the number of the
                frames sent by the bridge."
        ::= { fmStatBrdgTraffic 20 }


    fmsBrdgTrafOutBroadcastPktsCounter OBJECT-TYPE
        SYNTAX  Counter
        ACCESS  read-only
        STATUS  mandatory
        DESCRIPTION
                "The value of this object is the number of the data
                frames diffusions."
        ::= { fmStatBrdgTraffic 21 }


    fmsBrdgTrafInServCounter OBJECT-TYPE
        SYNTAX  Counter
        ACCESS  read-only
        STATUS  mandatory
        DESCRIPTION
                "The value of this object is the number of the RIL
                service frames received by the bridge."
        ::= { fmStatBrdgTraffic 50 }


    fmsBrdgTrafOutServCounter OBJECT-TYPE
        SYNTAX  Counter
        ACCESS  read-only
        STATUS  mandatory
        DESCRIPTION
                "The value of this object is the number of the RIL
                service frames sent by the bridge."
        ::= { fmStatBrdgTraffic 51 }


    fmsBrdgTrafOutBroadcastServCounter OBJECT-TYPE
        SYNTAX  Counter
        ACCESS  read-only
        STATUS  mandatory
        DESCRIPTION
                "The value of this object is the number of the
                service frames diffusions."
        ::= { fmStatBrdgTraffic 52 }


    fmStatIpRouter OBJECT IDENTIFIER ::= { fmStat 51 }


    fmsIpRouterState OBJECT-TYPE
        SYNTAX  INTEGER {
                off(1),
                on(2)
                }
        ACCESS  read-only
        STATUS  mandatory
        DESCRIPTION
                "The value of this object is the state of the IP
                routing function."
        ::= { fmStatIpRouter 1 }


    fmStatIpTraffic OBJECT IDENTIFIER ::= { fmStatIpRouter 18 }


    fmsIpTrafInReceivesCounter OBJECT-TYPE
        SYNTAX  Counter
        ACCESS  read-only
        STATUS  mandatory
        DESCRIPTION
                "The value of this object is the number of the IP
                datagrams received."
        ::= { fmStatIpTraffic 1 }


    fmsIpTrafOutRequestsCounter OBJECT-TYPE
        SYNTAX  Counter
        ACCESS  read-only
        STATUS  mandatory
        DESCRIPTION
                "The value of this object is the number of the IP
                datagrams sent."
        ::= { fmStatIpTraffic 2 }


    fmsIpTrafInOctetsCounter OBJECT-TYPE
        SYNTAX  Counter
        ACCESS  read-only
        STATUS  mandatory
        DESCRIPTION
                "The value of this object is the number of the
                bytes received with the IP protocol."
        ::= { fmStatIpTraffic 3 }


    fmsIpTrafOutOctetsCounter OBJECT-TYPE
        SYNTAX  Counter
        ACCESS  read-only
        STATUS  mandatory
        DESCRIPTION
                "The value of this object is the number of the
                bytes sent with the IP protocol."
        ::= { fmStatIpTraffic 4 }


    fmsIpTrafInUnknownProtosCounter OBJECT-TYPE
        SYNTAX  Counter
        ACCESS  read-only
        STATUS  mandatory
        DESCRIPTION
                "The value of this object is the number of the IP
                datagrams received and lost because of an unknown
                protocol."
        ::= { fmStatIpTraffic 5 }


    fmsIpTrafNoRoutesCounter OBJECT-TYPE
        SYNTAX  Counter
        ACCESS  read-only
        STATUS  mandatory
        DESCRIPTION
                "The value of this object is the number of the IP
                datagrams received and lost because of an
                impossible routing."
        ::= { fmStatIpTraffic 6 }


    fmsIpTrafInHdrErrorsCounter OBJECT-TYPE
        SYNTAX  Counter
        ACCESS  read-only
        STATUS  mandatory
        DESCRIPTION
                "The value of this object is the number of the IP
                datagrams received and lost because they are
                erroneous."
        ::= { fmStatIpTraffic 7 }


    fmsIpTrafOutForwDatagramsCounter OBJECT-TYPE
        SYNTAX  Counter
        ACCESS  read-only
        STATUS  mandatory
        DESCRIPTION
                "The value of this object is the number of the IP
                datagrams received and correctly routed."
        ::= { fmStatIpTraffic 8 }


    fmsIpTrafOutForwDefRouteCounter OBJECT-TYPE
        SYNTAX  Counter
        ACCESS  read-only
        STATUS  mandatory
        DESCRIPTION
                "The value of this object is the number of the IP
                datagrams received and routed on the default route."
        ::= { fmStatIpTraffic 9 }


    fmsIpTrafIcmpOutMsgsCounter OBJECT-TYPE
        SYNTAX  Counter
        ACCESS  read-only
        STATUS  mandatory
        DESCRIPTION
                "The value of this object is the number of the ICMP
                datagrams sent."
        ::= { fmStatIpTraffic 10 }


    fmsIpTrafIcmpInMsgsCounter OBJECT-TYPE
        SYNTAX  Counter
        ACCESS  read-only
        STATUS  mandatory
        DESCRIPTION
                "The value of this object is the number of the ICMP
                datagrams received."
        ::= { fmStatIpTraffic 11 }


    fmStatIpLanTraffic OBJECT IDENTIFIER ::= { fmStatIpRouter 19 }


    fmsIpLanIpAddr OBJECT-TYPE
        SYNTAX  IpAddress
        ACCESS  read-only
        STATUS  mandatory
        DESCRIPTION
                "fmStatIpLanTraffic 0
                The value of this object is the IP address of the
                LAN interface."
        ::= { fmStatIpLanTraffic 1 }


    fmsIpLanNetMask OBJECT-TYPE
        SYNTAX  IpAddress
        ACCESS  read-only
        STATUS  mandatory
        DESCRIPTION
                "The value of this object is the sub-network mask
                of the LAN interface."
        ::= { fmStatIpLanTraffic 2 }


    fmsIpLanOutRequestsCounter OBJECT-TYPE
        SYNTAX  Counter
        ACCESS  read-only
        STATUS  mandatory
        DESCRIPTION
                "The value of this object is the number of the IP
                datagrams sent on the LAN interface."
        ::= { fmStatIpLanTraffic 3 }


    fmsIpLanInReceivesCounter OBJECT-TYPE
        SYNTAX  Counter
        ACCESS  read-only
        STATUS  mandatory
        DESCRIPTION
                "The value of this object is the number of the IP
                datagrams received on the LAN interface."
        ::= { fmStatIpLanTraffic 4 }


    fmsIpLanOutOctetsIpCounter OBJECT-TYPE
        SYNTAX  Counter
        ACCESS  read-only
        STATUS  mandatory
        DESCRIPTION
                "The value of this object is the number of the
                bytes sent with the IP protocol on the LAN
                interface."
        ::= { fmStatIpLanTraffic 5 }


    fmsIpLanInOctetsIpCounter OBJECT-TYPE
        SYNTAX  Counter
        ACCESS  read-only
        STATUS  mandatory
        DESCRIPTION
                "The value of this object is the number of the
                bytes received with the IP protocol on the LAN
                interface."
        ::= { fmStatIpLanTraffic 6 }


    fmsIpLanNoRoutesCounter OBJECT-TYPE
        SYNTAX  Counter
        ACCESS  read-only
        STATUS  mandatory
        DESCRIPTION
                "The value of this object is the number of the IP
                datagrams received and lost because of impossible
                routing, on the LAN interface."
        ::= { fmStatIpLanTraffic 7 }


    fmsIpLanInHdrErrorsCounter OBJECT-TYPE
        SYNTAX  Counter
        ACCESS  read-only
        STATUS  mandatory
        DESCRIPTION
                "The value of this object is the number of the IP
                datagrams received and lost because of they are
                erroneous, on the LAN interface."
        ::= { fmStatIpLanTraffic 8 }


    fmsIpLanArpFailedCounter OBJECT-TYPE
        SYNTAX  Counter
        ACCESS  read-only
        STATUS  mandatory
        DESCRIPTION
                "The value of this object is the number of the not
                solved ARP request, on the LAN interface."
        ::= { fmStatIpLanTraffic 9 }


    fmStatIpClusterStateTable OBJECT-TYPE
        SYNTAX  SEQUENCE OF FmStatIpClusterStateEntry
        ACCESS  not-accessible
        STATUS  mandatory
        DESCRIPTION
                ""
        ::= { fmStatIpRouter 25 }


    fmStatIpClusterStateEntry OBJECT-TYPE
        SYNTAX  FmStatIpClusterStateEntry
        ACCESS  not-accessible
        STATUS  mandatory
        DESCRIPTION
                "An entry of fmStatIpClusterStateTable."
        INDEX   { fmsIpCluVpId,
                  fmsIpCluClusterNumber }
        ::= { fmStatIpClusterStateTable 1 }


        FmStatIpClusterStateEntry ::=
                SEQUENCE {
                    fmsIpCluVpId
                        INTEGER,
                    fmsIpCluClusterNumber
                        INTEGER,
                    fmsIpCluVirtualIpAddress
                        IpAddress,
                    fmsIpCluOperStatus
                        INTEGER,
                    fmsIpCluAdminStatus
                        INTEGER,
                    fmsIpCluLastChange
                        TimeTicks
                }


    fmsIpCluVpId OBJECT-TYPE
        SYNTAX  INTEGER (0..11)
        ACCESS  read-only
        STATUS  mandatory
        DESCRIPTION
                "VP id"
        ::= { fmStatIpClusterStateEntry 1 }


    fmsIpCluClusterNumber OBJECT-TYPE
        SYNTAX  INTEGER (0..255)
        ACCESS  read-only
        STATUS  mandatory
        DESCRIPTION
                "Cluster number"
        ::= { fmStatIpClusterStateEntry 2 }


    fmsIpCluVirtualIpAddress OBJECT-TYPE
        SYNTAX  IpAddress
        ACCESS  read-only
        STATUS  mandatory
        DESCRIPTION
                "Virtual IP Address"
        ::= { fmStatIpClusterStateEntry 3 }


    fmsIpCluOperStatus OBJECT-TYPE
        SYNTAX  INTEGER {
                off(1),
                backup(2),
                master(3)
                }
        ACCESS  read-only
        STATUS  mandatory
        DESCRIPTION
                "Operation State"
        ::= { fmStatIpClusterStateEntry 4 }


    fmsIpCluAdminStatus OBJECT-TYPE
        SYNTAX  INTEGER {
                on(1),
                off(2)
                }
        ACCESS  read-write
        STATUS  mandatory
        DESCRIPTION
                "Administration State"
        ::= { fmStatIpClusterStateEntry 5 }


    fmsIpCluLastChange OBJECT-TYPE
        SYNTAX  TimeTicks
        ACCESS  read-only
        STATUS  mandatory
        DESCRIPTION
                "Time from the Last Change"
        ::= { fmStatIpClusterStateEntry 6 }


    fmStatFrameRelay OBJECT IDENTIFIER ::= { fmStat 60 }


    fmsFrSwitch OBJECT IDENTIFIER ::= { fmStatFrameRelay 1 }


    fmsFrSwDataLinkConnEstablished OBJECT-TYPE
        SYNTAX  Gauge
        ACCESS  read-only
        STATUS  mandatory
        DESCRIPTION
                "Nb de connexions FR etablis (svc-svc, pvc-svc,
                proto-svc)."
        ::= { fmsFrSwitch 1 }


    fmsFrSwBookingInputThrouhput OBJECT-TYPE
        SYNTAX  Gauge
        ACCESS  read-only
        STATUS  mandatory
        DESCRIPTION
                "Debit reserve (somme des CIR abonnes vers reseau)."
        ::= { fmsFrSwitch 10 }


    fmsFrSwOverBookingThrouhput OBJECT-TYPE
        SYNTAX  Gauge
        ACCESS  read-only
        STATUS  mandatory
        DESCRIPTION
                "Debit reserve par les SVC en surbooking."
        ::= { fmsFrSwitch 12 }


    fmsFrLogicalPort OBJECT IDENTIFIER ::= { fmStatFrameRelay 2 }


    fmsFrLpLogPortTable OBJECT-TYPE
        SYNTAX  SEQUENCE OF FmsFrLpLogPortEntry
        ACCESS  not-accessible
        STATUS  mandatory
        DESCRIPTION
                ""
        ::= { fmsFrLogicalPort 1 }


    fmsFrLpLogPortEntry OBJECT-TYPE
        SYNTAX  FmsFrLpLogPortEntry
        ACCESS  not-accessible
        STATUS  mandatory
        DESCRIPTION
                "An entry of fmsFrLpLogPortTable."
        INDEX   { fmsFrLpLogPortId }
        ::= { fmsFrLpLogPortTable 1 }


        FmsFrLpLogPortEntry ::=
                SEQUENCE {
                    fmsFrLpLogPortId
                        INTEGER,
                    fmsFrLpInterfaceType
                        INTEGER,
                    fmsFrLpNumPlan
                        INTEGER,
                    fmsFrLpAddrDlciLen
                        INTEGER,
                    fmsFrLpVcSigProtocol
                        INTEGER
                }


    fmsFrLpLogPortId OBJECT-TYPE
        SYNTAX  INTEGER (0..255)
        ACCESS  read-only
        STATUS  mandatory
        DESCRIPTION
                "LP id."
        ::= { fmsFrLpLogPortEntry 1 }


    fmsFrLpInterfaceType OBJECT-TYPE
        SYNTAX  INTEGER {
                frCe(1),
                frTe(2),
                frSe(3)
                }
        ACCESS  read-only
        STATUS  mandatory
        DESCRIPTION
                "Type."
        ::= { fmsFrLpLogPortEntry 3 }


    fmsFrLpNumPlan OBJECT-TYPE
        SYNTAX  INTEGER {
                other(1),
                e164(2),
                x121(3),
                none(4)
                }
        ACCESS  read-only
        STATUS  mandatory
        DESCRIPTION
                "The value of this object identifies the network
                address numbering plan for this logical port. The
                network address is the object ifPhysAddress. The
                value none implies that there is no ifPhysAddress.
                The SNMP agent will return an octet string of zero
                length for ifPhysAddress. The value other means
                that an address has been assigned to this
                interface, but the numbering plan is not
                enumerated here."
        ::= { fmsFrLpLogPortEntry 11 }


    fmsFrLpAddrDlciLen OBJECT-TYPE
        SYNTAX  INTEGER {
                twoOctets10Bits(1),
                threeOctets10Bits(2),
                threeOctets16Bits(3),
                fourOctets17Bits(4),
                fourOctets23Bits(5)
                }
        ACCESS  read-only
        STATUS  mandatory
        DESCRIPTION
                "The value of this object identifies the Q.922
                Address field length and DLCI length for this
                logical port."
        ::= { fmsFrLpLogPortEntry 15 }


    fmsFrLpVcSigProtocol OBJECT-TYPE
        SYNTAX  INTEGER {
                none(1),
                lmi(2),
                ansiT1617D(3),
                ansiT1617B(4),
                itutQ933A(5),
                itutQ933(6)
                }
        ACCESS  read-only
        STATUS  mandatory
        DESCRIPTION
                "The value of this object identifies the Local
                In-Channel Signaling Protocol that is used for
                this frame relay logical port."
        ::= { fmsFrLpLogPortEntry 16 }


    fmsFrLpIncomingTable OBJECT-TYPE
        SYNTAX  SEQUENCE OF FmsFrLpIncomingEntry
        ACCESS  not-accessible
        STATUS  mandatory
        DESCRIPTION
                ""
        ::= { fmsFrLogicalPort 2 }


    fmsFrLpIncomingEntry OBJECT-TYPE
        SYNTAX  FmsFrLpIncomingEntry
        ACCESS  not-accessible
        STATUS  mandatory
        DESCRIPTION
                "An entry of fmsFrLpIncomingTable."
        INDEX   { fmsFrLpInLogPortId }
        ::= { fmsFrLpIncomingTable 1 }


        FmsFrLpIncomingEntry ::=
                SEQUENCE {
                    fmsFrLpInLogPortId
                        INTEGER,
                    fmsFrLpInOctets
                        Counter,
                    fmsFrLpInFrames
                        Counter,
                    fmsFrLpInErrors
                        Counter,
                    fmsFrLpInFrHeaderErrors
                        Counter,
                    fmsFrLpInFecnFrames
                        Counter,
                    fmsFrLpInBecnFrames
                        Counter,
                    fmsFrLpInExcessFrames
                        Counter,
                    fmsFrLpInDiscards
                        Counter
                }


    fmsFrLpInLogPortId OBJECT-TYPE
        SYNTAX  INTEGER (0..255)
        ACCESS  read-only
        STATUS  mandatory
        DESCRIPTION
                "LP id."
        ::= { fmsFrLpIncomingEntry 1 }


    fmsFrLpInOctets OBJECT-TYPE
        SYNTAX  Counter
        ACCESS  read-only
        STATUS  mandatory
        DESCRIPTION
                "The number of received octets. This counter only
                counts octets from the beginning of the frame
                relay header field to the end of user data."
        ::= { fmsFrLpIncomingEntry 2 }


    fmsFrLpInFrames OBJECT-TYPE
        SYNTAX  Counter
        ACCESS  read-only
        STATUS  mandatory
        DESCRIPTION
                "The number of received unerrored, unicast frames."
        ::= { fmsFrLpIncomingEntry 3 }


    fmsFrLpInErrors OBJECT-TYPE
        SYNTAX  Counter
        ACCESS  read-only
        STATUS  mandatory
        DESCRIPTION
                "The number of received frames that are discarded,
                because of an error. Possible errors can be the
                following: the frame relay frames were too long or
                were too short."
        ::= { fmsFrLpIncomingEntry 4 }


    fmsFrLpInFrHeaderErrors OBJECT-TYPE
        SYNTAX  Counter
        ACCESS  read-only
        STATUS  mandatory
        DESCRIPTION
                "The number of received frames that are discarded,
                because of an error. Possible errors can be the
                following: the frames had an invalid or
                unrecognized DLCI values, or incorrect header
                values."
        ::= { fmsFrLpIncomingEntry 5 }


    fmsFrLpInFecnFrames OBJECT-TYPE
        SYNTAX  Counter
        ACCESS  read-only
        STATUS  mandatory
        DESCRIPTION
                "Number of frames received indicating forward
                congestion."
        ::= { fmsFrLpIncomingEntry 10 }


    fmsFrLpInBecnFrames OBJECT-TYPE
        SYNTAX  Counter
        ACCESS  read-only
        STATUS  mandatory
        DESCRIPTION
                "Number of frames received indicating backward
                congestion."
        ::= { fmsFrLpIncomingEntry 12 }


    fmsFrLpInExcessFrames OBJECT-TYPE
        SYNTAX  Counter
        ACCESS  read-only
        STATUS  mandatory
        DESCRIPTION
                "Only on FR-CE or FR-TE logical ports : The number
                of frames received by the equipment (ingress) for
                this logical port which were treated as excess
                traffic. Frames which are sent to the equipment
                with DE set to zero are treated as excess when
                more than Bc bits are submitted to the equipment
                during the Committed Information Rate Measurement
                Interval (Tc). Excess traffic may or may not be
                discarded at the ingress if more than Bc + Be bits
                are submitted to the equipment during Tc. Traffic
                discarded at the ingress is not recorded in this
                object. Frames which are sent to the equipement
                with DE set to one are also treated as excess
                traffic."
        ::= { fmsFrLpIncomingEntry 15 }


    fmsFrLpInDiscards OBJECT-TYPE
        SYNTAX  Counter
        ACCESS  read-only
        STATUS  mandatory
        DESCRIPTION
                "Only on FR-CE or FR-TE logical ports : The number
                of frames received by the equipment (ingress) that
                were discarded due to traffic enforcement for this
                logical port."
        ::= { fmsFrLpIncomingEntry 16 }


    fmsFrLpOutgoingTable OBJECT-TYPE
        SYNTAX  SEQUENCE OF FmsFrLpOutgoingEntry
        ACCESS  not-accessible
        STATUS  mandatory
        DESCRIPTION
                ""
        ::= { fmsFrLogicalPort 3 }


    fmsFrLpOutgoingEntry OBJECT-TYPE
        SYNTAX  FmsFrLpOutgoingEntry
        ACCESS  not-accessible
        STATUS  mandatory
        DESCRIPTION
                "An entry of fmsFrLpOutgoingTable."
        INDEX   { fmsFrLpOutLogPortId }
        ::= { fmsFrLpOutgoingTable 1 }


        FmsFrLpOutgoingEntry ::=
                SEQUENCE {
                    fmsFrLpOutLogPortId
                        INTEGER,
                    fmsFrLpOutOctets
                        Counter,
                    fmsFrLpOutFrames
                        Counter,
                    fmsFrLpOutFecnFrames
                        Counter,
                    fmsFrLpOutLocalCongFecnFrames
                        Counter,
                    fmsFrLpOutBecnFrames
                        Counter,
                    fmsFrLpOutLocalCongBecnFrames
                        Counter,
                    fmsFrLpOutLocalCongDiscards
                        Counter
                }


    fmsFrLpOutLogPortId OBJECT-TYPE
        SYNTAX  INTEGER (0..255)
        ACCESS  read-only
        STATUS  mandatory
        DESCRIPTION
                "LP id."
        ::= { fmsFrLpOutgoingEntry 1 }


    fmsFrLpOutOctets OBJECT-TYPE
        SYNTAX  Counter
        ACCESS  read-only
        STATUS  mandatory
        DESCRIPTION
                "The number of transmitted octets. This counter
                only counts octets from the beginning of the frame
                relay header field to the end of user data."
        ::= { fmsFrLpOutgoingEntry 2 }


    fmsFrLpOutFrames OBJECT-TYPE
        SYNTAX  Counter
        ACCESS  read-only
        STATUS  mandatory
        DESCRIPTION
                "The number of frames sent."
        ::= { fmsFrLpOutgoingEntry 3 }


    fmsFrLpOutFecnFrames OBJECT-TYPE
        SYNTAX  Counter
        ACCESS  read-only
        STATUS  mandatory
        DESCRIPTION
                "Number of frames sent indicating forward
                congestion."
        ::= { fmsFrLpOutgoingEntry 10 }


    fmsFrLpOutLocalCongFecnFrames OBJECT-TYPE
        SYNTAX  Counter
        ACCESS  read-only
        STATUS  mandatory
        DESCRIPTION
                "Number of frames sent indicating forward
                congestion due to traffic enforcement on this
                logical port."
        ::= { fmsFrLpOutgoingEntry 11 }


    fmsFrLpOutBecnFrames OBJECT-TYPE
        SYNTAX  Counter
        ACCESS  read-only
        STATUS  mandatory
        DESCRIPTION
                "Number of frames sent indicating backward
                congestion."
        ::= { fmsFrLpOutgoingEntry 12 }


    fmsFrLpOutLocalCongBecnFrames OBJECT-TYPE
        SYNTAX  Counter
        ACCESS  read-only
        STATUS  mandatory
        DESCRIPTION
                "Number of frames sent indicating backward
                congestion due to traffic enforcement on the
                incoming logical port."
        ::= { fmsFrLpOutgoingEntry 13 }


    fmsFrLpOutLocalCongDiscards OBJECT-TYPE
        SYNTAX  Counter
        ACCESS  read-only
        STATUS  mandatory
        DESCRIPTION
                "The number of frames not sent by the equipment
                (egress) due to traffic enforcement on this
                logical port."
        ::= { fmsFrLpOutgoingEntry 15 }


    fmsFrLpLmiTable OBJECT-TYPE
        SYNTAX  SEQUENCE OF FmsFrLpLmiEntry
        ACCESS  not-accessible
        STATUS  mandatory
        DESCRIPTION
                ""
        ::= { fmsFrLogicalPort 4 }


    fmsFrLpLmiEntry OBJECT-TYPE
        SYNTAX  FmsFrLpLmiEntry
        ACCESS  not-accessible
        STATUS  mandatory
        DESCRIPTION
                "An entry of fmsFrLpLmiTable."
        INDEX   { fmsFrLpLmiLogPortId }
        ::= { fmsFrLpLmiTable 1 }


        FmsFrLpLmiEntry ::=
                SEQUENCE {
                    fmsFrLpLmiLogPortId
                        INTEGER,
                    fmsFrLpLmiProced
                        INTEGER,
                    fmsFrLpLmiUserN391
                        INTEGER,
                    fmsFrLpLmiUserN392
                        INTEGER,
                    fmsFrLpLmiUserN393
                        INTEGER,
                    fmsFrLpLmiUserT391
                        INTEGER,
                    fmsFrLpLmiNetN392
                        INTEGER,
                    fmsFrLpLmiNetN393
                        INTEGER,
                    fmsFrLpLmiNetT392
                        INTEGER,
                    fmsFrLpLmiUserLinkRelErrors
                        Counter,
                    fmsFrLpLmiUserProtErrors
                        Counter,
                    fmsFrLpLmiUserChanInactive
                        Counter,
                    fmsFrLpLmiNetLinkRelErrors
                        Counter,
                    fmsFrLpLmiNetProtErrors
                        Counter,
                    fmsFrLpLmiNetChanInactive
                        Counter
                }


    fmsFrLpLmiLogPortId OBJECT-TYPE
        SYNTAX  INTEGER (0..254)
        ACCESS  read-only
        STATUS  mandatory
        DESCRIPTION
                "LP id."
        ::= { fmsFrLpLmiEntry 1 }


    fmsFrLpLmiProced OBJECT-TYPE
        SYNTAX  INTEGER {
                u2nNet(1),
                bidirect(2),
                u2nUser(3)
                }
        ACCESS  read-only
        STATUS  mandatory
        DESCRIPTION
                "The value of this object identifies the Local
                In-Channel Signaling Procedure that is used for
                this logical port. The logical port can be
                performing user-to-network network-side
                procedures, bidirectional procedures or
                user-to-network user-side procedures."
        ::= { fmsFrLpLmiEntry 11 }


    fmsFrLpLmiUserN391 OBJECT-TYPE
        SYNTAX  INTEGER (1..255)
        ACCESS  read-only
        STATUS  mandatory
        DESCRIPTION
                "The value of this object identifies the User-side
                N391 full status polling cycle value for this
                logical port. If the logical port is not
                performing user-side procedures, then this value
                is not significant. This object applies to Q.933
                Annex A and T1.617 Annex D."
        ::= { fmsFrLpLmiEntry 12 }


    fmsFrLpLmiUserN392 OBJECT-TYPE
        SYNTAX  INTEGER (1..10)
        ACCESS  read-only
        STATUS  mandatory
        DESCRIPTION
                "The value of this object identifies the User-side
                N392 error threshold value for this logical port. 
                If the logical port is not performing user-side
                procedures, then this value is not significant.
                This object applies to Q.933 Annex A and T1.617
                Annex D."
        ::= { fmsFrLpLmiEntry 13 }


    fmsFrLpLmiUserN393 OBJECT-TYPE
        SYNTAX  INTEGER (1..10)
        ACCESS  read-only
        STATUS  mandatory
        DESCRIPTION
                "The value of this object identifies the User-side
                N393 monitored events count value for this logical
                port. If the logical port is not performing
                user-side procedures, then this value is not
                significant. This object applies to Q.933 Annex A
                and T1.617 Annex D."
        ::= { fmsFrLpLmiEntry 14 }


    fmsFrLpLmiUserT391 OBJECT-TYPE
        SYNTAX  INTEGER (5..30)
        ACCESS  read-only
        STATUS  mandatory
        DESCRIPTION
                "The value of this object identifies the User-side
                T391 link integrity verification polling timer
                value for this logical port. If the logical port
                is not performing user-side procedures, then this
                value is not significant. This object applies to
                Q.933 Annex A and T1.617 Annex D."
        ::= { fmsFrLpLmiEntry 15 }


    fmsFrLpLmiNetN392 OBJECT-TYPE
        SYNTAX  INTEGER (1..10)
        ACCESS  read-only
        STATUS  mandatory
        DESCRIPTION
                "The value of this object identifies the
                Network-side N392 error threshold value (nN2 for
                LMI) for this logical port. If the logical port is
                not performing network-side procedures, then this
                value is not significant. This object applies to
                Q.933 Annex A, T1.617 Annex D and LMI."
        ::= { fmsFrLpLmiEntry 16 }


    fmsFrLpLmiNetN393 OBJECT-TYPE
        SYNTAX  INTEGER (1..10)
        ACCESS  read-only
        STATUS  mandatory
        DESCRIPTION
                "The value of this object identifies the
                Network-side N393 monitored events count value
                (nN3 for LMI) for this logical port. If the
                logical port is not performing network-side
                procedures, then this value is not significant.
                This object applies to Q.933 Annex A, T1.617 Annex
                D and LMI."
        ::= { fmsFrLpLmiEntry 17 }


    fmsFrLpLmiNetT392 OBJECT-TYPE
        SYNTAX  INTEGER (5..30)
        ACCESS  read-only
        STATUS  mandatory
        DESCRIPTION
                "The value of this object identifies the
                Network-side T392 polling verification timer value
                (nT2 for LMI) for this logical port. If the
                logical port is not performing network-side
                procedures, then this value is not significant.
                This object applies to Q.933 Annex A, T1.617 Annex
                D and LMI."
        ::= { fmsFrLpLmiEntry 18 }


    fmsFrLpLmiUserLinkRelErrors OBJECT-TYPE
        SYNTAX  Counter
        ACCESS  read-only
        STATUS  mandatory
        DESCRIPTION
                "VCSigUserLinkRelErrors"
        ::= { fmsFrLpLmiEntry 21 }


    fmsFrLpLmiUserProtErrors OBJECT-TYPE
        SYNTAX  Counter
        ACCESS  read-only
        STATUS  mandatory
        DESCRIPTION
                "VCSigUserProtErrors"
        ::= { fmsFrLpLmiEntry 22 }


    fmsFrLpLmiUserChanInactive OBJECT-TYPE
        SYNTAX  Counter
        ACCESS  read-only
        STATUS  mandatory
        DESCRIPTION
                "VCSigUserChanInactive"
        ::= { fmsFrLpLmiEntry 23 }


    fmsFrLpLmiNetLinkRelErrors OBJECT-TYPE
        SYNTAX  Counter
        ACCESS  read-only
        STATUS  mandatory
        DESCRIPTION
                "VCSigNetLinkRelErrors"
        ::= { fmsFrLpLmiEntry 24 }


    fmsFrLpLmiNetProtErrors OBJECT-TYPE
        SYNTAX  Counter
        ACCESS  read-only
        STATUS  mandatory
        DESCRIPTION
                "VCSigNetProtErrors"
        ::= { fmsFrLpLmiEntry 25 }


    fmsFrLpLmiNetChanInactive OBJECT-TYPE
        SYNTAX  Counter
        ACCESS  read-only
        STATUS  mandatory
        DESCRIPTION
                "VCSigNetChanInactiveErrors"
        ::= { fmsFrLpLmiEntry 26 }


    fmsFrLpSvcSignallingTable OBJECT-TYPE
        SYNTAX  SEQUENCE OF FmsFrLpSvcSignallingEntry
        ACCESS  not-accessible
        STATUS  mandatory
        DESCRIPTION
                ""
        ::= { fmsFrLogicalPort 5 }


    fmsFrLpSvcSignallingEntry OBJECT-TYPE
        SYNTAX  FmsFrLpSvcSignallingEntry
        ACCESS  not-accessible
        STATUS  mandatory
        DESCRIPTION
                "An entry of fmsFrLpSvcSignallingTable."
        INDEX   { fmsFrLpSvcLogPortId }
        ::= { fmsFrLpSvcSignallingTable 1 }


        FmsFrLpSvcSignallingEntry ::=
                SEQUENCE {
                    fmsFrLpSvcLogPortId
                        INTEGER,
                    fmsFrLpSvcDlcInitialized
                        Gauge,
                    fmsFrLpSvcDlcUbr
                        Gauge,
                    fmsFrLpSvcDlcVbr
                        Gauge,
                    fmsFrLpSvcDlcVbrRt
                        Gauge,
                    fmsFrLpSvcBookingVbrThroughput
                        Gauge,
                    fmsFrLpSvcBookingVbrRtThroughput
                        Gauge,
                    fmsFrLpSvcOverBookingThroughput
                        Gauge,
                    fmsFrLpSvcBookingRate
                        Gauge
                }


    fmsFrLpSvcLogPortId OBJECT-TYPE
        SYNTAX  INTEGER (0..254)
        ACCESS  read-only
        STATUS  mandatory
        DESCRIPTION
                "LP id."
        ::= { fmsFrLpSvcSignallingEntry 1 }


    fmsFrLpSvcDlcInitialized OBJECT-TYPE
        SYNTAX  Gauge
        ACCESS  read-only
        STATUS  mandatory
        DESCRIPTION
                "Nb de Data Link Connexion correctement initialises."
        ::= { fmsFrLpSvcSignallingEntry 11 }


    fmsFrLpSvcDlcUbr OBJECT-TYPE
        SYNTAX  Gauge
        ACCESS  read-only
        STATUS  mandatory
        DESCRIPTION
                "Nb de DLC UBR etablies."
        ::= { fmsFrLpSvcSignallingEntry 12 }


    fmsFrLpSvcDlcVbr OBJECT-TYPE
        SYNTAX  Gauge
        ACCESS  read-only
        STATUS  mandatory
        DESCRIPTION
                "Nb de DLC VBR etablies."
        ::= { fmsFrLpSvcSignallingEntry 13 }


    fmsFrLpSvcDlcVbrRt OBJECT-TYPE
        SYNTAX  Gauge
        ACCESS  read-only
        STATUS  mandatory
        DESCRIPTION
                "Nb de DLC VBR-RT etablies."
        ::= { fmsFrLpSvcSignallingEntry 14 }


    fmsFrLpSvcBookingVbrThroughput OBJECT-TYPE
        SYNTAX  Gauge
        ACCESS  read-only
        STATUS  mandatory
        DESCRIPTION
                "Debit reserve VBR (en octets/s)."
        ::= { fmsFrLpSvcSignallingEntry 20 }


    fmsFrLpSvcBookingVbrRtThroughput OBJECT-TYPE
        SYNTAX  Gauge
        ACCESS  read-only
        STATUS  mandatory
        DESCRIPTION
                "Debit reserve VBR-RT (en octets/s)."
        ::= { fmsFrLpSvcSignallingEntry 21 }


    fmsFrLpSvcOverBookingThroughput OBJECT-TYPE
        SYNTAX  Gauge
        ACCESS  read-only
        STATUS  mandatory
        DESCRIPTION
                "Debit total avec surbooking (en octets/s)."
        ::= { fmsFrLpSvcSignallingEntry 22 }


    fmsFrLpSvcBookingRate OBJECT-TYPE
        SYNTAX  Gauge
        ACCESS  read-only
        STATUS  mandatory
        DESCRIPTION
                "Taux de reservation."
        ::= { fmsFrLpSvcSignallingEntry 23 }


    fmsFrDataLinkConnection OBJECT IDENTIFIER ::= { fmStatFrameRelay 3 }


    fmsFrDlcTable OBJECT-TYPE
        SYNTAX  SEQUENCE OF FmsFrDlcEntry
        ACCESS  not-accessible
        STATUS  mandatory
        DESCRIPTION
                ""
        ::= { fmsFrDataLinkConnection 1 }


    fmsFrDlcEntry OBJECT-TYPE
        SYNTAX  FmsFrDlcEntry
        ACCESS  not-accessible
        STATUS  mandatory
        DESCRIPTION
                "An entry of fmsFrDlcTable."
        INDEX   { fmsFrDlcLogPortId,
                  fmsFrDlcDlci }
        ::= { fmsFrDlcTable 1 }


        FmsFrDlcEntry ::=
                SEQUENCE {
                    fmsFrDlcLogPortId
                        INTEGER,
                    fmsFrDlcDlci
                        INTEGER,
                    fmsFrDlcState
                        INTEGER,
                    fmsFrDlcRcvdSigStatus
                        INTEGER,
                    fmsFrDlcCos
                        INTEGER
                }


    fmsFrDlcLogPortId OBJECT-TYPE
        SYNTAX  INTEGER (0..35)
        ACCESS  read-only
        STATUS  mandatory
        DESCRIPTION
                "LP Id."
        ::= { fmsFrDlcEntry 1 }


    fmsFrDlcDlci OBJECT-TYPE
        SYNTAX  INTEGER (0..1023)
        ACCESS  read-only
        STATUS  mandatory
        DESCRIPTION
                "DLCI."
        ::= { fmsFrDlcEntry 2 }


    fmsFrDlcState OBJECT-TYPE
        SYNTAX  INTEGER {
                invalid(1),
                active(2),
                inactive(3)
                }
        ACCESS  read-only
        STATUS  mandatory
        DESCRIPTION
                "Indicates whether the particular virtual circuit
                is operational."
        ::= { fmsFrDlcEntry 5 }


    fmsFrDlcRcvdSigStatus OBJECT-TYPE
        SYNTAX  INTEGER {
                deleted(1),
                active(2),
                inactive(3),
                none(4)
                }
        ACCESS  read-only
        STATUS  mandatory
        DESCRIPTION
                "PVC end point received status"
        ::= { fmsFrDlcEntry 7 }


    fmsFrDlcCos OBJECT-TYPE
        SYNTAX  INTEGER {
                ubr(1),
                vbr(2),
                vbr-rt(3)
                }
        ACCESS  read-only
        STATUS  mandatory
        DESCRIPTION
                "COS."
        ::= { fmsFrDlcEntry 10 }


    fmsFrDlcIncomingTable OBJECT-TYPE
        SYNTAX  SEQUENCE OF FmsFrDlcIncomingEntry
        ACCESS  not-accessible
        STATUS  mandatory
        DESCRIPTION
                ""
        ::= { fmsFrDataLinkConnection 2 }


    fmsFrDlcIncomingEntry OBJECT-TYPE
        SYNTAX  FmsFrDlcIncomingEntry
        ACCESS  not-accessible
        STATUS  mandatory
        DESCRIPTION
                "An entry of fmsFrDlcIncomingTable."
        INDEX   { fmsFrDlcInLogPortId,
                  fmsFrDlcInDlci }
        ::= { fmsFrDlcIncomingTable 1 }


        FmsFrDlcIncomingEntry ::=
                SEQUENCE {
                    fmsFrDlcInLogPortId
                        INTEGER,
                    fmsFrDlcInDlci
                        INTEGER,
                    fmsFrDlcInFrames
                        Counter,
                    fmsFrDlcInOctets
                        Counter,
                    fmsFrDlcInDeFrames
                        Counter,
                    fmsFrDlcInFecnFrames
                        Counter,
                    fmsFrDlcInBecnFrames
                        Counter,
                    fmsFrDlcInExcessFrames
                        Counter,
                    fmsFrDlcInDiscards
                        Counter,
                    fmsFrDlcInLostFrames
                        Counter,
                    fmsFrDlcInLostSegments
                        Counter
                }


    fmsFrDlcInLogPortId OBJECT-TYPE
        SYNTAX  INTEGER (0..35)
        ACCESS  read-only
        STATUS  mandatory
        DESCRIPTION
                "LP Id."
        ::= { fmsFrDlcIncomingEntry 1 }


    fmsFrDlcInDlci OBJECT-TYPE
        SYNTAX  INTEGER (0..1023)
        ACCESS  read-only
        STATUS  mandatory
        DESCRIPTION
                "The value of this object is equal to the DLCI
                value for this Data Link Connection."
        ::= { fmsFrDlcIncomingEntry 2 }


    fmsFrDlcInFrames OBJECT-TYPE
        SYNTAX  Counter
        ACCESS  read-only
        STATUS  mandatory
        DESCRIPTION
                "The number of frames received by the equipment
                (ingress) for this Data Link Connection. This
                includes any frames discarded by the equipment due
                to submitting more than Bc + Be data or due to any
                network congestion recovery procedure."
        ::= { fmsFrDlcIncomingEntry 10 }


    fmsFrDlcInOctets OBJECT-TYPE
        SYNTAX  Counter
        ACCESS  read-only
        STATUS  mandatory
        DESCRIPTION
                "The number of octets received by the equipment
                (ingress) for this Data Link Connection. This
                counter only counts octets from the beginning of
                the frame relay header field to the end of user
                data."
        ::= { fmsFrDlcIncomingEntry 11 }


    fmsFrDlcInDeFrames OBJECT-TYPE
        SYNTAX  Counter
        ACCESS  read-only
        STATUS  mandatory
        DESCRIPTION
                "The number of frames received by the equipment
                (ingress) with the DE bit set to (1) for this Data
                Link Connection."
        ::= { fmsFrDlcIncomingEntry 12 }


    fmsFrDlcInFecnFrames OBJECT-TYPE
        SYNTAX  Counter
        ACCESS  read-only
        STATUS  mandatory
        DESCRIPTION
                "Number of frames received by the equipment
                indicating forward congestion for this Data Link
                Connection."
        ::= { fmsFrDlcIncomingEntry 13 }


    fmsFrDlcInBecnFrames OBJECT-TYPE
        SYNTAX  Counter
        ACCESS  read-only
        STATUS  mandatory
        DESCRIPTION
                "Number of frames received by the equipment
                indicating backward congestion for this Data Link
                Connection"
        ::= { fmsFrDlcIncomingEntry 14 }


    fmsFrDlcInExcessFrames OBJECT-TYPE
        SYNTAX  Counter
        ACCESS  read-only
        STATUS  mandatory
        DESCRIPTION
                "The number of frames received by the equipment
                (ingress) for this Data Link Connection which were
                treated as excess traffic. Frames which are sent
                to the equipment with DE set to zero are treated
                as excess when more than Bc bits are submitted to
                the network during the Committed Information Rate
                Measurement Interval (Tc). Excess traffic may or
                may not be discarded at the ingress if more than
                Bc + Be bits are submitted to the equipment during
                Tc. Traffic discarded at the ingress is not
                recorded in this object. Frames which are sent to
                the equipment with DE set to one are also treated
                as excess traffic."
        ::= { fmsFrDlcIncomingEntry 15 }


    fmsFrDlcInDiscards OBJECT-TYPE
        SYNTAX  Counter
        ACCESS  read-only
        STATUS  mandatory
        DESCRIPTION
                "The number of frames received by the equipment
                (ingress) that were discarded due to traffic
                enforcement for this Data Link Connection."
        ::= { fmsFrDlcIncomingEntry 16 }


    fmsFrDlcInLostFrames OBJECT-TYPE
        SYNTAX  Counter
        ACCESS  read-only
        STATUS  mandatory
        DESCRIPTION
                "Nb de trames perdues dans le reseau (evalue par le
                mecanisme de segmentation / reassemblage)."
        ::= { fmsFrDlcIncomingEntry 30 }


    fmsFrDlcInLostSegments OBJECT-TYPE
        SYNTAX  Counter
        ACCESS  read-only
        STATUS  mandatory
        DESCRIPTION
                "Nb de segments perdus dans le reseau (evalue par
                le mecanisme de segmentation / reassemblage)."
        ::= { fmsFrDlcIncomingEntry 31 }


    fmsFrDlcOutgoingTable OBJECT-TYPE
        SYNTAX  SEQUENCE OF FmsFrDlcOutgoingEntry
        ACCESS  not-accessible
        STATUS  mandatory
        DESCRIPTION
                ""
        ::= { fmsFrDataLinkConnection 3 }


    fmsFrDlcOutgoingEntry OBJECT-TYPE
        SYNTAX  FmsFrDlcOutgoingEntry
        ACCESS  not-accessible
        STATUS  mandatory
        DESCRIPTION
                "An entry of fmsFrDlcOutgoingTable."
        INDEX   { fmsFrDlcOutLogPortId,
                  fmsFrDlcOutDlci }
        ::= { fmsFrDlcOutgoingTable 1 }


        FmsFrDlcOutgoingEntry ::=
                SEQUENCE {
                    fmsFrDlcOutLogPortId
                        INTEGER,
                    fmsFrDlcOutDlci
                        INTEGER,
                    fmsFrDlcOutFrames
                        Counter,
                    fmsFrDlcOutOctets
                        Counter,
                    fmsFrDlcOutFecnFrames
                        Counter,
                    fmsFrDlcOutBecnFrames
                        Counter,
                    fmsFrDlcOutExcessFrames
                        Counter,
                    fmsFrDlcOutDiscards
                        Counter
                }


    fmsFrDlcOutLogPortId OBJECT-TYPE
        SYNTAX  INTEGER (0..35)
        ACCESS  read-only
        STATUS  mandatory
        DESCRIPTION
                "LP Id."
        ::= { fmsFrDlcOutgoingEntry 1 }


    fmsFrDlcOutDlci OBJECT-TYPE
        SYNTAX  INTEGER (0..1023)
        ACCESS  read-only
        STATUS  mandatory
        DESCRIPTION
                "The value of this object is equal to the DLCI
                value for this Data Link Connection."
        ::= { fmsFrDlcOutgoingEntry 2 }


    fmsFrDlcOutFrames OBJECT-TYPE
        SYNTAX  Counter
        ACCESS  read-only
        STATUS  mandatory
        DESCRIPTION
                "The number of frames sent by the equipment
                (egress) regardless of whether they are Bc or Be
                frames for this Data Link Connection."
        ::= { fmsFrDlcOutgoingEntry 10 }


    fmsFrDlcOutOctets OBJECT-TYPE
        SYNTAX  Counter
        ACCESS  read-only
        STATUS  mandatory
        DESCRIPTION
                "The number of octets sent by the equipment
                (egress) for this Data Link Connection. This
                counter only counts octets from the beginning of
                the frame relay header field to the end of user
                data."
        ::= { fmsFrDlcOutgoingEntry 11 }


    fmsFrDlcOutFecnFrames OBJECT-TYPE
        SYNTAX  Counter
        ACCESS  read-only
        STATUS  mandatory
        DESCRIPTION
                "Number of frames sent by the equipment indicating
                forward congestion for this Data Link Connection."
        ::= { fmsFrDlcOutgoingEntry 13 }


    fmsFrDlcOutBecnFrames OBJECT-TYPE
        SYNTAX  Counter
        ACCESS  read-only
        STATUS  mandatory
        DESCRIPTION
                "Number of frames sent by the equipment indicating
                backward congestion for this Data Link Connection."
        ::= { fmsFrDlcOutgoingEntry 14 }


    fmsFrDlcOutExcessFrames OBJECT-TYPE
        SYNTAX  Counter
        ACCESS  read-only
        STATUS  mandatory
        DESCRIPTION
                "The number of frames sent by the equipment
                (egress) for this Data Link Connection which were
                treated as excess traffic. (The DE bit may be set
                to one.)."
        ::= { fmsFrDlcOutgoingEntry 15 }


    fmsFrDlcOutDiscards OBJECT-TYPE
        SYNTAX  Counter
        ACCESS  read-only
        STATUS  mandatory
        DESCRIPTION
                "Number of frames not sent by the equipment due to
                congestion for this Data Link Connection."
        ::= { fmsFrDlcOutgoingEntry 16 }


    fmStatFrLineTable OBJECT-TYPE
        SYNTAX  SEQUENCE OF FmStatFrLineEntry
        ACCESS  not-accessible
        STATUS  mandatory
        DESCRIPTION
                "This table contains the information about the
                Frame Relay lines."
        ::= { fmStatFrameRelay 20 }


    fmStatFrLineEntry OBJECT-TYPE
        SYNTAX  FmStatFrLineEntry
        ACCESS  not-accessible
        STATUS  mandatory
        DESCRIPTION
                "An entry of fmStatFrLineTable."
        INDEX   { fmsFrLineId }
        ::= { fmStatFrLineTable 1 }


        FmStatFrLineEntry ::=
                SEQUENCE {
                    fmsFrLineId
                        INTEGER,
                    fmsFrLineStatus
                        INTEGER,
                    fmsFrLineLmiStatus
                        INTEGER,
                    fmsFrLineCircuitCount
                        Gauge,
                    fmsFrLineActiveCircuitCount
                        Gauge
                }


    fmsFrLineId OBJECT-TYPE
        SYNTAX  INTEGER (0..35)
        ACCESS  read-only
        STATUS  mandatory
        DESCRIPTION
                "The value of this object is the one physical line
                identifier."
        ::= { fmStatFrLineEntry 1 }


    fmsFrLineStatus OBJECT-TYPE
        SYNTAX  INTEGER {
                down(1),
                up(2)
                }
        ACCESS  read-only
        STATUS  mandatory
        DESCRIPTION
                "The value of this object indicates the state of
                this physical line."
        ::= { fmStatFrLineEntry 2 }


    fmsFrLineLmiStatus OBJECT-TYPE
        SYNTAX  INTEGER {
                off(1),
                down(2),
                up(3)
                }
        ACCESS  read-only
        STATUS  mandatory
        DESCRIPTION
                "The value of this object indicates the LMI state."
        ::= { fmStatFrLineEntry 3 }


    fmsFrLineCircuitCount OBJECT-TYPE
        SYNTAX  Gauge
        ACCESS  read-only
        STATUS  mandatory
        DESCRIPTION
                "The value of this object indicates the total
                number of the DLCI on this physical line."
        ::= { fmStatFrLineEntry 4 }


    fmsFrLineActiveCircuitCount OBJECT-TYPE
        SYNTAX  Gauge
        ACCESS  read-only
        STATUS  mandatory
        DESCRIPTION
                "The value of this objects is the number of active
                DLCI on this physical line."
        ::= { fmStatFrLineEntry 5 }


    fmStatFrCircuitTable OBJECT-TYPE
        SYNTAX  SEQUENCE OF FmStatFrCircuitEntry
        ACCESS  not-accessible
        STATUS  mandatory
        DESCRIPTION
                "This table contains the information about each
                circuit."
        ::= { fmStatFrameRelay 21 }


    fmStatFrCircuitEntry OBJECT-TYPE
        SYNTAX  FmStatFrCircuitEntry
        ACCESS  not-accessible
        STATUS  mandatory
        DESCRIPTION
                "An entry of fmStatFrCircuitTable."
        INDEX   { fmsFrCircuitLineId,
                  fmsFrCircuitDlci }
        ::= { fmStatFrCircuitTable 1 }


        FmStatFrCircuitEntry ::=
                SEQUENCE {
                    fmsFrCircuitLineId
                        INTEGER,
                    fmsFrCircuitDlci
                        INTEGER,
                    fmsFrCircuitStatus
                        INTEGER,
                    fmsFrCircuitAge
                        INTEGER,
                    fmsFrCircuitOutOctetsCounter
                        Counter,
                    fmsFrCircuitInOctetsCounter
                        Counter
                }


    fmsFrCircuitLineId OBJECT-TYPE
        SYNTAX  INTEGER (0..35)
        ACCESS  read-only
        STATUS  mandatory
        DESCRIPTION
                "The value of this object is the one physical line
                identifier."
        ::= { fmStatFrCircuitEntry 1 }


    fmsFrCircuitDlci OBJECT-TYPE
        SYNTAX  INTEGER (0..1023)
        ACCESS  read-only
        STATUS  mandatory
        DESCRIPTION
                "The value of this object is the identifier of one
                circuit. It is the DLCI."
        ::= { fmStatFrCircuitEntry 2 }


    fmsFrCircuitStatus OBJECT-TYPE
        SYNTAX  INTEGER {
                active(1),
                inactive(2)
                }
        ACCESS  read-only
        STATUS  mandatory
        DESCRIPTION
                "The value of this object is the state of this
                circuit."
        ::= { fmStatFrCircuitEntry 3 }


    fmsFrCircuitAge OBJECT-TYPE
        SYNTAX  INTEGER {
                old(1),
                new(2),
                indeterminate(3)
                }
        ACCESS  read-only
        STATUS  mandatory
        DESCRIPTION
                "The value of this object indicates the age of this
                circuit."
        ::= { fmStatFrCircuitEntry 4 }


    fmsFrCircuitOutOctetsCounter OBJECT-TYPE
        SYNTAX  Counter
        ACCESS  read-only
        STATUS  mandatory
        DESCRIPTION
                "The value of this object is the number of octets
                sent on this circuit."
        ::= { fmStatFrCircuitEntry 5 }


    fmsFrCircuitInOctetsCounter OBJECT-TYPE
        SYNTAX  Counter
        ACCESS  read-only
        STATUS  mandatory
        DESCRIPTION
                "The value of this object is the number of octets
                received on this circuit."
        ::= { fmStatFrCircuitEntry 6 }


    fmsFrCommIdentification OBJECT IDENTIFIER ::= { fmStatFrameRelay 30 }


    fmsFrCommStorageTable OBJECT-TYPE
        SYNTAX  SEQUENCE OF FmsFrCommStorageEntry
        ACCESS  not-accessible
        STATUS  mandatory
        DESCRIPTION
                "This table contains"
        ::= { fmsFrCommIdentification 1 }


    fmsFrCommStorageEntry OBJECT-TYPE
        SYNTAX  FmsFrCommStorageEntry
        ACCESS  not-accessible
        STATUS  mandatory
        DESCRIPTION
                "An entry of fmsFrCommStorageTable."
        INDEX   { fmsFrcStoragePhysIfId,
                  fmsFrcStorageChannelId,
                  fmsFrcStorageDlci,
                  fmsFrcStorageSubDlci }
        ::= { fmsFrCommStorageTable 1 }


        FmsFrCommStorageEntry ::=
                SEQUENCE {
                    fmsFrcStoragePhysIfId
                        INTEGER,
                    fmsFrcStorageChannelId
                        INTEGER,
                    fmsFrcStorageDlci
                        INTEGER,
                    fmsFrcStorageSubDlci
                        INTEGER,
                    fmsFrcStorageTypeOfDlci
                        INTEGER,
                    fmsFrcStorageDirection
                        OCTET STRING,
                    fmsFrcStorageTypeOfTransport
                        INTEGER,
                    fmsFrcStoragePvcStatus
                        INTEGER,
                    fmsFrcStorageDestAddr
                        OCTET STRING,
                    fmsFrcStorageSrcAddr
                        OCTET STRING,
                    fmsFrcStorageCos
                        INTEGER,
                    fmsFrcStorageCir
                        INTEGER,
                    fmsFrcStorageMinCir
                        INTEGER,
                    fmsFrcStorageBc
                        INTEGER,
                    fmsFrcStorageBe
                        INTEGER
                }


    fmsFrcStoragePhysIfId OBJECT-TYPE
        SYNTAX  INTEGER (0..255)
        ACCESS  read-only
        STATUS  mandatory
        DESCRIPTION
                "Interface physique"
        ::= { fmsFrCommStorageEntry 1 }


    fmsFrcStorageChannelId OBJECT-TYPE
        SYNTAX  INTEGER (0..31)
        ACCESS  read-only
        STATUS  mandatory
        DESCRIPTION
                "Channel ID"
        ::= { fmsFrCommStorageEntry 2 }


    fmsFrcStorageDlci OBJECT-TYPE
        SYNTAX  INTEGER (0..1023)
        ACCESS  read-only
        STATUS  mandatory
        DESCRIPTION
                "DLCI"
        ::= { fmsFrCommStorageEntry 3 }


    fmsFrcStorageSubDlci OBJECT-TYPE
        SYNTAX  INTEGER (0..1023)
        ACCESS  read-only
        STATUS  mandatory
        DESCRIPTION
                "Channel"
        ::= { fmsFrCommStorageEntry 4 }


    fmsFrcStorageTypeOfDlci OBJECT-TYPE
        SYNTAX  INTEGER {
                unknown(1),
                svc(2),
                pvc(255)
                }
        ACCESS  read-only
        STATUS  mandatory
        DESCRIPTION
                "Type de DLCI"
        ::= { fmsFrCommStorageEntry 5 }


    fmsFrcStorageDirection OBJECT-TYPE
        SYNTAX  OCTET STRING (SIZE(8))
        ACCESS  read-only
        STATUS  mandatory
        DESCRIPTION
                "Direction"
        ::= { fmsFrCommStorageEntry 6 }


    fmsFrcStorageTypeOfTransport OBJECT-TYPE
        SYNTAX  INTEGER {
                tunnel(19),
                annexG(32),
                frsna(34),
                frt(36),
                switch(99),
                unknown(255)
                }
        ACCESS  read-only
        STATUS  mandatory
        DESCRIPTION
                "Type de transport"
        ::= { fmsFrCommStorageEntry 7 }


    fmsFrcStoragePvcStatus OBJECT-TYPE
        SYNTAX  INTEGER {
                active(1),
                inactive(2),
                unknown(255)
                }
        ACCESS  read-only
        STATUS  mandatory
        DESCRIPTION
                "PVC Status"
        ::= { fmsFrCommStorageEntry 8 }


    fmsFrcStorageDestAddr OBJECT-TYPE
        SYNTAX  OCTET STRING (SIZE(8))
        ACCESS  read-only
        STATUS  mandatory
        DESCRIPTION
                "Destinataire"
        ::= { fmsFrCommStorageEntry 9 }


    fmsFrcStorageSrcAddr OBJECT-TYPE
        SYNTAX  OCTET STRING (SIZE(8))
        ACCESS  read-only
        STATUS  mandatory
        DESCRIPTION
                "Adresse source"
        ::= { fmsFrCommStorageEntry 10 }


    fmsFrcStorageCos OBJECT-TYPE
        SYNTAX  INTEGER {
                vbr(1),
                vbr-rt(2),
                ubr(3),
                unknown(255)
                }
        ACCESS  read-only
        STATUS  mandatory
        DESCRIPTION
                "COS"
        ::= { fmsFrCommStorageEntry 11 }


    fmsFrcStorageCir OBJECT-TYPE
        SYNTAX  INTEGER (0..2048000)
        ACCESS  read-only
        STATUS  mandatory
        DESCRIPTION
                "CIR"
        ::= { fmsFrCommStorageEntry 12 }


    fmsFrcStorageMinCir OBJECT-TYPE
        SYNTAX  INTEGER (0..2048000)
        ACCESS  read-only
        STATUS  mandatory
        DESCRIPTION
                "CIR Min"
        ::= { fmsFrCommStorageEntry 13 }


    fmsFrcStorageBc OBJECT-TYPE
        SYNTAX  INTEGER (0..2048000)
        ACCESS  read-only
        STATUS  mandatory
        DESCRIPTION
                "BC"
        ::= { fmsFrCommStorageEntry 14 }


    fmsFrcStorageBe OBJECT-TYPE
        SYNTAX  INTEGER (0..2048000)
        ACCESS  read-only
        STATUS  mandatory
        DESCRIPTION
                "BE"
        ::= { fmsFrCommStorageEntry 15 }


    fmsFrCommFilter OBJECT IDENTIFIER ::= { fmsFrCommIdentification 2 }


    fmsFrcFilterPhysIfId OBJECT-TYPE
        SYNTAX  DisplayString (SIZE(0..10))
        ACCESS  read-write
        STATUS  mandatory
        DESCRIPTION
                "Interface physique"
        ::= { fmsFrCommFilter 1 }


    fmsFrcFilterChannelId OBJECT-TYPE
        SYNTAX  DisplayString (SIZE(0..10))
        ACCESS  read-write
        STATUS  mandatory
        DESCRIPTION
                "Channel ID"
        ::= { fmsFrCommFilter 2 }


    fmsFrcFilterDlci OBJECT-TYPE
        SYNTAX  DisplayString (SIZE(0..10))
        ACCESS  read-write
        STATUS  mandatory
        DESCRIPTION
                "DLCI"
        ::= { fmsFrCommFilter 3 }


    fmsFrcFilterAction OBJECT-TYPE
        SYNTAX  INTEGER {
                setFilter(1),
                activateFilter(2)
                }
        ACCESS  read-write
        STATUS  mandatory
        DESCRIPTION
                "Action"
        ::= { fmsFrCommFilter 4 }


    fmStatPointToPointProtocol OBJECT IDENTIFIER ::= { fmStat 71 }


    fmStatPppPhysLineTable OBJECT-TYPE
        SYNTAX  SEQUENCE OF FmStatPppPhysLineEntry
        ACCESS  not-accessible
        STATUS  mandatory
        DESCRIPTION
                "This table contains the general information about
                PPP lines."
        ::= { fmStatPointToPointProtocol 1 }


    fmStatPppPhysLineEntry OBJECT-TYPE
        SYNTAX  FmStatPppPhysLineEntry
        ACCESS  not-accessible
        STATUS  mandatory
        DESCRIPTION
                "An entry of fmStatPppPhysLineTable."
        INDEX   { fmsPppPhysLineId }
        ::= { fmStatPppPhysLineTable 1 }


        FmStatPppPhysLineEntry ::=
                SEQUENCE {
                    fmsPppPhysLineId
                        INTEGER,
                    fmsPppPhysLocalMru
                        INTEGER,
                    fmsPppPhysRemoteMru
                        INTEGER,
                    fmsPppPhysMagicNumber
                        INTEGER
                }


    fmsPppPhysLineId OBJECT-TYPE
        SYNTAX  INTEGER (0..35)
        ACCESS  read-only
        STATUS  mandatory
        DESCRIPTION
                "The value of this object is the one physical port
                identifier."
        ::= { fmStatPppPhysLineEntry 1 }


    fmsPppPhysLocalMru OBJECT-TYPE
        SYNTAX  INTEGER (100..1600)
        ACCESS  read-only
        STATUS  mandatory
        DESCRIPTION
                "The value of this object is the current value of
                the MRU (Maximum Receive Unit) for the local PPP
                entity. This value is the MRU that the remote
                entity is using when sending packets to the local
                PPP entity. The value of this object is meaningful
                only when the link has reached the open state
                (ifOperStatus is up)."
        ::= { fmStatPppPhysLineEntry 2 }


    fmsPppPhysRemoteMru OBJECT-TYPE
        SYNTAX  INTEGER (100..1600)
        ACCESS  read-only
        STATUS  mandatory
        DESCRIPTION
                "The value of this object is the current value of
                the MRU (Maximum Receive Unit) for the remote PPP
                entity. This value is the MRU that the local
                entity is using when sending packets to the remote
                PPP entity. The value of this object is meaningful
                only when the link has reached the open state
                (ifOperStatus is up)."
        ::= { fmStatPppPhysLineEntry 3 }


    fmsPppPhysMagicNumber OBJECT-TYPE
        SYNTAX  INTEGER {
                used(1),
                notUsed(2)
                }
        ACCESS  read-only
        STATUS  mandatory
        DESCRIPTION
                "The value of this object indicates the magic
                number state. If 'used' then the local node will
                attempt to perform Magic Number negotiation with
                the remote node. If 'notUsed' then this
                negotiation is not performed. In any event, the
                local node will comply with any magic number
                negotiations attempted by the remote node, per the
                PPP specification. Changing this object will have
                an effect when the link is next restarted."
        ::= { fmStatPppPhysLineEntry 4 }


    fmStatPppProtocolStatusTable OBJECT-TYPE
        SYNTAX  SEQUENCE OF FmStatPppProtocolStatusEntry
        ACCESS  not-accessible
        STATUS  mandatory
        DESCRIPTION
                "This table contains the information about the
                protocol layers (LCP and NCP level) for each PPP
                line."
        ::= { fmStatPointToPointProtocol 2 }


    fmStatPppProtocolStatusEntry OBJECT-TYPE
        SYNTAX  FmStatPppProtocolStatusEntry
        ACCESS  not-accessible
        STATUS  mandatory
        DESCRIPTION
                "An entry of fmStatPppProtocolStatusTable."
        INDEX   { fmsPppProtoLineId }
        ::= { fmStatPppProtocolStatusTable 1 }


        FmStatPppProtocolStatusEntry ::=
                SEQUENCE {
                    fmsPppProtoLineId
                        INTEGER,
                    fmsPppProtoLcpStatus
                        INTEGER,
                    fmsPppProtoLcpDiag
                        INTEGER,
                    fmsPppProtoIpNcpStatus
                        INTEGER,
                    fmsPppProtoIpNcpDiag
                        INTEGER,
                    fmsPppProtoBrdgNcpStatus
                        INTEGER,
                    fmsPppProtoBrdgNcpDiag
                        INTEGER,
                    fmsPppProtoIpxNcpStatus
                        INTEGER,
                    fmsPppProtoIpxNcpDiag
                        INTEGER,
                    fmsPppProtoClnpNcpStatus
                        INTEGER,
                    fmsPppProtoClnpNcpDiag
                        INTEGER
                }


    fmsPppProtoLineId OBJECT-TYPE
        SYNTAX  INTEGER (0..35)
        ACCESS  read-only
        STATUS  mandatory
        DESCRIPTION
                "The value of this object is the one PPP line
                identifier."
        ::= { fmStatPppProtocolStatusEntry 1 }


    fmsPppProtoLcpStatus OBJECT-TYPE
        SYNTAX  INTEGER {
                stop(1),
                wait(2),
                opening(3),
                up(4),
                down(5),
                closed(6),
                freeze(7)
                }
        ACCESS  read-only
        STATUS  mandatory
        DESCRIPTION
                "The value of this object is the current state of
                the LCP layer."
        ::= { fmStatPppProtocolStatusEntry 2 }


    fmsPppProtoLcpDiag OBJECT-TYPE
        SYNTAX  INTEGER {
                ok(1),
                timeOut(2),
                underlyingLayerDown(3),
                protocol(4),
                rejected(5),
                authenticationFailure(6)
                }
        ACCESS  read-only
        STATUS  mandatory
        DESCRIPTION
                "The value of this object is the LCP layer
                diagnostic report."
        ::= { fmStatPppProtocolStatusEntry 3 }


    fmsPppProtoIpNcpStatus OBJECT-TYPE
        SYNTAX  INTEGER {
                stop(1),
                wait(2),
                opening(3),
                up(4),
                down(5),
                closed(6),
                freeze(7)
                }
        ACCESS  read-only
        STATUS  mandatory
        DESCRIPTION
                "The value of this object is the current state of
                the IP NCP layer."
        ::= { fmStatPppProtocolStatusEntry 4 }


    fmsPppProtoIpNcpDiag OBJECT-TYPE
        SYNTAX  INTEGER {
                ok(1),
                timeOut(2),
                underlyingLayerDown(3),
                protocol(4),
                rejected(5)
                }
        ACCESS  read-only
        STATUS  mandatory
        DESCRIPTION
                "The value of this object is the IP NCP layer
                diagnostic report."
        ::= { fmStatPppProtocolStatusEntry 5 }


    fmsPppProtoBrdgNcpStatus OBJECT-TYPE
        SYNTAX  INTEGER {
                stop(1),
                wait(2),
                opening(3),
                up(4),
                down(5),
                closed(6),
                freeze(7)
                }
        ACCESS  read-only
        STATUS  mandatory
        DESCRIPTION
                "The value of this object is the current state of
                the Bridge NCP layer."
        ::= { fmStatPppProtocolStatusEntry 6 }


    fmsPppProtoBrdgNcpDiag OBJECT-TYPE
        SYNTAX  INTEGER {
                ok(1),
                timeOut(2),
                underlyingLayerDown(3),
                protocol(4),
                rejected(5)
                }
        ACCESS  read-only
        STATUS  mandatory
        DESCRIPTION
                "The value of this object is the Bridge NCP layer
                diagnostic report."
        ::= { fmStatPppProtocolStatusEntry 7 }


    fmsPppProtoIpxNcpStatus OBJECT-TYPE
        SYNTAX  INTEGER {
                stop(1),
                wait(2),
                opening(3),
                up(4),
                down(5),
                closed(6),
                freeze(7)
                }
        ACCESS  read-only
        STATUS  mandatory
        DESCRIPTION
                "The value of this object is the current state of
                the IPX NCP layer."
        ::= { fmStatPppProtocolStatusEntry 8 }


    fmsPppProtoIpxNcpDiag OBJECT-TYPE
        SYNTAX  INTEGER {
                ok(1),
                timeOut(2),
                underlyingLayerDown(3),
                protocol(4),
                rejected(5)
                }
        ACCESS  read-only
        STATUS  mandatory
        DESCRIPTION
                "The value of this object is the IPX NCP layer
                diagnostic report."
        ::= { fmStatPppProtocolStatusEntry 9 }


    fmsPppProtoClnpNcpStatus OBJECT-TYPE
        SYNTAX  INTEGER {
                stop(1),
                wait(2),
                opening(3),
                up(4),
                down(5),
                closed(6),
                freeze(7)
                }
        ACCESS  read-only
        STATUS  mandatory
        DESCRIPTION
                "The value of this object is the current state of
                the CLNP NCP layer."
        ::= { fmStatPppProtocolStatusEntry 10 }


    fmsPppProtoClnpNcpDiag OBJECT-TYPE
        SYNTAX  INTEGER {
                ok(1),
                timeOut(2),
                underlyingLayerDown(3),
                protocol(4),
                rejected(5)
                }
        ACCESS  read-only
        STATUS  mandatory
        DESCRIPTION
                "The value of this object is the CLNP NCP layer
                diagnostic report."
        ::= { fmStatPppProtocolStatusEntry 11 }


    fmStatPppAuthenticationTable OBJECT-TYPE
        SYNTAX  SEQUENCE OF FmStatPppAuthenticationEntry
        ACCESS  not-accessible
        STATUS  mandatory
        DESCRIPTION
                ""
        ::= { fmStatPointToPointProtocol 10 }


    fmStatPppAuthenticationEntry OBJECT-TYPE
        SYNTAX  FmStatPppAuthenticationEntry
        ACCESS  not-accessible
        STATUS  mandatory
        DESCRIPTION
                "An entry of fmStatPppAuthenticationTable."
        INDEX   { fmsPppAuthLineId }
        ::= { fmStatPppAuthenticationTable 1 }


        FmStatPppAuthenticationEntry ::=
                SEQUENCE {
                    fmsPppAuthLineId
                        INTEGER,
                    fmsPppAuthMasterAuthentication
                        INTEGER,
                    fmsPppAuthMasterSuccessCounter
                        Counter,
                    fmsPppAuthMasterFailureCounter
                        Counter,
                    fmsPppAuthSlaveAuthentication
                        INTEGER,
                    fmsPppAuthSlaveSuccessCounter
                        Counter,
                    fmsPppAuthSlaveFailureCounter
                        Counter
                }


    fmsPppAuthLineId OBJECT-TYPE
        SYNTAX  INTEGER (0..35)
        ACCESS  read-only
        STATUS  mandatory
        DESCRIPTION
                "Numero de la ligne PPP."
        ::= { fmStatPppAuthenticationEntry 1 }


    fmsPppAuthMasterAuthentication OBJECT-TYPE
        SYNTAX  INTEGER {
                none(1),
                pap(2),
                chap(3)
                }
        ACCESS  read-only
        STATUS  mandatory
        DESCRIPTION
                "Authentifieur : Protocole d'authentification."
        ::= { fmStatPppAuthenticationEntry 10 }


    fmsPppAuthMasterSuccessCounter OBJECT-TYPE
        SYNTAX  Counter
        ACCESS  read-only
        STATUS  mandatory
        DESCRIPTION
                "Authentifieur : Nb d'authentifications reussies."
        ::= { fmStatPppAuthenticationEntry 11 }


    fmsPppAuthMasterFailureCounter OBJECT-TYPE
        SYNTAX  Counter
        ACCESS  read-only
        STATUS  mandatory
        DESCRIPTION
                "Authentifieur : Nb d'authentifications echouees."
        ::= { fmStatPppAuthenticationEntry 12 }


    fmsPppAuthSlaveAuthentication OBJECT-TYPE
        SYNTAX  INTEGER {
                none(1),
                pap(2),
                chap(3)
                }
        ACCESS  read-only
        STATUS  mandatory
        DESCRIPTION
                "Authentifie : Protocole d'authentification."
        ::= { fmStatPppAuthenticationEntry 20 }


    fmsPppAuthSlaveSuccessCounter OBJECT-TYPE
        SYNTAX  Counter
        ACCESS  read-only
        STATUS  mandatory
        DESCRIPTION
                "Authentifie : Nb d'authentifications reussies."
        ::= { fmStatPppAuthenticationEntry 21 }


    fmsPppAuthSlaveFailureCounter OBJECT-TYPE
        SYNTAX  Counter
        ACCESS  read-only
        STATUS  mandatory
        DESCRIPTION
                "Authentifie : Nb d'authentifications echouees."
        ::= { fmStatPppAuthenticationEntry 22 }


    fmStatPppIpAddrAssignmentTable OBJECT-TYPE
        SYNTAX  SEQUENCE OF FmStatPppIpAddrAssignmentEntry
        ACCESS  not-accessible
        STATUS  mandatory
        DESCRIPTION
                ""
        ::= { fmStatPointToPointProtocol 11 }


    fmStatPppIpAddrAssignmentEntry OBJECT-TYPE
        SYNTAX  FmStatPppIpAddrAssignmentEntry
        ACCESS  not-accessible
        STATUS  mandatory
        DESCRIPTION
                "An entry of fmStatPppIpAddrAssignmentTable."
        INDEX   { fmsPppIpAddrLineId }
        ::= { fmStatPppIpAddrAssignmentTable 1 }


        FmStatPppIpAddrAssignmentEntry ::=
                SEQUENCE {
                    fmsPppIpAddrLineId
                        INTEGER,
                    fmsPppIpAddrReceived
                        IpAddress,
                    fmsPppIpAddrSent
                        IpAddress
                }


    fmsPppIpAddrLineId OBJECT-TYPE
        SYNTAX  INTEGER (0..35)
        ACCESS  read-only
        STATUS  mandatory
        DESCRIPTION
                "Numero de la ligne PPP."
        ::= { fmStatPppIpAddrAssignmentEntry 1 }


    fmsPppIpAddrReceived OBJECT-TYPE
        SYNTAX  IpAddress
        ACCESS  read-only
        STATUS  mandatory
        DESCRIPTION
                "Adresse IP recue."
        ::= { fmStatPppIpAddrAssignmentEntry 10 }


    fmsPppIpAddrSent OBJECT-TYPE
        SYNTAX  IpAddress
        ACCESS  read-only
        STATUS  mandatory
        DESCRIPTION
                "Adresse IP attribuee."
        ::= { fmStatPppIpAddrAssignmentEntry 11 }


    fmStatE1 OBJECT IDENTIFIER ::= { fmStat 80 }


    fmStatE1Ds1ChannelNumber OBJECT IDENTIFIER ::= { fmStatE1 1 }


    fmsE1Ds1ChIfNumber OBJECT-TYPE
        SYNTAX  INTEGER (0..60)
        ACCESS  read-only
        STATUS  mandatory
        DESCRIPTION
                "Nombre de canaux E1 ou DS1"
        ::= { fmStatE1Ds1ChannelNumber 1 }


    fmStatE1Ds1ChannelTable OBJECT-TYPE
        SYNTAX  SEQUENCE OF FmStatE1Ds1ChannelEntry
        ACCESS  not-accessible
        STATUS  mandatory
        DESCRIPTION
                "This table contains"
        ::= { fmStatE1 2 }


    fmStatE1Ds1ChannelEntry OBJECT-TYPE
        SYNTAX  FmStatE1Ds1ChannelEntry
        ACCESS  not-accessible
        STATUS  mandatory
        DESCRIPTION
                "An entry of fmStatE1Ds1ChannelTable."
        INDEX   { fmsE1Ds1ChIfPhysId,
                  fmsE1Ds1ChIfChannelId }
        ::= { fmStatE1Ds1ChannelTable 1 }


        FmStatE1Ds1ChannelEntry ::=
                SEQUENCE {
                    fmsE1Ds1ChIfPhysId
                        INTEGER,
                    fmsE1Ds1ChIfChannelId
                        INTEGER,
                    fmsE1Ds1ChIfType
                        INTEGER,
                    fmsE1Ds1ChIfDescr
                        DisplayString,
                    fmsE1Ds1ChIfMtu
                        INTEGER,
                    fmsE1Ds1ChIfSpeed
                        INTEGER,
                    fmsE1Ds1ChIfPhysAddress
                        OCTET STRING,
                    fmsE1Ds1ChIfAdminStatus
                        INTEGER,
                    fmsE1Ds1ChIfOperStatus
                        INTEGER,
                    fmsE1Ds1ChIfLastChange
                        TimeTicks,
                    fmsE1Ds1ChIfInOctets
                        Counter,
                    fmsE1Ds1ChIfInUcastPkts
                        Counter,
                    fmsE1Ds1ChIfInNUcastPkts
                        Counter,
                    fmsE1Ds1ChIfInDiscards
                        Counter,
                    fmsE1Ds1ChIfInErrors
                        Counter,
                    fmsE1Ds1ChIfInUnknownProtos
                        Counter,
                    fmsE1Ds1ChIfOutOctets
                        Counter,
                    fmsE1Ds1ChIfOutUcastPkts
                        Counter,
                    fmsE1Ds1ChIfOutNUcastPkts
                        Counter,
                    fmsE1Ds1ChIfOutDiscards
                        Counter,
                    fmsE1Ds1ChIfOutErrors
                        Counter,
                    fmsE1Ds1ChIfOutQLen
                        Gauge,
                    fmsE1Ds1ChIfSpecific
                        INTEGER
                }


    fmsE1Ds1ChIfPhysId OBJECT-TYPE
        SYNTAX  INTEGER (0..35)
        ACCESS  read-only
        STATUS  mandatory
        DESCRIPTION
                "Interface physique E1"
        ::= { fmStatE1Ds1ChannelEntry 1 }


    fmsE1Ds1ChIfChannelId OBJECT-TYPE
        SYNTAX  INTEGER (42..131)
        ACCESS  read-only
        STATUS  mandatory
        DESCRIPTION
                "Interface canal E1"
        ::= { fmStatE1Ds1ChannelEntry 2 }


    fmsE1Ds1ChIfType OBJECT-TYPE
        SYNTAX  INTEGER {
                other(1),
                rfc877-x25(5),
                ppp(23),
                frame-relay(32),
                hdlc-t(100)
                }
        ACCESS  read-only
        STATUS  mandatory
        DESCRIPTION
                "Type de l'interface"
        ::= { fmStatE1Ds1ChannelEntry 3 }


    fmsE1Ds1ChIfDescr OBJECT-TYPE
        SYNTAX  DisplayString (SIZE(0..80))
        ACCESS  read-only
        STATUS  mandatory
        DESCRIPTION
                "Description"
        ::= { fmStatE1Ds1ChannelEntry 4 }


    fmsE1Ds1ChIfMtu OBJECT-TYPE
        SYNTAX  INTEGER (0..4294967295)
        ACCESS  read-only
        STATUS  mandatory
        DESCRIPTION
                "Taille maximum d'une trame"
        ::= { fmStatE1Ds1ChannelEntry 5 }


    fmsE1Ds1ChIfSpeed OBJECT-TYPE
        SYNTAX  INTEGER (0..4294967295)
        ACCESS  read-only
        STATUS  mandatory
        DESCRIPTION
                "Debit de l'interface"
        ::= { fmStatE1Ds1ChannelEntry 6 }


    fmsE1Ds1ChIfPhysAddress OBJECT-TYPE
        SYNTAX  OCTET STRING (SIZE(6))
        ACCESS  read-only
        STATUS  mandatory
        DESCRIPTION
                "Adresse physique"
        ::= { fmStatE1Ds1ChannelEntry 7 }


    fmsE1Ds1ChIfAdminStatus OBJECT-TYPE
        SYNTAX  INTEGER {
                up(1),
                down(2),
                testing(3)
                }
        ACCESS  read-write
        STATUS  mandatory
        DESCRIPTION
                "Etat desire de l'interface"
        ::= { fmStatE1Ds1ChannelEntry 8 }


    fmsE1Ds1ChIfOperStatus OBJECT-TYPE
        SYNTAX  INTEGER {
                up(1),
                down(2),
                testing(3)
                }
        ACCESS  read-only
        STATUS  mandatory
        DESCRIPTION
                "Etat operationnel de l'interface"
        ::= { fmStatE1Ds1ChannelEntry 9 }


    fmsE1Ds1ChIfLastChange OBJECT-TYPE
        SYNTAX  TimeTicks
        ACCESS  read-only
        STATUS  mandatory
        DESCRIPTION
                "Valeur de sysUpTime au moment ou l'interface est
                passe dans l'etat operationnel courant"
        ::= { fmStatE1Ds1ChannelEntry 10 }


    fmsE1Ds1ChIfInOctets OBJECT-TYPE
        SYNTAX  Counter
        ACCESS  read-only
        STATUS  mandatory
        DESCRIPTION
                "Nombre d'octets recus"
        ::= { fmStatE1Ds1ChannelEntry 11 }


    fmsE1Ds1ChIfInUcastPkts OBJECT-TYPE
        SYNTAX  Counter
        ACCESS  read-only
        STATUS  mandatory
        DESCRIPTION
                "Nombre de paquets Unicast recus"
        ::= { fmStatE1Ds1ChannelEntry 12 }


    fmsE1Ds1ChIfInNUcastPkts OBJECT-TYPE
        SYNTAX  Counter
        ACCESS  read-only
        STATUS  mandatory
        DESCRIPTION
                "Nombre de paquets non Unicast recus"
        ::= { fmStatE1Ds1ChannelEntry 13 }


    fmsE1Ds1ChIfInDiscards OBJECT-TYPE
        SYNTAX  Counter
        ACCESS  read-only
        STATUS  mandatory
        DESCRIPTION
                "Nombre de paquets recus detruits"
        ::= { fmStatE1Ds1ChannelEntry 14 }


    fmsE1Ds1ChIfInErrors OBJECT-TYPE
        SYNTAX  Counter
        ACCESS  read-only
        STATUS  mandatory
        DESCRIPTION
                "Nombre de paquets recus en erreur"
        ::= { fmStatE1Ds1ChannelEntry 15 }


    fmsE1Ds1ChIfInUnknownProtos OBJECT-TYPE
        SYNTAX  Counter
        ACCESS  read-only
        STATUS  mandatory
        DESCRIPTION
                "Nombre de paquets recus avec protocole inconnu"
        ::= { fmStatE1Ds1ChannelEntry 16 }


    fmsE1Ds1ChIfOutOctets OBJECT-TYPE
        SYNTAX  Counter
        ACCESS  read-only
        STATUS  mandatory
        DESCRIPTION
                "Nombre d'octets emis"
        ::= { fmStatE1Ds1ChannelEntry 17 }


    fmsE1Ds1ChIfOutUcastPkts OBJECT-TYPE
        SYNTAX  Counter
        ACCESS  read-only
        STATUS  mandatory
        DESCRIPTION
                "Nombre de paquets Unicast emis"
        ::= { fmStatE1Ds1ChannelEntry 18 }


    fmsE1Ds1ChIfOutNUcastPkts OBJECT-TYPE
        SYNTAX  Counter
        ACCESS  read-only
        STATUS  mandatory
        DESCRIPTION
                "Nombre de paquets non Unicast emis"
        ::= { fmStatE1Ds1ChannelEntry 19 }


    fmsE1Ds1ChIfOutDiscards OBJECT-TYPE
        SYNTAX  Counter
        ACCESS  read-only
        STATUS  mandatory
        DESCRIPTION
                "Nombre de paquets emis detruits"
        ::= { fmStatE1Ds1ChannelEntry 20 }


    fmsE1Ds1ChIfOutErrors OBJECT-TYPE
        SYNTAX  Counter
        ACCESS  read-only
        STATUS  mandatory
        DESCRIPTION
                "Nombre de paquets emis en erreur"
        ::= { fmStatE1Ds1ChannelEntry 21 }


    fmsE1Ds1ChIfOutQLen OBJECT-TYPE
        SYNTAX  Gauge
        ACCESS  read-only
        STATUS  mandatory
        DESCRIPTION
                "Longueur de la file des paquets emis"
        ::= { fmStatE1Ds1ChannelEntry 22 }


    fmsE1Ds1ChIfSpecific OBJECT-TYPE
        SYNTAX  INTEGER (0..4294967295)
        ACCESS  read-only
        STATUS  mandatory
        DESCRIPTION
                "OID de la MIB de reference"
        ::= { fmStatE1Ds1ChannelEntry 23 }


    fmStatS2 OBJECT IDENTIFIER ::= { fmStat 90 }


    fmStatS2BChannelTable OBJECT-TYPE
        SYNTAX  SEQUENCE OF FmStatS2BChannelEntry
        ACCESS  not-accessible
        STATUS  mandatory
        DESCRIPTION
                ""
        ::= { fmStatS2 1 }


    fmStatS2BChannelEntry OBJECT-TYPE
        SYNTAX  FmStatS2BChannelEntry
        ACCESS  not-accessible
        STATUS  mandatory
        DESCRIPTION
                "An entry of fmStatS2BChannelTable."
        INDEX   { fmsS2BChPhysIfId,
                  fmsS2BChChannelId }
        ::= { fmStatS2BChannelTable 1 }


        FmStatS2BChannelEntry ::=
                SEQUENCE {
                    fmsS2BChPhysIfId
                        INTEGER,
                    fmsS2BChChannelId
                        INTEGER,
                    fmsS2BChProto
                        INTEGER,
                    fmsS2BChIfSpeed
                        INTEGER,
                    fmsS2BChAdminStatus
                        INTEGER,
                    fmsS2BChOperStatus
                        INTEGER,
                    fmsS2BChIfLastChange
                        TimeTicks,
                    fmsS2BChIfInOctets
                        Counter,
                    fmsS2BChIfOutOctets
                        Counter,
                    fmsS2BChIfCalledAddress
                        OCTET STRING,
                    fmsS2BChIfCallingAddress
                        OCTET STRING
                }


    fmsS2BChPhysIfId OBJECT-TYPE
        SYNTAX  INTEGER (0..35)
        ACCESS  read-only
        STATUS  mandatory
        DESCRIPTION
                "Interface physique associee au canal"
        ::= { fmStatS2BChannelEntry 1 }


    fmsS2BChChannelId OBJECT-TYPE
        SYNTAX  INTEGER (1..30)
        ACCESS  read-only
        STATUS  mandatory
        DESCRIPTION
                "Numero de canal"
        ::= { fmStatS2BChannelEntry 2 }


    fmsS2BChProto OBJECT-TYPE
        SYNTAX  INTEGER {
                other(1),
                rfc877-x25(5),
                ppp(23),
                frame-relay(32)
                }
        ACCESS  read-only
        STATUS  mandatory
        DESCRIPTION
                "Protocole associe au canal"
        ::= { fmStatS2BChannelEntry 3 }


    fmsS2BChIfSpeed OBJECT-TYPE
        SYNTAX  INTEGER (0..4294967295)
        ACCESS  read-only
        STATUS  mandatory
        DESCRIPTION
                "Debit du canal"
        ::= { fmStatS2BChannelEntry 4 }


    fmsS2BChAdminStatus OBJECT-TYPE
        SYNTAX  INTEGER {
                up(1),
                down(2),
                testing(3)
                }
        ACCESS  read-write
        STATUS  mandatory
        DESCRIPTION
                "Etat desire du canal"
        ::= { fmStatS2BChannelEntry 5 }


    fmsS2BChOperStatus OBJECT-TYPE
        SYNTAX  INTEGER {
                up(1),
                down(2),
                testing(3)
                }
        ACCESS  read-only
        STATUS  mandatory
        DESCRIPTION
                "Etat operationnel du canal"
        ::= { fmStatS2BChannelEntry 6 }


    fmsS2BChIfLastChange OBJECT-TYPE
        SYNTAX  TimeTicks
        ACCESS  read-only
        STATUS  mandatory
        DESCRIPTION
                "Valeur de sysUpTime au moment ou le canal est
                passe dans l'etat operationnel courant"
        ::= { fmStatS2BChannelEntry 7 }


    fmsS2BChIfInOctets OBJECT-TYPE
        SYNTAX  Counter
        ACCESS  read-only
        STATUS  mandatory
        DESCRIPTION
                "Nombre d'octets recus"
        ::= { fmStatS2BChannelEntry 8 }


    fmsS2BChIfOutOctets OBJECT-TYPE
        SYNTAX  Counter
        ACCESS  read-only
        STATUS  mandatory
        DESCRIPTION
                "Nombre d'octets emis"
        ::= { fmStatS2BChannelEntry 9 }


    fmsS2BChIfCalledAddress OBJECT-TYPE
        SYNTAX  OCTET STRING (SIZE(15))
        ACCESS  read-only
        STATUS  mandatory
        DESCRIPTION
                "Adresse appelee"
        ::= { fmStatS2BChannelEntry 10 }


    fmsS2BChIfCallingAddress OBJECT-TYPE
        SYNTAX  OCTET STRING (SIZE(15))
        ACCESS  read-only
        STATUS  mandatory
        DESCRIPTION
                "Adresse appelante"
        ::= { fmStatS2BChannelEntry 11 }


    fmStatS0 OBJECT IDENTIFIER ::= { fmStat 91 }


    fmStatS0BChannelTable OBJECT-TYPE
        SYNTAX  SEQUENCE OF FmStatS0BChannelEntry
        ACCESS  not-accessible
        STATUS  mandatory
        DESCRIPTION
                ""
        ::= { fmStatS0 1 }


    fmStatS0BChannelEntry OBJECT-TYPE
        SYNTAX  FmStatS0BChannelEntry
        ACCESS  not-accessible
        STATUS  mandatory
        DESCRIPTION
                "An entry of fmStatS0BChannelTable."
        INDEX   { fmsS0BChPhysIfId,
                  fmsS0BChChannelId }
        ::= { fmStatS0BChannelTable 1 }


        FmStatS0BChannelEntry ::=
                SEQUENCE {
                    fmsS0BChPhysIfId
                        INTEGER,
                    fmsS0BChChannelId
                        INTEGER,
                    fmsS0BChProto
                        INTEGER,
                    fmsS0BChIfSpeed
                        INTEGER,
                    fmsS0BChAdminStatus
                        INTEGER,
                    fmsS0BChOperStatus
                        INTEGER,
                    fmsS0BChIfLastChange
                        TimeTicks,
                    fmsS0BChIfInOctets
                        Counter,
                    fmsS0BChIfOutOctets
                        Counter,
                    fmsS0BChIfCalledAddress
                        OCTET STRING,
                    fmsS0BChIfCallingAddress
                        OCTET STRING
                }


    fmsS0BChPhysIfId OBJECT-TYPE
        SYNTAX  INTEGER (0..6)
        ACCESS  read-only
        STATUS  mandatory
        DESCRIPTION
                "The value of this object is the number of the
                physical port the basic rate interface B channel
                is related to."
        ::= { fmStatS0BChannelEntry 1 }


    fmsS0BChChannelId OBJECT-TYPE
        SYNTAX  INTEGER (1..9)
        ACCESS  read-only
        STATUS  mandatory
        DESCRIPTION
                "The value of this object is the identification
                number of the basic rate interface B channel."
        ::= { fmStatS0BChannelEntry 2 }


    fmsS0BChProto OBJECT-TYPE
        SYNTAX  INTEGER {
                other(1),
                rfc877-x25(5),
                ppp(23),
                frame-relay(32)
                }
        ACCESS  read-only
        STATUS  mandatory
        DESCRIPTION
                "The value of this object is the protocol related
                to the basic rate interface B channel."
        ::= { fmStatS0BChannelEntry 3 }


    fmsS0BChIfSpeed OBJECT-TYPE
        SYNTAX  INTEGER (0..4294967295)
        ACCESS  read-only
        STATUS  mandatory
        DESCRIPTION
                "The value of this object is the speed of the basic
                rate interface B channel."
        ::= { fmStatS0BChannelEntry 4 }


    fmsS0BChAdminStatus OBJECT-TYPE
        SYNTAX  INTEGER {
                up(1),
                down(2),
                testing(3)
                }
        ACCESS  read-write
        STATUS  mandatory
        DESCRIPTION
                "The value of this object is the operational state
                wanted for the basic rate interface B channel."
        ::= { fmStatS0BChannelEntry 5 }


    fmsS0BChOperStatus OBJECT-TYPE
        SYNTAX  INTEGER {
                up(1),
                down(2),
                testing(3)
                }
        ACCESS  read-only
        STATUS  mandatory
        DESCRIPTION
                "The value of this object is the current
                operational state of the basic rate interface B
                channel."
        ::= { fmStatS0BChannelEntry 6 }


    fmsS0BChIfLastChange OBJECT-TYPE
        SYNTAX  TimeTicks
        ACCESS  read-only
        STATUS  mandatory
        DESCRIPTION
                "The value of this object is the value of the
                sysUpTime at the time when the basic rate
                interface B channel took its current operational
                state."
        ::= { fmStatS0BChannelEntry 7 }


    fmsS0BChIfInOctets OBJECT-TYPE
        SYNTAX  Counter
        ACCESS  read-only
        STATUS  mandatory
        DESCRIPTION
                "The value of this object is the number of bytes
                received on the basic rate interface B channel."
        ::= { fmStatS0BChannelEntry 8 }


    fmsS0BChIfOutOctets OBJECT-TYPE
        SYNTAX  Counter
        ACCESS  read-only
        STATUS  mandatory
        DESCRIPTION
                "The value of this object is the number of bytes
                sent on the basic rate interface B channel."
        ::= { fmStatS0BChannelEntry 9 }


    fmsS0BChIfCalledAddress OBJECT-TYPE
        SYNTAX  OCTET STRING (SIZE(15))
        ACCESS  read-only
        STATUS  mandatory
        DESCRIPTION
                "The value of this object is the called address."
        ::= { fmStatS0BChannelEntry 10 }


    fmsS0BChIfCallingAddress OBJECT-TYPE
        SYNTAX  OCTET STRING (SIZE(15))
        ACCESS  read-only
        STATUS  mandatory
        DESCRIPTION
                "The value of this object is the caller address."
        ::= { fmStatS0BChannelEntry 11 }


    fmOsi OBJECT IDENTIFIER ::= { frxManagement 15 }


    fmOsiCLNP OBJECT IDENTIFIER ::= { fmOsi 1 }


    fmOsiCLNPSystem OBJECT IDENTIFIER ::= { fmOsiCLNP 1 }


    fmOsiForwarding OBJECT-TYPE
        SYNTAX  INTEGER {
                off(1),
                on(2)
                }
        ACCESS  read-only
        STATUS  mandatory
        DESCRIPTION
                "Forwarding"
        ::= { fmOsiCLNPSystem 20 }


    fmOsiCLNPSysOutPDUs OBJECT-TYPE
        SYNTAX  Counter
        ACCESS  read-only
        STATUS  mandatory
        DESCRIPTION
                "clnpSysOutPDUs"
        ::= { fmOsiCLNPSystem 30 }


    fmOsiCLNPSysInPDUs OBJECT-TYPE
        SYNTAX  Counter
        ACCESS  read-only
        STATUS  mandatory
        DESCRIPTION
                "clnpSysInPDUs"
        ::= { fmOsiCLNPSystem 35 }


    fmOsiCLNPSysErrMemFails OBJECT-TYPE
        SYNTAX  Counter
        ACCESS  read-only
        STATUS  mandatory
        DESCRIPTION
                "clnpSysErrMemFails"
        ::= { fmOsiCLNPSystem 40 }


    fmOsiCLNPCircuitTable OBJECT-TYPE
        SYNTAX  SEQUENCE OF FmOsiCLNPCircuitEntry
        ACCESS  not-accessible
        STATUS  mandatory
        DESCRIPTION
                ""
        ::= { fmOsiCLNP 5 }


    fmOsiCLNPCircuitEntry OBJECT-TYPE
        SYNTAX  FmOsiCLNPCircuitEntry
        ACCESS  not-accessible
        STATUS  mandatory
        DESCRIPTION
                "An entry of fmOsiCLNPCircuitTable."
        INDEX   { fmOsiCLNPCircIndex }
        ::= { fmOsiCLNPCircuitTable 1 }


        FmOsiCLNPCircuitEntry ::=
                SEQUENCE {
                    fmOsiCLNPCircIndex
                        INTEGER,
                    fmOsiCLNPCircOutPDUs
                        Counter,
                    fmOsiCLNPCircInPDUs
                        Counter
                }


    fmOsiCLNPCircIndex OBJECT-TYPE
        SYNTAX  INTEGER (1..60)
        ACCESS  read-only
        STATUS  mandatory
        DESCRIPTION
                "clnpCircIndex"
        ::= { fmOsiCLNPCircuitEntry 1 }


    fmOsiCLNPCircOutPDUs OBJECT-TYPE
        SYNTAX  Counter
        ACCESS  read-only
        STATUS  mandatory
        DESCRIPTION
                "clnpCircOutPDUs"
        ::= { fmOsiCLNPCircuitEntry 35 }


    fmOsiCLNPCircInPDUs OBJECT-TYPE
        SYNTAX  Counter
        ACCESS  read-only
        STATUS  mandatory
        DESCRIPTION
                "clnpCircInPDUs"
        ::= { fmOsiCLNPCircuitEntry 40 }


    fmOsiESIS OBJECT IDENTIFIER ::= { fmOsi 5 }


    fmOsiESISSystem OBJECT IDENTIFIER ::= { fmOsiESIS 1 }


    fmOsiESISSysOutPDUs OBJECT-TYPE
        SYNTAX  Counter
        ACCESS  read-only
        STATUS  mandatory
        DESCRIPTION
                "esisSysOutPDUs"
        ::= { fmOsiESISSystem 30 }


    fmOsiESISSysInPDUs OBJECT-TYPE
        SYNTAX  Counter
        ACCESS  read-only
        STATUS  mandatory
        DESCRIPTION
                "esisSysInPDUs"
        ::= { fmOsiESISSystem 35 }


    fmOsiESISCircuitTable OBJECT-TYPE
        SYNTAX  SEQUENCE OF FmOsiESISCircuitEntry
        ACCESS  not-accessible
        STATUS  mandatory
        DESCRIPTION
                ""
        ::= { fmOsiESIS 5 }


    fmOsiESISCircuitEntry OBJECT-TYPE
        SYNTAX  FmOsiESISCircuitEntry
        ACCESS  not-accessible
        STATUS  mandatory
        DESCRIPTION
                "An entry of fmOsiESISCircuitTable."
        INDEX   { fmOsiESISCircIndex }
        ::= { fmOsiESISCircuitTable 1 }


        FmOsiESISCircuitEntry ::=
                SEQUENCE {
                    fmOsiESISCircIndex
                        INTEGER,
                    fmOsiESISCircOutPDUs
                        Counter,
                    fmOsiESISCircInPDUs
                        Counter
                }


    fmOsiESISCircIndex OBJECT-TYPE
        SYNTAX  INTEGER (1..60)
        ACCESS  read-only
        STATUS  mandatory
        DESCRIPTION
                "esisCircIndex"
        ::= { fmOsiESISCircuitEntry 1 }


    fmOsiESISCircOutPDUs OBJECT-TYPE
        SYNTAX  Counter
        ACCESS  read-only
        STATUS  mandatory
        DESCRIPTION
                "esisCircOutPDUs"
        ::= { fmOsiESISCircuitEntry 35 }


    fmOsiESISCircInPDUs OBJECT-TYPE
        SYNTAX  Counter
        ACCESS  read-only
        STATUS  mandatory
        DESCRIPTION
                "esisCircInPDUs"
        ::= { fmOsiESISCircuitEntry 40 }


    fmOsiISIS OBJECT IDENTIFIER ::= { fmOsi 10 }


    fmOsiISISSystem OBJECT IDENTIFIER ::= { fmOsiISIS 1 }


    fmOsiISISSysOutPdu OBJECT-TYPE
        SYNTAX  Counter
        ACCESS  read-only
        STATUS  mandatory
        DESCRIPTION
                "isisSysOutPDUs"
        ::= { fmOsiISISSystem 30 }


    fmOsiISISSysInPdu OBJECT-TYPE
        SYNTAX  Counter
        ACCESS  read-only
        STATUS  mandatory
        DESCRIPTION
                "isisSysInPDUs"
        ::= { fmOsiISISSystem 33 }


    fmOsiISISSysL1State OBJECT-TYPE
        SYNTAX  INTEGER {
                off(1),
                on(2),
                waiting(3)
                }
        ACCESS  read-only
        STATUS  mandatory
        DESCRIPTION
                "isisSysL1State"
        ::= { fmOsiISISSystem 35 }


    fmOsiISISSysCorrLSP OBJECT-TYPE
        SYNTAX  Counter
        ACCESS  read-only
        STATUS  mandatory
        DESCRIPTION
                "isisSysCorrLSPs"
        ::= { fmOsiISISSystem 37 }


    fmOsiISISSysL1DbaseOloads OBJECT-TYPE
        SYNTAX  Counter
        ACCESS  read-only
        STATUS  mandatory
        DESCRIPTION
                "isisSysLSPL1DbaseOloads"
        ::= { fmOsiISISSystem 40 }


    fmOsiISISSysttmpToExMaxSaqNums OBJECT-TYPE
        SYNTAX  Counter
        ACCESS  read-only
        STATUS  mandatory
        DESCRIPTION
                "isisSysAttmptToExMaxSeqNums"
        ::= { fmOsiISISSystem 42 }


    fmOsiISISSysSeqNumSkips OBJECT-TYPE
        SYNTAX  Counter
        ACCESS  read-only
        STATUS  mandatory
        DESCRIPTION
                "isisSysSeqNumSkips"
        ::= { fmOsiISISSystem 44 }


    fmOsiISISSysOwnLSPPurges OBJECT-TYPE
        SYNTAX  Counter
        ACCESS  read-only
        STATUS  mandatory
        DESCRIPTION
                "isisSysOwnLSPPurges"
        ::= { fmOsiISISSystem 46 }


    fmOsiISISSysISFieldLenMismatches OBJECT-TYPE
        SYNTAX  Counter
        ACCESS  read-only
        STATUS  mandatory
        DESCRIPTION
                "isisSysIDFieldLenMismatches"
        ::= { fmOsiISISSystem 48 }


    fmOsiISISSysMaxAreaAddrMismatches OBJECT-TYPE
        SYNTAX  Counter
        ACCESS  read-only
        STATUS  mandatory
        DESCRIPTION
                "isisSysMaxAreaAddrMismatches"
        ::= { fmOsiISISSystem 50 }


    fmOsiISISSysL2State OBJECT-TYPE
        SYNTAX  INTEGER {
                off(1),
                on(2),
                waiting(3)
                }
        ACCESS  read-only
        STATUS  mandatory
        DESCRIPTION
                "isisSysL2State"
        ::= { fmOsiISISSystem 52 }


    fmOsiISISSysLSPL2DbaseOloads OBJECT-TYPE
        SYNTAX  Counter
        ACCESS  read-only
        STATUS  mandatory
        DESCRIPTION
                "isisSysLSPL2DbaseOloads"
        ::= { fmOsiISISSystem 54 }


    fmOsiISISSysAuthFails OBJECT-TYPE
        SYNTAX  Counter
        ACCESS  read-only
        STATUS  mandatory
        DESCRIPTION
                "isisSysAuthFails"
        ::= { fmOsiISISSystem 56 }


    fmOsiISISLogAdjcencyStateChanges OBJECT-TYPE
        SYNTAX  Counter
        ACCESS  read-write
        STATUS  mandatory
        DESCRIPTION
                "isisLogAdjacencyStateChanges"
        ::= { fmOsiISISSystem 58 }


    fmOsiISISCircuitTable OBJECT-TYPE
        SYNTAX  SEQUENCE OF FmOsiISISCircuitEntry
        ACCESS  not-accessible
        STATUS  mandatory
        DESCRIPTION
                ""
        ::= { fmOsiISIS 5 }


    fmOsiISISCircuitEntry OBJECT-TYPE
        SYNTAX  FmOsiISISCircuitEntry
        ACCESS  not-accessible
        STATUS  mandatory
        DESCRIPTION
                "An entry of fmOsiISISCircuitTable."
        INDEX   { fmOsiISISCircIndex }
        ::= { fmOsiISISCircuitTable 1 }


        FmOsiISISCircuitEntry ::=
                SEQUENCE {
                    fmOsiISISCircIndex
                        INTEGER,
                    fmOsiISISCircOutPdu
                        Counter,
                    fmOsiISISCircInPdu
                        Counter,
                    fmOsiISISCircAdjChanges
                        Counter,
                    fmOsiISISCircInitFails
                        Counter,
                    fmOsiISISCircRejAdjs
                        Counter,
                    fmOsiISISCircOutCtrlPdu
                        Counter,
                    fmOsiISISCircInCrtlPdu
                        Counter,
                    fmOsiISISCircIDFieldLenMismatches
                        Counter,
                    fmOsiISISCircMaxAreaAddrMismatches
                        Counter,
                    fmOsiISISCircL1DesIS
                        DisplayString,
                    fmOsiISISCircLANL1DesISChanges
                        Counter,
                    fmOsiISISCircL2DesIS
                        DisplayString,
                    fmOsiISISCircLANL2DesISChanges
                        Counter,
                    fmOsiISISCircAuthFails
                        Counter
                }


    fmOsiISISCircIndex OBJECT-TYPE
        SYNTAX  INTEGER (1..60)
        ACCESS  read-only
        STATUS  mandatory
        DESCRIPTION
                "isisCircIndex"
        ::= { fmOsiISISCircuitEntry 1 }


    fmOsiISISCircOutPdu OBJECT-TYPE
        SYNTAX  Counter
        ACCESS  read-only
        STATUS  mandatory
        DESCRIPTION
                "isisCircOutPDUs"
        ::= { fmOsiISISCircuitEntry 30 }


    fmOsiISISCircInPdu OBJECT-TYPE
        SYNTAX  Counter
        ACCESS  read-only
        STATUS  mandatory
        DESCRIPTION
                "isisCircInPDUs"
        ::= { fmOsiISISCircuitEntry 35 }


    fmOsiISISCircAdjChanges OBJECT-TYPE
        SYNTAX  Counter
        ACCESS  read-only
        STATUS  mandatory
        DESCRIPTION
                "isisCircAdjChanges"
        ::= { fmOsiISISCircuitEntry 40 }


    fmOsiISISCircInitFails OBJECT-TYPE
        SYNTAX  Counter
        ACCESS  read-only
        STATUS  mandatory
        DESCRIPTION
                "isisCircInitFails"
        ::= { fmOsiISISCircuitEntry 42 }


    fmOsiISISCircRejAdjs OBJECT-TYPE
        SYNTAX  Counter
        ACCESS  read-only
        STATUS  mandatory
        DESCRIPTION
                "isisCircRejAdjs"
        ::= { fmOsiISISCircuitEntry 44 }


    fmOsiISISCircOutCtrlPdu OBJECT-TYPE
        SYNTAX  Counter
        ACCESS  read-only
        STATUS  mandatory
        DESCRIPTION
                "isisCircOutCtrlPDUs"
        ::= { fmOsiISISCircuitEntry 46 }


    fmOsiISISCircInCrtlPdu OBJECT-TYPE
        SYNTAX  Counter
        ACCESS  read-only
        STATUS  mandatory
        DESCRIPTION
                "isisCircInCtrlPDUs"
        ::= { fmOsiISISCircuitEntry 48 }


    fmOsiISISCircIDFieldLenMismatches OBJECT-TYPE
        SYNTAX  Counter
        ACCESS  read-only
        STATUS  mandatory
        DESCRIPTION
                "isisCircIDFieldLenMismatches"
        ::= { fmOsiISISCircuitEntry 50 }


    fmOsiISISCircMaxAreaAddrMismatches OBJECT-TYPE
        SYNTAX  Counter
        ACCESS  read-only
        STATUS  mandatory
        DESCRIPTION
                "isisCircMaxAreaAddrMismatches"
        ::= { fmOsiISISCircuitEntry 52 }


    fmOsiISISCircL1DesIS OBJECT-TYPE
        SYNTAX  DisplayString (SIZE(0..12))
        ACCESS  read-only
        STATUS  mandatory
        DESCRIPTION
                "isisCircL1DesIS"
        ::= { fmOsiISISCircuitEntry 54 }


    fmOsiISISCircLANL1DesISChanges OBJECT-TYPE
        SYNTAX  Counter
        ACCESS  read-only
        STATUS  mandatory
        DESCRIPTION
                "isisCircLANL1DesISChanges"
        ::= { fmOsiISISCircuitEntry 56 }


    fmOsiISISCircL2DesIS OBJECT-TYPE
        SYNTAX  DisplayString (SIZE(0..12))
        ACCESS  read-only
        STATUS  mandatory
        DESCRIPTION
                "isisCircL2DesIS"
        ::= { fmOsiISISCircuitEntry 58 }


    fmOsiISISCircLANL2DesISChanges OBJECT-TYPE
        SYNTAX  Counter
        ACCESS  read-only
        STATUS  mandatory
        DESCRIPTION
                "isisCircLANL2DesISChanges"
        ::= { fmOsiISISCircuitEntry 60 }


    fmOsiISISCircAuthFails OBJECT-TYPE
        SYNTAX  Counter
        ACCESS  read-only
        STATUS  mandatory
        DESCRIPTION
                "isisCircAuthFails"
        ::= { fmOsiISISCircuitEntry 62 }


    fmOsiISISAreaTable OBJECT-TYPE
        SYNTAX  SEQUENCE OF FmOsiISISAreaEntry
        ACCESS  not-accessible
        STATUS  mandatory
        DESCRIPTION
                ""
        ::= { fmOsiISIS 10 }


    fmOsiISISAreaEntry OBJECT-TYPE
        SYNTAX  FmOsiISISAreaEntry
        ACCESS  not-accessible
        STATUS  mandatory
        DESCRIPTION
                "An entry of fmOsiISISAreaTable."
        INDEX   { fmOsiISISAreaAddress }
        ::= { fmOsiISISAreaTable 1 }


        FmOsiISISAreaEntry ::=
                SEQUENCE {
                    fmOsiISISAreaAddress
                        DisplayString
                }


    fmOsiISISAreaAddress OBJECT-TYPE
        SYNTAX  DisplayString (SIZE(0..46))
        ACCESS  read-only
        STATUS  mandatory
        DESCRIPTION
                "Area Address"
        ::= { fmOsiISISAreaEntry 1 }


    fmOsiISISISAdjacencyTable OBJECT-TYPE
        SYNTAX  SEQUENCE OF FmOsiISISISAdjacencyEntry
        ACCESS  not-accessible
        STATUS  mandatory
        DESCRIPTION
                ""
        ::= { fmOsiISIS 15 }


    fmOsiISISISAdjacencyEntry OBJECT-TYPE
        SYNTAX  FmOsiISISISAdjacencyEntry
        ACCESS  not-accessible
        STATUS  mandatory
        DESCRIPTION
                "An entry of fmOsiISISISAdjacencyTable."
        INDEX   { fmOsiISISISAdjCircIndex,
                  fmOsiISISISAdjIndex }
        ::= { fmOsiISISISAdjacencyTable 1 }


        FmOsiISISISAdjacencyEntry ::=
                SEQUENCE {
                    fmOsiISISISAdjCircIndex
                        INTEGER,
                    fmOsiISISISAdjIndex
                        INTEGER,
                    fmOsiISISISAdjSysID
                        DisplayString,
                    fmOsiISISISAdjState
                        INTEGER,
                    fmOsiISISISAdjSNPAAddress
                        DisplayString,
                    fmOsiISISISAdjType
                        INTEGER,
                    fmOsiISISISAdjUsage
                        INTEGER,
                    fmOsiISISISAdjHoldTimer
                        INTEGER,
                    fmOsiISISISAdjPriority
                        INTEGER
                }


    fmOsiISISISAdjCircIndex OBJECT-TYPE
        SYNTAX  INTEGER (1..60)
        ACCESS  read-only
        STATUS  mandatory
        DESCRIPTION
                "Circuit Index"
        ::= { fmOsiISISISAdjacencyEntry 1 }


    fmOsiISISISAdjIndex OBJECT-TYPE
        SYNTAX  INTEGER (1..1024)
        ACCESS  read-only
        STATUS  mandatory
        DESCRIPTION
                "Adjacency Index"
        ::= { fmOsiISISISAdjacencyEntry 5 }


    fmOsiISISISAdjSysID OBJECT-TYPE
        SYNTAX  DisplayString (SIZE(0..8))
        ACCESS  read-only
        STATUS  mandatory
        DESCRIPTION
                "System ID"
        ::= { fmOsiISISISAdjacencyEntry 10 }


    fmOsiISISISAdjState OBJECT-TYPE
        SYNTAX  INTEGER {
                initializing(1),
                up(2),
                failed(3),
                down(4)
                }
        ACCESS  read-only
        STATUS  mandatory
        DESCRIPTION
                "State"
        ::= { fmOsiISISISAdjacencyEntry 12 }


    fmOsiISISISAdjSNPAAddress OBJECT-TYPE
        SYNTAX  DisplayString (SIZE(0..46))
        ACCESS  read-only
        STATUS  mandatory
        DESCRIPTION
                "SNPA Address"
        ::= { fmOsiISISISAdjacencyEntry 14 }


    fmOsiISISISAdjType OBJECT-TYPE
        SYNTAX  INTEGER {
                automatic(1),
                manual(2)
                }
        ACCESS  read-only
        STATUS  mandatory
        DESCRIPTION
                "Type"
        ::= { fmOsiISISISAdjacencyEntry 20 }


    fmOsiISISISAdjUsage OBJECT-TYPE
        SYNTAX  INTEGER {
                undefined(1),
                level1(2),
                level2(3),
                level1and2(4)
                }
        ACCESS  read-only
        STATUS  mandatory
        DESCRIPTION
                "Usage"
        ::= { fmOsiISISISAdjacencyEntry 22 }


    fmOsiISISISAdjHoldTimer OBJECT-TYPE
        SYNTAX  INTEGER (0..4294967295)
        ACCESS  read-only
        STATUS  mandatory
        DESCRIPTION
                "Holding Timer"
        ::= { fmOsiISISISAdjacencyEntry 26 }


    fmOsiISISISAdjPriority OBJECT-TYPE
        SYNTAX  INTEGER (1..127)
        ACCESS  read-only
        STATUS  mandatory
        DESCRIPTION
                "Priority"
        ::= { fmOsiISISISAdjacencyEntry 30 }


    fmOsiISISISAdjacencyAreaAddressTable OBJECT-TYPE
        SYNTAX  SEQUENCE OF FmOsiISISISAdjacencyAreaAddressEntry
        ACCESS  not-accessible
        STATUS  mandatory
        DESCRIPTION
                ""
        ::= { fmOsiISIS 17 }


    fmOsiISISISAdjacencyAreaAddressEntry OBJECT-TYPE
        SYNTAX  FmOsiISISISAdjacencyAreaAddressEntry
        ACCESS  not-accessible
        STATUS  mandatory
        DESCRIPTION
                "An entry of fmOsiISISISAdjacencyAreaAddressTable."
        INDEX   { fmOsiISISISAdjAreaAddrCircIndex,
                  fmOsiISISISAdjAreaAddrAdjIndex,
                  fmOsiISISISAdjAreaAddress }
        ::= { fmOsiISISISAdjacencyAreaAddressTable 1 }


        FmOsiISISISAdjacencyAreaAddressEntry ::=
                SEQUENCE {
                    fmOsiISISISAdjAreaAddrCircIndex
                        INTEGER,
                    fmOsiISISISAdjAreaAddrAdjIndex
                        INTEGER,
                    fmOsiISISISAdjAreaAddress
                        DisplayString
                }


    fmOsiISISISAdjAreaAddrCircIndex OBJECT-TYPE
        SYNTAX  INTEGER (1..60)
        ACCESS  read-only
        STATUS  mandatory
        DESCRIPTION
                "Circuit Index"
        ::= { fmOsiISISISAdjacencyAreaAddressEntry 1 }


    fmOsiISISISAdjAreaAddrAdjIndex OBJECT-TYPE
        SYNTAX  INTEGER (1..1024)
        ACCESS  read-only
        STATUS  mandatory
        DESCRIPTION
                "Adjacency Index"
        ::= { fmOsiISISISAdjacencyAreaAddressEntry 3 }


    fmOsiISISISAdjAreaAddress OBJECT-TYPE
        SYNTAX  DisplayString (SIZE(0..46))
        ACCESS  read-only
        STATUS  mandatory
        DESCRIPTION
                "Area Address"
        ::= { fmOsiISISISAdjacencyAreaAddressEntry 5 }


    fmOsiISISESAdjacencyTable OBJECT-TYPE
        SYNTAX  SEQUENCE OF FmOsiISISESAdjacencyEntry
        ACCESS  not-accessible
        STATUS  mandatory
        DESCRIPTION
                ""
        ::= { fmOsiISIS 20 }


    fmOsiISISESAdjacencyEntry OBJECT-TYPE
        SYNTAX  FmOsiISISESAdjacencyEntry
        ACCESS  not-accessible
        STATUS  mandatory
        DESCRIPTION
                "An entry of fmOsiISISESAdjacencyTable."
        INDEX   { fmOsiISISESAdjCircIndex,
                  fmOsiISISESAdjAdjIndex }
        ::= { fmOsiISISESAdjacencyTable 1 }


        FmOsiISISESAdjacencyEntry ::=
                SEQUENCE {
                    fmOsiISISESAdjCircIndex
                        INTEGER,
                    fmOsiISISESAdjAdjIndex
                        INTEGER,
                    fmOsiISISESAdjESID
                        DisplayString,
                    fmOsiISISESAdjState
                        INTEGER,
                    fmOsiISISESAdjNeighSNPAAdress
                        DisplayString,
                    fmOsiISISESAdjType
                        INTEGER
                }


    fmOsiISISESAdjCircIndex OBJECT-TYPE
        SYNTAX  INTEGER (1..60)
        ACCESS  read-only
        STATUS  mandatory
        DESCRIPTION
                "Circuit Index"
        ::= { fmOsiISISESAdjacencyEntry 1 }


    fmOsiISISESAdjAdjIndex OBJECT-TYPE
        SYNTAX  INTEGER (1..1024)
        ACCESS  read-only
        STATUS  mandatory
        DESCRIPTION
                "Adjacency Index"
        ::= { fmOsiISISESAdjacencyEntry 3 }


    fmOsiISISESAdjESID OBJECT-TYPE
        SYNTAX  DisplayString (SIZE(0..8))
        ACCESS  read-only
        STATUS  mandatory
        DESCRIPTION
                "System ID"
        ::= { fmOsiISISESAdjacencyEntry 5 }


    fmOsiISISESAdjState OBJECT-TYPE
        SYNTAX  INTEGER {
                initializing(1),
                up(2),
                failed(3),
                down(4)
                }
        ACCESS  read-only
        STATUS  mandatory
        DESCRIPTION
                "State"
        ::= { fmOsiISISESAdjacencyEntry 10 }


    fmOsiISISESAdjNeighSNPAAdress OBJECT-TYPE
        SYNTAX  DisplayString (SIZE(0..46))
        ACCESS  read-only
        STATUS  mandatory
        DESCRIPTION
                "SNPA Address"
        ::= { fmOsiISISESAdjacencyEntry 15 }


    fmOsiISISESAdjType OBJECT-TYPE
        SYNTAX  INTEGER {
                automatic(1),
                manual(2)
                }
        ACCESS  read-only
        STATUS  mandatory
        DESCRIPTION
                "Type"
        ::= { fmOsiISISESAdjacencyEntry 20 }


    fmOsiISISReachableAddressTable OBJECT-TYPE
        SYNTAX  SEQUENCE OF FmOsiISISReachableAddressEntry
        ACCESS  not-accessible
        STATUS  mandatory
        DESCRIPTION
                ""
        ::= { fmOsiISIS 25 }


    fmOsiISISReachableAddressEntry OBJECT-TYPE
        SYNTAX  FmOsiISISReachableAddressEntry
        ACCESS  not-accessible
        STATUS  mandatory
        DESCRIPTION
                "An entry of fmOsiISISReachableAddressTable."
        INDEX   { fmOsiISISRASystemType,
                  fmOsiISISRAAddress,
                  fmOsiISISRAMetric,
                  fmOsiISISRAPathIdentifier }
        ::= { fmOsiISISReachableAddressTable 1 }


        FmOsiISISReachableAddressEntry ::=
                SEQUENCE {
                    fmOsiISISRASystemType
                        INTEGER,
                    fmOsiISISRAAddress
                        DisplayString,
                    fmOsiISISRAMetric
                        INTEGER,
                    fmOsiISISRAPathIdentifier
                        INTEGER,
                    fmOsiISISRAType
                        INTEGER,
                    fmOsiISISRACircuitId
                        INTEGER,
                    fmOsiISISRAAdjacencyId
                        INTEGER,
                    fmOsiISISRAPathCost
                        INTEGER,
                    fmOsiISISRASNPAAddress
                        DisplayString
                }


    fmOsiISISRASystemType OBJECT-TYPE
        SYNTAX  INTEGER {
                es(1),
                l1IS(2),
                l2IS(3),
                prefix(4)
                }
        ACCESS  read-only
        STATUS  mandatory
        DESCRIPTION
                "System Type"
        ::= { fmOsiISISReachableAddressEntry 1 }


    fmOsiISISRAAddress OBJECT-TYPE
        SYNTAX  DisplayString (SIZE(0..46))
        ACCESS  read-only
        STATUS  mandatory
        DESCRIPTION
                "Reachable Address "
        ::= { fmOsiISISReachableAddressEntry 5 }


    fmOsiISISRAMetric OBJECT-TYPE
        SYNTAX  INTEGER {
                default(1),
                delay(2),
                expense(3),
                error(4)
                }
        ACCESS  read-only
        STATUS  mandatory
        DESCRIPTION
                "Metric "
        ::= { fmOsiISISReachableAddressEntry 10 }


    fmOsiISISRAPathIdentifier OBJECT-TYPE
        SYNTAX  INTEGER (1..32)
        ACCESS  read-only
        STATUS  mandatory
        DESCRIPTION
                "Path Idendifier "
        ::= { fmOsiISISReachableAddressEntry 15 }


    fmOsiISISRAType OBJECT-TYPE
        SYNTAX  INTEGER {
                automatic(1),
                manual(2)
                }
        ACCESS  read-only
        STATUS  mandatory
        DESCRIPTION
                "Type"
        ::= { fmOsiISISReachableAddressEntry 20 }


    fmOsiISISRACircuitId OBJECT-TYPE
        SYNTAX  INTEGER (1..60)
        ACCESS  read-only
        STATUS  mandatory
        DESCRIPTION
                "Circuit Id"
        ::= { fmOsiISISReachableAddressEntry 25 }


    fmOsiISISRAAdjacencyId OBJECT-TYPE
        SYNTAX  INTEGER (1..65535)
        ACCESS  read-only
        STATUS  mandatory
        DESCRIPTION
                "Adjacency Id"
        ::= { fmOsiISISReachableAddressEntry 35 }


    fmOsiISISRAPathCost OBJECT-TYPE
        SYNTAX  INTEGER (1..1024)
        ACCESS  read-only
        STATUS  mandatory
        DESCRIPTION
                "Path Cost"
        ::= { fmOsiISISReachableAddressEntry 40 }


    fmOsiISISRASNPAAddress OBJECT-TYPE
        SYNTAX  DisplayString (SIZE(0..46))
        ACCESS  read-only
        STATUS  mandatory
        DESCRIPTION
                "SNPA Address"
        ::= { fmOsiISISReachableAddressEntry 45 }


    fmPing OBJECT IDENTIFIER ::= { frxManagement 16 }


    fmPingTable OBJECT-TYPE
        SYNTAX  SEQUENCE OF FmPingEntry
        ACCESS  not-accessible
        STATUS  mandatory
        DESCRIPTION
                ""
        ::= { fmPing 1 }


    fmPingEntry OBJECT-TYPE
        SYNTAX  FmPingEntry
        ACCESS  not-accessible
        STATUS  mandatory
        DESCRIPTION
                "An entry of fmPingTable."
        INDEX   { fmPingIdentifier }
        ::= { fmPingTable 1 }


        FmPingEntry ::=
                SEQUENCE {
                    fmPingIdentifier
                        INTEGER,
                    fmPingProtocol
                        INTEGER,
                    fmPingAddress
                        DisplayString,
                    fmPingCountRequest
                        INTEGER,
                    fmPingPacketSize
                        INTEGER,
                    fmPingDelay
                        INTEGER,
                    fmPingTimeout
                        INTEGER,
                    fmPingPermanent
                        INTEGER,
                    fmPingSentPackets
                        Counter,
                    fmPingReceivedPackets
                        Counter,
                    fmPingMinRoundTrip
                        INTEGER,
                    fmPingAvgRoundTrip
                        INTEGER,
                    fmPingMaxRoundTrip
                        INTEGER,
                    fmPingCompletedFlag
                        INTEGER,
                    fmPingOwner
                        DisplayString,
                    fmPingAdminState
                        INTEGER
                }


    fmPingIdentifier OBJECT-TYPE
        SYNTAX  INTEGER (1..2147483647)
        ACCESS  read-write
        STATUS  mandatory
        DESCRIPTION
                "Identifier"
        ::= { fmPingEntry 1 }


    fmPingProtocol OBJECT-TYPE
        SYNTAX  INTEGER {
                ip(1),
                clnp(8),
                novell(14)
                }
        ACCESS  read-write
        STATUS  mandatory
        DESCRIPTION
                "Protocol"
        ::= { fmPingEntry 4 }


    fmPingAddress OBJECT-TYPE
        SYNTAX  DisplayString (SIZE(0..46))
        ACCESS  read-write
        STATUS  mandatory
        DESCRIPTION
                "Address"
        ::= { fmPingEntry 6 }


    fmPingCountRequest OBJECT-TYPE
        SYNTAX  INTEGER (1..2147483647)
        ACCESS  read-write
        STATUS  mandatory
        DESCRIPTION
                "CountRequest"
        ::= { fmPingEntry 10 }


    fmPingPacketSize OBJECT-TYPE
        SYNTAX  INTEGER (64..1500)
        ACCESS  read-write
        STATUS  mandatory
        DESCRIPTION
                "PacketSize"
        ::= { fmPingEntry 12 }


    fmPingDelay OBJECT-TYPE
        SYNTAX  INTEGER (0..3600000)
        ACCESS  read-write
        STATUS  mandatory
        DESCRIPTION
                "Delay"
        ::= { fmPingEntry 16 }


    fmPingTimeout OBJECT-TYPE
        SYNTAX  INTEGER (0..3600000)
        ACCESS  read-write
        STATUS  mandatory
        DESCRIPTION
                "Timeout"
        ::= { fmPingEntry 18 }


    fmPingPermanent OBJECT-TYPE
        SYNTAX  INTEGER {
                true(1),
                false(2)
                }
        ACCESS  read-write
        STATUS  mandatory
        DESCRIPTION
                "Permanent Flag"
        ::= { fmPingEntry 20 }


    fmPingSentPackets OBJECT-TYPE
        SYNTAX  Counter
        ACCESS  read-only
        STATUS  mandatory
        DESCRIPTION
                "Sent Packets"
        ::= { fmPingEntry 30 }


    fmPingReceivedPackets OBJECT-TYPE
        SYNTAX  Counter
        ACCESS  read-only
        STATUS  mandatory
        DESCRIPTION
                "Received Packets"
        ::= { fmPingEntry 32 }


    fmPingMinRoundTrip OBJECT-TYPE
        SYNTAX  INTEGER (0..4294967295)
        ACCESS  read-only
        STATUS  mandatory
        DESCRIPTION
                "Min Round Trip"
        ::= { fmPingEntry 40 }


    fmPingAvgRoundTrip OBJECT-TYPE
        SYNTAX  INTEGER (0..4294967295)
        ACCESS  read-only
        STATUS  mandatory
        DESCRIPTION
                "Avg Round Trip"
        ::= { fmPingEntry 41 }


    fmPingMaxRoundTrip OBJECT-TYPE
        SYNTAX  INTEGER (0..4294967295)
        ACCESS  read-only
        STATUS  mandatory
        DESCRIPTION
                "Max Round Trip"
        ::= { fmPingEntry 42 }


    fmPingCompletedFlag OBJECT-TYPE
        SYNTAX  INTEGER {
                true(1),
                false(2)
                }
        ACCESS  read-only
        STATUS  mandatory
        DESCRIPTION
                "Ping completed flag"
        ::= { fmPingEntry 48 }


    fmPingOwner OBJECT-TYPE
        SYNTAX  DisplayString (SIZE(0..75))
        ACCESS  read-write
        STATUS  mandatory
        DESCRIPTION
                "Owner description"
        ::= { fmPingEntry 50 }


    fmPingAdminState OBJECT-TYPE
        SYNTAX  INTEGER {
                active(1),
                notInService(2),
                notReady(3),
                createAndGo(4),
                createAndWait(5),
                destroy(6),
                stop(7)
                }
        ACCESS  read-write
        STATUS  mandatory
        DESCRIPTION
                "AdminState"
        ::= { fmPingEntry 52 }


    fmRip2 OBJECT IDENTIFIER ::= { frxManagement 17 }


    fmRip2GlobalGroup OBJECT IDENTIFIER ::= { fmRip2 1 }


    fmRip2GlobalRouteChanges OBJECT-TYPE
        SYNTAX  Counter
        ACCESS  read-only
        STATUS  mandatory
        DESCRIPTION
                "RIP2 Global Route Changes. The number of changes
                made to the IP Route Database by RIP."
        ::= { fmRip2GlobalGroup 1 }


    fmRip2GlobalQueries OBJECT-TYPE
        SYNTAX  Counter
        ACCESS  read-only
        STATUS  mandatory
        DESCRIPTION
                "RIP2 Global Queries. The number of responses sent 
                to  RIP queries from other systems."
        ::= { fmRip2GlobalGroup 2 }


    fmRip2IfStatTable OBJECT-TYPE
        SYNTAX  SEQUENCE OF FmRip2IfStatEntry
        ACCESS  not-accessible
        STATUS  mandatory
        DESCRIPTION
                "A  list  of  subnets  which  require  separate
                status monitoring in RIP"
        ::= { fmRip2 2 }


    fmRip2IfStatEntry OBJECT-TYPE
        SYNTAX  FmRip2IfStatEntry
        ACCESS  not-accessible
        STATUS  mandatory
        DESCRIPTION
                "An entry of fmRip2IfStatTable."
        INDEX   { fmRip2IfStatAddress }
        ::= { fmRip2IfStatTable 1 }


        FmRip2IfStatEntry ::=
                SEQUENCE {
                    fmRip2IfStatAddress
                        IpAddress,
                    fmRip2IfStatRcvBadPackets
                        Counter,
                    fmRip2IfStatRcvBadRoutes
                        Counter,
                    fmRip2IfStatSentUpdates
                        Counter,
                    fmRip2IfStatStatus
                        INTEGER
                }


    fmRip2IfStatAddress OBJECT-TYPE
        SYNTAX  IpAddress
        ACCESS  read-only
        STATUS  mandatory
        DESCRIPTION
                "RIP2 Interface Stat Ip Address. The IP Address of
                this system on the indicated subnet"
        ::= { fmRip2IfStatEntry 1 }


    fmRip2IfStatRcvBadPackets OBJECT-TYPE
        SYNTAX  Counter
        ACCESS  read-only
        STATUS  mandatory
        DESCRIPTION
                "RIP2 Interface Stat Received Bad Packets. The
                number of RIP response packets received bythe  RIP
                 process  which were subsequently discarded for
                any reason (e.g. a version 0 packet, or an unknown
                command type).
                "
        ::= { fmRip2IfStatEntry 2 }


    fmRip2IfStatRcvBadRoutes OBJECT-TYPE
        SYNTAX  Counter
        ACCESS  read-only
        STATUS  mandatory
        DESCRIPTION
                "RIP2 Interface Stat Received Bad Routes. The
                number of routes, in  valid  RIP  packets,which
                were ignored for any reason (e.g. unknown address
                family, or invalid metric)."
        ::= { fmRip2IfStatEntry 3 }


    fmRip2IfStatSentUpdates OBJECT-TYPE
        SYNTAX  Counter
        ACCESS  read-only
        STATUS  mandatory
        DESCRIPTION
                "RIP2 Interface Stat Sent Updates. The number of
                triggered RIP  updates  actually sent  on  this
                interface.  This explicitly does NOT include full
                updates  sent  containing  new information."
        ::= { fmRip2IfStatEntry 4 }


    fmRip2IfStatStatus OBJECT-TYPE
        SYNTAX  INTEGER {
                valid(1),
                invalid(2)
                }
        ACCESS  read-only
        STATUS  mandatory
        DESCRIPTION
                "RIP2 Interface Stat Status. Writing invalid has 
                the  effect  of  deleting this interface."
        ::= { fmRip2IfStatEntry 5 }


    fmRip2IfConfTable OBJECT-TYPE
        SYNTAX  SEQUENCE OF FmRip2IfConfEntry
        ACCESS  not-accessible
        STATUS  mandatory
        DESCRIPTION
                "A list of subnets which require separate 
                configuration in RIP."
        ::= { fmRip2 3 }


    fmRip2IfConfEntry OBJECT-TYPE
        SYNTAX  FmRip2IfConfEntry
        ACCESS  not-accessible
        STATUS  mandatory
        DESCRIPTION
                "An entry of fmRip2IfConfTable."
        INDEX   { fmRip2IfConfAddress }
        ::= { fmRip2IfConfTable 1 }


        FmRip2IfConfEntry ::=
                SEQUENCE {
                    fmRip2IfConfAddress
                        IpAddress,
                    fmRip2IfConfDomain
                        DisplayString,
                    fmRip2IfConfAuthType
                        INTEGER,
                    fmRip2IfConfAuthKey
                        DisplayString,
                    fmRip2IfConfSend
                        INTEGER,
                    fmRip2IfConfReceive
                        INTEGER,
                    fmRip2IfConfDefaultMetric
                        INTEGER,
                    fmRip2IfConfStatus
                        INTEGER
                }


    fmRip2IfConfAddress OBJECT-TYPE
        SYNTAX  IpAddress
        ACCESS  read-only
        STATUS  mandatory
        DESCRIPTION
                "RIP2 Interface Conf Ip Address. The IP Address of
                this system on the indicated subnet."
        ::= { fmRip2IfConfEntry 1 }


    fmRip2IfConfDomain OBJECT-TYPE
        SYNTAX  DisplayString (SIZE(0..2))
        ACCESS  read-only
        STATUS  mandatory
        DESCRIPTION
                "RIP2 Interface Conf Domain. Value inserted into
                the Routing  Domain  field of all RIP packets sent
                on this interface."
        ::= { fmRip2IfConfEntry 2 }


    fmRip2IfConfAuthType OBJECT-TYPE
        SYNTAX  INTEGER {
                noAuthentication(1),
                simplePassword(2)
                }
        ACCESS  read-only
        STATUS  mandatory
        DESCRIPTION
                "RIP2 Interface Conf Authentiction Type. The type
                of Authentication used on this interface."
        ::= { fmRip2IfConfEntry 3 }


    fmRip2IfConfAuthKey OBJECT-TYPE
        SYNTAX  DisplayString (SIZE(0..16))
        ACCESS  read-only
        STATUS  mandatory
        DESCRIPTION
                "RIP2 Interface Conf Authentication Key. The value
                to be used as the Authentication Key whenever   
                the   corresponding   instance of
                rip2IfConfAuthType has  the  value 
                simplePassword.   A modification of the
                corresponding instance of rip2IfConfAuthType  does
                 not  modify the rip2IfConfAuthKey value. If a
                string shorter than 16 octets is supplied, it 
                will be left-justified and padded to 16 octets, on
                the right, with nulls (0x00). Reading this object
                always results in an  OCTET STRING  of  length
                zero; authentication may not be bypassed by
                reading the MIB object."
        ::= { fmRip2IfConfEntry 4 }


    fmRip2IfConfSend OBJECT-TYPE
        SYNTAX  INTEGER {
                doNotSend(1),
                ripVersion1(2),
                rip1Compatible(3),
                ripVersion2(4)
                }
        ACCESS  read-only
        STATUS  mandatory
        DESCRIPTION
                "RIP2 Interface Conf Send. What  the  router  sends
                 on  this  interface. ripVersion1 implies sending
                RIP updates compliant  with  RFC  1058.
                rip1Compatible  implies broadcasting RIP-2 updates
                using RFC 1058 route subsumption rules. 
                ripVersion2 implies  multicasting RIP-2 updates."
        ::= { fmRip2IfConfEntry 5 }


    fmRip2IfConfReceive OBJECT-TYPE
        SYNTAX  INTEGER {
                rip1(1),
                rip2(2),
                rip1OrRip2(3)
                }
        ACCESS  read-only
        STATUS  mandatory
        DESCRIPTION
                "RIP2 Interface Conf Receive. This indicates which
                version  of  RIP  updates are to be accepted.  
                Note  that  rip2  and rip1OrRip2 implies reception
                of multicast packets."
        ::= { fmRip2IfConfEntry 6 }


    fmRip2IfConfDefaultMetric OBJECT-TYPE
        SYNTAX  INTEGER (0..15)
        ACCESS  read-only
        STATUS  mandatory
        DESCRIPTION
                "RIP2 Interface Conf Default Metric. This variable
                indicates what metric is  to  be used  as  a 
                default  route in RIP updates originated on this
                interface.  A value of zero indicates  that  no 
                default route should be originated; in this  case,
                 a  default  route  via another router may be
                propagated."
        ::= { fmRip2IfConfEntry 7 }


    fmRip2IfConfStatus OBJECT-TYPE
        SYNTAX  INTEGER {
                valid(1),
                invalid(2)
                }
        ACCESS  read-only
        STATUS  mandatory
        DESCRIPTION
                "RIP2 Interface Conf Status. Writing invalid has 
                the  effect  of  deleting this interface."
        ::= { fmRip2IfConfEntry 8 }


    fmRip2PeerTable OBJECT-TYPE
        SYNTAX  SEQUENCE OF FmRip2PeerEntry
        ACCESS  not-accessible
        STATUS  mandatory
        DESCRIPTION
                "A list of RIP Peers."
        ::= { fmRip2 4 }


    fmRip2PeerEntry OBJECT-TYPE
        SYNTAX  FmRip2PeerEntry
        ACCESS  not-accessible
        STATUS  mandatory
        DESCRIPTION
                "An entry of fmRip2PeerTable."
        INDEX   { fmRip2PeerAddress,
                  fmRip2PeerDomain }
        ::= { fmRip2PeerTable 1 }


        FmRip2PeerEntry ::=
                SEQUENCE {
                    fmRip2PeerAddress
                        IpAddress,
                    fmRip2PeerDomain
                        DisplayString,
                    fmRip2PeerLastUpdate
                        TimeTicks,
                    fmRip2PeerVersion
                        INTEGER,
                    fmRip2PeerRcvBadPackets
                        Counter,
                    fmRip2PeerRcvBadRoutes
                        Counter
                }


    fmRip2PeerAddress OBJECT-TYPE
        SYNTAX  IpAddress
        ACCESS  read-only
        STATUS  mandatory
        DESCRIPTION
                "RIP2 Peer Ip Address. The IP Address of the Peer
                System."
        ::= { fmRip2PeerEntry 1 }


    fmRip2PeerDomain OBJECT-TYPE
        SYNTAX  DisplayString (SIZE(0..2))
        ACCESS  read-only
        STATUS  mandatory
        DESCRIPTION
                "RIP2 Peer Domain. The value in the Routing Domain
                field  in  RIP packets received from the peer
                "
        ::= { fmRip2PeerEntry 2 }


    fmRip2PeerLastUpdate OBJECT-TYPE
        SYNTAX  TimeTicks
        ACCESS  read-only
        STATUS  mandatory
        DESCRIPTION
                "RIP2 Peer Last Update. The value of sysUpTime when
                the most  recent RIP update was received from this
                system."
        ::= { fmRip2PeerEntry 3 }


    fmRip2PeerVersion OBJECT-TYPE
        SYNTAX  INTEGER (0..255)
        ACCESS  read-only
        STATUS  mandatory
        DESCRIPTION
                "RIP2 Peer Version. The RIP version number in the 
                header  of  the last RIP packet received."
        ::= { fmRip2PeerEntry 4 }


    fmRip2PeerRcvBadPackets OBJECT-TYPE
        SYNTAX  Counter
        ACCESS  read-only
        STATUS  mandatory
        DESCRIPTION
                "RIP2 Peer Received Bad Packets. The number of RIP
                response packets  from  this peer discarded as
                invalid.
                "
        ::= { fmRip2PeerEntry 5 }


    fmRip2PeerRcvBadRoutes OBJECT-TYPE
        SYNTAX  Counter
        ACCESS  read-only
        STATUS  mandatory
        DESCRIPTION
                "RIP2 Peer Received Bad Routes. The number of
                routes from this peer that  were ignored because
                the entry format was invalid."
        ::= { fmRip2PeerEntry 6 }


    fmOspf OBJECT IDENTIFIER ::= { frxManagement 18 }


    fmOspfStandard OBJECT IDENTIFIER ::= { fmOspf 1 }


    fmOspfStandardGeneralGroup OBJECT IDENTIFIER ::= { fmOspfStandard 1 }


    fmOspfStandardRouterId OBJECT-TYPE
        SYNTAX  IpAddress
        ACCESS  read-only
        STATUS  mandatory
        DESCRIPTION
                "OSPF Router Id. A 32-bit integer uniquely
                identifying the router in the Autonomous System.
                By convention, to ensure uniqueness, this should
                default to the value of one of the router's IP
                interface addresses."
        ::= { fmOspfStandardGeneralGroup 1 }


    fmOspfStandardAdminStat OBJECT-TYPE
        SYNTAX  INTEGER {
                enabled(1),
                disabled(2)
                }
        ACCESS  read-only
        STATUS  mandatory
        DESCRIPTION
                "OSPF Administrative Status. The administrative
                status of OSPF in the router. The value 'enabled'
                denotes that the OSPF Process is active on at
                least one interface; 'disabled' disables it on all
                interfaces."
        ::= { fmOspfStandardGeneralGroup 2 }


    fmOspfStandardVersionNumber OBJECT-TYPE
        SYNTAX  INTEGER {
                version1(1),
                version2(2)
                }
        ACCESS  read-only
        STATUS  mandatory
        DESCRIPTION
                "OSPF Version Number. The current version number of
                the OSPF protocol is 2."
        ::= { fmOspfStandardGeneralGroup 3 }


    fmOspfStandardAreaBdrRtrStatus OBJECT-TYPE
        SYNTAX  INTEGER {
                true(1),
                false(2)
                }
        ACCESS  read-only
        STATUS  mandatory
        DESCRIPTION
                "OSPF Area Border Router Status. A flag to note
                whether this router is an area border router."
        ::= { fmOspfStandardGeneralGroup 4 }


    fmOspfStandardASBdrRtrStatus OBJECT-TYPE
        SYNTAX  INTEGER {
                true(1),
                false(2)
                }
        ACCESS  read-only
        STATUS  mandatory
        DESCRIPTION
                "OSPF AS Border Router Status A flag to note
                whether this router is an Autonomous System border
                router."
        ::= { fmOspfStandardGeneralGroup 5 }


    fmOspfStandardExternLSACount OBJECT-TYPE
        SYNTAX  Gauge
        ACCESS  read-only
        STATUS  mandatory
        DESCRIPTION
                "OSPF Extern LSA Count. The number of external (LS
                type 5) link-state advertisements in the
                link-state database."
        ::= { fmOspfStandardGeneralGroup 6 }


    fmOspfStandardExternLSACksumSum OBJECT-TYPE
        SYNTAX  INTEGER (0..4294967295)
        ACCESS  read-only
        STATUS  mandatory
        DESCRIPTION
                "OSPF Extern LSA Checksum. The 32-bit unsigned sum
                of the LS checksums of the external link-state
                advertisements contained in the link-state
                database. This sum can be used to determine if
                there has been a change in a router's link state
                database, and to compare the link-state database
                of two routers."
        ::= { fmOspfStandardGeneralGroup 7 }


    fmOspfStandardTOSSupport OBJECT-TYPE
        SYNTAX  INTEGER {
                true(1),
                false(2)
                }
        ACCESS  read-only
        STATUS  mandatory
        DESCRIPTION
                "OSPF TOS Support. The router's support for
                type-of-service routing."
        ::= { fmOspfStandardGeneralGroup 8 }


    fmOspfStandardOriginateNewLSAs OBJECT-TYPE
        SYNTAX  Counter
        ACCESS  read-only
        STATUS  mandatory
        DESCRIPTION
                "OSPF Originate New LSAs. The number of new
                link-state advertisements that have been
                originated. This number is incremented each time
                the router originates a new LSA."
        ::= { fmOspfStandardGeneralGroup 9 }


    fmOspfStandardRxNewLSAs OBJECT-TYPE
        SYNTAX  Counter
        ACCESS  read-only
        STATUS  mandatory
        DESCRIPTION
                "OSPF Receive New LSAs. The number of link-state
                advertisements received determined to be new
                instantiations. This number does not include newer
                instantiations of self-originated link-state
                advertisements.
                "
        ::= { fmOspfStandardGeneralGroup 10 }


    fmOspfStandardAreaTable OBJECT-TYPE
        SYNTAX  SEQUENCE OF FmOspfStandardAreaEntry
        ACCESS  not-accessible
        STATUS  mandatory
        DESCRIPTION
                "Information describing the configured parameters
                and cumulative statistics of the router's attached
                areas."
        ::= { fmOspfStandard 2 }


    fmOspfStandardAreaEntry OBJECT-TYPE
        SYNTAX  FmOspfStandardAreaEntry
        ACCESS  not-accessible
        STATUS  mandatory
        DESCRIPTION
                "An entry of fmOspfStandardAreaTable."
        INDEX   { fmOspfStandardAreaId }
        ::= { fmOspfStandardAreaTable 1 }


        FmOspfStandardAreaEntry ::=
                SEQUENCE {
                    fmOspfStandardAreaId
                        IpAddress,
                    fmOspfStandardAuthType
                        INTEGER,
                    fmOspfStandardImportASExtern
                        INTEGER,
                    fmOspfStandardSpfRuns
                        Counter,
                    fmOspfStandardAreaBdrRtrCount
                        Gauge,
                    fmOspfStandardASBdrRtrCount
                        Gauge,
                    fmOspfStandardAreaLSACount
                        Gauge,
                    fmOspfStandardAreaLSACksumSum
                        INTEGER
                }


    fmOspfStandardAreaId OBJECT-TYPE
        SYNTAX  IpAddress
        ACCESS  read-only
        STATUS  mandatory
        DESCRIPTION
                "OSPF Area Id. A 32-bit integer uniquely
                identifying an area.  Area ID 0.0.0.0 is used for
                the OSPF backbone."
        ::= { fmOspfStandardAreaEntry 1 }


    fmOspfStandardAuthType OBJECT-TYPE
        SYNTAX  INTEGER (0..255)
        ACCESS  read-only
        STATUS  mandatory
        DESCRIPTION
                "OSPF Area Authentication Type. The authentication
                type specified for an area. Additional
                authentication types may be assigned locally on a
                per Area basis."
        ::= { fmOspfStandardAreaEntry 2 }


    fmOspfStandardImportASExtern OBJECT-TYPE
        SYNTAX  INTEGER {
                true(1),
                false(2)
                }
        ACCESS  read-only
        STATUS  mandatory
        DESCRIPTION
                "OSPF Area Import AS Extern. The area's support for
                importing AS external link-state advertisements."
        ::= { fmOspfStandardAreaEntry 3 }


    fmOspfStandardSpfRuns OBJECT-TYPE
        SYNTAX  Counter
        ACCESS  read-only
        STATUS  mandatory
        DESCRIPTION
                "OSPF Area SPF Runs. The number of times that the
                intra-area route table has been calculated using
                this area's link-state database. This is typically
                done using Dijkstra's algorithm."
        ::= { fmOspfStandardAreaEntry 4 }


    fmOspfStandardAreaBdrRtrCount OBJECT-TYPE
        SYNTAX  Gauge
        ACCESS  read-only
        STATUS  mandatory
        DESCRIPTION
                "OSPF Area Border Router Count. The total number of
                area border routers reachable within this area. 
                This is initially zero, and is calculated in each
                SPF Pass."
        ::= { fmOspfStandardAreaEntry 5 }


    fmOspfStandardASBdrRtrCount OBJECT-TYPE
        SYNTAX  Gauge
        ACCESS  read-only
        STATUS  mandatory
        DESCRIPTION
                "OSPF Area AS Border Router Count. The total number
                of Autonomous System border routers reachable
                within this area.  This is initially zero, and is
                calculated in each SPF Pass."
        ::= { fmOspfStandardAreaEntry 6 }


    fmOspfStandardAreaLSACount OBJECT-TYPE
        SYNTAX  Gauge
        ACCESS  read-only
        STATUS  mandatory
        DESCRIPTION
                "OSPF Area LSA Count. The total number of
                link-state advertisements in this area's
                link-state database, excluding AS External LSA's."
        ::= { fmOspfStandardAreaEntry 7 }


    fmOspfStandardAreaLSACksumSum OBJECT-TYPE
        SYNTAX  INTEGER (0..4294967295)
        ACCESS  read-only
        STATUS  mandatory
        DESCRIPTION
                "OSPF Area LSA Checksum Sum. The 32-bit unsigned
                sum of the link-state advertisements' LS checksums
                contained in this area's link-state database. This
                sum excludes external (LS type 5) link-state
                advertisements. The sum can be used to determine
                if there has been a change in a router's link
                state database, and to compare the link-state
                database of two routers."
        ::= { fmOspfStandardAreaEntry 8 }


    fmOspfStandardStubAreaTable OBJECT-TYPE
        SYNTAX  SEQUENCE OF FmOspfStandardStubAreaEntry
        ACCESS  not-accessible
        STATUS  mandatory
        DESCRIPTION
                "The set of metrics that will be advertised by a
                default Area Border Router into a stub area"
        ::= { fmOspfStandard 3 }


    fmOspfStandardStubAreaEntry OBJECT-TYPE
        SYNTAX  FmOspfStandardStubAreaEntry
        ACCESS  not-accessible
        STATUS  mandatory
        DESCRIPTION
                "An entry of fmOspfStandardStubAreaTable."
        INDEX   { fmOspfStandardStubAreaID,
                  fmOspfStandardStubTOS }
        ::= { fmOspfStandardStubAreaTable 1 }


        FmOspfStandardStubAreaEntry ::=
                SEQUENCE {
                    fmOspfStandardStubAreaID
                        IpAddress,
                    fmOspfStandardStubTOS
                        INTEGER,
                    fmOspfStandardStubMetric
                        INTEGER,
                    fmOspfStandardStubStatus
                        INTEGER
                }


    fmOspfStandardStubAreaID OBJECT-TYPE
        SYNTAX  IpAddress
        ACCESS  read-only
        STATUS  mandatory
        DESCRIPTION
                "OSPF Stub Area Id. The 32 bit identifier for the
                Stub Area.  On creation, this can be derived from
                the instance.
                "
        ::= { fmOspfStandardStubAreaEntry 1 }


    fmOspfStandardStubTOS OBJECT-TYPE
        SYNTAX  INTEGER (0..31)
        ACCESS  read-only
        STATUS  mandatory
        DESCRIPTION
                "OSPF Stub Area TOS. The Type of Service associated
                with the metric. On creation, this can be derived
                from the instance."
        ::= { fmOspfStandardStubAreaEntry 2 }


    fmOspfStandardStubMetric OBJECT-TYPE
        SYNTAX  INTEGER (1..16777215)
        ACCESS  read-only
        STATUS  mandatory
        DESCRIPTION
                "OSPF Stub Area Metric. The metric value applied at
                the indicated type of service. By default, this
                equals the least metric at the type of service
                among the interfaces to other areas."
        ::= { fmOspfStandardStubAreaEntry 3 }


    fmOspfStandardStubStatus OBJECT-TYPE
        SYNTAX  INTEGER {
                valid(1),
                invalid(2)
                }
        ACCESS  read-only
        STATUS  mandatory
        DESCRIPTION
                "OSPF Stub Area Status. This variable displays the
                validity or invalidity of the entry. Setting it to
                'invalid' has the effect of rendering it
                inoperative.  The internal effect (row removal) is
                implementation dependent
                ."
        ::= { fmOspfStandardStubAreaEntry 4 }


    fmOspfStandardLsdbTable OBJECT-TYPE
        SYNTAX  SEQUENCE OF FmOspfStandardLsdbEntry
        ACCESS  not-accessible
        STATUS  mandatory
        DESCRIPTION
                "The OSPF Process's Links State Database."
        ::= { fmOspfStandard 4 }


    fmOspfStandardLsdbEntry OBJECT-TYPE
        SYNTAX  FmOspfStandardLsdbEntry
        ACCESS  not-accessible
        STATUS  mandatory
        DESCRIPTION
                "An entry of fmOspfStandardLsdbTable."
        INDEX   { fmOspfStandardLsdbAreaId,
                  fmOspfStandardLsdbType }
        ::= { fmOspfStandardLsdbTable 1 }


        FmOspfStandardLsdbEntry ::=
                SEQUENCE {
                    fmOspfStandardLsdbAreaId
                        IpAddress,
                    fmOspfStandardLsdbType
                        INTEGER,
                    fmOspfStandardLsdbLSID
                        IpAddress,
                    fmOspfStandardLsdbRouterId
                        IpAddress,
                    fmOspfStandardLsdbSequence
                        INTEGER,
                    fmOspfStandardLsdbAge
                        INTEGER,
                    fmOspfStandardLsdbChecksum
                        INTEGER,
                    fmOspfStandardLsdbAdvertisement
                        DisplayString
                }


    fmOspfStandardLsdbAreaId OBJECT-TYPE
        SYNTAX  IpAddress
        ACCESS  read-only
        STATUS  mandatory
        DESCRIPTION
                "OSPF Link State Database Area Id The OSPF
                Process's Links State Database."
        ::= { fmOspfStandardLsdbEntry 1 }


    fmOspfStandardLsdbType OBJECT-TYPE
        SYNTAX  INTEGER {
                routerLink(1),
                networkLink(2),
                summaryLink(3),
                asSummaryLink(4),
                asExternalLink(5)
                }
        ACCESS  read-only
        STATUS  mandatory
        DESCRIPTION
                "OSPF Link State Database LS Type. The type of the
                link state advertisement. Each link state type has
                a separate advertisement format.
                "
        ::= { fmOspfStandardLsdbEntry 2 }


    fmOspfStandardLsdbLSID OBJECT-TYPE
        SYNTAX  IpAddress
        ACCESS  read-only
        STATUS  mandatory
        DESCRIPTION
                "OSPF Link State Database LS Id. The Link State ID
                is an LS Type Specific field containing either a
                Router ID or an IP Address; it identifies the
                piece of the routing domain that is being
                described by the advertisement."
        ::= { fmOspfStandardLsdbEntry 3 }


    fmOspfStandardLsdbRouterId OBJECT-TYPE
        SYNTAX  IpAddress
        ACCESS  read-only
        STATUS  mandatory
        DESCRIPTION
                "OSPF Link State Database Router Id. The 32 bit
                number that uniquely identifies the originating
                router in the Autonomous System.
                "
        ::= { fmOspfStandardLsdbEntry 4 }


    fmOspfStandardLsdbSequence OBJECT-TYPE
        SYNTAX  INTEGER (0..4294967295)
        ACCESS  read-only
        STATUS  mandatory
        DESCRIPTION
                "OSPF Link State Database Sequence. The sequence
                number field is a signed 32-bit integer. It is
                used to detect old and duplicate link state
                advertisements. The space of sequence numbers is
                linearly ordered. The larger the sequence number
                the more recent the advertisement."
        ::= { fmOspfStandardLsdbEntry 5 }


    fmOspfStandardLsdbAge OBJECT-TYPE
        SYNTAX  INTEGER (0..4294967295)
        ACCESS  read-only
        STATUS  mandatory
        DESCRIPTION
                "OSPF Link State Database Age. This field is the
                age of the link state advertisement in seconds.
                "
        ::= { fmOspfStandardLsdbEntry 6 }


    fmOspfStandardLsdbChecksum OBJECT-TYPE
        SYNTAX  INTEGER (0..4294967295)
        ACCESS  read-only
        STATUS  mandatory
        DESCRIPTION
                "OSPF Link State Database Checksum. This field is
                the checksum of the complete contents of the
                advertisement, excepting the age field. The age
                field is excepted so that an advertisement's age
                can be incremented without updating the checksum.
                The checksum used is the same that is used for ISO
                connectionless datagrams; it is commonly referred
                to as the Fletcher checksum.
                "
        ::= { fmOspfStandardLsdbEntry 7 }


    fmOspfStandardLsdbAdvertisement OBJECT-TYPE
        SYNTAX  DisplayString (SIZE(0..255))
        ACCESS  read-only
        STATUS  mandatory
        DESCRIPTION
                "OSPF Link State Database Advertisement. The entire
                Link State Advertisement, including its header.
                "
        ::= { fmOspfStandardLsdbEntry 8 }


    fmOspfStandardAreaRangeTable OBJECT-TYPE
        SYNTAX  SEQUENCE OF FmOspfStandardAreaRangeEntry
        ACCESS  not-accessible
        STATUS  mandatory
        DESCRIPTION
                "A range if IP addresses specified by an IP
                address/IP network mask pair.  For example, class
                B address range of X.X.X.X with a network mask of
                255.255.0.0 includes all IP addresses from X.X.0.0
                to X.X.255.255."
        ::= { fmOspfStandard 5 }


    fmOspfStandardAreaRangeEntry OBJECT-TYPE
        SYNTAX  FmOspfStandardAreaRangeEntry
        ACCESS  not-accessible
        STATUS  mandatory
        DESCRIPTION
                "An entry of fmOspfStandardAreaRangeTable."
        INDEX   { fmOspfStandardAreaRangeAreaID,
                  fmOspfStandardAreaRangeNet }
        ::= { fmOspfStandardAreaRangeTable 1 }


        FmOspfStandardAreaRangeEntry ::=
                SEQUENCE {
                    fmOspfStandardAreaRangeAreaID
                        IpAddress,
                    fmOspfStandardAreaRangeNet
                        IpAddress,
                    fmOspfStandardAreaRangeMask
                        IpAddress,
                    fmOspfStandardAreaRangeStatus
                        INTEGER
                }


    fmOspfStandardAreaRangeAreaID OBJECT-TYPE
        SYNTAX  IpAddress
        ACCESS  read-only
        STATUS  mandatory
        DESCRIPTION
                "OSPF Area Range Area Id. The Area the Address
                Range is to be found within."
        ::= { fmOspfStandardAreaRangeEntry 1 }


    fmOspfStandardAreaRangeNet OBJECT-TYPE
        SYNTAX  IpAddress
        ACCESS  read-only
        STATUS  mandatory
        DESCRIPTION
                "OSPF Area Range Net. The IP Address of the Net or
                Subnet indicated by the range."
        ::= { fmOspfStandardAreaRangeEntry 2 }


    fmOspfStandardAreaRangeMask OBJECT-TYPE
        SYNTAX  IpAddress
        ACCESS  read-only
        STATUS  mandatory
        DESCRIPTION
                "OSPF Area Range Mask. The Subnet Mask that
                pertains to the Net or Subnet."
        ::= { fmOspfStandardAreaRangeEntry 3 }


    fmOspfStandardAreaRangeStatus OBJECT-TYPE
        SYNTAX  INTEGER {
                valid(1),
                invalid(2)
                }
        ACCESS  read-only
        STATUS  mandatory
        DESCRIPTION
                "OSPF Area Range Status. This variable displays the
                validity or invalidity of the entry. Setting it to
                'invalid' has the effect of rendering it
                inoperative. The internal effect (row removal) is
                implementation dependent."
        ::= { fmOspfStandardAreaRangeEntry 4 }


    fmOspfStandardHostTable OBJECT-TYPE
        SYNTAX  SEQUENCE OF FmOspfStandardHostEntry
        ACCESS  not-accessible
        STATUS  mandatory
        DESCRIPTION
                "The list of Hosts, and their metrics, that the
                router will advertise as host routes."
        ::= { fmOspfStandard 6 }


    fmOspfStandardHostEntry OBJECT-TYPE
        SYNTAX  FmOspfStandardHostEntry
        ACCESS  not-accessible
        STATUS  mandatory
        DESCRIPTION
                "An entry of fmOspfStandardHostTable."
        INDEX   { fmOspfStandardHostIpAddress,
                  fmOspfStandardHostTOS }
        ::= { fmOspfStandardHostTable 1 }


        FmOspfStandardHostEntry ::=
                SEQUENCE {
                    fmOspfStandardHostIpAddress
                        IpAddress,
                    fmOspfStandardHostTOS
                        INTEGER,
                    fmOspfStandardHostMetric
                        INTEGER,
                    fmOspfStandardHostStatus
                        INTEGER
                }


    fmOspfStandardHostIpAddress OBJECT-TYPE
        SYNTAX  IpAddress
        ACCESS  read-only
        STATUS  mandatory
        DESCRIPTION
                "OSPF Host Ip Address. The IP Address of the Host."
        ::= { fmOspfStandardHostEntry 1 }


    fmOspfStandardHostTOS OBJECT-TYPE
        SYNTAX  INTEGER (0..31)
        ACCESS  read-only
        STATUS  mandatory
        DESCRIPTION
                "OSPF Host TOS. The Type of Service of the route
                being configured."
        ::= { fmOspfStandardHostEntry 2 }


    fmOspfStandardHostMetric OBJECT-TYPE
        SYNTAX  INTEGER (1..65535)
        ACCESS  read-only
        STATUS  mandatory
        DESCRIPTION
                "OSPF Host Metric. The Metric to be advertised."
        ::= { fmOspfStandardHostEntry 3 }


    fmOspfStandardHostStatus OBJECT-TYPE
        SYNTAX  INTEGER {
                valid(1),
                invalid(2)
                }
        ACCESS  read-only
        STATUS  mandatory
        DESCRIPTION
                "OSPF Host Status. This variable displays the
                validity or invalidity of the entry. Setting it to
                'invalid' has the effect of rendering it
                inoperative. The internal effect (row removal) is
                implementation dependent."
        ::= { fmOspfStandardHostEntry 4 }


    fmOspfStandardIfTable OBJECT-TYPE
        SYNTAX  SEQUENCE OF FmOspfStandardIfEntry
        ACCESS  not-accessible
        STATUS  mandatory
        DESCRIPTION
                "The OSPF Interface Table describes the interfaces
                from the viewpoint of OSPF."
        ::= { fmOspfStandard 7 }


    fmOspfStandardIfEntry OBJECT-TYPE
        SYNTAX  FmOspfStandardIfEntry
        ACCESS  not-accessible
        STATUS  mandatory
        DESCRIPTION
                "An entry of fmOspfStandardIfTable."
        INDEX   { fmOspfStandardIfIpAddress,
                  fmOspfStandardAddressLessIf }
        ::= { fmOspfStandardIfTable 1 }


        FmOspfStandardIfEntry ::=
                SEQUENCE {
                    fmOspfStandardIfIpAddress
                        IpAddress,
                    fmOspfStandardAddressLessIf
                        INTEGER,
                    fmOspfStandardIfAreaId
                        IpAddress,
                    fmOspfStandardIfType
                        INTEGER,
                    fmOspfStandardIfAdminStat
                        INTEGER,
                    fmOspfStandardIfRtrPriority
                        INTEGER,
                    fmOspfStandardIfTransitDelay
                        INTEGER,
                    fmOspfStandardIfRetransInterval
                        INTEGER,
                    fmOspfStandardIfHelloInterval
                        INTEGER,
                    fmOspfStandardIfRtrDeadInterval
                        INTEGER,
                    fmOspfStandardIfPollInterval
                        INTEGER,
                    fmOspfStandardIfState
                        INTEGER,
                    fmOspfStandardIfDesignatedRouter
                        IpAddress,
                    fmOspfStandardIfBackupDesignatedRouter
                        IpAddress,
                    fmOspfStandardIfEvents
                        Counter,
                    fmOspfStandardIfAuthKey
                        DisplayString
                }


    fmOspfStandardIfIpAddress OBJECT-TYPE
        SYNTAX  IpAddress
        ACCESS  read-only
        STATUS  mandatory
        DESCRIPTION
                "OSPF Interface Ip Address. The IP address of this
                OSPF interface."
        ::= { fmOspfStandardIfEntry 1 }


    fmOspfStandardAddressLessIf OBJECT-TYPE
        SYNTAX  INTEGER (0..35)
        ACCESS  read-only
        STATUS  mandatory
        DESCRIPTION
                "OSPF Interface Address Less If. For the purpose of
                easing the instancing of addressed and addressless
                interfaces; This variable takes the value 0 on
                interfaces with IP Addresses, and the
                corresponding value of ifIndex for interfaces
                having no IP Address."
        ::= { fmOspfStandardIfEntry 2 }


    fmOspfStandardIfAreaId OBJECT-TYPE
        SYNTAX  IpAddress
        ACCESS  read-only
        STATUS  mandatory
        DESCRIPTION
                "OSPF Interface Area Id. A 32-bit integer uniquely
                identifying the area to which the interface
                connects. Area ID 0.0.0.0 is used for the OSPF
                backbone."
        ::= { fmOspfStandardIfEntry 3 }


    fmOspfStandardIfType OBJECT-TYPE
        SYNTAX  INTEGER {
                broadcast(1),
                nbma(2),
                pointToPoint(3)
                }
        ACCESS  read-only
        STATUS  mandatory
        DESCRIPTION
                "OSPF Interface Type. The OSPF interface type. By
                way of a default, this field may be intuited from
                the corresponding value of ifType. Broadcast LANs,
                such as Ethernet and IEEE 802.5, take the value
                'broadcast', X.25, Frame Relay, and similar
                technologies take the value 'nbma', and links that
                are definitively point to point take the value
                'pointToPoint'"
        ::= { fmOspfStandardIfEntry 4 }


    fmOspfStandardIfAdminStat OBJECT-TYPE
        SYNTAX  INTEGER {
                enabled(1),
                disabled(2)
                }
        ACCESS  read-only
        STATUS  mandatory
        DESCRIPTION
                "OSPF Interface Administrative Status. The OSPF
                interface's administrative status. The value
                'enabled' denotes that neighbor relationships may
                be formed on the interface, and the interface will
                be advertised as an internal route to some area.
                The value 'disabled' denotes that the interface is
                external to OSPF."
        ::= { fmOspfStandardIfEntry 5 }


    fmOspfStandardIfRtrPriority OBJECT-TYPE
        SYNTAX  INTEGER (0..255)
        ACCESS  read-only
        STATUS  mandatory
        DESCRIPTION
                "OSPF Interface Router Priority. The priority of
                this interface. Used in multi-access networks,
                this field is used in the designated router
                election algorithm. The value 0 signifies that the
                router is not eligible to become the designated
                router on this particular network. In the event of
                a tie in this value, routers will use their router
                id as a tie breaker"
        ::= { fmOspfStandardIfEntry 6 }


    fmOspfStandardIfTransitDelay OBJECT-TYPE
        SYNTAX  INTEGER (1..3600)
        ACCESS  read-only
        STATUS  mandatory
        DESCRIPTION
                "OSPF Interface Transit Delay. The estimated number
                of seconds it takes to transmit a link- state
                update packet over this interface."
        ::= { fmOspfStandardIfEntry 7 }


    fmOspfStandardIfRetransInterval OBJECT-TYPE
        SYNTAX  INTEGER (1..3600)
        ACCESS  read-only
        STATUS  mandatory
        DESCRIPTION
                "OSPF Interface Retransmit Interval. The number of
                seconds between link-state advertisement
                retransmissions, for adjacencies belonging to this
                interface. This value is also used when
                retransmitting database description and link-state
                request packets."
        ::= { fmOspfStandardIfEntry 8 }


    fmOspfStandardIfHelloInterval OBJECT-TYPE
        SYNTAX  INTEGER (1..65535)
        ACCESS  read-only
        STATUS  mandatory
        DESCRIPTION
                "OSPF Interface Hello Interval. The length of time,
                in seconds, between the Hello packets that the
                router sends on the interface. This value must be
                the same for all routers attached to a common
                network."
        ::= { fmOspfStandardIfEntry 9 }


    fmOspfStandardIfRtrDeadInterval OBJECT-TYPE
        SYNTAX  INTEGER (1..4294967295)
        ACCESS  read-only
        STATUS  mandatory
        DESCRIPTION
                "OSPF Interface Dead Interval. The number of
                seconds that a router's Hello packets have not
                been seen before it's neighbors declare the router
                down. This should be some multiple of the Hello
                interval. This value must be the same for all
                routers attached to a common network."
        ::= { fmOspfStandardIfEntry 10 }


    fmOspfStandardIfPollInterval OBJECT-TYPE
        SYNTAX  INTEGER (1..4294967295)
        ACCESS  read-only
        STATUS  mandatory
        DESCRIPTION
                "OSPF Interface Poll Interval. The larger time
                interval, in seconds, between the Hello packets
                sent to an inactive non-broadcast multi- access
                neighbor."
        ::= { fmOspfStandardIfEntry 11 }


    fmOspfStandardIfState OBJECT-TYPE
        SYNTAX  INTEGER {
                down(1),
                loopback(2),
                waiting(3),
                pointToPoint(4),
                designatedRouter(5),
                backupDesignatedRouter(6),
                otherDesignatedRouter(7)
                }
        ACCESS  read-only
        STATUS  mandatory
        DESCRIPTION
                "OSPF Interface State. The OSPF Interface State."
        ::= { fmOspfStandardIfEntry 12 }


    fmOspfStandardIfDesignatedRouter OBJECT-TYPE
        SYNTAX  IpAddress
        ACCESS  read-only
        STATUS  mandatory
        DESCRIPTION
                "OSPF Interface Designated Router. The IP Address
                of the Designated Router."
        ::= { fmOspfStandardIfEntry 13 }


    fmOspfStandardIfBackupDesignatedRouter OBJECT-TYPE
        SYNTAX  IpAddress
        ACCESS  read-only
        STATUS  mandatory
        DESCRIPTION
                "OSPF Interface Backup Designated Router. The IP
                Address of the Backup Designated Router.
                "
        ::= { fmOspfStandardIfEntry 14 }


    fmOspfStandardIfEvents OBJECT-TYPE
        SYNTAX  Counter
        ACCESS  read-only
        STATUS  mandatory
        DESCRIPTION
                "OSPF Interface Events. The number of times this
                OSPF interface has changed its state, or an error
                has occurred.
                "
        ::= { fmOspfStandardIfEntry 15 }


    fmOspfStandardIfAuthKey OBJECT-TYPE
        SYNTAX  DisplayString (SIZE(0..255))
        ACCESS  read-only
        STATUS  mandatory
        DESCRIPTION
                "OSPF Interface Authentication Key. The
                Authentication Key. If the Area's Authorization
                Type is simplePassword, and the key length is
                shorter than 8 octets, the agent will left adjust
                and zero fill to 8 octets. When read, it always
                returns an Octet String of length zero."
        ::= { fmOspfStandardIfEntry 16 }


    fmOspfStandardIfMetricTable OBJECT-TYPE
        SYNTAX  SEQUENCE OF FmOspfStandardIfMetricEntry
        ACCESS  not-accessible
        STATUS  mandatory
        DESCRIPTION
                "The TOS metrics for a non-virtual interface
                identified by the interface index."
        ::= { fmOspfStandard 8 }


    fmOspfStandardIfMetricEntry OBJECT-TYPE
        SYNTAX  FmOspfStandardIfMetricEntry
        ACCESS  not-accessible
        STATUS  mandatory
        DESCRIPTION
                "An entry of fmOspfStandardIfMetricTable."
        INDEX   { fmOspfStandardIfMetricIpAddress,
                  fmOspfStandardIfMetricAddressLessIf,
                  fmOspfStandardIfMetricTOS }
        ::= { fmOspfStandardIfMetricTable 1 }


        FmOspfStandardIfMetricEntry ::=
                SEQUENCE {
                    fmOspfStandardIfMetricIpAddress
                        IpAddress,
                    fmOspfStandardIfMetricAddressLessIf
                        INTEGER,
                    fmOspfStandardIfMetricTOS
                        INTEGER,
                    fmOspfStandardIfMetricMetric
                        INTEGER,
                    fmOspfStandardIfMetricStatus
                        INTEGER
                }


    fmOspfStandardIfMetricIpAddress OBJECT-TYPE
        SYNTAX  IpAddress
        ACCESS  read-only
        STATUS  mandatory
        DESCRIPTION
                "OSPF Interface Metric Ip Address. The IP address
                of this OSPF interface. On row creation, this can
                be derived from the instance."
        ::= { fmOspfStandardIfMetricEntry 1 }


    fmOspfStandardIfMetricAddressLessIf OBJECT-TYPE
        SYNTAX  INTEGER (0..35)
        ACCESS  read-only
        STATUS  mandatory
        DESCRIPTION
                "OSPF Interface Metric Address Less If. For the
                purpose of easing the instancing of addressed and
                addressless interfaces; This variable takes the
                value 0 on interfaces with IP Addresses, and the
                value of ifIndex for interfaces having no IP
                Address. On row creation, this can be derived from
                the instance."
        ::= { fmOspfStandardIfMetricEntry 2 }


    fmOspfStandardIfMetricTOS OBJECT-TYPE
        SYNTAX  INTEGER (0..31)
        ACCESS  read-only
        STATUS  mandatory
        DESCRIPTION
                "OSPF Interface Metric TOS. The type of service
                metric being referenced. On row creation, this can
                be derived from the instance."
        ::= { fmOspfStandardIfMetricEntry 3 }


    fmOspfStandardIfMetricMetric OBJECT-TYPE
        SYNTAX  INTEGER (1..65535)
        ACCESS  read-only
        STATUS  mandatory
        DESCRIPTION
                "OSPF Interface Metric Metric. The metric of using
                this type of service on this interface. The
                default value of the TOS 0 Metric is 10^8 /
                ifSpeed. The value FFFF is distinguished to mean
                'no route via this TOS."
        ::= { fmOspfStandardIfMetricEntry 4 }


    fmOspfStandardIfMetricStatus OBJECT-TYPE
        SYNTAX  INTEGER {
                valid(1),
                invalid(2)
                }
        ACCESS  read-only
        STATUS  mandatory
        DESCRIPTION
                "ID FMSIPOSPF Interface Metric Status. This
                variable displays the validity or invalidity of
                the entry. Setting it to 'invalid' has the effect
                of rendering it inoperative. he internal effect
                (row removal) is implementation dependent."
        ::= { fmOspfStandardIfMetricEntry 5 }


    fmOspfStandardVirtIfTable OBJECT-TYPE
        SYNTAX  SEQUENCE OF FmOspfStandardVirtIfEntry
        ACCESS  not-accessible
        STATUS  mandatory
        DESCRIPTION
                "Information about this router's virtual interfaces."
        ::= { fmOspfStandard 9 }


    fmOspfStandardVirtIfEntry OBJECT-TYPE
        SYNTAX  FmOspfStandardVirtIfEntry
        ACCESS  not-accessible
        STATUS  mandatory
        DESCRIPTION
                "An entry of fmOspfStandardVirtIfTable."
        INDEX   { fmOspfStandardVirtIfAreaID,
                  fmOspfStandardVirtIfNeighbor }
        ::= { fmOspfStandardVirtIfTable 1 }


        FmOspfStandardVirtIfEntry ::=
                SEQUENCE {
                    fmOspfStandardVirtIfAreaID
                        IpAddress,
                    fmOspfStandardVirtIfNeighbor
                        IpAddress,
                    fmOspfStandardVirtIfTransitDelay
                        INTEGER,
                    fmOspfStandardVirtIfRetransInterval
                        INTEGER,
                    fmOspfStandardVirtIfHelloInterval
                        INTEGER,
                    fmOspfStandardVirtIfRtrDeadInterval
                        INTEGER,
                    fmOspfStandardVirtIfState
                        INTEGER,
                    fmOspfStandardVirtIfEvents
                        Counter,
                    fmOspfStandardVirtIfAuthKey
                        DisplayString,
                    fmOspfStandardVirtIfStatus
                        INTEGER
                }


    fmOspfStandardVirtIfAreaID OBJECT-TYPE
        SYNTAX  IpAddress
        ACCESS  read-only
        STATUS  mandatory
        DESCRIPTION
                "OSPF Virtual Interface Area ID. The Transit Area
                that the Virtual Link traverses. By definition,
                this is not 0.0.0.0"
        ::= { fmOspfStandardVirtIfEntry 1 }


    fmOspfStandardVirtIfNeighbor OBJECT-TYPE
        SYNTAX  IpAddress
        ACCESS  read-only
        STATUS  mandatory
        DESCRIPTION
                "OSPF Virtual Interface Neighbor. The Router ID of
                the Virtual Neighbor."
        ::= { fmOspfStandardVirtIfEntry 2 }


    fmOspfStandardVirtIfTransitDelay OBJECT-TYPE
        SYNTAX  INTEGER (1..3600)
        ACCESS  read-only
        STATUS  mandatory
        DESCRIPTION
                "OSPF Virtual Interface Transit Delay. The
                estimated number of seconds it takes to transmit a
                link- state update packet over this interface."
        ::= { fmOspfStandardVirtIfEntry 3 }


    fmOspfStandardVirtIfRetransInterval OBJECT-TYPE
        SYNTAX  INTEGER (1..3600)
        ACCESS  read-only
        STATUS  mandatory
        DESCRIPTION
                "OSPF Virtual Interface Retransmit Interval. The
                number of seconds between link-state advertisement
                retransmissions, for adjacencies belonging to this
                interface. This value is also used when
                retransmitting database description and link-state
                request packets. This value should be well over
                the expected round-trip time."
        ::= { fmOspfStandardVirtIfEntry 4 }


    fmOspfStandardVirtIfHelloInterval OBJECT-TYPE
        SYNTAX  INTEGER (1..65535)
        ACCESS  read-only
        STATUS  mandatory
        DESCRIPTION
                "OSPF Virtual Interface Hello Interval. The length
                of time, in seconds, between the Hello packets
                that the router sends on the interface. This value
                must be the same for the virtual neighbor."
        ::= { fmOspfStandardVirtIfEntry 5 }


    fmOspfStandardVirtIfRtrDeadInterval OBJECT-TYPE
        SYNTAX  INTEGER (1..4294967295)
        ACCESS  read-only
        STATUS  mandatory
        DESCRIPTION
                "OSPF Virtual Interface Router Dead Interval. The
                number of seconds that a router's Hello packets
                have not been seen before it's neighbors declare
                the router down. This should be some multiple of
                the Hello interval. This value must be the same
                for the virtual neighbor."
        ::= { fmOspfStandardVirtIfEntry 6 }


    fmOspfStandardVirtIfState OBJECT-TYPE
        SYNTAX  INTEGER {
                down(1),
                pointToPoint(4)
                }
        ACCESS  read-only
        STATUS  mandatory
        DESCRIPTION
                "OSPF Virtual Interface State. OSPF virtual
                interface states."
        ::= { fmOspfStandardVirtIfEntry 7 }


    fmOspfStandardVirtIfEvents OBJECT-TYPE
        SYNTAX  Counter
        ACCESS  read-only
        STATUS  mandatory
        DESCRIPTION
                "OSPF Virtual Interface Events. The number of state
                changes or error events on this Virtual Link."
        ::= { fmOspfStandardVirtIfEntry 8 }


    fmOspfStandardVirtIfAuthKey OBJECT-TYPE
        SYNTAX  DisplayString (SIZE(0..255))
        ACCESS  read-only
        STATUS  mandatory
        DESCRIPTION
                "OSPF Virtual Interface Authentication Type. If
                Authentication Type is simplePassword, the device
                will left adjust and zero fill to 8 octets. When
                read, ospfVifAuthKey always returns a string of
                length zero."
        ::= { fmOspfStandardVirtIfEntry 9 }


    fmOspfStandardVirtIfStatus OBJECT-TYPE
        SYNTAX  INTEGER {
                valid(1),
                invalid(2)
                }
        ACCESS  read-only
        STATUS  mandatory
        DESCRIPTION
                "OSPF Virtual Interface Status. This variable
                displays the validity or invalidity of the entry.
                Setting it to 'invalid' has the effect of
                rendering it inoperative. The internal effect (row
                removal) is implementation dependent."
        ::= { fmOspfStandardVirtIfEntry 10 }


    fmOspfStandardNbrTable OBJECT-TYPE
        SYNTAX  SEQUENCE OF FmOspfStandardNbrEntry
        ACCESS  not-accessible
        STATUS  mandatory
        DESCRIPTION
                "A table of non-virtual neighbor information."
        ::= { fmOspfStandard 10 }


    fmOspfStandardNbrEntry OBJECT-TYPE
        SYNTAX  FmOspfStandardNbrEntry
        ACCESS  not-accessible
        STATUS  mandatory
        DESCRIPTION
                "An entry of fmOspfStandardNbrTable."
        INDEX   { fmOspfStandardNbrIpAddress,
                  fmOspfStandardNbrAddressLessIndex }
        ::= { fmOspfStandardNbrTable 1 }


        FmOspfStandardNbrEntry ::=
                SEQUENCE {
                    fmOspfStandardNbrIpAddress
                        IpAddress,
                    fmOspfStandardNbrAddressLessIndex
                        INTEGER,
                    fmOspfStandardNbrRtrId
                        IpAddress,
                    fmOspfStandardNbrOptions
                        INTEGER,
                    fmOspfStandardNbrPriority
                        INTEGER,
                    fmOspfStandardNbrState
                        INTEGER,
                    fmOspfStandardNbrEvents
                        Counter,
                    fmOspfStandardNbrLSRetransQLen
                        Gauge,
                    fmOspfStandardNBMANbrStatus
                        INTEGER
                }


    fmOspfStandardNbrIpAddress OBJECT-TYPE
        SYNTAX  IpAddress
        ACCESS  read-only
        STATUS  mandatory
        DESCRIPTION
                "OSPF Neighbor Ip Address. The IP address of this
                neighbor."
        ::= { fmOspfStandardNbrEntry 1 }


    fmOspfStandardNbrAddressLessIndex OBJECT-TYPE
        SYNTAX  INTEGER (0..35)
        ACCESS  read-only
        STATUS  mandatory
        DESCRIPTION
                "OSPF Neighbor Address Less Index. On an interface
                having an IP Address, zero. On addressless
                interfaces, the corresponding value of ifIndex in
                the Internet Standard MIB. On row creation, this
                can be derived from the instance."
        ::= { fmOspfStandardNbrEntry 2 }


    fmOspfStandardNbrRtrId OBJECT-TYPE
        SYNTAX  IpAddress
        ACCESS  read-only
        STATUS  mandatory
        DESCRIPTION
                "OSPF Neighbor Router Id. A 32-bit integer
                (represented as a type IpAddress) uniquely
                identifying the neighboring router in the
                Autonomous System."
        ::= { fmOspfStandardNbrEntry 3 }


    fmOspfStandardNbrOptions OBJECT-TYPE
        SYNTAX  INTEGER (0..255)
        ACCESS  read-only
        STATUS  mandatory
        DESCRIPTION
                "OSPF Neighbor Options. A Bit Mask corresponding to
                the neighbor's options field. Bit 0, if set,
                indicates that the area accepts and operates on
                external information; if zero, it is a stub area.
                Bit 1, if set, indicates that the system will
                operate on Type of Service metrics other than TOS
                0. If zero, the neighbor will ignore all metrics
                except the TOS 0 metric."
        ::= { fmOspfStandardNbrEntry 4 }


    fmOspfStandardNbrPriority OBJECT-TYPE
        SYNTAX  INTEGER (0..255)
        ACCESS  read-only
        STATUS  mandatory
        DESCRIPTION
                "OSPF Neighbor Priority. The priority of this
                neighbor in the designated router election
                algorithm. The value 0 signifies that the neighbor
                is not eligible to become the designated router on
                this particular network.
                "
        ::= { fmOspfStandardNbrEntry 5 }


    fmOspfStandardNbrState OBJECT-TYPE
        SYNTAX  INTEGER {
                down(1),
                attempt(2),
                init(3),
                twoWay(4),
                exchangeStart(5),
                exchange(6),
                loading(7),
                full(8)
                }
        ACCESS  read-only
        STATUS  mandatory
        DESCRIPTION
                "OSPF Neighbor State. The State of the relationship
                with this Neighbor."
        ::= { fmOspfStandardNbrEntry 6 }


    fmOspfStandardNbrEvents OBJECT-TYPE
        SYNTAX  Counter
        ACCESS  read-only
        STATUS  mandatory
        DESCRIPTION
                "OSPF Neighbor Events. The number of times this
                neighbor relationship has changed state, or an
                error has occurred."
        ::= { fmOspfStandardNbrEntry 7 }


    fmOspfStandardNbrLSRetransQLen OBJECT-TYPE
        SYNTAX  Gauge
        ACCESS  read-only
        STATUS  mandatory
        DESCRIPTION
                "OSPF Neighbor LS Retransmit Queue Length. The
                current length of the retransmission queue.
                "
        ::= { fmOspfStandardNbrEntry 8 }


    fmOspfStandardNBMANbrStatus OBJECT-TYPE
        SYNTAX  INTEGER {
                valid(1),
                invalid(2)
                }
        ACCESS  read-only
        STATUS  mandatory
        DESCRIPTION
                "OSPF Neighbor Status. This variable displays the
                validity or invalidity of the entry. Setting it to
                'invalid' has the effect of rendering it
                inoperative. The internal effect (row removal) is
                implementation dependent.
                "
        ::= { fmOspfStandardNbrEntry 9 }


    fmOspfStandardVirtNbrTable OBJECT-TYPE
        SYNTAX  SEQUENCE OF FmOspfStandardVirtNbrEntry
        ACCESS  not-accessible
        STATUS  mandatory
        DESCRIPTION
                "A table of virtual neighbor information."
        ::= { fmOspfStandard 11 }


    fmOspfStandardVirtNbrEntry OBJECT-TYPE
        SYNTAX  FmOspfStandardVirtNbrEntry
        ACCESS  not-accessible
        STATUS  mandatory
        DESCRIPTION
                "An entry of fmOspfStandardVirtNbrTable."
        INDEX   { fmOspfStandardVirtNbrArea,
                  fmOspfStandardVirtNbrRtrId }
        ::= { fmOspfStandardVirtNbrTable 1 }


        FmOspfStandardVirtNbrEntry ::=
                SEQUENCE {
                    fmOspfStandardVirtNbrArea
                        IpAddress,
                    fmOspfStandardVirtNbrRtrId
                        IpAddress,
                    fmOspfStandardVirtNbrIpAddr
                        IpAddress,
                    fmOspfStandardVirtNbrOptions
                        INTEGER,
                    fmOspfStandardVirtNbrState
                        INTEGER,
                    fmOspfStandardVirtNbrEvents
                        Counter,
                    fmOspfStandardVirtNbrLSRetransQLen
                        Gauge
                }


    fmOspfStandardVirtNbrArea OBJECT-TYPE
        SYNTAX  IpAddress
        ACCESS  read-only
        STATUS  mandatory
        DESCRIPTION
                "OSPF Virtual Neighbor Area. The Transit Area
                Identifier."
        ::= { fmOspfStandardVirtNbrEntry 1 }


    fmOspfStandardVirtNbrRtrId OBJECT-TYPE
        SYNTAX  IpAddress
        ACCESS  read-only
        STATUS  mandatory
        DESCRIPTION
                "OSPF Virtual Neighbor Router Id. A 32-bit integer
                uniquely identifying the neighboring router in the
                Autonomous System."
        ::= { fmOspfStandardVirtNbrEntry 2 }


    fmOspfStandardVirtNbrIpAddr OBJECT-TYPE
        SYNTAX  IpAddress
        ACCESS  read-only
        STATUS  mandatory
        DESCRIPTION
                "OSPF Virtual Neighbor Ip Address. The IP address
                this Virtual Neighbor is using."
        ::= { fmOspfStandardVirtNbrEntry 3 }


    fmOspfStandardVirtNbrOptions OBJECT-TYPE
        SYNTAX  INTEGER (0..255)
        ACCESS  read-only
        STATUS  mandatory
        DESCRIPTION
                "OSPF Virtual Neighbor Options. A bit map
                corresponding to the neighbor's options field.
                Thus, Bit 1, if set, indicates that the neighbor
                supports Type of Service Routing; if zero, no
                metrics other than TOS 0 are in use by the
                neighbor."
        ::= { fmOspfStandardVirtNbrEntry 4 }


    fmOspfStandardVirtNbrState OBJECT-TYPE
        SYNTAX  INTEGER {
                down(1),
                attempt(2),
                init(3),
                twoWay(4),
                exchangeStart(5),
                exchange(6),
                loading(7),
                full(8)
                }
        ACCESS  read-only
        STATUS  mandatory
        DESCRIPTION
                "OSPF Virtual Neighbor State. The state of the
                Virtual Neighbor Relationship."
        ::= { fmOspfStandardVirtNbrEntry 5 }


    fmOspfStandardVirtNbrEvents OBJECT-TYPE
        SYNTAX  Counter
        ACCESS  read-only
        STATUS  mandatory
        DESCRIPTION
                "OSPF Virtual Neighbor Events. The number of times
                this virtual link has changed its state, or an
                error has occurred."
        ::= { fmOspfStandardVirtNbrEntry 6 }


    fmOspfStandardVirtNbrLSRetransQLen OBJECT-TYPE
        SYNTAX  Gauge
        ACCESS  read-only
        STATUS  mandatory
        DESCRIPTION
                "OSPF Virtual Neighbor LS Retransmit Queue Length.
                The current length of the retransmission queue.
                "
        ::= { fmOspfStandardVirtNbrEntry 7 }


    fmUsersRights OBJECT IDENTIFIER ::= { frxManagement 20 }


    fmuVersionRight OBJECT IDENTIFIER ::= { fmUsersRights 1 }


    fmuVersMax OBJECT-TYPE
        SYNTAX  INTEGER (1..15)
        ACCESS  read-only
        STATUS  mandatory
        DESCRIPTION
                "Version max autorisee"
        ::= { fmuVersionRight 1 }


    fmuLineAccess OBJECT IDENTIFIER ::= { fmUsersRights 5 }


    fmuAccessLineNbMax OBJECT-TYPE
        SYNTAX  INTEGER (0..12)
        ACCESS  read-only
        STATUS  mandatory
        DESCRIPTION
                "Nombre max de lignes autorises"
        ::= { fmuLineAccess 1 }


    fmuAccessX25PlsLineNbMax OBJECT-TYPE
        SYNTAX  INTEGER (0..12)
        ACCESS  read-only
        STATUS  mandatory
        DESCRIPTION
                "Nombre max de lignes X25 PLS"
        ::= { fmuLineAccess 2 }


    fmuAccessX25MlpLineNbMax OBJECT-TYPE
        SYNTAX  INTEGER (0..12)
        ACCESS  read-only
        STATUS  mandatory
        DESCRIPTION
                "Nombre max de lignes X25 MLP"
        ::= { fmuLineAccess 3 }


    fmuAccessAsynLineNbMax OBJECT-TYPE
        SYNTAX  INTEGER (0..12)
        ACCESS  read-only
        STATUS  mandatory
        DESCRIPTION
                "Nombre max de lignes Asyn"
        ::= { fmuLineAccess 4 }


    fmuAccessVipLineNbMax OBJECT-TYPE
        SYNTAX  INTEGER (0..12)
        ACCESS  read-only
        STATUS  mandatory
        DESCRIPTION
                "Nombre max de lignes VIP"
        ::= { fmuLineAccess 5 }


    fmuAccessSdlcLineNbMax OBJECT-TYPE
        SYNTAX  INTEGER (0..12)
        ACCESS  read-only
        STATUS  mandatory
        DESCRIPTION
                "Nombre max de lignes SDLC"
        ::= { fmuLineAccess 6 }


    fmuAccessBsc3270LineNbMax OBJECT-TYPE
        SYNTAX  INTEGER (0..12)
        ACCESS  read-only
        STATUS  mandatory
        DESCRIPTION
                "Nombre max de lignes BSC 3270"
        ::= { fmuLineAccess 7 }


    fmuAccessBsc2780LineNbMax OBJECT-TYPE
        SYNTAX  INTEGER (0..12)
        ACCESS  read-only
        STATUS  mandatory
        DESCRIPTION
                "Nombre max de lignes BSC 2780/3780"
        ::= { fmuLineAccess 8 }


    fmuAccessBscTranspLineNbMax OBJECT-TYPE
        SYNTAX  INTEGER (0..12)
        ACCESS  read-only
        STATUS  mandatory
        DESCRIPTION
                "Nombre max de lignes BSC transparent"
        ::= { fmuLineAccess 9 }


    fmuAccessRnisChannelBNbMax OBJECT-TYPE
        SYNTAX  INTEGER (0..12)
        ACCESS  read-only
        STATUS  mandatory
        DESCRIPTION
                "Nombre de canaux B avec signalisation"
        ::= { fmuLineAccess 10 }


    fmuAccessRnisChannelDNbMax OBJECT-TYPE
        SYNTAX  INTEGER (0..12)
        ACCESS  read-only
        STATUS  mandatory
        DESCRIPTION
                "Nombre de canaux D"
        ::= { fmuLineAccess 11 }


    fmuAccessHdlcTranspLineNbMax OBJECT-TYPE
        SYNTAX  INTEGER (0..12)
        ACCESS  read-only
        STATUS  mandatory
        DESCRIPTION
                "Nombre de lignes HDLC transparent"
        ::= { fmuLineAccess 12 }


    fmuAccessFrSuscribLineNbMax OBJECT-TYPE
        SYNTAX  INTEGER (0..12)
        ACCESS  read-only
        STATUS  mandatory
        DESCRIPTION
                "Nombre de lignes Frame Relay abonne"
        ::= { fmuLineAccess 13 }


    fmuAccessFrPublicNetworkLineNbMax OBJECT-TYPE
        SYNTAX  INTEGER (0..12)
        ACCESS  read-only
        STATUS  mandatory
        DESCRIPTION
                "Nombre de lignes Frame Relay parmi FRSE FRTE FRCE"
        ::= { fmuLineAccess 14 }


    fmuAccessFrseLineNbMax OBJECT-TYPE
        SYNTAX  INTEGER (0..12)
        ACCESS  read-only
        STATUS  mandatory
        DESCRIPTION
                "Nombre max de lignes FR SE"
        ::= { fmuLineAccess 15 }


    fmuAccessX29ReroutLineNbMax OBJECT-TYPE
        SYNTAX  INTEGER (0..12)
        ACCESS  read-only
        STATUS  mandatory
        DESCRIPTION
                "Nombre de lignes avec reroutage X29"
        ::= { fmuLineAccess 16 }


    fmuAccessCvfLineNbMax OBJECT-TYPE
        SYNTAX  INTEGER (0..12)
        ACCESS  read-only
        STATUS  mandatory
        DESCRIPTION
                "Nombre de lignes abonnees CVF"
        ::= { fmuLineAccess 17 }


    fmuAccessX75LineNbMax OBJECT-TYPE
        SYNTAX  INTEGER (0..12)
        ACCESS  read-only
        STATUS  mandatory
        DESCRIPTION
                "Nombre max de lignes X75"
        ::= { fmuLineAccess 18 }


    fmuAccessPaviLineNbMax OBJECT-TYPE
        SYNTAX  INTEGER (0..12)
        ACCESS  read-only
        STATUS  mandatory
        DESCRIPTION
                "Nombre max de lignes PAVI"
        ::= { fmuLineAccess 19 }


    fmuAccessX28PlusLineNbMax OBJECT-TYPE
        SYNTAX  INTEGER (0..12)
        ACCESS  read-only
        STATUS  mandatory
        DESCRIPTION
                "Nombre max de lignes X28 Plus"
        ::= { fmuLineAccess 20 }


    fmuAccessPadLineNbMax OBJECT-TYPE
        SYNTAX  INTEGER (0..12)
        ACCESS  read-only
        STATUS  mandatory
        DESCRIPTION
                "Nombre max de lignes PAD multinormes"
        ::= { fmuLineAccess 21 }


    fmuAccessPppaLineNbMax OBJECT-TYPE
        SYNTAX  INTEGER (0..12)
        ACCESS  read-only
        STATUS  mandatory
        DESCRIPTION
                "Nombre max de lignes PPPA"
        ::= { fmuLineAccess 22 }


    fmuAccessPppsLineNbMax OBJECT-TYPE
        SYNTAX  INTEGER (0..12)
        ACCESS  read-only
        STATUS  mandatory
        DESCRIPTION
                "Nombre max de lignes PPPS"
        ::= { fmuLineAccess 23 }


    fmuFunctionRight OBJECT IDENTIFIER ::= { fmUsersRights 10 }


    fmuFunctionRouterAndBridge OBJECT-TYPE
        SYNTAX  INTEGER {
                mcx104-64kbs(1),
                pont(2),
                routeurIP(3),
                pontAndRouteurIP(4)
                }
        ACCESS  read-only
        STATUS  mandatory
        DESCRIPTION
                "Comlan bridge ou routeur"
        ::= { fmuFunctionRight 1 }


    fmuFunctionMemTypeForMCXType4 OBJECT-TYPE
        SYNTAX  INTEGER {
                flash2Mo-ram2Mo(1),
                flash4Mo-ram2Mo(2),
                flash2Mo-ram4Mo(3),
                flash4Mo-ram4Mo(4),
                obsolete-object(5)
                }
        ACCESS  read-only
        STATUS  mandatory
        DESCRIPTION
                "Types de memoires (MCX type 4)"
        ::= { fmuFunctionRight 2 }


    fmuFunctionAccessFrProtoco OBJECT-TYPE
        SYNTAX  INTEGER (0..15)
        ACCESS  read-only
        STATUS  mandatory
        DESCRIPTION
                "Autorisation protocoles FRSNA FRIP FRI FRT"
        ::= { fmuFunctionRight 3 }


    fmuFunctionBridgeAndStp OBJECT-TYPE
        SYNTAX  INTEGER {
                on(1),
                off(2)
                }
        ACCESS  read-only
        STATUS  mandatory
        DESCRIPTION
                "Fonction Pont et STP"
        ::= { fmuFunctionRight 4 }


    fmuFunctionIpRouter OBJECT-TYPE
        SYNTAX  INTEGER {
                on(1),
                off(2)
                }
        ACCESS  read-only
        STATUS  mandatory
        DESCRIPTION
                "Fonction Routeur IP"
        ::= { fmuFunctionRight 5 }


    fmuFunctionIpxRouter OBJECT-TYPE
        SYNTAX  INTEGER {
                on(1),
                off(2)
                }
        ACCESS  read-only
        STATUS  mandatory
        DESCRIPTION
                "Fonction Routeur IPX"
        ::= { fmuFunctionRight 6 }


    fmuFunctionClnpRouter OBJECT-TYPE
        SYNTAX  INTEGER {
                on(1),
                off(2)
                }
        ACCESS  read-only
        STATUS  mandatory
        DESCRIPTION
                "Fonction Routeur CLNP"
        ::= { fmuFunctionRight 7 }


    fmuFunctionLz77Compression OBJECT-TYPE
        SYNTAX  INTEGER {
                on(1),
                off(2)
                }
        ACCESS  read-only
        STATUS  mandatory
        DESCRIPTION
                "Compression LZ77"
        ::= { fmuFunctionRight 8 }


    fmuFunctionLz78Compression OBJECT-TYPE
        SYNTAX  INTEGER {
                on(1),
                off(2)
                }
        ACCESS  read-only
        STATUS  mandatory
        DESCRIPTION
                "Compression LZ78"
        ::= { fmuFunctionRight 9 }


    fmuFunctionSecurCard OBJECT-TYPE
        SYNTAX  INTEGER {
                on(1),
                off(2)
                }
        ACCESS  read-only
        STATUS  mandatory
        DESCRIPTION
                "Droit securise"
        ::= { fmuFunctionRight 10 }


    fmuFunctionLoadStat OBJECT-TYPE
        SYNTAX  INTEGER {
                on(1),
                off(2)
                }
        ACCESS  read-only
        STATUS  mandatory
        DESCRIPTION
                "Statistiques de charge"
        ::= { fmuFunctionRight 11 }


    fmuFunctionOverflowResc OBJECT-TYPE
        SYNTAX  INTEGER {
                on(1),
                off(2)
                }
        ACCESS  read-only
        STATUS  mandatory
        DESCRIPTION
                "Secours-debordement"
        ::= { fmuFunctionRight 12 }


    fmuFunctionPae OBJECT-TYPE
        SYNTAX  INTEGER {
                on(1),
                off(2)
                }
        ACCESS  read-only
        STATUS  mandatory
        DESCRIPTION
                "PAE"
        ::= { fmuFunctionRight 13 }


    fmuFunctionOnlineFileTransfer OBJECT-TYPE
        SYNTAX  INTEGER {
                on(1),
                off(2)
                }
        ACCESS  read-only
        STATUS  mandatory
        DESCRIPTION
                "Transfert de fichiers on line"
        ::= { fmuFunctionRight 14 }


    fmuFunctionDPacket OBJECT-TYPE
        SYNTAX  INTEGER {
                on(1),
                off(2)
                }
        ACCESS  read-only
        STATUS  mandatory
        DESCRIPTION
                "Paquet dans D"
        ::= { fmuFunctionRight 15 }


    fmuFunctionExploitMibUse OBJECT-TYPE
        SYNTAX  INTEGER {
                on(1),
                off(2)
                }
        ACCESS  read-only
        STATUS  mandatory
        DESCRIPTION
                "Droits d'utilisation de la MIB exploitation"
        ::= { fmuFunctionRight 16 }


    fmuFunctionLlcOnEthernet OBJECT-TYPE
        SYNTAX  INTEGER {
                on(1),
                off(2)
                }
        ACCESS  read-only
        STATUS  mandatory
        DESCRIPTION
                "Autorisation LLC sur Ethernet"
        ::= { fmuFunctionRight 17 }


    fmHardwareId OBJECT IDENTIFIER ::= { frxManagement 25 }


    fmhTechnicalsFeatures OBJECT IDENTIFIER ::= { fmHardwareId 1 }


    fmhTechnicEquipmType OBJECT-TYPE
        SYNTAX  INTEGER {
                lmx506-type1(1),
                mcx104(2),
                lmx506-3(3),
                mcx-type1(4),
                mcx-type2(5),
                lmx506-type2(6),
                mcx300B(7),
                mcx300H(8),
                cmd-chd(9),
                frx-msb2-1(10),
                frx-msb2-s2(11),
                vpb(12)
                }
        ACCESS  read-only
        STATUS  mandatory
        DESCRIPTION
                "Type de machine"
        ::= { fmhTechnicalsFeatures 1 }


    fmhTechnicLineNb OBJECT-TYPE
        SYNTAX  INTEGER (3..12)
        ACCESS  read-only
        STATUS  mandatory
        DESCRIPTION
                "Nombre de lignes"
        ::= { fmhTechnicalsFeatures 2 }


    fmhTechnicPromFlashSize OBJECT-TYPE
        SYNTAX  INTEGER {
                flash-512K(1),
                flash-768K(2),
                flash-1M(3),
                flash-1M256(4),
                flash-1M512(5),
                flash-1M768(6),
                flash-2M(7),
                flash-2M256(8),
                flash-2M512(9),
                flash-2M768(10),
                flash-3M(11),
                flash-3M256(12),
                flash-3M512(13),
                flash-3M768(14),
                flash-4M(15),
                flash-6M(16),
                flash-8M(17),
                flash-10M(18),
                flash-12M(19),
                flash-14M(20),
                flash-16M(21)
                }
        ACCESS  read-only
        STATUS  mandatory
        DESCRIPTION
                "Taille de la PROM Flash"
        ::= { fmhTechnicalsFeatures 3 }


    fmhTechnicRamSize OBJECT-TYPE
        SYNTAX  INTEGER {
                ram-512K(1),
                ram-1M(2),
                ram-1M512(3),
                ram-2M(4),
                ram-4M(5),
                ram-8M(6),
                ram-16M(7),
                ram-32M(8)
                }
        ACCESS  read-only
        STATUS  mandatory
        DESCRIPTION
                "Taille de la RAM"
        ::= { fmhTechnicalsFeatures 4 }


    fmhTechnicEepromSize OBJECT-TYPE
        SYNTAX  INTEGER {
                eeprom-32K(1),
                eeprom-64K(2),
                eeprom-128K(3),
                eeprom-256K(4)
                }
        ACCESS  read-only
        STATUS  mandatory
        DESCRIPTION
                "Taille de l'EEPROM"
        ::= { fmhTechnicalsFeatures 5 }


    fmhTechnicTransputerPresence OBJECT-TYPE
        SYNTAX  INTEGER {
                notpresent(1),
                present(2)
                }
        ACCESS  read-only
        STATUS  mandatory
        DESCRIPTION
                "Presence Transputer"
        ::= { fmhTechnicalsFeatures 6 }


    fmhTechnicEthernetPresence OBJECT-TYPE
        SYNTAX  INTEGER {
                notpresent(1),
                present(2)
                }
        ACCESS  read-only
        STATUS  mandatory
        DESCRIPTION
                "Presence Ethernet"
        ::= { fmhTechnicalsFeatures 7 }


    fmhTechnicTokenRingPresence OBJECT-TYPE
        SYNTAX  INTEGER {
                notpresent(1),
                present(2)
                }
        ACCESS  read-only
        STATUS  mandatory
        DESCRIPTION
                "Presence Token Ring"
        ::= { fmhTechnicalsFeatures 8 }


    fmhTechnicMacAdress OBJECT-TYPE
        SYNTAX  OCTET STRING (SIZE(6))
        ACCESS  read-only
        STATUS  mandatory
        DESCRIPTION
                "Adresse MAC"
        ::= { fmhTechnicalsFeatures 9 }


    fmhEquipmentId OBJECT IDENTIFIER ::= { fmHardwareId 5 }


    fmhEqIdReference OBJECT-TYPE
        SYNTAX  INTEGER (0..4294967295)
        ACCESS  read-only
        STATUS  mandatory
        DESCRIPTION
                "Reference de l'equipement"
        ::= { fmhEquipmentId 1 }


    fmhEqIdSerialNbEncodingType OBJECT-TYPE
        SYNTAX  INTEGER {
                bcd(1),
                hexa(2)
                }
        ACCESS  read-only
        STATUS  mandatory
        DESCRIPTION
                "Type de codage du numero de serie de l'equipement"
        ::= { fmhEquipmentId 2 }


    fmhEqIdSerialNb OBJECT-TYPE
        SYNTAX  OCTET STRING (SIZE(2))
        ACCESS  read-only
        STATUS  mandatory
        DESCRIPTION
                "Numero de serie de l'equipement"
        ::= { fmhEquipmentId 3 }


    fmhEqIdFactoryReleaseDate OBJECT-TYPE
        SYNTAX  OCTET STRING (SIZE(3))
        ACCESS  read-only
        STATUS  mandatory
        DESCRIPTION
                "Date de sortie d'usine"
        ::= { fmhEquipmentId 4 }


    fmhEqIdFirstFactoryReturnDate OBJECT-TYPE
        SYNTAX  OCTET STRING (SIZE(3))
        ACCESS  read-only
        STATUS  mandatory
        DESCRIPTION
                "Premiere date de retour usine"
        ::= { fmhEquipmentId 5 }


    fmhEqIdSecondFactoryReturnDate OBJECT-TYPE
        SYNTAX  OCTET STRING (SIZE(3))
        ACCESS  read-only
        STATUS  mandatory
        DESCRIPTION
                "Deuxieme date de retour usine"
        ::= { fmhEquipmentId 6 }


    fmhEqIdThirdFactoryReturnDate OBJECT-TYPE
        SYNTAX  OCTET STRING (SIZE(3))
        ACCESS  read-only
        STATUS  mandatory
        DESCRIPTION
                "Troisieme date de retour usine"
        ::= { fmhEquipmentId 7 }


    fmhEqIdFourthFactoryReturnDate OBJECT-TYPE
        SYNTAX  OCTET STRING (SIZE(3))
        ACCESS  read-only
        STATUS  mandatory
        DESCRIPTION
                "Quatrieme date de retour usine"
        ::= { fmhEquipmentId 8 }


    fmhEqIdFifthFactoryReturnDate OBJECT-TYPE
        SYNTAX  OCTET STRING (SIZE(3))
        ACCESS  read-only
        STATUS  mandatory
        DESCRIPTION
                "Cinquieme date de retour usine"
        ::= { fmhEquipmentId 9 }


    fmhE1S2ModuleDescription OBJECT IDENTIFIER ::= { fmHardwareId 10 }


    fmhE1S2ModDescSoftwareVersion OBJECT-TYPE
        SYNTAX  DisplayString (SIZE(0..64))
        ACCESS  read-only
        STATUS  mandatory
        DESCRIPTION
                "Version logicielle"
        ::= { fmhE1S2ModuleDescription 1 }


    fmhE1S2ModDescHardwareVersion OBJECT-TYPE
        SYNTAX  DisplayString (SIZE(0..64))
        ACCESS  read-only
        STATUS  mandatory
        DESCRIPTION
                "Version materielle"
        ::= { fmhE1S2ModuleDescription 2 }


    fmsInverseArp OBJECT IDENTIFIER ::= { frxManagement 26 }


    fmsInArpVirtualPortTable OBJECT-TYPE
        SYNTAX  SEQUENCE OF FmsInArpVirtualPortEntry
        ACCESS  not-accessible
        STATUS  mandatory
        DESCRIPTION
                ""
        ::= { fmsInverseArp 1 }


    fmsInArpVirtualPortEntry OBJECT-TYPE
        SYNTAX  FmsInArpVirtualPortEntry
        ACCESS  not-accessible
        STATUS  mandatory
        DESCRIPTION
                "An entry of fmsInArpVirtualPortTable."
        INDEX   { fmsInArpVpConnX121 }
        ::= { fmsInArpVirtualPortTable 1 }


        FmsInArpVirtualPortEntry ::=
                SEQUENCE {
                    fmsInArpVpConnX121
                        OCTET STRING,
                    fmsInArpVpVirtualPortId
                        INTEGER,
                    fmsInArpVpOutRequests
                        Counter,
                    fmsInArpVpInResponses
                        Counter,
                    fmsInArpVpInRequests
                        Counter,
                    fmsInArpVpOutResponses
                        Counter,
                    fmsInArpVpInverseArpStatus
                        INTEGER,
                    fmsInArpVpRemoteIpAddr
                        IpAddress,
                    fmsInArpVpLocalIpAddr
                        IpAddress
                }


    fmsInArpVpConnX121 OBJECT-TYPE
        SYNTAX  OCTET STRING (SIZE(8))
        ACCESS  read-only
        STATUS  mandatory
        DESCRIPTION
                "X121 address on which an inverse ARP has been done."
        ::= { fmsInArpVirtualPortEntry 1 }


    fmsInArpVpVirtualPortId OBJECT-TYPE
        SYNTAX  INTEGER (0..11)
        ACCESS  read-only
        STATUS  mandatory
        DESCRIPTION
                "Virtual Port Identifier of the Inverse ARP
                statistic."
        ::= { fmsInArpVirtualPortEntry 2 }


    fmsInArpVpOutRequests OBJECT-TYPE
        SYNTAX  Counter
        ACCESS  read-only
        STATUS  mandatory
        DESCRIPTION
                "Number of Inverse ARP request sent on this
                connection."
        ::= { fmsInArpVirtualPortEntry 3 }


    fmsInArpVpInResponses OBJECT-TYPE
        SYNTAX  Counter
        ACCESS  read-only
        STATUS  mandatory
        DESCRIPTION
                "Number of Inverse ARP reply received on the
                connection."
        ::= { fmsInArpVirtualPortEntry 4 }


    fmsInArpVpInRequests OBJECT-TYPE
        SYNTAX  Counter
        ACCESS  read-only
        STATUS  mandatory
        DESCRIPTION
                "Number of Inverse ARP request received on the
                connection."
        ::= { fmsInArpVirtualPortEntry 5 }


    fmsInArpVpOutResponses OBJECT-TYPE
        SYNTAX  Counter
        ACCESS  read-only
        STATUS  mandatory
        DESCRIPTION
                "Number of Inverse ARP reply sent on the connection."
        ::= { fmsInArpVirtualPortEntry 6 }


    fmsInArpVpInverseArpStatus OBJECT-TYPE
        SYNTAX  INTEGER {
                unsuccessful(1),
                successful(2)
                }
        ACCESS  read-only
        STATUS  mandatory
        DESCRIPTION
                "State of the inverse ARP resolution."
        ::= { fmsInArpVirtualPortEntry 7 }


    fmsInArpVpRemoteIpAddr OBJECT-TYPE
        SYNTAX  IpAddress
        ACCESS  read-only
        STATUS  mandatory
        DESCRIPTION
                "Associated remote IP address."
        ::= { fmsInArpVirtualPortEntry 8 }


    fmsInArpVpLocalIpAddr OBJECT-TYPE
        SYNTAX  IpAddress
        ACCESS  read-only
        STATUS  mandatory
        DESCRIPTION
                "Associated local IP address."
        ::= { fmsInArpVirtualPortEntry 9 }


    fmsBootP OBJECT IDENTIFIER ::= { frxManagement 27 }


    fmsBootPClient OBJECT IDENTIFIER ::= { fmsBootP 1 }


    fmsBootPClientStatus OBJECT-TYPE
        SYNTAX  INTEGER {
                notLaunched(1),
                inProgress(2),
                succeed(3),
                failed(4)
                }
        ACCESS  read-only
        STATUS  mandatory
        DESCRIPTION
                "The value of this object identifies result of
                BootP transaction."
        ::= { fmsBootPClient 1 }


    fmsBootPClientFileName OBJECT-TYPE
        SYNTAX  DisplayString (SIZE(0..64))
        ACCESS  read-only
        STATUS  mandatory
        DESCRIPTION
                "The value of this object identifies the file name
                received after bootreply reception."
        ::= { fmsBootPClient 2 }


    fmsBootPClientServerIpAddr OBJECT-TYPE
        SYNTAX  IpAddress
        ACCESS  read-only
        STATUS  mandatory
        DESCRIPTION
                "The value of this object identifies the server IP
                address which has contacted bootp client manager."
        ::= { fmsBootPClient 3 }


    fmsBootPClientGatewayIpAddr OBJECT-TYPE
        SYNTAX  IpAddress
        ACCESS  read-only
        STATUS  mandatory
        DESCRIPTION
                "The value of this object identifies the gateway IP
                address. This field is used in optional
                cross-gateway booting."
        ::= { fmsBootPClient 4 }


    fmsBootPRelayTable OBJECT-TYPE
        SYNTAX  SEQUENCE OF FmsBootPRelayEntry
        ACCESS  not-accessible
        STATUS  mandatory
        DESCRIPTION
                "This table describes the parameters used in BootP
                Relay mode. It gives statistics of BootP packets
                transfers."
        ::= { fmsBootP 10 }


    fmsBootPRelayEntry OBJECT-TYPE
        SYNTAX  FmsBootPRelayEntry
        ACCESS  not-accessible
        STATUS  mandatory
        DESCRIPTION
                "An entry of fmsBootPRelayTable."
        INDEX   { fmsBootPRelayVirtualPortId }
        ::= { fmsBootPRelayTable 1 }


        FmsBootPRelayEntry ::=
                SEQUENCE {
                    fmsBootPRelayVirtualPortId
                        INTEGER,
                    fmsBootPRelayRelayedPkts
                        Counter,
                    fmsBootPRelayDroppedPkts
                        Counter,
                    fmsBootPRelayRecRequests
                        Counter,
                    fmsBootPRelayRecReplies
                        Counter
                }


    fmsBootPRelayVirtualPortId OBJECT-TYPE
        SYNTAX  INTEGER (0..11)
        ACCESS  read-only
        STATUS  mandatory
        DESCRIPTION
                "The value of this object identifies the Virtual
                Port Identifier of BootP Relay statistic."
        ::= { fmsBootPRelayEntry 1 }


    fmsBootPRelayRelayedPkts OBJECT-TYPE
        SYNTAX  Counter
        ACCESS  read-only
        STATUS  mandatory
        DESCRIPTION
                "The value of this object identifies the number of
                packets routed by gateway in the case of BootP
                Relay mode."
        ::= { fmsBootPRelayEntry 2 }


    fmsBootPRelayDroppedPkts OBJECT-TYPE
        SYNTAX  Counter
        ACCESS  read-only
        STATUS  mandatory
        DESCRIPTION
                "The value of this object identifies the number of
                destroyed packets."
        ::= { fmsBootPRelayEntry 3 }


    fmsBootPRelayRecRequests OBJECT-TYPE
        SYNTAX  Counter
        ACCESS  read-only
        STATUS  mandatory
        DESCRIPTION
                "The value of this object identifies the number of
                received packets."
        ::= { fmsBootPRelayEntry 4 }


    fmsBootPRelayRecReplies OBJECT-TYPE
        SYNTAX  Counter
        ACCESS  read-only
        STATUS  mandatory
        DESCRIPTION
                "The value of this object identifies the number of
                received responses."
        ::= { fmsBootPRelayEntry 5 }



    frxStateChange TRAP-TYPE
        ENTERPRISE  pce
        VARIABLES   { fmeTrapLineId,
                      fmeTrapFamilyId,
                      fmeTrapEventType,
                      fmeTrapEventData }
        DESCRIPTION "A frxStateChange trap signifies that a outstanding
                    events takes place. This event is not in frxNodeStateChange,
                    frxLineStateChange, frxLoadAndTrafficEvent, 
                    frxManagementEvent, frxServicesStateChange."
        ::= 5

    frxNodeStateChange TRAP-TYPE
        ENTERPRISE  pce
        VARIABLES   { fmeTrapLineId,
                      fmeTrapFamilyId,
                      fmeTrapEventType,
                      fmeTrapEventData }
        DESCRIPTION "A frxNodeStateChange trap signifies that a state
                    changing takes place in the equipment or in a
                    module."
        ::= 6
    
    frxLineStateChange TRAP-TYPE
        ENTERPRISE  pce
        VARIABLES   { fmeTrapLineId,
                      fmeTrapFamilyId,
                      fmeTrapEventType,
                      fmeTrapEventData }
        DESCRIPTION "A frxLineStateChange trap signifies that a state
                    changing takes place over a SLL (Switched
                    Logical Link), over the level 2 or 3 protocol
                    of the line. It can indicate a charge overflow
                    of the line."
        ::= 7

    frxLoadAndTrafficEvent TRAP-TYPE
        ENTERPRISE  pce
        VARIABLES   { fmeTrapLineId,
                      fmeTrapFamilyId,
                      fmeTrapEventType,
                      fmeTrapEventData }
        DESCRIPTION "A frxLoadAndTrafficEvent trap signifies that the
                    maximum threshold, like the number of virtual circuits,
                    the data frame rejection threshold ..., is reached."
        ::= 8

    frxManagementEvent TRAP-TYPE
        ENTERPRISE  pce
        VARIABLES   { fmeTrapLineId,
                      fmeTrapFamilyId,
                      fmeTrapEventType,
                      fmeTrapEventData }
        DESCRIPTION "A frxManagementEvent trap signifies that a
                    configuration changing takes place or someone
                    behaves on the system."
        ::= 9

    frxServicesStateChange TRAP-TYPE
        ENTERPRISE  pce
        VARIABLES   { fmeTrapLineId,
                      fmeTrapFamilyId,
                      fmeTrapEventType,
                      fmeTrapEventData }
        DESCRIPTION "A frxServicesStateChange trap signifies that something
                    about additional services (securized virtual circuit,
                    compression, regrouping frames) takes place."
        ::= 10


    fdPhysicalPorts OBJECT IDENTIFIER ::= { frxDiagnostic 10 }


    fdpIdentification OBJECT IDENTIFIER ::= { fdPhysicalPorts 1 }


    fdpIdentPhysPortId OBJECT-TYPE
        SYNTAX  INTEGER (0..35)
        ACCESS  read-write
        STATUS  mandatory
        DESCRIPTION
                "The value of this object is the physical port
                number. This value may be modified only if
                fdpIdentPhysPortState is 'notConfigured', 'up' or
                'down'."
        ::= { fdpIdentification 1 }


    fdpIdentPhysPortState OBJECT-TYPE
        SYNTAX  INTEGER {
                notConfigured(1),
                up(2),
                down(3),
                loopBack0(10),
                loopBack3(11),
                remoteLoopBack2(12),
                modemManagement(13)
                }
        ACCESS  read-only
        STATUS  mandatory
        DESCRIPTION
                "The value of this object is the state of the
                physical port identified by fdpIdentPhysPortId."
        ::= { fdpIdentification 3 }


    fdpControl OBJECT IDENTIFIER ::= { fdPhysicalPorts 2 }


    fdpCtrlCommand OBJECT-TYPE
        SYNTAX  INTEGER {
                ready(1),
                up(2),
                down(3)
                }
        ACCESS  read-write
        STATUS  mandatory
        DESCRIPTION
                "The value of this object is the desired state of
                the physical port described in fdpIdentPhysPortId.
                The equipment answers always with the value
                'ready' to a GetRequest on this object."
        ::= { fdpControl 1 }


    fdpCtrlDiagCode OBJECT-TYPE
        SYNTAX  INTEGER {
                noError(1),
                unknownCommand(2),
                noSuchPhysPortId(3),
                noSuchPhysPortType(4),
                badLoopBackType(5),
                deviceDown(6),
                physPortIsTheLinkToManager(7),
                physPortNotMonitored(8)
                }
        ACCESS  read-only
        STATUS  mandatory
        DESCRIPTION
                "The value of this object is the result of the
                last SET on fdpCtrlCommand."
        ::= { fdpControl 10 }


    fdpTest OBJECT IDENTIFIER ::= { fdPhysicalPorts 3 }


    fdpTestLoopBackType OBJECT-TYPE
        SYNTAX  INTEGER {
                loopBack0(1),
                loopBack3(2),
                remoteLoopBack2(3)
                }
        ACCESS  read-write
        STATUS  mandatory
        DESCRIPTION
                "The value of this object is the desired loop type
                run on the physical port described in
                fdpIdentPhysPortId."
        ::= { fdpTest 1 }


    fdpTestOutputPacketsCount OBJECT-TYPE
        SYNTAX  INTEGER (0..99)
        ACCESS  read-write
        STATUS  mandatory
        DESCRIPTION
                "The value of this object is the maximum number of
                messages to be sent during the test. '0' means
                'infinite'."
        ::= { fdpTest 2 }


    fdpTestMaxDuration OBJECT-TYPE
        SYNTAX  INTEGER (10..90)
        ACCESS  read-write
        STATUS  mandatory
        DESCRIPTION
                "The value of this object is the maximum duration
                of the test in seconds."
        ::= { fdpTest 3 }


    fdpTestCommand OBJECT-TYPE
        SYNTAX  INTEGER {
                ready(1),
                start(2),
                stop(3)
                }
        ACCESS  read-write
        STATUS  mandatory
        DESCRIPTION
                "The value of this object permits to start or stop
                the loop test described in fdpTestLoopBackType,
                fdpTestOutputPacketsCount and fdpTestMaxDuration.
                The equipment answers always with the value
                'ready' to a GetRequest on this object."
        ::= { fdpTest 4 }


    fdpTestDiagCode OBJECT-TYPE
        SYNTAX  INTEGER {
                noError(1),
                unknownCommand(2),
                noSuchPhysPortId(3),
                noSuchPhysPortType(4),
                badLoopBackType(5),
                deviceDown(6),
                physPortIsTheLinkToManager(7),
                physPortNotMonitored(8),
                testInProgress(20),
                noTestInProgress(21),
                testStopped(22),
                waitingFirstStatusReport(23),
                atLeastOneInputErrPacket(24),
                atLeastOneLostPacket(25),
                atLeastOneFailedOutputPacket(26),
                noTestIndicator142(27),
                unavailableTest(28),
                loopBackBeforeTimeOut(29),
                loopBackOk(30)
                }
        ACCESS  read-only
        STATUS  mandatory
        DESCRIPTION
                "The value of this object is the result of the
                last SET on fdpTestCommand."
        ::= { fdpTest 10 }


    fdpTestState OBJECT-TYPE
        SYNTAX  INTEGER {
                ready(1),
                waitingFirstStatusReport(2),
                waitingLastStatusReport(3)
                }
        ACCESS  read-only
        STATUS  mandatory
        DESCRIPTION
                "The value of this object is the state of the last
                test started."
        ::= { fdpTest 11 }


    fdpTestOutPktsCounter OBJECT-TYPE
        SYNTAX  INTEGER (0..255)
        ACCESS  read-only
        STATUS  mandatory
        DESCRIPTION
                "The value of this object is the number of
                messages sent during the test."
        ::= { fdpTest 12 }


    fdpTestInPktsCounter OBJECT-TYPE
        SYNTAX  INTEGER (0..255)
        ACCESS  read-only
        STATUS  mandatory
        DESCRIPTION
                "The value of this object is the number of
                messages received during the test."
        ::= { fdpTest 13 }


    fdpTestInErrPktsCounter OBJECT-TYPE
        SYNTAX  INTEGER (0..255)
        ACCESS  read-only
        STATUS  mandatory
        DESCRIPTION
                "The value of this object is the number of
                incorrect messages received during the test."
        ::= { fdpTest 14 }


    fdpTestInErrOctetsCounter OBJECT-TYPE
        SYNTAX  INTEGER (0..65535)
        ACCESS  read-only
        STATUS  mandatory
        DESCRIPTION
                "The value of this object is the number of
                incorrect characters received during the test."
        ::= { fdpTest 15 }


    fdpModemManagement OBJECT IDENTIFIER ::= { fdPhysicalPorts 4 }


    fdpModCommand OBJECT-TYPE
        SYNTAX  INTEGER {
                ready(1),
                open(2),
                close(3)
                }
        ACCESS  read-write
        STATUS  mandatory
        DESCRIPTION
                "The value of this object permits to open or close
                a session with a modem connected on the physical
                port described in fdpIdentPhysPortId. The
                equipment answers always with the value 'ready' to
                a GetRequest on this object."
        ::= { fdpModemManagement 1 }


    fdpModControlData OBJECT-TYPE
        SYNTAX  DisplayString (SIZE(0..32))
        ACCESS  read-write
        STATUS  mandatory
        DESCRIPTION
                "The value of this object is AT Commands to be
                sent to the modem"
        ::= { fdpModemManagement 2 }


    fdpModDiagCode OBJECT-TYPE
        SYNTAX  INTEGER {
                noError(1),
                unknownCommand(2),
                noSuchPhysPortId(3),
                noSuchPhysPortType(4),
                badLoopBackType(5),
                deviceDown(6),
                physPortIsTheLinkToManager(7),
                physPortNotMonitored(8),
                openingSequence(40),
                modemStabilization(41),
                sequenceOpen(42),
                noResponseFromModem(43),
                noSequenceOpen(44),
                sequenceAlreadyOpen(45),
                modemData(46),
                openingSequenceWithoutAtCommand(47)
                }
        ACCESS  read-only
        STATUS  mandatory
        DESCRIPTION
                "The value of this object is the result of the
                last SET on fdpModCommand or fdpModControlData.
                The value 'modemData' means that the modem has
                sent one or several responses which may be seen in
                fdpModResponseTable."
        ::= { fdpModemManagement 10 }


    fdpModResponseTable OBJECT-TYPE
        SYNTAX  SEQUENCE OF FdpModResponseEntry
        ACCESS  not-accessible
        STATUS  mandatory
        DESCRIPTION
                "This table contents the result of the last AT
                commands described in fdpModControlData."
        ::= { fdpModemManagement 15 }


    fdpModResponseEntry OBJECT-TYPE
        SYNTAX  FdpModResponseEntry
        ACCESS  not-accessible
        STATUS  mandatory
        DESCRIPTION
                "An entry of fdpModResponseTable."
        INDEX   { fdpModRespEltNum }
        ::= { fdpModResponseTable 1 }


        FdpModResponseEntry ::=
                SEQUENCE {
                    fdpModRespEltNum
                        INTEGER,
                    fdpModRespElement
                        DisplayString
                }


    fdpModRespEltNum OBJECT-TYPE
        SYNTAX  INTEGER (1..32)
        ACCESS  read-only
        STATUS  mandatory
        DESCRIPTION
                "The value of this object is the identifier of one
                text line of a response of the modem."
        ::= { fdpModResponseEntry 1 }


    fdpModRespElement OBJECT-TYPE
        SYNTAX  DisplayString (SIZE(0..64))
        ACCESS  read-only
        STATUS  mandatory
        DESCRIPTION
                "The value of this object contains the ASCII
                characters of this text line."
        ::= { fdpModResponseEntry 2 }



    cpcDiagnostic OBJECT IDENTIFIER ::= { compacProxySoftware 20 }


    cdPhysicalPorts OBJECT IDENTIFIER ::= { cpcDiagnostic 10 }


    cdpIdentification OBJECT IDENTIFIER ::= { cdPhysicalPorts 1 }


    cdpIdentPhysPortType OBJECT-TYPE
        SYNTAX  INTEGER {
                other (1),
                synchronous (2),
                asynchronous (3)
                }
        ACCESS  read-write
        STATUS  mandatory
        DESCRIPTION
                "Physical port type"
        ::= { cdpIdentification 2 }


    cpcManagement OBJECT IDENTIFIER ::= { compacProxySoftware 10 }


    cmEvents OBJECT IDENTIFIER ::= { cpcManagement 5 }


    cmeEventSynchronize OBJECT-TYPE
        SYNTAX  INTEGER {
                node(1),
                local(2)
                }
        ACCESS  read-write
        STATUS  mandatory
        DESCRIPTION
                "Action."
        ::= { cmEvents 4 }


    cmeClearVirtualCircuitInfo OBJECT IDENTIFIER ::= { cmEvents 5 }


    cmeClearX121Address OBJECT-TYPE
        SYNTAX  DisplayString (SIZE(0..15))
        ACCESS  read-only
        STATUS  mandatory
        DESCRIPTION
                "The value of this object is the X121 address of
                the remote equipment."
        ::= { cmeClearVirtualCircuitInfo 1 }


    cmeClearCallUserData OBJECT-TYPE
        SYNTAX  DisplayString (SIZE(0..20))
        ACCESS  read-only
        STATUS  mandatory
        DESCRIPTION
                "The value of this object is the call user data
                send to the Compac management function."
        ::= { cmeClearVirtualCircuitInfo 2 }


    cmeClearEvent OBJECT-TYPE
        SYNTAX  INTEGER {
                timeout(1),
                x25ClearReceived(2)
                }
        ACCESS  read-only
        STATUS  mandatory
        DESCRIPTION
                "The value of this object is the type of
                X25 failed connection."
        ::= { cmeClearVirtualCircuitInfo 3 }


    cmeClearCause OBJECT-TYPE
        SYNTAX  INTEGER (0..255)
        ACCESS  read-only
        STATUS  mandatory
        DESCRIPTION
                "The value of this object is the X25 clear cause
                number."
        ::= { cmeClearVirtualCircuitInfo 4 }


    cmeClearDiag OBJECT-TYPE
        SYNTAX  INTEGER (0..255)
        ACCESS  read-only
        STATUS  mandatory
        DESCRIPTION
                "The value of this object is the X25 clear
                diagnostic number."
        ::= { cmeClearVirtualCircuitInfo 5 }


    cmeClearTimeStamp OBJECT-TYPE
        SYNTAX  TimeTicks
        ACCESS  read-only
        STATUS  mandatory
        DESCRIPTION
                "The value of this object is the sysUpTime at last
                disconnection time."
        ::= { cmeClearVirtualCircuitInfo 6 }


    cpcFileTransfer OBJECT IDENTIFIER ::= { compacProxySoftware 30 }


    cfFileTransferService OBJECT-TYPE
        SYNTAX  INTEGER { 
                softwareIdentification(1),
                configurationDownloading(2),
                offLineSoftwareDownloading(3),
                configurationUploading(4),
                equipmentReset(5),
                equipmentHalt(6),
                hardwareIdentification(7),
                softwareList(8),
                onLineSoftwareDownloading(9),
                onLineSoftwareDownloadingAndReset(10)
                }
        ACCESS  read-write
        STATUS  mandatory
        DESCRIPTION
                "File Transfer Service"
        ::= { cpcFileTransfer 1 }


    cfConfigurationFileToDownload OBJECT-TYPE
        SYNTAX  DisplayString (SIZE(0..80))
        ACCESS  read-write
        STATUS  mandatory
        DESCRIPTION
                "Name of configuration file to download"
        ::= { cpcFileTransfer 2 }


    cfConfigurationFileToUpload OBJECT-TYPE
        SYNTAX  DisplayString (SIZE(0..80))
        ACCESS  read-write
        STATUS  mandatory
        DESCRIPTION
                "Name of file in which configuration will be
                uploaded"
        ::= { cpcFileTransfer 3 }


    cfSoftwareFileToDownload OBJECT-TYPE
        SYNTAX  DisplayString (SIZE(0..80))
        ACCESS  read-write
        STATUS  mandatory
        DESCRIPTION
                "Name of software file to download"
        ::= { cpcFileTransfer 4 }


    cfStartUpChoiceAfterReset OBJECT-TYPE
        SYNTAX  INTEGER { 
                withDefaultConfiguration(1),
                withCopyOfDefaultToOperational(2),
                withOperationalConfiguration(3)
                }
        ACCESS  read-write
        STATUS  mandatory
        DESCRIPTION
                "Choice of start up after reset"
        ::= { cpcFileTransfer 5 }


    cfModuleToIdentify OBJECT-TYPE
        SYNTAX  INTEGER { 
                module0(1),
                module1(2),
                module2(3),
                calledModule(4)
                }
        ACCESS  read-write
        STATUS  mandatory
        DESCRIPTION
                "Selection of module for hardware identification"
        ::= { cpcFileTransfer 6 }


    cfZoneToIdentify OBJECT-TYPE
        SYNTAX  INTEGER { 
                manufacturerZone(1),
                customerZone(2)
                }
        ACCESS  read-write
        STATUS  mandatory
        DESCRIPTION
                "Selection of zone for hardware identification"
        ::= { cpcFileTransfer 7 }


    cfHardwareIdentificationPassword OBJECT-TYPE
        SYNTAX  DisplayString (SIZE(0..80))
        ACCESS  read-write
        STATUS  mandatory
        DESCRIPTION
                ""
        ::= { cpcFileTransfer 8 }


    cfSoftwareListPassword OBJECT-TYPE
        SYNTAX  DisplayString (SIZE(0..80))
        ACCESS  read-write
        STATUS  mandatory
        DESCRIPTION
                ""
        ::= { cpcFileTransfer 9 }


-- File Transfer Results

    cfServiceReport OBJECT-TYPE
        SYNTAX  INTEGER { 
                normalEndOfService(1),
                abnormalEndOfService(2),
                sessionOpened(3),
                sessionCleared(4)
                }
        ACCESS  read-only
        STATUS  mandatory
        DESCRIPTION
                "Report after service execution"
        ::= { cpcFileTransfer 10 }


    cfVersion OBJECT-TYPE
        SYNTAX  DisplayString (SIZE(0..80))
        ACCESS  read-only
        STATUS  mandatory
        DESCRIPTION
                "Version of equipment returned by software
                identification"
        ::= { cpcFileTransfer 11 }


    cfRevision OBJECT-TYPE
        SYNTAX  DisplayString (SIZE(0..80))
        ACCESS  read-only
        STATUS  mandatory
        DESCRIPTION
                "Revision of equipment returned by software
                identification"
        ::= { cpcFileTransfer 12 }


    cfEdition OBJECT-TYPE
        SYNTAX  DisplayString (SIZE(0..80))
        ACCESS  read-only
        STATUS  mandatory
        DESCRIPTION
                "Edition of equipment returned by software
                identification"
        ::= { cpcFileTransfer 13 }


    cfCpuBoardType OBJECT-TYPE
        SYNTAX  DisplayString (SIZE(0..80))
        ACCESS  read-only
        STATUS  mandatory
        DESCRIPTION
                "Type of CPU board returned by software
                identification"
        ::= { cpcFileTransfer 14 }


    cfProductType OBJECT-TYPE
        SYNTAX  DisplayString (SIZE(0..80))
        ACCESS  read-only
        STATUS  mandatory
        DESCRIPTION
                "Type of product returned by software
                identification"
        ::= { cpcFileTransfer 15 }


    cfConfigurationVersion OBJECT-TYPE
        SYNTAX  DisplayString (SIZE(0..80))
        ACCESS  read-only
        STATUS  mandatory
        DESCRIPTION
                "Version of configuration returned by software
                identification"
        ::= { cpcFileTransfer 16 }


    cfConfigurationRelease OBJECT-TYPE
        SYNTAX  DisplayString (SIZE(0..80))
        ACCESS  read-only
        STATUS  mandatory
        DESCRIPTION
                "Release of configuration returned by software
                identification"
        ::= { cpcFileTransfer 17 }


    cfConfigurationEdition OBJECT-TYPE
        SYNTAX  DisplayString (SIZE(0..80))
        ACCESS  read-only
        STATUS  mandatory
        DESCRIPTION
                "Edition of configuration returned by software
                identification"
        ::= { cpcFileTransfer 18 }


    cfConfigurationDate OBJECT-TYPE
        SYNTAX  DisplayString (SIZE(0..80))
        ACCESS  read-only
        STATUS  mandatory
        DESCRIPTION
                "Date of configuration returned by software
                identification"
        ::= { cpcFileTransfer 19 }


    cfUserField OBJECT-TYPE
        SYNTAX  DisplayString (SIZE(0..80))
        ACCESS  read-only
        STATUS  mandatory
        DESCRIPTION
                "User field returned by software identification"
        ::= { cpcFileTransfer 20 }


    cf12NcNumber35 OBJECT-TYPE
        SYNTAX  DisplayString (SIZE(0..13))
        ACCESS  read-only
        STATUS  mandatory
        DESCRIPTION
                "12NC Number in 35xxxx returned by software
                identification"
        ::= { cpcFileTransfer 21 }


    cf12NcNumber75 OBJECT-TYPE
        SYNTAX  DisplayString (SIZE(0..13))
        ACCESS  read-only
        STATUS  mandatory
        DESCRIPTION
                "12NC Number in 75xxxx returned by software
                identification"
        ::= { cpcFileTransfer 22 }


    cfField1 OBJECT-TYPE
        SYNTAX  DisplayString (SIZE(0..9))
        ACCESS  read-only
        STATUS  mandatory
        DESCRIPTION
                "Field 1 returned by hardware identification"
        ::= { cpcFileTransfer 23 }


    cfField2 OBJECT-TYPE
        SYNTAX  DisplayString (SIZE(0..9))
        ACCESS  read-only
        STATUS  mandatory
        DESCRIPTION
                "Field 2 returned by hardware identification"
        ::= { cpcFileTransfer 24 }


    cfField3 OBJECT-TYPE
        SYNTAX  DisplayString (SIZE(0..9))
        ACCESS  read-only
        STATUS  mandatory
        DESCRIPTION
                "Field 3 returned by hardware identification"
        ::= { cpcFileTransfer 25 }


    cfField4 OBJECT-TYPE
        SYNTAX  DisplayString (SIZE(0..9))
        ACCESS  read-only
        STATUS  mandatory
        DESCRIPTION
                "Field 4 returned by hardware identification"
        ::= { cpcFileTransfer 26 }


    cfFlashSize OBJECT-TYPE
        SYNTAX  DisplayString (SIZE(0..6))
        ACCESS  read-only
        STATUS  mandatory
        DESCRIPTION
                "Flash size returned by hardware identification"
        ::= { cpcFileTransfer 27 }


    cfRamSize OBJECT-TYPE
        SYNTAX  DisplayString (SIZE(0..6))
        ACCESS  read-only
        STATUS  mandatory
        DESCRIPTION
                "RAM size returned by hardware identification"
        ::= { cpcFileTransfer 28 }


    cfEepromSize OBJECT-TYPE
        SYNTAX  DisplayString (SIZE(0..6))
        ACCESS  read-only
        STATUS  mandatory
        DESCRIPTION
                "EEPROM size returned by hardware identification"
        ::= { cpcFileTransfer 29 }


    cfNumberOfLines OBJECT-TYPE
        SYNTAX  DisplayString (SIZE(0..10))
        ACCESS  read-only
        STATUS  mandatory
        DESCRIPTION
                "Number of lines returned by hardware
                identification"
        ::= { cpcFileTransfer 30 }


    cfTransputerPresence OBJECT-TYPE
        SYNTAX  OCTET STRING (SIZE(1))
        ACCESS  read-only
        STATUS  mandatory
        DESCRIPTION
                "Presence of transputer on board returned by hardware
                identification"
        ::= { cpcFileTransfer 31 }


    cfMpbBoardReference255 OBJECT-TYPE
        SYNTAX  DisplayString (SIZE(0..10))
        ACCESS  read-only
        STATUS  mandatory
        DESCRIPTION
                "Reference 255xxxx of the MPB returned by hardware
                identification"
        ::= { cpcFileTransfer 32 }


    cfMpbBoardSerialNumber OBJECT-TYPE
        SYNTAX  DisplayString (SIZE(0..10))
        ACCESS  read-only
        STATUS  mandatory
        DESCRIPTION
                "Serial number of the MPB board returned by
                hardware identification"
        ::= { cpcFileTransfer 33 }


    cfMtbBoardReference255 OBJECT-TYPE
        SYNTAX  DisplayString (SIZE(0..10))
        ACCESS  read-only
        STATUS  mandatory
        DESCRIPTION
                "Reference 255xxxx of the MTB returned by hardware
                identification"
        ::= { cpcFileTransfer 34 }


    cfMtbBoardSerialNumber OBJECT-TYPE
        SYNTAX  DisplayString (SIZE(0..10))
        ACCESS  read-only
        STATUS  mandatory
        DESCRIPTION
                "Serial number of the MTB board returned by
                hardware identification"
        ::= { cpcFileTransfer 35 }


    cfReleaseDate OBJECT-TYPE
        SYNTAX  DisplayString (SIZE(0..10))
        ACCESS  read-only
        STATUS  mandatory
        DESCRIPTION
                "Release date returned by hardware identification"
        ::= { cpcFileTransfer 36 }


    cfFactoryReturnDate1 OBJECT-TYPE
        SYNTAX  DisplayString (SIZE(0..10))
        ACCESS  read-only
        STATUS  mandatory
        DESCRIPTION
                "Factory return date number 1 returned by hardware
                identification"
        ::= { cpcFileTransfer 37 }


    cfFactoryReturnDate2 OBJECT-TYPE
        SYNTAX  DisplayString (SIZE(0..10))
        ACCESS  read-only
        STATUS  mandatory
        DESCRIPTION
                "Factory return date number 2 returned by hardware
                identification"
        ::= { cpcFileTransfer 38 }


    cfFactoryReturnDate3 OBJECT-TYPE
        SYNTAX  DisplayString (SIZE(0..10))
        ACCESS  read-only
        STATUS  mandatory
        DESCRIPTION
                "Factory return date number 3 returned by hardware
                identification"
        ::= { cpcFileTransfer 39 }


    cfFactoryReturnDate4 OBJECT-TYPE
        SYNTAX  DisplayString (SIZE(0..10))
        ACCESS  read-only
        STATUS  mandatory
        DESCRIPTION
                "Factory return date number 4 returned by hardware
                identification"
        ::= { cpcFileTransfer 40 }


    cfFactoryReturnDate5 OBJECT-TYPE
        SYNTAX  DisplayString (SIZE(0..10))
        ACCESS  read-only
        STATUS  mandatory
        DESCRIPTION
                "Factory return date number 5 returned by hardware
                identification"
        ::= { cpcFileTransfer 41 }


    cfSoftwareList OBJECT-TYPE
        SYNTAX  DisplayString (SIZE(0..2048))
        ACCESS  read-only
        STATUS  mandatory
        DESCRIPTION
                "List of software (user's right)"
        ::= { cpcFileTransfer 42 }


--  Proxy agent specific trap

    cpcClearVirtualCircuitEvent TRAP-TYPE
        ENTERPRISE  pce
        VARIABLES   { cmeClearX121Address,
                      cmeClearCallUserData,
                      cmeClearEvent,
                      cmeClearCause,
                      cmeClearDiag }
        DESCRIPTION "A cpcClearVirtualCircuitEvent trap signifies
                    a X25 failed connection between proxy agent
                    and remote equipment."
        ::= 100



    vcControl OBJECT IDENTIFIER ::= { vcxConfig 1 }


    vcCtlDate OBJECT-TYPE
        SYNTAX  OCTET STRING (SIZE(3))
        ACCESS  read-write
        STATUS  mandatory
        DESCRIPTION
                ""
        ::= { vcControl 1 }


    vcCtlHour OBJECT-TYPE
        SYNTAX  TimeTicks
        ACCESS  read-write
        STATUS  mandatory
        DESCRIPTION
                ""
        ::= { vcControl 2 }


    vcCtlConfigCom OBJECT-TYPE
        SYNTAX  INTEGER {
                ready(1),
                check(2),
                load(5),
                save(6),
                hotReset(10)
                }
        ACCESS  read-write
        STATUS  mandatory
        DESCRIPTION
                ""
        ::= { vcControl 3 }


    vcCtlConfigLoad OBJECT-TYPE
        SYNTAX  INTEGER (1..9)
        ACCESS  read-write
        STATUS  mandatory
        DESCRIPTION
                ""
        ::= { vcControl 4 }


    vcCtlErrorTable OBJECT-TYPE
        SYNTAX  SEQUENCE OF VcCtlErrorEntry
        ACCESS  not-accessible
        STATUS  mandatory
        DESCRIPTION
                ""
        ::= { vcControl 10 }


    vcCtlErrorEntry OBJECT-TYPE
        SYNTAX  VcCtlErrorEntry
        ACCESS  not-accessible
        STATUS  mandatory
        DESCRIPTION
                "An entry of vcCtlErrorTable."
        INDEX   { vcCtlErrorIndex }
        ::= { vcCtlErrorTable 1 }


        VcCtlErrorEntry ::=
                SEQUENCE {
                    vcCtlErrorIndex
                        INTEGER,
                    vcCtlErrorCode
                        INTEGER,
                    vcCtlErrorMessage
                        DisplayString,
                    vcCtlErrorTime
                        TimeTicks
                }


    vcCtlErrorIndex OBJECT-TYPE
        SYNTAX  INTEGER (1..8)
        ACCESS  read-only
        STATUS  mandatory
        DESCRIPTION
                ""
        ::= { vcCtlErrorEntry 1 }


    vcCtlErrorCode OBJECT-TYPE
        SYNTAX  INTEGER (0..255)
        ACCESS  read-only
        STATUS  mandatory
        DESCRIPTION
                ""
        ::= { vcCtlErrorEntry 2 }


    vcCtlErrorMessage OBJECT-TYPE
        SYNTAX  DisplayString (SIZE(0..80))
        ACCESS  read-only
        STATUS  mandatory
        DESCRIPTION
                ""
        ::= { vcCtlErrorEntry 3 }


    vcCtlErrorTime OBJECT-TYPE
        SYNTAX  TimeTicks
        ACCESS  read-only
        STATUS  mandatory
        DESCRIPTION
                ""
        ::= { vcCtlErrorEntry 4 }


    vcSystem OBJECT IDENTIFIER ::= { vcxConfig 5 }


    vcSysConfActive OBJECT-TYPE
        SYNTAX  INTEGER {
                s1(1),
                s2(2),
                s3(3),
                s4(4),
                s5(5),
                s6(6),
                s7(7),
                s8(8),
                s9(9),
                w0(10),
                w1(11),
                w2(12),
                w3(13),
                w4(14),
                w5(15),
                w6(16),
                w7(17),
                w8(18),
                w9(19),
                w0-1(20),
                w0-2(21),
                w0-3(22),
                w0-4(23),
                w0-5(24),
                w0-6(25),
                w0-7(26),
                w0-8(27),
                w0-9(28)
                }
        ACCESS  read-write
        STATUS  mandatory
        DESCRIPTION
                ""
        ::= { vcSystem 1 }


    vcSysConfDate OBJECT-TYPE
        SYNTAX  OCTET STRING (SIZE(3))
        ACCESS  read-only
        STATUS  mandatory
        DESCRIPTION
                ""
        ::= { vcSystem 2 }


    vcSysConfHour OBJECT-TYPE
        SYNTAX  TimeTicks
        ACCESS  read-only
        STATUS  mandatory
        DESCRIPTION
                ""
        ::= { vcSystem 3 }


    vcManagement OBJECT IDENTIFIER ::= { vcxConfig 10 }


    vcmAlrmGenTable OBJECT-TYPE
        SYNTAX  SEQUENCE OF VcmAlrmGenEntry
        ACCESS  not-accessible
        STATUS  mandatory
        DESCRIPTION
                ""
        ::= { vcManagement 1 }


    vcmAlrmGenEntry OBJECT-TYPE
        SYNTAX  VcmAlrmGenEntry
        ACCESS  not-accessible
        STATUS  mandatory
        DESCRIPTION
                "An entry of vcmAlrmGenTable."
        INDEX   { vcmAlrmGenFamilyId,
                  vcmAlrmGenTyp }
        ::= { vcmAlrmGenTable 1 }


        VcmAlrmGenEntry ::=
                SEQUENCE {
                    vcmAlrmGenFamilyId
                        INTEGER,
                    vcmAlrmGenTyp
                        INTEGER,
                    vcmAlrmGenTrapSend
                        INTEGER,
                    vcmAlrmGenDisplay
                        INTEGER
                }


    vcmAlrmGenFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmGenEntry 1 }


    vcmAlrmGenTyp OBJECT-TYPE
        SYNTAX  INTEGER {
                lnkReady208(1),
                lnkNotReady209(2),
                fatalError222(3),
                reboot233(4)
                }
        ACCESS  read-only
        STATUS  mandatory
        DESCRIPTION
                ""
        ::= { vcmAlrmGenEntry 2 }


    vcmAlrmGenTrapSend OBJECT-TYPE
        SYNTAX  INTEGER {
                yes(1),
                no(2)
                }
        ACCESS  read-write
        STATUS  mandatory
        DESCRIPTION
                ""
        ::= { vcmAlrmGenEntry 3 }


    vcmAlrmGenDisplay OBJECT-TYPE
        SYNTAX  INTEGER {
                yes(1),
                no(2)
                }
        ACCESS  read-write
        STATUS  mandatory
        DESCRIPTION
                ""
        ::= { vcmAlrmGenEntry 4 }


    vcmAlrmSCTable OBJECT-TYPE
        SYNTAX  SEQUENCE OF VcmAlrmSCEntry
        ACCESS  not-accessible
        STATUS  mandatory
        DESCRIPTION
                ""
        ::= { vcManagement 2 }


    vcmAlrmSCEntry OBJECT-TYPE
        SYNTAX  VcmAlrmSCEntry
        ACCESS  not-accessible
        STATUS  mandatory
        DESCRIPTION
                "An entry of vcmAlrmSCTable."
        INDEX   { vcmAlrmSCFamilyId,
                  vcmAlrmSCTyp }
        ::= { vcmAlrmSCTable 1 }


        VcmAlrmSCEntry ::=
                SEQUENCE {
                    vcmAlrmSCFamilyId
                        INTEGER,
                    vcmAlrmSCTyp
                        INTEGER,
                    vcmAlrmSCTrapSend
                        INTEGER,
                    vcmAlrmSCDisplay
                        INTEGER
                }


    vcmAlrmSCFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmSCEntry 1 }


    vcmAlrmSCTyp OBJECT-TYPE
        SYNTAX  INTEGER {
                scReady210(1),
                scNotReady211(2),
                frAddrError223(3),
                dlciError224(4),
                scNotFree225(5),
                scDynamic226(6),
                scReinit227(7),
                unexpectedFrame230(8)
                }
        ACCESS  read-only
        STATUS  mandatory
        DESCRIPTION
                ""
        ::= { vcmAlrmSCEntry 2 }


    vcmAlrmSCTrapSend OBJECT-TYPE
        SYNTAX  INTEGER {
                yes(1),
                no(2)
                }
        ACCESS  read-write
        STATUS  mandatory
        DESCRIPTION
                ""
        ::= { vcmAlrmSCEntry 3 }


    vcmAlrmSCDisplay OBJECT-TYPE
        SYNTAX  INTEGER {
                yes(1),
                no(2)
                }
        ACCESS  read-write
        STATUS  mandatory
        DESCRIPTION
                ""
        ::= { vcmAlrmSCEntry 4 }


    vcmAlrmVCTable OBJECT-TYPE
        SYNTAX  SEQUENCE OF VcmAlrmVCEntry
        ACCESS  not-accessible
        STATUS  mandatory
        DESCRIPTION
                ""
        ::= { vcManagement 3 }


    vcmAlrmVCEntry OBJECT-TYPE
        SYNTAX  VcmAlrmVCEntry
        ACCESS  not-accessible
        STATUS  mandatory
        DESCRIPTION
                "An entry of vcmAlrmVCTable."
        INDEX   { vcmAlrmVCFamilyId,
                  vcmAlrmVCTyp }
        ::= { vcmAlrmVCTable 1 }


        VcmAlrmVCEntry ::=
                SEQUENCE {
                    vcmAlrmVCFamilyId
                        INTEGER,
                    vcmAlrmVCTyp
                        INTEGER,
                    vcmAlrmVCTrapSend
                        INTEGER,
                    vcmAlrmVCDisplay
                        INTEGER
                }


    vcmAlrmVCFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmVCEntry 1 }


    vcmAlrmVCTyp OBJECT-TYPE
        SYNTAX  INTEGER {
                vcReady212(1),
                vcNotReady213(2),
                lossOfSync220(3),
                syncBack221(4),
                vcRejected231(5),
                endOfReject232(6)
                }
        ACCESS  read-only
        STATUS  mandatory
        DESCRIPTION
                ""
        ::= { vcmAlrmVCEntry 2 }


    vcmAlrmVCTrapSend OBJECT-TYPE
        SYNTAX  INTEGER {
                yes(1),
                no(2)
                }
        ACCESS  read-write
        STATUS  mandatory
        DESCRIPTION
                ""
        ::= { vcmAlrmVCEntry 3 }


    vcmAlrmVCDisplay OBJECT-TYPE
        SYNTAX  INTEGER {
                yes(1),
                no(2)
                }
        ACCESS  read-write
        STATUS  mandatory
        DESCRIPTION
                ""
        ::= { vcmAlrmVCEntry 4 }


    vcmAlrmLMITable OBJECT-TYPE
        SYNTAX  SEQUENCE OF VcmAlrmLMIEntry
        ACCESS  not-accessible
        STATUS  mandatory
        DESCRIPTION
                ""
        ::= { vcManagement 4 }


    vcmAlrmLMIEntry OBJECT-TYPE
        SYNTAX  VcmAlrmLMIEntry
        ACCESS  not-accessible
        STATUS  mandatory
        DESCRIPTION
                "An entry of vcmAlrmLMITable."
        INDEX   { vcmAlrmLMIFamilyId,
                  vcmAlrmLMITyp }
        ::= { vcmAlrmLMITable 1 }


        VcmAlrmLMIEntry ::=
                SEQUENCE {
                    vcmAlrmLMIFamilyId
                        INTEGER,
                    vcmAlrmLMITyp
                        INTEGER,
                    vcmAlrmLMITrapSend
                        INTEGER,
                    vcmAlrmLMIDisplay
                        INTEGER
                }


    vcmAlrmLMIFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmLMIEntry 1 }


    vcmAlrmLMITyp OBJECT-TYPE
        SYNTAX  INTEGER {
                dcnxLmi234(1),
                cnxLmi235(2),
                lmiDlciNotConf236(3),
                lmiIntError237(4)
                }
        ACCESS  read-only
        STATUS  mandatory
        DESCRIPTION
                ""
        ::= { vcmAlrmLMIEntry 2 }


    vcmAlrmLMITrapSend OBJECT-TYPE
        SYNTAX  INTEGER {
                yes(1),
                no(2)
                }
        ACCESS  read-write
        STATUS  mandatory
        DESCRIPTION
                ""
        ::= { vcmAlrmLMIEntry 3 }


    vcmAlrmLMIDisplay OBJECT-TYPE
        SYNTAX  INTEGER {
                yes(1),
                no(2)
                }
        ACCESS  read-write
        STATUS  mandatory
        DESCRIPTION
                ""
        ::= { vcmAlrmLMIEntry 4 }


    vcmAlrmSwTable OBJECT-TYPE
        SYNTAX  SEQUENCE OF VcmAlrmSwEntry
        ACCESS  not-accessible
        STATUS  mandatory
        DESCRIPTION
                ""
        ::= { vcManagement 5 }


    vcmAlrmSwEntry OBJECT-TYPE
        SYNTAX  VcmAlrmSwEntry
        ACCESS  not-accessible
        STATUS  mandatory
        DESCRIPTION
                "An entry of vcmAlrmSwTable."
        INDEX   { vcmAlrmSwFamilyId,
                  vcmAlrmSwTyp }
        ::= { vcmAlrmSwTable 1 }


        VcmAlrmSwEntry ::=
                SEQUENCE {
                    vcmAlrmSwFamilyId
                        INTEGER,
                    vcmAlrmSwTyp
                        INTEGER,
                    vcmAlrmSwTrapSend
                        INTEGER,
                    vcmAlrmSwDisplay
                        INTEGER
                }


    vcmAlrmSwFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmSwEntry 1 }


    vcmAlrmSwTyp OBJECT-TYPE
        SYNTAX  INTEGER {
                outgoingCall238(1),
                incomingCall239(2),
                localDisc240(3),
                remoteDisc241(4),
                backup242(5)
                }
        ACCESS  read-only
        STATUS  mandatory
        DESCRIPTION
                ""
        ::= { vcmAlrmSwEntry 2 }


    vcmAlrmSwTrapSend OBJECT-TYPE
        SYNTAX  INTEGER {
                yes(1),
                no(2)
                }
        ACCESS  read-write
        STATUS  mandatory
        DESCRIPTION
                ""
        ::= { vcmAlrmSwEntry 3 }


    vcmAlrmSwDisplay OBJECT-TYPE
        SYNTAX  INTEGER {
                yes(1),
                no(2)
                }
        ACCESS  read-write
        STATUS  mandatory
        DESCRIPTION
                ""
        ::= { vcmAlrmSwEntry 4 }


    vcmAlrmCmpTable OBJECT-TYPE
        SYNTAX  SEQUENCE OF VcmAlrmCmpEntry
        ACCESS  not-accessible
        STATUS  mandatory
        DESCRIPTION
                ""
        ::= { vcManagement 6 }


    vcmAlrmCmpEntry OBJECT-TYPE
        SYNTAX  VcmAlrmCmpEntry
        ACCESS  not-accessible
        STATUS  mandatory
        DESCRIPTION
                "An entry of vcmAlrmCmpTable."
        INDEX   { vcmAlrmCmpFamilyId,
                  vcmAlrmCmpTyp }
        ::= { vcmAlrmCmpTable 1 }


        VcmAlrmCmpEntry ::=
                SEQUENCE {
                    vcmAlrmCmpFamilyId
                        INTEGER,
                    vcmAlrmCmpTyp
                        INTEGER,
                    vcmAlrmCmpTrapSend
                        INTEGER,
                    vcmAlrmCmpDisplay
                        INTEGER
                }


    vcmAlrmCmpFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmCmpEntry 1 }


    vcmAlrmCmpTyp OBJECT-TYPE
        SYNTAX  INTEGER {
                compOn214(1),
                compOff215(2),
                algoCompNotOk228(3),
                algoCompOk229(4)
                }
        ACCESS  read-only
        STATUS  mandatory
        DESCRIPTION
                ""
        ::= { vcmAlrmCmpEntry 2 }


    vcmAlrmCmpTrapSend OBJECT-TYPE
        SYNTAX  INTEGER {
                yes(1),
                no(2)
                }
        ACCESS  read-write
        STATUS  mandatory
        DESCRIPTION
                ""
        ::= { vcmAlrmCmpEntry 3 }


    vcmAlrmCmpDisplay OBJECT-TYPE
        SYNTAX  INTEGER {
                yes(1),
                no(2)
                }
        ACCESS  read-write
        STATUS  mandatory
        DESCRIPTION
                ""
        ::= { vcmAlrmCmpEntry 4 }


    vcmAlrmFaxTable OBJECT-TYPE
        SYNTAX  SEQUENCE OF VcmAlrmFaxEntry
        ACCESS  not-accessible
        STATUS  mandatory
        DESCRIPTION
                ""
        ::= { vcManagement 7 }


    vcmAlrmFaxEntry OBJECT-TYPE
        SYNTAX  VcmAlrmFaxEntry
        ACCESS  not-accessible
        STATUS  mandatory
        DESCRIPTION
                "An entry of vcmAlrmFaxTable."
        INDEX   { vcmAlrmFaxFamilyId,
                  vcmAlrmFaxTyp }
        ::= { vcmAlrmFaxTable 1 }


        VcmAlrmFaxEntry ::=
                SEQUENCE {
                    vcmAlrmFaxFamilyId
                        INTEGER,
                    vcmAlrmFaxTyp
                        INTEGER,
                    vcmAlrmFaxTrapSend
                        INTEGER,
                    vcmAlrmFaxDisplay
                        INTEGER
                }


    vcmAlrmFaxFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmFaxEntry 1 }


    vcmAlrmFaxTyp OBJECT-TYPE
        SYNTAX  INTEGER {
                faxStart218(1),
                faxEnd219(2)
                }
        ACCESS  read-only
        STATUS  mandatory
        DESCRIPTION
                ""
        ::= { vcmAlrmFaxEntry 2 }


    vcmAlrmFaxTrapSend OBJECT-TYPE
        SYNTAX  INTEGER {
                yes(1),
                no(2)
                }
        ACCESS  read-write
        STATUS  mandatory
        DESCRIPTION
                ""
        ::= { vcmAlrmFaxEntry 3 }


    vcmAlrmFaxDisplay OBJECT-TYPE
        SYNTAX  INTEGER {
                yes(1),
                no(2)
                }
        ACCESS  read-write
        STATUS  mandatory
        DESCRIPTION
                ""
        ::= { vcmAlrmFaxEntry 4 }


    vcmAlrmTftpTable OBJECT-TYPE
        SYNTAX  SEQUENCE OF VcmAlrmTftpEntry
        ACCESS  not-accessible
        STATUS  mandatory
        DESCRIPTION
                ""
        ::= { vcManagement 8 }


    vcmAlrmTftpEntry OBJECT-TYPE
        SYNTAX  VcmAlrmTftpEntry
        ACCESS  not-accessible
        STATUS  mandatory
        DESCRIPTION
                "An entry of vcmAlrmTftpTable."
        INDEX   { vcmAlrmTftpFamilyId,
                  vcmAlrmTftpTyp }
        ::= { vcmAlrmTftpTable 1 }


        VcmAlrmTftpEntry ::=
                SEQUENCE {
                    vcmAlrmTftpFamilyId
                        INTEGER,
                    vcmAlrmTftpTyp
                        INTEGER,
                    vcmAlrmTftpTrapSend
                        INTEGER,
                    vcmAlrmTftpDisplay
                        INTEGER
                }


    vcmAlrmTftpFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmTftpEntry 1 }


    vcmAlrmTftpTyp OBJECT-TYPE
        SYNTAX  INTEGER {
                dwnStart243(1),
                dwnEnd244(2),
                dwnError245(3)
                }
        ACCESS  read-only
        STATUS  mandatory
        DESCRIPTION
                ""
        ::= { vcmAlrmTftpEntry 2 }


    vcmAlrmTftpTrapSend OBJECT-TYPE
        SYNTAX  INTEGER {
                yes(1),
                no(2)
                }
        ACCESS  read-write
        STATUS  mandatory
        DESCRIPTION
                ""
        ::= { vcmAlrmTftpEntry 3 }


    vcmAlrmTftpDisplay OBJECT-TYPE
        SYNTAX  INTEGER {
                yes(1),
                no(2)
                }
        ACCESS  read-write
        STATUS  mandatory
        DESCRIPTION
                ""
        ::= { vcmAlrmTftpEntry 4 }


    vcmAlrmSvcTable OBJECT-TYPE
        SYNTAX  SEQUENCE OF VcmAlrmSvcEntry
        ACCESS  not-accessible
        STATUS  mandatory
        DESCRIPTION
                ""
        ::= { vcManagement 9 }


    vcmAlrmSvcEntry OBJECT-TYPE
        SYNTAX  VcmAlrmSvcEntry
        ACCESS  not-accessible
        STATUS  mandatory
        DESCRIPTION
                "An entry of vcmAlrmSvcTable."
        INDEX   { vcmAlrmSvcFamilyId,
                  vcmAlrmSvcTyp }
        ::= { vcmAlrmSvcTable 1 }


        VcmAlrmSvcEntry ::=
                SEQUENCE {
                    vcmAlrmSvcFamilyId
                        INTEGER,
                    vcmAlrmSvcTyp
                        INTEGER,
                    vcmAlrmSvcTrapSend
                        INTEGER,
                    vcmAlrmSvcDisplay
                        INTEGER
                }


    vcmAlrmSvcFamilyId OBJECT-TYPE
        SYNTAX  INTEGER {
                f00System(1),
                f01Tftp(2),
                f02Junction(3),
                f03Lmi(4),
                f04Svc(5),
                f05Compression(6),
                f06ServiceCanal(7),
                f07Fax(8),
                f08Switching(9)
                }
        ACCESS  read-only
        STATUS  mandatory
        DESCRIPTION
                ""
        ::= { vcmAlrmSvcEntry 1 }


    vcmAlrmSvcTyp OBJECT-TYPE
        SYNTAX  INTEGER {
                svcOutCall246(1),
                svcInCall247(2),
                svcLocalConnect248(3),
                svcLocalDisc249(4),
                svcRemoteDisc250(5),
                svcOutFailCall251(6),
                svcInFailCall252(7)
                }
        ACCESS  read-only
        STATUS  mandatory
        DESCRIPTION
                ""
        ::= { vcmAlrmSvcEntry 2 }


    vcmAlrmSvcTrapSend OBJECT-TYPE
        SYNTAX  INTEGER {
                yes(1),
                no(2)
                }
        ACCESS  read-write
        STATUS  mandatory
        DESCRIPTION
                ""
        ::= { vcmAlrmSvcEntry 3 }


    vcmAlrmSvcDisplay OBJECT-TYPE
        SYNTAX  INTEGER {
                yes(1),
                no(2)
                }
        ACCESS  read-write
        STATUS  mandatory
        DESCRIPTION
                ""
        ::= { vcmAlrmSvcEntry 4 }


    vcInterfaces OBJECT IDENTIFIER ::= { vcxConfig 15 }


    vcfPhysicalPortTable OBJECT-TYPE
        SYNTAX  SEQUENCE OF VcfPhysicalPortEntry
        ACCESS  not-accessible
        STATUS  mandatory
        DESCRIPTION
                ""
        ::= { vcInterfaces 1 }


    vcfPhysicalPortEntry OBJECT-TYPE
        SYNTAX  VcfPhysicalPortEntry
        ACCESS  not-accessible
        STATUS  mandatory
        DESCRIPTION
                "An entry of vcfPhysicalPortTable."
        INDEX   { vcfPhysPortId }
        ::= { vcfPhysicalPortTable 1 }


        VcfPhysicalPortEntry ::=
                SEQUENCE {
                    vcfPhysPortId
                        INTEGER,
                    vcfPhysPortConnector
                        INTEGER
                }


    vcfPhysPortId OBJECT-TYPE
        SYNTAX  INTEGER {
                l0(1),
                l1(2),
                frontPannel(3)
                }
        ACCESS  read-only
        STATUS  mandatory
        DESCRIPTION
                ""
        ::= { vcfPhysicalPortEntry 1 }


    vcfPhysPortConnector OBJECT-TYPE
        SYNTAX  INTEGER {
                db15V11(1),
                db15V28(2),
                din(3)
                }
        ACCESS  read-only
        STATUS  mandatory
        DESCRIPTION
                ""
        ::= { vcfPhysicalPortEntry 2 }


    vcfNumericLines OBJECT IDENTIFIER ::= { vcInterfaces 5 }


    vcfNumericLineTable OBJECT-TYPE
        SYNTAX  SEQUENCE OF VcfNumericLineEntry
        ACCESS  not-accessible
        STATUS  mandatory
        DESCRIPTION
                ""
        ::= { vcfNumericLines 1 }


    vcfNumericLineEntry OBJECT-TYPE
        SYNTAX  VcfNumericLineEntry
        ACCESS  not-accessible
        STATUS  mandatory
        DESCRIPTION
                "An entry of vcfNumericLineTable."
        INDEX   { vcfNumericLineInterfaceId }
        ::= { vcfNumericLineTable 1 }


        VcfNumericLineEntry ::=
                SEQUENCE {
                    vcfNumericLineInterfaceId
                        INTEGER,
                    vcfNumericLineType
                        INTEGER
                }


    vcfNumericLineInterfaceId OBJECT-TYPE
        SYNTAX  INTEGER {
                l0(1),
                l1(2),
                frontPannel(3)
                }
        ACCESS  read-only
        STATUS  mandatory
        DESCRIPTION
                ""
        ::= { vcfNumericLineEntry 1 }


    vcfNumericLineType OBJECT-TYPE
        SYNTAX  INTEGER {
                dataLine(1),
                configurationLine(2),
                debug(3)
                }
        ACCESS  read-only
        STATUS  mandatory
        DESCRIPTION
                ""
        ::= { vcfNumericLineEntry 2 }


    vcfDataLineTable OBJECT-TYPE
        SYNTAX  SEQUENCE OF VcfDataLineEntry
        ACCESS  not-accessible
        STATUS  mandatory
        DESCRIPTION
                ""
        ::= { vcfNumericLines 2 }


    vcfDataLineEntry OBJECT-TYPE
        SYNTAX  VcfDataLineEntry
        ACCESS  not-accessible
        STATUS  mandatory
        DESCRIPTION
                "An entry of vcfDataLineTable."
        INDEX   { vcfDataLineInterfaceId }
        ::= { vcfDataLineTable 1 }


        VcfDataLineEntry ::=
                SEQUENCE {
                    vcfDataLineInterfaceId
                        INTEGER,
                    vcfDataLineRate
                        INTEGER,
                    vcfDataLineRts105
                        INTEGER,
                    vcfDataLineDtr108
                        INTEGER,
                    vcfDataLineCts106
                        INTEGER,
                    vcfDataLineDsr107
                        INTEGER,
                    vcfDataLineDcd109
                        INTEGER
                }


    vcfDataLineInterfaceId OBJECT-TYPE
        SYNTAX  INTEGER {
                l0(1),
                l1(2)
                }
        ACCESS  read-only
        STATUS  mandatory
        DESCRIPTION
                ""
        ::= { vcfDataLineEntry 1 }


    vcfDataLineRate OBJECT-TYPE
        SYNTAX  INTEGER {
                s4800(1),
                s9600(2),
                s19200(3),
                s38400(4),
                s48000(5),
                s56000(6),
                s64000(7),
                s72000(8),
                s128000(9),
                s144000(10),
                s256000(11),
                s512000(12)
                }
        ACCESS  read-write
        STATUS  mandatory
        DESCRIPTION
                ""
        ::= { vcfDataLineEntry 2 }


    vcfDataLineRts105 OBJECT-TYPE
        SYNTAX  INTEGER {
                unused(1),
                used(2),
                standard(3),
                off(4),
                on(5)
                }
        ACCESS  read-write
        STATUS  mandatory
        DESCRIPTION
                ""
        ::= { vcfDataLineEntry 3 }


    vcfDataLineDtr108 OBJECT-TYPE
        SYNTAX  INTEGER {
                unused(1),
                used(2),
                standard(3),
                off(4),
                on(5)
                }
        ACCESS  read-write
        STATUS  mandatory
        DESCRIPTION
                ""
        ::= { vcfDataLineEntry 4 }


    vcfDataLineCts106 OBJECT-TYPE
        SYNTAX  INTEGER {
                unused(1),
                used(2),
                standard(3),
                off(4),
                on(5)
                }
        ACCESS  read-write
        STATUS  mandatory
        DESCRIPTION
                ""
        ::= { vcfDataLineEntry 5 }


    vcfDataLineDsr107 OBJECT-TYPE
        SYNTAX  INTEGER {
                unused(1),
                used(2),
                standard(3),
                off(4),
                on(5)
                }
        ACCESS  read-write
        STATUS  mandatory
        DESCRIPTION
                ""
        ::= { vcfDataLineEntry 6 }


    vcfDataLineDcd109 OBJECT-TYPE
        SYNTAX  INTEGER {
                unused(1),
                used(2),
                standard(3),
                off(4),
                on(5)
                }
        ACCESS  read-write
        STATUS  mandatory
        DESCRIPTION
                ""
        ::= { vcfDataLineEntry 7 }


    vcfConfLineTable OBJECT-TYPE
        SYNTAX  SEQUENCE OF VcfConfLineEntry
        ACCESS  not-accessible
        STATUS  mandatory
        DESCRIPTION
                ""
        ::= { vcfNumericLines 3 }


    vcfConfLineEntry OBJECT-TYPE
        SYNTAX  VcfConfLineEntry
        ACCESS  not-accessible
        STATUS  mandatory
        DESCRIPTION
                "An entry of vcfConfLineTable."
        INDEX   { vcfConfLineInterfaceId }
        ::= { vcfConfLineTable 1 }


        VcfConfLineEntry ::=
                SEQUENCE {
                    vcfConfLineInterfaceId
                        INTEGER,
                    vcfConfLineRate
                        INTEGER
                }


    vcfConfLineInterfaceId OBJECT-TYPE
        SYNTAX  INTEGER {
                l0(1),
                l1(2),
                frontPannel(3)
                }
        ACCESS  read-only
        STATUS  mandatory
        DESCRIPTION
                ""
        ::= { vcfConfLineEntry 1 }


    vcfConfLineRate OBJECT-TYPE
        SYNTAX  INTEGER {
                s4800(1),
                s9600(2),
                s19200(3),
                s38400(4),
                s48000(5),
                s56000(6),
                s64000(7),
                s72000(8),
                s128000(9),
                s144000(10),
                s256000(11),
                s512000(12)
                }
        ACCESS  read-only
        STATUS  mandatory
        DESCRIPTION
                ""
        ::= { vcfConfLineEntry 2 }


    vcFrameRelaySw OBJECT IDENTIFIER ::= { vcxConfig 20 }


    vcFrSwitchingTable OBJECT-TYPE
        SYNTAX  SEQUENCE OF VcFrSwitchingEntry
        ACCESS  not-accessible
        STATUS  mandatory
        DESCRIPTION
                ""
        ::= { vcFrameRelaySw 1 }


    vcFrSwitchingEntry OBJECT-TYPE
        SYNTAX  VcFrSwitchingEntry
        ACCESS  not-accessible
        STATUS  mandatory
        DESCRIPTION
                "An entry of vcFrSwitchingTable."
        INDEX   { vcFrSwL0Dlci,
                  vcFrSwL1Dlci }
        ::= { vcFrSwitchingTable 1 }


        VcFrSwitchingEntry ::=
                SEQUENCE {
                    vcFrSwL0Dlci
                        INTEGER,
                    vcFrSwL1Dlci
                        INTEGER,
                    vcFrSwStatus
                        INTEGER,
                    vcFrSwL0DlciPriority
                        INTEGER,
                    vcFrSwL0MuxEnable
                        INTEGER,
                    vcFrSwL0ChanelIdentifierCID
                        INTEGER,
                    vcFrSwL1DlciPriority
                        INTEGER,
                    vcFrSwL1MuxEnable
                        INTEGER,
                    vcFrSwL1ChanelIdentifierCID
                        INTEGER
                }


    vcFrSwL0Dlci OBJECT-TYPE
        SYNTAX  INTEGER (1..1022)
        ACCESS  read-only
        STATUS  mandatory
        DESCRIPTION
                ""
        ::= { vcFrSwitchingEntry 1 }


    vcFrSwL1Dlci OBJECT-TYPE
        SYNTAX  INTEGER (1..1022)
        ACCESS  read-only
        STATUS  mandatory
        DESCRIPTION
                ""
        ::= { vcFrSwitchingEntry 2 }


    vcFrSwStatus OBJECT-TYPE
        SYNTAX  INTEGER {
                valid(1),
                invalid(2)
                }
        ACCESS  read-write
        STATUS  mandatory
        DESCRIPTION
                ""
        ::= { vcFrSwitchingEntry 3 }


    vcFrSwL0DlciPriority OBJECT-TYPE
        SYNTAX  INTEGER {
                highPriority(1),
                lowPriority(2)
                }
        ACCESS  read-write
        STATUS  mandatory
        DESCRIPTION
                ""
        ::= { vcFrSwitchingEntry 4 }


    vcFrSwL0MuxEnable OBJECT-TYPE
        SYNTAX  INTEGER {
                yes(1),
                no(2)
                }
        ACCESS  read-write
        STATUS  mandatory
        DESCRIPTION
                ""
        ::= { vcFrSwitchingEntry 5 }


    vcFrSwL0ChanelIdentifierCID OBJECT-TYPE
        SYNTAX  INTEGER (0..63)
        ACCESS  read-write
        STATUS  mandatory
        DESCRIPTION
                ""
        ::= { vcFrSwitchingEntry 6 }


    vcFrSwL1DlciPriority OBJECT-TYPE
        SYNTAX  INTEGER {
                highPriority(1),
                lowPriority(2)
                }
        ACCESS  read-write
        STATUS  mandatory
        DESCRIPTION
                ""
        ::= { vcFrSwitchingEntry 7 }


    vcFrSwL1MuxEnable OBJECT-TYPE
        SYNTAX  INTEGER {
                yes(1),
                no(2)
                }
        ACCESS  read-write
        STATUS  mandatory
        DESCRIPTION
                ""
        ::= { vcFrSwitchingEntry 8 }


    vcFrSwL1ChanelIdentifierCID OBJECT-TYPE
        SYNTAX  INTEGER (0..63)
        ACCESS  read-write
        STATUS  mandatory
        DESCRIPTION
                ""
        ::= { vcFrSwitchingEntry 9 }


    vcLogicalPorts OBJECT IDENTIFIER ::= { vcxConfig 25 }


    vclLogicalPortTable OBJECT-TYPE
        SYNTAX  SEQUENCE OF VclLogicalPortEntry
        ACCESS  not-accessible
        STATUS  mandatory
        DESCRIPTION
                ""
        ::= { vcLogicalPorts 1 }


    vclLogicalPortEntry OBJECT-TYPE
        SYNTAX  VclLogicalPortEntry
        ACCESS  not-accessible
        STATUS  mandatory
        DESCRIPTION
                "An entry of vclLogicalPortTable."
        INDEX   { vclLogPortId }
        ::= { vclLogicalPortTable 1 }


        VclLogicalPortEntry ::=
                SEQUENCE {
                    vclLogPortId
                        INTEGER,
                    vclLogPortStatus
                        INTEGER,
                    vclLogPortType
                        INTEGER
                }


    vclLogPortId OBJECT-TYPE
        SYNTAX  INTEGER (0..1)
        ACCESS  read-only
        STATUS  mandatory
        DESCRIPTION
                ""
        ::= { vclLogicalPortEntry 1 }


    vclLogPortStatus OBJECT-TYPE
        SYNTAX  INTEGER {
                valid(1),
                invalid(2)
                }
        ACCESS  read-write
        STATUS  mandatory
        DESCRIPTION
                ""
        ::= { vclLogicalPortEntry 2 }


    vclLogPortType OBJECT-TYPE
        SYNTAX  INTEGER {
                hdlc(1),
                frCe(2),
                frTe(3),
                frSe(4)
                }
        ACCESS  read-write
        STATUS  mandatory
        DESCRIPTION
                ""
        ::= { vclLogicalPortEntry 3 }


    vclHdlcAccessLogPort OBJECT IDENTIFIER ::= { vcLogicalPorts 5 }


    vclHdlcLogPortTable OBJECT-TYPE
        SYNTAX  SEQUENCE OF VclHdlcLogPortEntry
        ACCESS  not-accessible
        STATUS  mandatory
        DESCRIPTION
                ""
        ::= { vclHdlcAccessLogPort 1 }


    vclHdlcLogPortEntry OBJECT-TYPE
        SYNTAX  VclHdlcLogPortEntry
        ACCESS  not-accessible
        STATUS  mandatory
        DESCRIPTION
                "An entry of vclHdlcLogPortTable."
        INDEX   { vclHdlcLpLogPortId }
        ::= { vclHdlcLogPortTable 1 }


        VclHdlcLogPortEntry ::=
                SEQUENCE {
                    vclHdlcLpLogPortId
                        INTEGER,
                    vclHdlcLpFragmentationLength
                        INTEGER,
                    vclHdlcLpRemoteAddress
                        OCTET STRING
                }


    vclHdlcLpLogPortId OBJECT-TYPE
        SYNTAX  INTEGER (0..1)
        ACCESS  read-only
        STATUS  mandatory
        DESCRIPTION
                ""
        ::= { vclHdlcLogPortEntry 1 }


    vclHdlcLpFragmentationLength OBJECT-TYPE
        SYNTAX  INTEGER (60..390)
        ACCESS  read-write
        STATUS  mandatory
        DESCRIPTION
                ""
        ::= { vclHdlcLogPortEntry 2 }


    vclHdlcLpRemoteAddress OBJECT-TYPE
        SYNTAX  OCTET STRING (SIZE(8))
        ACCESS  read-write
        STATUS  mandatory
        DESCRIPTION
                ""
        ::= { vclHdlcLogPortEntry 3 }


    vclFrameRelay OBJECT IDENTIFIER ::= { vcLogicalPorts 10 }


    vclFrCommunicationEquipment OBJECT IDENTIFIER ::= { vclFrameRelay 1 }


    vclFrCeLogPortTable OBJECT-TYPE
        SYNTAX  SEQUENCE OF VclFrCeLogPortEntry
        ACCESS  not-accessible
        STATUS  mandatory
        DESCRIPTION
                ""
        ::= { vclFrCommunicationEquipment 1 }


    vclFrCeLogPortEntry OBJECT-TYPE
        SYNTAX  VclFrCeLogPortEntry
        ACCESS  not-accessible
        STATUS  mandatory
        DESCRIPTION
                "An entry of vclFrCeLogPortTable."
        INDEX   { vclFrCeLpLogPortId }
        ::= { vclFrCeLogPortTable 1 }


        VclFrCeLogPortEntry ::=
                SEQUENCE {
                    vclFrCeLpLogPortId
                        INTEGER,
                    vclFrCeLpInterfaceId
                        INTEGER
                }


    vclFrCeLpLogPortId OBJECT-TYPE
        SYNTAX  INTEGER (0..1)
        ACCESS  read-only
        STATUS  mandatory
        DESCRIPTION
                ""
        ::= { vclFrCeLogPortEntry 1 }


    vclFrCeLpInterfaceId OBJECT-TYPE
        SYNTAX  INTEGER {
                l0(1),
                l1(2)
                }
        ACCESS  read-write
        STATUS  mandatory
        DESCRIPTION
                ""
        ::= { vclFrCeLogPortEntry 2 }


    vclFrTerminalEquipment OBJECT IDENTIFIER ::= { vclFrameRelay 2 }


    vclFrTeLogPortTable OBJECT-TYPE
        SYNTAX  SEQUENCE OF VclFrTeLogPortEntry
        ACCESS  not-accessible
        STATUS  mandatory
        DESCRIPTION
                ""
        ::= { vclFrTerminalEquipment 1 }


    vclFrTeLogPortEntry OBJECT-TYPE
        SYNTAX  VclFrTeLogPortEntry
        ACCESS  not-accessible
        STATUS  mandatory
        DESCRIPTION
                "An entry of vclFrTeLogPortTable."
        INDEX   { vclFrTeLpLogPortId }
        ::= { vclFrTeLogPortTable 1 }


        VclFrTeLogPortEntry ::=
                SEQUENCE {
                    vclFrTeLpLogPortId
                        INTEGER,
                    vclFrTeLpInterfaceId
                        INTEGER,
                    vclFrTeLpConfigId
                        INTEGER,
                    vclFrTeLpLmi
                        INTEGER
                }


    vclFrTeLpLogPortId OBJECT-TYPE
        SYNTAX  INTEGER (0..1)
        ACCESS  read-only
        STATUS  mandatory
        DESCRIPTION
                ""
        ::= { vclFrTeLogPortEntry 1 }


    vclFrTeLpInterfaceId OBJECT-TYPE
        SYNTAX  INTEGER {
                l0(1),
                l1(2)
                }
        ACCESS  read-write
        STATUS  mandatory
        DESCRIPTION
                ""
        ::= { vclFrTeLogPortEntry 2 }


    vclFrTeLpConfigId OBJECT-TYPE
        SYNTAX  INTEGER (0..1)
        ACCESS  read-only
        STATUS  mandatory
        DESCRIPTION
                ""
        ::= { vclFrTeLogPortEntry 3 }


    vclFrTeLpLmi OBJECT-TYPE
        SYNTAX  INTEGER {
                off(1),
                lmiUni(2)
                }
        ACCESS  read-write
        STATUS  mandatory
        DESCRIPTION
                ""
        ::= { vclFrTeLogPortEntry 4 }


    vclFrSwitchEquipment OBJECT IDENTIFIER ::= { vclFrameRelay 3 }


    vclFrSeLogPortTable OBJECT-TYPE
        SYNTAX  SEQUENCE OF VclFrSeLogPortEntry
        ACCESS  not-accessible
        STATUS  mandatory
        DESCRIPTION
                ""
        ::= { vclFrSwitchEquipment 1 }


    vclFrSeLogPortEntry OBJECT-TYPE
        SYNTAX  VclFrSeLogPortEntry
        ACCESS  not-accessible
        STATUS  mandatory
        DESCRIPTION
                "An entry of vclFrSeLogPortTable."
        INDEX   { vclFrSeLpLogPortId }
        ::= { vclFrSeLogPortTable 1 }


        VclFrSeLogPortEntry ::=
                SEQUENCE {
                    vclFrSeLpLogPortId
                        INTEGER,
                    vclFrSeLpInterfaceId
                        INTEGER,
                    vclFrSeLpConfigId
                        INTEGER
                }


    vclFrSeLpLogPortId OBJECT-TYPE
        SYNTAX  INTEGER (0..1)
        ACCESS  read-only
        STATUS  mandatory
        DESCRIPTION
                ""
        ::= { vclFrSeLogPortEntry 1 }


    vclFrSeLpInterfaceId OBJECT-TYPE
        SYNTAX  INTEGER {
                l0(1),
                l1(2)
                }
        ACCESS  read-write
        STATUS  mandatory
        DESCRIPTION
                ""
        ::= { vclFrSeLogPortEntry 2 }


    vclFrSeLpConfigId OBJECT-TYPE
        SYNTAX  INTEGER (0..1)
        ACCESS  read-only
        STATUS  mandatory
        DESCRIPTION
                ""
        ::= { vclFrSeLogPortEntry 3 }


    vclFrConfigurationTe OBJECT IDENTIFIER ::= { vclFrameRelay 4 }


    vclFrLmiParameterTable OBJECT-TYPE
        SYNTAX  SEQUENCE OF VclFrLmiParameterEntry
        ACCESS  not-accessible
        STATUS  mandatory
        DESCRIPTION
                ""
        ::= { vclFrConfigurationTe 1 }


    vclFrLmiParameterEntry OBJECT-TYPE
        SYNTAX  VclFrLmiParameterEntry
        ACCESS  not-accessible
        STATUS  mandatory
        DESCRIPTION
                "An entry of vclFrLmiParameterTable."
        INDEX   { vclFrLmiParaConfigId }
        ::= { vclFrLmiParameterTable 1 }


        VclFrLmiParameterEntry ::=
                SEQUENCE {
                    vclFrLmiParaConfigId
                        INTEGER,
                    vclFrLmiParaDlci
                        INTEGER,
                    vclFrLmiParaStandard
                        INTEGER,
                    vclFrLmiParaAccessibilityCondition
                        INTEGER,
                    vclFrLmiParaN391FullStatusPollCount
                        INTEGER,
                    vclFrLmiParaN392ErrorThreshold
                        INTEGER,
                    vclFrLmiParaN393MonitoredEventCount
                        INTEGER,
                    vclFrLmiParaT391LinkIntegPollTimer
                        INTEGER
                }


    vclFrLmiParaConfigId OBJECT-TYPE
        SYNTAX  INTEGER (0..0)
        ACCESS  read-only
        STATUS  mandatory
        DESCRIPTION
                ""
        ::= { vclFrLmiParameterEntry 1 }


    vclFrLmiParaDlci OBJECT-TYPE
        SYNTAX  INTEGER (0..1023)
        ACCESS  read-write
        STATUS  mandatory
        DESCRIPTION
                ""
        ::= { vclFrLmiParameterEntry 2 }


    vclFrLmiParaStandard OBJECT-TYPE
        SYNTAX  INTEGER {
                ansiT1-617d(1),
                itutQ933a(2)
                }
        ACCESS  read-write
        STATUS  mandatory
        DESCRIPTION
                ""
        ::= { vclFrLmiParameterEntry 3 }


    vclFrLmiParaAccessibilityCondition OBJECT-TYPE
        SYNTAX  INTEGER (0..10)
        ACCESS  read-write
        STATUS  mandatory
        DESCRIPTION
                ""
        ::= { vclFrLmiParameterEntry 4 }


    vclFrLmiParaN391FullStatusPollCount OBJECT-TYPE
        SYNTAX  INTEGER (1..255)
        ACCESS  read-write
        STATUS  mandatory
        DESCRIPTION
                ""
        ::= { vclFrLmiParameterEntry 5 }


    vclFrLmiParaN392ErrorThreshold OBJECT-TYPE
        SYNTAX  INTEGER (1..10)
        ACCESS  read-write
        STATUS  mandatory
        DESCRIPTION
                ""
        ::= { vclFrLmiParameterEntry 6 }


    vclFrLmiParaN393MonitoredEventCount OBJECT-TYPE
        SYNTAX  INTEGER (1..10)
        ACCESS  read-write
        STATUS  mandatory
        DESCRIPTION
                ""
        ::= { vclFrLmiParameterEntry 7 }


    vclFrLmiParaT391LinkIntegPollTimer OBJECT-TYPE
        SYNTAX  INTEGER (5..30)
        ACCESS  read-write
        STATUS  mandatory
        DESCRIPTION
                ""
        ::= { vclFrLmiParameterEntry 8 }


    vclFrConfigurationSe OBJECT IDENTIFIER ::= { vclFrameRelay 5 }


    vclFrSeSignallingTable OBJECT-TYPE
        SYNTAX  SEQUENCE OF VclFrSeSignallingEntry
        ACCESS  not-accessible
        STATUS  mandatory
        DESCRIPTION
                ""
        ::= { vclFrConfigurationSe 1 }


    vclFrSeSignallingEntry OBJECT-TYPE
        SYNTAX  VclFrSeSignallingEntry
        ACCESS  not-accessible
        STATUS  mandatory
        DESCRIPTION
                "An entry of vclFrSeSignallingTable."
        INDEX   { vclFrSeSigConfigId }
        ::= { vclFrSeSignallingTable 1 }


        VclFrSeSignallingEntry ::=
                SEQUENCE {
                    vclFrSeSigConfigId
                        INTEGER,
                    vclFrSeSigOuputTimeout
                        INTEGER,
                    vclFrSeSigSignalOutputWinSize
                        INTEGER,
                    vclFrSeSigN200RetransMaxCount
                        INTEGER,
                    vclFrSeSigT200RetransTimer
                        INTEGER,
                    vclFrSeSigT203InactivityTimer
                        INTEGER,
                    vclFrSeSigT303SetupResponseTimer
                        INTEGER,
                    vclFrSeSigT305DisconnectResponseTimer
                        INTEGER,
                    vclFrSeSigT308ReleaseResponseTimer
                        INTEGER,
                    vclFrSeSigT310CallProceedingTimer
                        INTEGER,
                    vclFrSeSigT316RestartAcknowledgeTimer
                        INTEGER
                }


    vclFrSeSigConfigId OBJECT-TYPE
        SYNTAX  INTEGER (0..0)
        ACCESS  read-only
        STATUS  mandatory
        DESCRIPTION
                ""
        ::= { vclFrSeSignallingEntry 1 }


    vclFrSeSigOuputTimeout OBJECT-TYPE
        SYNTAX  INTEGER (0..51000)
        ACCESS  read-write
        STATUS  mandatory
        DESCRIPTION
                ""
        ::= { vclFrSeSignallingEntry 2 }


    vclFrSeSigSignalOutputWinSize OBJECT-TYPE
        SYNTAX  INTEGER (1..7)
        ACCESS  read-write
        STATUS  mandatory
        DESCRIPTION
                ""
        ::= { vclFrSeSignallingEntry 3 }


    vclFrSeSigN200RetransMaxCount OBJECT-TYPE
        SYNTAX  INTEGER (1..255)
        ACCESS  read-write
        STATUS  mandatory
        DESCRIPTION
                ""
        ::= { vclFrSeSignallingEntry 5 }


    vclFrSeSigT200RetransTimer OBJECT-TYPE
        SYNTAX  INTEGER (0..25500)
        ACCESS  read-write
        STATUS  mandatory
        DESCRIPTION
                ""
        ::= { vclFrSeSignallingEntry 6 }


    vclFrSeSigT203InactivityTimer OBJECT-TYPE
        SYNTAX  INTEGER (0..255)
        ACCESS  read-write
        STATUS  mandatory
        DESCRIPTION
                ""
        ::= { vclFrSeSignallingEntry 7 }


    vclFrSeSigT303SetupResponseTimer OBJECT-TYPE
        SYNTAX  INTEGER (1..255)
        ACCESS  read-write
        STATUS  mandatory
        DESCRIPTION
                ""
        ::= { vclFrSeSignallingEntry 8 }


    vclFrSeSigT305DisconnectResponseTimer OBJECT-TYPE
        SYNTAX  INTEGER (1..255)
        ACCESS  read-write
        STATUS  mandatory
        DESCRIPTION
                ""
        ::= { vclFrSeSignallingEntry 9 }


    vclFrSeSigT308ReleaseResponseTimer OBJECT-TYPE
        SYNTAX  INTEGER (1..255)
        ACCESS  read-write
        STATUS  mandatory
        DESCRIPTION
                ""
        ::= { vclFrSeSignallingEntry 10 }


    vclFrSeSigT310CallProceedingTimer OBJECT-TYPE
        SYNTAX  INTEGER (1..255)
        ACCESS  read-write
        STATUS  mandatory
        DESCRIPTION
                ""
        ::= { vclFrSeSignallingEntry 11 }


    vclFrSeSigT316RestartAcknowledgeTimer OBJECT-TYPE
        SYNTAX  INTEGER (0..255)
        ACCESS  read-write
        STATUS  mandatory
        DESCRIPTION
                ""
        ::= { vclFrSeSignallingEntry 12 }


    vcWanSwitch OBJECT IDENTIFIER ::= { vcxConfig 30 }


    vcwEquipParams OBJECT IDENTIFIER ::= { vcWanSwitch 1 }


    vcwEquipDnicZoAddr OBJECT-TYPE
        SYNTAX  OCTET STRING (SIZE(3))
        ACCESS  read-write
        STATUS  mandatory
        DESCRIPTION
                ""
        ::= { vcwEquipParams 1 }


    vcwEquipVoiceRoutingServicePortAddr OBJECT-TYPE
        SYNTAX  OCTET STRING (SIZE(1))
        ACCESS  read-write
        STATUS  mandatory
        DESCRIPTION
                ""
        ::= { vcwEquipParams 2 }


    vcwEquipIpVirtualPortAddr OBJECT-TYPE
        SYNTAX  OCTET STRING (SIZE(1))
        ACCESS  read-write
        STATUS  mandatory
        DESCRIPTION
                ""
        ::= { vcwEquipParams 3 }


    vcwEquipRemoteConfPortAddr OBJECT-TYPE
        SYNTAX  OCTET STRING (SIZE(1))
        ACCESS  read-write
        STATUS  mandatory
        DESCRIPTION
                ""
        ::= { vcwEquipParams 4 }


    vcwEquipVoiceVirtualPortAddr OBJECT-TYPE
        SYNTAX  OCTET STRING (SIZE(4))
        ACCESS  read-write
        STATUS  mandatory
        DESCRIPTION
                ""
        ::= { vcwEquipParams 5 }


    vcwEquipSVCDisconnectOnCongestion OBJECT-TYPE
        SYNTAX  INTEGER {
                valid(1),
                invalid(2)
                }
        ACCESS  read-write
        STATUS  mandatory
        DESCRIPTION
                ""
        ::= { vcwEquipParams 6 }


    vcwEquipOutLogPort OBJECT-TYPE
        SYNTAX  INTEGER (0..1)
        ACCESS  read-write
        STATUS  mandatory
        DESCRIPTION
                ""
        ::= { vcwEquipParams 7 }


    vcwABPvcLpTable OBJECT-TYPE
        SYNTAX  SEQUENCE OF VcwABPvcLpEntry
        ACCESS  not-accessible
        STATUS  mandatory
        DESCRIPTION
                ""
        ::= { vcWanSwitch 2 }


    vcwABPvcLpEntry OBJECT-TYPE
        SYNTAX  VcwABPvcLpEntry
        ACCESS  not-accessible
        STATUS  mandatory
        DESCRIPTION
                "An entry of vcwABPvcLpTable."
        INDEX   { vcwABPvcLpId }
        ::= { vcwABPvcLpTable 1 }


        VcwABPvcLpEntry ::=
                SEQUENCE {
                    vcwABPvcLpId
                        INTEGER,
                    vcwABPvcLpAddress
                        OCTET STRING
                }


    vcwABPvcLpId OBJECT-TYPE
        SYNTAX  INTEGER (0..1)
        ACCESS  read-only
        STATUS  mandatory
        DESCRIPTION
                ""
        ::= { vcwABPvcLpEntry 1 }


    vcwABPvcLpAddress OBJECT-TYPE
        SYNTAX  OCTET STRING (SIZE(1))
        ACCESS  read-write
        STATUS  mandatory
        DESCRIPTION
                ""
        ::= { vcwABPvcLpEntry 2 }


    vcwWanRouteTable OBJECT-TYPE
        SYNTAX  SEQUENCE OF VcwWanRouteEntry
        ACCESS  not-accessible
        STATUS  mandatory
        DESCRIPTION
                ""
        ::= { vcWanSwitch 3 }


    vcwWanRouteEntry OBJECT-TYPE
        SYNTAX  VcwWanRouteEntry
        ACCESS  not-accessible
        STATUS  mandatory
        DESCRIPTION
                "An entry of vcwWanRouteTable."
        INDEX   { vcwWanRouteDnicZoAddress }
        ::= { vcwWanRouteTable 1 }


        VcwWanRouteEntry ::=
                SEQUENCE {
                    vcwWanRouteDnicZoAddress
                        OCTET STRING,
                    vcwWanRouteStatus
                        INTEGER,
                    vcwWanRouteLogPortId
                        INTEGER
                }


    vcwWanRouteDnicZoAddress OBJECT-TYPE
        SYNTAX  OCTET STRING (SIZE(3))
        ACCESS  read-only
        STATUS  mandatory
        DESCRIPTION
                ""
        ::= { vcwWanRouteEntry 1 }


    vcwWanRouteStatus OBJECT-TYPE
        SYNTAX  INTEGER {
                valid(1),
                invalid(2)
                }
        ACCESS  read-write
        STATUS  mandatory
        DESCRIPTION
                ""
        ::= { vcwWanRouteEntry 2 }


    vcwWanRouteLogPortId OBJECT-TYPE
        SYNTAX  INTEGER (0..1)
        ACCESS  read-write
        STATUS  mandatory
        DESCRIPTION
                ""
        ::= { vcwWanRouteEntry 3 }


    vcVirtualPorts OBJECT IDENTIFIER ::= { vcxConfig 35 }


    vcvVirtualPortTable OBJECT-TYPE
        SYNTAX  SEQUENCE OF VcvVirtualPortEntry
        ACCESS  not-accessible
        STATUS  mandatory
        DESCRIPTION
                ""
        ::= { vcVirtualPorts 1 }


    vcvVirtualPortEntry OBJECT-TYPE
        SYNTAX  VcvVirtualPortEntry
        ACCESS  not-accessible
        STATUS  mandatory
        DESCRIPTION
                "An entry of vcvVirtualPortTable."
        INDEX   { vcvVirtualPortId }
        ::= { vcvVirtualPortTable 1 }


        VcvVirtualPortEntry ::=
                SEQUENCE {
                    vcvVirtualPortId
                        INTEGER
                }


    vcvVirtualPortId OBJECT-TYPE
        SYNTAX  INTEGER {
                vpVoix(1),
                vpIp(2)
                }
        ACCESS  read-only
        STATUS  mandatory
        DESCRIPTION
                ""
        ::= { vcvVirtualPortEntry 1 }


    vcvIpVirtualPort OBJECT IDENTIFIER ::= { vcVirtualPorts 5 }


    vcvIpLocalTable OBJECT-TYPE
        SYNTAX  SEQUENCE OF VcvIpLocalEntry
        ACCESS  not-accessible
        STATUS  mandatory
        DESCRIPTION
                ""
        ::= { vcvIpVirtualPort 1 }


    vcvIpLocalEntry OBJECT-TYPE
        SYNTAX  VcvIpLocalEntry
        ACCESS  not-accessible
        STATUS  mandatory
        DESCRIPTION
                "An entry of vcvIpLocalTable."
        INDEX   { vcvIpLocVirtualPortId }
        ::= { vcvIpLocalTable 1 }


        VcvIpLocalEntry ::=
                SEQUENCE {
                    vcvIpLocVirtualPortId
                        INTEGER,
                    vcvIpLocAddressHost
                        IpAddress,
                    vcvIpLocSubNetMask
                        IpAddress,
                    vcvIpLocMtu
                        INTEGER,
                    vcvIpLocRouteNextHop
                        IpAddress,
                    vcvIpLocMinimumRecallTimer
                        INTEGER,
                    vcvIpLocSvcClearCallTimer
                        INTEGER,
                    vcvIpLocSvcCallRetryCount
                        INTEGER
                }


    vcvIpLocVirtualPortId OBJECT-TYPE
        SYNTAX  INTEGER {
                vpVoix(1),
                vpIp(2)
                }
        ACCESS  read-only
        STATUS  mandatory
        DESCRIPTION
                ""
        ::= { vcvIpLocalEntry 1 }


    vcvIpLocAddressHost OBJECT-TYPE
        SYNTAX  IpAddress
        ACCESS  read-write
        STATUS  mandatory
        DESCRIPTION
                ""
        ::= { vcvIpLocalEntry 2 }


    vcvIpLocSubNetMask OBJECT-TYPE
        SYNTAX  IpAddress
        ACCESS  read-write
        STATUS  mandatory
        DESCRIPTION
                ""
        ::= { vcvIpLocalEntry 3 }


    vcvIpLocMtu OBJECT-TYPE
        SYNTAX  INTEGER (576..9180)
        ACCESS  read-only
        STATUS  mandatory
        DESCRIPTION
                ""
        ::= { vcvIpLocalEntry 4 }


    vcvIpLocRouteNextHop OBJECT-TYPE
        SYNTAX  IpAddress
        ACCESS  read-write
        STATUS  mandatory
        DESCRIPTION
                ""
        ::= { vcvIpLocalEntry 5 }


    vcvIpLocMinimumRecallTimer OBJECT-TYPE
        SYNTAX  INTEGER (0..65535)
        ACCESS  read-write
        STATUS  mandatory
        DESCRIPTION
                ""
        ::= { vcvIpLocalEntry 6 }


    vcvIpLocSvcClearCallTimer OBJECT-TYPE
        SYNTAX  INTEGER (0..65535)
        ACCESS  read-write
        STATUS  mandatory
        DESCRIPTION
                ""
        ::= { vcvIpLocalEntry 7 }


    vcvIpLocSvcCallRetryCount OBJECT-TYPE
        SYNTAX  INTEGER (0..65535)
        ACCESS  read-write
        STATUS  mandatory
        DESCRIPTION
                ""
        ::= { vcvIpLocalEntry 8 }


    vcvSnmp OBJECT IDENTIFIER ::= { vcvIpVirtualPort 5 }


    vcvSnmpGen OBJECT IDENTIFIER ::= { vcvSnmp 1 }


    vcvSnmpGenVirtualPortId OBJECT-TYPE
        SYNTAX  INTEGER {
                vpVoix(1),
                vpIp(2)
                }
        ACCESS  read-write
        STATUS  mandatory
        DESCRIPTION
                ""
        ::= { vcvSnmpGen 1 }


    vcvSnmpGenCommunityStringReadOnly OBJECT-TYPE
        SYNTAX  DisplayString (SIZE(1..14))
        ACCESS  read-write
        STATUS  mandatory
        DESCRIPTION
                ""
        ::= { vcvSnmpGen 2 }


    vcvSnmpGenCommunityStringReadWrite OBJECT-TYPE
        SYNTAX  DisplayString (SIZE(1..14))
        ACCESS  read-write
        STATUS  mandatory
        DESCRIPTION
                ""
        ::= { vcvSnmpGen 3 }


    vcvSnmpGenCommunityStringTrap OBJECT-TYPE
        SYNTAX  DisplayString (SIZE(1..14))
        ACCESS  read-write
        STATUS  mandatory
        DESCRIPTION
                ""
        ::= { vcvSnmpGen 4 }


    vcvSnmpGenAuthenticationFailureTrap OBJECT-TYPE
        SYNTAX  INTEGER {
                off(1),
                on(2)
                }
        ACCESS  read-write
        STATUS  mandatory
        DESCRIPTION
                ""
        ::= { vcvSnmpGen 5 }


    vcvSnmpManagerTable OBJECT-TYPE
        SYNTAX  SEQUENCE OF VcvSnmpManagerEntry
        ACCESS  not-accessible
        STATUS  mandatory
        DESCRIPTION
                ""
        ::= { vcvSnmp 2 }


    vcvSnmpManagerEntry OBJECT-TYPE
        SYNTAX  VcvSnmpManagerEntry
        ACCESS  not-accessible
        STATUS  mandatory
        DESCRIPTION
                "An entry of vcvSnmpManagerTable."
        INDEX   { vcvSnmpManagerIpAddress }
        ::= { vcvSnmpManagerTable 1 }


        VcvSnmpManagerEntry ::=
                SEQUENCE {
                    vcvSnmpManagerIpAddress
                        IpAddress,
                    vcvSnmpManagerStatus
                        INTEGER,
                    vcvSnmpManagerName
                        DisplayString,
                    vcvSnmpManagerSendTraps
                        INTEGER,
                    vcvSnmpManagerTrapsUdpPort
                        INTEGER
                }


    vcvSnmpManagerIpAddress OBJECT-TYPE
        SYNTAX  IpAddress
        ACCESS  read-only
        STATUS  mandatory
        DESCRIPTION
                ""
        ::= { vcvSnmpManagerEntry 1 }


    vcvSnmpManagerStatus OBJECT-TYPE
        SYNTAX  INTEGER {
                valid(1),
                invalid(2)
                }
        ACCESS  read-write
        STATUS  mandatory
        DESCRIPTION
                ""
        ::= { vcvSnmpManagerEntry 2 }


    vcvSnmpManagerName OBJECT-TYPE
        SYNTAX  DisplayString (SIZE(1..12))
        ACCESS  read-write
        STATUS  mandatory
        DESCRIPTION
                ""
        ::= { vcvSnmpManagerEntry 3 }


    vcvSnmpManagerSendTraps OBJECT-TYPE
        SYNTAX  INTEGER {
                off(1),
                on(2)
                }
        ACCESS  read-write
        STATUS  mandatory
        DESCRIPTION
                ""
        ::= { vcvSnmpManagerEntry 4 }


    vcvSnmpManagerTrapsUdpPort OBJECT-TYPE
        SYNTAX  INTEGER (0..65535)
        ACCESS  read-write
        STATUS  mandatory
        DESCRIPTION
                ""
        ::= { vcvSnmpManagerEntry 5 }


    vcvRemoteConfTable OBJECT-TYPE
        SYNTAX  SEQUENCE OF VcvRemoteConfEntry
        ACCESS  not-accessible
        STATUS  mandatory
        DESCRIPTION
                ""
        ::= { vcvSnmp 3 }


    vcvRemoteConfEntry OBJECT-TYPE
        SYNTAX  VcvRemoteConfEntry
        ACCESS  not-accessible
        STATUS  mandatory
        DESCRIPTION
                "An entry of vcvRemoteConfTable."
        INDEX   { vcvRemoteConfName }
        ::= { vcvRemoteConfTable 1 }


        VcvRemoteConfEntry ::=
                SEQUENCE {
                    vcvRemoteConfName
                        DisplayString,
                    vcvRemoteConfStatus
                        INTEGER,
                    vcvRemoteConfWanAddress
                        OCTET STRING
                }


    vcvRemoteConfName OBJECT-TYPE
        SYNTAX  DisplayString (SIZE(1..12))
        ACCESS  read-only
        STATUS  mandatory
        DESCRIPTION
                ""
        ::= { vcvRemoteConfEntry 1 }


    vcvRemoteConfStatus OBJECT-TYPE
        SYNTAX  INTEGER {
                valid(1),
                invalid(2)
                }
        ACCESS  read-write
        STATUS  mandatory
        DESCRIPTION
                ""
        ::= { vcvRemoteConfEntry 2 }


    vcvRemoteConfWanAddress OBJECT-TYPE
        SYNTAX  OCTET STRING (SIZE(8))
        ACCESS  read-write
        STATUS  mandatory
        DESCRIPTION
                ""
        ::= { vcvRemoteConfEntry 3 }


    vcvTftpTable OBJECT-TYPE
        SYNTAX  SEQUENCE OF VcvTftpEntry
        ACCESS  not-accessible
        STATUS  mandatory
        DESCRIPTION
                ""
        ::= { vcvIpVirtualPort 10 }


    vcvTftpEntry OBJECT-TYPE
        SYNTAX  VcvTftpEntry
        ACCESS  not-accessible
        STATUS  mandatory
        DESCRIPTION
                "An entry of vcvTftpTable."
        INDEX   { vcvTftpIpAddress }
        ::= { vcvTftpTable 1 }


        VcvTftpEntry ::=
                SEQUENCE {
                    vcvTftpIpAddress
                        IpAddress,
                    vcvTftpStatus
                        INTEGER,
                    vcvTftpName
                        DisplayString,
                    vcvTftpRetryTimer
                        INTEGER,
                    vcvTftpInactTimer
                        INTEGER
                }


    vcvTftpIpAddress OBJECT-TYPE
        SYNTAX  IpAddress
        ACCESS  read-only
        STATUS  mandatory
        DESCRIPTION
                ""
        ::= { vcvTftpEntry 1 }


    vcvTftpStatus OBJECT-TYPE
        SYNTAX  INTEGER {
                valid(1),
                invalid(2)
                }
        ACCESS  read-write
        STATUS  mandatory
        DESCRIPTION
                ""
        ::= { vcvTftpEntry 2 }


    vcvTftpName OBJECT-TYPE
        SYNTAX  DisplayString (SIZE(1..32))
        ACCESS  read-write
        STATUS  mandatory
        DESCRIPTION
                ""
        ::= { vcvTftpEntry 3 }


    vcvTftpRetryTimer OBJECT-TYPE
        SYNTAX  INTEGER (1..600)
        ACCESS  read-write
        STATUS  mandatory
        DESCRIPTION
                ""
        ::= { vcvTftpEntry 4 }


    vcvTftpInactTimer OBJECT-TYPE
        SYNTAX  INTEGER (10..3600)
        ACCESS  read-write
        STATUS  mandatory
        DESCRIPTION
                ""
        ::= { vcvTftpEntry 5 }


    vcvRemoteNetToMediaTable OBJECT-TYPE
        SYNTAX  SEQUENCE OF VcvRemoteNetToMediaEntry
        ACCESS  not-accessible
        STATUS  mandatory
        DESCRIPTION
                ""
        ::= { vcvIpVirtualPort 15 }


    vcvRemoteNetToMediaEntry OBJECT-TYPE
        SYNTAX  VcvRemoteNetToMediaEntry
        ACCESS  not-accessible
        STATUS  mandatory
        DESCRIPTION
                "An entry of vcvRemoteNetToMediaTable."
        INDEX   { vcvRemNetIpAddress }
        ::= { vcvRemoteNetToMediaTable 1 }


        VcvRemoteNetToMediaEntry ::=
                SEQUENCE {
                    vcvRemNetIpAddress
                        IpAddress,
                    vcvRemNetStatus
                        INTEGER,
                    vcvRemNetWanAddress
                        OCTET STRING,
                    vcvRemNetEncapsulation
                        INTEGER
                }


    vcvRemNetIpAddress OBJECT-TYPE
        SYNTAX  IpAddress
        ACCESS  read-only
        STATUS  mandatory
        DESCRIPTION
                ""
        ::= { vcvRemoteNetToMediaEntry 1 }


    vcvRemNetStatus OBJECT-TYPE
        SYNTAX  INTEGER {
                valid(1),
                invalid(2)
                }
        ACCESS  read-write
        STATUS  mandatory
        DESCRIPTION
                ""
        ::= { vcvRemoteNetToMediaEntry 2 }


    vcvRemNetWanAddress OBJECT-TYPE
        SYNTAX  OCTET STRING (SIZE(8))
        ACCESS  read-write
        STATUS  mandatory
        DESCRIPTION
                ""
        ::= { vcvRemoteNetToMediaEntry 3 }


    vcvRemNetEncapsulation OBJECT-TYPE
        SYNTAX  INTEGER {
                fripSimple(1),
                fripRFC(2)
                }
        ACCESS  read-write
        STATUS  mandatory
        DESCRIPTION
                ""
        ::= { vcvRemoteNetToMediaEntry 4 }


    vcvVoiceVirtualPort OBJECT IDENTIFIER ::= { vcVirtualPorts 10 }


    vcvVoiceGen OBJECT IDENTIFIER ::= { vcvVoiceVirtualPort 1 }


    vcvVoiceVirtualPortId OBJECT-TYPE
        SYNTAX  INTEGER {
                vpVoix(1),
                vpIp(2)
                }
        ACCESS  read-write
        STATUS  mandatory
        DESCRIPTION
                ""
        ::= { vcvVoiceGen 1 }


    vcvVoiceTransportTable OBJECT-TYPE
        SYNTAX  SEQUENCE OF VcvVoiceTransportEntry
        ACCESS  not-accessible
        STATUS  mandatory
        DESCRIPTION
                ""
        ::= { vcvVoiceVirtualPort 2 }


    vcvVoiceTransportEntry OBJECT-TYPE
        SYNTAX  VcvVoiceTransportEntry
        ACCESS  not-accessible
        STATUS  mandatory
        DESCRIPTION
                "An entry of vcvVoiceTransportTable."
        INDEX   { vcvVoiceTransProfileId }
        ::= { vcvVoiceTransportTable 1 }


        VcvVoiceTransportEntry ::=
                SEQUENCE {
                    vcvVoiceTransProfileId
                        INTEGER,
                    vcvVoiceTransEncapsulationMode
                        INTEGER,
                    vcvVoiceTransMaxPayLoadNumber
                        INTEGER,
                    vcvVoiceTransCompressionAlgorithm
                        INTEGER,
                    vcvVoiceTransJitterCompensation
                        INTEGER,
                    vcvVoiceTransVoicePacketsCombination
                        INTEGER,
                    vcvVoiceTransQosBc
                        INTEGER,
                    vcvVoiceTransQosBe
                        INTEGER,
                    vcvVoiceTransQosCir
                        INTEGER
                }


    vcvVoiceTransProfileId OBJECT-TYPE
        SYNTAX  INTEGER (0..1)
        ACCESS  read-write
        STATUS  mandatory
        DESCRIPTION
                ""
        ::= { vcvVoiceTransportEntry 1 }


    vcvVoiceTransEncapsulationMode OBJECT-TYPE
        SYNTAX  INTEGER {
                frf(1),
                private(2)
                }
        ACCESS  read-write
        STATUS  mandatory
        DESCRIPTION
                ""
        ::= { vcvVoiceTransportEntry 2 }


    vcvVoiceTransMaxPayLoadNumber OBJECT-TYPE
        SYNTAX  INTEGER (1..4)
        ACCESS  read-write
        STATUS  mandatory
        DESCRIPTION
                ""
        ::= { vcvVoiceTransportEntry 3 }


    vcvVoiceTransCompressionAlgorithm OBJECT-TYPE
        SYNTAX  INTEGER {
                g728(1),
                celp(2),
                g729(3),
                g729A(4)
                }
        ACCESS  read-write
        STATUS  mandatory
        DESCRIPTION
                ""
        ::= { vcvVoiceTransportEntry 4 }


    vcvVoiceTransJitterCompensation OBJECT-TYPE
        SYNTAX  INTEGER (1..9)
        ACCESS  read-write
        STATUS  mandatory
        DESCRIPTION
                ""
        ::= { vcvVoiceTransportEntry 5 }


    vcvVoiceTransVoicePacketsCombination OBJECT-TYPE
        SYNTAX  INTEGER (1..4)
        ACCESS  read-write
        STATUS  mandatory
        DESCRIPTION
                ""
        ::= { vcvVoiceTransportEntry 6 }


    vcvVoiceTransQosBc OBJECT-TYPE
        SYNTAX  INTEGER {
                s9600(1),
                s14400(2),
                s19200(3),
                s32000(4),
                s38400(5),
                s48000(6)
                }
        ACCESS  read-write
        STATUS  mandatory
        DESCRIPTION
                ""
        ::= { vcvVoiceTransportEntry 7 }


    vcvVoiceTransQosBe OBJECT-TYPE
        SYNTAX  INTEGER {
                s9600(1),
                s14400(2),
                s19200(3),
                s32000(4),
                s38400(5),
                s48000(6)
                }
        ACCESS  read-write
        STATUS  mandatory
        DESCRIPTION
                ""
        ::= { vcvVoiceTransportEntry 8 }


    vcvVoiceTransQosCir OBJECT-TYPE
        SYNTAX  INTEGER {
                s9600(1),
                s14400(2),
                s19200(3),
                s32000(4),
                s38400(5),
                s48000(6)
                }
        ACCESS  read-write
        STATUS  mandatory
        DESCRIPTION
                ""
        ::= { vcvVoiceTransportEntry 9 }


    vcvVoiceSuscriberTable OBJECT-TYPE
        SYNTAX  SEQUENCE OF VcvVoiceSuscriberEntry
        ACCESS  not-accessible
        STATUS  mandatory
        DESCRIPTION
                ""
        ::= { vcvVoiceVirtualPort 3 }


    vcvVoiceSuscriberEntry OBJECT-TYPE
        SYNTAX  VcvVoiceSuscriberEntry
        ACCESS  not-accessible
        STATUS  mandatory
        DESCRIPTION
                "An entry of vcvVoiceSuscriberTable."
        INDEX   { vcvVoiceSuscrOrderNumber,
                  vcvVoiceSuscrNumber }
        ::= { vcvVoiceSuscriberTable 1 }


        VcvVoiceSuscriberEntry ::=
                SEQUENCE {
                    vcvVoiceSuscrOrderNumber
                        INTEGER,
                    vcvVoiceSuscrNumber
                        DisplayString,
                    vcvVoiceSuscrStatus
                        INTEGER,
                    vcvVoiceSuscrTransportNetwork
                        INTEGER,
                    vcvVoiceSuscrTransportNetworkAddress
                        OCTET STRING,
                    vcvVoiceSuscrTransportProfileId
                        INTEGER,
                    vcvVoiceSuscrRemovedDigitNumber
                        INTEGER,
                    vcvVoiceSuscrInsPrefix
                        DisplayString,
                    vcvVoiceSuscrInsSuffix
                        DisplayString
                }


    vcvVoiceSuscrOrderNumber OBJECT-TYPE
        SYNTAX  INTEGER (0..9)
        ACCESS  read-only
        STATUS  mandatory
        DESCRIPTION
                ""
        ::= { vcvVoiceSuscriberEntry 1 }


    vcvVoiceSuscrNumber OBJECT-TYPE
        SYNTAX  DisplayString (SIZE(1..21))
        ACCESS  read-only
        STATUS  mandatory
        DESCRIPTION
                ""
        ::= { vcvVoiceSuscriberEntry 2 }


    vcvVoiceSuscrStatus OBJECT-TYPE
        SYNTAX  INTEGER {
                valid(1),
                invalid(2)
                }
        ACCESS  read-write
        STATUS  mandatory
        DESCRIPTION
                ""
        ::= { vcvVoiceSuscriberEntry 3 }


    vcvVoiceSuscrTransportNetwork OBJECT-TYPE
        SYNTAX  INTEGER {
                fr(1),
                other(2)
                }
        ACCESS  read-only
        STATUS  mandatory
        DESCRIPTION
                ""
        ::= { vcvVoiceSuscriberEntry 4 }


    vcvVoiceSuscrTransportNetworkAddress OBJECT-TYPE
        SYNTAX  OCTET STRING (SIZE(8))
        ACCESS  read-write
        STATUS  mandatory
        DESCRIPTION
                ""
        ::= { vcvVoiceSuscriberEntry 5 }


    vcvVoiceSuscrTransportProfileId OBJECT-TYPE
        SYNTAX  INTEGER (0..1)
        ACCESS  read-write
        STATUS  mandatory
        DESCRIPTION
                ""
        ::= { vcvVoiceSuscriberEntry 6 }


    vcvVoiceSuscrRemovedDigitNumber OBJECT-TYPE
        SYNTAX  INTEGER (0..21)
        ACCESS  read-write
        STATUS  mandatory
        DESCRIPTION
                ""
        ::= { vcvVoiceSuscriberEntry 7 }


    vcvVoiceSuscrInsPrefix OBJECT-TYPE
        SYNTAX  DisplayString (SIZE(1..21))
        ACCESS  read-write
        STATUS  mandatory
        DESCRIPTION
                ""
        ::= { vcvVoiceSuscriberEntry 8 }


    vcvVoiceSuscrInsSuffix OBJECT-TYPE
        SYNTAX  DisplayString (SIZE(1..21))
        ACCESS  read-write
        STATUS  mandatory
        DESCRIPTION
                ""
        ::= { vcvVoiceSuscriberEntry 9 }


    vcvVoiceSwTable OBJECT-TYPE
        SYNTAX  SEQUENCE OF VcvVoiceSwEntry
        ACCESS  not-accessible
        STATUS  mandatory
        DESCRIPTION
                ""
        ::= { vcvVoiceVirtualPort 4 }


    vcvVoiceSwEntry OBJECT-TYPE
        SYNTAX  VcvVoiceSwEntry
        ACCESS  not-accessible
        STATUS  mandatory
        DESCRIPTION
                "An entry of vcvVoiceSwTable."
        INDEX   { vcvVoiceSwOrderNumber,
                  vcvVoiceSwSuscriberNumber }
        ::= { vcvVoiceSwTable 1 }


        VcvVoiceSwEntry ::=
                SEQUENCE {
                    vcvVoiceSwOrderNumber
                        INTEGER,
                    vcvVoiceSwSuscriberNumber
                        DisplayString,
                    vcvVoiceSwStatus
                        INTEGER,
                    vcvVoiceSwLogPortSetId
                        INTEGER,
                    vcvVoiceSwRemovedDigitNumber
                        INTEGER,
                    vcvVoiceSwInsPrefix
                        DisplayString,
                    vcvVoiceSwInsSuffix
                        DisplayString
                }


    vcvVoiceSwOrderNumber OBJECT-TYPE
        SYNTAX  INTEGER (0..9)
        ACCESS  read-only
        STATUS  mandatory
        DESCRIPTION
                ""
        ::= { vcvVoiceSwEntry 1 }


    vcvVoiceSwSuscriberNumber OBJECT-TYPE
        SYNTAX  DisplayString (SIZE(1..21))
        ACCESS  read-only
        STATUS  mandatory
        DESCRIPTION
                ""
        ::= { vcvVoiceSwEntry 2 }


    vcvVoiceSwStatus OBJECT-TYPE
        SYNTAX  INTEGER {
                valid(1),
                invalid(2)
                }
        ACCESS  read-write
        STATUS  mandatory
        DESCRIPTION
                ""
        ::= { vcvVoiceSwEntry 3 }


    vcvVoiceSwLogPortSetId OBJECT-TYPE
        SYNTAX  INTEGER (0..9)
        ACCESS  read-write
        STATUS  mandatory
        DESCRIPTION
                ""
        ::= { vcvVoiceSwEntry 4 }


    vcvVoiceSwRemovedDigitNumber OBJECT-TYPE
        SYNTAX  INTEGER (0..21)
        ACCESS  read-write
        STATUS  mandatory
        DESCRIPTION
                ""
        ::= { vcvVoiceSwEntry 5 }


    vcvVoiceSwInsPrefix OBJECT-TYPE
        SYNTAX  DisplayString (SIZE(1..21))
        ACCESS  read-write
        STATUS  mandatory
        DESCRIPTION
                ""
        ::= { vcvVoiceSwEntry 6 }


    vcvVoiceSwInsSuffix OBJECT-TYPE
        SYNTAX  DisplayString (SIZE(1..21))
        ACCESS  read-write
        STATUS  mandatory
        DESCRIPTION
                ""
        ::= { vcvVoiceSwEntry 7 }


    vcvDialingReceptTable OBJECT-TYPE
        SYNTAX  SEQUENCE OF VcvDialingReceptEntry
        ACCESS  not-accessible
        STATUS  mandatory
        DESCRIPTION
                ""
        ::= { vcvVoiceVirtualPort 5 }


    vcvDialingReceptEntry OBJECT-TYPE
        SYNTAX  VcvDialingReceptEntry
        ACCESS  not-accessible
        STATUS  mandatory
        DESCRIPTION
                "An entry of vcvDialingReceptTable."
        INDEX   { vcvDialRxSuscriberNumber }
        ::= { vcvDialingReceptTable 1 }


        VcvDialingReceptEntry ::=
                SEQUENCE {
                    vcvDialRxSuscriberNumber
                        DisplayString,
                    vcvDialRxStatus
                        INTEGER,
                    vcvDialRxNumberLength
                        INTEGER,
                    vcvDialRxEndOfDialingTimer
                        INTEGER
                }


    vcvDialRxSuscriberNumber OBJECT-TYPE
        SYNTAX  DisplayString (SIZE(1..21))
        ACCESS  read-only
        STATUS  mandatory
        DESCRIPTION
                ""
        ::= { vcvDialingReceptEntry 1 }


    vcvDialRxStatus OBJECT-TYPE
        SYNTAX  INTEGER {
                valid(1),
                invalid(2)
                }
        ACCESS  read-write
        STATUS  mandatory
        DESCRIPTION
                ""
        ::= { vcvDialingReceptEntry 2 }


    vcvDialRxNumberLength OBJECT-TYPE
        SYNTAX  INTEGER (0..21)
        ACCESS  read-write
        STATUS  mandatory
        DESCRIPTION
                ""
        ::= { vcvDialingReceptEntry 3 }


    vcvDialRxEndOfDialingTimer OBJECT-TYPE
        SYNTAX  INTEGER {
                yes(1),
                no(2)
                }
        ACCESS  read-write
        STATUS  mandatory
        DESCRIPTION
                ""
        ::= { vcvDialingReceptEntry 4 }


    vcvVoiceLogPort OBJECT IDENTIFIER ::= { vcvVoiceVirtualPort 10 }


    vcvVoiceLogicalPortTable OBJECT-TYPE
        SYNTAX  SEQUENCE OF VcvVoiceLogicalPortEntry
        ACCESS  not-accessible
        STATUS  mandatory
        DESCRIPTION
                ""
        ::= { vcvVoiceLogPort 1 }


    vcvVoiceLogicalPortEntry OBJECT-TYPE
        SYNTAX  VcvVoiceLogicalPortEntry
        ACCESS  not-accessible
        STATUS  mandatory
        DESCRIPTION
                "An entry of vcvVoiceLogicalPortTable."
        INDEX   { vcvVoiceLogPortId }
        ::= { vcvVoiceLogicalPortTable 1 }


        VcvVoiceLogicalPortEntry ::=
                SEQUENCE {
                    vcvVoiceLogPortId
                        INTEGER,
                    vcvVoiceLogPortStatus
                        INTEGER,
                    vcvVoiceLogPortType
                        INTEGER
                }


    vcvVoiceLogPortId OBJECT-TYPE
        SYNTAX  INTEGER (0..1)
        ACCESS  read-only
        STATUS  mandatory
        DESCRIPTION
                ""
        ::= { vcvVoiceLogicalPortEntry 1 }


    vcvVoiceLogPortStatus OBJECT-TYPE
        SYNTAX  INTEGER {
                valid(1),
                invalid(2)
                }
        ACCESS  read-write
        STATUS  mandatory
        DESCRIPTION
                ""
        ::= { vcvVoiceLogicalPortEntry 2 }


    vcvVoiceLogPortType OBJECT-TYPE
        SYNTAX  INTEGER {
                emPermanent(1),
                emSwitched(2),
                fxx(3)
                }
        ACCESS  read-write
        STATUS  mandatory
        DESCRIPTION
                ""
        ::= { vcvVoiceLogicalPortEntry 3 }


    vcvProfileTone OBJECT IDENTIFIER ::= { vcvVoiceLogPort 5 }


    vcvToneGenTable OBJECT-TYPE
        SYNTAX  SEQUENCE OF VcvToneGenEntry
        ACCESS  not-accessible
        STATUS  mandatory
        DESCRIPTION
                ""
        ::= { vcvProfileTone 1 }


    vcvToneGenEntry OBJECT-TYPE
        SYNTAX  VcvToneGenEntry
        ACCESS  not-accessible
        STATUS  mandatory
        DESCRIPTION
                "An entry of vcvToneGenTable."
        INDEX   { vcvToneGenProfileId }
        ::= { vcvToneGenTable 1 }


        VcvToneGenEntry ::=
                SEQUENCE {
                    vcvToneGenProfileId
                        INTEGER,
                    vcvToneGenLevel
                        INTEGER
                }


    vcvToneGenProfileId OBJECT-TYPE
        SYNTAX  INTEGER (0..0)
        ACCESS  read-only
        STATUS  mandatory
        DESCRIPTION
                ""
        ::= { vcvToneGenEntry 1 }


    vcvToneGenLevel OBJECT-TYPE
        SYNTAX  INTEGER (0..60)
        ACCESS  read-write
        STATUS  mandatory
        DESCRIPTION
                ""
        ::= { vcvToneGenEntry 2 }


    vcvToneTable OBJECT-TYPE
        SYNTAX  SEQUENCE OF VcvToneEntry
        ACCESS  not-accessible
        STATUS  mandatory
        DESCRIPTION
                ""
        ::= { vcvProfileTone 2 }


    vcvToneEntry OBJECT-TYPE
        SYNTAX  VcvToneEntry
        ACCESS  not-accessible
        STATUS  mandatory
        DESCRIPTION
                "An entry of vcvToneTable."
        INDEX   { vcvToneProfileId,
                  vcvToneType }
        ::= { vcvToneTable 1 }


        VcvToneEntry ::=
                SEQUENCE {
                    vcvToneProfileId
                        INTEGER,
                    vcvToneType
                        INTEGER,
                    vcvToneEnable
                        INTEGER,
                    vcvToneFreq1
                        INTEGER,
                    vcvToneDuration1
                        INTEGER,
                    vcvToneFreq2
                        INTEGER,
                    vcvToneDuration2
                        INTEGER
                }


    vcvToneProfileId OBJECT-TYPE
        SYNTAX  INTEGER (0..0)
        ACCESS  read-only
        STATUS  mandatory
        DESCRIPTION
                ""
        ::= { vcvToneEntry 1 }


    vcvToneType OBJECT-TYPE
        SYNTAX  INTEGER {
                dialTone(1),
                trouble(2),
                congestion(3),
                busy(4),
                callBack(5)
                }
        ACCESS  read-only
        STATUS  mandatory
        DESCRIPTION
                ""
        ::= { vcvToneEntry 2 }


    vcvToneEnable OBJECT-TYPE
        SYNTAX  INTEGER {
                no(1),
                yes(2)
                }
        ACCESS  read-write
        STATUS  mandatory
        DESCRIPTION
                ""
        ::= { vcvToneEntry 3 }


    vcvToneFreq1 OBJECT-TYPE
        SYNTAX  INTEGER (0..255)
        ACCESS  read-write
        STATUS  mandatory
        DESCRIPTION
                ""
        ::= { vcvToneEntry 4 }


    vcvToneDuration1 OBJECT-TYPE
        SYNTAX  INTEGER (0..500)
        ACCESS  read-write
        STATUS  mandatory
        DESCRIPTION
                ""
        ::= { vcvToneEntry 5 }


    vcvToneFreq2 OBJECT-TYPE
        SYNTAX  INTEGER (0..255)
        ACCESS  read-write
        STATUS  mandatory
        DESCRIPTION
                ""
        ::= { vcvToneEntry 6 }


    vcvToneDuration2 OBJECT-TYPE
        SYNTAX  INTEGER (0..500)
        ACCESS  read-write
        STATUS  mandatory
        DESCRIPTION
                ""
        ::= { vcvToneEntry 7 }


    vcvVoiceLogicalPortEM OBJECT IDENTIFIER ::= { vcvVoiceLogPort 10 }


    vcvEMPerm OBJECT IDENTIFIER ::= { vcvVoiceLogicalPortEM 1 }


    vcvEMPermTable OBJECT-TYPE
        SYNTAX  SEQUENCE OF VcvEMPermEntry
        ACCESS  not-accessible
        STATUS  mandatory
        DESCRIPTION
                ""
        ::= { vcvEMPerm 1 }


    vcvEMPermEntry OBJECT-TYPE
        SYNTAX  VcvEMPermEntry
        ACCESS  not-accessible
        STATUS  mandatory
        DESCRIPTION
                "An entry of vcvEMPermTable."
        INDEX   { vcvEMPermLpId }
        ::= { vcvEMPermTable 1 }


        VcvEMPermEntry ::=
                SEQUENCE {
                    vcvEMPermLpId
                        INTEGER,
                    vcvEMPermCommunicationMode
                        INTEGER,
                    vcvEMPermRemoteNumber
                        DisplayString,
                    vcvEMPermInterfaceId
                        INTEGER
                }


    vcvEMPermLpId OBJECT-TYPE
        SYNTAX  INTEGER (0..1)
        ACCESS  read-only
        STATUS  mandatory
        DESCRIPTION
                ""
        ::= { vcvEMPermEntry 1 }


    vcvEMPermCommunicationMode OBJECT-TYPE
        SYNTAX  INTEGER {
                dte(1),
                dce(2)
                }
        ACCESS  read-write
        STATUS  mandatory
        DESCRIPTION
                ""
        ::= { vcvEMPermEntry 2 }


    vcvEMPermRemoteNumber OBJECT-TYPE
        SYNTAX  DisplayString (SIZE(1..21))
        ACCESS  read-write
        STATUS  mandatory
        DESCRIPTION
                ""
        ::= { vcvEMPermEntry 3 }


    vcvEMPermInterfaceId OBJECT-TYPE
        SYNTAX  INTEGER {
                v0(1),
                v1(2)
                }
        ACCESS  read-write
        STATUS  mandatory
        DESCRIPTION
                ""
        ::= { vcvEMPermEntry 4 }


    vcvEMSw OBJECT IDENTIFIER ::= { vcvVoiceLogicalPortEM 2 }


    vcvEMSwTable OBJECT-TYPE
        SYNTAX  SEQUENCE OF VcvEMSwEntry
        ACCESS  not-accessible
        STATUS  mandatory
        DESCRIPTION
                ""
        ::= { vcvEMSw 1 }


    vcvEMSwEntry OBJECT-TYPE
        SYNTAX  VcvEMSwEntry
        ACCESS  not-accessible
        STATUS  mandatory
        DESCRIPTION
                "An entry of vcvEMSwTable."
        INDEX   { vcvEMSwLpId }
        ::= { vcvEMSwTable 1 }


        VcvEMSwEntry ::=
                SEQUENCE {
                    vcvEMSwLpId
                        INTEGER,
                    vcvEMSwLogPortSetId
                        INTEGER,
                    vcvEMSwCallType
                        INTEGER,
                    vcvEMSwRemoteNumber
                        DisplayString,
                    vcvEMSwConfigId
                        INTEGER,
                    vcvEMSwInterfaceId
                        INTEGER
                }


    vcvEMSwLpId OBJECT-TYPE
        SYNTAX  INTEGER (0..1)
        ACCESS  read-only
        STATUS  mandatory
        DESCRIPTION
                ""
        ::= { vcvEMSwEntry 1 }


    vcvEMSwLogPortSetId OBJECT-TYPE
        SYNTAX  INTEGER (0..9)
        ACCESS  read-write
        STATUS  mandatory
        DESCRIPTION
                ""
        ::= { vcvEMSwEntry 2 }


    vcvEMSwCallType OBJECT-TYPE
        SYNTAX  INTEGER {
                incoming(1),
                outgoing(2),
                mixed(3)
                }
        ACCESS  read-write
        STATUS  mandatory
        DESCRIPTION
                ""
        ::= { vcvEMSwEntry 3 }


    vcvEMSwRemoteNumber OBJECT-TYPE
        SYNTAX  DisplayString (SIZE(1..21))
        ACCESS  read-write
        STATUS  mandatory
        DESCRIPTION
                ""
        ::= { vcvEMSwEntry 4 }


    vcvEMSwConfigId OBJECT-TYPE
        SYNTAX  INTEGER (0..0)
        ACCESS  read-only
        STATUS  mandatory
        DESCRIPTION
                ""
        ::= { vcvEMSwEntry 5 }


    vcvEMSwInterfaceId OBJECT-TYPE
        SYNTAX  INTEGER {
                v0(1),
                v1(2)
                }
        ACCESS  read-write
        STATUS  mandatory
        DESCRIPTION
                ""
        ::= { vcvEMSwEntry 6 }


    vcvEMConfigTable OBJECT-TYPE
        SYNTAX  SEQUENCE OF VcvEMConfigEntry
        ACCESS  not-accessible
        STATUS  mandatory
        DESCRIPTION
                ""
        ::= { vcvEMSw 2 }


    vcvEMConfigEntry OBJECT-TYPE
        SYNTAX  VcvEMConfigEntry
        ACCESS  not-accessible
        STATUS  mandatory
        DESCRIPTION
                "An entry of vcvEMConfigTable."
        INDEX   { vcvEMConfId }
        ::= { vcvEMConfigTable 1 }


        VcvEMConfigEntry ::=
                SEQUENCE {
                    vcvEMConfId
                        INTEGER,
                    vcvEMConfCallSignalling
                        INTEGER,
                    vcvEMConfDialingMode
                        INTEGER,
                    vcvEMConfDialingTimeOut
                        INTEGER,
                    vcvEMConfSigChannelDiscTimeOut
                        INTEGER,
                    vcvEMConfTimeBetweenSuccOutCall
                        INTEGER,
                    vcvEMConfLineInterfacePolarity
                        INTEGER,
                    vcvEMConfMinLineSeizureAckTime
                        INTEGER,
                    vcvEMConfMaxLineSeizureAckTime
                        INTEGER,
                    vcvEMConfLineSeizureAckTime
                        INTEGER,
                    vcvEMConfClearToIncCallTime
                        INTEGER,
                    vcvEMConfSeizureAckPulseDuration
                        INTEGER,
                    vcvEMConfMinSeizureAckPulseDuration
                        INTEGER,
                    vcvEMConfDialingFormat
                        INTEGER,
                    vcvEMConfInterdigitTime
                        INTEGER,
                    vcvEMConfPauseTime
                        INTEGER,
                    vcvEMConfDtmfDigitTime
                        INTEGER,
                    vcvEMConfDtmfDigitLevel
                        INTEGER,
                    vcvEMConfDelayBeforeDialing
                        INTEGER,
                    vcvEMConfDigitReceptionTimeOut
                        INTEGER,
                    vcvEMConfEndOfDialingTimer
                        INTEGER,
                    vcvEMConfToneProfile
                        INTEGER
                }


    vcvEMConfId OBJECT-TYPE
        SYNTAX  INTEGER (0..0)
        ACCESS  read-only
        STATUS  mandatory
        DESCRIPTION
                ""
        ::= { vcvEMConfigEntry 1 }


    vcvEMConfCallSignalling OBJECT-TYPE
        SYNTAX  INTEGER {
                nColisee(1),
                uColisee(2),
                simm(3),
                sDelay(4),
                swink(5),
                noResp(6)
                }
        ACCESS  read-write
        STATUS  mandatory
        DESCRIPTION
                ""
        ::= { vcvEMConfigEntry 2 }


    vcvEMConfDialingMode OBJECT-TYPE
        SYNTAX  INTEGER {
                dec(1),
                dtmf(2)
                }
        ACCESS  read-write
        STATUS  mandatory
        DESCRIPTION
                ""
        ::= { vcvEMConfigEntry 3 }


    vcvEMConfDialingTimeOut OBJECT-TYPE
        SYNTAX  INTEGER (1..60)
        ACCESS  read-write
        STATUS  mandatory
        DESCRIPTION
                ""
        ::= { vcvEMConfigEntry 4 }


    vcvEMConfSigChannelDiscTimeOut OBJECT-TYPE
        SYNTAX  INTEGER (1..60)
        ACCESS  read-write
        STATUS  mandatory
        DESCRIPTION
                ""
        ::= { vcvEMConfigEntry 5 }


    vcvEMConfTimeBetweenSuccOutCall OBJECT-TYPE
        SYNTAX  INTEGER (1..60)
        ACCESS  read-write
        STATUS  mandatory
        DESCRIPTION
                ""
        ::= { vcvEMConfigEntry 6 }


    vcvEMConfLineInterfacePolarity OBJECT-TYPE
        SYNTAX  INTEGER {
                normal(1),
                inverted(2)
                }
        ACCESS  read-write
        STATUS  mandatory
        DESCRIPTION
                ""
        ::= { vcvEMConfigEntry 7 }


    vcvEMConfMinLineSeizureAckTime OBJECT-TYPE
        SYNTAX  INTEGER (0..50)
        ACCESS  read-write
        STATUS  mandatory
        DESCRIPTION
                ""
        ::= { vcvEMConfigEntry 8 }


    vcvEMConfMaxLineSeizureAckTime OBJECT-TYPE
        SYNTAX  INTEGER (1..50)
        ACCESS  read-write
        STATUS  mandatory
        DESCRIPTION
                ""
        ::= { vcvEMConfigEntry 9 }


    vcvEMConfLineSeizureAckTime OBJECT-TYPE
        SYNTAX  INTEGER (1..50)
        ACCESS  read-write
        STATUS  mandatory
        DESCRIPTION
                ""
        ::= { vcvEMConfigEntry 10 }


    vcvEMConfClearToIncCallTime OBJECT-TYPE
        SYNTAX  INTEGER (3..50)
        ACCESS  read-write
        STATUS  mandatory
        DESCRIPTION
                ""
        ::= { vcvEMConfigEntry 11 }


    vcvEMConfSeizureAckPulseDuration OBJECT-TYPE
        SYNTAX  INTEGER (1..100)
        ACCESS  read-write
        STATUS  mandatory
        DESCRIPTION
                ""
        ::= { vcvEMConfigEntry 12 }


    vcvEMConfMinSeizureAckPulseDuration OBJECT-TYPE
        SYNTAX  INTEGER (1..100)
        ACCESS  read-write
        STATUS  mandatory
        DESCRIPTION
                ""
        ::= { vcvEMConfigEntry 13 }


    vcvEMConfDialingFormat OBJECT-TYPE
        SYNTAX  INTEGER {
                ds1(1),
                ds2(2)
                }
        ACCESS  read-write
        STATUS  mandatory
        DESCRIPTION
                ""
        ::= { vcvEMConfigEntry 14 }


    vcvEMConfInterdigitTime OBJECT-TYPE
        SYNTAX  INTEGER (1..100)
        ACCESS  read-write
        STATUS  mandatory
        DESCRIPTION
                ""
        ::= { vcvEMConfigEntry 15 }


    vcvEMConfPauseTime OBJECT-TYPE
        SYNTAX  INTEGER (1..100)
        ACCESS  read-write
        STATUS  mandatory
        DESCRIPTION
                ""
        ::= { vcvEMConfigEntry 16 }


    vcvEMConfDtmfDigitTime OBJECT-TYPE
        SYNTAX  INTEGER (2..10)
        ACCESS  read-write
        STATUS  mandatory
        DESCRIPTION
                ""
        ::= { vcvEMConfigEntry 17 }


    vcvEMConfDtmfDigitLevel OBJECT-TYPE
        SYNTAX  INTEGER (0..40)
        ACCESS  read-write
        STATUS  mandatory
        DESCRIPTION
                ""
        ::= { vcvEMConfigEntry 18 }


    vcvEMConfDelayBeforeDialing OBJECT-TYPE
        SYNTAX  INTEGER (1..100)
        ACCESS  read-write
        STATUS  mandatory
        DESCRIPTION
                ""
        ::= { vcvEMConfigEntry 19 }


    vcvEMConfDigitReceptionTimeOut OBJECT-TYPE
        SYNTAX  INTEGER (1..60)
        ACCESS  read-write
        STATUS  mandatory
        DESCRIPTION
                ""
        ::= { vcvEMConfigEntry 20 }


    vcvEMConfEndOfDialingTimer OBJECT-TYPE
        SYNTAX  INTEGER (2..60)
        ACCESS  read-write
        STATUS  mandatory
        DESCRIPTION
                ""
        ::= { vcvEMConfigEntry 21 }


    vcvEMConfToneProfile OBJECT-TYPE
        SYNTAX  INTEGER (0..0)
        ACCESS  read-only
        STATUS  mandatory
        DESCRIPTION
                ""
        ::= { vcvEMConfigEntry 22 }


    vcvVoiceLogicalPortFxx OBJECT IDENTIFIER ::= { vcvVoiceLogPort 15 }


    vcvFxxLpTable OBJECT-TYPE
        SYNTAX  SEQUENCE OF VcvFxxLpEntry
        ACCESS  not-accessible
        STATUS  mandatory
        DESCRIPTION
                ""
        ::= { vcvVoiceLogicalPortFxx 1 }


    vcvFxxLpEntry OBJECT-TYPE
        SYNTAX  VcvFxxLpEntry
        ACCESS  not-accessible
        STATUS  mandatory
        DESCRIPTION
                "An entry of vcvFxxLpTable."
        INDEX   { vcvFxxLpLogPortId }
        ::= { vcvFxxLpTable 1 }


        VcvFxxLpEntry ::=
                SEQUENCE {
                    vcvFxxLpLogPortId
                        INTEGER,
                    vcvFxxLpSetId
                        INTEGER,
                    vcvFxxLpCallType
                        INTEGER,
                    vcvFxxLpRemoteNumber
                        DisplayString,
                    vcvFxxLpConfigId
                        INTEGER,
                    vcvFxxLpInterfaceId
                        INTEGER
                }


    vcvFxxLpLogPortId OBJECT-TYPE
        SYNTAX  INTEGER (0..1)
        ACCESS  read-only
        STATUS  mandatory
        DESCRIPTION
                ""
        ::= { vcvFxxLpEntry 1 }


    vcvFxxLpSetId OBJECT-TYPE
        SYNTAX  INTEGER (0..9)
        ACCESS  read-write
        STATUS  mandatory
        DESCRIPTION
                ""
        ::= { vcvFxxLpEntry 2 }


    vcvFxxLpCallType OBJECT-TYPE
        SYNTAX  INTEGER {
                incoming(1),
                outgoing(2),
                mixed(3)
                }
        ACCESS  read-write
        STATUS  mandatory
        DESCRIPTION
                ""
        ::= { vcvFxxLpEntry 3 }


    vcvFxxLpRemoteNumber OBJECT-TYPE
        SYNTAX  DisplayString (SIZE(1..21))
        ACCESS  read-write
        STATUS  mandatory
        DESCRIPTION
                ""
        ::= { vcvFxxLpEntry 4 }


    vcvFxxLpConfigId OBJECT-TYPE
        SYNTAX  INTEGER (0..0)
        ACCESS  read-only
        STATUS  mandatory
        DESCRIPTION
                ""
        ::= { vcvFxxLpEntry 5 }


    vcvFxxLpInterfaceId OBJECT-TYPE
        SYNTAX  INTEGER {
                v0(1),
                v1(2)
                }
        ACCESS  read-write
        STATUS  mandatory
        DESCRIPTION
                ""
        ::= { vcvFxxLpEntry 6 }


    vcvFxxConfigTable OBJECT-TYPE
        SYNTAX  SEQUENCE OF VcvFxxConfigEntry
        ACCESS  not-accessible
        STATUS  mandatory
        DESCRIPTION
                ""
        ::= { vcvVoiceLogicalPortFxx 2 }


    vcvFxxConfigEntry OBJECT-TYPE
        SYNTAX  VcvFxxConfigEntry
        ACCESS  not-accessible
        STATUS  mandatory
        DESCRIPTION
                "An entry of vcvFxxConfigTable."
        INDEX   { vcvFxxConfId }
        ::= { vcvFxxConfigTable 1 }


        VcvFxxConfigEntry ::=
                SEQUENCE {
                    vcvFxxConfId
                        INTEGER,
                    vcvFxxConfCallSignalling
                        INTEGER,
                    vcvFxxConfDialingMode
                        INTEGER,
                    vcvFxxConfSigChannelDiscTimeOut
                        INTEGER,
                    vcvFxxConfTimeBetweenSuccOutCall
                        INTEGER,
                    vcvFxxConfDialingFormat
                        INTEGER,
                    vcvFxxConfInterdigitTime
                        INTEGER,
                    vcvFxxConfPauseTime
                        INTEGER,
                    vcvFxxConfDtmfDigitTime
                        INTEGER,
                    vcvFxxConfDtmfDigitLevel
                        INTEGER,
                    vcvFxxConfTxRecallSignalDuration
                        INTEGER,
                    vcvFxxConfDelayBeforeDialing
                        INTEGER,
                    vcvFxxConfDialingTimeOut
                        INTEGER,
                    vcvFxxConfDigitReceptionTimeOut
                        INTEGER,
                    vcvFxxConfEndOfDialingTimer
                        INTEGER,
                    vcvFxxConfMinRxRecallSignalDuration
                        INTEGER,
                    vcvFxxConfToneProfile
                        INTEGER,
                    vcvFxxConfRingingProfile
                        INTEGER
                }


    vcvFxxConfId OBJECT-TYPE
        SYNTAX  INTEGER (0..0)
        ACCESS  read-only
        STATUS  mandatory
        DESCRIPTION
                ""
        ::= { vcvFxxConfigEntry 1 }


    vcvFxxConfCallSignalling OBJECT-TYPE
        SYNTAX  INTEGER {
                fxx(1),
                other(2)
                }
        ACCESS  read-only
        STATUS  mandatory
        DESCRIPTION
                ""
        ::= { vcvFxxConfigEntry 2 }


    vcvFxxConfDialingMode OBJECT-TYPE
        SYNTAX  INTEGER {
                dec(1),
                dtmf(2)
                }
        ACCESS  read-write
        STATUS  mandatory
        DESCRIPTION
                ""
        ::= { vcvFxxConfigEntry 3 }


    vcvFxxConfSigChannelDiscTimeOut OBJECT-TYPE
        SYNTAX  INTEGER (1..60)
        ACCESS  read-write
        STATUS  mandatory
        DESCRIPTION
                ""
        ::= { vcvFxxConfigEntry 4 }


    vcvFxxConfTimeBetweenSuccOutCall OBJECT-TYPE
        SYNTAX  INTEGER (1..60)
        ACCESS  read-write
        STATUS  mandatory
        DESCRIPTION
                ""
        ::= { vcvFxxConfigEntry 5 }


    vcvFxxConfDialingFormat OBJECT-TYPE
        SYNTAX  INTEGER {
                ds1(1),
                ds2(2)
                }
        ACCESS  read-write
        STATUS  mandatory
        DESCRIPTION
                ""
        ::= { vcvFxxConfigEntry 6 }


    vcvFxxConfInterdigitTime OBJECT-TYPE
        SYNTAX  INTEGER (1..100)
        ACCESS  read-write
        STATUS  mandatory
        DESCRIPTION
                ""
        ::= { vcvFxxConfigEntry 7 }


    vcvFxxConfPauseTime OBJECT-TYPE
        SYNTAX  INTEGER (1..100)
        ACCESS  read-write
        STATUS  mandatory
        DESCRIPTION
                ""
        ::= { vcvFxxConfigEntry 8 }


    vcvFxxConfDtmfDigitTime OBJECT-TYPE
        SYNTAX  INTEGER (2..10)
        ACCESS  read-write
        STATUS  mandatory
        DESCRIPTION
                ""
        ::= { vcvFxxConfigEntry 9 }


    vcvFxxConfDtmfDigitLevel OBJECT-TYPE
        SYNTAX  INTEGER (0..40)
        ACCESS  read-write
        STATUS  mandatory
        DESCRIPTION
                ""
        ::= { vcvFxxConfigEntry 10 }


    vcvFxxConfTxRecallSignalDuration OBJECT-TYPE
        SYNTAX  INTEGER (5..50)
        ACCESS  read-write
        STATUS  mandatory
        DESCRIPTION
                ""
        ::= { vcvFxxConfigEntry 11 }


    vcvFxxConfDelayBeforeDialing OBJECT-TYPE
        SYNTAX  INTEGER (1..50)
        ACCESS  read-write
        STATUS  mandatory
        DESCRIPTION
                ""
        ::= { vcvFxxConfigEntry 12 }


    vcvFxxConfDialingTimeOut OBJECT-TYPE
        SYNTAX  INTEGER (1..60)
        ACCESS  read-write
        STATUS  mandatory
        DESCRIPTION
                ""
        ::= { vcvFxxConfigEntry 13 }


    vcvFxxConfDigitReceptionTimeOut OBJECT-TYPE
        SYNTAX  INTEGER (1..60)
        ACCESS  read-write
        STATUS  mandatory
        DESCRIPTION
                ""
        ::= { vcvFxxConfigEntry 14 }


    vcvFxxConfEndOfDialingTimer OBJECT-TYPE
        SYNTAX  INTEGER (2..60)
        ACCESS  read-write
        STATUS  mandatory
        DESCRIPTION
                ""
        ::= { vcvFxxConfigEntry 15 }


    vcvFxxConfMinRxRecallSignalDuration OBJECT-TYPE
        SYNTAX  INTEGER (5..25)
        ACCESS  read-write
        STATUS  mandatory
        DESCRIPTION
                ""
        ::= { vcvFxxConfigEntry 16 }


    vcvFxxConfToneProfile OBJECT-TYPE
        SYNTAX  INTEGER (0..0)
        ACCESS  read-only
        STATUS  mandatory
        DESCRIPTION
                ""
        ::= { vcvFxxConfigEntry 17 }


    vcvFxxConfRingingProfile OBJECT-TYPE
        SYNTAX  INTEGER (0..0)
        ACCESS  read-only
        STATUS  mandatory
        DESCRIPTION
                ""
        ::= { vcvFxxConfigEntry 18 }


    vcvFxxRingTable OBJECT-TYPE
        SYNTAX  SEQUENCE OF VcvFxxRingEntry
        ACCESS  not-accessible
        STATUS  mandatory
        DESCRIPTION
                ""
        ::= { vcvVoiceLogicalPortFxx 3 }


    vcvFxxRingEntry OBJECT-TYPE
        SYNTAX  VcvFxxRingEntry
        ACCESS  not-accessible
        STATUS  mandatory
        DESCRIPTION
                "An entry of vcvFxxRingTable."
        INDEX   { vcvFxxRingProfile }
        ::= { vcvFxxRingTable 1 }


        VcvFxxRingEntry ::=
                SEQUENCE {
                    vcvFxxRingProfile
                        INTEGER,
                    vcvFxxRingFrequency
                        INTEGER,
                    vcvFxxRingTopDuration
                        INTEGER,
                    vcvFxxRingSilenceDuration
                        INTEGER,
                    vcvFxxRingMaxRingingTime
                        INTEGER
                }


    vcvFxxRingProfile OBJECT-TYPE
        SYNTAX  INTEGER (0..0)
        ACCESS  read-only
        STATUS  mandatory
        DESCRIPTION
                ""
        ::= { vcvFxxRingEntry 1 }


    vcvFxxRingFrequency OBJECT-TYPE
        SYNTAX  INTEGER (10..80)
        ACCESS  read-write
        STATUS  mandatory
        DESCRIPTION
                ""
        ::= { vcvFxxRingEntry 2 }


    vcvFxxRingTopDuration OBJECT-TYPE
        SYNTAX  INTEGER (1..50)
        ACCESS  read-write
        STATUS  mandatory
        DESCRIPTION
                ""
        ::= { vcvFxxRingEntry 3 }


    vcvFxxRingSilenceDuration OBJECT-TYPE
        SYNTAX  INTEGER (0..50)
        ACCESS  read-write
        STATUS  mandatory
        DESCRIPTION
                ""
        ::= { vcvFxxRingEntry 4 }


    vcvFxxRingMaxRingingTime OBJECT-TYPE
        SYNTAX  INTEGER (10..600)
        ACCESS  read-write
        STATUS  mandatory
        DESCRIPTION
                ""
        ::= { vcvFxxRingEntry 5 }


    vcvAnalogLines OBJECT IDENTIFIER ::= { vcvVoiceVirtualPort 15 }


    vcvAnalogLineTable OBJECT-TYPE
        SYNTAX  SEQUENCE OF VcvAnalogLineEntry
        ACCESS  not-accessible
        STATUS  mandatory
        DESCRIPTION
                ""
        ::= { vcvAnalogLines 1 }


    vcvAnalogLineEntry OBJECT-TYPE
        SYNTAX  VcvAnalogLineEntry
        ACCESS  not-accessible
        STATUS  mandatory
        DESCRIPTION
                "An entry of vcvAnalogLineTable."
        INDEX   { vcvAnalogLineInterfaceId }
        ::= { vcvAnalogLineTable 1 }


        VcvAnalogLineEntry ::=
                SEQUENCE {
                    vcvAnalogLineInterfaceId
                        INTEGER,
                    vcvAnalogLineTypeInterface
                        INTEGER,
                    vcvAnalogLineVoiceProfile
                        INTEGER
                }


    vcvAnalogLineInterfaceId OBJECT-TYPE
        SYNTAX  INTEGER {
                v0(1),
                v1(2)
                }
        ACCESS  read-only
        STATUS  mandatory
        DESCRIPTION
                ""
        ::= { vcvAnalogLineEntry 1 }


    vcvAnalogLineTypeInterface OBJECT-TYPE
        SYNTAX  INTEGER {
                em(1),
                fxo(2),
                fxs(3),
                ibx(4),
                ia50Hz(5)
                }
        ACCESS  read-write
        STATUS  mandatory
        DESCRIPTION
                ""
        ::= { vcvAnalogLineEntry 2 }


    vcvAnalogLineVoiceProfile OBJECT-TYPE
        SYNTAX  INTEGER (0..1)
        ACCESS  read-write
        STATUS  mandatory
        DESCRIPTION
                ""
        ::= { vcvAnalogLineEntry 3 }


    vcvVoiceProfileTable OBJECT-TYPE
        SYNTAX  SEQUENCE OF VcvVoiceProfileEntry
        ACCESS  not-accessible
        STATUS  mandatory
        DESCRIPTION
                ""
        ::= { vcvAnalogLines 5 }


    vcvVoiceProfileEntry OBJECT-TYPE
        SYNTAX  VcvVoiceProfileEntry
        ACCESS  not-accessible
        STATUS  mandatory
        DESCRIPTION
                "An entry of vcvVoiceProfileTable."
        INDEX   { vcvVoiceProfId }
        ::= { vcvVoiceProfileTable 1 }


        VcvVoiceProfileEntry ::=
                SEQUENCE {
                    vcvVoiceProfId
                        INTEGER,
                    vcvVoiceProfTransmitLevel
                        INTEGER,
                    vcvVoiceProfReceiveLevel
                        INTEGER,
                    vcvVoiceProfSilenceDetection
                        INTEGER,
                    vcvVoiceProfSilenceDetectionLevel
                        INTEGER,
                    vcvVoiceProfEchoCancellation
                        INTEGER,
                    vcvVoiceProfEchoCancellationLength
                        INTEGER,
                    vcvVoiceProfNoiseFramesPeriodicity
                        INTEGER,
                    vcvVoiceProfLoopActivation
                        INTEGER,
                    vcvVoiceProfFaxActivation
                        INTEGER,
                    vcvVoiceProfMaximumFaxSpeed
                        INTEGER
                }


    vcvVoiceProfId OBJECT-TYPE
        SYNTAX  INTEGER (0..1)
        ACCESS  read-only
        STATUS  mandatory
        DESCRIPTION
                ""
        ::= { vcvVoiceProfileEntry 1 }


    vcvVoiceProfTransmitLevel OBJECT-TYPE
        SYNTAX  INTEGER (0..24)
        ACCESS  read-write
        STATUS  mandatory
        DESCRIPTION
                ""
        ::= { vcvVoiceProfileEntry 2 }


    vcvVoiceProfReceiveLevel OBJECT-TYPE
        SYNTAX  INTEGER (0..15)
        ACCESS  read-write
        STATUS  mandatory
        DESCRIPTION
                ""
        ::= { vcvVoiceProfileEntry 3 }


    vcvVoiceProfSilenceDetection OBJECT-TYPE
        SYNTAX  INTEGER {
                no(1),
                yes(2),
                cng(3)
                }
        ACCESS  read-write
        STATUS  mandatory
        DESCRIPTION
                ""
        ::= { vcvVoiceProfileEntry 4 }


    vcvVoiceProfSilenceDetectionLevel OBJECT-TYPE
        SYNTAX  INTEGER {
                low(1),
                medium(2),
                high(3)
                }
        ACCESS  read-write
        STATUS  mandatory
        DESCRIPTION
                ""
        ::= { vcvVoiceProfileEntry 5 }


    vcvVoiceProfEchoCancellation OBJECT-TYPE
        SYNTAX  INTEGER {
                no(1),
                yes(2)
                }
        ACCESS  read-write
        STATUS  mandatory
        DESCRIPTION
                ""
        ::= { vcvVoiceProfileEntry 6 }


    vcvVoiceProfEchoCancellationLength OBJECT-TYPE
        SYNTAX  INTEGER {
                low(1),
                medium(2),
                high(3)
                }
        ACCESS  read-write
        STATUS  mandatory
        DESCRIPTION
                ""
        ::= { vcvVoiceProfileEntry 7 }


    vcvVoiceProfNoiseFramesPeriodicity OBJECT-TYPE
        SYNTAX  INTEGER (4..10)
        ACCESS  read-write
        STATUS  mandatory
        DESCRIPTION
                ""
        ::= { vcvVoiceProfileEntry 8 }


    vcvVoiceProfLoopActivation OBJECT-TYPE
        SYNTAX  INTEGER {
                no(1),
                local(2),
                remote(3)
                }
        ACCESS  read-write
        STATUS  mandatory
        DESCRIPTION
                ""
        ::= { vcvVoiceProfileEntry 9 }


    vcvVoiceProfFaxActivation OBJECT-TYPE
        SYNTAX  INTEGER {
                no(1),
                yes(2)
                }
        ACCESS  read-write
        STATUS  mandatory
        DESCRIPTION
                ""
        ::= { vcvVoiceProfileEntry 10 }


    vcvVoiceProfMaximumFaxSpeed OBJECT-TYPE
        SYNTAX  INTEGER {
                s9600(1),
                s4800(2)
                }
        ACCESS  read-write
        STATUS  mandatory
        DESCRIPTION
                ""
        ::= { vcvVoiceProfileEntry 11 }


    vcvVoicePhysicalPortTable OBJECT-TYPE
        SYNTAX  SEQUENCE OF VcvVoicePhysicalPortEntry
        ACCESS  not-accessible
        STATUS  mandatory
        DESCRIPTION
                ""
        ::= { vcvAnalogLines 10 }


    vcvVoicePhysicalPortEntry OBJECT-TYPE
        SYNTAX  VcvVoicePhysicalPortEntry
        ACCESS  not-accessible
        STATUS  mandatory
        DESCRIPTION
                "An entry of vcvVoicePhysicalPortTable."
        INDEX   { vcvVoicePhysPortId }
        ::= { vcvVoicePhysicalPortTable 1 }


        VcvVoicePhysicalPortEntry ::=
                SEQUENCE {
                    vcvVoicePhysPortId
                        INTEGER,
                    vcvVoicePhysPortConnector
                        INTEGER
                }


    vcvVoicePhysPortId OBJECT-TYPE
        SYNTAX  INTEGER {
                v0(1),
                v1(2)
                }
        ACCESS  read-only
        STATUS  mandatory
        DESCRIPTION
                ""
        ::= { vcvVoicePhysicalPortEntry 1 }


    vcvVoicePhysPortConnector OBJECT-TYPE
        SYNTAX  INTEGER {
                em(1),
                fxofxs(2),
                fxo(3),
                fxs(4),
                ia50(5)
                }
        ACCESS  read-only
        STATUS  mandatory
        DESCRIPTION
                ""
        ::= { vcvVoicePhysicalPortEntry 2 }



    dcControl OBJECT IDENTIFIER ::= { dvbConfig 1 }


    dcCtlDate OBJECT-TYPE
        SYNTAX  OCTET STRING (SIZE(3))
        ACCESS  read-write
        STATUS  mandatory
        DESCRIPTION
                ""
        ::= { dcControl 1 }


    dcCtlHour OBJECT-TYPE
        SYNTAX  TimeTicks
        ACCESS  read-write
        STATUS  mandatory
        DESCRIPTION
                ""
        ::= { dcControl 2 }


    dcCtlConfigCom OBJECT-TYPE
        SYNTAX  INTEGER {
                ready(1),
                check(2),
                load(5),
                save(6),
                hotReset(10)
                }
        ACCESS  read-write
        STATUS  mandatory
        DESCRIPTION
                ""
        ::= { dcControl 3 }


    dcCtlConfigLoad OBJECT-TYPE
        SYNTAX  INTEGER (1..9)
        ACCESS  read-write
        STATUS  mandatory
        DESCRIPTION
                ""
        ::= { dcControl 4 }


    dcCtlErrorTable OBJECT-TYPE
        SYNTAX  SEQUENCE OF DcCtlErrorEntry
        ACCESS  not-accessible
        STATUS  mandatory
        DESCRIPTION
                ""
        ::= { dcControl 10 }


    dcCtlErrorEntry OBJECT-TYPE
        SYNTAX  DcCtlErrorEntry
        ACCESS  not-accessible
        STATUS  mandatory
        DESCRIPTION
                "An entry of dcCtlErrorTable."
        INDEX   { dcCtlErrorIndex }
        ::= { dcCtlErrorTable 1 }


        DcCtlErrorEntry ::=
                SEQUENCE {
                    dcCtlErrorIndex
                        INTEGER,
                    dcCtlErrorCode
                        INTEGER,
                    dcCtlErrorMessage
                        DisplayString,
                    dcCtlErrorTime
                        TimeTicks
                }


    dcCtlErrorIndex OBJECT-TYPE
        SYNTAX  INTEGER (1..8)
        ACCESS  read-only
        STATUS  mandatory
        DESCRIPTION
                ""
        ::= { dcCtlErrorEntry 1 }


    dcCtlErrorCode OBJECT-TYPE
        SYNTAX  INTEGER (0..255)
        ACCESS  read-only
        STATUS  mandatory
        DESCRIPTION
                ""
        ::= { dcCtlErrorEntry 2 }


    dcCtlErrorMessage OBJECT-TYPE
        SYNTAX  DisplayString (SIZE(0..80))
        ACCESS  read-only
        STATUS  mandatory
        DESCRIPTION
                ""
        ::= { dcCtlErrorEntry 3 }


    dcCtlErrorTime OBJECT-TYPE
        SYNTAX  TimeTicks
        ACCESS  read-only
        STATUS  mandatory
        DESCRIPTION
                ""
        ::= { dcCtlErrorEntry 4 }


    dcSystem OBJECT IDENTIFIER ::= { dvbConfig 5 }


    dcSysConfActive OBJECT-TYPE
        SYNTAX  INTEGER {
                s1(1),
                s2(2),
                s3(3),
                s4(4),
                s5(5),
                s6(6),
                s7(7),
                s8(8),
                s9(9),
                w0(10),
                w1(11),
                w2(12),
                w3(13),
                w4(14),
                w5(15),
                w6(16),
                w7(17),
                w8(18),
                w9(19),
                w0-1(20),
                w0-2(21),
                w0-3(22),
                w0-4(23),
                w0-5(24),
                w0-6(25),
                w0-7(26),
                w0-8(27),
                w0-9(28)
                }
        ACCESS  read-write
        STATUS  mandatory
        DESCRIPTION
                ""
        ::= { dcSystem 1 }


    dcSysConfDate OBJECT-TYPE
        SYNTAX  OCTET STRING (SIZE(3))
        ACCESS  read-only
        STATUS  mandatory
        DESCRIPTION
                ""
        ::= { dcSystem 2 }


    dcSysConfHour OBJECT-TYPE
        SYNTAX  TimeTicks
        ACCESS  read-only
        STATUS  mandatory
        DESCRIPTION
                ""
        ::= { dcSystem 3 }


    dcManagement OBJECT IDENTIFIER ::= { dvbConfig 10 }


    dcmAlrmGenTable OBJECT-TYPE
        SYNTAX  SEQUENCE OF DcmAlrmGenEntry
        ACCESS  not-accessible
        STATUS  mandatory
        DESCRIPTION
                ""
        ::= { dcManagement 1 }


    dcmAlrmGenEntry OBJECT-TYPE
        SYNTAX  DcmAlrmGenEntry
        ACCESS  not-accessible
        STATUS  mandatory
        DESCRIPTION
                "An entry of dcmAlrmGenTable."
        INDEX   { dcmAlrmGenFamilyId,
                  dcmAlrmGenTyp }
        ::= { dcmAlrmGenTable 1 }


        DcmAlrmGenEntry ::=
                SEQUENCE {
                    dcmAlrmGenFamilyId
                        INTEGER,
                    dcmAlrmGenTyp
                        INTEGER,
                    dcmAlrmGenTrapSend
                        INTEGER,
                    dcmAlrmGenDisplay
                        INTEGER
                }


    dcmAlrmGenFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmGenEntry 1 }


    dcmAlrmGenTyp OBJECT-TYPE
        SYNTAX  INTEGER {
                lnkReady208(1),
                lnkNotReady209(2),
                fatalError222(3),
                reboot233(4),
                dspOutofOrder257(5),
                dspNoResourcesLeft258(6)
                }
        ACCESS  read-only
        STATUS  mandatory
        DESCRIPTION
                ""
        ::= { dcmAlrmGenEntry 2 }


    dcmAlrmGenTrapSend OBJECT-TYPE
        SYNTAX  INTEGER {
                yes(1),
                no(2)
                }
        ACCESS  read-write
        STATUS  mandatory
        DESCRIPTION
                ""
        ::= { dcmAlrmGenEntry 3 }


    dcmAlrmGenDisplay OBJECT-TYPE
        SYNTAX  INTEGER {
                yes(1),
                no(2)
                }
        ACCESS  read-write
        STATUS  mandatory
        DESCRIPTION
                ""
        ::= { dcmAlrmGenEntry 4 }


    dcmAlrmSCTable OBJECT-TYPE
        SYNTAX  SEQUENCE OF DcmAlrmSCEntry
        ACCESS  not-accessible
        STATUS  mandatory
        DESCRIPTION
                ""
        ::= { dcManagement 2 }


    dcmAlrmSCEntry OBJECT-TYPE
        SYNTAX  DcmAlrmSCEntry
        ACCESS  not-accessible
        STATUS  mandatory
        DESCRIPTION
                "An entry of dcmAlrmSCTable."
        INDEX   { dcmAlrmSCFamilyId,
                  dcmAlrmSCTyp }
        ::= { dcmAlrmSCTable 1 }


        DcmAlrmSCEntry ::=
                SEQUENCE {
                    dcmAlrmSCFamilyId
                        INTEGER,
                    dcmAlrmSCTyp
                        INTEGER,
                    dcmAlrmSCTrapSend
                        INTEGER,
                    dcmAlrmSCDisplay
                        INTEGER
                }


    dcmAlrmSCFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmSCEntry 1 }


    dcmAlrmSCTyp OBJECT-TYPE
        SYNTAX  INTEGER {
                scReady210(1),
                scNotReady211(2),
                frAddrError223(3),
                dlciError224(4),
                scNotFree225(5),
                scDynamic226(6),
                scReinit227(7),
                unexpectedFrame230(8)
                }
        ACCESS  read-only
        STATUS  mandatory
        DESCRIPTION
                ""
        ::= { dcmAlrmSCEntry 2 }


    dcmAlrmSCTrapSend OBJECT-TYPE
        SYNTAX  INTEGER {
                yes(1),
                no(2)
                }
        ACCESS  read-write
        STATUS  mandatory
        DESCRIPTION
                ""
        ::= { dcmAlrmSCEntry 3 }


    dcmAlrmSCDisplay OBJECT-TYPE
        SYNTAX  INTEGER {
                yes(1),
                no(2)
                }
        ACCESS  read-write
        STATUS  mandatory
        DESCRIPTION
                ""
        ::= { dcmAlrmSCEntry 4 }


    dcmAlrmVCTable OBJECT-TYPE
        SYNTAX  SEQUENCE OF DcmAlrmVCEntry
        ACCESS  not-accessible
        STATUS  mandatory
        DESCRIPTION
                ""
        ::= { dcManagement 3 }


    dcmAlrmVCEntry OBJECT-TYPE
        SYNTAX  DcmAlrmVCEntry
        ACCESS  not-accessible
        STATUS  mandatory
        DESCRIPTION
                "An entry of dcmAlrmVCTable."
        INDEX   { dcmAlrmVCFamilyId,
                  dcmAlrmVCTyp }
        ::= { dcmAlrmVCTable 1 }


        DcmAlrmVCEntry ::=
                SEQUENCE {
                    dcmAlrmVCFamilyId
                        INTEGER,
                    dcmAlrmVCTyp
                        INTEGER,
                    dcmAlrmVCTrapSend
                        INTEGER,
                    dcmAlrmVCDisplay
                        INTEGER
                }


    dcmAlrmVCFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmVCEntry 1 }


    dcmAlrmVCTyp OBJECT-TYPE
        SYNTAX  INTEGER {
                vcReady212(1),
                vcNotReady213(2),
                lossOfSync220(3),
                syncBack221(4),
                vcRejected231(5),
                endOfReject232(6)
                }
        ACCESS  read-only
        STATUS  mandatory
        DESCRIPTION
                ""
        ::= { dcmAlrmVCEntry 2 }


    dcmAlrmVCTrapSend OBJECT-TYPE
        SYNTAX  INTEGER {
                yes(1),
                no(2)
                }
        ACCESS  read-write
        STATUS  mandatory
        DESCRIPTION
                ""
        ::= { dcmAlrmVCEntry 3 }


    dcmAlrmVCDisplay OBJECT-TYPE
        SYNTAX  INTEGER {
                yes(1),
                no(2)
                }
        ACCESS  read-write
        STATUS  mandatory
        DESCRIPTION
                ""
        ::= { dcmAlrmVCEntry 4 }


    dcmAlrmLMITable OBJECT-TYPE
        SYNTAX  SEQUENCE OF DcmAlrmLMIEntry
        ACCESS  not-accessible
        STATUS  mandatory
        DESCRIPTION
                ""
        ::= { dcManagement 4 }


    dcmAlrmLMIEntry OBJECT-TYPE
        SYNTAX  DcmAlrmLMIEntry
        ACCESS  not-accessible
        STATUS  mandatory
        DESCRIPTION
                "An entry of dcmAlrmLMITable."
        INDEX   { dcmAlrmLMIFamilyId,
                  dcmAlrmLMITyp }
        ::= { dcmAlrmLMITable 1 }


        DcmAlrmLMIEntry ::=
                SEQUENCE {
                    dcmAlrmLMIFamilyId
                        INTEGER,
                    dcmAlrmLMITyp
                        INTEGER,
                    dcmAlrmLMITrapSend
                        INTEGER,
                    dcmAlrmLMIDisplay
                        INTEGER
                }


    dcmAlrmLMIFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmLMIEntry 1 }


    dcmAlrmLMITyp OBJECT-TYPE
        SYNTAX  INTEGER {
                dcnxLmi234(1),
                cnxLmi235(2),
                lmiDlciNotConf236(3),
                lmiIntError237(4)
                }
        ACCESS  read-only
        STATUS  mandatory
        DESCRIPTION
                ""
        ::= { dcmAlrmLMIEntry 2 }


    dcmAlrmLMITrapSend OBJECT-TYPE
        SYNTAX  INTEGER {
                yes(1),
                no(2)
                }
        ACCESS  read-write
        STATUS  mandatory
        DESCRIPTION
                ""
        ::= { dcmAlrmLMIEntry 3 }


    dcmAlrmLMIDisplay OBJECT-TYPE
        SYNTAX  INTEGER {
                yes(1),
                no(2)
                }
        ACCESS  read-write
        STATUS  mandatory
        DESCRIPTION
                ""
        ::= { dcmAlrmLMIEntry 4 }


    dcmAlrmSwTable OBJECT-TYPE
        SYNTAX  SEQUENCE OF DcmAlrmSwEntry
        ACCESS  not-accessible
        STATUS  mandatory
        DESCRIPTION
                ""
        ::= { dcManagement 5 }


    dcmAlrmSwEntry OBJECT-TYPE
        SYNTAX  DcmAlrmSwEntry
        ACCESS  not-accessible
        STATUS  mandatory
        DESCRIPTION
                "An entry of dcmAlrmSwTable."
        INDEX   { dcmAlrmSwFamilyId,
                  dcmAlrmSwTyp }
        ::= { dcmAlrmSwTable 1 }


        DcmAlrmSwEntry ::=
                SEQUENCE {
                    dcmAlrmSwFamilyId
                        INTEGER,
                    dcmAlrmSwTyp
                        INTEGER,
                    dcmAlrmSwTrapSend
                        INTEGER,
                    dcmAlrmSwDisplay
                        INTEGER
                }


    dcmAlrmSwFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmSwEntry 1 }


    dcmAlrmSwTyp OBJECT-TYPE
        SYNTAX  INTEGER {
                outgoingCall238(1),
                incomingCall239(2),
                localDisc240(3),
                remoteDisc241(4),
                backup242(5)
                }
        ACCESS  read-only
        STATUS  mandatory
        DESCRIPTION
                ""
        ::= { dcmAlrmSwEntry 2 }


    dcmAlrmSwTrapSend OBJECT-TYPE
        SYNTAX  INTEGER {
                yes(1),
                no(2)
                }
        ACCESS  read-write
        STATUS  mandatory
        DESCRIPTION
                ""
        ::= { dcmAlrmSwEntry 3 }


    dcmAlrmSwDisplay OBJECT-TYPE
        SYNTAX  INTEGER {
                yes(1),
                no(2)
                }
        ACCESS  read-write
        STATUS  mandatory
        DESCRIPTION
                ""
        ::= { dcmAlrmSwEntry 4 }


    dcmAlrmCmpTable OBJECT-TYPE
        SYNTAX  SEQUENCE OF DcmAlrmCmpEntry
        ACCESS  not-accessible
        STATUS  mandatory
        DESCRIPTION
                ""
        ::= { dcManagement 6 }


    dcmAlrmCmpEntry OBJECT-TYPE
        SYNTAX  DcmAlrmCmpEntry
        ACCESS  not-accessible
        STATUS  mandatory
        DESCRIPTION
                "An entry of dcmAlrmCmpTable."
        INDEX   { dcmAlrmCmpFamilyId,
                  dcmAlrmCmpTyp }
        ::= { dcmAlrmCmpTable 1 }


        DcmAlrmCmpEntry ::=
                SEQUENCE {
                    dcmAlrmCmpFamilyId
                        INTEGER,
                    dcmAlrmCmpTyp
                        INTEGER,
                    dcmAlrmCmpTrapSend
                        INTEGER,
                    dcmAlrmCmpDisplay
                        INTEGER
                }


    dcmAlrmCmpFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmCmpEntry 1 }


    dcmAlrmCmpTyp OBJECT-TYPE
        SYNTAX  INTEGER {
                compOn214(1),
                compOff215(2),
                algoCompNotOk228(3),
                algoCompOk229(4)
                }
        ACCESS  read-only
        STATUS  mandatory
        DESCRIPTION
                ""
        ::= { dcmAlrmCmpEntry 2 }


    dcmAlrmCmpTrapSend OBJECT-TYPE
        SYNTAX  INTEGER {
                yes(1),
                no(2)
                }
        ACCESS  read-write
        STATUS  mandatory
        DESCRIPTION
                ""
        ::= { dcmAlrmCmpEntry 3 }


    dcmAlrmCmpDisplay OBJECT-TYPE
        SYNTAX  INTEGER {
                yes(1),
                no(2)
                }
        ACCESS  read-write
        STATUS  mandatory
        DESCRIPTION
                ""
        ::= { dcmAlrmCmpEntry 4 }


    dcmAlrmFaxTable OBJECT-TYPE
        SYNTAX  SEQUENCE OF DcmAlrmFaxEntry
        ACCESS  not-accessible
        STATUS  mandatory
        DESCRIPTION
                ""
        ::= { dcManagement 7 }


    dcmAlrmFaxEntry OBJECT-TYPE
        SYNTAX  DcmAlrmFaxEntry
        ACCESS  not-accessible
        STATUS  mandatory
        DESCRIPTION
                "An entry of dcmAlrmFaxTable."
        INDEX   { dcmAlrmFaxFamilyId,
                  dcmAlrmFaxTyp }
        ::= { dcmAlrmFaxTable 1 }


        DcmAlrmFaxEntry ::=
                SEQUENCE {
                    dcmAlrmFaxFamilyId
                        INTEGER,
                    dcmAlrmFaxTyp
                        INTEGER,
                    dcmAlrmFaxTrapSend
                        INTEGER,
                    dcmAlrmFaxDisplay
                        INTEGER
                }


    dcmAlrmFaxFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmFaxEntry 1 }


    dcmAlrmFaxTyp OBJECT-TYPE
        SYNTAX  INTEGER {
                faxStart218(1),
                faxEnd219(2)
                }
        ACCESS  read-only
        STATUS  mandatory
        DESCRIPTION
                ""
        ::= { dcmAlrmFaxEntry 2 }


    dcmAlrmFaxTrapSend OBJECT-TYPE
        SYNTAX  INTEGER {
                yes(1),
                no(2)
                }
        ACCESS  read-write
        STATUS  mandatory
        DESCRIPTION
                ""
        ::= { dcmAlrmFaxEntry 3 }


    dcmAlrmFaxDisplay OBJECT-TYPE
        SYNTAX  INTEGER {
                yes(1),
                no(2)
                }
        ACCESS  read-write
        STATUS  mandatory
        DESCRIPTION
                ""
        ::= { dcmAlrmFaxEntry 4 }


    dcmAlrmTftpTable OBJECT-TYPE
        SYNTAX  SEQUENCE OF DcmAlrmTftpEntry
        ACCESS  not-accessible
        STATUS  mandatory
        DESCRIPTION
                ""
        ::= { dcManagement 8 }


    dcmAlrmTftpEntry OBJECT-TYPE
        SYNTAX  DcmAlrmTftpEntry
        ACCESS  not-accessible
        STATUS  mandatory
        DESCRIPTION
                "An entry of dcmAlrmTftpTable."
        INDEX   { dcmAlrmTftpFamilyId,
                  dcmAlrmTftpTyp }
        ::= { dcmAlrmTftpTable 1 }


        DcmAlrmTftpEntry ::=
                SEQUENCE {
                    dcmAlrmTftpFamilyId
                        INTEGER,
                    dcmAlrmTftpTyp
                        INTEGER,
                    dcmAlrmTftpTrapSend
                        INTEGER,
                    dcmAlrmTftpDisplay
                        INTEGER
                }


    dcmAlrmTftpFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmTftpEntry 1 }


    dcmAlrmTftpTyp OBJECT-TYPE
        SYNTAX  INTEGER {
                dwnStart243(1),
                dwnEnd244(2),
                dwnError245(3)
                }
        ACCESS  read-only
        STATUS  mandatory
        DESCRIPTION
                ""
        ::= { dcmAlrmTftpEntry 2 }


    dcmAlrmTftpTrapSend OBJECT-TYPE
        SYNTAX  INTEGER {
                yes(1),
                no(2)
                }
        ACCESS  read-write
        STATUS  mandatory
        DESCRIPTION
                ""
        ::= { dcmAlrmTftpEntry 3 }


    dcmAlrmTftpDisplay OBJECT-TYPE
        SYNTAX  INTEGER {
                yes(1),
                no(2)
                }
        ACCESS  read-write
        STATUS  mandatory
        DESCRIPTION
                ""
        ::= { dcmAlrmTftpEntry 4 }


    dcmAlrmSvcTable OBJECT-TYPE
        SYNTAX  SEQUENCE OF DcmAlrmSvcEntry
        ACCESS  not-accessible
        STATUS  mandatory
        DESCRIPTION
                ""
        ::= { dcManagement 9 }


    dcmAlrmSvcEntry OBJECT-TYPE
        SYNTAX  DcmAlrmSvcEntry
        ACCESS  not-accessible
        STATUS  mandatory
        DESCRIPTION
                "An entry of dcmAlrmSvcTable."
        INDEX   { dcmAlrmSvcFamilyId,
                  dcmAlrmSvcTyp }
        ::= { dcmAlrmSvcTable 1 }


        DcmAlrmSvcEntry ::=
                SEQUENCE {
                    dcmAlrmSvcFamilyId
                        INTEGER,
                    dcmAlrmSvcTyp
                        INTEGER,
                    dcmAlrmSvcTrapSend
                        INTEGER,
                    dcmAlrmSvcDisplay
                        INTEGER
                }


    dcmAlrmSvcFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmSvcEntry 1 }


    dcmAlrmSvcTyp OBJECT-TYPE
        SYNTAX  INTEGER {
                svcOutCall246(1),
                svcInCall247(2),
                svcLocalConnect248(3),
                svcLocalDisc249(4),
                svcRemoteDisc250(5),
                svcOutFailCall251(6),
                svcInFailCall252(7)
                }
        ACCESS  read-only
        STATUS  mandatory
        DESCRIPTION
                ""
        ::= { dcmAlrmSvcEntry 2 }


    dcmAlrmSvcTrapSend OBJECT-TYPE
        SYNTAX  INTEGER {
                yes(1),
                no(2)
                }
        ACCESS  read-write
        STATUS  mandatory
        DESCRIPTION
                ""
        ::= { dcmAlrmSvcEntry 3 }


    dcmAlrmSvcDisplay OBJECT-TYPE
        SYNTAX  INTEGER {
                yes(1),
                no(2)
                }
        ACCESS  read-write
        STATUS  mandatory
        DESCRIPTION
                ""
        ::= { dcmAlrmSvcEntry 4 }


    dcmAlrmSyncTable OBJECT-TYPE
        SYNTAX  SEQUENCE OF DcmAlrmSyncEntry
        ACCESS  not-accessible
        STATUS  mandatory
        DESCRIPTION
                ""
        ::= { dcManagement 10 }


    dcmAlrmSyncEntry OBJECT-TYPE
        SYNTAX  DcmAlrmSyncEntry
        ACCESS  not-accessible
        STATUS  mandatory
        DESCRIPTION
                "An entry of dcmAlrmSyncTable."
        INDEX   { dcmAlrmSyncFamilyId,
                  dcmAlrmSyncTyp }
        ::= { dcmAlrmSyncTable 1 }


        DcmAlrmSyncEntry ::=
                SEQUENCE {
                    dcmAlrmSyncFamilyId
                        INTEGER,
                    dcmAlrmSyncTyp
                        INTEGER,
                    dcmAlrmSyncTrapSend
                        INTEGER,
                    dcmAlrmSyncDisplay
                        INTEGER
                }


    dcmAlrmSyncFamilyId OBJECT-TYPE
        SYNTAX  INTEGER {
                f00System(1),
                f01Tftp(2),
                f02Junction(3),
                f03Lmi(4),
                f04Svc(5),
                f05Compression(6),
                f06ServiceCanal(7),
                f07Fax(8),
                f08Switching(9),
                f09Synchronization(10)
                }
        ACCESS  read-only
        STATUS  mandatory
        DESCRIPTION
                ""
        ::= { dcmAlrmSyncEntry 1 }


    dcmAlrmSyncTyp OBJECT-TYPE
        SYNTAX  INTEGER {
                tdmUp253(1),
                tdmDown254(2),
                vpbSync255(3),
                vpbOutofSync256(4)
                }
        ACCESS  read-only
        STATUS  mandatory
        DESCRIPTION
                ""
        ::= { dcmAlrmSyncEntry 2 }


    dcmAlrmSyncTrapSend OBJECT-TYPE
        SYNTAX  INTEGER {
                yes(1),
                no(2)
                }
        ACCESS  read-write
        STATUS  mandatory
        DESCRIPTION
                ""
        ::= { dcmAlrmSyncEntry 3 }


    dcmAlrmSyncDisplay OBJECT-TYPE
        SYNTAX  INTEGER {
                yes(1),
                no(2)
                }
        ACCESS  read-write
        STATUS  mandatory
        DESCRIPTION
                ""
        ::= { dcmAlrmSyncEntry 4 }


    dcInterfaces OBJECT IDENTIFIER ::= { dvbConfig 15 }


    dcfPhysicalPortTable OBJECT-TYPE
        SYNTAX  SEQUENCE OF DcfPhysicalPortEntry
        ACCESS  not-accessible
        STATUS  mandatory
        DESCRIPTION
                ""
        ::= { dcInterfaces 1 }


    dcfPhysicalPortEntry OBJECT-TYPE
        SYNTAX  DcfPhysicalPortEntry
        ACCESS  not-accessible
        STATUS  mandatory
        DESCRIPTION
                "An entry of dcfPhysicalPortTable."
        INDEX   { dcfPhysPortId }
        ::= { dcfPhysicalPortTable 1 }


        DcfPhysicalPortEntry ::=
                SEQUENCE {
                    dcfPhysPortId
                        INTEGER,
                    dcfPhysPortConnector
                        INTEGER
                }


    dcfPhysPortId OBJECT-TYPE
        SYNTAX  INTEGER {
                l0(1),
                l1(2),
                frontPannel(3)
                }
        ACCESS  read-only
        STATUS  mandatory
        DESCRIPTION
                ""
        ::= { dcfPhysicalPortEntry 1 }


    dcfPhysPortConnector OBJECT-TYPE
        SYNTAX  INTEGER {
                db25(1),
                din(2)
                }
        ACCESS  read-only
        STATUS  mandatory
        DESCRIPTION
                ""
        ::= { dcfPhysicalPortEntry 2 }


    dcfNumericLines OBJECT IDENTIFIER ::= { dcInterfaces 5 }


    dcfNumericLineTable OBJECT-TYPE
        SYNTAX  SEQUENCE OF DcfNumericLineEntry
        ACCESS  not-accessible
        STATUS  mandatory
        DESCRIPTION
                ""
        ::= { dcfNumericLines 1 }


    dcfNumericLineEntry OBJECT-TYPE
        SYNTAX  DcfNumericLineEntry
        ACCESS  not-accessible
        STATUS  mandatory
        DESCRIPTION
                "An entry of dcfNumericLineTable."
        INDEX   { dcfNumericLineInterfaceId }
        ::= { dcfNumericLineTable 1 }


        DcfNumericLineEntry ::=
                SEQUENCE {
                    dcfNumericLineInterfaceId
                        INTEGER,
                    dcfNumericLineType
                        INTEGER
                }


    dcfNumericLineInterfaceId OBJECT-TYPE
        SYNTAX  INTEGER {
                l0(1),
                l1(2),
                frontPannel(3)
                }
        ACCESS  read-only
        STATUS  mandatory
        DESCRIPTION
                ""
        ::= { dcfNumericLineEntry 1 }


    dcfNumericLineType OBJECT-TYPE
        SYNTAX  INTEGER {
                dataLine(1),
                configurationLine(2),
                debug(3)
                }
        ACCESS  read-only
        STATUS  mandatory
        DESCRIPTION
                ""
        ::= { dcfNumericLineEntry 2 }


    dcfDataLineTable OBJECT-TYPE
        SYNTAX  SEQUENCE OF DcfDataLineEntry
        ACCESS  not-accessible
        STATUS  mandatory
        DESCRIPTION
                ""
        ::= { dcfNumericLines 2 }


    dcfDataLineEntry OBJECT-TYPE
        SYNTAX  DcfDataLineEntry
        ACCESS  not-accessible
        STATUS  mandatory
        DESCRIPTION
                "An entry of dcfDataLineTable."
        INDEX   { dcfDataLineInterfaceId }
        ::= { dcfDataLineTable 1 }


        DcfDataLineEntry ::=
                SEQUENCE {
                    dcfDataLineInterfaceId
                        INTEGER,
                    dcfDataLineRate
                        INTEGER,
                    dcfDataLineRts105
                        INTEGER,
                    dcfDataLineDtr108
                        INTEGER,
                    dcfDataLineCts106
                        INTEGER,
                    dcfDataLineDsr107
                        INTEGER,
                    dcfDataLineDcd109
                        INTEGER
                }


    dcfDataLineInterfaceId OBJECT-TYPE
        SYNTAX  INTEGER {
                l0(1),
                l1(2),
                other(3)
                }
        ACCESS  read-only
        STATUS  mandatory
        DESCRIPTION
                ""
        ::= { dcfDataLineEntry 1 }


    dcfDataLineRate OBJECT-TYPE
        SYNTAX  INTEGER {
                s4800(1),
                s9600(2),
                s19200(3),
                s38400(4),
                s48000(5),
                s56000(6),
                s64000(7),
                s72000(8),
                s128000(9),
                s144000(10),
                s256000(11),
                s512000(12),
                s1024000(13),
                s2048000(14)
                }
        ACCESS  read-write
        STATUS  mandatory
        DESCRIPTION
                ""
        ::= { dcfDataLineEntry 2 }


    dcfDataLineRts105 OBJECT-TYPE
        SYNTAX  INTEGER {
                unused(1),
                used(2),
                standard(3),
                off(4),
                on(5)
                }
        ACCESS  read-write
        STATUS  mandatory
        DESCRIPTION
                ""
        ::= { dcfDataLineEntry 3 }


    dcfDataLineDtr108 OBJECT-TYPE
        SYNTAX  INTEGER {
                unused(1),
                used(2),
                standard(3),
                off(4),
                on(5)
                }
        ACCESS  read-write
        STATUS  mandatory
        DESCRIPTION
                ""
        ::= { dcfDataLineEntry 4 }


    dcfDataLineCts106 OBJECT-TYPE
        SYNTAX  INTEGER {
                unused(1),
                used(2),
                standard(3),
                off(4),
                on(5)
                }
        ACCESS  read-write
        STATUS  mandatory
        DESCRIPTION
                ""
        ::= { dcfDataLineEntry 5 }


    dcfDataLineDsr107 OBJECT-TYPE
        SYNTAX  INTEGER {
                unused(1),
                used(2),
                standard(3),
                off(4),
                on(5)
                }
        ACCESS  read-write
        STATUS  mandatory
        DESCRIPTION
                ""
        ::= { dcfDataLineEntry 6 }


    dcfDataLineDcd109 OBJECT-TYPE
        SYNTAX  INTEGER {
                unused(1),
                used(2),
                standard(3),
                off(4),
                on(5)
                }
        ACCESS  read-write
        STATUS  mandatory
        DESCRIPTION
                ""
        ::= { dcfDataLineEntry 7 }


    dcfConfLineTable OBJECT-TYPE
        SYNTAX  SEQUENCE OF DcfConfLineEntry
        ACCESS  not-accessible
        STATUS  mandatory
        DESCRIPTION
                ""
        ::= { dcfNumericLines 3 }


    dcfConfLineEntry OBJECT-TYPE
        SYNTAX  DcfConfLineEntry
        ACCESS  not-accessible
        STATUS  mandatory
        DESCRIPTION
                "An entry of dcfConfLineTable."
        INDEX   { dcfConfLineInterfaceId }
        ::= { dcfConfLineTable 1 }


        DcfConfLineEntry ::=
                SEQUENCE {
                    dcfConfLineInterfaceId
                        INTEGER,
                    dcfConfLineRate
                        INTEGER
                }


    dcfConfLineInterfaceId OBJECT-TYPE
        SYNTAX  INTEGER {
                l0(1),
                l1(2),
                frontPannel(3)
                }
        ACCESS  read-only
        STATUS  mandatory
        DESCRIPTION
                ""
        ::= { dcfConfLineEntry 1 }


    dcfConfLineRate OBJECT-TYPE
        SYNTAX  INTEGER {
                s4800(1),
                s9600(2),
                s19200(3),
                s38400(4),
                s48000(5),
                s56000(6),
                s64000(7),
                s72000(8),
                s128000(9),
                s144000(10),
                s256000(11),
                s512000(12),
                s1024000(13),
                s2048000(14)
                }
        ACCESS  read-only
        STATUS  mandatory
        DESCRIPTION
                ""
        ::= { dcfConfLineEntry 2 }


    dcLogicalPorts OBJECT IDENTIFIER ::= { dvbConfig 20 }


    dclLogicalPortTable OBJECT-TYPE
        SYNTAX  SEQUENCE OF DclLogicalPortEntry
        ACCESS  not-accessible
        STATUS  mandatory
        DESCRIPTION
                ""
        ::= { dcLogicalPorts 1 }


    dclLogicalPortEntry OBJECT-TYPE
        SYNTAX  DclLogicalPortEntry
        ACCESS  not-accessible
        STATUS  mandatory
        DESCRIPTION
                "An entry of dclLogicalPortTable."
        INDEX   { dclLogPortId }
        ::= { dclLogicalPortTable 1 }


        DclLogicalPortEntry ::=
                SEQUENCE {
                    dclLogPortId
                        INTEGER,
                    dclLogPortStatus
                        INTEGER,
                    dclLogPortType
                        INTEGER
                }


    dclLogPortId OBJECT-TYPE
        SYNTAX  INTEGER (0..0)
        ACCESS  read-only
        STATUS  mandatory
        DESCRIPTION
                ""
        ::= { dclLogicalPortEntry 1 }


    dclLogPortStatus OBJECT-TYPE
        SYNTAX  INTEGER {
                valid(1),
                invalid(2)
                }
        ACCESS  read-write
        STATUS  mandatory
        DESCRIPTION
                ""
        ::= { dclLogicalPortEntry 2 }


    dclLogPortType OBJECT-TYPE
        SYNTAX  INTEGER {
                frTe(1),
                frSe(2)
                }
        ACCESS  read-write
        STATUS  mandatory
        DESCRIPTION
                ""
        ::= { dclLogicalPortEntry 3 }


    dclFrameRelay OBJECT IDENTIFIER ::= { dcLogicalPorts 5 }


    dclFrTerminalEquipment OBJECT IDENTIFIER ::= { dclFrameRelay 1 }


    dclFrTeLogPortTable OBJECT-TYPE
        SYNTAX  SEQUENCE OF DclFrTeLogPortEntry
        ACCESS  not-accessible
        STATUS  mandatory
        DESCRIPTION
                ""
        ::= { dclFrTerminalEquipment 1 }


    dclFrTeLogPortEntry OBJECT-TYPE
        SYNTAX  DclFrTeLogPortEntry
        ACCESS  not-accessible
        STATUS  mandatory
        DESCRIPTION
                "An entry of dclFrTeLogPortTable."
        INDEX   { dclFrTeLpLogPortId }
        ::= { dclFrTeLogPortTable 1 }


        DclFrTeLogPortEntry ::=
                SEQUENCE {
                    dclFrTeLpLogPortId
                        INTEGER,
                    dclFrTeLpInterfaceId
                        INTEGER,
                    dclFrTeLpConfigId
                        INTEGER,
                    dclFrTeLpLmi
                        INTEGER
                }


    dclFrTeLpLogPortId OBJECT-TYPE
        SYNTAX  INTEGER (0..0)
        ACCESS  read-only
        STATUS  mandatory
        DESCRIPTION
                ""
        ::= { dclFrTeLogPortEntry 1 }


    dclFrTeLpInterfaceId OBJECT-TYPE
        SYNTAX  INTEGER {
                l0(1),
                l1(2),
                other(3)
                }
        ACCESS  read-only
        STATUS  mandatory
        DESCRIPTION
                ""
        ::= { dclFrTeLogPortEntry 2 }


    dclFrTeLpConfigId OBJECT-TYPE
        SYNTAX  INTEGER (0..0)
        ACCESS  read-only
        STATUS  mandatory
        DESCRIPTION
                ""
        ::= { dclFrTeLogPortEntry 3 }


    dclFrTeLpLmi OBJECT-TYPE
        SYNTAX  INTEGER {
                off(1),
                lmiUni(2)
                }
        ACCESS  read-write
        STATUS  mandatory
        DESCRIPTION
                ""
        ::= { dclFrTeLogPortEntry 4 }


    dclFrSwitchEquipment OBJECT IDENTIFIER ::= { dclFrameRelay 2 }


    dclFrSeLogPortTable OBJECT-TYPE
        SYNTAX  SEQUENCE OF DclFrSeLogPortEntry
        ACCESS  not-accessible
        STATUS  mandatory
        DESCRIPTION
                ""
        ::= { dclFrSwitchEquipment 1 }


    dclFrSeLogPortEntry OBJECT-TYPE
        SYNTAX  DclFrSeLogPortEntry
        ACCESS  not-accessible
        STATUS  mandatory
        DESCRIPTION
                "An entry of dclFrSeLogPortTable."
        INDEX   { dclFrSeLpLogPortId }
        ::= { dclFrSeLogPortTable 1 }


        DclFrSeLogPortEntry ::=
                SEQUENCE {
                    dclFrSeLpLogPortId
                        INTEGER,
                    dclFrSeLpInterfaceId
                        INTEGER,
                    dclFrSeLpConfigId
                        INTEGER
                }


    dclFrSeLpLogPortId OBJECT-TYPE
        SYNTAX  INTEGER (0..0)
        ACCESS  read-only
        STATUS  mandatory
        DESCRIPTION
                ""
        ::= { dclFrSeLogPortEntry 1 }


    dclFrSeLpInterfaceId OBJECT-TYPE
        SYNTAX  INTEGER {
                l0(1),
                l1(2),
                other(3)
                }
        ACCESS  read-only
        STATUS  mandatory
        DESCRIPTION
                ""
        ::= { dclFrSeLogPortEntry 2 }


    dclFrSeLpConfigId OBJECT-TYPE
        SYNTAX  INTEGER (0..0)
        ACCESS  read-only
        STATUS  mandatory
        DESCRIPTION
                ""
        ::= { dclFrSeLogPortEntry 3 }


    dclFrConfigurationTe OBJECT IDENTIFIER ::= { dclFrameRelay 3 }


    dclFrLmiParameterTable OBJECT-TYPE
        SYNTAX  SEQUENCE OF DclFrLmiParameterEntry
        ACCESS  not-accessible
        STATUS  mandatory
        DESCRIPTION
                ""
        ::= { dclFrConfigurationTe 1 }


    dclFrLmiParameterEntry OBJECT-TYPE
        SYNTAX  DclFrLmiParameterEntry
        ACCESS  not-accessible
        STATUS  mandatory
        DESCRIPTION
                "An entry of dclFrLmiParameterTable."
        INDEX   { dclFrLmiParaConfigId }
        ::= { dclFrLmiParameterTable 1 }


        DclFrLmiParameterEntry ::=
                SEQUENCE {
                    dclFrLmiParaConfigId
                        INTEGER,
                    dclFrLmiParaDlci
                        INTEGER,
                    dclFrLmiParaStandard
                        INTEGER,
                    dclFrLmiParaAccessibilityCondition
                        INTEGER,
                    dclFrLmiParaN391FullStatusPollCount
                        INTEGER,
                    dclFrLmiParaN392ErrorThreshold
                        INTEGER,
                    dclFrLmiParaN393MonitoredEventCount
                        INTEGER,
                    dclFrLmiParaT391LinkIntegPollTimer
                        INTEGER
                }


    dclFrLmiParaConfigId OBJECT-TYPE
        SYNTAX  INTEGER (0..0)
        ACCESS  read-only
        STATUS  mandatory
        DESCRIPTION
                ""
        ::= { dclFrLmiParameterEntry 1 }


    dclFrLmiParaDlci OBJECT-TYPE
        SYNTAX  INTEGER (0..1023)
        ACCESS  read-write
        STATUS  mandatory
        DESCRIPTION
                ""
        ::= { dclFrLmiParameterEntry 2 }


    dclFrLmiParaStandard OBJECT-TYPE
        SYNTAX  INTEGER {
                ansiT1-617d(1),
                itutQ933a(2)
                }
        ACCESS  read-write
        STATUS  mandatory
        DESCRIPTION
                ""
        ::= { dclFrLmiParameterEntry 3 }


    dclFrLmiParaAccessibilityCondition OBJECT-TYPE
        SYNTAX  INTEGER (0..10)
        ACCESS  read-write
        STATUS  mandatory
        DESCRIPTION
                ""
        ::= { dclFrLmiParameterEntry 4 }


    dclFrLmiParaN391FullStatusPollCount OBJECT-TYPE
        SYNTAX  INTEGER (1..255)
        ACCESS  read-write
        STATUS  mandatory
        DESCRIPTION
                ""
        ::= { dclFrLmiParameterEntry 5 }


    dclFrLmiParaN392ErrorThreshold OBJECT-TYPE
        SYNTAX  INTEGER (1..10)
        ACCESS  read-write
        STATUS  mandatory
        DESCRIPTION
                ""
        ::= { dclFrLmiParameterEntry 6 }


    dclFrLmiParaN393MonitoredEventCount OBJECT-TYPE
        SYNTAX  INTEGER (1..10)
        ACCESS  read-write
        STATUS  mandatory
        DESCRIPTION
                ""
        ::= { dclFrLmiParameterEntry 7 }


    dclFrLmiParaT391LinkIntegPollTimer OBJECT-TYPE
        SYNTAX  INTEGER (5..30)
        ACCESS  read-write
        STATUS  mandatory
        DESCRIPTION
                ""
        ::= { dclFrLmiParameterEntry 8 }


    dclFrConfigurationSe OBJECT IDENTIFIER ::= { dclFrameRelay 4 }


    dclFrSeSignallingTable OBJECT-TYPE
        SYNTAX  SEQUENCE OF DclFrSeSignallingEntry
        ACCESS  not-accessible
        STATUS  mandatory
        DESCRIPTION
                ""
        ::= { dclFrConfigurationSe 1 }


    dclFrSeSignallingEntry OBJECT-TYPE
        SYNTAX  DclFrSeSignallingEntry
        ACCESS  not-accessible
        STATUS  mandatory
        DESCRIPTION
                "An entry of dclFrSeSignallingTable."
        INDEX   { dclFrSeSigConfigId }
        ::= { dclFrSeSignallingTable 1 }


        DclFrSeSignallingEntry ::=
                SEQUENCE {
                    dclFrSeSigConfigId
                        INTEGER,
                    dclFrSeSigOuputTimeout
                        INTEGER,
                    dclFrSeSigSignalOutputWinSize
                        INTEGER,
                    dclFrSeSigN200RetransMaxCount
                        INTEGER,
                    dclFrSeSigT200RetransTimer
                        INTEGER,
                    dclFrSeSigT203InactivityTimer
                        INTEGER,
                    dclFrSeSigT303SetupResponseTimer
                        INTEGER,
                    dclFrSeSigT305DisconnectResponseTimer
                        INTEGER,
                    dclFrSeSigT308ReleaseResponseTimer
                        INTEGER,
                    dclFrSeSigT310CallProceedingTimer
                        INTEGER,
                    dclFrSeSigT316RestartAcknowledgeTimer
                        INTEGER
                }


    dclFrSeSigConfigId OBJECT-TYPE
        SYNTAX  INTEGER (0..0)
        ACCESS  read-only
        STATUS  mandatory
        DESCRIPTION
                ""
        ::= { dclFrSeSignallingEntry 1 }


    dclFrSeSigOuputTimeout OBJECT-TYPE
        SYNTAX  INTEGER (0..51000)
        ACCESS  read-write
        STATUS  mandatory
        DESCRIPTION
                ""
        ::= { dclFrSeSignallingEntry 2 }


    dclFrSeSigSignalOutputWinSize OBJECT-TYPE
        SYNTAX  INTEGER (1..7)
        ACCESS  read-write
        STATUS  mandatory
        DESCRIPTION
                ""
        ::= { dclFrSeSignallingEntry 3 }


    dclFrSeSigN200RetransMaxCount OBJECT-TYPE
        SYNTAX  INTEGER (1..255)
        ACCESS  read-write
        STATUS  mandatory
        DESCRIPTION
                ""
        ::= { dclFrSeSignallingEntry 5 }


    dclFrSeSigT200RetransTimer OBJECT-TYPE
        SYNTAX  INTEGER (0..25500)
        ACCESS  read-write
        STATUS  mandatory
        DESCRIPTION
                ""
        ::= { dclFrSeSignallingEntry 6 }


    dclFrSeSigT203InactivityTimer OBJECT-TYPE
        SYNTAX  INTEGER (0..255)
        ACCESS  read-write
        STATUS  mandatory
        DESCRIPTION
                ""
        ::= { dclFrSeSignallingEntry 7 }


    dclFrSeSigT303SetupResponseTimer OBJECT-TYPE
        SYNTAX  INTEGER (1..255)
        ACCESS  read-write
        STATUS  mandatory
        DESCRIPTION
                ""
        ::= { dclFrSeSignallingEntry 8 }


    dclFrSeSigT305DisconnectResponseTimer OBJECT-TYPE
        SYNTAX  INTEGER (1..255)
        ACCESS  read-write
        STATUS  mandatory
        DESCRIPTION
                ""
        ::= { dclFrSeSignallingEntry 9 }


    dclFrSeSigT308ReleaseResponseTimer OBJECT-TYPE
        SYNTAX  INTEGER (1..255)
        ACCESS  read-write
        STATUS  mandatory
        DESCRIPTION
                ""
        ::= { dclFrSeSignallingEntry 10 }


    dclFrSeSigT310CallProceedingTimer OBJECT-TYPE
        SYNTAX  INTEGER (1..255)
        ACCESS  read-write
        STATUS  mandatory
        DESCRIPTION
                ""
        ::= { dclFrSeSignallingEntry 11 }


    dclFrSeSigT316RestartAcknowledgeTimer OBJECT-TYPE
        SYNTAX  INTEGER (0..255)
        ACCESS  read-write
        STATUS  mandatory
        DESCRIPTION
                ""
        ::= { dclFrSeSignallingEntry 12 }


    dcWanSwitch OBJECT IDENTIFIER ::= { dvbConfig 25 }


    dcwEquipParams OBJECT IDENTIFIER ::= { dcWanSwitch 1 }


    dcwEquipDnicZoAddr OBJECT-TYPE
        SYNTAX  OCTET STRING (SIZE(3))
        ACCESS  read-write
        STATUS  mandatory
        DESCRIPTION
                ""
        ::= { dcwEquipParams 1 }


    dcwEquipVoiceRoutingServicePortAddr OBJECT-TYPE
        SYNTAX  OCTET STRING (SIZE(1))
        ACCESS  read-write
        STATUS  mandatory
        DESCRIPTION
                ""
        ::= { dcwEquipParams 2 }


    dcwEquipIpVirtualPortAddr OBJECT-TYPE
        SYNTAX  OCTET STRING (SIZE(1))
        ACCESS  read-write
        STATUS  mandatory
        DESCRIPTION
                ""
        ::= { dcwEquipParams 3 }


    dcwEquipRemoteConfPortAddr OBJECT-TYPE
        SYNTAX  OCTET STRING (SIZE(1))
        ACCESS  read-write
        STATUS  mandatory
        DESCRIPTION
                ""
        ::= { dcwEquipParams 4 }


    dcwEquipVoiceVirtualPortAddr OBJECT-TYPE
        SYNTAX  OCTET STRING (SIZE(4))
        ACCESS  read-write
        STATUS  mandatory
        DESCRIPTION
                ""
        ::= { dcwEquipParams 5 }


    dcwEquipSVCDisconnectOnCongestion OBJECT-TYPE
        SYNTAX  INTEGER {
                valid(1),
                invalid(2)
                }
        ACCESS  read-write
        STATUS  mandatory
        DESCRIPTION
                ""
        ::= { dcwEquipParams 6 }


    dcwABPvcLpTable OBJECT-TYPE
        SYNTAX  SEQUENCE OF DcwABPvcLpEntry
        ACCESS  not-accessible
        STATUS  mandatory
        DESCRIPTION
                ""
        ::= { dcWanSwitch 2 }


    dcwABPvcLpEntry OBJECT-TYPE
        SYNTAX  DcwABPvcLpEntry
        ACCESS  not-accessible
        STATUS  mandatory
        DESCRIPTION
                "An entry of dcwABPvcLpTable."
        INDEX   { dcwABPvcLpId }
        ::= { dcwABPvcLpTable 1 }


        DcwABPvcLpEntry ::=
                SEQUENCE {
                    dcwABPvcLpId
                        INTEGER,
                    dcwABPvcLpAddress
                        OCTET STRING
                }


    dcwABPvcLpId OBJECT-TYPE
        SYNTAX  INTEGER (0..0)
        ACCESS  read-only
        STATUS  mandatory
        DESCRIPTION
                ""
        ::= { dcwABPvcLpEntry 1 }


    dcwABPvcLpAddress OBJECT-TYPE
        SYNTAX  OCTET STRING (SIZE(1))
        ACCESS  read-write
        STATUS  mandatory
        DESCRIPTION
                ""
        ::= { dcwABPvcLpEntry 2 }


    dcVirtualPorts OBJECT IDENTIFIER ::= { dvbConfig 30 }


    dcvVirtualPortTable OBJECT-TYPE
        SYNTAX  SEQUENCE OF DcvVirtualPortEntry
        ACCESS  not-accessible
        STATUS  mandatory
        DESCRIPTION
                ""
        ::= { dcVirtualPorts 1 }


    dcvVirtualPortEntry OBJECT-TYPE
        SYNTAX  DcvVirtualPortEntry
        ACCESS  not-accessible
        STATUS  mandatory
        DESCRIPTION
                "An entry of dcvVirtualPortTable."
        INDEX   { dcvVirtualPortId }
        ::= { dcvVirtualPortTable 1 }


        DcvVirtualPortEntry ::=
                SEQUENCE {
                    dcvVirtualPortId
                        INTEGER
                }


    dcvVirtualPortId OBJECT-TYPE
        SYNTAX  INTEGER {
                vpVoix(1),
                vpIp(2)
                }
        ACCESS  read-only
        STATUS  mandatory
        DESCRIPTION
                ""
        ::= { dcvVirtualPortEntry 1 }


    dcvIpVirtualPort OBJECT IDENTIFIER ::= { dcVirtualPorts 5 }


    dcvIpLocalTable OBJECT-TYPE
        SYNTAX  SEQUENCE OF DcvIpLocalEntry
        ACCESS  not-accessible
        STATUS  mandatory
        DESCRIPTION
                ""
        ::= { dcvIpVirtualPort 1 }


    dcvIpLocalEntry OBJECT-TYPE
        SYNTAX  DcvIpLocalEntry
        ACCESS  not-accessible
        STATUS  mandatory
        DESCRIPTION
                "An entry of dcvIpLocalTable."
        INDEX   { dcvIpLocVirtualPortId }
        ::= { dcvIpLocalTable 1 }


        DcvIpLocalEntry ::=
                SEQUENCE {
                    dcvIpLocVirtualPortId
                        INTEGER,
                    dcvIpLocAddressHost
                        IpAddress,
                    dcvIpLocSubNetMask
                        IpAddress,
                    dcvIpLocMtu
                        INTEGER,
                    dcvIpLocRouteNextHop
                        IpAddress,
                    dcvIpLocMinimumRecallTimer
                        INTEGER,
                    dcvIpLocSvcClearCallTimer
                        INTEGER,
                    dcvIpLocSvcCallRetryCount
                        INTEGER
                }


    dcvIpLocVirtualPortId OBJECT-TYPE
        SYNTAX  INTEGER {
                vpVoix(1),
                vpIp(2)
                }
        ACCESS  read-only
        STATUS  mandatory
        DESCRIPTION
                ""
        ::= { dcvIpLocalEntry 1 }


    dcvIpLocAddressHost OBJECT-TYPE
        SYNTAX  IpAddress
        ACCESS  read-write
        STATUS  mandatory
        DESCRIPTION
                ""
        ::= { dcvIpLocalEntry 2 }


    dcvIpLocSubNetMask OBJECT-TYPE
        SYNTAX  IpAddress
        ACCESS  read-write
        STATUS  mandatory
        DESCRIPTION
                ""
        ::= { dcvIpLocalEntry 3 }


    dcvIpLocMtu OBJECT-TYPE
        SYNTAX  INTEGER (576..9180)
        ACCESS  read-only
        STATUS  mandatory
        DESCRIPTION
                ""
        ::= { dcvIpLocalEntry 4 }


    dcvIpLocRouteNextHop OBJECT-TYPE
        SYNTAX  IpAddress
        ACCESS  read-write
        STATUS  mandatory
        DESCRIPTION
                ""
        ::= { dcvIpLocalEntry 5 }


    dcvIpLocMinimumRecallTimer OBJECT-TYPE
        SYNTAX  INTEGER (0..65535)
        ACCESS  read-write
        STATUS  mandatory
        DESCRIPTION
                ""
        ::= { dcvIpLocalEntry 6 }


    dcvIpLocSvcClearCallTimer OBJECT-TYPE
        SYNTAX  INTEGER (0..65535)
        ACCESS  read-write
        STATUS  mandatory
        DESCRIPTION
                ""
        ::= { dcvIpLocalEntry 7 }


    dcvIpLocSvcCallRetryCount OBJECT-TYPE
        SYNTAX  INTEGER (0..65535)
        ACCESS  read-write
        STATUS  mandatory
        DESCRIPTION
                ""
        ::= { dcvIpLocalEntry 8 }


    dcvSnmp OBJECT IDENTIFIER ::= { dcvIpVirtualPort 5 }


    dcvSnmpGen OBJECT IDENTIFIER ::= { dcvSnmp 1 }


    dcvSnmpGenVirtualPortId OBJECT-TYPE
        SYNTAX  INTEGER {
                vpVoix(1),
                vpIp(2)
                }
        ACCESS  read-write
        STATUS  mandatory
        DESCRIPTION
                ""
        ::= { dcvSnmpGen 1 }


    dcvSnmpGenCommunityStringReadOnly OBJECT-TYPE
        SYNTAX  DisplayString (SIZE(1..14))
        ACCESS  read-write
        STATUS  mandatory
        DESCRIPTION
                ""
        ::= { dcvSnmpGen 2 }


    dcvSnmpGenCommunityStringReadWrite OBJECT-TYPE
        SYNTAX  DisplayString (SIZE(1..14))
        ACCESS  read-write
        STATUS  mandatory
        DESCRIPTION
                ""
        ::= { dcvSnmpGen 3 }


    dcvSnmpGenCommunityStringTrap OBJECT-TYPE
        SYNTAX  DisplayString (SIZE(1..14))
        ACCESS  read-write
        STATUS  mandatory
        DESCRIPTION
                ""
        ::= { dcvSnmpGen 4 }


    dcvSnmpGenAuthenticationFailureTrap OBJECT-TYPE
        SYNTAX  INTEGER {
                off(1),
                on(2)
                }
        ACCESS  read-write
        STATUS  mandatory
        DESCRIPTION
                ""
        ::= { dcvSnmpGen 5 }


    dcvSnmpManagerTable OBJECT-TYPE
        SYNTAX  SEQUENCE OF DcvSnmpManagerEntry
        ACCESS  not-accessible
        STATUS  mandatory
        DESCRIPTION
                ""
        ::= { dcvSnmp 2 }


    dcvSnmpManagerEntry OBJECT-TYPE
        SYNTAX  DcvSnmpManagerEntry
        ACCESS  not-accessible
        STATUS  mandatory
        DESCRIPTION
                "An entry of dcvSnmpManagerTable."
        INDEX   { dcvSnmpManagerIpAddress }
        ::= { dcvSnmpManagerTable 1 }


        DcvSnmpManagerEntry ::=
                SEQUENCE {
                    dcvSnmpManagerIpAddress
                        IpAddress,
                    dcvSnmpManagerStatus
                        INTEGER,
                    dcvSnmpManagerName
                        DisplayString,
                    dcvSnmpManagerSendTraps
                        INTEGER,
                    dcvSnmpManagerTrapsUdpPort
                        INTEGER
                }


    dcvSnmpManagerIpAddress OBJECT-TYPE
        SYNTAX  IpAddress
        ACCESS  read-only
        STATUS  mandatory
        DESCRIPTION
                ""
        ::= { dcvSnmpManagerEntry 1 }


    dcvSnmpManagerStatus OBJECT-TYPE
        SYNTAX  INTEGER {
                valid(1),
                invalid(2)
                }
        ACCESS  read-write
        STATUS  mandatory
        DESCRIPTION
                ""
        ::= { dcvSnmpManagerEntry 2 }


    dcvSnmpManagerName OBJECT-TYPE
        SYNTAX  DisplayString (SIZE(1..12))
        ACCESS  read-write
        STATUS  mandatory
        DESCRIPTION
                ""
        ::= { dcvSnmpManagerEntry 3 }


    dcvSnmpManagerSendTraps OBJECT-TYPE
        SYNTAX  INTEGER {
                off(1),
                on(2)
                }
        ACCESS  read-write
        STATUS  mandatory
        DESCRIPTION
                ""
        ::= { dcvSnmpManagerEntry 4 }


    dcvSnmpManagerTrapsUdpPort OBJECT-TYPE
        SYNTAX  INTEGER (0..65535)
        ACCESS  read-write
        STATUS  mandatory
        DESCRIPTION
                ""
        ::= { dcvSnmpManagerEntry 5 }


    dcvRemoteConfTable OBJECT-TYPE
        SYNTAX  SEQUENCE OF DcvRemoteConfEntry
        ACCESS  not-accessible
        STATUS  mandatory
        DESCRIPTION
                ""
        ::= { dcvSnmp 3 }


    dcvRemoteConfEntry OBJECT-TYPE
        SYNTAX  DcvRemoteConfEntry
        ACCESS  not-accessible
        STATUS  mandatory
        DESCRIPTION
                "An entry of dcvRemoteConfTable."
        INDEX   { dcvRemoteConfName }
        ::= { dcvRemoteConfTable 1 }


        DcvRemoteConfEntry ::=
                SEQUENCE {
                    dcvRemoteConfName
                        DisplayString,
                    dcvRemoteConfStatus
                        INTEGER,
                    dcvRemoteConfWanAddress
                        OCTET STRING
                }


    dcvRemoteConfName OBJECT-TYPE
        SYNTAX  DisplayString (SIZE(1..12))
        ACCESS  read-only
        STATUS  mandatory
        DESCRIPTION
                ""
        ::= { dcvRemoteConfEntry 1 }


    dcvRemoteConfStatus OBJECT-TYPE
        SYNTAX  INTEGER {
                valid(1),
                invalid(2)
                }
        ACCESS  read-write
        STATUS  mandatory
        DESCRIPTION
                ""
        ::= { dcvRemoteConfEntry 2 }


    dcvRemoteConfWanAddress OBJECT-TYPE
        SYNTAX  OCTET STRING (SIZE(8))
        ACCESS  read-write
        STATUS  mandatory
        DESCRIPTION
                ""
        ::= { dcvRemoteConfEntry 3 }


    dcvTftpTable OBJECT-TYPE
        SYNTAX  SEQUENCE OF DcvTftpEntry
        ACCESS  not-accessible
        STATUS  mandatory
        DESCRIPTION
                ""
        ::= { dcvIpVirtualPort 10 }


    dcvTftpEntry OBJECT-TYPE
        SYNTAX  DcvTftpEntry
        ACCESS  not-accessible
        STATUS  mandatory
        DESCRIPTION
                "An entry of dcvTftpTable."
        INDEX   { dcvTftpIpAddress }
        ::= { dcvTftpTable 1 }


        DcvTftpEntry ::=
                SEQUENCE {
                    dcvTftpIpAddress
                        IpAddress,
                    dcvTftpStatus
                        INTEGER,
                    dcvTftpName
                        DisplayString,
                    dcvTftpRetryTimer
                        INTEGER,
                    dcvTftpInactTimer
                        INTEGER
                }


    dcvTftpIpAddress OBJECT-TYPE
        SYNTAX  IpAddress
        ACCESS  read-only
        STATUS  mandatory
        DESCRIPTION
                ""
        ::= { dcvTftpEntry 1 }


    dcvTftpStatus OBJECT-TYPE
        SYNTAX  INTEGER {
                valid(1),
                invalid(2)
                }
        ACCESS  read-write
        STATUS  mandatory
        DESCRIPTION
                ""
        ::= { dcvTftpEntry 2 }


    dcvTftpName OBJECT-TYPE
        SYNTAX  DisplayString (SIZE(1..32))
        ACCESS  read-write
        STATUS  mandatory
        DESCRIPTION
                ""
        ::= { dcvTftpEntry 3 }


    dcvTftpRetryTimer OBJECT-TYPE
        SYNTAX  INTEGER (1..600)
        ACCESS  read-write
        STATUS  mandatory
        DESCRIPTION
                ""
        ::= { dcvTftpEntry 4 }


    dcvTftpInactTimer OBJECT-TYPE
        SYNTAX  INTEGER (10..3600)
        ACCESS  read-write
        STATUS  mandatory
        DESCRIPTION
                ""
        ::= { dcvTftpEntry 5 }


    dcvRemoteNetToMediaTable OBJECT-TYPE
        SYNTAX  SEQUENCE OF DcvRemoteNetToMediaEntry
        ACCESS  not-accessible
        STATUS  mandatory
        DESCRIPTION
                ""
        ::= { dcvIpVirtualPort 15 }


    dcvRemoteNetToMediaEntry OBJECT-TYPE
        SYNTAX  DcvRemoteNetToMediaEntry
        ACCESS  not-accessible
        STATUS  mandatory
        DESCRIPTION
                "An entry of dcvRemoteNetToMediaTable."
        INDEX   { dcvRemNetIpAddress }
        ::= { dcvRemoteNetToMediaTable 1 }


        DcvRemoteNetToMediaEntry ::=
                SEQUENCE {
                    dcvRemNetIpAddress
                        IpAddress,
                    dcvRemNetStatus
                        INTEGER,
                    dcvRemNetWanAddress
                        OCTET STRING,
                    dcvRemNetEncapsulation
                        INTEGER
                }


    dcvRemNetIpAddress OBJECT-TYPE
        SYNTAX  IpAddress
        ACCESS  read-only
        STATUS  mandatory
        DESCRIPTION
                ""
        ::= { dcvRemoteNetToMediaEntry 1 }


    dcvRemNetStatus OBJECT-TYPE
        SYNTAX  INTEGER {
                valid(1),
                invalid(2)
                }
        ACCESS  read-write
        STATUS  mandatory
        DESCRIPTION
                ""
        ::= { dcvRemoteNetToMediaEntry 2 }


    dcvRemNetWanAddress OBJECT-TYPE
        SYNTAX  OCTET STRING (SIZE(8))
        ACCESS  read-write
        STATUS  mandatory
        DESCRIPTION
                ""
        ::= { dcvRemoteNetToMediaEntry 3 }


    dcvRemNetEncapsulation OBJECT-TYPE
        SYNTAX  INTEGER {
                fripSimple(1),
                fripRFC(2)
                }
        ACCESS  read-write
        STATUS  mandatory
        DESCRIPTION
                ""
        ::= { dcvRemoteNetToMediaEntry 4 }


    dcvVoiceVirtualPort OBJECT IDENTIFIER ::= { dcVirtualPorts 10 }


    dcvVoiceGen OBJECT IDENTIFIER ::= { dcvVoiceVirtualPort 1 }


    dcvVoiceVirtualPortId OBJECT-TYPE
        SYNTAX  INTEGER {
                vpVoix(1),
                vpIp(2)
                }
        ACCESS  read-write
        STATUS  mandatory
        DESCRIPTION
                ""
        ::= { dcvVoiceGen 1 }


    dcvVoiceTransportTable OBJECT-TYPE
        SYNTAX  SEQUENCE OF DcvVoiceTransportEntry
        ACCESS  not-accessible
        STATUS  mandatory
        DESCRIPTION
                ""
        ::= { dcvVoiceVirtualPort 2 }


    dcvVoiceTransportEntry OBJECT-TYPE
        SYNTAX  DcvVoiceTransportEntry
        ACCESS  not-accessible
        STATUS  mandatory
        DESCRIPTION
                "An entry of dcvVoiceTransportTable."
        INDEX   { dcvVoiceTransProfileId }
        ::= { dcvVoiceTransportTable 1 }


        DcvVoiceTransportEntry ::=
                SEQUENCE {
                    dcvVoiceTransProfileId
                        INTEGER,
                    dcvVoiceTransEncapsulationMode
                        INTEGER,
                    dcvVoiceTransMaxPayLoadNumber
                        INTEGER,
                    dcvVoiceTransCompressionAlgorithm
                        INTEGER,
                    dcvVoiceTransJitterCompensation
                        INTEGER,
                    dcvVoiceTransVoicePacketsCombination
                        INTEGER,
                    dcvVoiceTransQosBc
                        INTEGER,
                    dcvVoiceTransQosBe
                        INTEGER,
                    dcvVoiceTransQosCir
                        INTEGER
                }


    dcvVoiceTransProfileId OBJECT-TYPE
        SYNTAX  INTEGER (0..1)
        ACCESS  read-write
        STATUS  mandatory
        DESCRIPTION
                ""
        ::= { dcvVoiceTransportEntry 1 }


    dcvVoiceTransEncapsulationMode OBJECT-TYPE
        SYNTAX  INTEGER {
                frf(1),
                private(2)
                }
        ACCESS  read-write
        STATUS  mandatory
        DESCRIPTION
                ""
        ::= { dcvVoiceTransportEntry 2 }


    dcvVoiceTransMaxPayLoadNumber OBJECT-TYPE
        SYNTAX  INTEGER (1..4)
        ACCESS  read-write
        STATUS  mandatory
        DESCRIPTION
                ""
        ::= { dcvVoiceTransportEntry 3 }


    dcvVoiceTransCompressionAlgorithm OBJECT-TYPE
        SYNTAX  INTEGER {
                g729(1),
                g729A(2)
                }
        ACCESS  read-write
        STATUS  mandatory
        DESCRIPTION
                ""
        ::= { dcvVoiceTransportEntry 4 }


    dcvVoiceTransJitterCompensation OBJECT-TYPE
        SYNTAX  INTEGER (1..9)
        ACCESS  read-write
        STATUS  mandatory
        DESCRIPTION
                ""
        ::= { dcvVoiceTransportEntry 5 }


    dcvVoiceTransVoicePacketsCombination OBJECT-TYPE
        SYNTAX  INTEGER (1..4)
        ACCESS  read-write
        STATUS  mandatory
        DESCRIPTION
                ""
        ::= { dcvVoiceTransportEntry 6 }


    dcvVoiceTransQosBc OBJECT-TYPE
        SYNTAX  INTEGER {
                s9600(1),
                s14400(2),
                s19200(3),
                s32000(4),
                s38400(5),
                s48000(6)
                }
        ACCESS  read-write
        STATUS  mandatory
        DESCRIPTION
                ""
        ::= { dcvVoiceTransportEntry 7 }


    dcvVoiceTransQosBe OBJECT-TYPE
        SYNTAX  INTEGER {
                s9600(1),
                s14400(2),
                s19200(3),
                s32000(4),
                s38400(5),
                s48000(6)
                }
        ACCESS  read-write
        STATUS  mandatory
        DESCRIPTION
                ""
        ::= { dcvVoiceTransportEntry 8 }


    dcvVoiceTransQosCir OBJECT-TYPE
        SYNTAX  INTEGER {
                s9600(1),
                s14400(2),
                s19200(3),
                s32000(4),
                s38400(5),
                s48000(6)
                }
        ACCESS  read-write
        STATUS  mandatory
        DESCRIPTION
                ""
        ::= { dcvVoiceTransportEntry 9 }


    dcvVoiceSuscriberTable OBJECT-TYPE
        SYNTAX  SEQUENCE OF DcvVoiceSuscriberEntry
        ACCESS  not-accessible
        STATUS  mandatory
        DESCRIPTION
                ""
        ::= { dcvVoiceVirtualPort 3 }


    dcvVoiceSuscriberEntry OBJECT-TYPE
        SYNTAX  DcvVoiceSuscriberEntry
        ACCESS  not-accessible
        STATUS  mandatory
        DESCRIPTION
                "An entry of dcvVoiceSuscriberTable."
        INDEX   { dcvVoiceSuscrOrderNumber,
                  dcvVoiceSuscrNumber }
        ::= { dcvVoiceSuscriberTable 1 }


        DcvVoiceSuscriberEntry ::=
                SEQUENCE {
                    dcvVoiceSuscrOrderNumber
                        INTEGER,
                    dcvVoiceSuscrNumber
                        DisplayString,
                    dcvVoiceSuscrStatus
                        INTEGER,
                    dcvVoiceSuscrTransportNetwork
                        INTEGER,
                    dcvVoiceSuscrTransportNetworkAddress
                        OCTET STRING,
                    dcvVoiceSuscrTransportProfileId
                        INTEGER,
                    dcvVoiceSuscrRemovedDigitNumber
                        INTEGER,
                    dcvVoiceSuscrInsPrefix
                        DisplayString,
                    dcvVoiceSuscrInsSuffix
                        DisplayString
                }


    dcvVoiceSuscrOrderNumber OBJECT-TYPE
        SYNTAX  INTEGER (0..9)
        ACCESS  read-only
        STATUS  mandatory
        DESCRIPTION
                ""
        ::= { dcvVoiceSuscriberEntry 1 }


    dcvVoiceSuscrNumber OBJECT-TYPE
        SYNTAX  DisplayString (SIZE(1..21))
        ACCESS  read-only
        STATUS  mandatory
        DESCRIPTION
                ""
        ::= { dcvVoiceSuscriberEntry 2 }


    dcvVoiceSuscrStatus OBJECT-TYPE
        SYNTAX  INTEGER {
                valid(1),
                invalid(2)
                }
        ACCESS  read-write
        STATUS  mandatory
        DESCRIPTION
                ""
        ::= { dcvVoiceSuscriberEntry 3 }


    dcvVoiceSuscrTransportNetwork OBJECT-TYPE
        SYNTAX  INTEGER {
                fr(1),
                other(2)
                }
        ACCESS  read-only
        STATUS  mandatory
        DESCRIPTION
                ""
        ::= { dcvVoiceSuscriberEntry 4 }


    dcvVoiceSuscrTransportNetworkAddress OBJECT-TYPE
        SYNTAX  OCTET STRING (SIZE(8))
        ACCESS  read-write
        STATUS  mandatory
        DESCRIPTION
                ""
        ::= { dcvVoiceSuscriberEntry 5 }


    dcvVoiceSuscrTransportProfileId OBJECT-TYPE
        SYNTAX  INTEGER (0..1)
        ACCESS  read-write
        STATUS  mandatory
        DESCRIPTION
                ""
        ::= { dcvVoiceSuscriberEntry 6 }


    dcvVoiceSuscrRemovedDigitNumber OBJECT-TYPE
        SYNTAX  INTEGER (0..21)
        ACCESS  read-write
        STATUS  mandatory
        DESCRIPTION
                ""
        ::= { dcvVoiceSuscriberEntry 7 }


    dcvVoiceSuscrInsPrefix OBJECT-TYPE
        SYNTAX  DisplayString (SIZE(1..21))
        ACCESS  read-write
        STATUS  mandatory
        DESCRIPTION
                ""
        ::= { dcvVoiceSuscriberEntry 8 }


    dcvVoiceSuscrInsSuffix OBJECT-TYPE
        SYNTAX  DisplayString (SIZE(1..21))
        ACCESS  read-write
        STATUS  mandatory
        DESCRIPTION
                ""
        ::= { dcvVoiceSuscriberEntry 9 }


    dcvVoiceSwTable OBJECT-TYPE
        SYNTAX  SEQUENCE OF DcvVoiceSwEntry
        ACCESS  not-accessible
        STATUS  mandatory
        DESCRIPTION
                ""
        ::= { dcvVoiceVirtualPort 4 }


    dcvVoiceSwEntry OBJECT-TYPE
        SYNTAX  DcvVoiceSwEntry
        ACCESS  not-accessible
        STATUS  mandatory
        DESCRIPTION
                "An entry of dcvVoiceSwTable."
        INDEX   { dcvVoiceSwOrderNumber,
                  dcvVoiceSwSuscriberNumber }
        ::= { dcvVoiceSwTable 1 }


        DcvVoiceSwEntry ::=
                SEQUENCE {
                    dcvVoiceSwOrderNumber
                        INTEGER,
                    dcvVoiceSwSuscriberNumber
                        DisplayString,
                    dcvVoiceSwStatus
                        INTEGER,
                    dcvVoiceSwLogPortSetId
                        INTEGER,
                    dcvVoiceSwRemovedDigitNumber
                        INTEGER,
                    dcvVoiceSwInsPrefix
                        DisplayString,
                    dcvVoiceSwInsSuffix
                        DisplayString
                }


    dcvVoiceSwOrderNumber OBJECT-TYPE
        SYNTAX  INTEGER (0..9)
        ACCESS  read-only
        STATUS  mandatory
        DESCRIPTION
                ""
        ::= { dcvVoiceSwEntry 1 }


    dcvVoiceSwSuscriberNumber OBJECT-TYPE
        SYNTAX  DisplayString (SIZE(1..21))
        ACCESS  read-only
        STATUS  mandatory
        DESCRIPTION
                ""
        ::= { dcvVoiceSwEntry 2 }


    dcvVoiceSwStatus OBJECT-TYPE
        SYNTAX  INTEGER {
                valid(1),
                invalid(2)
                }
        ACCESS  read-write
        STATUS  mandatory
        DESCRIPTION
                ""
        ::= { dcvVoiceSwEntry 3 }


    dcvVoiceSwLogPortSetId OBJECT-TYPE
        SYNTAX  INTEGER (0..9)
        ACCESS  read-write
        STATUS  mandatory
        DESCRIPTION
                ""
        ::= { dcvVoiceSwEntry 4 }


    dcvVoiceSwRemovedDigitNumber OBJECT-TYPE
        SYNTAX  INTEGER (0..21)
        ACCESS  read-write
        STATUS  mandatory
        DESCRIPTION
                ""
        ::= { dcvVoiceSwEntry 5 }


    dcvVoiceSwInsPrefix OBJECT-TYPE
        SYNTAX  DisplayString (SIZE(1..21))
        ACCESS  read-write
        STATUS  mandatory
        DESCRIPTION
                ""
        ::= { dcvVoiceSwEntry 6 }


    dcvVoiceSwInsSuffix OBJECT-TYPE
        SYNTAX  DisplayString (SIZE(1..21))
        ACCESS  read-write
        STATUS  mandatory
        DESCRIPTION
                ""
        ::= { dcvVoiceSwEntry 7 }


    dcvDialingReceptTable OBJECT-TYPE
        SYNTAX  SEQUENCE OF DcvDialingReceptEntry
        ACCESS  not-accessible
        STATUS  mandatory
        DESCRIPTION
                ""
        ::= { dcvVoiceVirtualPort 5 }


    dcvDialingReceptEntry OBJECT-TYPE
        SYNTAX  DcvDialingReceptEntry
        ACCESS  not-accessible
        STATUS  mandatory
        DESCRIPTION
                "An entry of dcvDialingReceptTable."
        INDEX   { dcvDialRxSuscriberNumber }
        ::= { dcvDialingReceptTable 1 }


        DcvDialingReceptEntry ::=
                SEQUENCE {
                    dcvDialRxSuscriberNumber
                        DisplayString,
                    dcvDialRxStatus
                        INTEGER,
                    dcvDialRxNumberLength
                        INTEGER,
                    dcvDialRxEndOfDialingTimer
                        INTEGER
                }


    dcvDialRxSuscriberNumber OBJECT-TYPE
        SYNTAX  DisplayString (SIZE(1..21))
        ACCESS  read-only
        STATUS  mandatory
        DESCRIPTION
                ""
        ::= { dcvDialingReceptEntry 1 }


    dcvDialRxStatus OBJECT-TYPE
        SYNTAX  INTEGER {
                valid(1),
                invalid(2)
                }
        ACCESS  read-write
        STATUS  mandatory
        DESCRIPTION
                ""
        ::= { dcvDialingReceptEntry 2 }


    dcvDialRxNumberLength OBJECT-TYPE
        SYNTAX  INTEGER (0..21)
        ACCESS  read-write
        STATUS  mandatory
        DESCRIPTION
                ""
        ::= { dcvDialingReceptEntry 3 }


    dcvDialRxEndOfDialingTimer OBJECT-TYPE
        SYNTAX  INTEGER {
                yes(1),
                no(2)
                }
        ACCESS  read-write
        STATUS  mandatory
        DESCRIPTION
                ""
        ::= { dcvDialingReceptEntry 4 }


    dcvVoiceLogPort OBJECT IDENTIFIER ::= { dcvVoiceVirtualPort 10 }


    dcvVoiceLogicalPortTable OBJECT-TYPE
        SYNTAX  SEQUENCE OF DcvVoiceLogicalPortEntry
        ACCESS  not-accessible
        STATUS  mandatory
        DESCRIPTION
                ""
        ::= { dcvVoiceLogPort 1 }


    dcvVoiceLogicalPortEntry OBJECT-TYPE
        SYNTAX  DcvVoiceLogicalPortEntry
        ACCESS  not-accessible
        STATUS  mandatory
        DESCRIPTION
                "An entry of dcvVoiceLogicalPortTable."
        INDEX   { dcvVoiceLogPortId }
        ::= { dcvVoiceLogicalPortTable 1 }


        DcvVoiceLogicalPortEntry ::=
                SEQUENCE {
                    dcvVoiceLogPortId
                        INTEGER,
                    dcvVoiceLogPortStatus
                        INTEGER,
                    dcvVoiceLogPortType
                        INTEGER
                }


    dcvVoiceLogPortId OBJECT-TYPE
        SYNTAX  INTEGER (1..31)
        ACCESS  read-only
        STATUS  mandatory
        DESCRIPTION
                ""
        ::= { dcvVoiceLogicalPortEntry 1 }


    dcvVoiceLogPortStatus OBJECT-TYPE
        SYNTAX  INTEGER {
                valid(1),
                invalid(2)
                }
        ACCESS  read-write
        STATUS  mandatory
        DESCRIPTION
                ""
        ::= { dcvVoiceLogicalPortEntry 2 }


    dcvVoiceLogPortType OBJECT-TYPE
        SYNTAX  INTEGER {
                tsPCMPermanent(1),
                tsPCMSwitched(2)
                }
        ACCESS  read-write
        STATUS  mandatory
        DESCRIPTION
                ""
        ::= { dcvVoiceLogicalPortEntry 3 }


    dcvProfileTone OBJECT IDENTIFIER ::= { dcvVoiceLogPort 5 }


    dcvToneGenTable OBJECT-TYPE
        SYNTAX  SEQUENCE OF DcvToneGenEntry
        ACCESS  not-accessible
        STATUS  mandatory
        DESCRIPTION
                ""
        ::= { dcvProfileTone 1 }


    dcvToneGenEntry OBJECT-TYPE
        SYNTAX  DcvToneGenEntry
        ACCESS  not-accessible
        STATUS  mandatory
        DESCRIPTION
                "An entry of dcvToneGenTable."
        INDEX   { dcvToneGenProfileId }
        ::= { dcvToneGenTable 1 }


        DcvToneGenEntry ::=
                SEQUENCE {
                    dcvToneGenProfileId
                        INTEGER,
                    dcvToneGenLevel
                        INTEGER
                }


    dcvToneGenProfileId OBJECT-TYPE
        SYNTAX  INTEGER (0..0)
        ACCESS  read-only
        STATUS  mandatory
        DESCRIPTION
                ""
        ::= { dcvToneGenEntry 1 }


    dcvToneGenLevel OBJECT-TYPE
        SYNTAX  INTEGER (0..60)
        ACCESS  read-write
        STATUS  mandatory
        DESCRIPTION
                ""
        ::= { dcvToneGenEntry 2 }


    dcvToneTable OBJECT-TYPE
        SYNTAX  SEQUENCE OF DcvToneEntry
        ACCESS  not-accessible
        STATUS  mandatory
        DESCRIPTION
                ""
        ::= { dcvProfileTone 2 }


    dcvToneEntry OBJECT-TYPE
        SYNTAX  DcvToneEntry
        ACCESS  not-accessible
        STATUS  mandatory
        DESCRIPTION
                "An entry of dcvToneTable."
        INDEX   { dcvToneProfileId,
                  dcvToneType }
        ::= { dcvToneTable 1 }


        DcvToneEntry ::=
                SEQUENCE {
                    dcvToneProfileId
                        INTEGER,
                    dcvToneType
                        INTEGER,
                    dcvToneEnable
                        INTEGER,
                    dcvToneFreq1
                        INTEGER,
                    dcvToneDuration1
                        INTEGER,
                    dcvToneFreq2
                        INTEGER,
                    dcvToneDuration2
                        INTEGER
                }


    dcvToneProfileId OBJECT-TYPE
        SYNTAX  INTEGER (0..0)
        ACCESS  read-only
        STATUS  mandatory
        DESCRIPTION
                ""
        ::= { dcvToneEntry 1 }


    dcvToneType OBJECT-TYPE
        SYNTAX  INTEGER {
                dialTone(1),
                trouble(2),
                congestion(3),
                busy(4),
                callBack(5)
                }
        ACCESS  read-only
        STATUS  mandatory
        DESCRIPTION
                ""
        ::= { dcvToneEntry 2 }


    dcvToneEnable OBJECT-TYPE
        SYNTAX  INTEGER {
                no(1),
                yes(2)
                }
        ACCESS  read-write
        STATUS  mandatory
        DESCRIPTION
                ""
        ::= { dcvToneEntry 3 }


    dcvToneFreq1 OBJECT-TYPE
        SYNTAX  INTEGER (0..255)
        ACCESS  read-write
        STATUS  mandatory
        DESCRIPTION
                ""
        ::= { dcvToneEntry 4 }


    dcvToneDuration1 OBJECT-TYPE
        SYNTAX  INTEGER (0..500)
        ACCESS  read-write
        STATUS  mandatory
        DESCRIPTION
                ""
        ::= { dcvToneEntry 5 }


    dcvToneFreq2 OBJECT-TYPE
        SYNTAX  INTEGER (0..255)
        ACCESS  read-write
        STATUS  mandatory
        DESCRIPTION
                ""
        ::= { dcvToneEntry 6 }


    dcvToneDuration2 OBJECT-TYPE
        SYNTAX  INTEGER (0..500)
        ACCESS  read-write
        STATUS  mandatory
        DESCRIPTION
                ""
        ::= { dcvToneEntry 7 }


    dcvVoiceLogicalPortTSPCM OBJECT IDENTIFIER ::= { dcvVoiceLogPort 10 }


    dcvTSPCMPerm OBJECT IDENTIFIER ::= { dcvVoiceLogicalPortTSPCM 1 }


    dcvTSPCMPermTable OBJECT-TYPE
        SYNTAX  SEQUENCE OF DcvTSPCMPermEntry
        ACCESS  not-accessible
        STATUS  mandatory
        DESCRIPTION
                ""
        ::= { dcvTSPCMPerm 1 }


    dcvTSPCMPermEntry OBJECT-TYPE
        SYNTAX  DcvTSPCMPermEntry
        ACCESS  not-accessible
        STATUS  mandatory
        DESCRIPTION
                "An entry of dcvTSPCMPermTable."
        INDEX   { dcvTSPCMPermLpId }
        ::= { dcvTSPCMPermTable 1 }


        DcvTSPCMPermEntry ::=
                SEQUENCE {
                    dcvTSPCMPermLpId
                        INTEGER,
                    dcvTSPCMPermCommunicationMode
                        INTEGER,
                    dcvTSPCMPermRemoteNumber
                        DisplayString,
                    dcvTSPCMPermConfigId
                        INTEGER,
                    dcvTSPCMPermChannIfId
                        INTEGER
                }


    dcvTSPCMPermLpId OBJECT-TYPE
        SYNTAX  INTEGER (1..31)
        ACCESS  read-only
        STATUS  mandatory
        DESCRIPTION
                ""
        ::= { dcvTSPCMPermEntry 1 }


    dcvTSPCMPermCommunicationMode OBJECT-TYPE
        SYNTAX  INTEGER {
                dte(1),
                dce(2)
                }
        ACCESS  read-write
        STATUS  mandatory
        DESCRIPTION
                ""
        ::= { dcvTSPCMPermEntry 2 }


    dcvTSPCMPermRemoteNumber OBJECT-TYPE
        SYNTAX  DisplayString (SIZE(1..21))
        ACCESS  read-write
        STATUS  mandatory
        DESCRIPTION
                ""
        ::= { dcvTSPCMPermEntry 3 }


    dcvTSPCMPermConfigId OBJECT-TYPE
        SYNTAX  INTEGER (0..0)
        ACCESS  read-only
        STATUS  mandatory
        DESCRIPTION
                ""
        ::= { dcvTSPCMPermEntry 4 }


    dcvTSPCMPermChannIfId OBJECT-TYPE
        SYNTAX  INTEGER (1..31)
        ACCESS  read-write
        STATUS  mandatory
        DESCRIPTION
                ""
        ::= { dcvTSPCMPermEntry 5 }


    dcvTSPCMSw OBJECT IDENTIFIER ::= { dcvVoiceLogicalPortTSPCM 2 }


    dcvTSPCMSwTable OBJECT-TYPE
        SYNTAX  SEQUENCE OF DcvTSPCMSwEntry
        ACCESS  not-accessible
        STATUS  mandatory
        DESCRIPTION
                ""
        ::= { dcvTSPCMSw 1 }


    dcvTSPCMSwEntry OBJECT-TYPE
        SYNTAX  DcvTSPCMSwEntry
        ACCESS  not-accessible
        STATUS  mandatory
        DESCRIPTION
                "An entry of dcvTSPCMSwTable."
        INDEX   { dcvTSPCMSwLpId }
        ::= { dcvTSPCMSwTable 1 }


        DcvTSPCMSwEntry ::=
                SEQUENCE {
                    dcvTSPCMSwLpId
                        INTEGER,
                    dcvTSPCMSwLogPortSetId
                        INTEGER,
                    dcvTSPCMSwCallType
                        INTEGER,
                    dcvTSPCMSwRemoteNumber
                        DisplayString,
                    dcvTSPCMSwConfigId
                        INTEGER,
                    dcvTSPCMSwChannIfId
                        INTEGER
                }


    dcvTSPCMSwLpId OBJECT-TYPE
        SYNTAX  INTEGER (1..31)
        ACCESS  read-only
        STATUS  mandatory
        DESCRIPTION
                ""
        ::= { dcvTSPCMSwEntry 1 }


    dcvTSPCMSwLogPortSetId OBJECT-TYPE
        SYNTAX  INTEGER (0..9)
        ACCESS  read-write
        STATUS  mandatory
        DESCRIPTION
                ""
        ::= { dcvTSPCMSwEntry 2 }


    dcvTSPCMSwCallType OBJECT-TYPE
        SYNTAX  INTEGER {
                incoming(1),
                outgoing(2),
                mixed(3)
                }
        ACCESS  read-write
        STATUS  mandatory
        DESCRIPTION
                ""
        ::= { dcvTSPCMSwEntry 3 }


    dcvTSPCMSwRemoteNumber OBJECT-TYPE
        SYNTAX  DisplayString (SIZE(1..21))
        ACCESS  read-write
        STATUS  mandatory
        DESCRIPTION
                ""
        ::= { dcvTSPCMSwEntry 4 }


    dcvTSPCMSwConfigId OBJECT-TYPE
        SYNTAX  INTEGER (0..0)
        ACCESS  read-only
        STATUS  mandatory
        DESCRIPTION
                ""
        ::= { dcvTSPCMSwEntry 5 }


    dcvTSPCMSwChannIfId OBJECT-TYPE
        SYNTAX  INTEGER (1..31)
        ACCESS  read-write
        STATUS  mandatory
        DESCRIPTION
                ""
        ::= { dcvTSPCMSwEntry 6 }


    dcvCASConfigTable OBJECT-TYPE
        SYNTAX  SEQUENCE OF DcvCASConfigEntry
        ACCESS  not-accessible
        STATUS  mandatory
        DESCRIPTION
                ""
        ::= { dcvVoiceLogicalPortTSPCM 5 }


    dcvCASConfigEntry OBJECT-TYPE
        SYNTAX  DcvCASConfigEntry
        ACCESS  not-accessible
        STATUS  mandatory
        DESCRIPTION
                "An entry of dcvCASConfigTable."
        INDEX   { dcvCASConfId }
        ::= { dcvCASConfigTable 1 }


        DcvCASConfigEntry ::=
                SEQUENCE {
                    dcvCASConfId
                        INTEGER,
                    dcvCASConfSignallingTransport
                        INTEGER,
                    dcvCASConfCallSignalling
                        INTEGER,
                    dcvCASConfDialingMode
                        INTEGER,
                    dcvCASConfDialingTimeOut
                        INTEGER,
                    dcvCASConfSigChannelDiscTimeOut
                        INTEGER,
                    dcvCASConfTimeBetweenSuccOutCall
                        INTEGER,
                    dcvCASConfLineInterfacePolarity
                        INTEGER,
                    dcvCASConfMinLineSeizureAckTime
                        INTEGER,
                    dcvCASConfMaxLineSeizureAckTime
                        INTEGER,
                    dcvCASConfLineSeizureAckTime
                        INTEGER,
                    dcvCASConfClearToIncCallTime
                        INTEGER,
                    dcvCASConfSeizureAckPulseDuration
                        INTEGER,
                    dcvCASConfMinSeizureAckPulseDuration
                        INTEGER,
                    dcvCASConfDialingFormat
                        INTEGER,
                    dcvCASConfInterdigitTime
                        INTEGER,
                    dcvCASConfPauseTime
                        INTEGER,
                    dcvCASConfDtmfDigitTime
                        INTEGER,
                    dcvCASConfDtmfDigitLevel
                        INTEGER,
                    dcvCASConfDelayBeforeDialing
                        INTEGER,
                    dcvCASConfDigitReceptionTimeOut
                        INTEGER,
                    dcvCASConfEndOfDialingTimer
                        INTEGER,
                    dcvCASConfToneProfile
                        INTEGER,
                    dcvCASConfIdleState
                        INTEGER,
                    dcvCASConfAlarmState
                        INTEGER
                }


    dcvCASConfId OBJECT-TYPE
        SYNTAX  INTEGER (0..0)
        ACCESS  read-only
        STATUS  mandatory
        DESCRIPTION
                ""
        ::= { dcvCASConfigEntry 1 }


    dcvCASConfSignallingTransport OBJECT-TYPE
        SYNTAX  INTEGER {
                none(1),
                a(2),
                ab(3),
                abcd(4)
                }
        ACCESS  read-write
        STATUS  mandatory
        DESCRIPTION
                ""
        ::= { dcvCASConfigEntry 2 }


    dcvCASConfCallSignalling OBJECT-TYPE
        SYNTAX  INTEGER {
                nColisee(1),
                uColisee(2),
                simm(3),
                sDelay(4),
                swink(5),
                noResp(6)
                }
        ACCESS  read-write
        STATUS  mandatory
        DESCRIPTION
                ""
        ::= { dcvCASConfigEntry 3 }


    dcvCASConfDialingMode OBJECT-TYPE
        SYNTAX  INTEGER {
                dec(1),
                dtmf(2)
                }
        ACCESS  read-write
        STATUS  mandatory
        DESCRIPTION
                ""
        ::= { dcvCASConfigEntry 4 }


    dcvCASConfDialingTimeOut OBJECT-TYPE
        SYNTAX  INTEGER (1..60)
        ACCESS  read-write
        STATUS  mandatory
        DESCRIPTION
                ""
        ::= { dcvCASConfigEntry 5 }


    dcvCASConfSigChannelDiscTimeOut OBJECT-TYPE
        SYNTAX  INTEGER (1..60)
        ACCESS  read-write
        STATUS  mandatory
        DESCRIPTION
                ""
        ::= { dcvCASConfigEntry 6 }


    dcvCASConfTimeBetweenSuccOutCall OBJECT-TYPE
        SYNTAX  INTEGER (1..60)
        ACCESS  read-write
        STATUS  mandatory
        DESCRIPTION
                ""
        ::= { dcvCASConfigEntry 7 }


    dcvCASConfLineInterfacePolarity OBJECT-TYPE
        SYNTAX  INTEGER {
                normal(1),
                inverted(2)
                }
        ACCESS  read-write
        STATUS  mandatory
        DESCRIPTION
                ""
        ::= { dcvCASConfigEntry 8 }


    dcvCASConfMinLineSeizureAckTime OBJECT-TYPE
        SYNTAX  INTEGER (0..50)
        ACCESS  read-write
        STATUS  mandatory
        DESCRIPTION
                ""
        ::= { dcvCASConfigEntry 9 }


    dcvCASConfMaxLineSeizureAckTime OBJECT-TYPE
        SYNTAX  INTEGER (1..50)
        ACCESS  read-write
        STATUS  mandatory
        DESCRIPTION
                ""
        ::= { dcvCASConfigEntry 10 }


    dcvCASConfLineSeizureAckTime OBJECT-TYPE
        SYNTAX  INTEGER (1..50)
        ACCESS  read-write
        STATUS  mandatory
        DESCRIPTION
                ""
        ::= { dcvCASConfigEntry 11 }


    dcvCASConfClearToIncCallTime OBJECT-TYPE
        SYNTAX  INTEGER (3..50)
        ACCESS  read-write
        STATUS  mandatory
        DESCRIPTION
                ""
        ::= { dcvCASConfigEntry 12 }


    dcvCASConfSeizureAckPulseDuration OBJECT-TYPE
        SYNTAX  INTEGER (1..100)
        ACCESS  read-write
        STATUS  mandatory
        DESCRIPTION
                ""
        ::= { dcvCASConfigEntry 13 }


    dcvCASConfMinSeizureAckPulseDuration OBJECT-TYPE
        SYNTAX  INTEGER (1..100)
        ACCESS  read-write
        STATUS  mandatory
        DESCRIPTION
                ""
        ::= { dcvCASConfigEntry 14 }


    dcvCASConfDialingFormat OBJECT-TYPE
        SYNTAX  INTEGER {
                ds1(1),
                ds2(2)
                }
        ACCESS  read-write
        STATUS  mandatory
        DESCRIPTION
                ""
        ::= { dcvCASConfigEntry 15 }


    dcvCASConfInterdigitTime OBJECT-TYPE
        SYNTAX  INTEGER (1..100)
        ACCESS  read-write
        STATUS  mandatory
        DESCRIPTION
                ""
        ::= { dcvCASConfigEntry 16 }


    dcvCASConfPauseTime OBJECT-TYPE
        SYNTAX  INTEGER (1..100)
        ACCESS  read-write
        STATUS  mandatory
        DESCRIPTION
                ""
        ::= { dcvCASConfigEntry 17 }


    dcvCASConfDtmfDigitTime OBJECT-TYPE
        SYNTAX  INTEGER (2..10)
        ACCESS  read-write
        STATUS  mandatory
        DESCRIPTION
                ""
        ::= { dcvCASConfigEntry 18 }


    dcvCASConfDtmfDigitLevel OBJECT-TYPE
        SYNTAX  INTEGER (0..40)
        ACCESS  read-write
        STATUS  mandatory
        DESCRIPTION
                ""
        ::= { dcvCASConfigEntry 19 }


    dcvCASConfDelayBeforeDialing OBJECT-TYPE
        SYNTAX  INTEGER (1..100)
        ACCESS  read-write
        STATUS  mandatory
        DESCRIPTION
                ""
        ::= { dcvCASConfigEntry 20 }


    dcvCASConfDigitReceptionTimeOut OBJECT-TYPE
        SYNTAX  INTEGER (1..60)
        ACCESS  read-write
        STATUS  mandatory
        DESCRIPTION
                ""
        ::= { dcvCASConfigEntry 21 }


    dcvCASConfEndOfDialingTimer OBJECT-TYPE
        SYNTAX  INTEGER (2..60)
        ACCESS  read-write
        STATUS  mandatory
        DESCRIPTION
                ""
        ::= { dcvCASConfigEntry 22 }


    dcvCASConfToneProfile OBJECT-TYPE
        SYNTAX  INTEGER (0..0)
        ACCESS  read-only
        STATUS  mandatory
        DESCRIPTION
                ""
        ::= { dcvCASConfigEntry 23 }


    dcvCASConfIdleState OBJECT-TYPE
        SYNTAX  INTEGER (0..15)
        ACCESS  read-write
        STATUS  mandatory
        DESCRIPTION
                ""
        ::= { dcvCASConfigEntry 24 }


    dcvCASConfAlarmState OBJECT-TYPE
        SYNTAX  INTEGER (0..15)
        ACCESS  read-write
        STATUS  mandatory
        DESCRIPTION
                ""
        ::= { dcvCASConfigEntry 25 }


    dcvDigitalLines OBJECT IDENTIFIER ::= { dcvVoiceVirtualPort 15 }


    dcvIfPCM OBJECT IDENTIFIER ::= { dcvDigitalLines 1 }


    dcvIfPCMPhysTable OBJECT-TYPE
        SYNTAX  SEQUENCE OF DcvIfPCMPhysEntry
        ACCESS  not-accessible
        STATUS  mandatory
        DESCRIPTION
                ""
        ::= { dcvIfPCM 1 }


    dcvIfPCMPhysEntry OBJECT-TYPE
        SYNTAX  DcvIfPCMPhysEntry
        ACCESS  not-accessible
        STATUS  mandatory
        DESCRIPTION
                "An entry of dcvIfPCMPhysTable."
        INDEX   { dcvIfPCMPhysIfId }
        ::= { dcvIfPCMPhysTable 1 }


        DcvIfPCMPhysEntry ::=
                SEQUENCE {
                    dcvIfPCMPhysIfId
                        INTEGER,
                    dcvIfPCMPhysTypeId
                        INTEGER,
                    dcvIfPCMPhysPhysicalPort
                        INTEGER
                }


    dcvIfPCMPhysIfId OBJECT-TYPE
        SYNTAX  INTEGER {
                pcm1(1),
                other(2)
                }
        ACCESS  read-only
        STATUS  mandatory
        DESCRIPTION
                ""
        ::= { dcvIfPCMPhysEntry 1 }


    dcvIfPCMPhysTypeId OBJECT-TYPE
        SYNTAX  INTEGER {
                e1(1),
                t1-12(2),
                t1-24(3)
                }
        ACCESS  read-write
        STATUS  mandatory
        DESCRIPTION
                ""
        ::= { dcvIfPCMPhysEntry 2 }


    dcvIfPCMPhysPhysicalPort OBJECT-TYPE
        SYNTAX  INTEGER {
                v1(1),
                v2(2)
                }
        ACCESS  read-write
        STATUS  mandatory
        DESCRIPTION
                ""
        ::= { dcvIfPCMPhysEntry 3 }


    dcvIfPCMChannelTable OBJECT-TYPE
        SYNTAX  SEQUENCE OF DcvIfPCMChannelEntry
        ACCESS  not-accessible
        STATUS  mandatory
        DESCRIPTION
                ""
        ::= { dcvIfPCM 2 }


    dcvIfPCMChannelEntry OBJECT-TYPE
        SYNTAX  DcvIfPCMChannelEntry
        ACCESS  not-accessible
        STATUS  mandatory
        DESCRIPTION
                "An entry of dcvIfPCMChannelTable."
        INDEX   { dcvIfPCMChannelIfId }
        ::= { dcvIfPCMChannelTable 1 }


        DcvIfPCMChannelEntry ::=
                SEQUENCE {
                    dcvIfPCMChannelIfId
                        INTEGER,
                    dcvIfPCMChannelStatus
                        INTEGER,
                    dcvIfPCMChannelVoiceProfId
                        INTEGER,
                    dcvIfPCMChannelPhysIf
                        INTEGER
                }


    dcvIfPCMChannelIfId OBJECT-TYPE
        SYNTAX  INTEGER (1..31)
        ACCESS  read-only
        STATUS  mandatory
        DESCRIPTION
                ""
        ::= { dcvIfPCMChannelEntry 1 }


    dcvIfPCMChannelStatus OBJECT-TYPE
        SYNTAX  INTEGER {
                valid(1),
                invalid(2)
                }
        ACCESS  read-write
        STATUS  mandatory
        DESCRIPTION
                ""
        ::= { dcvIfPCMChannelEntry 2 }


    dcvIfPCMChannelVoiceProfId OBJECT-TYPE
        SYNTAX  INTEGER (0..9)
        ACCESS  read-write
        STATUS  mandatory
        DESCRIPTION
                ""
        ::= { dcvIfPCMChannelEntry 3 }


    dcvIfPCMChannelPhysIf OBJECT-TYPE
        SYNTAX  INTEGER {
                pcm1(1),
                other(2)
                }
        ACCESS  read-only
        STATUS  mandatory
        DESCRIPTION
                ""
        ::= { dcvIfPCMChannelEntry 4 }


    dcvVoiceProfileTable OBJECT-TYPE
        SYNTAX  SEQUENCE OF DcvVoiceProfileEntry
        ACCESS  not-accessible
        STATUS  mandatory
        DESCRIPTION
                ""
        ::= { dcvDigitalLines 5 }


    dcvVoiceProfileEntry OBJECT-TYPE
        SYNTAX  DcvVoiceProfileEntry
        ACCESS  not-accessible
        STATUS  mandatory
        DESCRIPTION
                "An entry of dcvVoiceProfileTable."
        INDEX   { dcvVoiceProfId }
        ::= { dcvVoiceProfileTable 1 }


        DcvVoiceProfileEntry ::=
                SEQUENCE {
                    dcvVoiceProfId
                        INTEGER,
                    dcvVoiceProfTransmitLevel
                        INTEGER,
                    dcvVoiceProfReceiveLevel
                        INTEGER,
                    dcvVoiceProfSilenceDetection
                        INTEGER,
                    dcvVoiceProfSilenceDetectionLevel
                        INTEGER,
                    dcvVoiceProfEchoCancellation
                        INTEGER,
                    dcvVoiceProfEchoCancellationLength
                        INTEGER,
                    dcvVoiceProfNoiseFramesPeriodicity
                        INTEGER,
                    dcvVoiceProfLoopActivation
                        INTEGER,
                    dcvVoiceProfFaxActivation
                        INTEGER,
                    dcvVoiceProfMaximumFaxSpeed
                        INTEGER,
                    dcvVoiceProfCESMode
                        INTEGER,
                    dcvVoiceProfCESModeAverageDelay
                        INTEGER
                }


    dcvVoiceProfId OBJECT-TYPE
        SYNTAX  INTEGER (0..9)
        ACCESS  read-only
        STATUS  mandatory
        DESCRIPTION
                ""
        ::= { dcvVoiceProfileEntry 1 }


    dcvVoiceProfTransmitLevel OBJECT-TYPE
        SYNTAX  INTEGER (0..24)
        ACCESS  read-write
        STATUS  mandatory
        DESCRIPTION
                ""
        ::= { dcvVoiceProfileEntry 2 }


    dcvVoiceProfReceiveLevel OBJECT-TYPE
        SYNTAX  INTEGER (0..15)
        ACCESS  read-write
        STATUS  mandatory
        DESCRIPTION
                ""
        ::= { dcvVoiceProfileEntry 3 }


    dcvVoiceProfSilenceDetection OBJECT-TYPE
        SYNTAX  INTEGER {
                no(1),
                yes(2),
                cng(3)
                }
        ACCESS  read-write
        STATUS  mandatory
        DESCRIPTION
                ""
        ::= { dcvVoiceProfileEntry 4 }


    dcvVoiceProfSilenceDetectionLevel OBJECT-TYPE
        SYNTAX  INTEGER {
                low(1),
                medium(2),
                high(3)
                }
        ACCESS  read-write
        STATUS  mandatory
        DESCRIPTION
                ""
        ::= { dcvVoiceProfileEntry 5 }


    dcvVoiceProfEchoCancellation OBJECT-TYPE
        SYNTAX  INTEGER {
                no(1),
                yes(2)
                }
        ACCESS  read-write
        STATUS  mandatory
        DESCRIPTION
                ""
        ::= { dcvVoiceProfileEntry 6 }


    dcvVoiceProfEchoCancellationLength OBJECT-TYPE
        SYNTAX  INTEGER {
                low(1),
                medium(2),
                high(3)
                }
        ACCESS  read-write
        STATUS  mandatory
        DESCRIPTION
                ""
        ::= { dcvVoiceProfileEntry 7 }


    dcvVoiceProfNoiseFramesPeriodicity OBJECT-TYPE
        SYNTAX  INTEGER (4..10)
        ACCESS  read-write
        STATUS  mandatory
        DESCRIPTION
                ""
        ::= { dcvVoiceProfileEntry 8 }


    dcvVoiceProfLoopActivation OBJECT-TYPE
        SYNTAX  INTEGER {
                no(1),
                local(2),
                remote(3)
                }
        ACCESS  read-write
        STATUS  mandatory
        DESCRIPTION
                ""
        ::= { dcvVoiceProfileEntry 9 }


    dcvVoiceProfFaxActivation OBJECT-TYPE
        SYNTAX  INTEGER {
                no(1),
                yes(2)
                }
        ACCESS  read-write
        STATUS  mandatory
        DESCRIPTION
                ""
        ::= { dcvVoiceProfileEntry 10 }


    dcvVoiceProfMaximumFaxSpeed OBJECT-TYPE
        SYNTAX  INTEGER {
                s9600(1),
                s4800(2)
                }
        ACCESS  read-write
        STATUS  mandatory
        DESCRIPTION
                ""
        ::= { dcvVoiceProfileEntry 11 }


    dcvVoiceProfCESMode OBJECT-TYPE
        SYNTAX  INTEGER {
                no(1),
                yes(2)
                }
        ACCESS  read-write
        STATUS  mandatory
        DESCRIPTION
                ""
        ::= { dcvVoiceProfileEntry 12 }


    dcvVoiceProfCESModeAverageDelay OBJECT-TYPE
        SYNTAX  INTEGER (4..15)
        ACCESS  read-write
        STATUS  mandatory
        DESCRIPTION
                ""
        ::= { dcvVoiceProfileEntry 13 }


    dcvVoicePhysicalPortTable OBJECT-TYPE
        SYNTAX  SEQUENCE OF DcvVoicePhysicalPortEntry
        ACCESS  not-accessible
        STATUS  mandatory
        DESCRIPTION
                ""
        ::= { dcvDigitalLines 10 }


    dcvVoicePhysicalPortEntry OBJECT-TYPE
        SYNTAX  DcvVoicePhysicalPortEntry
        ACCESS  not-accessible
        STATUS  mandatory
        DESCRIPTION
                "An entry of dcvVoicePhysicalPortTable."
        INDEX   { dcvVoicePhysPortId }
        ::= { dcvVoicePhysicalPortTable 1 }


        DcvVoicePhysicalPortEntry ::=
                SEQUENCE {
                    dcvVoicePhysPortId
                        INTEGER,
                    dcvVoicePhysPortConnector
                        INTEGER
                }


    dcvVoicePhysPortId OBJECT-TYPE
        SYNTAX  INTEGER {
                v1(1),
                v2(2)
                }
        ACCESS  read-only
        STATUS  mandatory
        DESCRIPTION
                ""
        ::= { dcvVoicePhysicalPortEntry 1 }


    dcvVoicePhysPortConnector OBJECT-TYPE
        SYNTAX  INTEGER {
                tdm(1),
                other(2)
                }
        ACCESS  read-only
        STATUS  mandatory
        DESCRIPTION
                ""
        ::= { dcvVoicePhysicalPortEntry 2 }



    END
