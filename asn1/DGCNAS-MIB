DGCNAS-MIB DEFINITIONS ::= BEGIN

        IMPORTS
		DisplayString FROM SNMPv2-TC
			enterprises, Counter, Gauge, TimeTicks, IpAddress
				FROM RFC1155-SMI
			OBJECT-TYPE
				FROM RFC-1212
			TRAP-TYPE
				FROM RFC-1215;
				

        -- The following are OIDs defined in the dgc-mib, 
        -- They are defined here so this module can stand alone.
        -- If you are using both the DGCNAS-MIB and the DGC-MIB
        -- you may have to remove these two lines to get them to compile.

			dataGeneral	OBJECT IDENTIFIER ::= {	enterprises 106	}

			dgEvent OBJECT IDENTIFIER ::= { dataGeneral 3 }

		-- These identifiers define the objects that are sent in a Enterprise
		-- trap generated by a NAS device.
	

			dgNasEvent OBJECT IDENTIFIER ::= { dgEvent 3 }

				--
				-- Events generated from the Event-Log (Notification) subsystem
				--

				dgNasEventLog OBJECT IDENTIFIER ::= { dgNasEvent 1 }

					dgNasEventLogSeverity OBJECT-TYPE
						SYNTAX INTEGER {
							none(0),
							debug(1),
							info(2),
							warning(3),
							error(4),
							critical(5)
							}
						ACCESS	read-only
						STATUS	mandatory
						DESCRIPTION
							"Indicates the Severity of the Event"
						::= { dgNasEventLog	1 }

							
					dgNasEventLogSource OBJECT-TYPE
						SYNTAX	OCTET STRING (SIZE (0..16))
						ACCESS	read-only
						STATUS	mandatory
						DESCRIPTION
							"Indicates the source of the Event."
						::= { dgNasEventLog	2 }


					dgNasEventLogDescription OBJECT-TYPE
						SYNTAX	OCTET STRING (SIZE (0..128))
						ACCESS	read-only
						STATUS	mandatory
						DESCRIPTION
							"Description of the event"
						::= { dgNasEventLog	3 } 
                                        
                                        dgNasEventLogSerialNumber OBJECT-TYPE
						SYNTAX	DisplayString (SIZE (0..255))
						ACCESS	read-only
						STATUS	mandatory
						DESCRIPTION
							"Indicates the serial number of the NAS device"
						::= { dgNasEventLog	4 } 
						
                                         dgNasEventLogSystemType OBJECT-TYPE
						SYNTAX	DisplayString (SIZE (0..255))
						ACCESS	read-only
						STATUS	mandatory
						DESCRIPTION
							"Indicates the system type of the NAS device"
						::= { dgNasEventLog	5 } 
		
                dgTrapNasEventLogNotification	TRAP-TYPE
			ENTERPRISE	dataGeneral  
			VARIABLES	{ dgNasEventLogSeverity, dgNasEventLogSource, 
			                          dgNasEventLogDescription, dgNasEventLogSerialNumber, dgNasEventLogSystemType }
			DESCRIPTION	"Generated for Log events that exceed the notification threshold."
			::= 4

END
