PDN-IFEXT-MIB DEFINITIONS ::= BEGIN

IMPORTS
	ifIndex
		FROM RFC1213-MIB
	Counter,IpAddress
		FROM RFC1155-SMI
	OBJECT-TYPE
		FROM RFC-1212
     	pdnIfExt
		FROM PDN-HEADER-MIB
	RowStatus
		FROM SNMPv2-TC
	;

-- ===============================================================
--
--   Extentions to the IF-MIB
--
--  Release: 1.4  03/20/2000 D.Gough
--  Release: 1.3  03/02/2000 D.Gough
--  Release: 1.2  02/10/2000 D.Gough
--  Release: 1.1  10/12/99 F. Mota
--  Release: 1.0  05/26/99 (Initial Release) J.Strain
--
--  Last Updated: 03/20/2000 by D.Gough
--		  Updated pdnIfTable (interface configuration
--		  table)
--  Last Updated: 03/02/2000 by D.Gough
--	          Updated pdnAddressConfigIfTable
--		  and added pdnIfExtRouterID
--  Last Updated: 02/10/2000 by D.Gough
--		  Added pdnAddressConfigifTable
--  Last Updated: 10/12/99 by F. Mota (fmota@eng.paradyne.com)
--                (Added object pdnIfExtTotalUASs)
--
--
--	This MIB is intended to AUGMENT the ifEntry Table like ifTestEntry
--	and ifXEntry does.
--

pdnIfExtConfig OBJECT IDENTIFIER ::= { pdnIfExt  1 }
pdnIfExtTestConfig OBJECT IDENTIFIER   ::= { pdnIfExt  2 }

pdnIfExtTable OBJECT-TYPE
    SYNTAX  SEQUENCE OF PdnIfExtEntry
    ACCESS  not-accessible
    STATUS  mandatory
    DESCRIPTION
           "The Paradyne IF-MIB Table Augment."
    ::= { pdnIfExtConfig 1   }

pdnIfExtEntry OBJECT-TYPE
    SYNTAX  PdnIfExtEntry
    ACCESS  not-accessible
    STATUS  mandatory
    DESCRIPTION
           "An entry in the Paradyne If-MIB Interface Config Table."
    INDEX   { pdnIfExtIndex }
    ::= { pdnIfExtTable  1 }

PdnIfExtEntry ::=
    SEQUENCE {
    pdnIfExtIndex
        INTEGER,

    pdnIfExtInOctetRollovers
        Counter,

    pdnIfExtOutOctetRollovers
        Counter,

    pdnIfExtTotalUASs
        Counter
    }

pdnIfExtIndex OBJECT-TYPE
    SYNTAX  INTEGER
    ACCESS  read-only
    STATUS  mandatory
    DESCRIPTION
           "The index value which uniquely identifies the
            interface for which this entry contains information
            on interface tests.  The interface identified by a
            particular value of this index is the same interface
            as identified by the same value of ifIndex from the
            Interfaces table of MIB II (RFC 1213)."
    ::= { pdnIfExtEntry 1 }

pdnIfExtInOctetRollovers OBJECT-TYPE
    SYNTAX 	Counter
    ACCESS  read-only
    STATUS 	mandatory
    DESCRIPTION
			"The number of times that the associated instance of the ifInOctets
			 object has overflowed or incremented from the value 2^^32-1 to zero."
    ::= { pdnIfExtEntry 2 }

pdnIfExtOutOctetRollovers OBJECT-TYPE
    SYNTAX	Counter
    ACCESS  read-only
    STATUS 	mandatory
    DESCRIPTION
			"The number of times that the associated instance of the ifOutOctets 
			object has overflowed or incremented from the value 2^^32-1 to zero."
    ::= { pdnIfExtEntry 3 }

pdnIfExtTotalUASs OBJECT-TYPE
    SYNTAX	Counter
    ACCESS	read-only
    STATUS	mandatory
    DESCRIPTION
			"The number of Unavailable Seconds encountered by this interface."
    ::= { pdnIfExtEntry 4 }
-- ------------------------------------------------------
--
--   Interface Test Group
--
--  Release: 1.0  05/26/99 (Initial Release) J.Strain
--
--  Last Updated:
--
-- This Group extends the interface table for only those interfaces
-- where test are to be performed on them.
--
-- ------------------------------------------------------
 
 
pdnIfExtTestConfigTable OBJECT-TYPE
    SYNTAX  SEQUENCE OF PdnIfExtTestConfigEntry
    ACCESS  not-accessible
    STATUS  mandatory
    DESCRIPTION
           "The Paradyne Interface Test Table"
    ::= { pdnIfExtTestConfig 1 }
 
pdnIfExtTestConfigEntry OBJECT-TYPE
    SYNTAX  PdnIfExtTestConfigEntry
    ACCESS  not-accessible
    STATUS  mandatory
    DESCRIPTION
           "An entry in the Paradyne Interface Test Config Table."
    INDEX   { pdnIfExtTestConfigIfIndex }
    ::= { pdnIfExtTestConfigTable  1 }
 
PdnIfExtTestConfigEntry ::=
    SEQUENCE {
    pdnIfExtTestConfigIfIndex
        INTEGER,
 
    pdnIfExtTestConfigNearTimer
        INTEGER,
 
    pdnIfExtTestConfigFarTimer
        INTEGER
    }
 
pdnIfExtTestConfigIfIndex OBJECT-TYPE
    SYNTAX  INTEGER
    ACCESS  read-only
    STATUS  mandatory
    DESCRIPTION
           "The index value which uniquely identifies the
            interface for which this entry contains information
            on interface tests.  The interface identified by a
            particular value of this index is the same interface
            as identified by the same value of ifIndex from the
            Interfaces table of MIB II (RFC 1213)."
    ::= { pdnIfExtTestConfigEntry 1 }
 
pdnIfExtTestConfigNearTimer OBJECT-TYPE
    SYNTAX  INTEGER
    ACCESS  read-write
    STATUS  mandatory
    DESCRIPTION
           "This object is used to specify a near end timer primarily
            used as a timeout for a local loopback. The time is in seconds."
    ::= { pdnIfExtTestConfigEntry  2 }
 
pdnIfExtTestConfigFarTimer OBJECT-TYPE
    SYNTAX  INTEGER
    ACCESS  read-write
    STATUS  mandatory
    DESCRIPTION
           "This object is used to specify a far end timer, primarily
            used as a timeout from a far end initiated loopback.
			The time is in seconds."
    ::= { pdnIfExtTestConfigEntry  3 }

-- ------------------------------------------------------
--
--   Interface Address Configuration Group
--
--  Release:   02/10/2000 (Initial Release) D.Gough 
--
--  Last Updated: 03/20/2000 D.Gough
--
-- This Group allows configuration of interface  
--
-- ------------------------------------------------------
        pdnIfTable OBJECT-TYPE
	    SYNTAX  SEQUENCE OF PdnIfEntry
	    ACCESS  not-accessible
	    STATUS  mandatory
	    DESCRIPTION
	 	    " This table that contains additional  
		      interface configuration information. "
            ::= { pdnIfExtConfig 2 }

        pdnIfEntry OBJECT-TYPE
  	    SYNTAX   PdnIfEntry
	    ACCESS   not-accessible
	    STATUS   mandatory
	    DESCRIPTION
	  	    " There will be one of these rows for each IP address
		    assigned ot an interface, and one for an unnumbered interface."
	    INDEX   { ifIndex, pdnIfAddr }
            ::= { pdnIfTable 1 }

        PdnIfEntry ::=
  	    SEQUENCE {
	     pdnIfAddr               IpAddress,
	     pdnIfAddrMask           IpAddress,
	     pdnIfStatus	           RowStatus
            }

        pdnIfAddr   OBJECT-TYPE
  	    SYNTAX	  IpAddress
	    ACCESS	  read-only
	    STATUS        mandatory
	    DESCRIPTION
	 	    " The value of this object specifies an 
		      interface IP Address. The value 0.0.0.0 means that
		      the interface is unnumbered."
            ::= { pdnIfEntry 1 }

        pdnIfAddrMask  OBJECT-TYPE
    	    SYNTAX	 IpAddress
	    ACCESS   read-write
	    STATUS   mandatory
	    DESCRIPTION
		    " The value of this object specifies the
		      subnet mask associated with the corresponding
		      interface IP Address. The value of this
		      object along with corresponding interface IP
		      address, determines a subnet address for the interface."
            ::= { pdnIfEntry 2 }

        pdnIfStatus  OBJECT-TYPE
	    SYNTAX	RowStatus
	    ACCESS	read-write
	    STATUS 	mandatory
	    DESCRIPTION
		    " This object is used to create a new row or
		      delete an existing row in this table."
            ::= { pdnIfEntry 3 }

END
