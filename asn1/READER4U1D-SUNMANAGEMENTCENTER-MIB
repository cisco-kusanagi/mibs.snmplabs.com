-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
READER4U1D-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
hardware        OBJECT IDENTIFIER ::= { modules 1 }
--
--
config          OBJECT IDENTIFIER ::= { hardware 1 }
reader4u        OBJECT IDENTIFIER ::= { config 1 }
reader4udt      OBJECT IDENTIFIER ::= { config 2 }
reader4uwg      OBJECT IDENTIFIER ::= { config 3 }
reader4u1P      OBJECT IDENTIFIER ::= { config 4 }
reader4u1D      OBJECT IDENTIFIER ::= { config 5 }
reader4unt      OBJECT IDENTIFIER ::= { config 6 }
readerSerengeti OBJECT IDENTIFIER ::= { config 7 }
reader4uvh      OBJECT IDENTIFIER ::= { config 8 }
readerECP       OBJECT IDENTIFIER ::= { config 9 }
readerELP       OBJECT IDENTIFIER ::= { config 10 }


sunSmTreeProp	OBJECT IDENTIFIER ::= { networkEntry 1 }
sunSmNodeName	OBJECT IDENTIFIER ::= { networkEntry 2 }
entry-no	OBJECT IDENTIFIER ::= { networkEntry 3 }
interface-name	OBJECT IDENTIFIER ::= { networkEntry 4 }
scard-num	OBJECT IDENTIFIER ::= { networkEntry 5 }
symbolic-name	OBJECT IDENTIFIER ::= { networkEntry 6 }
inet	OBJECT IDENTIFIER ::= { networkEntry 7 }
ether	OBJECT IDENTIFIER ::= { networkEntry 8 }
library-availability	OBJECT IDENTIFIER ::= { system 1 }
total-model-changes	OBJECT IDENTIFIER ::= { system 2 }
total-config-changes	OBJECT IDENTIFIER ::= { system 3 }
sunSmTreeProp	OBJECT IDENTIFIER ::= { system 4 }
sunSmNodeName	OBJECT IDENTIFIER ::= { system 5 }
hostname	OBJECT IDENTIFIER ::= { system 6 }
serial-number	OBJECT IDENTIFIER ::= { system 7 }
os	OBJECT IDENTIFIER ::= { system 8 }
os-version	OBJECT IDENTIFIER ::= { system 9 }
system-clock-frequency	OBJECT IDENTIFIER ::= { system 10 }
architecture	OBJECT IDENTIFIER ::= { system 11 }
machine	OBJECT IDENTIFIER ::= { system 12 }
platform	OBJECT IDENTIFIER ::= { system 13 }
timestamp	OBJECT IDENTIFIER ::= { system 14 }
total-disks	OBJECT IDENTIFIER ::= { system 15 }
total-memory	OBJECT IDENTIFIER ::= { system 16 }
total-processors	OBJECT IDENTIFIER ::= { system 17 }
total-tape-devices	OBJECT IDENTIFIER ::= { system 18 }
cu	OBJECT IDENTIFIER ::= { cpu-unit 1 }
sunSmTreeProp	OBJECT IDENTIFIER ::= { cpu-unitEntry 1 }
sunSmNodeName	OBJECT IDENTIFIER ::= { cpu-unitEntry 2 }
entry-no	OBJECT IDENTIFIER ::= { cpu-unitEntry 3 }
unit	OBJECT IDENTIFIER ::= { cpu-unitEntry 4 }
processor-id	OBJECT IDENTIFIER ::= { cpu-unitEntry 5 }
post-status	OBJECT IDENTIFIER ::= { cpu-unitEntry 6 }
status	OBJECT IDENTIFIER ::= { cpu-unitEntry 7 }
clock-frequency	OBJECT IDENTIFIER ::= { cpu-unitEntry 8 }
ecache-size	OBJECT IDENTIFIER ::= { cpu-unitEntry 9 }
dcache-size	OBJECT IDENTIFIER ::= { cpu-unitEntry 10 }
icache-size	OBJECT IDENTIFIER ::= { cpu-unitEntry 11 }
cpu-type	OBJECT IDENTIFIER ::= { cpu-unitEntry 12 }
model	OBJECT IDENTIFIER ::= { cpu-unitEntry 13 }
fru	OBJECT IDENTIFIER ::= { cpu-unitEntry 14 }
ia	OBJECT IDENTIFIER ::= { io-adaptor 1 }
sunSmTreeProp	OBJECT IDENTIFIER ::= { io-deviceEntry 1 }
sunSmNodeName	OBJECT IDENTIFIER ::= { io-deviceEntry 2 }
entry-no	OBJECT IDENTIFIER ::= { io-deviceEntry 3 }
scard-num	OBJECT IDENTIFIER ::= { io-deviceEntry 4 }
device-type	OBJECT IDENTIFIER ::= { io-deviceEntry 5 }
id	OBJECT IDENTIFIER ::= { io-device 1 }
ic	OBJECT IDENTIFIER ::= { io-controller 1 }
sunSmTreeProp	OBJECT IDENTIFIER ::= { tapeEntry 1 }
sunSmNodeName	OBJECT IDENTIFIER ::= { tapeEntry 2 }
entry-no	OBJECT IDENTIFIER ::= { tapeEntry 3 }
tape-name	OBJECT IDENTIFIER ::= { tapeEntry 4 }
scard-num	OBJECT IDENTIFIER ::= { tapeEntry 5 }
status	OBJECT IDENTIFIER ::= { tapeEntry 6 }
tape-error	OBJECT IDENTIFIER ::= { tapeEntry 7 }
model	OBJECT IDENTIFIER ::= { tapeEntry 8 }
target	OBJECT IDENTIFIER ::= { tapeEntry 9 }
fru	OBJECT IDENTIFIER ::= { tapeEntry 10 }
sunSmTreeProp	OBJECT IDENTIFIER ::= { io-controllerEntry 1 }
sunSmNodeName	OBJECT IDENTIFIER ::= { io-controllerEntry 2 }
entry-no	OBJECT IDENTIFIER ::= { io-controllerEntry 3 }
io-controller-num	OBJECT IDENTIFIER ::= { io-controllerEntry 4 }
post-status	OBJECT IDENTIFIER ::= { io-controllerEntry 5 }
upa-portid	OBJECT IDENTIFIER ::= { io-controllerEntry 6 }
clock-frequency	OBJECT IDENTIFIER ::= { io-controllerEntry 7 }
model	OBJECT IDENTIFIER ::= { io-controllerEntry 8 }
version-no	OBJECT IDENTIFIER ::= { io-controllerEntry 9 }
mg	OBJECT IDENTIFIER ::= { mem-group 1 }
sunSmTreeProp	OBJECT IDENTIFIER ::= { system-boardEntry 1 }
sunSmNodeName	OBJECT IDENTIFIER ::= { system-boardEntry 2 }
entry-no	OBJECT IDENTIFIER ::= { system-boardEntry 3 }
board-num	OBJECT IDENTIFIER ::= { system-boardEntry 4 }
post-status	OBJECT IDENTIFIER ::= { system-boardEntry 5 }
memory-size	OBJECT IDENTIFIER ::= { system-boardEntry 6 }
number-cpus	OBJECT IDENTIFIER ::= { system-boardEntry 7 }
number-IO-cards	OBJECT IDENTIFIER ::= { system-boardEntry 8 }
fru	OBJECT IDENTIFIER ::= { system-boardEntry 9 }
hpu	OBJECT IDENTIFIER ::= { system-boardEntry 10 }
sunSmTreeProp	OBJECT IDENTIFIER ::= { asicEntry 1 }
sunSmNodeName	OBJECT IDENTIFIER ::= { asicEntry 2 }
entry-no	OBJECT IDENTIFIER ::= { asicEntry 3 }
board-num	OBJECT IDENTIFIER ::= { asicEntry 4 }
cic0	OBJECT IDENTIFIER ::= { asicEntry 5 }
cic1	OBJECT IDENTIFIER ::= { asicEntry 6 }
cic2	OBJECT IDENTIFIER ::= { asicEntry 7 }
cic3	OBJECT IDENTIFIER ::= { asicEntry 8 }
ldpath0	OBJECT IDENTIFIER ::= { asicEntry 9 }
ldpath1	OBJECT IDENTIFIER ::= { asicEntry 10 }
pc0	OBJECT IDENTIFIER ::= { asicEntry 11 }
pc1	OBJECT IDENTIFIER ::= { asicEntry 12 }
pc2	OBJECT IDENTIFIER ::= { asicEntry 13 }
xdb0	OBJECT IDENTIFIER ::= { asicEntry 14 }
xdb1	OBJECT IDENTIFIER ::= { asicEntry 15 }
xdb2	OBJECT IDENTIFIER ::= { asicEntry 16 }
xdb3	OBJECT IDENTIFIER ::= { asicEntry 17 }
io-adaptorEntry	OBJECT IDENTIFIER ::= { ia 1 }
networkEntry	OBJECT IDENTIFIER ::= { nw 1 }
sunSmTreeProp	OBJECT IDENTIFIER ::= { diskEntry 1 }
sunSmNodeName	OBJECT IDENTIFIER ::= { diskEntry 2 }
entry-no	OBJECT IDENTIFIER ::= { diskEntry 3 }
disk-name	OBJECT IDENTIFIER ::= { diskEntry 4 }
scard-num	OBJECT IDENTIFIER ::= { diskEntry 5 }
disk-error	OBJECT IDENTIFIER ::= { diskEntry 6 }
target	OBJECT IDENTIFIER ::= { diskEntry 7 }
fru	OBJECT IDENTIFIER ::= { diskEntry 8 }
as	OBJECT IDENTIFIER ::= { asic 1 }
io-controllerEntry	OBJECT IDENTIFIER ::= { ic 1 }
asicEntry	OBJECT IDENTIFIER ::= { as 1 }
io-deviceEntry	OBJECT IDENTIFIER ::= { id 1 }
tapeEntry	OBJECT IDENTIFIER ::= { tp 1 }
dm	OBJECT IDENTIFIER ::= { dimm 1 }
cpu-unitEntry	OBJECT IDENTIFIER ::= { cu 1 }
sunSmTreeProp	OBJECT IDENTIFIER ::= { starfire-platform 1 }
sunSmNodeName	OBJECT IDENTIFIER ::= { starfire-platform 2 }
platform-name	OBJECT IDENTIFIER ::= { starfire-platform 3 }
ssp-hostname	OBJECT IDENTIFIER ::= { starfire-platform 4 }
ssp-ipaddr	OBJECT IDENTIFIER ::= { starfire-platform 5 }
sysbrd-count	OBJECT IDENTIFIER ::= { starfire-platform 6 }
sysbrd-list	OBJECT IDENTIFIER ::= { starfire-platform 7 }
tp	OBJECT IDENTIFIER ::= { tape 1 }
mem-groupEntry	OBJECT IDENTIFIER ::= { mg 1 }
sunSmTreeProp	OBJECT IDENTIFIER ::= { io-unitEntry 1 }
sunSmNodeName	OBJECT IDENTIFIER ::= { io-unitEntry 2 }
entry-no	OBJECT IDENTIFIER ::= { io-unitEntry 3 }
board-num	OBJECT IDENTIFIER ::= { io-unitEntry 4 }
device-type	OBJECT IDENTIFIER ::= { io-unitEntry 5 }
number-IO-cards	OBJECT IDENTIFIER ::= { io-unitEntry 6 }
fru	OBJECT IDENTIFIER ::= { io-unitEntry 7 }
dk	OBJECT IDENTIFIER ::= { disk 1 }
sunSmTreeProp	OBJECT IDENTIFIER ::= { mem-groupEntry 1 }
sunSmNodeName	OBJECT IDENTIFIER ::= { mem-groupEntry 2 }
entry-no	OBJECT IDENTIFIER ::= { mem-groupEntry 3 }
group-num	OBJECT IDENTIFIER ::= { mem-groupEntry 4 }
post-status	OBJECT IDENTIFIER ::= { mem-groupEntry 5 }
memory-size	OBJECT IDENTIFIER ::= { mem-groupEntry 6 }
io-unitEntry	OBJECT IDENTIFIER ::= { iu 1 }
sunSmTreeProp	OBJECT IDENTIFIER ::= { mem-unitEntry 1 }
sunSmNodeName	OBJECT IDENTIFIER ::= { mem-unitEntry 2 }
entry-no	OBJECT IDENTIFIER ::= { mem-unitEntry 3 }
board-num	OBJECT IDENTIFIER ::= { mem-unitEntry 4 }
post-status	OBJECT IDENTIFIER ::= { mem-unitEntry 5 }
memory-size	OBJECT IDENTIFIER ::= { mem-unitEntry 6 }
fru	OBJECT IDENTIFIER ::= { mem-unitEntry 7 }
system	OBJECT IDENTIFIER ::= { reader4u1D 1 }
starfire-platform	OBJECT IDENTIFIER ::= { reader4u1D 2 }
system-board	OBJECT IDENTIFIER ::= { reader4u1D 3 }
asic	OBJECT IDENTIFIER ::= { reader4u1D 4 }
cpu-unit	OBJECT IDENTIFIER ::= { reader4u1D 5 }
mem-unit	OBJECT IDENTIFIER ::= { reader4u1D 6 }
mem-group	OBJECT IDENTIFIER ::= { reader4u1D 7 }
dimm	OBJECT IDENTIFIER ::= { reader4u1D 8 }
io-unit	OBJECT IDENTIFIER ::= { reader4u1D 9 }
io-controller	OBJECT IDENTIFIER ::= { reader4u1D 10 }
io-adaptor	OBJECT IDENTIFIER ::= { reader4u1D 11 }
io-device	OBJECT IDENTIFIER ::= { reader4u1D 12 }
tape	OBJECT IDENTIFIER ::= { reader4u1D 13 }
network	OBJECT IDENTIFIER ::= { reader4u1D 14 }
disk	OBJECT IDENTIFIER ::= { reader4u1D 15 }
hardware-rules	OBJECT IDENTIFIER ::= { reader4u1D 16 }
domainRefreshString	OBJECT IDENTIFIER ::= { reader4u1D 17 }
pvlv	OBJECT IDENTIFIER ::= { reader4u1D 18 }
e10klsec	OBJECT IDENTIFIER ::= { hardware-rules 1 }
e10klsdk	OBJECT IDENTIFIER ::= { hardware-rules 2 }
e10klstp	OBJECT IDENTIFIER ::= { hardware-rules 3 }
sunSmTreeProp	OBJECT IDENTIFIER ::= { io-adaptorEntry 1 }
sunSmNodeName	OBJECT IDENTIFIER ::= { io-adaptorEntry 2 }
entry-no	OBJECT IDENTIFIER ::= { io-adaptorEntry 3 }
scard-num	OBJECT IDENTIFIER ::= { io-adaptorEntry 4 }
post-status	OBJECT IDENTIFIER ::= { io-adaptorEntry 5 }
model	OBJECT IDENTIFIER ::= { io-adaptorEntry 6 }
device-summary	OBJECT IDENTIFIER ::= { io-adaptorEntry 7 }
disk-count	OBJECT IDENTIFIER ::= { io-adaptorEntry 8 }
network-count	OBJECT IDENTIFIER ::= { io-adaptorEntry 9 }
tape-count	OBJECT IDENTIFIER ::= { io-adaptorEntry 10 }
fru	OBJECT IDENTIFIER ::= { io-adaptorEntry 11 }
system-boardEntry	OBJECT IDENTIFIER ::= { sb 1 }
sb	OBJECT IDENTIFIER ::= { system-board 1 }
reader4u1D	OBJECT IDENTIFIER ::= { config 5 }
iu	OBJECT IDENTIFIER ::= { io-unit 1 }
nw	OBJECT IDENTIFIER ::= { network 1 }
mem-unitEntry	OBJECT IDENTIFIER ::= { mu 1 }
mu	OBJECT IDENTIFIER ::= { mem-unit 1 }
diskEntry	OBJECT IDENTIFIER ::= { dk 1 }
dimmEntry	OBJECT IDENTIFIER ::= { dm 1 }
sunSmTreeProp	OBJECT IDENTIFIER ::= { dimmEntry 1 }
sunSmNodeName	OBJECT IDENTIFIER ::= { dimmEntry 2 }
entry-no	OBJECT IDENTIFIER ::= { dimmEntry 3 }
dimm-id	OBJECT IDENTIFIER ::= { dimmEntry 4 }
mem-error	OBJECT IDENTIFIER ::= { dimmEntry 5 }
memory-size	OBJECT IDENTIFIER ::= { dimmEntry 6 }
board-reference	OBJECT IDENTIFIER ::= { dimmEntry 7 }
fru	OBJECT IDENTIFIER ::= { dimmEntry 8 }

END
