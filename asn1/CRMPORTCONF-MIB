-- automatically generated by mosy 7.1 #1 (elc), do not edit!
-- crmCacTable add(99.3.30 kameishi)
-- crmCacThreshold1 accsece change(99.4.13 kameishi)

CRMPORTCONF-MIB DEFINITIONS ::= BEGIN


IMPORTS
	DisplayString
		FROM RFC1213-MIB
	OBJECT-TYPE
		FROM RFC-1212
	Counter, IpAddress
		FROM RFC1155-SMI
	mib-2, ifIndex
		FROM RFC1213-MIB
	RowStatus, TimeStamp
		FROM SNMPv2-TC;

org OBJECT IDENTIFIER ::= { iso  3 }

dod OBJECT IDENTIFIER ::= { org  6 }

internet OBJECT IDENTIFIER ::= { dod  1 }

private OBJECT IDENTIFIER ::= { internet  4 }

enterprises OBJECT IDENTIFIER ::= { private  1 }

ntt OBJECT IDENTIFIER ::= { enterprises  210 }

mibDoc OBJECT IDENTIFIER ::= { ntt  2 }

ba3000 OBJECT IDENTIFIER ::= { mibDoc  8 }

crmCommon OBJECT IDENTIFIER ::= { ba3000  1 }

-- created from crmPortConf (9605221200Z)

crmPortConf OBJECT IDENTIFIER ::= { crmCommon  9 }

crmPortConfTable OBJECT-TYPE
    SYNTAX  SEQUENCE OF CrmPortConfEntry
    ACCESS  not-accessible
    STATUS  mandatory
    DESCRIPTION
           "DUMMY"
    ::= { crmPortConf  1 }

crmPortConfEntry OBJECT-TYPE
    SYNTAX  CrmPortConfEntry
    ACCESS  not-accessible
    STATUS  mandatory
    DESCRIPTION
           "DUMMY"
    INDEX   { ifIndex }
    ::= { crmPortConfTable  1 }

CrmPortConfEntry ::=
    SEQUENCE {
        crmPortType
            INTEGER,

        crmPortMode
            INTEGER,

        crmPortConfAdminStatus
            INTEGER,

        crmPortConfOperStatus
            INTEGER,

        crmPortConfRowStatus
            INTEGER (-2147483648..2147483647)
    }

crmPortType OBJECT-TYPE
    SYNTAX  INTEGER {
    atm600(1),
    atm150(2),
    sonet150(3),
    sdh150(4),
    sdh50(5),
    atm63(6),
    hsd63(7),
    hsd63clad(8),
    atm15(9),
    hsd15(10),
    hsd15clad(11),
    hsd192(12),
    fr20(13),
    fr15(14),
    ins15(15),
    ins64(16),
    rs449(17),
    e1(25),
    t1(26)
}
    ACCESS  read-write
    STATUS  mandatory
    DESCRIPTION
           "DUMMY"
    ::= { crmPortConfEntry  1 }

crmPortMode OBJECT-TYPE
    SYNTAX  INTEGER {
    lan-mode(1),
    wan-mode(2)
}
    ACCESS  read-write
    STATUS  mandatory
    DESCRIPTION
           "DUMMY"
    DEFVAL {  1  }

    ::= { crmPortConfEntry  2 }

crmPortConfAdminStatus OBJECT-TYPE
    SYNTAX  INTEGER {
    up(1),
    down(2)
}
    ACCESS  read-write
    STATUS  mandatory
    DESCRIPTION
           "DUMMY"
    ::= { crmPortConfEntry  3 }

crmPortConfOperStatus OBJECT-TYPE
    SYNTAX  INTEGER {
    up(1),
    down(2)
}
    ACCESS  read-only
    STATUS  mandatory
    DESCRIPTION
           "DUMMY"
    ::= { crmPortConfEntry  4 }

crmPortConfRowStatus OBJECT-TYPE
    SYNTAX  INTEGER (-2147483648..2147483647)
    ACCESS  read-write
    STATUS  mandatory
    DESCRIPTION
           "DUMMY"
    ::= { crmPortConfEntry  5 }

crmPriContPatternTable OBJECT-TYPE
    SYNTAX  SEQUENCE OF CrmPriContPatternEntry
    ACCESS  not-accessible
    STATUS  mandatory
    DESCRIPTION
           "DUMMY"
    ::= { crmPortConf  2 }

crmPriContPatternEntry OBJECT-TYPE
    SYNTAX  CrmPriContPatternEntry
    ACCESS  not-accessible
    STATUS  mandatory
    DESCRIPTION
           "DUMMY"
    INDEX   { ifIndex }
    ::= { crmPriContPatternTable  1 }

CrmPriContPatternEntry ::=
    SEQUENCE {
        crmPriContPatternActnPattern
            INTEGER,

        crmPriContPatternAdminStatus
            INTEGER,

        crmPriContPatternOperStatus
            INTEGER,

        crmPriContPatternRowStatus
            INTEGER (-2147483648..2147483647)
    }

crmPriContPatternActnPattern OBJECT-TYPE
    SYNTAX  INTEGER {
    pricont-pattern1(1),
    pricont-pattern2(2),
    pricont-pattern3(3),
    pricont-pattern4(4),
    pricont-pattern5(5),
    pricont-pattern6(6),
    pricont-pattern7(7),
    pricont-pattern8(8)
}
    ACCESS  read-write
    STATUS  mandatory
    DESCRIPTION
           "DUMMY"
    ::= { crmPriContPatternEntry  1 }

crmPriContPatternAdminStatus OBJECT-TYPE
    SYNTAX  INTEGER {
    up(1),
    down(2)
}
    ACCESS  read-write
    STATUS  mandatory
    DESCRIPTION
           "DUMMY"
    ::= { crmPriContPatternEntry  2 }

crmPriContPatternOperStatus OBJECT-TYPE
    SYNTAX  INTEGER {
    up(1),
    down(2)
}
    ACCESS  read-only
    STATUS  mandatory
    DESCRIPTION
           "DUMMY"
    ::= { crmPriContPatternEntry  3 }

crmPriContPatternRowStatus OBJECT-TYPE
    SYNTAX  INTEGER (-2147483648..2147483647)
    ACCESS  read-write
    STATUS  mandatory
    DESCRIPTION
           "DUMMY"
    ::= { crmPriContPatternEntry  4 }

crmPriContBufManageTable OBJECT-TYPE
    SYNTAX  SEQUENCE OF CrmPriContBufManageEntry
    ACCESS  not-accessible
    STATUS  mandatory
    DESCRIPTION
           "DUMMY"
    ::= { crmPortConf  3 }

crmPriContBufManageEntry OBJECT-TYPE
    SYNTAX  CrmPriContBufManageEntry
    ACCESS  not-accessible
    STATUS  mandatory
    DESCRIPTION
           "DUMMY"
    INDEX   { ifIndex }
    ::= { crmPriContBufManageTable  1 }

CrmPriContBufManageEntry ::=
    SEQUENCE {
        crmPriContBufSizeTblNumber
            INTEGER,

        crmPriContBufManageAdminStatus
            INTEGER,

        crmPriContBufManageOperStatus
            INTEGER,

        crmPriContBufManageRowStatus
            INTEGER (-2147483648..2147483647)
    }

crmPriContBufSizeTblNumber OBJECT-TYPE
    SYNTAX  INTEGER
    ACCESS  read-only
    STATUS  mandatory
    DESCRIPTION
           "DUMMY"
    DEFVAL {  0  }

    ::= { crmPriContBufManageEntry  1 }

crmPriContBufManageAdminStatus OBJECT-TYPE
    SYNTAX  INTEGER {
    up(1),
    down(2)
}
    ACCESS  read-write
    STATUS  mandatory
    DESCRIPTION
           "DUMMY"
    ::= { crmPriContBufManageEntry  2 }

crmPriContBufManageOperStatus OBJECT-TYPE
    SYNTAX  INTEGER {
    up(1),
    down(2)
}
    ACCESS  read-only
    STATUS  mandatory
    DESCRIPTION
           "DUMMY"
    ::= { crmPriContBufManageEntry  3 }

crmPriContBufManageRowStatus OBJECT-TYPE
    SYNTAX  INTEGER (-2147483648..2147483647)
    ACCESS  read-write
    STATUS  mandatory
    DESCRIPTION
           "DUMMY"
    ::= { crmPriContBufManageEntry  4 }

crmPriContBufSizeTable OBJECT-TYPE
    SYNTAX  SEQUENCE OF CrmPriContBufEntry
    ACCESS  not-accessible
    STATUS  mandatory
    DESCRIPTION
           "DUMMY"
    ::= { crmPortConf  4 }

crmPriContBufEntry OBJECT-TYPE
    SYNTAX  CrmPriContBufEntry
    ACCESS  not-accessible
    STATUS  mandatory
    DESCRIPTION
           "DUMMY"
    INDEX   { ifIndex }
    ::= { crmPriContBufSizeTable  1 }

CrmPriContBufEntry ::=
    SEQUENCE {
        crmPriContIfBufSize
            INTEGER,

        crmPriContCls1BufSize
            INTEGER,

        crmPriContCls2BufSize
            INTEGER,

        crmPriContCls3BufSize
            INTEGER,

        crmPriContCls4BufSize
            INTEGER,

        crmPriContCls1ConnNumber
            INTEGER,

        crmPriContCls2ConnNumber
            INTEGER,

        crmPriContCls3ConnNumber
            INTEGER,

        crmPriContCls4ConnNumber
            INTEGER,

        crmPriContShapingBufSize
            INTEGER,

        crmPriContBufSizeRowStatus
            INTEGER (-2147483648..2147483647)
    }

crmPriContIfBufSize OBJECT-TYPE
    SYNTAX  INTEGER
    ACCESS  read-write
    STATUS  mandatory
    DESCRIPTION
           "DUMMY"
    DEFVAL {  100  }

    ::= { crmPriContBufEntry  1 }

crmPriContCls1BufSize OBJECT-TYPE
    SYNTAX  INTEGER
    ACCESS  read-write
    STATUS  mandatory
    DESCRIPTION
           "DUMMY"
    DEFVAL {  10  }

    ::= { crmPriContBufEntry  2 }

crmPriContCls2BufSize OBJECT-TYPE
    SYNTAX  INTEGER
    ACCESS  read-write
    STATUS  mandatory
    DESCRIPTION
           "DUMMY"
    DEFVAL {  20  }

    ::= { crmPriContBufEntry  3 }

crmPriContCls3BufSize OBJECT-TYPE
    SYNTAX  INTEGER
    ACCESS  read-write
    STATUS  mandatory
    DESCRIPTION
           "DUMMY"
    DEFVAL {  30  }

    ::= { crmPriContBufEntry  4 }

crmPriContCls4BufSize OBJECT-TYPE
    SYNTAX  INTEGER
    ACCESS  read-write
    STATUS  mandatory
    DESCRIPTION
           "DUMMY"
    DEFVAL {  40  }

    ::= { crmPriContBufEntry  5 }

crmPriContCls1ConnNumber OBJECT-TYPE
    SYNTAX  INTEGER
    ACCESS  read-write
    STATUS  mandatory
    DESCRIPTION
           "DUMMY"
    DEFVAL {  16  }

    ::= { crmPriContBufEntry  6 }

crmPriContCls2ConnNumber OBJECT-TYPE
    SYNTAX  INTEGER
    ACCESS  read-write
    STATUS  mandatory
    DESCRIPTION
           "DUMMY"
    DEFVAL {  16  }

    ::= { crmPriContBufEntry  7 }

crmPriContCls3ConnNumber OBJECT-TYPE
    SYNTAX  INTEGER
    ACCESS  read-write
    STATUS  mandatory
    DESCRIPTION
           "DUMMY"
    DEFVAL {  16  }

    ::= { crmPriContBufEntry  8 }

crmPriContCls4ConnNumber OBJECT-TYPE
    SYNTAX  INTEGER
    ACCESS  read-write
    STATUS  mandatory
    DESCRIPTION
           "DUMMY"
    DEFVAL {  16  }

    ::= { crmPriContBufEntry  9 }

crmPriContShapingBufSize OBJECT-TYPE
    SYNTAX  INTEGER
    ACCESS  read-write
    STATUS  mandatory
    DESCRIPTION
           "DUMMY"
    DEFVAL {  0  }

    ::= { crmPriContBufEntry  10 }

crmPriContBufSizeRowStatus OBJECT-TYPE
    SYNTAX  INTEGER (-2147483648..2147483647)
    ACCESS  read-write
    STATUS  mandatory
    DESCRIPTION
           "DUMMY"
    ::= { crmPriContBufEntry  11 }

crmPriContVpiShaperTable OBJECT-TYPE
    SYNTAX  SEQUENCE OF CrmPriContVpiShaperEntry
    ACCESS  not-accessible
    STATUS  mandatory
    DESCRIPTION
           "DUMMY"
    ::= { crmPortConf  5 }

crmPriContVpiShaperEntry OBJECT-TYPE
    SYNTAX  CrmPriContVpiShaperEntry
    ACCESS  not-accessible
    STATUS  mandatory
    DESCRIPTION
           "DUMMY"
    INDEX   { ifIndex }
    ::= { crmPriContVpiShaperTable  1 }

CrmPriContVpiShaperEntry ::=
    SEQUENCE {
        crmPriContVpiShaperAdminStatus
            INTEGER,

        crmPriContVpiShaperOperStatus
            INTEGER,

        crmPriContVpiShaperRowStatus
            INTEGER (-2147483648..2147483647)
    }

crmPriContVpiShaperAdminStatus OBJECT-TYPE
    SYNTAX  INTEGER {
    up(1),
    down(2)
}
    ACCESS  read-write
    STATUS  mandatory
    DESCRIPTION
           "DUMMY"
    ::= { crmPriContVpiShaperEntry  1 }

crmPriContVpiShaperOperStatus OBJECT-TYPE
    SYNTAX  INTEGER {
    up(1),
    down(2)
}
    ACCESS  read-only
    STATUS  mandatory
    DESCRIPTION
           "DUMMY"
    ::= { crmPriContVpiShaperEntry  2 }

crmPriContVpiShaperRowStatus OBJECT-TYPE
    SYNTAX  INTEGER (-2147483648..2147483647)
    ACCESS  read-write
    STATUS  mandatory
    DESCRIPTION
           "DUMMY"
    ::= { crmPriContVpiShaperEntry  3 }

-- add object
crmCacTable OBJECT-TYPE
    SYNTAX  SEQUENCE OF CrmPortConfEntry
    ACCESS  not-accessible
    STATUS  mandatory
    DESCRIPTION
           "DUMMY"
    ::= { crmPortConf  6 }

crmCacEntry OBJECT-TYPE
    SYNTAX  CrmCacEntry
    ACCESS  not-accessible
    STATUS  mandatory
    DESCRIPTION
           "DUMMY"
    INDEX   { ifIndex , crmCacDirection }
    ::= { crmCacTable  1 }

CrmCacEntry ::=
    SEQUENCE {
        crmCacDirection
            INTEGER,

        crmCacCurrentBand
            INTEGER (-2147483648..2147483647),

        crmCacCapacityBand
            INTEGER (-2147483648..2147483647),

        crmCacThreshold1
            INTEGER (-2147483648..2147483647),

        crmCacThreshold2
            INTEGER (-2147483648..2147483647),

        crmCacTrapStatus
            INTEGER
    }

crmCacDirection OBJECT-TYPE
    SYNTAX  INTEGER {
    ifp2sw(1),
    sw2ifp(2)
}
    ACCESS  not-accessible
    STATUS  mandatory
    DESCRIPTION
           "DUMMY"
    ::= { crmCacEntry  1 }

crmCacCurrentBand OBJECT-TYPE
    SYNTAX  INTEGER (-2147483648..2147483647)
    ACCESS  read-only
    STATUS  mandatory
    DESCRIPTION
           "DUMMY"
    ::= { crmCacEntry  2 }

crmCacCapacityBand OBJECT-TYPE
    SYNTAX  INTEGER (-2147483648..2147483647)
    ACCESS  read-only
    STATUS  mandatory
    DESCRIPTION
           "DUMMY"
    ::= { crmCacEntry  3 }

crmCacThreshold1 OBJECT-TYPE
    SYNTAX  INTEGER (-2147483648..2147483647)
    ACCESS  read-write
    STATUS  mandatory
    DESCRIPTION
           "DUMMY"
    DEFVAL {  95  }
    ::= { crmCacEntry  4 }

crmCacThreshold2 OBJECT-TYPE
    SYNTAX  INTEGER (-2147483648..2147483647)
    ACCESS  read-write
    STATUS  mandatory
    DESCRIPTION
           "DUMMY"
    DEFVAL {  50  }
    ::= { crmCacEntry  5 }

crmCacTrapStatus OBJECT-TYPE
    SYNTAX  INTEGER {
    on(1),
    off(2)
}
    ACCESS  read-write
    STATUS  mandatory
    DESCRIPTION
           "DUMMY"
    DEFVAL {  2  }
    ::= { crmCacEntry  6 }
-- 

END
