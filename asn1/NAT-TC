-- extracted from draft-ietf-nat-natmib-05.txt
-- at Sat Nov  9 06:11:19 2002

NAT-TC DEFINITIONS ::= BEGIN

IMPORTS
    MODULE-IDENTITY, 
    mib-2
            FROM SNMPv2-SMI
    TEXTUAL-CONVENTION
            FROM SNMPv2-TC;

natTextualConventions  MODULE-IDENTITY
    LAST-UPDATED "200111090000Z"
    ORGANIZATION "IETF NAT Working Group"
    CONTACT-INFO
             " Rohit
               World Wide Packets
               115 North Sullivan Road
               Veradale, Spokane, WA 99037 
               Phone: +1 509 242 9320
               Email: Rohit.Rohit@worldwidepackets.com

               Nalinaksh Pai
               Cisco Systems, Inc. 
               Prestige Waterford
               No. 9, Brunton Road
               Bangalore - 560 025
               India
               Phone: +91 80 532 1300 
               Email: npai@cisco.com

               Rajiv Raghunarayan
               Cisco Systems Inc.
               170 West Tasman Drive
               San Jose, CA 95134
               Phone: +1 408 853 9612
               Email: raraghun@cisco.com

               Cliff Wang
               Information Security
               Bank One Corp
               1111 Polaris Pkwy
               Columbus, OH 43240
               Phone: +1 614 213 6117
               Email: cliffwang2000@yahoo.com

               P. Srisuresh
               Kuokoa networks
               475 Potrero Ave.
               Sunnyvale, CA 94085
               Phone: +1 408 962 3709
               Email: srisuresh@yahoo.com
             "

     DESCRIPTION
             "This MIB module defines the NATProtocolType textual
              convention for use in MIBs that need to identify the
              protocols which support network address translation."

     REVISION     "200111090000Z"  -- 9th Nov. 2001
     DESCRIPTION
             "Initial version of this MIB module."
     ::= { mib-2 xx } -- to be assigned by RFC-editor

NATProtocolType ::= TEXTUAL-CONVENTION
       STATUS       current
       DESCRIPTION
               "A list of protocols that are affected/support
                network address translation. Inclusion of values is
                not intended to imply that those protocols need be
                supported."
       SYNTAX       INTEGER {
                        none (1),  -- not specified
                        other (2), -- none of the following
                        icmp (3),
                        udp (4),
                        tcp (5)
                    }

END

--    "Copyright (C) The Internet Society (2000). All Rights Reserved.
--    This document and translations of it may be copied and furnished to
--    others, and derivative works that comment on or otherwise explain it
--    or assist in its implementation may be prepared, copied, published
--    and distributed, in whole or in part, without restriction of any
--    kind, provided that the above copyright notice and this paragraph
--    are included on all such copies and derivative works. However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
--     
--    The limited permissions granted above are perpetual and will not be 
--    revoked by the Internet Society or its successors or assigns. 
--     
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
