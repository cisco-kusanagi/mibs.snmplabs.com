FASTPATH-MIB DEFINITIONS ::= BEGIN

-- Title:	FASTPATH MIB
-- Date:	April 4, 1990
-- By:		Brian Holmes <BHOLMES@CMS.CC.WAYNE.EDU>

IMPORTS
	OBJECT-TYPE FROM RFC-1212
	enterprises, NetworkAddress, IpAddress, Counter, Gauge,
	TimeTicks 
		FROM RFC1065-SMI;

	    
excelan		OBJECT	IDENTIFIER ::= { enterprises 23 }
genericGroup	OBJECT IDENTIFIER ::= { excelan 2 }
fastpathMib	OBJECT IDENTIFIER ::= { genericGroup 11 }

scc		OBJECT IDENTIFIER ::= { fastpathMib 1 }
alap		OBJECT IDENTIFIER ::= { fastpathMib 2 }
ethernet	OBJECT IDENTIFIER ::= { fastpathMib 3 }
aarp		OBJECT IDENTIFIER ::= { fastpathMib 4 }
atif		OBJECT IDENTIFIER ::= { fastpathMib 5 }
ddp	        OBJECT IDENTIFIER ::= { fastpathMib 6 }
rtmp		OBJECT IDENTIFIER ::= { fastpathMib 7 }
kip		OBJECT IDENTIFIER ::= { fastpathMib 8 }
zip		OBJECT IDENTIFIER ::= { fastpathMib 9 }
nbp	        OBJECT IDENTIFIER ::= { fastpathMib 10 }
echo		OBJECT IDENTIFIER ::= { fastpathMib 11 }
buffer		OBJECT IDENTIFIER ::= { fastpathMib 12 }

    sccInterruptCount OBJECT-TYPE
	    SYNTAX  Counter
	    ACCESS  read-only
	    STATUS  mandatory
	    ::= { scc 1 }

    sccAbortCount OBJECT-TYPE
	    SYNTAX  Counter
	    ACCESS  read-only
	    STATUS  mandatory
	    ::= { scc 2 }

    sccSpuriousCount OBJECT-TYPE
	    SYNTAX  Counter
	    ACCESS  read-only
	    STATUS  mandatory
	    ::= { scc 3 }

    sccCRCCount OBJECT-TYPE
	    SYNTAX  Counter
	    ACCESS  read-only
	    STATUS  mandatory
	    ::= { scc 4 }

    sccOverrunCount OBJECT-TYPE
	    SYNTAX  Counter
	    ACCESS  read-only
	    STATUS  mandatory
	    ::= { scc 5 }

    sccUnderrunCount OBJECT-TYPE
	    SYNTAX  Counter
	    ACCESS  read-only
	    STATUS  mandatory
	    ::={ scc 6 }

    alapReceiveCount OBJECT-TYPE
	    SYNTAX  Counter
	    ACCESS  read-only
	    STATUS  mandatory
	    ::= { alap 1 }

    alapTransmitCount OBJECT-TYPE
	    SYNTAX  Counter
	    ACCESS  read-only
	    STATUS  mandatory
	    ::= { alap 2 }

    alapNoHandlerCount OBJECT-TYPE
	    SYNTAX  Counter
	    ACCESS  read-only
	    STATUS  mandatory
	    ::= { alap 3 }

    alapLengthErrorCount OBJECT-TYPE
	    SYNTAX  Counter
	    ACCESS  read-only
	    STATUS  mandatory
	    ::= { alap 4 }

    alapBadCount OBJECT-TYPE
	    SYNTAX  Counter
	    ACCESS  read-only
	    STATUS  mandatory
	    ::= { alap 5 }

    alapCollisionCount OBJECT-TYPE
	    SYNTAX  Counter
	    ACCESS  read-only
	    STATUS  mandatory
	    ::= { alap 6 }

    alapDeferCount OBJECT-TYPE
	    SYNTAX  Counter
	    ACCESS  read-only
	    STATUS  mandatory
	    ::= { alap 7 }

    alapNoDataCount OBJECT-TYPE
	    SYNTAX  Counter
	    ACCESS  read-only
	    STATUS  mandatory
	    ::= { alap 8 }

    alapRandomCTS OBJECT-TYPE
	    SYNTAX  Counter
	    ACCESS  read-only
	    STATUS  mandatory
	    ::= { alap 9 }

    etherCRCErrors OBJECT-TYPE
	    SYNTAX  Counter
	    ACCESS  read-only
	    STATUS  mandatory
	    ::= { ethernet 1 }

    etherAlignErrors OBJECT-TYPE
	    SYNTAX  Counter
	    ACCESS  read-only
	    STATUS  mandatory
	    ::= { ethernet 2 }

    etherResourceErrors OBJECT-TYPE
	    SYNTAX  Counter
	    ACCESS  read-only
	    STATUS  mandatory
	    ::= { ethernet 3 }

    etherOverrunErrors OBJECT-TYPE
	    SYNTAX  Counter
	    ACCESS  read-only
	    STATUS  mandatory
	    ::= { ethernet 4 }

    etherInPackets OBJECT-TYPE
	    SYNTAX  Counter
	    ACCESS  read-only
	    STATUS  mandatory
	    ::= { ethernet 5 }

    etherOutPackets OBJECT-TYPE
	    SYNTAX  Counter
	    ACCESS  read-only
	    STATUS  mandatory
	    ::= { ethernet 6 }

    etherBadTransmits OBJECT-TYPE
	    SYNTAX  Counter
	    ACCESS  read-only
	    STATUS  mandatory
	    ::= { ethernet 7 }

    etherOversizeFrames OBJECT-TYPE
	    SYNTAX  Counter
	    ACCESS  read-only
	    STATUS  mandatory
	    ::= { ethernet 8 }

    etherSpurRUReadys OBJECT-TYPE
	    SYNTAX  Counter
	    ACCESS  read-only
	    STATUS  mandatory
	    ::= { ethernet 9 }

    etherSpurCUActives OBJECT-TYPE
	    SYNTAX  Counter
	    ACCESS  read-only
	    STATUS  mandatory
	    ::= { ethernet 10 }

    etherSpurUnknown OBJECT-TYPE
	    SYNTAX  Counter
	    ACCESS  read-only
	    STATUS  mandatory
	    ::= { ethernet 11 }

    etherBcastDrops OBJECT-TYPE
	    SYNTAX  Counter
	    ACCESS  read-only
	    STATUS  mandatory
	    ::= { ethernet 12 }

    etherReceiverRestarts OBJECT-TYPE
	    SYNTAX  Counter
	    ACCESS  read-only
	    STATUS  mandatory
	    ::= { ethernet 13 }

    etherReinterrupts OBJECT-TYPE
	    SYNTAX  Counter
	    ACCESS  read-only
	    STATUS  mandatory
	    ::= { ethernet 14 }

    etherBufferReroutes OBJECT-TYPE
	    SYNTAX  Counter
	    ACCESS  read-only
	    STATUS  mandatory
	    ::= { ethernet 15 }

    etherBufferDrops OBJECT-TYPE
	    SYNTAX  Counter
	    ACCESS  read-only
	    STATUS  mandatory
	    ::= { ethernet 16 }

    etherCollisions OBJECT-TYPE
	    SYNTAX  Counter
	    ACCESS  read-only
	    STATUS  mandatory
	    ::= { ethernet 17 }

    etherDefers OBJECT-TYPE
	    SYNTAX  Counter
	    ACCESS  read-only
	    STATUS  mandatory
	    ::= { ethernet 18 }

    etherDMAUnderruns OBJECT-TYPE
	    SYNTAX  Counter
	    ACCESS  read-only
	    STATUS  mandatory
	    ::= { ethernet 19 }

    etherMaxCollisions OBJECT-TYPE
	    SYNTAX  Counter
	    ACCESS  read-only
	    STATUS  mandatory
	    ::= { ethernet 20 }

    etherNoCarriers OBJECT-TYPE
	    SYNTAX  Counter
	    ACCESS  read-only
	    STATUS  mandatory
	    ::= { ethernet 21 }

    etherNoCTS OBJECT-TYPE
	    SYNTAX  Counter
	    ACCESS  read-only
	    STATUS  mandatory
	    ::= { ethernet 22 }

    etherNoSQEs OBJECT-TYPE
	    SYNTAX  Counter
	    ACCESS  read-only
	    STATUS  mandatory
	    ::= { ethernet 23 }

    aarpTable OBJECT-TYPE
	    SYNTAX  SEQUENCE OF AarpEntry
	    ACCESS  read-write
	    STATUS  mandatory
	    ::= { aarp 1 }

    aarpEntry OBJECT-TYPE
	    SYNTAX  AarpEntry
	    ACCESS  read-write
	    STATUS  mandatory
	    ::= { aarpTable 1 }

    AarpEntry ::= SEQUENCE {
	    aarpIfIndex	INTEGER,
	    aarpPhysAddress	OCTET STRING,
	    aarpNetAddress	OCTET STRING
    }

    aarpIfIndex OBJECT-TYPE
	    SYNTAX  INTEGER
	    ACCESS  read-only
	    STATUS  mandatory
	    ::= { aarpEntry 1 }

    aarpPhysAddress OBJECT-TYPE
	    SYNTAX  OCTET STRING
	    ACCESS  read-only
	    STATUS  mandatory
	    ::= { aarpEntry 2 }

    aarpNetAddress OBJECT-TYPE
	    SYNTAX  OCTET STRING
	    ACCESS  read-only
	    STATUS  mandatory
	    ::= { aarpEntry 3 }

    atifTable OBJECT-TYPE
	    SYNTAX  SEQUENCE OF AtifEntry
	    ACCESS  read-write
	    STATUS  mandatory
	    ::= { atif 1 }

    atifEntry OBJECT-TYPE
	    SYNTAX  AtifEntry
	    ACCESS  read-write
	    STATUS  mandatory
	    ::= { atifTable 1 }

    AtifEntry ::= SEQUENCE {
	    atifIndex		INTEGER,
	    atifDescr		OCTET STRING,
	    atifType		INTEGER,
	    atifNetStart	OCTET STRING,
	    atifNetEnd		OCTET STRING,
	    atifNetAddress	OCTET STRING,
	    atifStatus		INTEGER,
	    atifNetConfig	INTEGER,
	    atifZoneConfig	INTEGER,
	    atifZone		OCTET STRING,
	    atifIfIndex		INTEGER
    }

    atifIndex OBJECT-TYPE
	    SYNTAX  INTEGER
	    ACCESS  read-only
	    STATUS  mandatory
	    ::= { atifEntry 1 }

    atifDescr OBJECT-TYPE
	    SYNTAX  OCTET STRING
	    ACCESS  read-only
	    STATUS  mandatory
	    ::= { atifEntry 2 }

    atifType OBJECT-TYPE
	    SYNTAX  INTEGER {
		other(1),	-- none of the following
		localtalk(2),
		ethertalk1(3),
		ethertalk2(4),
		tokentalk(5),
		iptalk(6)
	    }
	    ACCESS	read-only
	    STATUS	mandatory
	    ::= { atifEntry 3 }

    atifNetStart OBJECT-TYPE
	    SYNTAX  OCTET STRING
	    ACCESS  read-write
	    STATUS  mandatory
	    ::= { atifEntry 4 }

    atifNetEnd OBJECT-TYPE
	    SYNTAX  OCTET STRING
	    ACCESS  read-write
	    STATUS  mandatory
	    ::= { atifEntry 5 }

    atifNetAddress OBJECT-TYPE
	    SYNTAX  OCTET STRING
	    ACCESS  read-write
	    STATUS  mandatory
	    ::= { atifEntry 6 }

    atifStatus OBJECT-TYPE
	    SYNTAX  INTEGER
	    ACCESS  read-only
	    STATUS  mandatory
	    ::= { atifEntry 7 }

    atifNetConfig OBJECT-TYPE
	    SYNTAX  INTEGER {
		configured(1),
		garnered(2),
		guessed(3),
		unconfigured(4)
	    }
	    ACCESS  read-only
	    STATUS  mandatory
	    ::= { atifEntry 8 }

    atifZoneConfig OBJECT-TYPE
	    SYNTAX  INTEGER {
		configured(1),
		garnered(2),
		guessed(3),
		unconfigured(4)
	    }		
	    ACCESS  read-only
	    STATUS  mandatory
	    ::= { atifEntry 9 }

    atifZone OBJECT-TYPE
	    SYNTAX  OCTET STRING
	    ACCESS  read-write
	    STATUS  mandatory
	    ::= { atifEntry 10 }

    atifIfIndex OBJECT-TYPE
	    SYNTAX  INTEGER
	    ACCESS  read-write
	    STATUS  mandatory
	    ::= { atifEntry 11 }

    ddpOutRequests OBJECT-TYPE
	    SYNTAX  Counter
	    ACCESS  read-only
	    STATUS  mandatory
	    ::= { ddp 1 }

    ddpOutShort OBJECT-TYPE
	    SYNTAX  Counter
	    ACCESS  read-only
	    STATUS  mandatory
	    ::= { ddp 2 }

    ddpOutLong OBJECT-TYPE
	    SYNTAX  Counter
	    ACCESS  read-only
	    STATUS  mandatory
	    ::={ ddp 3 }

    ddpReceived OBJECT-TYPE
	    SYNTAX  Counter
	    ACCESS  read-only
	    STATUS  mandatory
	    ::= { ddp 4 }

    ddpToForward OBJECT-TYPE
	    SYNTAX  Counter
	    ACCESS  read-only
	    STATUS  mandatory
	    ::={ ddp 5 }

    ddpForwards OBJECT-TYPE
	    SYNTAX  Counter
	    ACCESS  read-only
	    STATUS  mandatory
	    ::= { ddp 6 }

    ddpForMe OBJECT-TYPE
	    SYNTAX  Counter
	    ACCESS  read-only
	    STATUS  mandatory
	    ::= { ddp 7 }

    ddpOutNoRoutes OBJECT-TYPE
	    SYNTAX  Counter
	    ACCESS  read-only
	    STATUS  mandatory
	    ::= { ddp 9 }

    ddpTooShortDrops OBJECT-TYPE
	    SYNTAX  Counter
	    ACCESS  read-only
	    STATUS  mandatory
	    ::= { ddp 10 }

    ddpTooLongDrops OBJECT-TYPE
	    SYNTAX  Counter
	    ACCESS  read-only
	    STATUS  mandatory
	    ::= { ddp 11 }

    ddpBroadcastDrops OBJECT-TYPE
	    SYNTAX  Counter
	    ACCESS  read-only
	    STATUS  mandatory
	    ::= { ddp 12 }

    ddpShortDDPDrops OBJECT-TYPE
	    SYNTAX  Counter
	    ACCESS  read-only
	    STATUS  mandatory
	    ::= { ddp 13 }

    ddpHopCountDrops OBJECT-TYPE
	    SYNTAX  Counter
	    ACCESS  read-only
	    STATUS  mandatory
	    ::= { ddp 14 }

    rtmpTable OBJECT-TYPE
	    SYNTAX  SEQUENCE OF RtmpEntry
	    ACCESS  read-write
	    STATUS  mandatory
	    ::= { rtmp 1 }

    rtmpEntry OBJECT-TYPE
	    SYNTAX  RtmpEntry
	    ACCESS  read-write
	    STATUS  mandatory
	    ::= { rtmpTable 1 }

    RtmpEntry ::= SEQUENCE {
	    rtmpRangeStart	OCTET STRING,
	    rtmpRangeEnd	OCTET STRING,
	    rtmpNextHop		OCTET STRING,
	    rtmpInterface	INTEGER,
	    rtmpHops		INTEGER,
	    rtmpState		INTEGER
    }

    rtmpRangeStart OBJECT-TYPE
	    SYNTAX  OCTET STRING
	    ACCESS  read-write
	    STATUS  mandatory
	    ::= { rtmpEntry 1 }

    rtmpRangeEnd OBJECT-TYPE
	    SYNTAX  OCTET STRING
	    ACCESS  read-write
	    STATUS  mandatory
	    ::= { rtmpEntry 2 }

    rtmpNextHop OBJECT-TYPE
	    SYNTAX  OCTET STRING
	    ACCESS  read-write
	    STATUS  mandatory
	    ::= { rtmpEntry 3 }

    rtmpInterface OBJECT-TYPE
	    SYNTAX  INTEGER
	    ACCESS  read-write
	    STATUS  mandatory
	    ::= { rtmpEntry 4 }

    rtmpHops OBJECT-TYPE
	    SYNTAX  INTEGER
	    ACCESS  read-write
	    STATUS  mandatory
	    ::= { rtmpEntry 5 }

    rtmpState OBJECT-TYPE
	    SYNTAX  INTEGER {
		good(1),
		suspect(2),
		bad(3)
	    }
	    ACCESS  read-write
	    STATUS  mandatory
	    ::= { rtmpEntry 6 }

    kipTable OBJECT-TYPE
	    SYNTAX  SEQUENCE OF KipEntry
	    ACCESS  read-write
	    STATUS  mandatory
	    ::= { kip 1 }

    kipEntry OBJECT-TYPE
	    SYNTAX  KipEntry
	    ACCESS  read-write
	    STATUS  mandatory
	    ::= { kipTable 1 }

    KipEntry ::= SEQUENCE {
	    kipNet		OCTET STRING,
	    kipNextHop		IpAddress,
	    kipHopCount		INTEGER,
	    kipBCastAddr	IpAddress,
	    kipCore		INTEGER,
	    kipKfps		INTEGER
    }

    kipNet OBJECT-TYPE
	    SYNTAX  OCTET STRING
	    ACCESS  read-write
	    STATUS  mandatory
	    ::= { kipEntry 1 }

    kipNextHop OBJECT-TYPE
	    SYNTAX  IpAddress
	    ACCESS  read-write
	    STATUS  mandatory
	    ::= { kipEntry 2 }

    kipHopCount OBJECT-TYPE
	    SYNTAX  INTEGER
	    ACCESS  read-write
	    STATUS  mandatory
	    ::= { kipEntry 3 }

    kipBCastAddr OBJECT-TYPE
	    SYNTAX  IpAddress
	    ACCESS  read-write
	    STATUS  mandatory
	    ::= { kipEntry 4 }

    kipCore OBJECT-TYPE
	    SYNTAX  INTEGER {
		core(1),
		notcore(2)
	    }
	    ACCESS  read-write
	    STATUS  mandatory
	    ::= { kipEntry 5 }

    kipKfps OBJECT-TYPE
	    SYNTAX  INTEGER
	    ACCESS  read-write
	    STATUS  mandatory
	    ::= { kipEntry 6 }

    zipTable OBJECT-TYPE
	    SYNTAX  SEQUENCE OF ZipEntry
	    ACCESS  read-write
	    STATUS  mandatory
	    ::= { zip 1 }

    zipEntry OBJECT-TYPE
	    SYNTAX  ZipEntry
	    ACCESS  read-write
	    STATUS  mandatory
	    ::= { zipTable 1 }

    ZipEntry ::= SEQUENCE {
	    zipZoneName	    OCTET STRING,
	    zipZoneIndex    INTEGER,
	    zipNetStart	    OCTET STRING,
	    zipNetEnd	    OCTET STRING
    }

    zipZoneName OBJECT-TYPE
	    SYNTAX  OCTET STRING
	    ACCESS  read-write
	    STATUS  mandatory
	    ::= { zipEntry 1 }

    zipZoneIndex OBJECT-TYPE
	    SYNTAX  INTEGER
	    ACCESS  read-only
	    STATUS  mandatory
	    ::= { zipEntry 2 }

    zipZoneNetStart OBJECT-TYPE
	    SYNTAX  OCTET STRING
	    ACCESS  read-write
	    STATUS  mandatory
	    ::= { zipEntry 3 }

    zipZoneNetEnd OBJECT-TYPE
	    SYNTAX  OCTET STRING
	    ACCESS  read-write
	    STATUS  mandatory
	    ::= { zipEntry 4 }

    nbpTable OBJECT-TYPE
	    SYNTAX  SEQUENCE OF NbpEntry
	    ACCESS  read-write
	    STATUS  mandatory
	    ::= { nbp 1 }

    nbpEntry OBJECT-TYPE
	    SYNTAX  NbpEntry
	    ACCESS  read-write
	    STATUS  mandatory
	    ::= { nbpTable  1 }


    NbpEntry ::= SEQUENCE {
	    nbpIndex	INTEGER,
	    nbpObject	OCTET STRING,
	    nbpType 	OCTET STRING,
	    nbpZone	OCTET STRING
    }

    nbpIndex OBJECT-TYPE
	    SYNTAX  INTEGER
	    ACCESS  read-only
	    STATUS  mandatory
	    ::= { nbpEntry 1 }

    nbpObject OBJECT-TYPE
	    SYNTAX  OCTET STRING
	    ACCESS  read-write
	    STATUS  mandatory
	    ::= { nbpEntry 2 }

    nbpType OBJECT-TYPE
	    SYNTAX  OCTET STRING
	    ACCESS  read-write
	    STATUS  mandatory
	    ::= { nbpEntry 3 }

    nbpZone OBJECT-TYPE
	    SYNTAX  OCTET STRING
	    ACCESS  read-write
	    STATUS  mandatory
	    ::= { nbpEntry 4 }

    echoRequests OBJECT-TYPE
	    SYNTAX  Counter
	    ACCESS  read-only
	    STATUS  mandatory
	    ::= { echo 1 }

    echoReplies OBJECT-TYPE
	    SYNTAX  Counter
	    ACCESS  read-only
	    STATUS  mandatory
	    ::= { echo 2 }

    bufferSize OBJECT-TYPE
	    SYNTAX  INTEGER
	    ACCESS  read-only
	    STATUS  mandatory
	    ::= { buffer 1 }

    bufferAvail OBJECT-TYPE
	    SYNTAX  INTEGER
	    ACCESS  read-only
	    STATUS  mandatory
	    ::= { buffer 2 }

    bufferDrops OBJECT-TYPE
	    SYNTAX  Counter
	    ACCESS  read-only
	    STATUS  mandatory
	    ::= { buffer 3 }

    bufferTypeTable OBJECT-TYPE
	    SYNTAX  SEQUENCE OF BufferTypeEntry
	    ACCESS  read-only
	    STATUS  mandatory
	    ::= { buffer 4 }

    bufferTypeEntry OBJECT-TYPE
	    SYNTAX  BufferTypeEntry
	    ACCESS  read-only
	    STATUS  mandatory
	    ::= { bufferTypeTable 1 }

    BufferTypeEntry ::= SEQUENCE {
	    bufferTypeIndex	INTEGER,
	    bufferType		INTEGER,
	    bufferTypeDescr	OCTET STRING,
	    bufferTypeCount	INTEGER
    }

    bufferTypeIndex OBJECT-TYPE
	    SYNTAX  INTEGER
	    ACCESS  read-only
	    STATUS  mandatory
	    ::= { bufferTypeEntry 1 }

    bufferType OBJECT-TYPE
	    SYNTAX  INTEGER {
		other(1),
		free(2),
		localtalk(3),
		ethernet(4),
		arp(5),
		data(6),	-- general data
		erbf(7),	-- ethernet receive
		etbf(8),	-- ethernet transmit complete
		malloc(9),
		tkbf(10),	-- token ring receive packet
		token(11)	-- token ring packet
	    }
	    ACCESS  read-only
	    STATUS  mandatory
	    ::= { bufferTypeEntry 2 }

    bufferTypeDescr OBJECT-TYPE
	    SYNTAX  OCTET STRING
	    ACCESS  read-only
	    STATUS  mandatory
	    ::= { bufferTypeEntry 3 }

    bufferTypeCount OBJECT-TYPE
	    SYNTAX  INTEGER
	    ACCESS  read-only
	    STATUS  mandatory
	    ::= { bufferTypeEntry 4 }

END
