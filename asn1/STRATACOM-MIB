-- MIB-File-Header-Block

--
--  STRATACOM Switch MIB
--  RELEASE:  8.1
--

STRATACOM-MIB
        --FORCE-INCLUDE <snmp-auxfuncs.h>
        --FORCE-INCLUDE <snmp-asn1.h>
        --FORCE-INCLUDE <snmp-mib.h>
        --FORCE-INCLUDE <snmp-buffer.h>
        --FORCE-INCLUDE <snmpdefs.h>
 
        -- all functions can use %n for object name and
        -- %t for object type, %p for parent name,
        -- %d for name of default-bearing node and %% for %
        --DEFAULT test-function   it-exists
        --DEFAULT set-function    null-set-proc
        --DEFAULT get-function    get-%n
        --DEFAULT next-function   std-next
        --DEFAULT view-mask       PUBLIC-VIEW
        --DEFAULT cookie          (char *)NULL
        --DEFAULT locator          0

DEFINITIONS ::= BEGIN

-- This MIB has not been officially released to the N.I.C.
IMPORTS
        enterprises, IpAddress, Counter, TimeTicks FROM RFC1155-SMI
        OBJECT-TYPE             FROM RFC-1212
        TRAP-TYPE               FROM RFC-1215;


     DisplayString ::= OCTET STRING

    stratacom             OBJECT IDENTIFIER ::= { enterprises 351 }
    strmErrors            OBJECT IDENTIFIER ::= { stratacom 910}
    snmpAgents            OBJECT IDENTIFIER ::= { stratacom 100}
    strmSwitchMIB         OBJECT IDENTIFIER ::= { snmpAgents 4 }


    switchInterfaces      OBJECT IDENTIFIER ::= { strmSwitchMIB 1 }
    switchServiceObjects  OBJECT IDENTIFIER ::= { strmSwitchMIB 2 }
    switchConnection      OBJECT IDENTIFIER ::= { strmSwitchMIB 3 }
    switchShelf           OBJECT IDENTIFIER ::= { strmSwitchMIB 4 }

    frServiceObjects      OBJECT IDENTIFIER ::= { switchServiceObjects 1 }
    atmServiceObjects     OBJECT IDENTIFIER ::= { switchServiceObjects 2 }
    voiceServiceObjects   OBJECT IDENTIFIER ::= { switchServiceObjects 3 }
    trunkServiceObjects   OBJECT IDENTIFIER ::= { switchServiceObjects 4 }

    shelfCnfgObjects      OBJECT IDENTIFIER ::= { switchShelf 1 }

-- The following describes the MIB variables for the switchIFTable. 
-- This table provides the manager a view of the interfaces available
-- on the requested switch. The table provides the physical interface
-- available as well as the service provided by that interface. 
--
-- ***************************************************************
-- This table will be developed in future phases of this project.
-- ***************************************************************
--
--switchIFTable OBJECT-TYPE
--    SYNTAX      SEQUENCE OF SlotPortEntry
--    ACCESS      not-accessible
--    STATUS      mandatory
--    DESCRIPTION "A list of slots and their associated ports"
--    DEFAULT   test-function test-switchiftable
--    DEFAULT   next-function next-switchiftable
--    DEFAULT   get-function  get-switchiftable-%t
--        ::= { switchInterfaces 1  }
--
--switchIFEntry OBJECT-TYPE
--    SYNTAX      SlotPortEntry
--    ACCESS      not-accessible
--    STATUS      mandatory
--    DESCRIPTION "A slot-port entry"
--    INDEX       { switchIFSlotIndex , switchIFPortIndex }
--        ::= { switchIFTable 1  }
--
--SwitchIFEntry ::=
--    SEQUENCE {
--        switchIFSlotIndex       INTEGER,
--        switchIFPortIndex       INTEGER,
--        switchIFType            INTEGER,
--        switchIFService         INTEGER
--   }

-- The following describes the MIB variables for the switchIFTable.

switchIfTable OBJECT-TYPE
    SYNTAX      SEQUENCE OF SwitchIfEntry
    ACCESS      not-accessible
    STATUS      mandatory
    DESCRIPTION "A list of ports and subports, and their interfaces"
    --DEFAULT   test-function test-switchiftable
    --DEFAULT   next-function next-switchiftable
    --DEFAULT   get-function  get-switchiftable-%t
        ::= { switchInterfaces 1  }

switchIfEntry OBJECT-TYPE
    SYNTAX      SwitchIfEntry
    ACCESS      not-accessible
    STATUS      mandatory
    DESCRIPTION "A slot-port-subport entry"
    INDEX       { switchIfIndex }
        ::= { switchIfTable 1  }

SwitchIfEntry ::=
    SEQUENCE {
        switchIfIndex      INTEGER,
        switchIfSlot       INTEGER,
        switchIfPort       INTEGER,
        switchIfSubPort    INTEGER,
        switchIfMediaType  INTEGER,
        switchIfService    INTEGER,
        switchIfAdmStatus  INTEGER,
        switchIfOperStatus INTEGER,
        switchIfPhysPort   INTEGER,
        switchIfPartiId    INTEGER,
        switchIfCtrlerId   INTEGER
        }

switchIfIndex OBJECT-TYPE
    SYNTAX      INTEGER
    ACCESS      read-write
    STATUS      mandatory
    DESCRIPTION "The interface number is the index for the switchIfTable,
                 as well as the switchMedia tables and the Trunk Service
                 tables. The switchIFIndex will be an INTEGER with the
                 value related to the slot, port, and subport as  follows:
                 switchIFIndex = (slot x 1000000)+(port x 10000)+(subport);"
        ::= { switchIfEntry 1  }

switchIfSlot  OBJECT-TYPE
--    SYNTAX      INTEGER (1..32)
    SYNTAX      INTEGER
    ACCESS      read-only
    STATUS      mandatory
    DESCRIPTION "The slot number."
        ::= { switchIfEntry 2  }

switchIfPort OBJECT-TYPE
--    SYNTAX      INTEGER (1..32)
    SYNTAX      INTEGER
    ACCESS      read-only
    STATUS      mandatory
    DESCRIPTION "The port number."
        ::= { switchIfEntry 3  }

switchIfSubPort OBJECT-TYPE
--    SYNTAX      INTEGER (0..32)
    SYNTAX      INTEGER
    ACCESS      read-only
    STATUS      mandatory
    DESCRIPTION "The subport number, used to identify virtual trunks."
        ::= { switchIfEntry 4  }

switchIfMediaType OBJECT-TYPE
    SYNTAX      INTEGER {
                other(1),
                ds1(18),
                serialPort(22),
                ds3(30),
                sonet(39)
        }
    ACCESS      read-only
    STATUS      mandatory
    DESCRIPTION "The type of interface. This object is normally used to
                 provide information about a media layer, such as ds1, ds3,
                 or sonet."
        ::= { switchIfEntry 5  }

switchIfService OBJECT-TYPE
    SYNTAX      INTEGER {
                other(1),
                frameRelay(2),
                atmAccessPort(3),
                voiceData(4),
                fpRoutingTrk(5),
                atmRoutingTrk(6),
                atmAxisIntfTrk(7),
                atmIPXAFIntfTrk(8),
                atmFdrIntfTrk(9),
                atmAPSIntfTrk(10),
                imaRoutingTrunk(11),
                physicalMedia(12),
                atmVsiIntfTrk(13),
                atmParIntfTrk(14)
        }
    ACCESS      read-write
    STATUS      mandatory
    DESCRIPTION "User requested service for logical interface table row.
                atmVsiIntfTrk is only available for BXM resource on BPX.
                IPX cannot support the service."
        ::= { switchIfEntry 6  }

switchIfAdmStatus OBJECT-TYPE
    SYNTAX      INTEGER {
                up(1),
                down(2),
                added(6),
                deleted(7)
        }
    ACCESS      read-write
    STATUS      mandatory
    DESCRIPTION "User requested state for logical interface table row.
                 A user may up, down, add, or delete an interface.
                 The set-request PDU should contain values for both
                 switchIFService and switchAdmStatus. A logical row
                 can be created in the switchIfTable by combining an
                 appropriate switchIFService and switchAdmStatus up(1).
                 switchIFService and switchAdmStatus. A logical row
                 can be deleted from the switchIfTable by combining an
                 appropriate switchIFService and switchAdmStatus down(2).
                 The values for added(6) and deleted(7) can be used 
                 only with a valid Trunk switchIfService (5..8)."
        ::= { switchIfEntry 7  }
 
switchIfOperStatus OBJECT-TYPE
    SYNTAX      INTEGER {
                up(1),
                down(2),
                testing(3),
                unknown(4),
                dormant(5),
                added(6)
        }
    ACCESS      read-only
    STATUS      mandatory
    DESCRIPTION "The current state for logical interface table row."
        ::= { switchIfEntry 8  }
 
switchIfPhysPort OBJECT-TYPE
    SYNTAX       INTEGER
    ACCESS       read-write
    STATUS       mandatory
    DESCRIPTION "This Integer is a Bit map specifying which physical ports 
                 are used by the IMA trunk. Bits corresponding to the physical 
                 ports forming this IMA trunk will be set to 1. Using this 
                 Integer we can represent maximum 32 ports.
                 For regular ATM Routing trunk bit related to that port will be
                 set. For access lines this field is unused and will return -1.
                 For example:
                 Value       Ports used           Trunk Type
                 -----------------------------------------------
                   0         Invalid              Invalid
                   1         1                    ATM RoutingTrk
                   2         2                    ATM RoutingTrk
                   3         1 & 2                IMA RoutingTrk
                   4         3                    ATM RoutingTrk
                   5         1 & 3                IMA RoutingTrk
                   15        1,2,3 & 4            IMA RoutingTrk
                "
        ::= { switchIfEntry 9}
 
switchIfPartiId OBJECT-TYPE
--    SYNTAX      INTEGER (0..2)
    SYNTAX      INTEGER
    ACCESS      read-write
    STATUS      mandatory
    DESCRIPTION "The partition ID for logical interface table row.
                 A partition in the BXM resource is dedicated for
                 control by the corresponding VSI Master. The
                 partition is not available for any other cards.
                 0 indicates non-existent partition for
                 all non-VSI controllers.
                 "
        ::= { switchIfEntry 10  }

switchIfCtrlerId OBJECT-TYPE
--    SYNTAX      INTEGER (-1..32)
    SYNTAX      INTEGER
    ACCESS      read-write
    STATUS      mandatory
    DESCRIPTION "The controller ID for logical interface table row.
                 The ID in the BXM resource is used to identify
                 a VSI mster. No other card can have a VSI controller.
                 -1 indicates an invalid controller ID"
        ::= { switchIfEntry 11  }


-- The following describes the MIB variables for the frLportCnfTable. 
-- This table provides the manager a detailed view of the logical ports 
-- available on the switch. 

frLportCnfTable OBJECT-TYPE
    SYNTAX      SEQUENCE OF FrLportCnfEntry
    ACCESS      not-accessible
    STATUS      mandatory
    DESCRIPTION "The Frame Relay Logical Port Configuration table.  
                This table provides the following areas of information 
                on per port basis:
                * Port identification 
                * Current admin & operation status
                * Port-specific configuration
                * LMI-related configuration
                * Port error status
                * Pointer(s) to other tables"
    --DEFAULT   test-function   test-frlportcnftable
    --DEFAULT   next-function   next-frlportcnftable
    --DEFAULT   get-function    get-frlportcnftable-%t
    --DEFAULT   view-mask       IPX-VIEW
        ::= { frServiceObjects 1  }

frLportCnfEntry OBJECT-TYPE
    SYNTAX      FrLportCnfEntry
    ACCESS      not-accessible
    STATUS      mandatory
    DESCRIPTION "An entry in the Frame Relay Logical Port Configuration table.
                 Some entries that are applicable to a specific FRI interface
                 are indicated in the parenthesis, such as (FRI subrate/
                 T1/E1 interface only). Otherwise, they are used for both 
                 interfaces."
    INDEX   { frLportSlotIndex , frLportPortIndex }
        ::= { frLportCnfTable 1  }

FrLportCnfEntry ::=
    SEQUENCE {
        frLportSlotIndex        INTEGER,
        frLportPortIndex        INTEGER,
        frLportPortDLCI         INTEGER,

        frLportAdminStatus      INTEGER,
        frLportOperStatus       INTEGER,
    
        frLportPortSpeed        INTEGER,
        frLportClockType        INTEGER,
        frLportPortType         INTEGER,

        frLportVcCount          INTEGER,
        frLportFirstVcPtr       OBJECT IDENTIFIER,
        frLportAggrChCnt        INTEGER,
        frLportChSpeed          INTEGER,

        frLportMaxTxQDepth      INTEGER,
        frLportECNQThresh       INTEGER,
        frLportDEThresh         INTEGER,
        frLportIDEMap           INTEGER,

        frLportSigProt          INTEGER,
        frLportNNIStatus        INTEGER,
        frLportAsynStatus       INTEGER,

        frLportPolVerTmr        INTEGER,
        frLportErrThresh        INTEGER,
        frLportMonEveCnt        INTEGER,

        frLportCommPri          INTEGER,
        frLportUpRNR            INTEGER,
        frLportLowRNR           INTEGER,

        frLportMinFrmFlgs       INTEGER,

        frLportOamThresh        INTEGER,

        frLportLinkTimer        INTEGER,
        frLportPollCycle        INTEGER,
        
        frLportCLLMTimer        INTEGER,
        frLportEFCItoBECN       INTEGER,

        frLportSrRTS            INTEGER,
        frLportSrDTR            INTEGER,
        frLportSrDCD            INTEGER,
        frLportSrCTS            INTEGER,
        frLportSrDSR            INTEGER,

        frLportLoopBack         INTEGER,
        frLportExtConFail       INTEGER
    }

frLportSlotIndex OBJECT-TYPE
    SYNTAX      INTEGER (1..32)
    ACCESS      read-only
    STATUS      mandatory
    DESCRIPTION "The slot number"
        ::= { frLportCnfEntry 1  }

frLportPortIndex OBJECT-TYPE
    SYNTAX      INTEGER (1..32)
    ACCESS      read-only
    STATUS      mandatory
    DESCRIPTION "The port number"
        ::= { frLportCnfEntry 2  }

frLportPortDLCI OBJECT-TYPE
    SYNTAX      INTEGER 
    ACCESS      read-only
    STATUS      mandatory
    DESCRIPTION "Port DLCI for Frame Forwarding (FRI subrate interface only).
                 - Get Operation:
                 If the network manager attempts to GET this object from a 
                 T1/E1 port, SNMP-OBJ-NA (Object Not Applicable -1) is 
                 returned."
        ::= { frLportCnfEntry 3  }

frLportAdminStatus OBJECT-TYPE
    SYNTAX      INTEGER {
                up(1),
                down(2),
                modify(3),
                writeOnly(4),
                add(5),
                delete(6)
        }
    ACCESS      read-write
    STATUS      mandatory
    DESCRIPTION "User requested state for logical port table row.  A user 
                may up, down, configure, add and delete a FR Logical port." 
        ::= { frLportCnfEntry 4  }

frLportOperStatus OBJECT-TYPE
    SYNTAX      INTEGER {
                inActive(1),
                active  (2),
                looped  (3),
                failed  (4),
                unknown (5)
        }
    ACCESS      read-only
    STATUS      mandatory
    DESCRIPTION "Actual state of the logical port."  
        ::= { frLportCnfEntry 5  }

frLportPortSpeed OBJECT-TYPE
    SYNTAX      INTEGER 
    ACCESS      read-write
    STATUS      mandatory
    DESCRIPTION "The baud rate of the port. For FRI T1/E1 interface, this
                 object is determined when this port is added by
                 the number of channels aggregated under it. Therefore,
                 it can be configured only if the port is subrated.
                 - Get Operation:
                 OK for both T1/E1 and subrate interface.
                 - Set Operation:
                 If the network manager attempts to SET this object on a 
                 T1/E1 port, an error is reported."
        ::= { frLportCnfEntry 6  }

frLportClockType OBJECT-TYPE
    SYNTAX      INTEGER {
                normal (1),
                looped (2),
                none   (3)
        }
    ACCESS      read-write
    STATUS      mandatory
    DESCRIPTION "The type of port clock (FRI subrate interface only). For
                 T1/E1 interface this object should be none.
                 - Get Operation:
                 If the network manager attempts to get this object from a 
                 T1/E1 port, none (3) is returned.
                 - Set Operation:
                 If the network manager attempts to set this object on a 
                 T1/E1 port wit, none, oror none, looped type, an error 
                 is returned."
        ::= { frLportCnfEntry 7  }

frLportPortType OBJECT-TYPE
    SYNTAX      INTEGER {
                fr  (1),
                atm (2)
        }
    ACCESS      read-only
    STATUS      mandatory
    DESCRIPTION "The type of FRP subrate port. This object is not used in
                 switch software release 8.1 It is retained for historical
                 reasons, and possible future enhancement."
        ::= { frLportCnfEntry 8  }

frLportVcCount OBJECT-TYPE
    SYNTAX      INTEGER (0..252)
    ACCESS      read-only
    STATUS      mandatory
    DESCRIPTION "The number of virtual connections that terminate on 
                 this port. Note that there can be up to 252 connections
                 per FRP cards shared among the ports. A port may have up
                 to 252 connections allocated."
        ::= { frLportCnfEntry 9  }

frLportFirstVcPtr OBJECT-TYPE
    SYNTAX      OBJECT IDENTIFIER 
    ACCESS      read-only
    STATUS      mandatory
    DESCRIPTION "The object identifier denoting the first endpoint 
                associated with  this port. For current implementation, 
                this OID points to the first frame relay connection
                on the port. It has a NULL OID value (i.e. { 0 0 }) if 
                there is no frame relay connection on this port. The 
                management station can retrieve all the information about 
                the first connection by reading from row pointed to by 
                this OID. Specifically, this OID specifies the first
                column of the appropriate row in the frEndptTable."
        ::= { frLportCnfEntry 10  }

frLportAggrChCnt OBJECT-TYPE
    SYNTAX      INTEGER 
    ACCESS      read-write
    STATUS      mandatory
    DESCRIPTION "The number of aggregate channels assigned to this logical
                 port (FRI T1/E1 interface only) when the port is added.
                 For subrate ports, this object is always 1."
        ::= { frLportCnfEntry 11  }

frLportChSpeed OBJECT-TYPE
    SYNTAX      INTEGER {
                s56k (1),
                s64k (2),
                na  (3)
        }
    ACCESS      read-write
    STATUS      mandatory
    DESCRIPTION "The channel speed (FRI T1/E1 interface only). For FRI
                 subrate interface this object should be set as na."
        ::= { frLportCnfEntry 12  }

frLportMaxTxQDepth OBJECT-TYPE
    SYNTAX      INTEGER (0..65535)
    ACCESS      read-write
    STATUS      mandatory
    DESCRIPTION "The maximum bytes queued for transmission from the 
                 FRP port"
        ::= { frLportCnfEntry 13  }

frLportECNQThresh OBJECT-TYPE
    SYNTAX      INTEGER (0..65535)
    ACCESS      read-write
    STATUS      mandatory
    DESCRIPTION "Port explicit congestion notification threshold. This 
                 is the point at which the BECN and FECN bits will be 
                 set in the communications to the user device."
        ::= { frLportCnfEntry 14  }

frLportDEThresh OBJECT-TYPE
    SYNTAX      INTEGER (0..100)
    ACCESS      read-write
    STATUS      mandatory
    DESCRIPTION "The percentage of the queue depth above which frames 
        with the Discard Eligibility bit set will be discarded.
        An entry of 100% effectively disables DE for the port."
        ::= { frLportCnfEntry 15  }

frLportIDEMap OBJECT-TYPE
    SYNTAX      INTEGER {
                no  (1),
                yes (2)
        }
    ACCESS      read-write
    STATUS      mandatory
    DESCRIPTION "The flag indicating whether IDE to DE mapping should be 
                 performed."
        ::= { frLportCnfEntry 16  }

frLportSigProt OBJECT-TYPE
    SYNTAX      INTEGER {
                xdisabled  (1),
                lmi-asyn   (2),
                disabled   (3),
                lmi-noasyn (4),
                uni-annexA (5),
                uni-annexD (6),
                nni-annexA (7),
                nni-annexD (8),
                auto-det   (9)
        }
    ACCESS      read-write
    STATUS      mandatory
    DESCRIPTION "The specified LMI operation mode. The options can be
        1 - (UNI)LMI disabled
        2 - (UNI)LMI and asynchronous update enabled
        3 - (UNI)LMI disabled
        4 - (UNI)LMI enabled but asynchronous update disabled
        5 - (UNI)LMI enabled using CCITT O.933 Annex A parameters
        6 - (UNI)LMI enabled using ANSI T1.617 parameters
        7 - (NNI)LMI enabled using CCITT O.933 Annex A parameters
        8 - (NNI)LMI enabled using ANSI T1.617 parameters
        Note that option 7 and 8 are both bidirectional protocols
        defined by FRF.2 and available only if Frame Relay NNI
        feature is enabled."
        ::= { frLportCnfEntry 17  }

frLportNNIStatus OBJECT-TYPE
    SYNTAX      INTEGER {
                no  (1),
                yes (2)
        }
    ACCESS      read-only
    STATUS      mandatory
    DESCRIPTION "The flag indicating whether NNI is active on the specified
                slot.port.
                - Get Operation only:
                This object is always NO if the network manager attempts
                to GET frLportNNIStatus from a disabled, LMI or LMI no
                update port. In other cases, the value of this object is
                determined by whether the port is configured as NNI or not."
                ::= { frLportCnfEntry 18  }

frLportAsynStatus OBJECT-TYPE
    SYNTAX      INTEGER {
                no  (1),
                yes (2)
        }
    ACCESS      read-write
    STATUS      mandatory
    DESCRIPTION "The flag indicating whether the IPX should send unsolicited
                 LMI update messages as they appear or wait for the polling 
                 from the user device. This object is applicable to only 
                 Annex A/D UNI and Annex A/D NNI protocols for write and
                 LMI, Annex A/D UNI and Annex A/D NNI for read. 
                 - Get Operation:
                 This object is always NO for ports without protocols; 
                 otherwise, its value is determined by the asynchronous
                 status of the port. 
                 - Set Operation:
                 If the network manager attempts to SET this object of a port
                 with none or LMI protocol, an error is reported."
        ::= { frLportCnfEntry 19  }

frLportPolVerTmr OBJECT-TYPE
    SYNTAX      INTEGER (5..30)
    ACCESS      read-write
    STATUS      mandatory
    DESCRIPTION "The link integrity verification timer heartbeat (keep-alive)
                 period. It should be set to 5 seconds more than the 
                 heartbeat time in the user device. Default is 15 seconds. 
                 - Get Operation:
                 Since this object is not applicable to disabled protocol,
                 SNMP-OBJ-NA (-1) is returned if the network manager attempts
                 to GET this object from a port without protocols.
                 - Set Operation:
                 If the network manager attempts to SET this object of a port
                 without any protocol, an error is reported."
        ::= { frLportCnfEntry 20  }

frLportErrThresh OBJECT-TYPE
    SYNTAX      INTEGER (1..10)
    ACCESS      read-write
    STATUS      mandatory
    DESCRIPTION "The number of the failures in the monitored events that
                 cause the keep-alive process to report an alarm. 
                 - Get Operation:
                 Since this object is not applicable to disabled protocol,
                 SNMP-OBJ-NA (-1) is returned if the network manager attempts
                 to GET this object from a port without protocols.
                 - Set Operation:
                 If the network manager attempts to SET this object of a port
                 without any protocol, an error is reported."
        ::= { frLportCnfEntry 21  }


frLportMonEveCnt OBJECT-TYPE
    SYNTAX      INTEGER (1..10)
    ACCESS      read-write
    STATUS      mandatory
    DESCRIPTION "The number of monitored events for the keep-alive process.
                 A port communication fail condition is cleared after this
                 number of successful polling cycles. 
                 - Get Operation:
                 Since this object is not applicable to disabled protocol,
                 SNMP-OBJ-NA (-1) is returned if the network manager attempts
                 to GET this object from a port without protocols.
                 - Set Operation:
                 If the network manager attempts to SET this object of a port
                 without any protocol, an error is reported."
        ::= { frLportCnfEntry 22  }

frLportCommPri OBJECT-TYPE
    SYNTAX      INTEGER {
                no (1),
                yes (2)
        }
    ACCESS      read-write
    STATUS      mandatory
    DESCRIPTION "The flag specifying if the connection SNA priority should
                 be communicated to the user device attached to the port.
                 - Get Operation:
                 Since this object is specific to LMI protocols, SNMP-OBJ-NA 
                 (-1) is returned if the network manager attempts to GET 
                 this object from a non-LMI port.
                 - Set Operation:
                 Likewise, if the network manager attempts to SET this object
                 of a non-LMI port, an error is reported."
        ::= { frLportCnfEntry 23  }

frLportUpRNR OBJECT-TYPE
    SYNTAX      INTEGER (1..100)
    ACCESS      read-write
    STATUS      mandatory
    DESCRIPTION "The upper Receiver-Not-Ready threshold. This threshold 
                 specifies the number of receiver not ready indications
                 from the user equipment before an alarm is generated for
                 this connection. The default is 75. 
                 - Get Operation:
                 Since this object is specific to LMI protocols, SNMP-OBJ-NA 
                 (-1) is returned if the network manager attempts to GET 
                 this object from a non-LMI port.
                 - Set Operation:
                 Likewise, if the network manager attempts to SET this object
                 of a non-LMI port, an error is reported."
        ::= { frLportCnfEntry 24  }

frLportLowRNR OBJECT-TYPE
    SYNTAX      INTEGER (1..100) 
    ACCESS      read-write
    STATUS      mandatory
    DESCRIPTION "The Lower Receiver-Not-Ready threshold. This threshold
                 specifies the number of receiver not ready indications
                 from the user equipment before an alarm is cleared for
                 this connection. The default is 75.
                 - Get Operation:
                 Since this object is specific to LMI protocols, SNMP-OBJ-NA 
                 (-1) is returned if the network manager attempts to GET 
                 this object from a non-LMI port.
                 - Set Operation:
                 Likewise, if the network manager attempts to SET this object
                 of a non-LMI port, an error is reported."
        ::= { frLportCnfEntry 25  }

frLportMinFrmFlgs OBJECT-TYPE
    SYNTAX      INTEGER (1..255) 
    ACCESS      read-write
    STATUS      mandatory
    DESCRIPTION "The minimum number of flags between frames. All values
                 in the range 1 to 255 are valid and the default is 1."
        ::= { frLportCnfEntry 26  }

frLportOamThresh OBJECT-TYPE
    SYNTAX  INTEGER (0..15)
    ACCESS  read-write
    STATUS  mandatory
    DESCRIPTION "The alarm threshold for number of OAM heartbeat
                 FastPackets missed before propagating A-bit=0.
                 This threshold is applicable to both UNI and NNI
                 Frame Relay ports when the node has FR NNI feature enabled
                 and this FRP firmware supports it.
                 - Get Operation:
                 Since this object is not applicable to disabled protocol,
                 SNMP-OBJ-NA (-1) is returned if the network manager attempts
                 to GET this object from a port without protocols.
                 - Set Operation:
                 If the network manager attempts to SET this object of a port
                 without any protocol, an error is reported."
    ::= { frLportCnfEntry 27  }  

frLportLinkTimer OBJECT-TYPE
    SYNTAX  INTEGER (5..30)
    ACCESS  read-write
    STATUS  mandatory
    DESCRIPTION "T391 - Link Integrity Timer (applicable to
                 NNI FR port only), indicating the interval at which
                 a Status Enquiry message is sent. This interval should be 
                 between 5 and 30 seconds with a default of 6 seconds.
                 - Get Operation:
                 the network manager attempts to GET this object from a port
                 with a protocol other than NNIs, SNMP-OBJ-NA (-1) is 
                 returned.
                 - Set Operation:
                 If the network manager attempts to SET this object of a port
                 with a protocol other than NNIs, an error is reported."
    ::= { frLportCnfEntry 28  }  

frLportPollCycle OBJECT-TYPE
    SYNTAX  INTEGER (1..255)
    ACCESS  read-write
    STATUS  mandatory
    DESCRIPTION "N391 - Full Status Polling Cycle (applicable to
                 NNI FR port only), indicating the interval (in terms
                 of polling cycles) at which a Full Status Report of
                 all PVCs is requested. The exact time duration
                 is N391*T391. This interval should be between 1 and
                 255 polling cycles with a default of 6.
                 - Get Operation:
                 If the network manager attempts to GET this object from 
                 a port with a protocol other than NNIs, SNMP-OBJ-NA (-1) 
                 is returned.
                 - Set Operation:
                 If the network manager attempts to SET this object of a port
                 with a protocol other than NNIs, an error is reported."
    ::= { frLportCnfEntry 29 }

frLportCLLMTimer OBJECT-TYPE
    SYNTAX      INTEGER 
    ACCESS      read-write
    STATUS      mandatory
    DESCRIPTION "The timer for CLLM messages in CLLM intervals. No CLLM if 0
                 is configured. If a user configures this value to be greater
                 than 0 then it should be in the range 4 to 35. The unit is
                 hundredth of a sec.  Note that ForeSight (CLLM) is available
                 only if the firmware supports it.
                 - Get Operation:
                 If the network manager attempts to GET this object from a 
                 port where ForeSight is not supported, SNMP-OBJ-NA (-1) is 
                 returned.
                 - Set Operation:
                 If the network manager attempts to SET this object of a port
                 where ForeSight is not supported, an error is reported."
        ::= { frLportCnfEntry 30 }

frLportEFCItoBECN OBJECT-TYPE
    SYNTAX      INTEGER {
                no  (1),
                yes (2),
                na  (3)
        }
    ACCESS      read-write
    STATUS      mandatory
    DESCRIPTION "This object indicates whether EFCI to BECN mapping
                 is enabled."
        ::= { frLportCnfEntry 31 }

frLportSrRTS OBJECT-TYPE
    SYNTAX      INTEGER {
                off (1),
                on  (2),
                na  (3)
        }
    ACCESS      read-only
    STATUS      mandatory
    DESCRIPTION "The current status of the RTS lead (subrated FRI only).
                 Na is used for T1/E1 FRI.
                 - Get Operation:
                 This object is valid only if the port is subrated and DTE.
                 Otherwise, na is returned."
        ::= { frLportCnfEntry 32 }

frLportSrDTR OBJECT-TYPE
    SYNTAX      INTEGER {
                off (1),
                on  (2),
                na  (3)
        }
    ACCESS      read-only
    STATUS      mandatory
    DESCRIPTION "The current status of the DTR lead (subrated FRI only).
                 Na is used for T1/E1 FRI.
                 - Get Operation:
                 This object is valid only if the port is subrated and DTE.
                 Otherwise, na is returned."
        ::= { frLportCnfEntry 33 }

frLportSrDCD OBJECT-TYPE
    SYNTAX      INTEGER {
                off (1),
                on  (2),
                na  (3)
        }
    ACCESS      read-only
    STATUS      mandatory
    DESCRIPTION "The current status of the DCD lead (subrated FRI only).
                 Na is used for T1/E1 FRI.
                 - Get Operation:
                 This object is valid only if the port is subrated and DCE.
                 Otherwise, na is returned."
        ::= { frLportCnfEntry 34 }

frLportSrCTS OBJECT-TYPE
    SYNTAX      INTEGER {
                off (1),
                on  (2),
                na  (3)
        }
    ACCESS      read-only
    STATUS      mandatory
    DESCRIPTION "The current status of the CTS lead (subrated FRI only).
                 Na is used for T1/E1 FRI.
                 - Get Operation:
                 This object is valid only if the port is subrated and DCE.
                 Otherwise, na is returned."
        ::= { frLportCnfEntry 35 }

frLportSrDSR OBJECT-TYPE
    SYNTAX      INTEGER {
                off (1),
                on  (2),
                na  (3)
        }
    ACCESS      read-only
    STATUS      mandatory
    DESCRIPTION "The current status of the DSR lead (subrated FRI only).
                 Na is used for T1/E1 FRI.
                 - Get Operation:
                 This object is valid only if the port is subrated and DCE.
                 Otherwise, na is returned."
    ::= { frLportCnfEntry 36 }

frLportLoopBack OBJECT-TYPE
    SYNTAX      INTEGER {
                none   (1),
                local  (2)
        }
    ACCESS      read-only
    STATUS      mandatory
    DESCRIPTION "The loopback mode"
        ::= { frLportCnfEntry 37 }

frLportExtConFail OBJECT-TYPE
    SYNTAX      INTEGER {
                false (1),
                true  (2)
        }
    ACCESS      read-only
    STATUS      mandatory
    DESCRIPTION "The flag indicating if the connection with the external
                 device is lost."
        ::= { frLportCnfEntry 38 }


-- The following describes the MIB variables for the frLportStatTable. 
-- This table provides the manager access to the statistics available
-- on the logical ports. 

frLportStatTable OBJECT-TYPE
    SYNTAX      SEQUENCE OF FrLportStatEntry
    ACCESS      not-accessible
    STATUS      mandatory
    DESCRIPTION "The Frame Relay Logical Port Statistics table.  
                 This table ...."
    --DEFAULT   test-function   test-frlportstattable
    --DEFAULT   next-function   next-frlportstattable
    --DEFAULT   get-function    get-frlportstattable-%t
    --DEFAULT   view-mask       IPX-VIEW
    --DEFAULT   locator         FRLPORT-STAT-LOCATOR
        ::= { frServiceObjects 2  }

frLportStatEntry OBJECT-TYPE
    SYNTAX      FrLportStatEntry
    ACCESS      not-accessible
    STATUS      mandatory
    DESCRIPTION "An entry in the Frame Relay Logical Port Statistics table."
    INDEX   { frLportSlotIndex , frLportPortIndex }
        ::= { frLportStatTable 1  }

FrLportStatEntry ::=
    SEQUENCE {
        frLportRxBytes          Counter,
        frLportRxFrms           Counter,

        frLportTxBytes          Counter,
        frLportTxFrms           Counter,
        frLportTxFrmsFecns      Counter,
        frLportTxFrmsBecns      Counter,

        frLportCrcErrors        Counter,
        frLportBadFmts          Counter,
        frLportAlgnErrors       Counter,
        frLportIllegLengths     Counter,
        frLportDmaOvruns        Counter,
        frLportStatEnqUnis      Counter,
        frLportStatTxUnis       Counter,
        frLportUpdtTxUnis       Counter,
        frLportInvldReqCnts     Counter,
        frLportToutCntUnis      Counter,
        frLportSeqnmErrUnis     Counter,
        frLportUnknDlcis        Counter,
        frLportDeFrmsDrops      Counter,
        frLportStatEnqNnis      Counter,
        frLportStatRxNnis       Counter,
        frLportUpdtRxNnis       Counter,
        frLportToutCntNnis      Counter,
        frLportSeqnmErrNnis     Counter,
        frLportCllmTxFrms       Counter,
        frLportCllmTxBytes      Counter,
        frLportCllmRxFrms       Counter,
        frLportCllmRxBytes      Counter,
        frLportCllmFailures     Counter,
        frLportDscdQTxFrms      Counter,
        frLportDscdQTxBytes     Counter,
        frLportLmiFailFrms      Counter,
        frLportLmiFailBytes     Counter

    }


frLportRxBytes  OBJECT-TYPE
    SYNTAX      Counter 
    ACCESS      read-only
    STATUS      mandatory
    DESCRIPTION "Frame Relay Logical Port Rx bytes"
        ::= { frLportStatEntry 1  }

frLportRxFrms  OBJECT-TYPE
    SYNTAX      Counter 
    ACCESS      read-only
    STATUS      mandatory
    DESCRIPTION "Frame Relay Logical Port Rx frames"
        ::= { frLportStatEntry 2  }

frLportTxBytes  OBJECT-TYPE
    SYNTAX      Counter 
    ACCESS      read-only
    STATUS      mandatory
    DESCRIPTION "Frame Relay Logical Port Tx bytes"
        ::= { frLportStatEntry 3  }

frLportTxFrms  OBJECT-TYPE
    SYNTAX      Counter 
    ACCESS      read-only
    STATUS      mandatory
    DESCRIPTION "Frame Relay Logical Port Tx frames"
        ::= { frLportStatEntry 4  }

frLportTxFrmsFecns  OBJECT-TYPE
    SYNTAX      Counter 
    ACCESS      read-only
    STATUS      mandatory
    DESCRIPTION "Frame Relay Logical Port Tx FECN frames"
        ::= { frLportStatEntry 5  }

frLportTxFrmsBecns  OBJECT-TYPE
    SYNTAX      Counter 
    ACCESS      read-only
    STATUS      mandatory
    DESCRIPTION "Frame Relay Logical Port Tx BECN frames"
        ::= { frLportStatEntry 6  }

frLportCrcErrors  OBJECT-TYPE
    SYNTAX      Counter 
    ACCESS      read-only
    STATUS      mandatory
    DESCRIPTION "Frame Relay Logical Port CRC errors on received frames"
        ::= { frLportStatEntry 7  }

frLportBadFmts  OBJECT-TYPE
    SYNTAX      Counter 
    ACCESS      read-only
    STATUS      mandatory
    DESCRIPTION "Frame Relay Logical Port frames with illegal formats"
        ::= { frLportStatEntry 8  }

frLportAlgnErrors  OBJECT-TYPE
    SYNTAX      Counter 
    ACCESS      read-only
    STATUS      mandatory
    DESCRIPTION "Frame Relay Logical Port Alignment errors on received 
                 frames"
        ::= { frLportStatEntry 9  }

frLportIllegLengths  OBJECT-TYPE
    SYNTAX      Counter 
    ACCESS      read-only
    STATUS      mandatory
    DESCRIPTION "Frame Relay Logical Port Illegal length on received frames"
        ::= { frLportStatEntry 10  }

frLportDmaOvruns  OBJECT-TYPE
    SYNTAX      Counter 
    ACCESS      read-only
    STATUS      mandatory
    DESCRIPTION "Frame Relay Logical Port number of DMA overruns"
        ::= { frLportStatEntry 11  }

frLportStatEnqUnis  OBJECT-TYPE
    SYNTAX      Counter 
    ACCESS      read-only
    STATUS      mandatory
    DESCRIPTION "Frame Relay Logical Port status enquiry count. Transmit
                 protocol LMI UNI."
        ::= { frLportStatEntry 12  }

frLportStatTxUnis  OBJECT-TYPE
    SYNTAX      Counter 
    ACCESS      read-only
    STATUS      mandatory
    DESCRIPTION "Frame Relay Logical Port status transmit count. Transmit
                 protocol LMI UNI."
        ::= { frLportStatEntry 13  }

frLportUpdtTxUnis  OBJECT-TYPE
    SYNTAX      Counter 
    ACCESS      read-only
    STATUS      mandatory
    DESCRIPTION "Frame Relay Logical Port update transmit count. Transmit
                 protocol LMI UNI."
        ::= { frLportStatEntry 14  }

frLportInvldReqCnts  OBJECT-TYPE
    SYNTAX      Counter 
    ACCESS      read-only
    STATUS      mandatory
    DESCRIPTION "Frame Relay Logical Port invalid request count. 
                 UNI and NNI."
        ::= { frLportStatEntry 15  }

frLportToutCntUnis  OBJECT-TYPE
    SYNTAX      Counter 
    ACCESS      read-only
    STATUS      mandatory
    DESCRIPTION "Frame Relay Logical Port timeout count. Transmit
                 protocol LMI UNI."
        ::= { frLportStatEntry 16  }

frLportSeqnmErrUnis  OBJECT-TYPE
    SYNTAX      Counter 
    ACCESS      read-only
    STATUS      mandatory
    DESCRIPTION "Frame Relay Logical Port sequence number error. Transmit
                 protocol UNI."
        ::= { frLportStatEntry 17  }

frLportUnknDlcis  OBJECT-TYPE
    SYNTAX      Counter 
    ACCESS      read-only
    STATUS      mandatory
    DESCRIPTION "Frame Relay Logical Port number of unknown DLCI's on
                 received frames."
        ::= { frLportStatEntry 18  }

frLportDeFrmsDrops  OBJECT-TYPE
    SYNTAX      Counter 
    ACCESS      read-only
    STATUS      mandatory
    DESCRIPTION "Frame Relay Logical Port number of DE dropped frames." 
        ::= { frLportStatEntry 19  }

frLportStatEnqNnis  OBJECT-TYPE
    SYNTAX      Counter
    ACCESS      read-only
    STATUS      mandatory
    DESCRIPTION "Frame Relay Logical Port status enquiry count. Transmit
                 protocol LMI NNIs."
        ::= { frLportStatEntry 20  }

frLportStatRxNnis  OBJECT-TYPE
    SYNTAX      Counter
    ACCESS      read-only
    STATUS      mandatory
    DESCRIPTION "Frame Relay Logical Port status transmit count. Transmit
                 protocol LMI NNIs."
        ::= { frLportStatEntry 21  }

frLportUpdtRxNnis  OBJECT-TYPE
    SYNTAX      Counter 
    ACCESS      read-only
    STATUS      mandatory
    DESCRIPTION "Frame Relay Logical Port update transmit count. Transmit
                 protocol LMI NNIs."
        ::= { frLportStatEntry 22  }

frLportToutCntNnis  OBJECT-TYPE
    SYNTAX      Counter
    ACCESS      read-only
    STATUS      mandatory
    DESCRIPTION "Frame Relay Logical Port timeout count. Transmit
                 protocol LMI NNIs."
        ::= { frLportStatEntry 23  }

frLportSeqnmErrNnis  OBJECT-TYPE
    SYNTAX      Counter
    ACCESS      read-only
    STATUS      mandatory
    DESCRIPTION "Frame Relay Logical Port sequence number error. Transmit
                 protocol NNIs."
        ::= { frLportStatEntry 24  }

frLportCllmTxFrms  OBJECT-TYPE
    SYNTAX      Counter 
    ACCESS      read-only
    STATUS      mandatory
    DESCRIPTION "Frame Relay Logical Port CLLM (Foresight) Tx frames"
        ::= { frLportStatEntry 25  }

frLportCllmTxBytes  OBJECT-TYPE
    SYNTAX      Counter 
    ACCESS      read-only
    STATUS      mandatory
    DESCRIPTION "Frame Relay Logical Port CLLM (Foresight) Tx bytes"
        ::= { frLportStatEntry 26 }

frLportCllmRxFrms  OBJECT-TYPE
    SYNTAX      Counter 
    ACCESS      read-only
    STATUS      mandatory
    DESCRIPTION "Frame Relay Logical Port CLLM (Foresight) Rx frames"
        ::= { frLportStatEntry 27 }

frLportCllmRxBytes  OBJECT-TYPE
    SYNTAX      Counter 
    ACCESS      read-only
    STATUS      mandatory
    DESCRIPTION "Frame Relay Logical Port CLLM (Foresight) Rx bytes"
        ::= { frLportStatEntry 28 }

frLportCllmFailures  OBJECT-TYPE
    SYNTAX      Counter 
    ACCESS      read-only
    STATUS      mandatory
    DESCRIPTION "Frame Relay Logical Port CLLM (Foresight) failures"
        ::= { frLportStatEntry 29 }

frLportDscdQTxFrms  OBJECT-TYPE
    SYNTAX      Counter 
    ACCESS      read-only
    STATUS      mandatory
    DESCRIPTION "Frame Relay Logical Port discard queue Tx frames"
        ::= { frLportStatEntry 30 }

frLportDscdQTxBytes  OBJECT-TYPE
    SYNTAX      Counter 
    ACCESS      read-only
    STATUS      mandatory
    DESCRIPTION "Frame Relay Logical Port discard queue Tx bytes"
        ::= { frLportStatEntry 31 }

frLportLmiFailFrms  OBJECT-TYPE
    SYNTAX      Counter 
    ACCESS      read-only
    STATUS      mandatory
    DESCRIPTION "Frame Relay Logical Port LMI failure frames"
        ::= { frLportStatEntry 32 }

frLportLmiFailBytes  OBJECT-TYPE
    SYNTAX      Counter 
    ACCESS      read-only
    STATUS      mandatory
    DESCRIPTION "Frame Relay Logical Port LMI failure bytes"
        ::= { frLportStatEntry 33 }

--
-- The following describes the MIB variables for the atmPortTable.
-- This table provides the manager a detailed view of the ATM ports
-- available on the switch. 

atmPortTable OBJECT-TYPE
    SYNTAX      SEQUENCE OF AtmPortEntry
    ACCESS      not-accessible
    STATUS      mandatory
    DESCRIPTION "The ATM Port Configuration table."
    --DEFAULT   test-function   test-atmporttable
    --DEFAULT   next-function   next-atmporttable
    --DEFAULT   get-function    get-atmporttable-%t
    --DEFAULT   view-mask       BPX-VIEW 
        ::= { atmServiceObjects 1  }

atmPortEntry OBJECT-TYPE
    SYNTAX      AtmPortEntry
    ACCESS      not-accessible
    STATUS      mandatory
    DESCRIPTION "An entry in the ATM Port Configuration table."
    INDEX   { atmPortSlot , atmPortPort }
        ::= { atmPortTable 1  }

AtmPortEntry ::=
    SEQUENCE {
        atmPortSlot             INTEGER,
        atmPortPort             INTEGER,
        atmPortAdminStatus      INTEGER,
        atmPortOperStatus       INTEGER,
        atmPortType             INTEGER,
        atmPortIfType           INTEGER,
        atmPortSpeed            INTEGER,
        atmPortAxis             INTEGER,
        atmPortVcCount          INTEGER,
        atmPortFirstVcPtr       OBJECT IDENTIFIER,
        atmPortMetro            INTEGER,
        atmPortMgmtProto        INTEGER,
        atmPortIlmiVpi          INTEGER,
        atmPortIlmiVci          INTEGER,
        atmPortIlmiPollEnable   INTEGER,
        atmPortIlmiTrapEnable   INTEGER,
        atmPortIlmiPollIntrvl   INTEGER,
        atmPortIlmiErrorThresh  INTEGER,
        atmPortIlmiEventThresh  INTEGER,
        atmPortLmiVpi           INTEGER,
        atmPortLmiVci           INTEGER,
        atmPortLmiPollEnable    INTEGER,
        atmPortLmiStatEnqTimer  INTEGER,
        atmPortLmiUpdStatTimer  INTEGER,
        atmPortLmiStatEnqRetry  INTEGER,
        atmPortLmiUpdStatRetry  INTEGER,
        atmPortLmiPollTimer     INTEGER,
        atmPortPercUtil         INTEGER
    }

atmPortSlot OBJECT-TYPE
    SYNTAX      INTEGER (1..32)
    ACCESS      read-only
    STATUS      mandatory
    DESCRIPTION "The slot number"
        ::= { atmPortEntry 1  }

atmPortPort OBJECT-TYPE
    SYNTAX      INTEGER (1..2)
    ACCESS      read-only
    STATUS      mandatory
    DESCRIPTION "The port number"
        ::= { atmPortEntry 2  }

atmPortAdminStatus OBJECT-TYPE
    SYNTAX      INTEGER {
                up(1),
                down(2),
                modify(3),
                writeOnly(4)
    }
    ACCESS      read-write
    STATUS      mandatory
    DESCRIPTION "User requested state for port table row.  A user
                may Up or Down an existing port.  The user may also
                modify the characteristics of the port."
        ::= { atmPortEntry 3  }

atmPortOperStatus OBJECT-TYPE
    SYNTAX      INTEGER {
                inactive(1),
                active  (2),
                looped  (3),
                failed  (4),
                unknown (5)
    }
    ACCESS      read-only
    STATUS      mandatory
    DESCRIPTION "Actual state of the port."
        ::= { atmPortEntry 4  }

atmPortType OBJECT-TYPE
    SYNTAX      INTEGER {
                uni     (1),
                nni     (2)
    }
    ACCESS      read-write
    STATUS      mandatory
    DESCRIPTION "Indicates whether this is a UNI or NNI port.
                 The switch supports this operation only on a
                 per-card level, so changing one port changes
                 the other also.
                 The value of this object cannot be changed 
                 if there are active connections on the card."
        ::= { atmPortEntry 5  }

atmPortIfType OBJECT-TYPE
    SYNTAX      INTEGER {
                unknown (1),
                t3      (2),
                e3      (3),
                oc3-smf (4),
                oc3-mmf (5)
    }
    ACCESS      read-only
    STATUS      mandatory
    DESCRIPTION "The type of interface for this port."
        ::= { atmPortEntry 6  }

atmPortSpeed OBJECT-TYPE
    SYNTAX      INTEGER 
    ACCESS      read-only
    STATUS      mandatory
    DESCRIPTION "The speed of the port in cells per seconds."
        ::= { atmPortEntry 7  }

atmPortAxis OBJECT-TYPE
    SYNTAX      INTEGER {
                none  (1),
                t1    (2),
                e1    (3)
    }
    ACCESS      read-write
    STATUS      mandatory
    DESCRIPTION "Indicates port support for BASIS shelf. 
                 The value of this object cannot be changed 
                 if there are active connections on the port.
                 For ASI-2 the value of this object is 'none'.
                 An attempt to change the value of this object
                 on an ASI-2 will return a BadValue error."
        ::= { atmPortEntry 8  }

atmPortVcCount OBJECT-TYPE
    SYNTAX      INTEGER (0..1024)
    ACCESS      read-only
    STATUS      mandatory
    DESCRIPTION "The number of virtual connections that terminate on
                 this port. A port may have up to 1024 connections
                 allocated."
        ::= { atmPortEntry 9  }

atmPortFirstVcPtr OBJECT-TYPE
    SYNTAX      OBJECT IDENTIFIER
    ACCESS      read-only
    STATUS      mandatory
    DESCRIPTION "The object identifier denoting the first connection 
                endpoint associated with  this port. For current 
                implementation, this OID points to the first 
                connection on the port. It has a NULL OID value
                (i.e. { 0 0 }) if there is no connection on this
                port. The management station can retrieve all the
                information about the first connection by reading
                from row pointed to by this OID. Specifically, this
                OID specifies the first column of the appropriate row
                in the atmEndptTable."
        ::= { atmPortEntry 10  }

atmPortMetro OBJECT-TYPE
    SYNTAX      INTEGER {
                enable  (1),
                disable (2)
    }
    ACCESS      read-write
    STATUS      mandatory
    DESCRIPTION "Metro Data Cell Header Format. This object applies
                 to T3 non-axis ports. The value of this object is
                 set to disable by the switch every time that the
                 value of the object atmPortAxis changes to or from
                 'none'."
        ::= { atmPortEntry 11  }

atmPortMgmtProto OBJECT-TYPE
    SYNTAX      INTEGER {
                none (1),
                lmi  (2),
                ilmi (3)
    }
    ACCESS      read-write
    STATUS      mandatory
    DESCRIPTION "Indicates the port management protocol used for
                 this port."
        ::= { atmPortEntry 12 }

atmPortIlmiVpi OBJECT-TYPE
    SYNTAX      INTEGER (0..4095) 
    ACCESS      read-write
    STATUS      mandatory
    DESCRIPTION "The virtual path identifier for the ILMI protocol."
        ::= { atmPortEntry 13 }

atmPortIlmiVci OBJECT-TYPE
    SYNTAX      INTEGER (1..65535)
    ACCESS      read-write
    STATUS      mandatory
    DESCRIPTION "The virtual channel identifier for the ILMI protocol."
        ::= { atmPortEntry 14 }

atmPortIlmiPollEnable OBJECT-TYPE
    SYNTAX      INTEGER {
                enable (1),
                disable(2)
    }
    ACCESS      read-write
    STATUS      mandatory
    DESCRIPTION "Enable ILMI keep alive polling procedure."
        ::= { atmPortEntry 15 }

atmPortIlmiTrapEnable OBJECT-TYPE
    SYNTAX      INTEGER {
                enable (1),
                disable(2)
    }
    ACCESS      read-write
    STATUS      mandatory
    DESCRIPTION "if enabled the ILMI agent will send unsolicited
                 Trap PDUs."
        ::= { atmPortEntry 16 }

atmPortIlmiPollIntrvl OBJECT-TYPE
    SYNTAX      INTEGER (5..60)
    ACCESS      read-write
    STATUS      mandatory
    DESCRIPTION "The number of seconds between each keep alive
                 poll transmitted by the port (T491)."
        ::= { atmPortEntry 17 }

atmPortIlmiErrorThresh OBJECT-TYPE
    SYNTAX      INTEGER (1..10)
    ACCESS      read-write
    STATUS      mandatory
    DESCRIPTION "The number of keep alive polls that must fail
                 within a window of N492 polls, before the port
                 is placed in the failed state (N491)."
        ::= { atmPortEntry 18 }

atmPortIlmiEventThresh OBJECT-TYPE
    SYNTAX      INTEGER (1..10)
    ACCESS      read-write
    STATUS      mandatory
    DESCRIPTION "It specifies the number of keep alive polls
                 within which if N491 polls fail the port is
                 placed in the failed state (N492)."
        ::= { atmPortEntry 19 }

atmPortLmiVpi OBJECT-TYPE
    SYNTAX      INTEGER (0..4095) 
    ACCESS      read-write
    STATUS      mandatory
    DESCRIPTION "The virtual path identifier for the LMI protocol."
        ::= { atmPortEntry 20 }

atmPortLmiVci OBJECT-TYPE
    SYNTAX      INTEGER (1..65535)
    ACCESS      read-write
    STATUS      mandatory
    DESCRIPTION "The virtual channel identifier for the ILMI protocol."
        ::= { atmPortEntry 21 }

atmPortLmiPollEnable OBJECT-TYPE
    SYNTAX      INTEGER {
                enable (1),
                disable(2)
    }
    ACCESS      read-write
    STATUS      mandatory
    DESCRIPTION "if enable an Status Enquiry message is sent when 
                 the polling timer expires."
        ::= { atmPortEntry 22 }

atmPortLmiStatEnqTimer  OBJECT-TYPE
    SYNTAX      INTEGER (5..30)
    ACCESS      read-write
    STATUS      mandatory
    DESCRIPTION "Link integrity timer for the port (T393)."
        ::= { atmPortEntry 23 }

atmPortLmiUpdStatTimer  OBJECT-TYPE
    SYNTAX      INTEGER (5..30)
    ACCESS      read-write
    STATUS      mandatory
    DESCRIPTION "Update status timer for the port (T394)."
        ::= { atmPortEntry 24 }

atmPortLmiStatEnqRetry  OBJECT-TYPE
    SYNTAX      INTEGER (1..10)
    ACCESS      read-write
    STATUS      mandatory
    DESCRIPTION "The maximum number of times a Status Enquiry
                 message is retransmitted. A Status Enquiry
                 message is retransmitted when timer T393
                 expires (N394)."
        ::= { atmPortEntry 25 }

atmPortLmiUpdStatRetry  OBJECT-TYPE
    SYNTAX      INTEGER (1..10)
    ACCESS      read-write
    STATUS      mandatory
    DESCRIPTION "The maximum number of times an Update Status
                 message is retransmitted. An Update Status
                 message is retransmitted when timer T394
                 expires (N395)."
        ::= { atmPortEntry 26 }

atmPortLmiPollTimer  OBJECT-TYPE
    SYNTAX      INTEGER (5..30)
    ACCESS      read-write
    STATUS      mandatory
    DESCRIPTION "Polling timer (T396). If polling is enabled
                 a Status Enquiry message is sent when this 
                 timer expires."
        ::= { atmPortEntry 27 }

atmPortPercUtil OBJECT-TYPE
    SYNTAX      INTEGER {
                enable (1),
                disable(2)
    }
    ACCESS      read-write
    STATUS      mandatory
    DESCRIPTION "Percentage Utilization can be disabled or enabled. 
                 If the use of percent utilization is disabled, the 
                 bandwidth for the connections terminating on the port 
                 will be used to determine the port load.
                 If the use of percent utilization is enabled, the 
                 bandwidth for the connection is multiplied by the 
                 percent utilization for the connection to determine the 
                 port load."
        ::= { atmPortEntry 28 }


--
-- The following describes the MIB variables for the atmPortQueueTable.
-- This table provides the manager access to read and configure the
-- ATM port egress queues.

atmPortQueueTable OBJECT-TYPE
    SYNTAX      SEQUENCE OF AtmPortQueueEntry
    ACCESS      not-accessible
    STATUS      mandatory
    DESCRIPTION "The ATM port egress queue table."
    --DEFAULT   test-function   test-atmportqueuetable
    --DEFAULT   next-function   next-atmportqueuetable
    --DEFAULT   get-function    get-atmportqueuetable-%t
    --DEFAULT   view-mask       BPX-VIEW
        ::= { atmServiceObjects 2  }

atmPortQueueEntry OBJECT-TYPE
    SYNTAX      AtmPortQueueEntry
    ACCESS      not-accessible
    STATUS      mandatory
    DESCRIPTION "An entry in the ATM port queue table."
    INDEX   { atmPortSlot , atmPortPort , atmPortQueueIndex }
        ::= { atmPortQueueTable 1  }

AtmPortQueueEntry ::=
    SEQUENCE {
        atmPortQueueIndex        INTEGER,
        atmPortQueueAdminStatus  INTEGER,
        atmPortQueueType         INTEGER,
        atmPortQueueDepth        INTEGER,
        atmPortQueueClpHi        INTEGER,
        atmPortQueueClpLo        INTEGER,
        atmPortQueueEfciTh       INTEGER,
        atmPortQueueAlgorithm    INTEGER
    }

atmPortQueueIndex  OBJECT-TYPE
    SYNTAX      INTEGER (0..15)
    ACCESS      read-only
    STATUS      mandatory
    DESCRIPTION "Index into the port egress queue array of the
                 given port that uniquely identifies this queue.
                 if the value of the atmPortQueueType object 
                 is 'axis', then the value of this object also
                 specifies the Axis slot associated with this
                 queue."
        ::= { atmPortQueueEntry 1  }

atmPortQueueAdminStatus OBJECT-TYPE
    SYNTAX      INTEGER {
                modify(1),
                writeOnly(2)
    }
    ACCESS      read-write
    STATUS      mandatory
    DESCRIPTION "User requested state for this port queue table
                 row. The only operation supported in this table
                 is modify."
        ::= { atmPortQueueEntry 2  }

atmPortQueueType  OBJECT-TYPE
    SYNTAX      INTEGER {
                unknown (1),
                unused  (2),
                cbr     (3),
                abr     (4),
                vbr     (5),
                axis    (6)
    }
    ACCESS      read-only
    STATUS      mandatory
    DESCRIPTION "The type of the queue. If the type is 'axis',
                 then the atmPortQueueIndex specifes the Axis
                 slot associated with this queue."
        ::= { atmPortQueueEntry 3  }

atmPortQueueDepth  OBJECT-TYPE
    SYNTAX      INTEGER (0..11000)
    ACCESS      read-write
    STATUS      mandatory
    DESCRIPTION "The storage depth allocated to this queue in
                 block of cells. The block size is one cell for
                 T3/E3 and 64 cells for OC3. The aggregate of 
                 the queue depths for all queues cannot exceed
                 the maximum storage available for the port."
        ::= { atmPortQueueEntry 4  }

atmPortQueueClpHi  OBJECT-TYPE
    SYNTAX      INTEGER (0..100)
    ACCESS      read-write
    STATUS      mandatory
    DESCRIPTION "The CLP tagging activation threshold for this
                 queue expressed as a percentage of queue depth."
        ::= { atmPortQueueEntry 5  }

atmPortQueueClpLo  OBJECT-TYPE
    SYNTAX      INTEGER (0..100)
    ACCESS      read-write
    STATUS      mandatory
    DESCRIPTION "The CLP tagging deactivation threshold for this
                 queue expressed as a percentage of queue depth."
        ::= { atmPortQueueEntry 6  }
 
atmPortQueueEfciTh  OBJECT-TYPE
    SYNTAX      INTEGER (0..100)
    ACCESS      read-write
    STATUS      mandatory
    DESCRIPTION "The EFCI threshold for this queue expressed
                 as a percentage of queue depth."
        ::= { atmPortQueueEntry 7  }
 
atmPortQueueAlgorithm OBJECT-TYPE
    SYNTAX      INTEGER {
                off        (1),
                always     (2),
                ok         (3),
                minGuar    (4),
                minSmooth  (5),
                minDelay   (6) 
    }
    ACCESS      read-only
    STATUS      mandatory
    DESCRIPTION "The queue service algorithm:
                 off:        never serve
                 always:     always serve 
                 ok:         ok to serve, not minimum guaranteed
                 min-guar:   minimum guaranteed bw, no limit
                 min-smooth: minimum guaranteed bw, smoothed
                 min-delay:  minimum guaranteed bw, delay limited
                " 
        ::= { atmPortQueueEntry 8  }
 


--
-- The following describes the MIB variables for the atmPortStatTable.
-- This table provides the manager access to the statistics available
-- on the ATM ports.

atmPortStatTable OBJECT-TYPE
    SYNTAX      SEQUENCE OF AtmPortStatEntry
    ACCESS      not-accessible
    STATUS      mandatory
    DESCRIPTION "The ATM Port Statistics table."
    --DEFAULT   test-function   test-atmportstattable
    --DEFAULT   next-function   next-atmportstattable
    --DEFAULT   get-function    get-atmportstattable-%t
    --DEFAULT   view-mask       BPX-VIEW
        ::= { atmServiceObjects 3  }

atmPortStatEntry OBJECT-TYPE
    SYNTAX      AtmPortStatEntry
    ACCESS      not-accessible
    STATUS      mandatory
    DESCRIPTION "An entry in the ATM Port Statistics table."
    INDEX   { atmPortSlot , atmPortPort }
        ::= { atmPortStatTable 1  }

AtmPortStatEntry ::=
    SEQUENCE {
        atmPortStatUnknVpiVcis     Counter,
        atmPortStatBufferOvfls     Counter,
        atmPortStatNonZeroGfcs     Counter,
        atmPortStatIsuDiscards     Counter,
        atmPortStatIsuEmptys       Counter,
        atmPortStatAisRxs          Counter,
        atmPortStatFerfRxs         Counter,
        atmPortStatCellsRxs        Counter,
        atmPortStatClpRxs          Counter,
        atmPortStatEfciRxs         Counter,
        atmPortStatBcmRxs          Counter,
        atmPortStatCellsTxs        Counter,
        atmPortStatOamRxs          Counter,
        atmPortStatPayldErrs       Counter,
        atmPortStatClpTxs          Counter,
        atmPortStatEfciTxs         Counter,
        atmPortStatHdrDiscards     Counter,
        atmPortStatIlmiGetRxs      Counter,
        atmPortStatIlmiGetNextRxs  Counter,
        atmPortStatIlmiGetNextTxs  Counter,
        atmPortStatIlmiSetRxs      Counter,
        atmPortStatIlmiTrapRxs     Counter,
        atmPortStatIlmiGetRspRxs   Counter,
        atmPortStatIlmiGetTxs      Counter,
        atmPortStatIlmiGetRspTxs   Counter,
        atmPortStatIlmiTrapTxs     Counter,
        atmPortStatIlmiUnkRxs      Counter,
        atmPortStatLmiStatTxs      Counter,
        atmPortStatLmiUpdtStatTxs  Counter,
        atmPortStatLmiStatAckTxs   Counter,
        atmPortStatLmiStatEnqRxs   Counter,
        atmPortStatLmiStatEnqTxs   Counter,
        atmPortStatLmiStatRxs      Counter,
        atmPortStatLmiUpdStatRxs   Counter,
        atmPortStatLmiStatAckRxs   Counter
    }


atmPortStatUnknVpiVcis  OBJECT-TYPE
    SYNTAX      Counter
    ACCESS      read-only
    STATUS      mandatory
    DESCRIPTION "The number of cells discarded due to unknown
                 address."
        ::= { atmPortStatEntry 1  }

atmPortStatBufferOvfls OBJECT-TYPE
    SYNTAX      Counter
    ACCESS      read-only
    STATUS      mandatory
    DESCRIPTION "The number of times the port has incurred a
                 cell buffer overflow."
        ::= { atmPortStatEntry 2  }

atmPortStatNonZeroGfcs  OBJECT-TYPE
    SYNTAX      Counter
    ACCESS      read-only
    STATUS      mandatory
    DESCRIPTION "The number of non-zero GFC cells for a UNI
                 port. For a NNI port this value is 0." 
        ::= { atmPortStatEntry 3  }

atmPortStatIsuDiscards  OBJECT-TYPE
    SYNTAX      Counter
    ACCESS      read-only
    STATUS      mandatory
    DESCRIPTION "The count of cells discarded by the Ingress
                 Control Service Unit."
        ::= { atmPortStatEntry 4  }

atmPortStatIsuEmptys  OBJECT-TYPE
    SYNTAX      Counter
    ACCESS      read-only
    STATUS      mandatory
    DESCRIPTION "The Ingress Control Service Unit free list
                 empty count."
        ::= { atmPortStatEntry 5  }

atmPortStatAisRxs  OBJECT-TYPE
    SYNTAX      Counter
    ACCESS      read-only
    STATUS      mandatory
    DESCRIPTION "Total numbers of cells received with AIS."   
        ::= { atmPortStatEntry 6  }

atmPortStatFerfRxs  OBJECT-TYPE
    SYNTAX      Counter
    ACCESS      read-only
    STATUS      mandatory
    DESCRIPTION "Total numbers of cells received with FERF."   
        ::= { atmPortStatEntry 7  }

atmPortStatCellsRxs  OBJECT-TYPE
    SYNTAX      Counter
    ACCESS      read-only
    STATUS      mandatory
    DESCRIPTION "Total numbers of cells received."
        ::= { atmPortStatEntry 8  }

atmPortStatClpRxs  OBJECT-TYPE
    SYNTAX      Counter
    ACCESS      read-only
    STATUS      mandatory
    DESCRIPTION "numbers of cells received with CLP set."   
        ::= { atmPortStatEntry 9  }

atmPortStatEfciRxs  OBJECT-TYPE
    SYNTAX      Counter
    ACCESS      read-only
    STATUS      mandatory
    DESCRIPTION "Total numbers of cells received with EFCI set."   
        ::= { atmPortStatEntry 10 }

atmPortStatBcmRxs  OBJECT-TYPE
    SYNTAX      Counter
    ACCESS      read-only
    STATUS      mandatory
    DESCRIPTION "Total numbers of BCM cells received."   
        ::= { atmPortStatEntry 11 }

atmPortStatCellsTxs OBJECT-TYPE
    SYNTAX      Counter
    ACCESS      read-only
    STATUS      mandatory
    DESCRIPTION "Total numbers of cells transmitted."   
        ::= { atmPortStatEntry 12 }

atmPortStatOamRxs  OBJECT-TYPE
    SYNTAX      Counter
    ACCESS      read-only
    STATUS      mandatory
    DESCRIPTION "Total numbers of OAM cells received."
        ::= { atmPortStatEntry 13 }

atmPortStatPayldErrs  OBJECT-TYPE
    SYNTAX      Counter
    ACCESS      read-only
    STATUS      mandatory
    DESCRIPTION "Total numbers of cells discarded due to BIP-16."
        ::= { atmPortStatEntry 14 }

atmPortStatClpTxs  OBJECT-TYPE
    SYNTAX      Counter
    ACCESS      read-only
    STATUS      mandatory
    DESCRIPTION "Total numbers of cells transmitted with CLP set."
        ::= { atmPortStatEntry 15 }

atmPortStatEfciTxs  OBJECT-TYPE
    SYNTAX      Counter
    ACCESS      read-only
    STATUS      mandatory
    DESCRIPTION "Total numbers of cells transmitted with EFCI set."
        ::= { atmPortStatEntry 16 }

atmPortStatHdrDiscards  OBJECT-TYPE
    SYNTAX      Counter
    ACCESS      read-only
    STATUS      mandatory
    DESCRIPTION "Total numbers of cells discarded due to parity error."
        ::= { atmPortStatEntry 17 }

atmPortStatIlmiGetRxs  OBJECT-TYPE
    SYNTAX      Counter
    ACCESS      read-only
    STATUS      mandatory
    DESCRIPTION "ILMI Get requests received."
        ::= { atmPortStatEntry 18 }

atmPortStatIlmiGetNextRxs  OBJECT-TYPE
    SYNTAX      Counter
    ACCESS      read-only
    STATUS      mandatory
    DESCRIPTION "ILMI Get Next requests received."
        ::= { atmPortStatEntry 19 }

atmPortStatIlmiGetNextTxs  OBJECT-TYPE
    SYNTAX      Counter
    ACCESS      read-only
    STATUS      mandatory
    DESCRIPTION "ILMI Get Next requests transmitted."
        ::= { atmPortStatEntry 20 }

atmPortStatIlmiSetRxs  OBJECT-TYPE
    SYNTAX      Counter
    ACCESS      read-only
    STATUS      mandatory
    DESCRIPTION "ILMI Set requests received."
        ::= { atmPortStatEntry 21 }

atmPortStatIlmiTrapRxs  OBJECT-TYPE
    SYNTAX      Counter
    ACCESS      read-only
    STATUS      mandatory
    DESCRIPTION "ILMI Trap received."
        ::= { atmPortStatEntry 22 }

atmPortStatIlmiGetRspRxs  OBJECT-TYPE
    SYNTAX      Counter
    ACCESS      read-only
    STATUS      mandatory
    DESCRIPTION "ILMI Get Response messages received."
        ::= { atmPortStatEntry 23 }

atmPortStatIlmiGetTxs  OBJECT-TYPE
    SYNTAX      Counter
    ACCESS      read-only
    STATUS      mandatory
    DESCRIPTION "ILMI Get requests transmitted."
        ::= { atmPortStatEntry 24 }

atmPortStatIlmiGetRspTxs  OBJECT-TYPE
    SYNTAX      Counter
    ACCESS      read-only
    STATUS      mandatory
    DESCRIPTION "ILMI Get Response messages transmitted."
        ::= { atmPortStatEntry 25 }

atmPortStatIlmiTrapTxs  OBJECT-TYPE
    SYNTAX      Counter
    ACCESS      read-only
    STATUS      mandatory
    DESCRIPTION "ILMI Traps transmitted."
        ::= { atmPortStatEntry 26 }

atmPortStatIlmiUnkRxs  OBJECT-TYPE
    SYNTAX      Counter
    ACCESS      read-only
    STATUS      mandatory
    DESCRIPTION "Unknown PDU type received."
        ::= { atmPortStatEntry 27 }

atmPortStatLmiStatTxs  OBJECT-TYPE
    SYNTAX      Counter
    ACCESS      read-only
    STATUS      mandatory
    DESCRIPTION "LMI Status messages transmitted."
        ::= { atmPortStatEntry 28 }

atmPortStatLmiUpdtStatTxs  OBJECT-TYPE
    SYNTAX      Counter
    ACCESS      read-only
    STATUS      mandatory
    DESCRIPTION "LMI Update Status messages transmitted."
        ::= { atmPortStatEntry 29 }

atmPortStatLmiStatAckTxs  OBJECT-TYPE
    SYNTAX      Counter
    ACCESS      read-only
    STATUS      mandatory
    DESCRIPTION "LMI Status Acknowledge messages transmitted."
        ::= { atmPortStatEntry 30 }

atmPortStatLmiStatEnqTxs  OBJECT-TYPE
    SYNTAX      Counter
    ACCESS      read-only
    STATUS      mandatory
    DESCRIPTION "LMI Status Enquiry messages transmitted."
        ::= { atmPortStatEntry 31 }

atmPortStatLmiStatEnqRxs  OBJECT-TYPE
    SYNTAX      Counter
    ACCESS      read-only
    STATUS      mandatory
    DESCRIPTION "LMI Status Enquiry messages received."
        ::= { atmPortStatEntry 32 }

atmPortStatLmiStatRxs  OBJECT-TYPE
    SYNTAX      Counter
    ACCESS      read-only
    STATUS      mandatory
    DESCRIPTION "LMI Status messages received."
        ::= { atmPortStatEntry 33 }

atmPortStatLmiUpdStatRxs  OBJECT-TYPE
    SYNTAX      Counter
    ACCESS      read-only
    STATUS      mandatory
    DESCRIPTION "LMI Update Status messages received."
        ::= { atmPortStatEntry 34 }

atmPortStatLmiStatAckRxs  OBJECT-TYPE
    SYNTAX      Counter
    ACCESS      read-only
    STATUS      mandatory
    DESCRIPTION "LMI Status Acknowledge messages received."
        ::= { atmPortStatEntry 35 }


--
-- The voiceChannel Table
--

voiceChannelTable  OBJECT-TYPE 
    SYNTAX      SEQUENCE OF VoiceChannelEntry
    ACCESS      not-accessible
    STATUS      mandatory
    DESCRIPTION "The voice channel  table has channel specific 
        configuration information. This is available for each of the 
        voice channel."
    --DEFAULT   test-function   test-vochantable
    --DEFAULT   next-function   next-vochantable
    --DEFAULT   get-function    get-vochantable-%t
    --DEFAULT   view-mask       IPX-VIEW 
        ::= { voiceServiceObjects  1 }

voiceChannelEntry OBJECT-TYPE
    SYNTAX      VoiceChannelEntry
    ACCESS      not-accessible
    STATUS      mandatory
    DESCRIPTION "An entry in the voice Channel information table."
    INDEX   { voiceChannelSlotIndex, voiceChannelChannelIndex }
        ::= { voiceChannelTable 1 }

VoiceChannelEntry ::=
    SEQUENCE {
    voiceChannelSlotIndex         INTEGER,
    voiceChannelChannelIndex      INTEGER,
    voiceChannelAdminStatus       INTEGER,
    voiceChannelEndptPtr          OBJECT IDENTIFIER,
    voiceChannelIf                INTEGER,
    voiceChannelAdapVoice         INTEGER,
    voiceChannelDialType          INTEGER,
    voiceChannelDtSignallingDelay INTEGER,
    voiceChannelDtMinWink         INTEGER,
    voiceChannelDtPlayOutDelay    INTEGER,
    voiceChannelRecvSigABit       INTEGER,
    voiceChannelRecvSigBBit       INTEGER,
    voiceChannelRecvSigCBit       INTEGER,
    voiceChannelRecvSigDBit       INTEGER,
    voiceChannelXmitSigABit       INTEGER,
    voiceChannelXmitSigBBit       INTEGER,
    voiceChannelXmitSigCBit       INTEGER,
    voiceChannelXmitSigDBit       INTEGER,
    voiceChannelIfTypeName        INTEGER,
    voiceChannelIfOnhkABit        INTEGER,
    voiceChannelIfOnhkBBit        INTEGER,
    voiceChannelIfOnhkCBit        INTEGER,
    voiceChannelIfOnhkDBit        INTEGER,
    voiceChannelIfCondIndex       INTEGER,
    voiceChannelEchoCancel        INTEGER,
    voiceChannelEchoRtnLoss       INTEGER,
    voiceChannelEchoTone          INTEGER,
    voiceChannelEchoConv          INTEGER,
    voiceChannelEchoNlp           INTEGER,
    voiceChannelInGain            INTEGER,
    voiceChannelOutGain           INTEGER,
    voiceChannelUtil              INTEGER
}

voiceChannelSlotIndex    OBJECT-TYPE
    SYNTAX      INTEGER (1..32)
    ACCESS      read-only
    STATUS      mandatory
    DESCRIPTION " The Slot Number."
        ::= { voiceChannelEntry 1  }

voiceChannelChannelIndex     OBJECT-TYPE
    SYNTAX      INTEGER (1..32)
    ACCESS      read-only
    STATUS      mandatory
    DESCRIPTION "The channel number. This shall serve as the index to 
                 this table"
        ::= { voiceChannelEntry 2  }

voiceChannelAdminStatus OBJECT-TYPE
    SYNTAX      INTEGER    {
                create(1),
                modify(2),
                writeOnly(3)
        }
    ACCESS      read-write
    STATUS      mandatory
    DESCRIPTION "User requested operation for this table. The operations 
                 supported on this table are modify and create The existing 
                 interfaceTypes cannot be changed (Please refer to 
                 voiceChannelIfTypeName variable definition). For 
                 associating a channel with a new interfaceType, all the 
                 values of the columns specified in the Description clause 
                 of voiceChannelIfTypeName should be provided."
        ::= { voiceChannelEntry 3  }

voiceChannelEndptPtr    OBJECT-TYPE
    SYNTAX      OBJECT IDENTIFIER
    ACCESS      read-only
    STATUS      mandatory
    DESCRIPTION "Pointer to channel End point table. This may not 
                 necessarily have a value. In the case that there is no 
                 corresponding voiceChannelEntry in the endpoint table, 
                 this would be 0."
        ::= { voiceChannelEntry 4  }

voiceChannelIf OBJECT-TYPE
    SYNTAX      INTEGER {
                unknown (1),
                t1      (2),
                e1      (3)
        }
    ACCESS      read-only
    STATUS      mandatory
    DESCRIPTION "The type of the line interface associated with this
                 channel"
        ::= { voiceChannelEntry 5  }

voiceChannelAdapVoice OBJECT-TYPE
    SYNTAX      INTEGER {
                false(1),
                true(2)
        }
    ACCESS      read-write
    STATUS      mandatory
    DESCRIPTION "Determines whether the channel is configured for Adaptive 
                 voice. This feature must be configured at both ends of the 
                 channel. The adaptive voice feature must also be equipped at
                 each node terminating the connection. If the adaptive voice 
                 feature is enabled for a channel connection which is used 
                 for a 'c' or 'v' connection, VAD is automatically disabled 
                 on that channel when trunk bandwidth is available, and it 
                 is enabled when trunk bandwidth is needed.
                 By DEFAULT this is True. This variable is not applicable,
                 if the channel is used for signalling." 
        ::= { voiceChannelEntry 6  } 

voiceChannelDialType OBJECT-TYPE
    SYNTAX      INTEGER {
                inband(1),
                pulse(2),
                userConfigured(3)
        }
    ACCESS      read-write
    STATUS      mandatory
    DESCRIPTION "Information about dail type used on the channel. By default 
                 Inband dail type is used.  In case it is of type 
                 userConfigured, the related objects for which values need 
                 to be provided are :
                    voiceChannelSignallingDelay
                    voiceChannelMinWink
                    voiceChannelPlayOutDelay.
                 If the values for any of the above variables are not 
                 provided for User Configured Dial type, the current 
                 values in the Database shall be retained. Each of the 
                 variables can be set independently.
                 These hold good for the CDP and CIP cards. By default 
                 every voice connection is configured with Inband signalling.                 When the dialType is Inband or Pulse, these are the values 
                 which are allowed :

                 SignallingType                Inband     Pulse

                 voiceChannelSignallingDelay      96        96
                 voiceChannelMinWink              20        20
                 voiceChannelPlayOutDelay         200       200.
                 When the dial type is INBAND or PULSE SET on the related 
                 objects mentioned above are not allowed"
        ::= { voiceChannelEntry 7  } 

voiceChannelDtSignallingDelay    OBJECT-TYPE
    SYNTAX      INTEGER (30..96)
    ACCESS      read-write
    STATUS      mandatory
    DESCRIPTION "It is the signalling delay, in milliseconds (ms), to assign 
                 the user configurable dail type. The value specified is 
                 rounded to the closest multiple of 1.5 ms. The default 
                 value for
                 inband         -  96
                 pulse          -  96. When the dial type is Inband or 
                                       Pulse value for 
                 this object should not be provided."
        ::= { voiceChannelEntry 8  } 

voiceChannelDtMinWink OBJECT-TYPE
    SYNTAX      INTEGER (120..300)
    ACCESS      read-write
    STATUS      mandatory
    DESCRIPTION "It is the minimum wink, in milliseconds, to assign to 
                 the user configurable dial type. The value specified 
                 is rounded off to the nearest whole multiple of 3ms. The 
                 default value for
                 inband  - 20 
                 pulse  -  20.
                 When the dial type is Inband or Pulse value for this 
                 object should not be provided."
        ::= { voiceChannelEntry 9  } 

voiceChannelDtPlayOutDelay  OBJECT-TYPE
    SYNTAX      INTEGER (100..200)
    ACCESS      read-write
    STATUS      mandatory
    DESCRIPTION "It is the playout  delay, in milliseconds, assigned to the 
                 user configurable dial type. The value specified is rounded                  to the closest multiple of 1.5 second.
                 The default value for
                 inband  - 200
                 pulse  -  200.
                 When the dial type is Inband or Pulse value for this 
                 object should not be provided."
        ::= { voiceChannelEntry 10 }

voiceChannelRecvSigABit  OBJECT-TYPE
    SYNTAX       INTEGER {
                 zero (1),
                 one (2),
                 xmitTransparent(3),
                 donotXmit(4),
                 revSigBit(5)
        }
    ACCESS      read-write
    STATUS      mandatory
    DESCRIPTION "It represents the configuration of bit conversion to 
                 received signalling on a channel. The value is given as 
                 one of the enumeration above which have following meaning:
                 one(1) :  Signalling bit is 1
                 zero(2) : Signalling bit is 0
                 xmitTransparent(3) : Transmit signalling bit transparently
                 noXmit(4) : Don't transmit signalling bit
                 revSigBit(5) : Reverse/Inverse signalling bit. The default 
                 value is one. If the signalling is not used at all, the 
                 A B C and D bits have 1 1 0 1 values respectively. The 
                 initialization value is xmitTransparent(3)"
        ::= { voiceChannelEntry 11 }

voiceChannelRecvSigBBit  OBJECT-TYPE
    SYNTAX       INTEGER {
                 zero (1),
                 one (2),
                 xmitTransparent(3),
                 donotXmit(4),
                 revSigBit(5)
        }
    ACCESS      read-write
    STATUS      mandatory
    DESCRIPTION "It represents the configuration of bit conversion to 
                 received signalling on a channel. The value is given as 
                 one of the enumeration above which have following meaning:
                 one(1) :  Signalling bit is 1
                 zero(2) : Signalling bit is 0
                 xmitTransparent(3) : Transmit signalling bit transparently
                 donotXmit(4) : Don't transmit signalling bit
                 revSigBit(5) : Reverse/Inverse signalling bit. The default 
                 value is one. If the signalling is not used at all, the 
                 A B C and D bits have 1 1 0 1 values respectively. 
                 The initialization value is xmitTransparent(3)."
        ::= { voiceChannelEntry 12 }

voiceChannelRecvSigCBit  OBJECT-TYPE
    SYNTAX       INTEGER {
                 zero (1),
                 one (2),
                 xmitTransparent(3),
                 donotXmit(4),
                 revSigBit(5)
        }
    ACCESS      read-write
    STATUS      mandatory
    DESCRIPTION "It represents the configuration of bit conversion to 
                 received signalling on a channel. The value is given as 
                 one of the enumeration above which have following meaning:
                 one(1) :  Signalling bit is 1
                 zero(2) : Signalling bit is 0
                 xmitTransparent(3) : Transmit signalling bit transparently
                 donotXmit(4) : Don't transmit signalling bit
                 revSigBit(5) : Reverse/Inverse signalling bit. The default 
                 value is zero. If the signalling is not used at all, the 
                 A B C and D bits have 1 1 0 1 values respectively. The 
                 initialization value is xmitTransparent(3)"
        ::= { voiceChannelEntry 13 }

voiceChannelRecvSigDBit  OBJECT-TYPE
    SYNTAX       INTEGER {
                 zero (1),
                 one (2),
                 xmitTransparent(3),
                 donotXmit(4),
                 revSigBit(5)
        }
    ACCESS      read-write
    STATUS      mandatory
    DESCRIPTION "It represents the configuration of bit conversion to 
                 received signalling on a channel. The value is given 
                 as one of the enumeration above which have following 
                 meaning:
                 one(1) :  Signalling bit is 1
                 zero(2) : Signalling bit is 0
                 xmitTransparent(3) : Transmit signalling bit transparently
                 donoXmit(4) : Don't transmit signalling bit
                 revSigBit(5) : Reverse/Inverse signalling bit. The default 
                 value is one. If the signalling is not used at all, the 
                 A B C and D bits  have 1 1 0 1 values respectively. The 
                 initialization values is xmitTransparent(3)"
        ::= { voiceChannelEntry 14 }

voiceChannelXmitSigABit  OBJECT-TYPE
    SYNTAX       INTEGER {
                 zero (1),
                 one (2),
                 xmitTransparent(3),
                 donotXmit(4),
                 revSigBit(5)
        }
    ACCESS      read-write
    STATUS      mandatory
    DESCRIPTION "This allows the node to pass A  channel signalling bits 
                 through unchanged, or to invert / hold them at a given 
                 value for a CDP/CIP circuit line. It affects signalling 
                 bits in the transmit direction (eg. to the CPE / PABX).  
                 The value is given as one of the enumeration above which 
                 have following meaning:
                 one(1) :  Signalling bit is 1
                 zero(2) : Signalling bit is 0
                 xmitTransparent(3) : Transmit signalling bit transparently
                 donotXmit(4) : Don't transmit signalling bit
                 revSigBit(5) : Reverse/Inverse signalling bit. The default 
                 value is one. If the signalling is not used at all, the 
                 A B C and D bits have 1 1 0 1 values respectively. The 
                 initialization values is xmitTransparent(3)."
        ::= { voiceChannelEntry 15 }

voiceChannelXmitSigBBit  OBJECT-TYPE
    SYNTAX       INTEGER {
                 zero (1),
                 one (2),
                 xmitTransparent(3),
                 donotXmit(4),
                 revSigBit(5)
    }
    ACCESS      read-write
    STATUS      mandatory
    DESCRIPTION "This allows the node to pass B  channel signalling bits 
                 through unchanged, or to invert / hold them at a given 
                 value for a CDP/CIP circuit line. It affects signalling 
                 bits in the transmit direction (eg. to the CPE / PABX).  
                 The value is given as one of the enumeration above which 
                 have following meaning:
                 one(1) :  Signalling bit is 1
                 zero(2) : Signalling bit is 0
                 xmitTransparent(3) : Transmit signalling bit transparently
                 donotXmit(4) : Don't transmit signalling bit
                 revSigBit(5) : Reverse/Inverse signalling bit. The default 
                 value is one. If the signalling is not used at all, the 
                 A B C and D bits have 1 1 0 1 values respectively. The 
                 initialization values is xmitTransparent(3)"
        ::= { voiceChannelEntry 16 }

voiceChannelXmitSigCBit  OBJECT-TYPE
    SYNTAX       INTEGER {
                 zero (1),
                 one (2),
                 xmitTransparent(3),
                 donotXmit(4),
                 revSigBit(5)
        }
    ACCESS      read-write
    STATUS      mandatory
    DESCRIPTION "This allows the node to pass C  channel signalling bits
                 through unchanged, or to invert / hold them at a given
                 value for a CDP/CIP circuit line. It affects signalling
                 bits in the transmit direction (eg. to the CPE / PABX).
                 The value is given as one of the enumeration above which
                 have following meaning:
                 one(1) :  Signalling bit is 1
                 zero(2) : Signalling bit is 0
                 xmitTransparent(3) : Transmit signalling bit transparently
                 donotXmit(4) : Don't transmit signalling bit
                 revSigBit(5) : Reverse/Inverse signalling bit. The default
                 value is one. If the signalling is not used at all, the
                 A B C and D bits have 1 1 0 1 values respectively. The
                 initialization values is xmitTransparent(3)"
        ::= { voiceChannelEntry 17 }


voiceChannelXmitSigDBit  OBJECT-TYPE
    SYNTAX       INTEGER {
                 zero (1),
                 one (2),
                 xmitTransparent(3),
                 donotXmit(4),
                 revSigBit(5)
        }
    ACCESS      read-write
    STATUS      mandatory
    DESCRIPTION "This allows the node to pass D  channel signalling bits
                 through unchanged, or to invert / hold them at a given
                 value for a CDP/CIP circuit line. It affects signalling
                 bits in the transmit direction (eg. to the CPE / PABX).
                 The value is given as one of the enumeration above which
                 have following meaning:
                 one(1) :  Signalling bit is 1
                 zero(2) : Signalling bit is 0
                 xmitTransparent(3) : Transmit signalling bit transparently
                 donotXmit(4) : Don't transmit signalling bit
                 revSigBit(5) : Reverse/Inverse signalling bit. The default
                 value is one. If the signalling is not used at all, the
                 A B C and D bits have 1 1 0 1 values respectively. The
                 initialization values is xmitTransparent(3)"
        ::= { voiceChannelEntry 18 }

voiceChannelIfTypeName OBJECT-TYPE
    SYNTAX         INTEGER {
                   userConfig(1),
                   unConfig(2),
                   noSig(3),
                   forceSig(4),
                   twoWireENM(5),
                   fourWireENM(6),
                   fXO(7),
                   fXSGS(8),
                   fXSLS(9),
                   dP0(10),
                   dPT(11),
                   rP0(12),
                   rPT(13),
                   sDP0(14),
                   dX(15),
                   eT0(16),
                   pLAR(17),
                   pLR(18),
                   rD(19),
                   r1(20),
                   sSDC5A(21),
                   r2Backward(22),
                   r2Forward(23)
        }
    ACCESS      read-write 
    STATUS      mandatory
    DESCRIPTION "It represents the interface type assigned to a channel.
                 The following different types of interfaces are possbile:

    Number   InterfaceType       A    B    C    D  CondName

    1         {User Config,      U,   U,   N,   N,  a},
    2         {Unconfig,         U,   U,   N,   N,  a},
    3         {No Sig,           U,   U,   U,   U,  a},
    4         {Force Sig,        U,   U,   N,   N,  a},
    5         {2W E&M,           0,   X,   N,   N,  a},
    6         {4W E&M,           0,   X,   N,   N,  a},
    7         {FXO,              1,   1,   N,   N,  b},
    8         {FXS G/S,          0,   1,   N,   N,  c},
    9         {FXS L/S,          0,   X,   N,   N,  d},
    10        {DPO,              0,   X,   N,   N,  a},
    11        {DPT,              0,   X,   N,   N,  a},
    12        {RPO,              0,   X,   N,   N,  a},
    13        {RPT,              0,   X,   N,   N,  a},
    14        {SDPO,             0,   X,   N,   N,  a},
    15        {DX,               0,   X,   N,   N,  a},
    16        {ETO,              U,   U,   N,   N,  e},
    17        {PLAR,             U,   U,   N,   N,  d},
    18        {PLR,              0,   X,   N,   N,  a},
    19        {RD,               U,   U,   N,   N,  a},
    20        {R1 (SOCOTEL),     0,   N,   N,   N,  e},
    21        {SSDC5A,           1,   1,   0,   1,  f},
    22        {R2 (backward),    1,   1,   N,   N,  e},
    23        {R2 (forward),     1,   0,   N,   N,  d}

        Where 
        A B C D are the signalling bits corresponding to Onhook values 
        having the following meanings:
        0 meaning 0
        1 meaning 1
        X meaning donot Care
        U meaning unknown
        N meaning not used
        and the Conditioning templates can be any of a b c d e f types.

        If the IPX receives A B C D bits corresponding to the on-hook 
        values, that channel is known to be on-hook. Otherwise that 
        channel is known to be offhook.  Each interface except for 
        UserConfigured type has a pre-determined conditioning template 
        associated with it which are of 5 different types apart from 
        user configurable conditioning templates.
        Examples of valid values are any of the above interface number
        given above.
        If it is a userConfigured OR Forced Signalling (FCDSIG = 4) interface 
        type then the following variables need to be supplied: 
        voiceChannelIfOnhkABit
        voiceChannelIfOnhkBBit
        voiceChannelIfOnhkCBit
        voiceChannelIfOnhkDBit
        voiceChannelIfCondName.
        If any of the above variables are not provided with values then, the  
        current values in the data base is retained.In all other cases the
        values are as shown in the table above.
        The interface type is ignored for 'D' type connections.
        The default values for a channel:
        InterfaceType    A    B    C    D   CondName
        
        UnConfigured     U    U    N    N    a.
        If a pre-defined Interface type is chosen in a SET, values for the 
        other related objects should not be provided."

        ::= { voiceChannelEntry 19 }


voiceChannelIfOnhkABit OBJECT-TYPE
    SYNTAX      INTEGER  {
                zero(1),
                one(2),
                donotCare(3),
                unKnown (4),
                notUsed(5)
        }
    ACCESS      read-write
    STATUS      mandatory
    DESCRIPTION "It represents the value of A signalling bit, for which 
                 the IPX shall recognize a on-hook condition. The default 
                 value is unKnown(4). The value corresponding to pre-defined
                 Interface types have been given in the table in the 
                 'Description' clause of the object voiceChannelIfTypeName. 
                 If the interface type is pre-defined type, value is not 
                 provided for this object."
        ::= { voiceChannelEntry 20 }

voiceChannelIfOnhkBBit OBJECT-TYPE
    SYNTAX      INTEGER {
                zero(1),
                one(2),
                donotCare(3),
                unKnown (4),
                notUsed(5)
        }
    ACCESS      read-write
    STATUS      mandatory
    DESCRIPTION "It represents the value of B signalling bit, for which
                 the IPX shall recognize a on-hook condition. The default
                 value is unKnown(4). The value corresponding to pre-defined
                 Interface types have been given in the table in the 
                 'Description' clause of the object voiceChannelIfTypeName. 
                 If the interface type is pre-defined type, value is not 
                 provided for this object."
        ::= { voiceChannelEntry 21 }

voiceChannelIfOnhkCBit OBJECT-TYPE
    SYNTAX      INTEGER  {
                zero(1),
                one(2),
                donotCare(3),
                unKnown (4),
                notUsed(5)
        }
    ACCESS      read-write
    STATUS      mandatory
    DESCRIPTION "It represents the value of C signalling bit, for which
                 the IPX shall recognize a on-hook condition. The default
                 value is unKnown(4). The value corresponding to pre-defined
                 Interface types have been given in the table in the 
                 'Description' clause of the object voiceChannelIfTypeName. 
                 If the interface type is pre-defined type, value is not 
                 provided for this object."
        ::= { voiceChannelEntry 22 }

voiceChannelIfOnhkDBit OBJECT-TYPE
    SYNTAX      INTEGER  {
                zero(1),
                one(2),
                donotCare(3),
                unKnown (4),
                notUsed(5)
        }
    ACCESS      read-write
    STATUS      mandatory
    DESCRIPTION "It represents the value of D signalling bit, for which
                 the IPX shall recognize a on-hook condition. The default
                 value is unKnown(4). The value corresponding to pre-defined
                 Interface types have been given in the table in the 
                 'Description' clause of the object voiceChannelIfTypeName. 
                 If the interface type is pre-defined type, value is not 
                 provided for this object."
        ::= { voiceChannelEntry 23 }

voiceChannelIfCondIndex OBJECT-TYPE
    SYNTAX      INTEGER (1..32)
    ACCESS      read-write
    STATUS      mandatory
    DESCRIPTION "It represents the name of one of the condition criterion
                 templates defined in the voiceConditioningTable. The value 
                 corresponding to pre-defined interface Types have been 
                 given in the table in the 'Description' clause of the 
                 object voiceChannelIfTypeName. Currentely, only the 
                 pre-defined conditioning templates are supported. If the 
                 interface type is pre-defined type, value is not provided 
                 for this object."
        ::= { voiceChannelEntry 24 }

voiceChannelEchoCancel  OBJECT-TYPE
    SYNTAX      INTEGER {
                enable(1),
                disable(2)
        }
    ACCESS      read-write
    STATUS      mandatory
    DESCRIPTION "This represents the integrated echo canceller channel 
        parameters associated with the specified voice channel. By 
        default it is disabled.  If it has to be enabled from a 
        disabled state then valued for following variables have to be 
        supplied:
        Name                        Value       Description

        voiceChannelEchoRtnLoss    High/Low    Set the echo return loss
                                               to High / Low.
        voiceChannelEchoTone       Enable/     Enables or disables the
                                   Disable     tone disabler.

        voiceChannelEchoConv       Enable/     Enables or disables 
                                   Disable     convergence.

        voiceChannelEchoNlp        Enable/     Enables or disables 
                                   Disable     non-linear processing.
        If any one of the variables are not specified, the previous 
        value of that variable shall be retained. If the Echo Cancel
        is to be SET to disable, values for the related parameters are not 
        allowed in the SET."
        ::= { voiceChannelEntry 25 }

voiceChannelEchoRtnLoss OBJECT-TYPE
    SYNTAX      INTEGER {
                low(1),
                high(2)
        }
    ACCESS      read-write
    STATUS      mandatory
    DESCRIPTION "This represents the Echo Return Loss if the echo canceller 
                 is enabled. The default value is High(2). If the Echo Cancel
                 is to be SET to disable, values for the related parameters 
                 are not allowed in the SET."
        ::= { voiceChannelEntry 26 }

voiceChannelEchoTone   OBJECT-TYPE
    SYNTAX      INTEGER {
                enable(1),
                disable(2)
        }
    ACCESS      read-write
    STATUS      mandatory
    DESCRIPTION "This represents whether the Tone disabler  is enabled. The 
                 default value is Enable(1). If the Echo Cancel
                 is to be SET to disable, values for the related parameters 
                 are not allowed in the SET."
        ::= { voiceChannelEntry 27 }

voiceChannelEchoConv    OBJECT-TYPE
    SYNTAX      INTEGER {
                enable(1),
                disable(2)
        }
    ACCESS      read-write
    STATUS      mandatory
    DESCRIPTION "This represents whether the Echo Convergence is enabled. 
                 The default  value is Enable(1). If the Echo Cancel
                 is to be SET to disable, values for the related parameters 
                 are not allowed in the SET."
        ::= { voiceChannelEntry 28 }

voiceChannelEchoNlp     OBJECT-TYPE
    SYNTAX      INTEGER {
                enable(1),
                disable(2)
        }
    ACCESS      read-write
    STATUS      mandatory
    DESCRIPTION "This represents whether the NonLinear processing is 
                 enabled. The default  value is Enable(1). If the Echo 
                 Cancel is to be SET to disable, values for the related 
                 parameters are not allowed in the SET."
        ::= { voiceChannelEntry 29 }

voiceChannelInGain OBJECT-TYPE
    SYNTAX      INTEGER (0..14)
    ACCESS      read-write
    STATUS      mandatory
    DESCRIPTION "This variable represents the amount of gain inserted at 
                 the receiver side of a CDP / CIP circuit line on voice 
                 connections.  The gain is specified in decibels to be 
                 assigned to the channel. The gain can  be configured  
                 between +6 dB and -8 dB. By default it is zero."
        ::= { voiceChannelEntry 30 }

voiceChannelOutGain OBJECT-TYPE
    SYNTAX      INTEGER (0..14)
    ACCESS      read-write
    STATUS      mandatory
    DESCRIPTION "This variable represents the amount of gain inserted at the 
                 transmit side of a CDP / CIP circuit line on voice 
                 connections. The gain is specified in decibels to be 
                 assigned to the channel. The gain can  be configured  
                 between +6 dB and -8 dB. By default it is zero."
        ::= { voiceChannelEntry 31 }

voiceChannelUtil OBJECT-TYPE
    SYNTAX      INTEGER (0..100)
    ACCESS      read-write
    STATUS      mandatory
    DESCRIPTION "Represents the percentage of utilization of this channel.  
                 This object informs the system software of the expected 
                 utilization rate of connections   with traffic depdendent 
                 compression algorithm. For voice connections with VAD.
                 Acceptable values are in the range of 0 to 100. The default 
                 value for voice is 40."
        ::= { voiceChannelEntry 32 }



--
-- This object is used for creating PVCs (connections).  The following
-- steps are required for creating PVCs (this example creates a
-- frame relay PVC):
--
--  1) Obtain the current value of connNextEndptIndex.
--  2) Create a new entry in the frEndptTable:
--     a. Set frEndptAdminStatus to create using index value 
--        obtained from connNextEndptIndex.
--     b. Set the values of frEndptDesc and frOtherEndptDesc
--        appropriately.  For example to creat a  from NodeA in domain
--        D1 using Frame Relay end-point 12.1.100 to NodeB in domain D2
--        with Frame Relay end-point 4.2.100:
--              Set frEndptDesc to string      12.1.100
--              Set frOtherEndptDesc to string D2.NodeB.4.2.100
--     c. Optionally Set the values of the input and output bandwidth
--        parameters.
--     d. Optionally Set the values of the other PVC options.
--  3) Issue a management protocol SET operation for the newly built
--     entry.
--
-- Once complete, a new row in the frEndptTable will exist with
-- the value obtained from connNextEndptIndex as the INDEX, and a new
-- row in the connTable will exist.  The connTable row is used to
-- manipulate the state of the connection, obtain current status of
-- the connection, and to obtain routing information about the connection.
--
-- To delete the connection, modify the frEndptAdminStatus object in the
-- corresponding end-point to "delete", and perform a management protocol
-- SET operation on the entry.  
--

connNextEndptIndex OBJECT-TYPE
    SYNTAX      INTEGER 
    ACCESS      read-only
    STATUS      mandatory
    DESCRIPTION "This object contains an appropriate value to be used
                 when creating entries in the connection specific
                 end-point tables (e.g. frEndptTable).  A value
                 of minus one (-1) indicates that no unassigned entries are
                 available.  To obtain the connNextEndptIndex value
                 for a new entry, the manager issues a management protocol
                 retrieval operation to obtain the current value of
                 this object.  After each retrieval, the agent should
                 modify the value to the next unassigned index."
    --DEFAULT    get-function get-conn-nextendptindex
        ::= { switchConnection 1  }


-- This object contains the value of the request id for the newest
-- entry in the error status table. Many management applications
-- have no knowledge of the request ids used by the SNMP engine.
-- These applications can get the value of this object and then
-- use it to retrieve the error status for the last SET operation.

errStatusLastIndex  OBJECT-TYPE
    SYNTAX      INTEGER 
    ACCESS      read-only
    STATUS      obsolete 
    DESCRIPTION "If at least one entry exists in the error status table
                 for the given manager, the value of this object contains
                 the index corresponding to the last entry. If no entry
                 exists in the error status table for the given manager
                 the value of this object is -1."
    --DEFAULT    get-function get-err-lastindex
        ::= { switchConnection 2  }


--
-- The following table is used to maintain status information about
-- SNMP SET requests from a Manager.  When an SNMP SET completes, an 
-- entry is created.  In addition to successful status, the manager
-- is provided information associated with any failed requests. This
-- table is indexed by request ID.  The request Id is the SNMP PDU 
-- identifier associated with the failed request.
--
-- Currently a limit of 10 entries are imposed on this table. Each
-- manager is allowed to access it's own table.  Individual manager
-- access is determined by IP address.
--
errStatusTable OBJECT-TYPE 
    SYNTAX      SEQUENCE OF ErrStatusTableEntry
    ACCESS      not-accessible
    STATUS      deprecated 
    DESCRIPTION "A List of Error Statuses for a given SNMP Manager"
    --DEFAULT   test-function   test-errtable
    --DEFAULT   next-function   next-errtable
    --DEFAULT   get-function    get-errtable-%t
        ::= { switchConnection 3  }

errStatusTableEntry OBJECT-TYPE
    SYNTAX      ErrStatusTableEntry
    ACCESS      not-accessible
    STATUS      deprecated 
    DESCRIPTION "A General Error Status Entry."
    INDEX   { errReqId }
        ::= { errStatusTable 1  }

ErrStatusTableEntry ::=
    SEQUENCE {
        errReqId                INTEGER,    
        errCode                 INTEGER,
        errStatusDesc           DisplayString
    }


errReqId OBJECT-TYPE
    SYNTAX      INTEGER 
    ACCESS      read-only
    STATUS      mandatory
    DESCRIPTION "This object contains the PDU request ID associated with
                 the error." 
        ::= { errStatusTableEntry 1  }

errCode OBJECT-TYPE
    SYNTAX      INTEGER {
                success(1),
                existErr(2),
                syntaxErr(3),
                resourceErr(4),
                databaseLocked(5),
                otherErr(6),
                wrongType(7),
                wrongLength(8),
                wrongEncoding(9),
                wrongValue(10),
                noCreation(11),
                inconsistentValue(12),
                resourceUnavailable(13),
                commitFailed(14),
                undoFailed(15),
                authorizationError(16),
                notWritable(17),
                inconsistentName(18),
                featureDisabled(19),
                m32Problem(20),
                sarProblem(21),
                bnmProblem(22),
                ascUpdFailed(23),
                lineEnabled(24),
                lineDisabled(25),
                lmMismatch(26),
                lineHasPorts(27),
                portEnabled(28),
                portDisable(29),
                portHasChan(30),
                chanEnabled(31),
                chanDisabled(32),
                dlciEnabled(33),
                dlciDisabled(34)
        }
    ACCESS      read-only
    STATUS      mandatory
    DESCRIPTION "This object contains an error status code used by
                 the manager to take automated corrective actions
                 when requests encounter failures. If no error is
                 encountered, a successful status is provided."
        ::= { errStatusTableEntry 2  }

errStatusDesc OBJECT-TYPE
    SYNTAX      DisplayString
    ACCESS      read-only
    STATUS      mandatory
    DESCRIPTION "This object contains error status information for failed
                 SETS to one or more objects in frEndptTable and/or
                 vcTable. This object is updated only on failed SETS.
                 Since the SNMP standard allows only limited number of
                 error status returns, the managers can retrieve this
                 variable to get additional information on a 
                 failed SET. Typically this object will contain 
                 information specifiying date, type of operation (SET or
                 GET), current SNMP table (connTable, frEndptTable,... etc) 
                 and additional error information."
        ::= { errStatusTableEntry 3  }
 

--
-- This is the table describing all the connections associated with 
-- this managed entity.  The endpoints (virtual circuits) related to
-- these connections are defined in connection type-specific tables.
--
-- This table contains entries for existing connections.  These
-- entries can be viewed for the purpose of obtaining current information
-- about the managed entities connections:
--
--  1) connLclEndptDesc describes the local end-point for the connection.
--     Via this description one can obtain local domain, nodename, and
--     connection specific identifiers (e.g. slot, port, and address).
--  2) connRmtEndptDesc describes the remote end-point for the connection.
--     Via this description one can obtain remote domain, nodename, and
--     connection specific identifiers (e.g. slot, port, and address).
--  3) connOeIndex allows a manager to obtain information about the
--     connection from the remote node viewpoint.  This information
--     can be obtained by querying the remote node's connTable using
--     connOeIndex as the key INDEX.
--  4) connAdminStatus allows the connection to have it's state
--     changed from up to down, modify it's class of service, or
--     configure the preffered route of the connection.
--  5) connOperStatus contains the current status of the connection.
--     If the status is "failed", connNoRouteFoundFailure, connBumpFailure,
--     connEndPointFailure, and connTestFailure give more details about the
--     failure.
--  6) connFirstEndptPtr is an object identifier pointer to obtain a row 
--     in the end-point table that describes the local virtual circuit 
--     end-point.
--     Using the connType object, it is known what type of table this is
--     pointing to.  For example, this may point to an entry in the
--     frEndptTable for connections with vcType of frame-relay.
--     It is through the end-point specific tables that more
--     information such as configuration and statistics can be obtained.
--     Configuration of the connection is accomplished via modification
--     of the entry in the end-point specific table.  For bundled or grouped
--     connections, this object identifier points to the first end-point
--     of the bundle or group.
--  7) connCurrRouteDesc describes the current route being used by this
--     connection.  All hops of the route are specified.
--  8) connPrefRouteDesc describes the preferred route being used by this
--     connection.  All hops of the route are specified.
--  9) connMstOSpacePkts provides the minimum packet load available on the
--     current path of this connection in master -> slave direction.
-- 9.1)connMstOSpaceCells provides the minimum cell load available on the
--     current path of this connection in master -> slave direction.
--  10) connMstOSpaceBdaCmax provides the minimum BData A Cmax available on
--      current path of this connection in master -> slave direction.
--  11) connMstOSpaceBdbCmax provides the minimum BData B Cmax available on
--      current path of this connection in master -> slave direction.
--  12) connSlvOSpacePkts provides the minimum packet load available on the
--      current path of this connection in slave -> master direction.
-- 12.1)connSlvOSpaceCells provides the minimum cell load available on the
--      current path of this connection in slave -> master direction.
--  13) connSlvOSpaceBdaCmax provides the minimum BData A Cmax available on
--      current path of this connection in slave -> master direction.
--  14) connSlvOSpaceBdbCmax provides the minimum BData B Cmax available on
--      current path of this connection in slave -> master direction.
--  

connTable OBJECT-TYPE 
    SYNTAX      SEQUENCE OF ConnTableEntry
    ACCESS      not-accessible
    STATUS      mandatory
    DESCRIPTION "A List of Connection Virtual Circuit Entries"
    --DEFAULT   test-function   test-conntable
    --DEFAULT   next-function   next-conntable
    --DEFAULT   get-function    get-conntable-%t
        ::= { switchConnection 4  }

connTableEntry OBJECT-TYPE
    SYNTAX      ConnTableEntry
    ACCESS      not-accessible
    STATUS      mandatory
    DESCRIPTION "A General Connection Entry"
    INDEX   { connIndex }
        ::= { connTable 1  }

ConnTableEntry ::=
    SEQUENCE {
        connIndex                INTEGER,    
        connLclEndptDesc         DisplayString,
        connType                 INTEGER,

        connOeIndex              INTEGER,
        connRmtEndptDesc         DisplayString,
        
        connMasterFlag           INTEGER,
        connClassOfService       INTEGER,

        connGroupFlag            INTEGER,

        connAdminStatus          INTEGER,
        connOperStatus           INTEGER,

        connNoRouteFoundFailure  INTEGER,
        connBumpFailure          INTEGER,    

        connFirstEndptPtr        OBJECT IDENTIFIER,

        connCurrRouteDesc        DisplayString,
        connPrefRouteDesc        DisplayString,

        connMstOSpacePkts        INTEGER,
        connMstOSpaceCells       INTEGER,
        connMstOSpaceBdaCmax     INTEGER,
        connMstOSpaceBdbCmax     INTEGER,
        connSlvOSpacePkts        INTEGER,
        connSlvOSpaceCells       INTEGER,
        connSlvOSpaceBdaCmax     INTEGER,
        connSlvOSpaceBdbCmax     INTEGER,
        connIcaRTD               INTEGER,
        connGroupDesc            DisplayString
    }

connIndex OBJECT-TYPE
    SYNTAX      INTEGER (0..1999)
    ACCESS      read-only
    STATUS      mandatory
    DESCRIPTION "Connection Table Index for this connection."
        ::= { connTableEntry 1  }

connLclEndptDesc OBJECT-TYPE
    SYNTAX      DisplayString
    ACCESS      read-write
    STATUS      mandatory
    DESCRIPTION "Description for Local VC end-point.  Contains
                 information about the domain, nodename, slot,
                 port, and address value for the end-point.  For
                 example, D1.Node1.12.1.100.200, is a valid description.
                 For Frame Relay groups, the domain, remote nodename,
                 and groupid are given, for example D1.Node2.1 is
                 valid."
        ::= { connTableEntry 2  }

connType OBJECT-TYPE
    SYNTAX      INTEGER {
                frameRelay(1),
                atf(2),
                atm(3),
                voice(4),
                unknown(5)
        }
    ACCESS      read-only
    STATUS      mandatory
    DESCRIPTION "Connection type"
        ::= { connTableEntry 3  }

connOeIndex OBJECT-TYPE
    SYNTAX      INTEGER (0..1999)
    ACCESS      read-only
    STATUS      mandatory
    DESCRIPTION "Index into remote node's connTable for this connection
                 end-point."
        ::= { connTableEntry 4  }

connRmtEndptDesc OBJECT-TYPE
    SYNTAX      DisplayString
    ACCESS      read-write
    STATUS      mandatory
    DESCRIPTION "Description for Remote VC end-point.  Contains
                 information about the domain, nodename, slot,
                 port, and address value for the end-point.  For
                 example, D2.Node2.10.1.100.200, is a valid description.
                 This object contains no information for Frame Relay
                 connection groups."
        ::= { connTableEntry 5  }

connMasterFlag OBJECT-TYPE
    SYNTAX      INTEGER {
                false(1),
                true(2)
        }
    ACCESS      read-only
    STATUS      mandatory
    DESCRIPTION "Specifies whether this end-point is the owner of
                 the connection."
        ::= { connTableEntry 6  }

connClassOfService OBJECT-TYPE
    SYNTAX      INTEGER (0..15)
    ACCESS      read-write
    STATUS      mandatory
    DESCRIPTION "A class of service for this connection.  The lower
                 the class value, the higher the routing priority
                 of the connection."
        ::= { connTableEntry 7  }

connGroupFlag OBJECT-TYPE
    SYNTAX      INTEGER {
                false(1),
                true(2)
        }
    ACCESS      read-only
    STATUS      mandatory
    DESCRIPTION "Specifies whether this is a grouped connection.  In
                 the grouped connection case, the connFirstEndptPtr object
                 is a pointer to a list of end-points in this group."
        ::= { connTableEntry 8  }

connAdminStatus OBJECT-TYPE
    SYNTAX      INTEGER {
                up(1),
                down(2),
                modify(3),
                writeOnly(4),
                createGroup(5),
                deleteGroup(6)
        }
    ACCESS      read-write
    STATUS      mandatory
    DESCRIPTION "User requested state for connection.  A user can change
                 the state of the connection to up or down.  The user is
                 also allowed to modify the connections class of service or
                 preferred route. The connOperStatus object maintains the 
                 current status of the connection."
        ::= { connTableEntry 9  }

connOperStatus OBJECT-TYPE
    SYNTAX      INTEGER {
                ok(1),
                okPendingDown(2),
                down(3),
                failed(4),
                okPendingRoute(5),
                unknown(6)
        }
    ACCESS      read-only
    STATUS      mandatory
    DESCRIPTION "Actual state of the connection.  If the state is failed,
                 then look to the objects connNoRouteFoundFailure,
                 and connBumpFailure to determine reason for failure."
        ::= { connTableEntry 10  }

connNoRouteFoundFailure OBJECT-TYPE
    SYNTAX      INTEGER {
                false(1),
                true(2)
        }
    ACCESS      read-only
    STATUS      mandatory
    DESCRIPTION "Connection is failed is because no route to the
                 remote end-point could be found."
        ::= { connTableEntry 11  }

connBumpFailure OBJECT-TYPE
    SYNTAX      INTEGER {
                false(1),
                true(2)
        }
    ACCESS      read-only
    STATUS      mandatory
    DESCRIPTION "Connection is failed because of insufficient bandwidth
                 to route to the remote end-point.  This may have also
                 been caused because a higher priority connection took
                 this connections bandwidth.  A higher priority connection
                 is one with the lowest class of service (COS)."
        ::= { connTableEntry 12  }

connFirstEndptPtr OBJECT-TYPE
    SYNTAX      OBJECT IDENTIFIER
    ACCESS      read-only
    STATUS      mandatory
    DESCRIPTION "Pointer to end-point specific information.  Using this
                 pointer the user can obtain configuration and statistical
                 information about the connection.  Specifically, this
                 object identifier specifies the MIB tree identification of
                 the first column of the appropriate end-point table row."
        ::= { connTableEntry 13  }

connCurrRouteDesc OBJECT-TYPE
    SYNTAX      DisplayString ( SIZE (0..255) )
    ACCESS      read-only
    STATUS      mandatory
    DESCRIPTION "Descriptor of the current route (all hops specified).
                 Descriptor gives information about the domain, nodename, 
                 slot, and possibly a port for each hop in the route.  For 
                 example, Node1 15--15Node2 is a valid route specifying a
                 terrestrial link between Node1 slot 15 and Node2 slot 15.
                 Inter-domain connection's routes will append the remote
                 domain and nodename of the terminating endpoint."
        ::= { connTableEntry 14  }

connPrefRouteDesc OBJECT-TYPE
    SYNTAX      DisplayString ( SIZE (0..255) )
    ACCESS      read-write
    STATUS      mandatory
    DESCRIPTION "Descriptor of the preferred route (all hops specified).
                 Descriptor gives information about the domain, nodename, 
                 slot, and possibly a port for each hop in the route.  For 
                 example, Node1 15--15Node2 is a valid route specifying a
                 terrestrial link between Node1 slot 15 and Node2 slot 15.
                 While doing a SET operation the following general format
                 for specifying a preferred route should be used:
                     (<node-name>.<TRK>[.0])* - <node-name>
                     (<node-name>.<slot.port>)* - <node-name>
                 Some more valid descriptions are:
                     1) Node1.15.1 - Node2.13.1 - Node3
                     2) Node1.15.1-Node2.13.1-Node3
                     3) Node1.15   - Node2.12   - Node3.15   - Node4
                     4) Node1.15.0 - Node2.12.0 - Node3.15.0 - Node4

                 NOTE: a> (...)* notation means the description inside
                          parenthesis may repeat any number of times,
                          only limited by the total length which is 255
                          and the [...] notation signifies that it is
                          optional.
                       b> 1) & 2) are equivalent so are 3) & 4).
                       c> Even GET preferred route description will
                          be made consistent with that of SET operation
                          in the future releases.
                       d> An empty string (null or string of blank spaces)
                          will clear the pref route description equivalent
                          to delete pref route."
        ::= { connTableEntry 15  }

connMstOSpacePkts OBJECT-TYPE
    SYNTAX      INTEGER (0..2147483647) 
    ACCESS      read-only
    STATUS      mandatory
    DESCRIPTION "This variable provides the minimum packet load 
                 available on the current path of this connection 
                 in master->slave direction. This variable
                 is determined by comparing available bandwidth on
                 every trunk on which the connection is currently 
                 routed and reporting the minimum available bandwidth. 
                 For interdomain connections this value represents
                 available bandwidth through all domains. This variable
                 is meaningful for routed connections only. 
                 These values are returned in packets per second."
        ::= { connTableEntry 16  }

connMstOSpaceCells OBJECT-TYPE
    SYNTAX      INTEGER (0..2147483647)
    ACCESS      read-only
    STATUS      mandatory
    DESCRIPTION "This variable provides the minimum cell load 
                 available on the current path of this connection 
                 in master->slave direction. This variable
                 is determined by comparing available bandwidth on
                 every trunk on which the connection is currently 
                 routed and reporting the minimum available bandwidth. 
                 For interdomain connections this value represents
                 available bandwidth through all domains. This variable
                 is meaningful for routed connections only. 
                 These values are returned in cells per second."
        ::= { connTableEntry 17  }

connMstOSpaceBdaCmax OBJECT-TYPE
    SYNTAX      INTEGER (0..65534)
    ACCESS      read-only
    STATUS      mandatory
    DESCRIPTION "This variable provides the minimum BData A Cmax 
                 available on the current path of this connection 
                 in master->slave direction. This variable
                 is determined by comparing available BData A Cmax on
                 every trunk on which the connection is currently 
                 routed and reporting the minumim available.  
                 For interdomain connections this value represents
                 available BData A Cmax through all domains. This variable
                 is meaningful for routed connections only. 
                 These values are returned in bytes."
        ::= { connTableEntry 18  }

connMstOSpaceBdbCmax OBJECT-TYPE
    SYNTAX      INTEGER (0..65534)
    ACCESS      read-only
    STATUS      mandatory
    DESCRIPTION "This variable provides the minimum BData B Cmax 
                 available on the current path of this connection 
                 in master->slave direction. This variable
                 is determined by comparing available BData B Cmax on
                 every trunk on which the connection is currently 
                 routed and reporting the minumim available.  
                 For interdomain connections this value represents
                 available BData B Cmax through all domains. This variable
                 is meaningful for routed connections only. 
                 These values are returned in bytes."
        ::= { connTableEntry 19  }

connSlvOSpacePkts OBJECT-TYPE
    SYNTAX      INTEGER (0..2147483647)
    ACCESS      read-only
    STATUS      mandatory
    DESCRIPTION "This variable provides the minimum packet load
                 available on the current path of this connection 
                 in slave->master direction. This variable
                 is determined by comparing available bandwidth on
                 every trunk on which the connection is currently
                 routed and reporting the minumim available bandwidth.
                 For interdomain connections this value represents
                 available bandwidth through all domains. This variable
                 is meaningful for routed connections only.
                 These values are returned in packets per second."
        ::= { connTableEntry 20  }

connSlvOSpaceCells OBJECT-TYPE
    SYNTAX      INTEGER (0..2147483647)
    ACCESS      read-only
    STATUS      mandatory
    DESCRIPTION "This variable provides the minimum cell load
                 available on the current path of this connection 
                 in slave->master direction. This variable
                 is determined by comparing available bandwidth on
                 every trunk on which the connection is currently
                 routed and reporting the minumim available bandwidth.
                 For interdomain connections this value represents
                 available bandwidth through all domains. This variable
                 is meaningful for routed connections only.
                 These values are returned in cells per second."
        ::= { connTableEntry 21  }

connSlvOSpaceBdaCmax OBJECT-TYPE
    SYNTAX      INTEGER (0..65534)
    ACCESS      read-only
    STATUS      mandatory
    DESCRIPTION "This variable provides the minimum BData A Cmax 
                 available on the current path of this connection 
                 in slave->master direction. This variable
                 is determined by comparing available BData A Cmax on
                 every trunk on which the connection is currently 
                 routed and reporting the minumim available.  
                 For interdomain connections this value represents
                 available BData A Cmax through all domains. This variable
                 is meaningful for routed connections only. 
                 These values are returned in bytes."
        ::= { connTableEntry 22  }

connSlvOSpaceBdbCmax OBJECT-TYPE
    SYNTAX      INTEGER (0..65534)
    ACCESS      read-only
    STATUS      mandatory
    DESCRIPTION "This variable provides the minimum BData B Cmax 
                 available on the current path of this connection 
                 in slave->master direction. This variable
                 is determined by comparing available BData B Cmax on
                 every trunk on which the connection is currently 
                 routed and reporting the minumim available.  
                 For interdomain connections this value represents
                 available BData B Cmax through all domains. This variable
                 is meaningful for routed connections only. 
                 These values are returned in bytes."
        ::= { connTableEntry 23  }

connIcaRTD OBJECT-TYPE
    SYNTAX      INTEGER
    ACCESS      read-only
    STATUS      mandatory
    DESCRIPTION "The value of this object is the calculated round
                 trip delay (measured in milliseconds) of this connection.
                 This object is calculated for Foresight connections only. 
                 (xxEndptEnableFST object value is true)."
        ::= { connTableEntry 24  }

connGroupDesc OBJECT-TYPE
    SYNTAX      DisplayString
    ACCESS      read-write
    STATUS      mandatory
    DESCRIPTION "Description for Group identifier. This string describes the
                 connection group name. The format of the group name is 
                 domain.node-name.grp-number (Example, D1.node1.1). The 
                 varaible connIndex needs to have a special value of 65535
                 when creating a group. The group number and the domain are
                 optional."
        ::= { connTableEntry 25  }


--
-- This table defines Frame Relay connection end-point configuration.
-- Each connection (virtual circuit or PVC) end-point describes the
-- particular characteristics of the end-point.  Such information
-- as local and remote end-point description, class of service, input
-- and output bandwidth parameters, special PVC options, and PVC
-- statistics are maintained in the end-point.  Also, mechanisms for
-- determining the connection information associated with this end-point,
-- the next end-point of a bundle or group, and a means for creating
-- or deleting this end-point are included.
--
frEndptTable OBJECT-TYPE 
    SYNTAX      SEQUENCE OF FrEndptEntry
    ACCESS      not-accessible
    STATUS      mandatory
    DESCRIPTION "The Frame Relay End-Point Configuration table. 
                 This table is used to model a Frame Relay end-point.  
                 The table contains the configuration parameters 
                 required to create and configure a Frame Relay end-point." 
    --DEFAULT   test-function   test-frendpttable
    --DEFAULT   next-function   next-frendpttable
    --DEFAULT   get-function    get-frendpttable-%t
    --DEFAULT   view-mask       IPX-VIEW 
        ::= { switchConnection 5  }

frEndptEntry OBJECT-TYPE
    SYNTAX      FrEndptEntry
    ACCESS      not-accessible
    STATUS      mandatory
    DESCRIPTION "An entry in the Frame Relay End-point Configuration table."
    INDEX   { frEndptIndex }
        ::= { frEndptTable 1  }

FrEndptEntry ::=
    SEQUENCE {
        frEndptIndex             INTEGER,    
        frEndptDesc              DisplayString,

        frOtherEndptIndex        INTEGER,    
        frOtherEndptDesc         DisplayString,

        frEndptAdminStatus       INTEGER,
        frEndptOperStatus        INTEGER,

        frNoRouteFoundFailure    INTEGER,
        frBumpFailure            INTEGER,    
        frEndPointFailure        INTEGER,
        frTestFailure            INTEGER,

        frConnPtr                OBJECT IDENTIFIER,
        frNextPtr                OBJECT IDENTIFIER,
        frNextOnPortPtr          OBJECT IDENTIFIER,

        frEndptConnDesc          DisplayString,    
        frEndptTrkAvoidType      INTEGER,    
        frEndptTrkAvoidZCS       INTEGER,    

        frEndptSubType           INTEGER,    
        frEndptBWClass           INTEGER,    

        frEndptMIR               INTEGER,
        frEndptCIR               INTEGER,
        frEndptBc                INTEGER,
        frEndptBe                INTEGER,
        frEndptVcQSize           INTEGER,
        frEndptPIR               INTEGER,
        frEndptCMAX              INTEGER,
        frEndptEcnQSize          INTEGER,
        frEndptQIR               INTEGER,
        frEndptPercUtil          INTEGER,

        frEndptOeMIR             INTEGER,
        frEndptOeCIR             INTEGER,
        frEndptOeBc              INTEGER,
        frEndptOeBe              INTEGER,
        frEndptOeVcQSize         INTEGER,
        frEndptOePIR             INTEGER,
        frEndptOeCMAX            INTEGER,
        frEndptOeEcnQSize        INTEGER,
        frEndptOeQIR             INTEGER,
        frEndptOePercUtil        INTEGER,

        frEndptEnableFST         INTEGER,
        frEndptConnPrio          INTEGER,

        frEndptGroupFlag         INTEGER,
        frEndptLocLpbkState      INTEGER,
        frEndptLocRmtLpbkState   INTEGER,
        frEndptLpbkStatus        INTEGER,
        frEndptTestType          INTEGER,
        frEndptRtdTestDelay      INTEGER,
        frEndptGroupDesc         DisplayString 
    }

frEndptIndex OBJECT-TYPE
    SYNTAX      INTEGER (0..2047)
    ACCESS      read-only
    STATUS      mandatory
    DESCRIPTION "Index into table for this  end-point. Although
                 only 1024  endpoints may exist on a node, 2048
                 possible index values exist to support DAX (intra-node)
                 connections."
        ::= { frEndptEntry 1  }

frEndptDesc OBJECT-TYPE
    SYNTAX      DisplayString
    ACCESS      read-write
    STATUS      mandatory
    DESCRIPTION "String describing this  end-point.  Contains
                 information about the domain, nodename, slot, port,
                 and DLCI for the end-point.  For example,
                 D1.Node1.12.1.100, is a valid description.  Domain
                 and nodename need not be given but slot, port,
                 and DLCI values must exist; 12.1.100 is valid."
        ::= { frEndptEntry 2  }

frOtherEndptIndex OBJECT-TYPE
    SYNTAX      INTEGER (0..2047)
    ACCESS      read-only
    STATUS      mandatory
    DESCRIPTION "Index into remote node's frEndptTable for this PVC
                 end-point.  For DAX (intra-node) connections, this index is 
                 associated with the local node and will be in the
                 range of 1024 to 2047."
        ::= { frEndptEntry 3  }

frOtherEndptDesc OBJECT-TYPE
    SYNTAX      DisplayString
    ACCESS      read-write
    STATUS      mandatory
    DESCRIPTION "String describing the remote  end-point.  Contains
                 information about the domain, nodename, slot, port,
                 and DLCI for the end-point.  For example,
                 D2.Node2.10.1.100, is a valid description. Nodename,
                 slot, port, and DLCI values must exist; Node2.10.1.100
                 is valid."
        ::= { frEndptEntry 4  }

frEndptAdminStatus OBJECT-TYPE
    SYNTAX      INTEGER {
                create(1),
                delete(2),
                modify(3),
                test(4),
                writeOnly(5)
        }
    ACCESS      read-write
    STATUS      mandatory
    DESCRIPTION "User requested state for end-point table row.  A user can
                 create this VC or delete this VC by setting this object
                 appropriately.  If the end-point is to be modified, set 
                 this object identifier to be modify. The user also has the
                 capability to test a particular object.  For this capability,
                 the user must set this value to test."
        ::= { frEndptEntry 5  }

frEndptOperStatus OBJECT-TYPE
    SYNTAX      INTEGER {
                ok(1),
                okPendingDown(2),
                down(3),
                failed(4),
                inTest(5),
                okPendingRoute(6),
                okPendingDelete(7),
                looped(8),
                unknown(9)
        }
    ACCESS      read-only
    STATUS      mandatory
    DESCRIPTION "Actual state of the end-point.  If the state is failed,
                 then look to the objects frNoRouteFoundFailure,
                 frBumpFailure, frEndPointFailure, and frTestFailure
                 to determine reason for failure."
        ::= { frEndptEntry 6  }

frNoRouteFoundFailure OBJECT-TYPE
    SYNTAX      INTEGER {
                false(1),
                true(2)
        }
    ACCESS      read-only
    STATUS      mandatory
    DESCRIPTION "End-point is failed is because no route to the
                 remote end-point could be found."
        ::= { frEndptEntry 7  }

frBumpFailure OBJECT-TYPE
    SYNTAX      INTEGER {
                false(1),
                true(2)
        }
    ACCESS      read-only
    STATUS      mandatory
    DESCRIPTION "End-point is failed because of insufficient bandwidth
                 to route to the remote end-point.  This may have also
                 been caused because a higher priority connection took
                 this end-point's bandwidth.  A higher priority connection
                 is one with the lowest class of service (COS)."
        ::= { frEndptEntry 8  }

frEndPointFailure OBJECT-TYPE
    SYNTAX      INTEGER {
                false(1),
                true(2)
        }
    ACCESS      read-only
    STATUS      mandatory
    DESCRIPTION "End-point is failed because of a remote end-point failure.
                 The remote end-point is on a node that resides in another
                 domain making the connection an inter-domain connection."
        ::= { frEndptEntry 9  }

frTestFailure OBJECT-TYPE
    SYNTAX      INTEGER {
                false(1),
                true(2)
        }
    ACCESS      read-only
    STATUS      mandatory
    DESCRIPTION "End-point is failed because of the failure of a
                 connection test."
        ::= { frEndptEntry 10  }

frConnPtr OBJECT-TYPE
    SYNTAX      OBJECT IDENTIFIER
    ACCESS      read-only
    STATUS      mandatory
    DESCRIPTION "Pointer to general connection information.  Using this
                 pointer the user can obtain connection status, and
                 routing information. Specifically, this is an object
                 identifier specifying the first column of the appropriate
                 row in the connTable."
        ::= { frEndptEntry 11  }

frNextPtr OBJECT-TYPE
    SYNTAX      OBJECT IDENTIFIER
    ACCESS      read-only
    STATUS      mandatory
    DESCRIPTION "Pointer to next end-point information.  This allows
                 logical sets of end-points to be linked up.  For example,
                 the end-points associated with a bundle or group.
                 Specifically, this is an object identifier specifying the
                 first column of the appropriate row in the frEndptTable."
        ::= { frEndptEntry 12  }

frNextOnPortPtr OBJECT-TYPE
    SYNTAX      OBJECT IDENTIFIER
    ACCESS      read-only
    STATUS      mandatory
    DESCRIPTION "Pointer to next end-point information for the port 
                 associated with this end-point.  For example, using 
                 this pointer all frame relay end-points on a given 
                 slot.port can be determined.  Specifically, this is
                 an object identifier specifying the first column of the
                 appropriate row in the frEndptTable."
        ::= { frEndptEntry 13  }

frEndptConnDesc OBJECT-TYPE
    SYNTAX      DisplayString ( SIZE (0..20) )
    ACCESS      read-write
    STATUS      mandatory
    DESCRIPTION "A string that has been defined for the connection to
                 give a more descriptive name.  Connections can be given
                 clear text names in order to make them more human readable."
        ::= { frEndptEntry 14  }

frEndptTrkAvoidType OBJECT-TYPE
    SYNTAX      INTEGER {
                none(1),
                satellite(2),
                terrestrial(3)
        }
    ACCESS      read-write
    STATUS      mandatory
    DESCRIPTION "User selectable types of trunks to avoid for the
                 transfer of FRP data.  Current choices are to avoid
                 satellite links, terrestrial links, or to not avoid
                 any specific type of link. This object is optional
                 during the creation of the endpoint."
        ::= { frEndptEntry 15  }

frEndptTrkAvoidZCS OBJECT-TYPE
    SYNTAX      INTEGER {
                false(1),
                true(2)
        }
    ACCESS      read-write
    STATUS      mandatory
    DESCRIPTION "Flag to force the connection to avoid trunks with zero
                 code suppression (ZCS). This object is optional during
                 the creation of the endpoint."
        ::= { frEndptEntry 16  }

frEndptSubType OBJECT-TYPE
    SYNTAX      INTEGER {
                frameRelay(1),
                atf(2),
                unknown(3)
        }
    ACCESS      read-only
    STATUS      mandatory
    DESCRIPTION "Frame Relay endpoint subtype object."
        ::= { frEndptEntry 17  }
 
frEndptBWClass OBJECT-TYPE
    SYNTAX      INTEGER (1..10)
    ACCESS      read-write
    STATUS      mandatory
    DESCRIPTION "User selectable connection class which defines the
                 operating parameters for the connection.  Any or
                 all of these parameters can be overridden by
                 specifying the bandwidth parameters directly. This
                 object is required during the creation of an endpoint."
        ::= { frEndptEntry 18  }
 
frEndptMIR OBJECT-TYPE
    SYNTAX      INTEGER (2400..2048000)
    ACCESS      read-write
    STATUS      mandatory
    DESCRIPTION "The minimum transmit bandwidth (MIR) parameter
                 (in 100s of bits per second) for this  end-point.
                 During creation of an endpoint, this object is 
                 required if no class index is provided.  This is
                 because the default values of bandwidth parameters
                 not provided are derived from this object."
        ::= { frEndptEntry 19  }

frEndptCIR OBJECT-TYPE
    SYNTAX      INTEGER (2400..2048000)
    ACCESS      read-write
    STATUS      mandatory
    DESCRIPTION "The value of this object is equal to the committed
                 information rate (CIR) parameter (in 100s of bits
                 per second) for this  end-point.  This value will
                 be defaulted to the provided MIR during an endpoint
                 create."
        ::= { frEndptEntry 20  }

frEndptBc OBJECT-TYPE
    SYNTAX      INTEGER (1..65535)
    ACCESS      read-write
    STATUS      mandatory
    DESCRIPTION "The value of this object is equal to the committed
                 burst size (Bc) parameter (in bytes) for
                 this  end-point.
                 This parameter is entered instead of the frEndptVcQSize 
                 parameter.  If both the Bc and VcQSize are provided, the
                 values are tested for compatibility."
        ::= { frEndptEntry 21  }

frEndptBe OBJECT-TYPE
    SYNTAX      INTEGER (0..65535)
    ACCESS      read-write
    STATUS      mandatory
    DESCRIPTION "The value of this object is equal to the excess
                 burst size (Be) parameter (in bytes) for
                 this  end-point.
                 This parameter is entered instead of the frEndptPIR 
                 parameter. If both the Be and the PIR are provided, the
                 values are tested for compatibility."
        ::= { frEndptEntry 22  }

frEndptVcQSize OBJECT-TYPE
    SYNTAX      INTEGER (1..65535)
    ACCESS      read-write
    STATUS      mandatory
    DESCRIPTION "The value of this object is the maximum queue depth
                 (in bytes) for this  end-point.
                 This parameter is entered instead of the frEndptBc
                 parameter. If both the VcQSize and the Bc are provided,
                 the values are tested for compatibility."
        ::= { frEndptEntry 23  }

frEndptPIR OBJECT-TYPE
    SYNTAX      INTEGER (2400..2048000)
    ACCESS      read-write
    STATUS      mandatory
    DESCRIPTION "The peak transmit bandwidth (PIR) parameter
                 (in 100s of bits per second) for this  end-point.
                 This parameter is entered instead of the frEndptBe
                 parameter. This value defaults to the current port
                 speed of the associated interface."
        ::= { frEndptEntry 24  }

frEndptCMAX OBJECT-TYPE
    SYNTAX      INTEGER (1..255)
    ACCESS      read-write
    STATUS      mandatory
    DESCRIPTION "The maximum credits that can be accrued for this
                  end-point."
        ::= { frEndptEntry 25  }

frEndptEcnQSize OBJECT-TYPE
    SYNTAX      INTEGER (0..65535)
    ACCESS      read-write
    STATUS      mandatory
    DESCRIPTION "The threshold setting used by the explicit congestion
                 notification feature for this  end-point's
                 transmit queue. This value is specified in bytes.
                 When the frEndptVcQSize value exceeds this value
                 then the FECN bit will be set in all frames transmitted
                 to the remote  end-point."
        ::= { frEndptEntry 26 }

frEndptQIR OBJECT-TYPE
    SYNTAX      INTEGER (2400..2048000)
    ACCESS      read-write
    STATUS      mandatory
    DESCRIPTION "The transmit quiescent information rate (QIR) parameter
                 (in 100s of bits per second) for this  end-point.
                 This value can range between the MIR and PIR values
                 and must be between 2400 and 2048000.  This parameter
                 has meaning only if the frEndptEnableFST parameter
                 is set to true."
        ::= { frEndptEntry 27 }

frEndptPercUtil OBJECT-TYPE
    SYNTAX      INTEGER (0..100)
    ACCESS      read-write
    STATUS      mandatory
    DESCRIPTION "The value of this object is equal to the channel
                 percentage utilization setting for this  end-point.
                 This is the expected long-term utilization of the
                 channel by this  end-point."
        ::= { frEndptEntry 28 }

frEndptOeMIR OBJECT-TYPE
    SYNTAX      INTEGER (2400..2048000)
    ACCESS      read-write
    STATUS      mandatory
    DESCRIPTION "The minimum receive bandwidth (MIR) parameter
                 (in 100s of bits per second) for the other end-point.
                 This parameter is actually the frEndptMIR
                 parameter for the remote end-point.
                 During creation of an endpoint, this object is
                 required if no class index is provided.  This is
                 because the default values of bandwidth parameters
                 not provided are derived from this object."
        ::= { frEndptEntry 29 }

frEndptOeCIR OBJECT-TYPE
    SYNTAX      INTEGER (2400..2048000)
    ACCESS      read-write
    STATUS      mandatory
    DESCRIPTION "The value of this object is equal to the committed
                 information rate (CIR) parameter (in 100s of bits
                 per second) for the other end-point.
                 This parameter is actually the frEndptCIR
                 parameter for the remote end-point."
        ::= { frEndptEntry 30 }

frEndptOeBc OBJECT-TYPE
    SYNTAX      INTEGER (0..65535)
    ACCESS      read-write
    STATUS      mandatory
    DESCRIPTION "The value of this object is equal to the committed
                 burst size (Bc) parameter (in bytes) for
                 the end-point.  This parameter is entered
                 instead of the frEndptOeVcQSize parameter.
                 This parameter is actually the frEndptBc
                 parameter for the remote end-point.
                 Since this value is calculated at the remote end based on 
                 the BW parameters unaccessible by the local agent during
                 the varbind validation, the value specifed in the success 
                 SET response MAY NOT be its end value. The NMS is advised 
                 to GET this parameter again to confirm its actual value. 
                 Note: While modifying the value of 
                 this object it should be in the range 1..65535."
        ::= { frEndptEntry 31 }

frEndptOeBe OBJECT-TYPE
    SYNTAX      INTEGER (0..65535)
    ACCESS      read-write
    STATUS      mandatory
    DESCRIPTION "The value of this object is equal to the excess
                 burst size (Be) parameter (in bytes) for
                 the other end-point This parameter is entered
                 instead of the frEndptOePIR parameter.
                 This parameter is actually the frEndptBe
                 parameter for the remote end-point.
                 Since this value is calculated at the remote end based on 
                 the BW parameters unaccessible by the local agent during
                 the varbind validation, the value specifed in the success 
                 SET response MAY NOT be its end value. The NMS is advised 
                 to GET this parameter again to confirm its actual value." 
        ::= { frEndptEntry 32 }

frEndptOeVcQSize OBJECT-TYPE
    SYNTAX      INTEGER (1..3072000)
    ACCESS      read-write
    STATUS      mandatory
    DESCRIPTION "The value of this object is the maximum queue depth
                 (in bytes) for this  end-point.
                 This parameter is entered instead of the frEndptOeBc
                 parameter.  This parameter is actually the
                 frEndptVcQSize parameter for the remote end-point.
                 Since this value is calculated at the remote end based on 
                 the BW parameters unaccessible by the local agent during
                 the varbind validation, the value specifed in the success 
                 SET response MAY NOT be its end value. The NMS is advised 
                 to GET this parameter again to confirm its actual value." 
        ::= { frEndptEntry 33 }

frEndptOePIR OBJECT-TYPE
    SYNTAX      INTEGER (2400..2048000)
    ACCESS      read-write
    STATUS      mandatory
    DESCRIPTION "The peak receive bandwidth (PIR) parameter
                 (in 100s of bits per second) for the other end-point 
                 This parameter is entered instead of the frEndptOeBe
                 parameter.  This parameter is actually the frEndptPIR
                 parameter for the remote end-point. This value defaults 
                 to the current port speed of the associated interface.
                 Since this value is calculated at the remote end based on 
                 the BW parameters unaccessible by the local agent during
                 the varbind validation, the value specifed in the success 
                 SET response MAY NOT be its end value. The NMS is advised 
                 to GET this parameter again to confirm its actual value."
        ::= { frEndptEntry 34 }

frEndptOeCMAX OBJECT-TYPE
    SYNTAX      INTEGER (1..57600)
    ACCESS      read-write
    STATUS      mandatory
    DESCRIPTION "The maximum credits that can be accrued for the other 
                 end-point. This parameter is actually the frEndptCMAX
                 parameter for the remote end-point."
        ::= { frEndptEntry 35 }

frEndptOeEcnQSize OBJECT-TYPE
    SYNTAX      INTEGER (0..65535)
    ACCESS      read-write
    STATUS      mandatory
    DESCRIPTION "The threshold setting used by the explicit congestion
                 notification feature for the other end-point's
                 receive queue. This value is specified in bytes.
                 When the frpVCEndptOeVcQSize value exceeds this value
                 then the BECN bit will be set in all frames transmitted
                 to Frame Relay Service User.  This parameter is actually
                 the frEndptEcnQSize parameter for the remote end-point."
        ::= { frEndptEntry 36 }

frEndptOeQIR OBJECT-TYPE
    SYNTAX      INTEGER (2400..2048000)
    ACCESS      read-write
    STATUS      mandatory
    DESCRIPTION "The receive quiescent information rate (QIR) parameter
                 (in 100s of bits per second) for the other end-point. 
                 This value can range between the MIR and PIR values
                 and must be between 2400 and 2048000.  This parameter
                 has meaning only if the frEndptEnableFST parameter
                 is set to true.  This parameter is actually the frEndptQIR
                 parameter for the remote end-point."
        ::= { frEndptEntry 37 }

frEndptOePercUtil OBJECT-TYPE
    SYNTAX      INTEGER (0..100)
    ACCESS      read-write
    STATUS      mandatory
    DESCRIPTION "The value of this object is equal to the channel
                 percentage utilization setting for the other end-point.
                 This is the expected long-term utilization of the
                 channel by the other end-point.  This parameter is actually
                 the frEndptPercUtil parameter for the remote end-point."
        ::= { frEndptEntry 38 }

frEndptEnableFST OBJECT-TYPE
    SYNTAX      INTEGER {
                enable(1),
                disable(2)
        }
    ACCESS      read-write
    STATUS      mandatory
    DESCRIPTION "The value of this object determines whether or not the
                 ForeSight option is being used for this .  If set
                 to false, then ForeSight is not used, and if true then
                 ForeSight will be used."
        ::= { frEndptEntry 39 }

frEndptConnPrio OBJECT-TYPE
    SYNTAX      INTEGER {
                low(1),
                high(2)
        }
    ACCESS      read-write
    STATUS      mandatory
    DESCRIPTION "The value of this object determines the priority
                 that is given to the data carried by this .  If
                 set to low, then the data is given the standard
                 priority, and if set to high, the  data will be
                 given a higher priority.  Higher priority data
                 is placed at the beginning of the port's queues."
        ::= { frEndptEntry 40 }

frEndptGroupFlag OBJECT-TYPE
    SYNTAX      INTEGER {
                false(1),
                true(2)
        }
    ACCESS      read-only
    STATUS      mandatory
    DESCRIPTION "Specifies whether this is a grouped connection. Note 
                 that MIB object connGroupFlag provides grouping 
                 information about all the connections using that
                 connTable entry whereas this object provides same 
                 information for this end point."
        ::= { frEndptEntry 41 }

frEndptLocLpbkState OBJECT-TYPE
    SYNTAX      INTEGER {
                enable(1),
                disable(2)
        }
    ACCESS      read-write
    STATUS      mandatory
    DESCRIPTION "Specifies the Local Loopback State the user would
                 like to set for the endpoint." 
        ::= { frEndptEntry 42 }

frEndptLocRmtLpbkState OBJECT-TYPE
    SYNTAX      INTEGER {
                enable(1),
                disable(2)
        }
    ACCESS      read-write 
    STATUS      mandatory
    DESCRIPTION "Specifies the Local-Remote Loopback State the user 
                 would like to set for the endpoint." 
        ::= { frEndptEntry 43 }

frEndptLpbkStatus OBJECT-TYPE
    SYNTAX      INTEGER 
    ACCESS      read-only
    STATUS      mandatory
    DESCRIPTION "Specifies the current Loopback State of the endpoint. 
                 The value returned from this object is a bitmap
                 of the current loopback states which the endpoint
                 has configured.  There currently are 16 loopback
                 states an endpoint may have configured. If NO LOOPBACK
                 is configured, the agent will return -1.  The bitmap
                 is defined as follows:
         LP-RMT-RMT   0 /* Remote nodes remote muxbus loopback   */
         LP-RMT-TST   1 /* Remote nodes tstcon loopback          */
         LP-LOC-RMT   2 /* Local  nodes remoet muxbus loopback   */
         LP-LOC-TST   3 /* Local  nodes tstcon loopback          */
         LP-LOC-LOC   4 /* Local  nodes local muxbus loopback    */
         LP-LOC-PORT  5 /* Local  nodes port loopback            */
         LP-LOC-TPORT 6 /* Local  nodes port test loopback       */
         LP-RMT-LOC   7 /* Remote nodes local muxbus loopback    */
         LP-RMT-PORT  8 /* Remote nodes port loopback            */
         LP-RMT-TPORT 9 /* Remote nodes port test looback        */
         LP-LOC-CSU 10 /* Local  DDS network requested CSU loopback */
         LP-RMT-CSU 11 /* Remote DDS network requested CSU loopback */
         LP-LOC-DSU 12 /* Local  DDS network requested DSU loopback */
         LP-RMT-DSU 13 /* Remote DDS network requested DSU loopback */
         LP-LOC-EXT 14 /* Local  DDS external loopback          */
         LP-RMT-EXT 15 /* Remote DDS external loopback          */
         "
        ::= { frEndptEntry 44 }

frEndptTestType OBJECT-TYPE
    SYNTAX      INTEGER {
                test(1),
                testDelay(2),
                testNoLoop(3),
                testDelayNoLoop(4),
                writeOnly(5)
        }
    ACCESS      read-write
    STATUS      mandatory
    DESCRIPTION "Specifies the type of test the user would like to
                 conduct on this endpoint.  There are currently two
                 types of tests.  Test will exercise continuity, while
                 TestDelay will calculate the delay incurred on the
                 connection. The result of the TestDelay may then be
                 accessed through the frEndptRtdTestDelay object.
                 To invoke a test, the frEndptAdminStatus is required 
                 to be set to test(4).
                 The NoLoop options provide the user the capability to
                 execute the tests without automatically invoking a 
                 loopback at the remote endpoint." 
        ::= { frEndptEntry 45 }

frEndptRtdTestDelay OBJECT-TYPE
    SYNTAX      INTEGER 
    ACCESS      read-only
    STATUS      mandatory
    DESCRIPTION "The value of this object is the calculated round
                 trip delay (measured in milliseconds) of this Frame
                 Relay endpoint. A delay test is invoked through setting
                 the frEndptTestType object to TestDelay." 
        ::= { frEndptEntry 46 }

frEndptGroupDesc OBJECT-TYPE
    SYNTAX      DisplayString
    ACCESS      read-write
    STATUS      mandatory
    DESCRIPTION "String describing the group this endpoint is 
                 associated with.  The format of the group text
                 description is domain.node.grp-number (Example,
                 D2.node1.1)." 
        ::= { frEndptEntry 47 }
 

--
-- This table defines Frame Relay connection end-point statistics with
-- information in the following areas:
--
--  1. Received or transmitted frame statistics
--  2. Received or transmitted but discarded frame statistics.
--  3. Frame relay flow and congestion control statistics.
--      4. Received or transmitted frame and bytes over CIR.
--

frEndptStatTable OBJECT-TYPE 
    SYNTAX      SEQUENCE OF FrEndptStatEntry
    ACCESS      not-accessible
    STATUS      mandatory
    DESCRIPTION "The Frame Relay End-Point Statistics table." 
    --DEFAULT   test-function   test-frendptstattable
    --DEFAULT   next-function   next-frendptstattable
    --DEFAULT   get-function    get-frendptstattable-%t
    --DEFAULT   view-mask       IPX-VIEW 
    --DEFAULT   locator         FRENDPT-STAT-LOCATOR
        ::= { switchConnection 6  }

frEndptStatEntry OBJECT-TYPE
    SYNTAX      FrEndptStatEntry
    ACCESS      not-accessible
    STATUS      mandatory
    DESCRIPTION "An entry in the Frame Relay End-point Statistics table."
    INDEX   { frEndptIndex }
        ::= { frEndptStatTable 1  }

FrEndptStatEntry ::=
    SEQUENCE {
        frEndptRxBytes          Counter,
        frEndptRxBytesDscds     Counter,
        frEndptRxFrms           Counter,
        frEndptRxFrmsDscds      Counter,
        frEndptRxPkts           Counter,
        frEndptRxPktsDscds      Counter,

        frEndptTxBytes          Counter,
        frEndptTxBytesDscds     Counter,
        frEndptTxFrms           Counter,
        frEndptTxFrmsDscds      Counter,
        frEndptTxPkts           Counter,
        frEndptTxFrmsFecns      Counter,
        frEndptTxFrmsBecns      Counter,

        frEndptSecInServices    Counter,
        frEndptCongestMins      Counter,

        frEndptRxFrmsDes        Counter,
        frEndptRxBytesDes       Counter,
        frEndptTxFrmsDes        Counter,
        frEndptRxFrmsDeDscds    Counter,

        frEndptRxFrmsCirs       Counter,
        frEndptRxBytesCirs      Counter,
        frEndptTxFrmsCirs       Counter,
        frEndptTxBytesCirs      Counter
    }

frEndptRxBytes  OBJECT-TYPE
    SYNTAX      Counter 
    ACCESS      read-only
    STATUS      mandatory
    DESCRIPTION "Frame Relay Endpoint Statistic, the number of frame
                 bytes received from the local frame relay port."
        ::= { frEndptStatEntry 1  }

frEndptRxBytesDscds  OBJECT-TYPE
    SYNTAX      Counter 
    ACCESS      read-only
    STATUS      mandatory
    DESCRIPTION "Frame Relay Endpoint Statistic, the number of frame
                 bytes received from the local frame relay port but 
                 discarded before being transmitted onto the Muxbus, due 
                 to the age of the frame in the IPX system or lack of 
                 buffer space."
        ::= { frEndptStatEntry 2  }

frEndptRxFrms  OBJECT-TYPE
    SYNTAX      Counter 
    ACCESS      read-only
    STATUS      mandatory
    DESCRIPTION "Frame Relay Endpoint Statistic, the number of frames
                 received from the local frame relay port."
        ::= { frEndptStatEntry 3  }

frEndptRxFrmsDscds  OBJECT-TYPE
    SYNTAX      Counter 
    ACCESS      read-only
    STATUS      mandatory
    DESCRIPTION "Frame Relay Endpoint Statistic, the number of frames
                 received from the local frame relay port but 
                 discarded before being transmitted onto the Muxbus, due 
                 to the age of the frame in the IPX system or lack of 
                 buffer space "
        ::= { frEndptStatEntry 4  }

frEndptRxPkts  OBJECT-TYPE
    SYNTAX      Counter 
    ACCESS      read-only
    STATUS      mandatory
    DESCRIPTION "Frame Relay Endpoint Statistic, the number of packets
                 received from the Muxbus by the local port card."
        ::= { frEndptStatEntry 5  }

frEndptRxPktsDscds  OBJECT-TYPE
    SYNTAX      Counter 
    ACCESS      read-only
    STATUS      mandatory
    DESCRIPTION "Frame Relay Endpoint Statistic, the number of packets
                 received from the Muxbus by the local port card but
                 discarded before being transmitted."
        ::= { frEndptStatEntry 6  }

frEndptTxBytes  OBJECT-TYPE
    SYNTAX      Counter
    ACCESS      read-only
    STATUS      mandatory
    DESCRIPTION "Frame Relay Endpoint Statistic, the number of frame
                 bytes received from the Muxbus and transmitted out the 
                 frame relay port."
        ::= { frEndptStatEntry 7  }

frEndptTxBytesDscds  OBJECT-TYPE
    SYNTAX      Counter
    ACCESS      read-only
    STATUS      mandatory
    DESCRIPTION "Frame Relay Endpoint Statistic, the number of frame
                 bytes received from the Muxbus but discarded 
                 before being transmitted out the frame relay port, due
                 to the age of the frame in the IPX system, CRC error,
                 or lack of buffer space."
        ::= { frEndptStatEntry 8  }

frEndptTxFrms  OBJECT-TYPE
    SYNTAX      Counter
    ACCESS      read-only
    STATUS      mandatory
    DESCRIPTION "Frame Relay Endpoint Statistic, the number of frames
                 transmitted out the frame relay port."
        ::= { frEndptStatEntry 9  }

frEndptTxFrmsDscds  OBJECT-TYPE
    SYNTAX      Counter
    ACCESS      read-only
    STATUS      mandatory
    DESCRIPTION "Frame Relay Endpoint Statistic, the number of frames,
                 which are discarded by the local frame relay card before 
                 being transmitted out the local port, due to the age of
                 the frame in the IPX system, a CRC error, or lack of
                 buffer space."
        ::= { frEndptStatEntry 10  }

frEndptTxPkts  OBJECT-TYPE
    SYNTAX      Counter 
    ACCESS      read-only
    STATUS      mandatory
    DESCRIPTION "Frame Relay Endpoint Statistic, the number of packets
                 tranmitted to the Muxbus by the local port card."
        ::= { frEndptStatEntry 11  }

frEndptTxFrmsFecns  OBJECT-TYPE
    SYNTAX      Counter
    ACCESS      read-only
    STATUS      mandatory
    DESCRIPTION "Frame Relay Endpoint Statistic, the number of frames
                 transmitted out the local frame relay port with FECN
                 bit set."
        ::= { frEndptStatEntry 12  }

frEndptTxFrmsBecns  OBJECT-TYPE
    SYNTAX      Counter
    ACCESS      read-only
    STATUS      mandatory
    DESCRIPTION "Frame Relay Endpoint Statistic, the number of frames
                 transmitted out the local frame relay port with BECN
                 bit set."
        ::= { frEndptStatEntry 13  }

frEndptSecInServices OBJECT-TYPE
    SYNTAX      Counter
    ACCESS      read-only
    STATUS      mandatory
    DESCRIPTION "Frame Relay Endpoint Statistic, the number of seconds in
                 which a connection is in service. A connection is 
                 considered to be in service if its end point is not in 
                 alarm, the cards required to support the connection 
                 are present and the connection is routed."
        ::= { frEndptStatEntry 14  }

frEndptCongestMins  OBJECT-TYPE
    SYNTAX      Counter
    ACCESS      read-only
    STATUS      mandatory
    DESCRIPTION "Frame Relay Endpoint Statistic, number of minutes in which
                 50% or more frames are tagged FECN by the FRP."
        ::= { frEndptStatEntry 15  }

frEndptRxFrmsDes  OBJECT-TYPE
    SYNTAX      Counter 
    ACCESS      read-only
    STATUS      mandatory
    DESCRIPTION "Frame Relay Endpoint Statistic, the number of frames
                 received from the local frame relay port with their
                 DE bit set. DE bits are only counted by model D frame 
                 relay firmware or later."
        ::= { frEndptStatEntry 16  }

frEndptRxBytesDes  OBJECT-TYPE
    SYNTAX      Counter 
    ACCESS      read-only
    STATUS      mandatory
    DESCRIPTION "Frame Relay Endpoint Statistic, the number of frames
                 received from the local frame relay port with their
                 DE bit set. DE bits are only counted by model D frame 
                 relay firmware or later."
        ::= { frEndptStatEntry 17  }

frEndptTxFrmsDes  OBJECT-TYPE
    SYNTAX      Counter 
    ACCESS      read-only
    STATUS      mandatory
    DESCRIPTION "Frame Relay Endpoint Statistic, the number of frames
                 transmitted out the local frame relay port with their
                 DE bit set. DE bits are only counted by model D frame 
                 relay firmware or later."
        ::= { frEndptStatEntry 18  }

frEndptRxFrmsDeDscds  OBJECT-TYPE
    SYNTAX      Counter 
    ACCESS      read-only
    STATUS      mandatory
    DESCRIPTION "Frame Relay Endpoint Statistic, the number of frame
                 received from the local frame relay port with their DE
                 bit set, which are discarded before being transmitted onto
                 the Muxbus. DE bits are only counted by model D frame
                 relay firmware or later."
        ::= { frEndptStatEntry 19  }

frEndptRxFrmsCirs  OBJECT-TYPE
    SYNTAX      Counter 
    ACCESS      read-only
    STATUS      mandatory
    DESCRIPTION "Frame Relay Endpoint Rx frames from port in excess of CIR."
        ::= { frEndptStatEntry 20  }

frEndptRxBytesCirs  OBJECT-TYPE
    SYNTAX      Counter 
    ACCESS      read-only
    STATUS      mandatory
    DESCRIPTION "Frame Relay Endpoint Rx bytes from port in excess of CIR."
        ::= { frEndptStatEntry 21  }

frEndptTxFrmsCirs  OBJECT-TYPE
    SYNTAX      Counter 
    ACCESS      read-only
    STATUS      mandatory
    DESCRIPTION "Frame Relay Endpoint Tx frames from port in excess of CIR."
        ::= { frEndptStatEntry 22  }

frEndptTxBytesCirs  OBJECT-TYPE
    SYNTAX      Counter 
    ACCESS      read-only
    STATUS      mandatory
    DESCRIPTION "Frame Relay Endpoint Tx bytes from port in excess of CIR."
        ::= { frEndptStatEntry 23  }



-- This table describes frame relay bandwith classes available on 
-- the node. In order to avoid specifying all the bandwidth parameters
-- while creating a frame relay connection user can specify a
-- frame relay bandwidth class by its number (available as index into
-- this table). 
--
frBwClassTable OBJECT-TYPE
    SYNTAX      SEQUENCE OF FrBwClassEntry
    ACCESS      not-accessible
    STATUS      mandatory
    DESCRIPTION "The Frame Relay Bandwidth Class table."
    --DEFAULT   test-function   test-frbwclasstable
    --DEFAULT   next-function   next-frbwclasstable
    --DEFAULT   get-function    get-frbwclasstable-%t
    --DEFAULT   view-mask       IPX-VIEW 
        ::= { switchConnection 7  }
 
frBwClassEntry OBJECT-TYPE
    SYNTAX      FrBwClassEntry
    ACCESS      not-accessible
    STATUS      mandatory
    DESCRIPTION "An entry in the Frame Relay Bandwidth Class table."
    INDEX   { frBwClassIndex }
        ::= { frBwClassTable 1  }
 
FrBwClassEntry ::=
    SEQUENCE {
        frBwClassIndex          INTEGER,

        frBwClassMIR            INTEGER,
        frBwClassCIR            INTEGER,
        frBwClassVcQSize        INTEGER,
        frBwClassBc             INTEGER,
        frBwClassPIR            INTEGER,
        frBwClassBe             INTEGER,
        frBwClassCMAX           INTEGER,
        frBwClassEcnQSize       INTEGER,
        frBwClassQIR            INTEGER,
        frBwClassPercUtil       INTEGER,

        frBwClassOeMIR            INTEGER,
        frBwClassOeCIR            INTEGER,
        frBwClassOeVcQSize        INTEGER,
        frBwClassOeBc             INTEGER,
        frBwClassOePIR            INTEGER,
        frBwClassOeBe             INTEGER,
        frBwClassOeCMAX           INTEGER,
        frBwClassOeEcnQSize       INTEGER,
        frBwClassOeQIR            INTEGER,
        frBwClassOePercUtil       INTEGER,

        frBwClassEnableFST      INTEGER,
        frBwClassDescription    DisplayString
    }

frBwClassIndex OBJECT-TYPE
    SYNTAX      INTEGER (1..10)
    ACCESS      read-only
    STATUS      mandatory
    DESCRIPTION "Index into FrBwClassTable. This index identifies the
                 frame relay bandwidth class."
        ::= { frBwClassEntry 1  }

frBwClassMIR OBJECT-TYPE
    SYNTAX      INTEGER (2400..2048000)
    ACCESS      read-only
    STATUS      mandatory
    DESCRIPTION "The minimum transmit bandwidth (MIR) parameter
                 (in 100s of bits per second) for this  end-point."
        ::= { frBwClassEntry 2  }

frBwClassCIR OBJECT-TYPE
    SYNTAX      INTEGER (2400..2048000)
    ACCESS      read-only
    STATUS      mandatory
    DESCRIPTION "The value of this object is equal to the committed
                 information rate (CIR) parameter (in 100s of bits
                 per second) for this  end-point."
        ::= { frBwClassEntry 3  }
 
frBwClassVcQSize OBJECT-TYPE
    SYNTAX      INTEGER (1..65535)
    ACCESS      read-only
    STATUS      mandatory
    DESCRIPTION "The value of this object is the maximum queue depth
                 (in bytes) for this  end-point."
        ::= { frBwClassEntry 4  }

frBwClassBc OBJECT-TYPE
    SYNTAX      INTEGER (1..65535)
    ACCESS      read-only
    STATUS      mandatory
    DESCRIPTION "The value of this object is equal to the committed
                 burst size (Bc) parameter (in bytes) for
                 this  end-point."
        ::= { frBwClassEntry 5  }

frBwClassPIR OBJECT-TYPE
    SYNTAX      INTEGER (2400..2048000)
    ACCESS      read-only
    STATUS      mandatory
    DESCRIPTION "The peak transmit bandwidth (PIR) parameter
                 (in 100s of bits per second) for this  end-point."
        ::= { frBwClassEntry 6  }
 
frBwClassBe OBJECT-TYPE
    SYNTAX      INTEGER (0..65535)
    ACCESS      read-only
    STATUS      mandatory
    DESCRIPTION "The value of this object is equal to the excess
                 burst size (Be) parameter (in bytes) for
                 this  end-point."
        ::= { frBwClassEntry 7  }

frBwClassCMAX OBJECT-TYPE
    SYNTAX      INTEGER (1..255)
    ACCESS      read-only
    STATUS      mandatory
    DESCRIPTION "The maximum credits that can be accrued for this
                 end-point."
        ::= { frBwClassEntry 8  }

frBwClassEcnQSize OBJECT-TYPE
    SYNTAX      INTEGER (0..65535)
    ACCESS      read-only
    STATUS      mandatory
    DESCRIPTION "The threshold setting used by the explicit congestion
                 notification feature for this  end-point's
                 transmit queue. This value is specified in bytes."
        ::= { frBwClassEntry 9  }

frBwClassQIR OBJECT-TYPE
    SYNTAX      INTEGER (2400..2048000)
    ACCESS      read-only
    STATUS      mandatory
    DESCRIPTION "The transmit quiescent information rate (QIR) parameter
                 (in 100s of bits per second) for this  end-point.
                 This value can range between the MIR and PIR values
                 and must be between 2400 and 2048000.  This parameter
                 has meaning only if the frEndptEnableFST parameter
                 is set to true."
        ::= { frBwClassEntry 10  }

frBwClassPercUtil OBJECT-TYPE
    SYNTAX      INTEGER (0..100)
    ACCESS      read-only
    STATUS      mandatory
    DESCRIPTION "The value of this object is equal to the channel
                 percentage utilization setting for this  end-point.
                 This is the expected long-term utilization of the
                 channel by this  end-point."
        ::= { frBwClassEntry 11  }

frBwClassOeMIR OBJECT-TYPE
    SYNTAX      INTEGER (2400..2048000)
    ACCESS      read-only
    STATUS      mandatory
    DESCRIPTION "The minimum receive bandwidth (MIR) parameter
                 (in 100s of bits per second) for the other end-point."
        ::= { frBwClassEntry 12  }

frBwClassOeCIR OBJECT-TYPE
    SYNTAX      INTEGER (2400..2048000)
    ACCESS      read-only
    STATUS      mandatory
    DESCRIPTION "The value of this object is equal to the committed
                 information rate (CIR) parameter (in 100s of bits
                 per second) for the other end-point."
        ::= { frBwClassEntry 13  }
 
frBwClassOeVcQSize OBJECT-TYPE
    SYNTAX      INTEGER (1..3072000)
    ACCESS      read-only
    STATUS      mandatory
    DESCRIPTION "The value of this object is the maximum queue depth
                 (in bytes) for this  end-point."
        ::= { frBwClassEntry 14  }

frBwClassOeBc OBJECT-TYPE
    SYNTAX      INTEGER (0..65535)
    ACCESS      read-only
    STATUS      mandatory
    DESCRIPTION "The value of this object is equal to the committed
                 burst size (Bc) parameter (in bytes) for
                 the end-point."
        ::= { frBwClassEntry 15  }

frBwClassOePIR OBJECT-TYPE
    SYNTAX      INTEGER (2400..2048000)
    ACCESS      read-only
    STATUS      mandatory
    DESCRIPTION "The peak receive bandwidth (PIR) parameter
                 (in 100s of bits per second) for the other end-point."
        ::= { frBwClassEntry 16  }
 
frBwClassOeBe OBJECT-TYPE
    SYNTAX      INTEGER (0..65535)
    ACCESS      read-only
    STATUS      mandatory
    DESCRIPTION "The value of this object is equal to the excess
                 burst size (Be) parameter (in bytes) for
                 the other end-point."
        ::= { frBwClassEntry 17  }

frBwClassOeCMAX OBJECT-TYPE
    SYNTAX      INTEGER (1..57600)
    ACCESS      read-only
    STATUS      mandatory
    DESCRIPTION "The maximum credits that can be accrued for the other 
                 end-point."
        ::= { frBwClassEntry 18  }

frBwClassOeEcnQSize OBJECT-TYPE
    SYNTAX      INTEGER (0..65535)
    ACCESS      read-only
    STATUS      mandatory
    DESCRIPTION "The threshold setting used by the explicit congestion
                 notification feature for the other end-point's
                 receive queue. This value is specified in bytes."
        ::= { frBwClassEntry 19  }

frBwClassOeQIR OBJECT-TYPE
    SYNTAX      INTEGER (2400..2048000)
    ACCESS      read-only
    STATUS      mandatory
    DESCRIPTION "The receive quiescent information rate (QIR) parameter
                 (in 100s of bits per second) for the other end-point."
        ::= { frBwClassEntry 20  }

frBwClassOePercUtil OBJECT-TYPE
    SYNTAX      INTEGER (0..100)
    ACCESS      read-only
    STATUS      mandatory
    DESCRIPTION "The value of this object is equal to the channel
                 percentage utilization setting for the other end-point."
        ::= { frBwClassEntry 21  }

frBwClassEnableFST OBJECT-TYPE
    SYNTAX      INTEGER {
                enable(1),
                disable(2)
                }
    ACCESS      read-only
    STATUS      mandatory
    DESCRIPTION "The value of this object determines whether or not the
                 ForeSight option is being used for this .  If set
                 to false, then ForeSight is not used, and if true then
                 ForeSight will be used."
        ::= { frBwClassEntry 22  }

frBwClassDescription OBJECT-TYPE
    SYNTAX      DisplayString ( SIZE (0..24) )
    ACCESS      read-only
    STATUS      mandatory
    DESCRIPTION "This MIB object contains a textual description of this
                 frame relay bandwidth class."
        ::= { frBwClassEntry 23  }

--
-- This is the table describing an ATM connection end-point.
-- Each connection (virtual circuit or ) end-point describes the
-- particular characteristics of the end-point.  Such information
-- as local and remote end-point description, class of service, input
-- and output bandwidth parameters, and special options are maintained 
-- in the end-point table.  
-- This table is only applicable on the BPX switch.
--
atmEndptTable OBJECT-TYPE 
    SYNTAX      SEQUENCE OF AtmEndptEntry
    ACCESS      not-accessible
    STATUS      mandatory
    DESCRIPTION "The ATM End-Point table.  This table
                 is used to model a PVC end-point.  This table
                 contains the traffic parameters for ATM end-point."
    --DEFAULT   test-function   test-atmendpttable
    --DEFAULT   next-function   next-atmendpttable
    --DEFAULT   get-function    get-atmendpttable-%t
    --DEFAULT   view-mask       BPX-VIEW 
        ::= { switchConnection 8  }

atmEndptEntry OBJECT-TYPE
    SYNTAX      AtmEndptEntry
    ACCESS      not-accessible
    STATUS      mandatory
    DESCRIPTION "An entry in the ATM End-point table."
    INDEX   { atmEndptIndex }
        ::= { atmEndptTable 1  }

AtmEndptEntry ::=
    SEQUENCE {
        atmEndptIndex             INTEGER,    
        atmEndptDesc              DisplayString,

        atmOtherEndptIndex        INTEGER,    
        atmOtherEndptDesc         DisplayString,

        atmEndptAdminStatus       INTEGER,
        atmEndptOperStatus        INTEGER,

        atmNoRouteFoundFailure    INTEGER,
        atmBumpFailure            INTEGER,    
        atmEndPointFailure        INTEGER,
        atmTestFailure            INTEGER,

        atmConnPtr                OBJECT IDENTIFIER,
        atmNextPtr                OBJECT IDENTIFIER,
        atmNextOnPortPtr          OBJECT IDENTIFIER,

        atmEndptConnDesc          DisplayString,    
        atmEndptTrkAvoidType      INTEGER,    
        atmEndptTrkAvoidZCS       INTEGER,    

        atmEndptSubType           INTEGER,    
        atmEndptBWClass           INTEGER,    

        atmEndptMIR               INTEGER,
        atmEndptCIR               INTEGER,
        atmEndptVcQSize           INTEGER,
        atmEndptPIR               INTEGER,
        atmEndptEfciQSize         INTEGER,
        atmEndptQIR               INTEGER,
        atmEndptPercUtil          INTEGER,
        atmEndptCBS               INTEGER,
        atmEndptIBS               INTEGER,
        atmEndptMFS               INTEGER,
        atmEndptCCDV              INTEGER,
        atmEndptHiCLP             INTEGER,
        atmEndptLoCLP             INTEGER,

        atmEndptOeMIR             INTEGER,
        atmEndptOeCIR             INTEGER,
        atmEndptOeVcQSize         INTEGER,
        atmEndptOePIR             INTEGER,
        atmEndptOeEfciQSize       INTEGER,
        atmEndptOeQIR             INTEGER,
        atmEndptOePercUtil        INTEGER,
        atmEndptOeCBS             INTEGER,
        atmEndptOeIBS             INTEGER,
        atmEndptOeMFS             INTEGER,
        atmEndptOeCCDV            INTEGER,
        atmEndptOeHiCLP           INTEGER,
        atmEndptOeLoCLP           INTEGER,

        atmEndptCLPTagging        INTEGER,
        atmEndptUPC               INTEGER,
        atmEndptEnableFST         INTEGER,
        atmEndptRateUpICA         INTEGER,
        atmEndptRateDnICA         INTEGER,
        atmEndptFastDnICA         INTEGER,
        atmEndptToQIR             INTEGER,
        atmEndptMinAdjustICA      INTEGER,

        atmEndptGroupFlag         INTEGER,
        atmEndptOamStatus         INTEGER,
        atmEndptBCM               INTEGER,
        atmEndptFGCRA             INTEGER,
 
        atmEndptLocLpbkState      INTEGER,
        atmEndptLpbkStatus        INTEGER,
        atmEndptTestType          INTEGER,
        atmEndptRtdTestDelay      INTEGER,
        atmEndptOeBCM             INTEGER,
        atmEndptOeFGCRA           INTEGER,
        atmEndptGroupDesc         DisplayString,
        atmEndptLocRmtLpbkState   INTEGER,

        atmEndptScrPlc            INTEGER,
        atmEndptOeScrPlc          INTEGER,
        atmEndptPCR0              INTEGER,
        atmEndptOePCR0            INTEGER,
        atmEndptCDVT0             INTEGER,
        atmEndptOeCDVT0           INTEGER,
        atmEndptOeRateUpICA       INTEGER,
        atmEndptFRTT              INTEGER,
        atmEndptTBE               INTEGER,
        atmEndptVSVD              INTEGER,
        atmEndptPolicing          INTEGER,
        atmEndptPCR               INTEGER

    }

atmEndptIndex OBJECT-TYPE
    SYNTAX      INTEGER (0..9999)
    ACCESS      read-only
    STATUS      mandatory
    DESCRIPTION "Index into table for this  end-point. Although
                 only 5000  endpoints may exist on a node, 10000
                 possible index values exist to support DAX (intra-node)
                 connections."
        ::= { atmEndptEntry 1  }

atmEndptDesc OBJECT-TYPE
    SYNTAX      DisplayString
    ACCESS      read-write
    STATUS      mandatory
    DESCRIPTION "String describing this  end-point.  Contains
                 information about the domain, nodename, slot, port,
                 vpi, and vci for the end-point.  For example,
                 D1.Node1.12.1.100.200, is a valid description.  Domain
                 and nodename need not be given but slot, port,
                 VPI and VCI values must exist; 12.1.100.200 is valid.
                 A virtual path connection endpoint of the form
                 12.1.100.* is also valid. For a basis port the last
                 4 bits of the VPI must be between 3 and 14."
        ::= { atmEndptEntry 2  }

atmOtherEndptIndex OBJECT-TYPE
    SYNTAX      INTEGER (0..9999)
    ACCESS      read-only
    STATUS      mandatory
    DESCRIPTION "Index into remote node's atmEndptTable for this 
                 end-point.  For DAX (intra-node) connections, this index is 
                 associated with the local node and will be in the
                 range of 5000 to 9999."
        ::= { atmEndptEntry 3  }

atmOtherEndptDesc OBJECT-TYPE
    SYNTAX      DisplayString
    ACCESS      read-write
    STATUS      mandatory
    DESCRIPTION "String describing the remote PVC end-point.  Contains
                 information about the domain, nodename, slot, port,
                 vpi, and vci for the end-point.  For example,
                 D2.Node2.10.1.100.200, is a valid description. Nodename,
                 slot, port, VPI and VCI values must exist. A virtual
                 path connection endpoint of the form D2.Node2.10.1.100.*
                 is also valid. For a basis port the last 4 bits of the
                 VPI must be between 3 and 14."
        ::= { atmEndptEntry 4  }

atmEndptAdminStatus OBJECT-TYPE
    SYNTAX      INTEGER {
                create(1),
                delete(2),
                modify(3),
                test(4),
                writeOnly(5)
        }
    ACCESS      read-write
    STATUS      mandatory
    DESCRIPTION "User requested state for end-point table row.  A user can
                 create this VC or delete this VC by setting this object
                 appropriately.  If the end-point is to be
                 modified, set this object identifier to be modify."
        ::= { atmEndptEntry 5  }

atmEndptOperStatus OBJECT-TYPE
    SYNTAX      INTEGER {
                ok(1),
                okPendingDown(2),
                down(3),
                failed(4),
                inTest(5),
                okPendingRoute(6),
                okPendingDelete(7),
                looped(8),
                unknown(9)
        }
    ACCESS      read-only
    STATUS      mandatory
    DESCRIPTION "Actual state of the end-point.  If the state is failed,
                 then look to the objects atmNoRouteFoundFailure,
                 atmBumpFailure, atmEndPointFailure, and atmTestFailure
                 to determine reason for failure."
        ::= { atmEndptEntry 6  }

atmNoRouteFoundFailure OBJECT-TYPE
    SYNTAX      INTEGER {
                false(1),
                true(2)
        }
    ACCESS      read-only
    STATUS      mandatory
    DESCRIPTION "End-point is failed is because no route to the
                 remote end-point could be found."
        ::= { atmEndptEntry 7  }

atmBumpFailure OBJECT-TYPE
    SYNTAX      INTEGER {
                false(1),
                true(2)
        }
    ACCESS      read-only
    STATUS      mandatory
    DESCRIPTION "End-point is failed because of insufficient bandwidth
                 to route to the remote end-point.  This may have also
                 been caused because a higher priority connection took
                 this end-point's bandwidth.  A higher priority connection
                 is one with the lowest class of service (COS)."
        ::= { atmEndptEntry 8  }

atmEndPointFailure OBJECT-TYPE
    SYNTAX      INTEGER {
                false(1),
                true(2)
        }
    ACCESS      read-only
    STATUS      mandatory
    DESCRIPTION "End-point is failed because of a remote end-point failure.
                 The remote end-point is on a node that resides in another
                 domain making the connection an inter-domain connection."
        ::= { atmEndptEntry 9  }

atmTestFailure OBJECT-TYPE
    SYNTAX      INTEGER {
                false(1),
                true(2)
        }
    ACCESS      read-only
    STATUS      mandatory
    DESCRIPTION "End-point is failed because of the failure of a
                 connection test."
        ::= { atmEndptEntry 10  }

atmConnPtr OBJECT-TYPE
    SYNTAX      OBJECT IDENTIFIER
    ACCESS      read-only
    STATUS      mandatory
    DESCRIPTION "Pointer to general connection information.  Using this
                 pointer the user can obtain connection status, and
                 routing information. Specifically, this is an object
                 identifier specifying the first column of the appropriate
                 row in the connTable."
        ::= { atmEndptEntry 11  }

atmNextPtr OBJECT-TYPE
    SYNTAX      OBJECT IDENTIFIER
    ACCESS      read-only
    STATUS      mandatory
    DESCRIPTION "Pointer to next end-point information.  This allows
                 logical sets of end-points to be linked up.  For example,
                 the end-points associated with a bundle or group.
                 Specifically, this is an object identifier specifying the
                 first column of the appropriate row in the atmEndptTable."
        ::= { atmEndptEntry 12  }

atmNextOnPortPtr OBJECT-TYPE
    SYNTAX      OBJECT IDENTIFIER
    ACCESS      read-only
    STATUS      mandatory
    DESCRIPTION "Pointer to next end-point information for the port 
                 associated with this end-point.  For example, using 
                 this pointer all atm end-points on a given 
                 slot.port can be determined.  Specifically, this is
                 an object identifier specifying the first column of the
                 appropriate row in the atmEndptTable."
        ::= { atmEndptEntry 13  }

atmEndptConnDesc OBJECT-TYPE
    SYNTAX      DisplayString ( SIZE (0..20) )
    ACCESS      read-write
    STATUS      mandatory
    DESCRIPTION "A string that has been defined for the connection to
                 give a more descriptive name.  Connections can be given
                 clear text names in order to make them more human readable."
        ::= { atmEndptEntry 14  }

atmEndptTrkAvoidType OBJECT-TYPE
    SYNTAX      INTEGER {
                none(1),
                satellite(2),
                terrestrial(3)
        }
    ACCESS      read-write
    STATUS      mandatory
    DESCRIPTION "User selectable types of trunks to avoid for the
                 transfer of ATM data.  Current choices are to avoid
                 satellite links, terrestrial links, or to not avoid
                 any specific type of link. This object is optional
                 during the creation of an endpoint."
        ::= { atmEndptEntry 15  }

atmEndptTrkAvoidZCS OBJECT-TYPE
    SYNTAX      INTEGER {
                false(1),
                true(2)
        }
    ACCESS      read-write
    STATUS      mandatory
    DESCRIPTION "Flag to force the connection to avoid trunks with zero
                 code suppression (ZCS). This object is optional during
                 the creation of an endpoint."
        ::= { atmEndptEntry 16  }

atmEndptSubType OBJECT-TYPE
    SYNTAX      INTEGER {
                atf(1),
                vbr(2),
                cbr(3),
                unknown(4),
                abr(5),
                atfst(6)
        }
    ACCESS      read-write
    STATUS      mandatory
    DESCRIPTION "ATM endpoint subtype object.
                atf   - Interworking conn (without Foresight)
                vbr   - Variable Bit Rate Conn (No ForeSight)
                cbr   - Constant Bit Rate Conn (No ForeSight)
                abr   - Available Bit Rte Conn (With ForeSight)
                atfst - Interworking Conn (with ForeSight)." 
        ::= { atmEndptEntry 17  }

atmEndptBWClass OBJECT-TYPE
    SYNTAX      INTEGER (1..10)
    ACCESS      read-write
    STATUS      mandatory
    DESCRIPTION "User selectable connection class which defines the
                 operating parameters for the connection.  Any or
                 all of these parameters can be overridden by
                 specifying the bandwidth parameters directly. This
                 object is required during the creation of an
                 endpoint."
        ::= { atmEndptEntry 18  }
 
atmEndptMIR OBJECT-TYPE
    SYNTAX      INTEGER (0..353208)
    ACCESS      read-write
    STATUS      mandatory
    DESCRIPTION "The minimum transmit bandwidth (MIR) parameter
                 (in cells per second) for this end-point.
                 The maximum value for this object is the port
                 speed of the associated interface.
                 This object does not apply to CBR connections.
                 For VBR and ATF without Foresight connections
                 this object corresponds to the PCR(0+1)
                 parameter defined by ATM standard documents.
                 For ABR and ATF with Foresight connections this
                 object corresponds to the Minimum Cell Rate (MCR)."
        ::= { atmEndptEntry 19 }

atmEndptCIR OBJECT-TYPE
    SYNTAX      INTEGER (7..353208)
    ACCESS      read-write
    STATUS      mandatory
    DESCRIPTION "The value of this object is equal to the committed
                 information rate (CIR) parameter (in cells 
                 per second) for this end-point. 
                 For CBR connections this object corresponds to the
                 PCR(0+1) parameter defined by ATM standard documents.
                 For VBR, ABR, and ATF connections this object
                 corresponds to the Sustainable Cell Rate (SCR) 
                 defined by ATM standard documents.
                 The maximum value for this object is the
                 port speed of the associated interface. 
                 For T3 and E3 interfaces only multiples of 10
                 are used internally. For OC3 interfaces only
                 values in the following set are used internally:
                      11, 17, 23, 34, 45, 68, 90, 136, 181,
                      271, 362, 543, 723, 1085, 1447, 2170,
                      2894, 4340, 5787, 8681, 11574, 17361,
                      23148, 34722, 46296, 69444, 92593,
                      138889, 185185, 277778.
                 Values between 277778 and 353208 are all valid
                 for OC3 interfaces.
                 All values in the valid range for a given 
                 interface will be accepted, but they will be
                 internally rounded up to the closest higher
                 value valid for that interface."
        ::= { atmEndptEntry 20 }

atmEndptVcQSize OBJECT-TYPE
    SYNTAX      INTEGER (1..64000)
    ACCESS      read-write
    STATUS      mandatory
    DESCRIPTION "The value of this object is the maximum queue depth
                 (in cells) for this end-point. This object does not
                 apply to vbr or cbr connections." 
        ::= { atmEndptEntry 21 }

atmEndptPIR OBJECT-TYPE
    SYNTAX      INTEGER (7..353208)
    ACCESS      read-write
    STATUS      mandatory
    DESCRIPTION "The peak transmit bandwidth (PIR) parameter
                 (in cells per second) for this end-point.
                 The maximum value for this object is the
                 port speed of the associated interface.
                 This object applies only to ABR and ATF with
                 Foresight connections and corresponds to the
                 PCR(0+1) parameter defined by ATM standard
                 documents."
        ::= { atmEndptEntry 22 }

atmEndptEfciQSize OBJECT-TYPE
    SYNTAX      INTEGER (1..100)
    ACCESS      read-write
    STATUS      mandatory
    DESCRIPTION "The threshold setting used by the explicit congestion
                 notification feature for this end-point's
                 transmit queue. This value is a percentage.
                 This object does not apply to vbr or cbr connections."
        ::= { atmEndptEntry 23 }

atmEndptQIR OBJECT-TYPE
    SYNTAX      INTEGER (0..96000)
    ACCESS      read-write
    STATUS      mandatory
    DESCRIPTION "The transmit quiescent information rate (QIR) parameter
                 (in cells per second) for this end-point.
                 This value can range between the MIR and PIR values
                 and must be between 0 and 96000.  This parameter
                 has meaning only for Foresight connections.
                 This object corresponds to the Initial Cell Rate (ICR)." 
        ::= { atmEndptEntry 24 }

atmEndptPercUtil OBJECT-TYPE
    SYNTAX      INTEGER (1..100)
    ACCESS      read-write
    STATUS      mandatory
    DESCRIPTION "The value of this object is equal to the channel
                 percentage utilization setting for this end-point.
                 This is the expected long-term utilization of the
                 channel by this end-point."
        ::= { atmEndptEntry 25  }

atmEndptCBS OBJECT-TYPE
    SYNTAX      INTEGER (1..24000) 
    ACCESS      read-write
    STATUS      mandatory
    DESCRIPTION "The value of this object is equal to the Compliant
                 Burst Size in cells for this end-point. The maximum
                 value for this object on OC3 end points is 1000.
                 This object corresponds to the Maximum Burst Size
                 (MBS) defined by ATM standard documents. This 
                 object can be set if atmEndptUPC is enabled."
        ::= { atmEndptEntry 26 }

atmEndptIBS OBJECT-TYPE
    SYNTAX      INTEGER (0..24000) 
    ACCESS      read-write
    STATUS      mandatory
    DESCRIPTION "The value of this object is equal to the Initial 
                 Burst Size in cells for this end-point. The maximum
                 value for this object on OC3 end points is 1000.
                 This object does not apply to vbr or cbr 
                 connections."
        ::= { atmEndptEntry 27 }

atmEndptMFS OBJECT-TYPE
    SYNTAX      INTEGER (1..200) 
    ACCESS      read-write
    STATUS      mandatory
    DESCRIPTION "This object is not used by the new UPC algorithm,
                 and its value is meaningless. Any attempt to write
                 to this object will fail."
        ::= { atmEndptEntry 28 }

atmEndptCCDV OBJECT-TYPE
    SYNTAX      INTEGER (0..250000) 
    ACCESS      read-write
    STATUS      mandatory
    DESCRIPTION "The value of this object is equal to the Compliant
                 Cell Delay Variation for this end-point. It corresponds
                 to the CDVT(0+1) parameter defined by the ATM standard 
                 documents. This object can be set if atmEndptUPC is
                 enabled. The maximum value for this object on OC3 end
                 points is 10000."
        ::= { atmEndptEntry 29 }

atmEndptHiCLP OBJECT-TYPE
    SYNTAX      INTEGER (1..100) 
    ACCESS      read-write
    STATUS      mandatory
    DESCRIPTION "The value of this object is equal to the CLP (Cell
                 Loss Priority) tagging activation threshold for this
                 end-point. This object only applies to Foresight
                 connections."
        ::= { atmEndptEntry 30 }

atmEndptLoCLP OBJECT-TYPE
    SYNTAX      INTEGER (1..100) 
    ACCESS      read-write
    STATUS      mandatory
    DESCRIPTION "The value of this object is equal to the CLP (Cell
                 Loss Priority) tagging deactivation threshold for
                 this end-point. This object only applies to Foresight
                 connections."
        ::= { atmEndptEntry 31 }

atmEndptOeMIR OBJECT-TYPE
    SYNTAX      INTEGER (0..353208)
    ACCESS      read-write
    STATUS      mandatory
    DESCRIPTION "The minimum receive bandwidth (MIR) parameter
                 (in cells per second) for the other end-point.
                 The maximum value for this object is the port
                 speed of the associated interface.
                 This object does not apply to CBR connections.
                 For VBR and ATF without Foresight connections
                 this object corresponds to the PCR(0+1)
                 parameter defined by ATM standard documents.
                 For ABR and ATF with Foresight connections this
                 object corresponds to the Minimum Cell Rate (MCR)."
        ::= { atmEndptEntry 32 }

atmEndptOeCIR OBJECT-TYPE
    SYNTAX      INTEGER (7..353208)
    ACCESS      read-write
    STATUS      mandatory
    DESCRIPTION "The value of this object is equal to the committed
                 information rate (CIR) parameter (in cells 
                 per second) for the other end-point. 
                 For CBR connections this object corresponds to the
                 PCR(0+1) parameter defined by ATM standard documents.
                 For VBR, ABR, and ATF connections this object
                 corresponds to the Sustainable Cell Rate (SCR)
                 defined by ATM standard documents.
                 The maximum value for this object is the
                 port speed of the associated interface.
                 For T3 and E3 interfaces only multiples of 10
                 are used internally. For OC3 interfaces only
                 values in the following set are used internally:
                      11, 17, 23, 34, 45, 68, 90, 136, 181,
                      271, 362, 543, 723, 1085, 1447, 2170,
                      2894, 4340, 5787, 8681, 11574, 17361,
                      23148, 34722, 46296, 69444, 92593,
                      138889, 185185, 277778.
                 Values between 277778 and 353208 are all valid
                 for OC3 interfaces.
                 All values in the valid range for a given 
                 interface will be accepted, but they will be
                 internally rounded up to the closest higher
                 value valid for that interface."
        ::= { atmEndptEntry 33 }

atmEndptOeVcQSize OBJECT-TYPE
    SYNTAX      INTEGER (1..64000)
    ACCESS      read-write
    STATUS      mandatory
    DESCRIPTION "The value of this object is the maximum queue depth
                 (in cells) for the other end-point. This object does
                 not apply to vbr or cbr connections." 
        ::= { atmEndptEntry 34 }

atmEndptOePIR OBJECT-TYPE
    SYNTAX      INTEGER (7..353208)
    ACCESS      read-write
    STATUS      mandatory
    DESCRIPTION "The peak receive bandwidth (PIR) parameter
                 (in cells per second) for the other end-point.
                 The maximum value for this object is the
                 port speed of the associated interface.
                 This object applies only to ABR and ATF with
                 Foresight connections and corresponds to the
                 PCR(0+1) parameter defined by ATM standard
                 documents."
        ::= { atmEndptEntry 35 }

atmEndptOeEfciQSize OBJECT-TYPE
    SYNTAX      INTEGER (1..100)
    ACCESS      read-write
    STATUS      mandatory
    DESCRIPTION "The threshold setting used by the explicit congestion
                 notification feature for the other end-point's
                 transmit queue. This object does not apply to vbr or
                 cbr connections."
        ::= { atmEndptEntry 36 }

atmEndptOeQIR OBJECT-TYPE
    SYNTAX      INTEGER (0..96000)
    ACCESS      read-write
    STATUS      mandatory
    DESCRIPTION "The transmit quiescent information rate (QIR) parameter
                 (in cells bits per second) for the other end-point.
                 This value can range between the MIR and PIR values
                 and must be between 0 and 96000.  This parameter
                 has meaning only for Foresight connections.
                 This object corresponds to the Initial Cell Rate (ICR)."
        ::= { atmEndptEntry 37 }

atmEndptOePercUtil OBJECT-TYPE
    SYNTAX      INTEGER (1..100)
    ACCESS      read-write
    STATUS      mandatory
    DESCRIPTION "The value of this object is equal to the channel
                 percentage utilization setting for the other end-point.
                 This is the expected long-term utilization of the
                 channel by the other end-point."
        ::= { atmEndptEntry 38 }

atmEndptOeCBS OBJECT-TYPE
    SYNTAX      INTEGER (1..24000) 
    ACCESS      read-write
    STATUS      mandatory
    DESCRIPTION "The value of this object is equal to the Compliant
                 Burst Size in cells for the other end-point. The
                 maximum value for this object on OC3 end points
                 is 1000. This object corresponds to the Maximum 
                 Burst Size (MBS) defined by ATM standard documents.
                 This object can be set if atmEndptUPC is enabled."
        ::= { atmEndptEntry 39 }

atmEndptOeIBS OBJECT-TYPE
    SYNTAX      INTEGER (0..24000) 
    ACCESS      read-write
    STATUS      mandatory
    DESCRIPTION "The value of this object is equal to the Initial 
                 Burst Size in cells for the other end-point. The
                 maximum value for this object on OC3 end points
                 is 1000. This object does not apply to vbr or cbr
                 connections."
        ::= { atmEndptEntry 40 }

atmEndptOeMFS OBJECT-TYPE
    SYNTAX      INTEGER (1..200) 
    ACCESS      read-write
    STATUS      mandatory
    DESCRIPTION "This object is not used by the new UPC algorithm,
                 and its value is meaningless. Any attempt to write
                 to this object will fail."
        ::= { atmEndptEntry 41 }

atmEndptOeCCDV OBJECT-TYPE
    SYNTAX      INTEGER (0..250000) 
    ACCESS      read-write
    STATUS      mandatory
    DESCRIPTION "The value of this object is equal to the Compliant
                 Cell Delay Variation for this end-point. It corresponds
                 to the CDVT(0+1) parameter defined by the ATM standard 
                 documents. This object can be set if atmEndptUPC is
                 enabled. The maximum value for this object on OC3 end
                 points is 10000."
        ::= { atmEndptEntry 42 }

atmEndptOeHiCLP OBJECT-TYPE
    SYNTAX      INTEGER (1..100) 
    ACCESS      read-write
    STATUS      mandatory
    DESCRIPTION "The value of this object is equal to the CLP (Cell
                 Loss Priority) tagging activation threshold for the
                 other end-point. This object only applies to Foresight
                 connections."
        ::= { atmEndptEntry 43 }

atmEndptOeLoCLP OBJECT-TYPE
    SYNTAX      INTEGER (1..100) 
    ACCESS      read-write
    STATUS      mandatory
    DESCRIPTION "The value of this object is equal to the CLP (Cell
                 Loss Priority) tagging deactivation threshold for
                 the other end-point. This object only applies to
                 Foresight connections."
        ::= { atmEndptEntry 44 }

atmEndptCLPTagging OBJECT-TYPE
    SYNTAX      INTEGER {
                enable(1),
                disable(2)
        }
    ACCESS      read-write
    STATUS      mandatory
    DESCRIPTION "The value of this object enables the CLP (Cell
                 Loss Priority) tagging for handling non-compliant
                 cells. When enabled the CLP bit is set on non-
                 compliant cells. When disabled non-compliant
                 cells are discarded. This object can be set
                 if atmEndptUPC is enabled."
        ::= { atmEndptEntry 45 }

atmEndptUPC OBJECT-TYPE
    SYNTAX      INTEGER {
                enable(1),
                disable(2)
        }
    ACCESS      read-write
    STATUS      mandatory
    DESCRIPTION "The value of this object enables the UPC algorithm."
        ::= { atmEndptEntry 46 }
 
atmEndptEnableFST OBJECT-TYPE
    SYNTAX      INTEGER {
                enable(1),
                disable(2)
        }
    ACCESS      read-write
    STATUS      mandatory
    DESCRIPTION "The value of this object determines whether or not the
                 ForeSight option is being used for this .  If set
                 to false, then ForeSight is not used, and if true then
                 ForeSight will be used. Foresight option is not 
                 supported on OC3 interfaces."
        ::= { atmEndptEntry 47 }

atmEndptRateUpICA OBJECT-TYPE
    SYNTAX      INTEGER (10..96000)
    ACCESS      read-write
    STATUS      mandatory
    DESCRIPTION "The value of this object is equal to the ForeSight
                 Rate Up value in cells per second per adjust for
                 this end point." 
        ::= { atmEndptEntry 48 }

atmEndptRateDnICA OBJECT-TYPE
    SYNTAX      INTEGER (1..100)
    ACCESS      read-write
    STATUS      mandatory
    DESCRIPTION "The value of this object is equal to the ForeSight
                 Rate Down value expressed as percentage of MCR." 
        ::= { atmEndptEntry 49 }

atmEndptFastDnICA OBJECT-TYPE
    SYNTAX      INTEGER (1..100)
    ACCESS      read-write
    STATUS      mandatory
    DESCRIPTION "The value of this object is equal to the ForeSight
                 Fast Down value expressed as percentage of MCR." 
        ::= { atmEndptEntry 50 }

atmEndptToQIR OBJECT-TYPE
    SYNTAX      INTEGER (1..255) 
    ACCESS      read-write
    STATUS      mandatory
    DESCRIPTION "The value of this object is equal to the QIR timeout
                 value. This object corresponds to the Initial Cell
                 Rate (ICR) timeout."
        ::= { atmEndptEntry 51 }

atmEndptMinAdjustICA  OBJECT-TYPE
    SYNTAX      INTEGER (20..250) 
    ACCESS      read-write
    STATUS      mandatory
    DESCRIPTION "The value of this object is equal to the ForeSight 
                 minimum adjustment period."
        ::= { atmEndptEntry 52 }

atmEndptGroupFlag OBJECT-TYPE
    SYNTAX      INTEGER {
                false(1),
                true(2)
        }
    ACCESS      read-only
    STATUS      mandatory
    DESCRIPTION "Specifies whether this is a grouped connection. Note 
                 that MIB object connGroupFlag provides grouping 
                 information about all the connections using that
                 connTable entry whereas this object provides same 
                 information for this end point."
        ::= { atmEndptEntry 53 }

atmEndptOamStatus  OBJECT-TYPE
    SYNTAX      INTEGER {
                unknown(1),
                clear(2),
                aisDetected(3),
                ferfDetected(4)
        }
    ACCESS      read-only
    STATUS      mandatory
    DESCRIPTION "The end to end OAM state."
        ::= { atmEndptEntry 54 }
 
atmEndptBCM OBJECT-TYPE
    SYNTAX      INTEGER {
                enable (1),
                disable (2)
    }
    ACCESS      read-write
    STATUS      mandatory
    DESCRIPTION "The value of this object enables the generation
                 of RM cells when congestion is detected in this
                 connection."
        ::= { atmEndptEntry 55 }
 
atmEndptFGCRA OBJECT-TYPE
    SYNTAX      INTEGER {
                enable(1),
                disable(2)
        }
    ACCESS      read-write
    STATUS      mandatory
    DESCRIPTION "The value of this object enables FGCRA.
                 FGCRA (Frame-based Generic Rate Control Algorithm)
                 is applicable with AAL-5 traffic only. This object
                 can be set if atmEndptUPC is enabled."
        ::= { atmEndptEntry 56 }
 
atmEndptLocLpbkState OBJECT-TYPE
    SYNTAX      INTEGER {
                enable(1),
                disable(2)
        }
    ACCESS      read-write
    STATUS      mandatory
    DESCRIPTION "Specifies the Local Loopback State the user would
                 like to set for the endpoint."
        ::= { atmEndptEntry 57 }
 
atmEndptLpbkStatus OBJECT-TYPE
    SYNTAX      INTEGER
    ACCESS      read-only
    STATUS      mandatory
    DESCRIPTION "Specifies the current Loopback State of the endpoint.
                 The value returned from this object is a bitmap
                 of the current loopback states which the endpoint
                 has configured.  There currently are 16 loopback
                 states an endpoint may have configured. The bitmap
                 is defined as follows from LSB to MSB:
                 Remote nodes remote muxbus loopback
                 Remote nodes tstcon loopback
                 Local  nodes remoet muxbus loopback
                 Local  nodes tstcon loopback
                 Local  nodes local muxbus loopback
                 Local  nodes port loopback
                 Local  nodes port test loopback
                 Remote nodes local muxbus loopback
                 Remote nodes port loopback
                 Remote nodes port test looback
                 Local  DDS network requested CSU loopback
                 Remote DDS network requested CSU loopback
                 Local  DDS network requested DSU loopback
                 Remote DDS network requested DSU loopback
                 Local  DDS external loopback
                 Remote DDS external loopback
                 "
        ::= { atmEndptEntry 58 }
 
atmEndptTestType OBJECT-TYPE
    SYNTAX      INTEGER {
                testDelay(1),
                writeOnly(2)
        }
    ACCESS      read-write
    STATUS      mandatory
    DESCRIPTION "Specifies the type of test the user would like to
                 conduct on this endpoint.  Only testDelay is currently
                 defined. TestDelay calculates the delay incurred on
                 the connection.  The result of the TestDelay may then
                 be accessed through the atmEndptRtdTestDelay object.
                 This is a non-disruptive test."
        ::= { atmEndptEntry 59 }
 
atmEndptRtdTestDelay OBJECT-TYPE
    SYNTAX      INTEGER
    ACCESS      read-only
    STATUS      mandatory
    DESCRIPTION "The value of this object is the calculated round
                 trip delay (measured in milliseconds) for an OAM
                 cell that is sent across the network to the remote
                 node where it is looped back and returned to this
                 node.
                 A delay test is invoked through setting the
                 the atmEndptTestType object to TestDelay."
        ::= { atmEndptEntry 60 }
  
atmEndptOeBCM OBJECT-TYPE
    SYNTAX      INTEGER {
                enable (1),
                disable (2)
    }
    ACCESS      read-write
    STATUS      mandatory
    DESCRIPTION "The value of this object enables the generation
                 of RM cells when congestion is detected in this
                 connection. This is the other endpoint view."
        ::= { atmEndptEntry 61 }
 
atmEndptOeFGCRA OBJECT-TYPE
    SYNTAX      INTEGER {
                enable(1),
                disable(2)
        }
    ACCESS      read-write
    STATUS      mandatory
    DESCRIPTION "The value of this object enables FGCRA.
                 FGCRA (Frame-based Generic Rate Control Algorithm)
                 is applicable with AAL-5 traffic only. This object
                 can be set if atmEndptUPC is enabled. This is the
                 other endpoint view."
        ::= { atmEndptEntry 62 }

atmEndptGroupDesc OBJECT-TYPE
    SYNTAX      DisplayString
    ACCESS      read-write
    STATUS      mandatory
    DESCRIPTION "String describing the group this endpoint is
                 associated with.  The format of the group text
                 description is domain.node.grp-number (Example,
                 D2.node1.1)."
        ::= { atmEndptEntry 63 }

atmEndptLocRmtLpbkState OBJECT-TYPE
    SYNTAX      INTEGER {
                enable(1),
                disable(2)
        }
    ACCESS      read-write
    STATUS      mandatory
    DESCRIPTION "Specifies the Local-Remote Loopback State the user
                 would like to set for the endpoint."
        ::= { atmEndptEntry 64 }
 
atmEndptScrPlc OBJECT-TYPE
    SYNTAX      INTEGER {
                clp0(1),
                clp0and1(2),
                off(3)
    }
    ACCESS      read-write
    STATUS      mandatory
    DESCRIPTION "Specifies the traffic policing for this end point
                 This object can be set only if atmEndptUPC is
                 enabled."
        ::= { atmEndptEntry 65 }
 
atmEndptOeScrPlc OBJECT-TYPE
    SYNTAX      INTEGER {
                clp0(1),
                clp0and1(2),
                off(3)
    }
    ACCESS      read-write
    STATUS      mandatory
    DESCRIPTION "Specifies the traffic policing for the other end
                 point. This object can be set only if atmEndptUPC
                 is enabled." 
        ::= { atmEndptEntry 66 }

atmEndptPCR0 OBJECT-TYPE
    SYNTAX      INTEGER (7..353208)
    ACCESS      read-write
    STATUS      mandatory
    DESCRIPTION "The peak cell rate (in cells per second) for the
                 second bucket for this end point. This object
                 corresponds to the parameter PCR(0) in standard
                 ATM documents and applies only to CBR connections.
                 This object can be set only if atmEndptUPC is
                 enabled. PCR(0) must be less or equal than
                 PCR(0+1)."
        ::= { atmEndptEntry 67 }
 
atmEndptOePCR0 OBJECT-TYPE
    SYNTAX      INTEGER (7..353208)
    ACCESS      read-write
    STATUS      mandatory
    DESCRIPTION "The peak cell rate (in cells per second) for the
                 second bucket for the other end point. This object
                 corresponds to the parameter PCR(0) in standard
                 ATM documents and applies only to CBR connections.
                 This object can be set only if atmEndptUPC is
                 enabled. PCR(0) must be less or equal than 
                 PCR(0+1)."
        ::= { atmEndptEntry 68 }
 
atmEndptCDVT0 OBJECT-TYPE
    SYNTAX      INTEGER (1..250000)
    ACCESS      read-write
    STATUS      mandatory
    DESCRIPTION "The cell delay variation tolerance for the second
                 bucket for this end point. This object corresponds
                 to the parameter CDVT(0) in standard ATM documents,
                 and applies only to CBR connections. This object
                 can be set only if atmEndptUPC is enabled."
        ::= { atmEndptEntry 69 }
 
atmEndptOeCDVT0 OBJECT-TYPE
    SYNTAX      INTEGER (1..250000)
    ACCESS      read-write
    STATUS      mandatory
    DESCRIPTION "The cell delay variation tolerance for the second
                 bucket for the other end point. This object corresponds
                 to the parameter CDVT(0) in standard ATM documents,
                 and applies only to CBR connections. This object 
                 can be set only if atmEndptUPC is enabled."
        ::= { atmEndptEntry 70 }
 
atmEndptOeRateUpICA OBJECT-TYPE
    SYNTAX      INTEGER (10..96000)
    ACCESS      read-write
    STATUS      mandatory
    DESCRIPTION "The value of this object is equal to the ForeSight
                 Rate Up value in cells per second per adjust for
                 the other end point."
        ::= { atmEndptEntry 71 }

-- The remaining entries come from the 9.1 Mib, we include them here so we can
-- have atmEndptPCR in our pcm file.

atmEndptFRTT OBJECT-TYPE
    SYNTAX      INTEGER (0..16700)
    ACCESS      read-write
    STATUS      mandatory
    DESCRIPTION "The Fixed Round-Trip Time (FRTT) is the sum of the fixed
                 and propagation delays from the source to a destination 
                 and back.
                 . Units: milliseconds.
                 . Applicable connection types: standard ABR only
                 . Default: 0
                 . Dependency: VSVD = enable(1)
                 "
        ::= { atmEndptEntry 72 }
 
atmEndptTBE OBJECT-TYPE
    SYNTAX      INTEGER (0..1048320)
    ACCESS      read-write
    STATUS      mandatory
    DESCRIPTION "Transient Buffer Exposure (TBE) is the negotiated number
                 of cells that the network would like to limit the source 
                 to sending during startup periods, before the first 
                 RM-cell returns.
                 . Units: cells
                 . Applicable connection types: standard ABR only
                 . Default: 1048320
                 . Dependency: VSVD = enable(1)
                 "
        ::= { atmEndptEntry 73 }
        
atmEndptVSVD OBJECT-TYPE
    SYNTAX      INTEGER {
                enable (1),
                disable (2)
    }
    ACCESS      read-write
    STATUS      mandatory
    DESCRIPTION "Virtual Source/Virtual Destination (VS/VD) is used to 
                 divide an ABR connection into two or more separately 
                 controlled ABR segment. This flag indicates whether
                 the ATM end points (both ends) will serve as VS/VD
                 or not.                 
                 . Applicable connection types:
                   . standard ABR
                   . ABRFST: Cannot be set, but always enable(1). 
                   . ATFST  : Cannot be set, but always enable(1).
                 . Dependency:
                   . The object CANNOT be MODIFIED after the first set!
                     All Subsequent sets will be rejected!
                     The object can be set  when only add ABRSTD connection.
                    ============================================
                    ABRSTD VSVD option     ABRSTD  ABRFST  ATFST
                    =============================================
                    available                Both   (Yes)  (Yes)
                    unavalable               No     (Yes)  (Yes)
                    Note:
                     . Yes  = Has to be set to enable(1) 
                       No   = Has to be set to disable(2)
                       Both = can be set to either enable(1) or disable(2)
                      (Yes) = Always enabled and cannot be set.
                      (No)  = Always disabled and cannot be set.
                 . Default: disable(2)
                 "
        ::= { atmEndptEntry 74 }
  
atmEndptPolicing OBJECT-TYPE
    SYNTAX      INTEGER {
                vbr1 (1),
                vbr2 (2),
                vbr3 (3),
                pcrplc(4),
                none  (5)
   }
    ACCESS      read-write
    STATUS      mandatory
    DESCRIPTION "Specifies the traffic policing for this end point.
                 --------------- ---------- ----------  
                  Policing Type  1st Bucket 2nd Bucket 
                 --------------- ---------- ----------
                   vbr.1          CLP(0+1)   CLP(0+1)            
                   vbr.2          CLP(0+1)   CLP(0)     
                   vbr.3          CLP(0+1)   CLP(0) with CLP Tagging
                   pcrplc         CLP(0+1)   none
                   none           none       none
                   
                 . Applicable connection types:
                   . CBR (only pcrplc(4) or none(5)), VBR, ATFR, 
                   . standard ABR, ABR FST, ATFST: VSVD = enable(1)
                 . Default: vbr3(3)
                 . Dependency: Not allowed for standard ABR without VSVD.
                               In this case, it is set to pcrplc(4).
                 "
        ::= { atmEndptEntry 75 }

atmEndptPCR   OBJECT-TYPE
    SYNTAX      INTEGER (50..1412832)
    ACCESS      read-write
    STATUS      mandatory
    DESCRIPTION "PCR(0+1), Peak Cell Rate, specifies an upper bound on
                 rate at which traffic can be submitted on an ATM
                 connection. This object applies to the First Leaky
                 Bucket for leaving cells with Cell Loss Priority of 0 or 1.
                 . Units: cells per second.
                 . Applicable connection types:
                   UBR, CBR, VBR, ATFR, standard ABR, ABR FST, ATFST
                 . Default: 50 or MCR
                 . Ranges:
                   T3  : MCR-96000
                   E3  : MCR-80000
                   OC3 : MCR-353208
                   OC12: MCR-1412832
                "
        ::= { atmEndptEntry 76 }

 


-- This table describes ATM bandwith classes available on 
-- the switch. In order to avoid specifying all the bandwidth parameters
-- while creating an ATM connection, the user can specify an
-- ATM bandwidth class by number (available as index into
-- this table). 
-- This table is only applicable on the BPX switch.
--
atmBwClassTable OBJECT-TYPE
    SYNTAX      SEQUENCE OF AtmBwClassEntry
    ACCESS      not-accessible
    STATUS      mandatory
    DESCRIPTION "The ATM Bandwidth Class table."
    --DEFAULT   test-function   test-atmbwclasstable
    --DEFAULT   next-function   next-atmbwclasstable
    --DEFAULT   get-function    get-atmbwclasstable-%t
    --DEFAULT   view-mask       BPX-VIEW 
        ::= { switchConnection 9  }
 
atmBwClassEntry OBJECT-TYPE
    SYNTAX      AtmBwClassEntry
    ACCESS      not-accessible
    STATUS      mandatory
    DESCRIPTION "An entry in the ATM Bandwidth Class table."
    INDEX   { atmBwClassIndex }
        ::= { atmBwClassTable 1  }
 
AtmBwClassEntry ::=
    SEQUENCE {
        atmBwClassIndex          INTEGER,

        atmBwClassMIR            INTEGER,
        atmBwClassCIR            INTEGER,
        atmBwClassVcQSize        INTEGER,
        atmBwClassPIR            INTEGER,
        atmBwClassEfciQSize      INTEGER,
        atmBwClassQIR            INTEGER,
        atmBwClassPercUtil       INTEGER,
        atmBwClassCBS            INTEGER,
        atmBwClassIBS            INTEGER,
        atmBwClassMFS            INTEGER,
        atmBwClassCCDV           INTEGER,
        atmBwClassHiCLP          INTEGER,
        atmBwClassLoCLP          INTEGER,

        atmBwClassOeMIR          INTEGER,
        atmBwClassOeCIR          INTEGER,
        atmBwClassOeVcQSize      INTEGER,
        atmBwClassOePIR          INTEGER,
        atmBwClassOeEfciQSize    INTEGER,
        atmBwClassOeQIR          INTEGER,
        atmBwClassOePercUtil     INTEGER,
        atmBwClassOeCBS          INTEGER,
        atmBwClassOeIBS          INTEGER,
        atmBwClassOeMFS          INTEGER,
        atmBwClassOeCCDV         INTEGER,
        atmBwClassOeHiCLP        INTEGER,
        atmBwClassOeLoCLP        INTEGER,

        atmBwClassCLPTagging     INTEGER,
        atmBwClassUPC            INTEGER,
        atmBwClassEnableFST      INTEGER,
        atmBwClassRateUpICA      INTEGER,
        atmBwClassRateDnICA      INTEGER,
        atmBwClassFastDnICA      INTEGER,
        atmBwClassToQIR          INTEGER,
        atmBwClassMinAdjustICA   INTEGER,
        atmBwClassDescription    DisplayString,

        atmBwClassBCM            INTEGER,
        atmBwClassOeFGCRA        INTEGER,
        atmBwClassOeBCM          INTEGER,
        atmBwClassFGCRA          INTEGER,
        atmBwClassConType        INTEGER,

        atmBwClassScrPlc            INTEGER,
        atmBwClassOeScrPlc          INTEGER,
        atmBwClassPCR0              INTEGER,
        atmBwClassOePCR0            INTEGER,
        atmBwClassCDVT0             INTEGER,
        atmBwClassOeCDVT0           INTEGER,
        atmBwClassOeRateUpICA       INTEGER

    }

atmBwClassIndex OBJECT-TYPE
    SYNTAX      INTEGER (1..10)
    ACCESS      read-only
    STATUS      mandatory
    DESCRIPTION "Index into atmBwClassTable. This index identifies the
                 ATM bandwidth class."
        ::= { atmBwClassEntry 1  }

atmBwClassMIR OBJECT-TYPE
    SYNTAX      INTEGER (0..353208)
    ACCESS      read-only
    STATUS      mandatory
    DESCRIPTION "The minimum transmit bandwidth (MIR) parameter
                 (in cells per second) for this end-point.
                 For VBR and ATF without Foresight connections
                 this object corresponds to the PCR(0+1)
                 parameter defined by ATM standard documents.
                 For ABR and ATF with Foresight connections this
                 object corresponds to the Minimum Cell Rate (MCR)."
        ::= { atmBwClassEntry 2  }

atmBwClassCIR OBJECT-TYPE
    SYNTAX      INTEGER (7..353208)
    ACCESS      read-only
    STATUS      mandatory
    DESCRIPTION "The value of this object is equal to the committed
                 information rate (CIR) parameter (in cells 
                 per second) for this end-point.
                 For CBR connections this object corresponds to the
                 PCR(0+1) parameter defined by ATM standard documents.
                 For VBR, ABR, and ATF connections this object
                 corresponds to the Sustainable Cell Rate (SCR)
                 defined by ATM standard documents."
        ::= { atmBwClassEntry 3  }

atmBwClassVcQSize OBJECT-TYPE
    SYNTAX      INTEGER (1..64000)
    ACCESS      read-only
    STATUS      mandatory
    DESCRIPTION "The value of this object is the maximum queue depth
                 (in cells) for this end-point."
        ::= { atmBwClassEntry 4  }

atmBwClassPIR OBJECT-TYPE
    SYNTAX      INTEGER (7..96000)
    ACCESS      read-only
    STATUS      mandatory
    DESCRIPTION "The peak transmit bandwidth (PIR) parameter
                 (in cells per second) for this end-point.
                 This object applies only to ABR and ATF with
                 Foresight connections and corresponds to the
                 PCR(0+1) parameter defined by ATM standard
                 documents."
        ::= { atmBwClassEntry 5  }

atmBwClassEfciQSize OBJECT-TYPE
    SYNTAX      INTEGER (1..100)
    ACCESS      read-only
    STATUS      mandatory
    DESCRIPTION "The threshold setting used by the explicit congestion
                 notification feature for this end-point's
                 transmit queue.  This value is a percentage."
        ::= { atmBwClassEntry 6  }

atmBwClassQIR OBJECT-TYPE
    SYNTAX      INTEGER (0..96000)
    ACCESS      read-only
    STATUS      mandatory
    DESCRIPTION "The transmit quiescent information rate (QIR) parameter
                 (in cells per second) for this end-point.
                 This value can range between the MIR and PIR values
                 and must be between 0 and 96000.  This parameter
                 has meaning only for Foresight connections.
                 This object corresponds to the Initial Cell Rate (ICR)."
        ::= { atmBwClassEntry 7  }

atmBwClassPercUtil OBJECT-TYPE
    SYNTAX      INTEGER (1..100)
    ACCESS      read-only
    STATUS      mandatory
    DESCRIPTION "The value of this object is equal to the channel
                 percentage utilization setting for this end-point.
                 This is the expected long-term utilization of the
                 channel by this end-point."
        ::= { atmBwClassEntry 8  }

atmBwClassCBS OBJECT-TYPE
    SYNTAX      INTEGER (1..24000) 
    ACCESS      read-only
    STATUS      mandatory
    DESCRIPTION "The value of this object is equal to the Compliant
                 Burst Size in cells for this end-point.
                 This object corresponds to the Maximum Burst Size
                 (MBS) defined by ATM standard documents."
        ::= { atmBwClassEntry 9  }

atmBwClassIBS OBJECT-TYPE
    SYNTAX      INTEGER (0..24000) 
    ACCESS      read-only
    STATUS      mandatory
    DESCRIPTION "The value of this object is equal to the Initial 
                 Burst Size in cells for this end-point."
        ::= { atmBwClassEntry 10  }

atmBwClassMFS OBJECT-TYPE
    SYNTAX      INTEGER (1..200) 
    ACCESS      read-only
    STATUS      mandatory
    DESCRIPTION "This object is not used by the new UPC algorithm,
                 and its value is meaningless."
        ::= { atmBwClassEntry 11  }

atmBwClassCCDV OBJECT-TYPE
    SYNTAX      INTEGER (0..250000) 
    ACCESS      read-only
    STATUS      mandatory
    DESCRIPTION "The value of this object is equal to the Compliant
                 Cell Delay Variation for this end-point.
                 It corresponds to the CDVT(0+1) parameter defined
                 by the ATM standard documents."
        ::= { atmBwClassEntry 12  }

atmBwClassHiCLP OBJECT-TYPE
    SYNTAX      INTEGER (1..100) 
    ACCESS      read-only
    STATUS      mandatory
    DESCRIPTION "The value of this object is equal to the CLP (Cell
                 Loss Priority) tagging activation threshold for
                 this end-point."
        ::= { atmBwClassEntry 13  }

atmBwClassLoCLP OBJECT-TYPE
    SYNTAX      INTEGER (1..100) 
    ACCESS      read-only
    STATUS      mandatory
    DESCRIPTION "The value of this object is equal to the CLP (Cell
                 Loss Priority) tagging deactivation threshold for
                 this end-point."
        ::= { atmBwClassEntry 14  }

atmBwClassOeMIR OBJECT-TYPE
    SYNTAX      INTEGER (0..353208)
    ACCESS      read-only
    STATUS      mandatory
    DESCRIPTION "The minimum receive bandwidth (MIR) parameter
                 (in cells per second) for the other end-point.
                 For VBR and ATF without Foresight connections
                 this object corresponds to the PCR(0+1)
                 parameter defined by ATM standard documents.
                 For ABR and ATF with Foresight connections this
                 object corresponds to the Minimum Cell Rate (MCR)."
        ::= { atmBwClassEntry 15  }

atmBwClassOeCIR OBJECT-TYPE
    SYNTAX      INTEGER (7..353208)
    ACCESS      read-only
    STATUS      mandatory
    DESCRIPTION "The value of this object is equal to the committed
                 information rate (CIR) parameter (in cells 
                 per second) for the other end-point.
                 For CBR connections this object corresponds to the
                 PCR(0+1) parameter defined by ATM standard documents.
                 For VBR, ABR, and ATF connections this object
                 corresponds to the Sustainable Cell Rate (SCR)
                 defined by ATM standard documents."
        ::= { atmBwClassEntry 16  }

atmBwClassOeVcQSize OBJECT-TYPE
    SYNTAX      INTEGER (1..64000)
    ACCESS      read-only
    STATUS      mandatory
    DESCRIPTION "The value of this object is the maximum queue depth
                 (in cells) for the other end-point."
        ::= { atmBwClassEntry 17  }

atmBwClassOePIR OBJECT-TYPE
    SYNTAX      INTEGER (7..96000)
    ACCESS      read-only
    STATUS      mandatory
    DESCRIPTION "The peak receive bandwidth (PIR) parameter
                 (in cells per second) for the other end-point.
                 This object applies only to ABR and ATF with
                 Foresight connections and corresponds to the
                 PCR(0+1) parameter defined by ATM standard
                 documents."
        ::= { atmBwClassEntry 18  }

atmBwClassOeEfciQSize OBJECT-TYPE
    SYNTAX      INTEGER (1..100)
    ACCESS      read-only
    STATUS      mandatory
    DESCRIPTION "The threshold setting used by the explicit congestion
                 notification feature for the other end-point's
                 transmit queue."
        ::= { atmBwClassEntry 19  }

atmBwClassOeQIR OBJECT-TYPE
    SYNTAX      INTEGER (0..96000)
    ACCESS      read-only
    STATUS      mandatory
    DESCRIPTION "The transmit quiescent information rate (QIR) parameter
                 (in cells bits per second) for the other end-point.
                 This value can range between the MIR and PIR values
                 and must be between 0 and 96000.  This parameter
                 has meaning only for Foresight connections.
                 This object corresponds to the Initial Cell Rate (ICR)."
        ::= { atmBwClassEntry 20  }

atmBwClassOePercUtil OBJECT-TYPE
    SYNTAX      INTEGER (1..100)
    ACCESS      read-only
    STATUS      mandatory
    DESCRIPTION "The value of this object is equal to the channel
                 percentage utilization setting for the other end-point.
                 This is the expected long-term utilization of the
                 channel by the other end-point."
        ::= { atmBwClassEntry 21  }

atmBwClassOeCBS OBJECT-TYPE
    SYNTAX      INTEGER (1..24000) 
    ACCESS      read-only
    STATUS      mandatory
    DESCRIPTION "The value of this object is equal to the Compliant
                 Burst Size in cells for the other end-point.
                 This object corresponds to the Maximum Burst Size
                 (MBS) defined by ATM standard documents."
        ::= { atmBwClassEntry 22  }

atmBwClassOeIBS OBJECT-TYPE
    SYNTAX      INTEGER (0..24000) 
    ACCESS      read-only
    STATUS      mandatory
    DESCRIPTION "The value of this object is equal to the Initial 
                 Burst Size in cells for the other end-point."
        ::= { atmBwClassEntry 23  }

atmBwClassOeMFS OBJECT-TYPE
    SYNTAX      INTEGER (1..200) 
    ACCESS      read-only
    STATUS      mandatory
    DESCRIPTION "This object is not used by the new UPC algorithm,
                 and its value is meaningless."
        ::= { atmBwClassEntry 24  }

atmBwClassOeCCDV OBJECT-TYPE
    SYNTAX      INTEGER (0..250000) 
    ACCESS      read-only
    STATUS      mandatory
    DESCRIPTION "The value of this object is equal to the Compliant
                 Cell Delay Variation for the other end-point.
                 It corresponds to the CDVT(0+1) parameter defined
                 by the ATM standard documents."
        ::= { atmBwClassEntry 25  }

atmBwClassOeHiCLP OBJECT-TYPE
    SYNTAX      INTEGER (1..100) 
    ACCESS      read-only
    STATUS      mandatory
    DESCRIPTION "The value of this object is equal to the CLP (Cell
                 Loss Priority) tagging activation threshold for the
                 other end-point."
        ::= { atmBwClassEntry 26 }

atmBwClassOeLoCLP OBJECT-TYPE
    SYNTAX      INTEGER (1..100) 
    ACCESS      read-only
    STATUS      mandatory
    DESCRIPTION "The value of this object is equal to the CLP (Cell
                 Loss Priority) tagging deactivation threshold for
                 the other end-point."
        ::= { atmBwClassEntry 27 }

atmBwClassCLPTagging OBJECT-TYPE
    SYNTAX      INTEGER {
                enabled(1),
                disabled(2)
        }
    ACCESS      read-only
    STATUS      mandatory
    DESCRIPTION "The value of this object enables the CLP (Cell
                 Loss Priority) tagging for handling non-compliant
                 cells. When enabled the CLP bit is set on non-
                 compliant cells. When disabled non-compliant
                 cells are discarded."
        ::= { atmBwClassEntry 28 }

atmBwClassUPC OBJECT-TYPE
    SYNTAX      INTEGER {
                enable(1),
                disable(2)
        }
    ACCESS      read-only
    STATUS      mandatory
    DESCRIPTION "The value of this object enables the UPC algorithm."
        ::= { atmBwClassEntry 29 }

atmBwClassEnableFST OBJECT-TYPE
    SYNTAX      INTEGER {
                enable(1),
                disable(2)
        }
    ACCESS      read-only
    STATUS      mandatory
    DESCRIPTION "The value of this object determines whether or not the
                 ForeSight option is being used for this .  If set
                 to false, then ForeSight is not used, and if true then
                 ForeSight will be used."
        ::= { atmBwClassEntry 30 }

atmBwClassRateUpICA OBJECT-TYPE
    SYNTAX      INTEGER (10..96000)
    ACCESS      read-only
    STATUS      mandatory
    DESCRIPTION "The value of this object is equal to the ForeSight
                 Rate Up value in cells per second per adjust for
                 this end point." 
        ::= { atmBwClassEntry 31 }

atmBwClassRateDnICA OBJECT-TYPE
    SYNTAX      INTEGER (1..100)
    ACCESS      read-only
    STATUS      mandatory
    DESCRIPTION "The value of this object is equal to the ForeSight
                 Rate Down value expressed as percentage of MCR." 
        ::= { atmBwClassEntry 32 }

atmBwClassFastDnICA OBJECT-TYPE
    SYNTAX      INTEGER (1..100)
    ACCESS      read-only
    STATUS      mandatory
    DESCRIPTION "The value of this object is equal to the ForeSight
                 Fast Down value expressed as percentage of MCR." 
        ::= { atmBwClassEntry 33 }

atmBwClassToQIR OBJECT-TYPE
    SYNTAX      INTEGER (1..255)
    ACCESS      read-only
    STATUS      mandatory
    DESCRIPTION "The value of this object is equal to the QIR timeout
                 value. This object corresponds to the Initial Cell
                 Rate (ICR) timeout."
        ::= { atmBwClassEntry 34 }

atmBwClassMinAdjustICA  OBJECT-TYPE
    SYNTAX      INTEGER (20..250) 
    ACCESS      read-only
    STATUS      mandatory
    DESCRIPTION "The value of this object is equal to the ForeSight 
                 minimum adjustment period."
        ::= { atmBwClassEntry 35 }

atmBwClassDescription  OBJECT-TYPE
    SYNTAX      DisplayString ( SIZE (0..24) )
    ACCESS      read-only
    STATUS      mandatory
    DESCRIPTION "This MIB object contains a textual description of this
                 frame relay bandwidth class."
        ::= { atmBwClassEntry 36 }

atmBwClassBCM OBJECT-TYPE
    SYNTAX      INTEGER {
                enable(1),
                disable(2)
        }
    ACCESS      read-only
    STATUS      mandatory
    DESCRIPTION "The value of this object enables the generation
                 of RM cells when congestion is detected in the
                 connection."
        ::= { atmBwClassEntry 37 }
 
atmBwClassFGCRA OBJECT-TYPE
    SYNTAX      INTEGER {
                enable(1),
                disable(2)
        }
    ACCESS      read-only
    STATUS      mandatory
    DESCRIPTION "The value of this object enables FGCRA.
                 FGCRA (Frame-based Generic Rate Control Algorithm)
                 is applicable with AAL-5 traffic only."
        ::= { atmBwClassEntry 38 }
 
atmBwClassOeBCM OBJECT-TYPE
    SYNTAX      INTEGER {
                enable(1),
                disable(2)
        }
    ACCESS      read-only
    STATUS      mandatory
    DESCRIPTION "The value of this object enables the generation
                 of RM cells when congestion is detected in the
                 connection. This is the other endpoint view."
        ::= { atmBwClassEntry 39 }
 
atmBwClassOeFGCRA OBJECT-TYPE
    SYNTAX      INTEGER {
                enable(1),
                disable(2)
        }
    ACCESS      read-only
    STATUS      mandatory
    DESCRIPTION "The value of this object enables FGCRA.
                 FGCRA (Frame-based Generic Rate Control Algorithm)
                 is applicable with AAL-5 traffic only. This is the 
                 other endpoint view."
        ::= { atmBwClassEntry 40 }

atmBwClassConType OBJECT-TYPE
    SYNTAX      INTEGER {
                atf(1),
                vbr(2),
                cbr(3),
                unknown(4),
                abr(5)
        }
    ACCESS      read-only
    STATUS      mandatory
    DESCRIPTION "The value of this object defines the connection
                 type associated with this class." 
        ::= { atmBwClassEntry 41 }

atmBwClassScrPlc OBJECT-TYPE
    SYNTAX      INTEGER {
                clp0(1),
                clp0and1(2),
                off(3)
    }
    ACCESS      read-only
    STATUS      mandatory
    DESCRIPTION "Specifies the traffic policing for this end point."
        ::= { atmBwClassEntry 42 }
 
atmBwClassOeScrPlc OBJECT-TYPE
    SYNTAX      INTEGER {
                clp0(1),
                clp0and1(2),
                off(3)
    }
    ACCESS      read-only
    STATUS      mandatory
    DESCRIPTION "Specifies the traffic policing for the other end
                 point." 
        ::= { atmBwClassEntry 43 }

atmBwClassPCR0 OBJECT-TYPE
    SYNTAX      INTEGER (7..353208)
    ACCESS      read-only
    STATUS      mandatory
    DESCRIPTION "The peak cell rate (in cells per second) for the
                 second bucket for this end point. This object
                 corresponds to the parameter PCR(0) in standard
                 ATM documents." 
        ::= { atmBwClassEntry 44 }
 
atmBwClassOePCR0 OBJECT-TYPE
    SYNTAX      INTEGER (7..353208)
    ACCESS      read-only
    STATUS      mandatory
    DESCRIPTION "The peak cell rate (in cells per second) for the
                 second bucket for the other end point. This object
                 corresponds to the parameter PCR(0) in standard
                 ATM documents."
        ::= { atmBwClassEntry 45 }
 
atmBwClassCDVT0 OBJECT-TYPE
    SYNTAX      INTEGER (1..250000)
    ACCESS      read-only
    STATUS      mandatory
    DESCRIPTION "The cell delay variation tolerance for the second
                 bucket for this end point. This object corresponds
                 to the parameter CDVT(0) in standard ATM documents."
        ::= { atmBwClassEntry 46 }
 
atmBwClassOeCDVT0 OBJECT-TYPE
    SYNTAX      INTEGER (1..250000)
    ACCESS      read-only
    STATUS      mandatory
    DESCRIPTION "The cell delay variation tolerance for the second
                 bucket for the other end point. This object corresponds
                 to the parameter CDVT(0) in standard ATM documents."
        ::= { atmBwClassEntry 47 }
 
atmBwClassOeRateUpICA OBJECT-TYPE
    SYNTAX      INTEGER (10..96000)
    ACCESS      read-only
    STATUS      mandatory
    DESCRIPTION "The value of this object is equal to the ForeSight
                 Rate Up value in cells per second per adjust for
                 the other end point."
        ::= { atmBwClassEntry 48 }
 

-- This table describes a mapping between Frame Relay endpoints 
-- described by slot.port.dlci and corresponding object identifier
-- pointers into connTable and the service specific endptTable.
-- This table allows the user to determine the table indeces associated
-- with the connection defined by the physical attributes of slot, port,
-- and dlci.  
--
frEndptMapTable OBJECT-TYPE
    SYNTAX      SEQUENCE OF FrEndptMapEntry
    ACCESS      not-accessible
    STATUS      mandatory
    DESCRIPTION "The Frame Relay Endpoint-Connection Mapping table."
    --DEFAULT   test-function   test-frendptmaptable
    --DEFAULT   next-function   next-frendptmaptable
    --DEFAULT   get-function    get-frendptmaptable-%t
    --DEFAULT   view-mask       IPX-VIEW 
        ::= { switchConnection 10  }
 
frEndptMapEntry OBJECT-TYPE
    SYNTAX      FrEndptMapEntry
    ACCESS      not-accessible
    STATUS      mandatory
    DESCRIPTION "An entry in the Frame Relay Endpoint Connection Mapping 
                 table."
    INDEX   { frEndptMapSlot,
              frEndptMapPort,
              frEndptMapDlci }
        ::= { frEndptMapTable 1  }
 
FrEndptMapEntry ::=
    SEQUENCE {
        frEndptMapSlot          INTEGER,
        frEndptMapPort          INTEGER,
        frEndptMapDlci          INTEGER,
        frEndptMapEndptPtr      OBJECT IDENTIFIER,          
        frEndptMapConnPtr       OBJECT IDENTIFIER           
    }

frEndptMapSlot OBJECT-TYPE
    SYNTAX      INTEGER (1..32)
    ACCESS      read-only
    STATUS      mandatory
    DESCRIPTION "This MIB object contains the slot number associated
                 with the requested connection endpoint."
        ::= { frEndptMapEntry 1  }
 
frEndptMapPort OBJECT-TYPE
    SYNTAX      INTEGER (1..32)
    ACCESS      read-only
    STATUS      mandatory
    DESCRIPTION "This MIB object contains the port number associated
                 with the requested connection endpoint."
        ::= { frEndptMapEntry 2  }

frEndptMapDlci OBJECT-TYPE
    SYNTAX      INTEGER 
    ACCESS      read-only
    STATUS      mandatory
    DESCRIPTION "This MIB object contains the Frame Relay DLCI 
                 associated with the requested connection endpoint."
        ::= { frEndptMapEntry 3  }

frEndptMapEndptPtr OBJECT-TYPE
    SYNTAX      OBJECT IDENTIFIER
    ACCESS      read-only
    STATUS      mandatory
    DESCRIPTION "This MIB object contains a pointer to first column of row
                 in the service specific EndptTable which corresponds to 
                 the slot, port, and dlci specified in the columns above."
        ::= { frEndptMapEntry 4  }

frEndptMapConnPtr OBJECT-TYPE
    SYNTAX      OBJECT IDENTIFIER
    ACCESS      read-only
    STATUS      mandatory
    DESCRIPTION "This MIB object contains a pointer to first column of row
                 in connTable which corresponds to the slot, port, and
                 dlci specified in the columns above."
        ::= { frEndptMapEntry 5  }



-- This table describes a mapping between ATM endpoints 
-- described by slot.port.vpi.vci and corresponding object identifier
-- pointers into connTable and the service specific endptTable.
-- This table allows the user to determine the table indeces associated
-- with the connection defined by the physical attributes of slot, port,
-- vpi, and vci.  
--
atmEndptMapTable OBJECT-TYPE
    SYNTAX      SEQUENCE OF AtmEndptMapEntry
    ACCESS      not-accessible
    STATUS      mandatory
    DESCRIPTION "The ATM Endpoint-Connection Mapping table."
    --DEFAULT   test-function   test-atmendptmaptable
    --DEFAULT   next-function   next-atmendptmaptable
    --DEFAULT   get-function    get-atmendptmaptable-%t
        ::= { switchConnection 11  }
 
atmEndptMapEntry OBJECT-TYPE
    SYNTAX      AtmEndptMapEntry
    ACCESS      not-accessible
    STATUS      mandatory
    DESCRIPTION "An entry in the ATM Endpoint Connection Mapping table."
    INDEX   { atmEndptMapSlot,
              atmEndptMapPort,
              atmEndptMapVpi,
              atmEndptMapVci }
        ::= { atmEndptMapTable 1  }
 
AtmEndptMapEntry ::=
    SEQUENCE {
        atmEndptMapSlot          INTEGER,
        atmEndptMapPort          INTEGER,
        atmEndptMapVpi           INTEGER,
        atmEndptMapVci           INTEGER,
        atmEndptMapEndptPtr      OBJECT IDENTIFIER,          
        atmEndptMapConnPtr       OBJECT IDENTIFIER           
    }

atmEndptMapSlot OBJECT-TYPE
    SYNTAX      INTEGER (1..32)
    ACCESS      read-only
    STATUS      mandatory
    DESCRIPTION "This MIB object contains the slot number associated
                 with the requested connection endpoint."
        ::= { atmEndptMapEntry 1  }
 
atmEndptMapPort OBJECT-TYPE
    SYNTAX      INTEGER (1..32)
    ACCESS      read-only
    STATUS      mandatory
    DESCRIPTION "This MIB object contains the port number associated
                 with the requested connection endpoint."
        ::= { atmEndptMapEntry 2  }

atmEndptMapVpi OBJECT-TYPE
    SYNTAX      INTEGER 
    ACCESS      read-only
    STATUS      mandatory
    DESCRIPTION "This MIB object contains the ATM endpoint VPI 
                 associated with the requested connection endpoint."
        ::= { atmEndptMapEntry 3  }

atmEndptMapVci OBJECT-TYPE
    SYNTAX      INTEGER 
    ACCESS      read-only
    STATUS      mandatory
    DESCRIPTION "This MIB object contains the ATM endpoint VCI 
                 associated with the requested connection endpoint."
        ::= { atmEndptMapEntry 4  }

atmEndptMapEndptPtr OBJECT-TYPE
    SYNTAX      OBJECT IDENTIFIER
    ACCESS      read-only
    STATUS      mandatory
    DESCRIPTION "This MIB object contains a pointer to first column of row
                 in the service specific EndptTable which corresponds to 
                 the slot, port, vpi, and vci specified in the columns above."
        ::= { atmEndptMapEntry 5  }

atmEndptMapConnPtr OBJECT-TYPE
    SYNTAX      OBJECT IDENTIFIER
    ACCESS      read-only
    STATUS      mandatory
    DESCRIPTION "This MIB object contains a pointer to first column of row
                 in connTable which corresponds to the slot, port, vpi,
                 and vci specified in the columns above."
        ::= { atmEndptMapEntry 6  }

--
-- This table defines the ATM connection end-point statistics 
-- Statistics are not supported on OC3 end points. The value for
-- objects in this table for OC3 end points is zero.
--

atmEndptStatTable OBJECT-TYPE 
    SYNTAX      SEQUENCE OF AtmEndptStatEntry
    ACCESS      not-accessible
    STATUS      mandatory
    DESCRIPTION "The ATM End-Point Statistics table." 
    --DEFAULT   test-function   test-atmendptstattable 
    --DEFAULT   next-function   next-atmendptstattable
    --DEFAULT   get-function    get-atmendptstattable-%t
    --DEFAULT   view-mask       BPX-VIEW 
        ::= { switchConnection 12  }

atmEndptStatEntry OBJECT-TYPE
    SYNTAX      AtmEndptStatEntry
    ACCESS      not-accessible
    STATUS      mandatory
    DESCRIPTION "An entry in the ATM End-point Statistics table."
    INDEX   { atmEndptIndex }
        ::= { atmEndptStatTable 1  }

AtmEndptStatEntry ::=
    SEQUENCE {
        atmCellsRxPorts          Counter,
        atmFramesRxPorts         Counter,
        atmCellsTxNets           Counter,
        atmClpRxs                Counter,
        atmViolRxs               Counter,
        atmDiscardVcqClpThs      Counter,
        atmDiscardVcqFulls       Counter,
        atmEfciRxs               Counter,
        atmNonCompRxs            Counter,
        atmDiscardFails          Counter,
        atmAvgVcqDepths          Counter,
        atmDiscardRsrcOflows     Counter,
        atmDiscardSbinFulls      Counter,
        atmBcmRxs                Counter,
        atmBcmTxs                Counter,
        atmOamTxs                Counter,
        atmDiscardQbinFulls      Counter,
        atmDiscardQbinClpThs     Counter,
        atmCellsRxNets           Counter,
        atmClpTxs                Counter,
        atmEfciTxs               Counter,
        atmCellsTxPorts          Counter,
        atmAisRxs                Counter,
        atmFerfRxs               Counter
    }

atmCellsRxPorts  OBJECT-TYPE
    SYNTAX      Counter 
    ACCESS      read-only
    STATUS      mandatory
    DESCRIPTION "The number of cells delivered to the port
                 from the line interface."
        ::= { atmEndptStatEntry 1  }

atmFramesRxPorts  OBJECT-TYPE
    SYNTAX      Counter 
    ACCESS      read-only
    STATUS      mandatory
    DESCRIPTION "The number of frames delivered to the port
                 from the line interface."
        ::= { atmEndptStatEntry 2  }

atmCellsTxNets  OBJECT-TYPE
    SYNTAX      Counter 
    ACCESS      read-only
    STATUS      mandatory
    DESCRIPTION "The number of received cells delivered to
                 the network."
        ::= { atmEndptStatEntry 3  }

atmClpRxs  OBJECT-TYPE
    SYNTAX      Counter 
    ACCESS      read-only
    STATUS      mandatory
    DESCRIPTION "The number of cells delivered to the port
                 from the line interface which had their
                 CLP bit set."
        ::= { atmEndptStatEntry 4  }

atmViolRxs  OBJECT-TYPE
    SYNTAX      Counter 
    ACCESS      read-only
    STATUS      mandatory
    DESCRIPTION "The number of cells that violated UPC."
        ::= { atmEndptStatEntry 5  }

atmDiscardVcqClpThs  OBJECT-TYPE
    SYNTAX      Counter 
    ACCESS      read-only
    STATUS      mandatory
    DESCRIPTION "The number of cells with CLP set that were
                 discarded due to VC queue exceeding CLP
                 thresholds."
        ::= { atmEndptStatEntry 6  }

atmDiscardVcqFulls  OBJECT-TYPE
    SYNTAX      Counter 
    ACCESS      read-only
    STATUS      mandatory
    DESCRIPTION "The number of received cells that were 
                 discarded due to the VC queue being
                 full."
        ::= { atmEndptStatEntry 7  }

atmEfciRxs  OBJECT-TYPE
    SYNTAX      Counter 
    ACCESS      read-only
    STATUS      mandatory
    DESCRIPTION "The number of cells received with EFCI set."
        ::= { atmEndptStatEntry 8  }

atmNonCompRxs  OBJECT-TYPE
    SYNTAX      Counter 
    ACCESS      read-only
    STATUS      mandatory
    DESCRIPTION "The number of non-compliant cells received."
        ::= { atmEndptStatEntry 9  }

atmDiscardFails  OBJECT-TYPE
    SYNTAX      Counter 
    ACCESS      read-only
    STATUS      mandatory
    DESCRIPTION "The number of received cells discarded due
                 to the connection being in failed state."
        ::= { atmEndptStatEntry 10 }

atmAvgVcqDepths  OBJECT-TYPE
    SYNTAX      Counter 
    ACCESS      read-only
    STATUS      mandatory
    DESCRIPTION "The average queue depth of the VC queue."
        ::= { atmEndptStatEntry 11 }

atmDiscardRsrcOflows  OBJECT-TYPE
    SYNTAX      Counter 
    ACCESS      read-only
    STATUS      mandatory
    DESCRIPTION "The number of received cells discarded due to
                 a resource overflow (e.g. cell buffer full)."
        ::= { atmEndptStatEntry 12 }

atmDiscardSbinFulls  OBJECT-TYPE
    SYNTAX      Counter 
    ACCESS      read-only
    STATUS      mandatory
    DESCRIPTION "The number of cells discarded on receipt from
                 from the port due to Sbin full."
        ::= { atmEndptStatEntry 13 }

atmBcmRxs  OBJECT-TYPE
    SYNTAX      Counter 
    ACCESS      read-only
    STATUS      mandatory
    DESCRIPTION "The number of BCM cells received from the port.
                 This object only applies to NNI ports. For UNI
                 ports returns 0."
        ::= { atmEndptStatEntry 14 }

atmBcmTxs  OBJECT-TYPE
    SYNTAX      Counter 
    ACCESS      read-only
    STATUS      mandatory
    DESCRIPTION "The number of BCM cells transmitted to the
                 network. This object only applies to NNI ports.
                 For UNI ports returns 0."
        ::= { atmEndptStatEntry 15 }

atmOamTxs  OBJECT-TYPE
    SYNTAX      Counter 
    ACCESS      read-only
    STATUS      mandatory
    DESCRIPTION "The number of OAM cells transmitted to the
                 network."
        ::= { atmEndptStatEntry 16 }

atmDiscardQbinFulls  OBJECT-TYPE
    SYNTAX      Counter 
    ACCESS      read-only
    STATUS      mandatory
    DESCRIPTION "The number of cells discarded due to the egress
                 Qbin being full."
        ::= { atmEndptStatEntry 17 }

atmDiscardQbinClpThs  OBJECT-TYPE
    SYNTAX      Counter 
    ACCESS      read-only
    STATUS      mandatory
    DESCRIPTION "The number of cells with CLP set that are
                 discarded due to the egress Qbin exceeding 
                 CLP thresholds."
        ::= { atmEndptStatEntry 18 }

atmCellsRxNets  OBJECT-TYPE
    SYNTAX      Counter 
    ACCESS      read-only
    STATUS      mandatory
    DESCRIPTION "The number of cells received from the network."
        ::= { atmEndptStatEntry 19 }

atmClpTxs  OBJECT-TYPE
    SYNTAX      Counter 
    ACCESS      read-only
    STATUS      mandatory
    DESCRIPTION "The number of cells transmitted to the port
                 that had their CLP bit set."
        ::= { atmEndptStatEntry 20 }

atmEfciTxs  OBJECT-TYPE
    SYNTAX      Counter 
    ACCESS      read-only
    STATUS      mandatory
    DESCRIPTION "The number of cells transmitted by the port
                 to the line interface that had EFCI set."
        ::= { atmEndptStatEntry 21 }

atmCellsTxPorts  OBJECT-TYPE
    SYNTAX      Counter 
    ACCESS      read-only
    STATUS      mandatory
    DESCRIPTION "The number of cells transmitted to the port
                 interface."
        ::= { atmEndptStatEntry 22 }

atmAisRxs  OBJECT-TYPE
    SYNTAX      Counter 
    ACCESS      read-only
    STATUS      mandatory
    DESCRIPTION "The number of received AIS cells."
        ::= { atmEndptStatEntry 23 }

atmFerfRxs  OBJECT-TYPE
    SYNTAX      Counter 
    ACCESS      read-only
    STATUS      mandatory
    DESCRIPTION "The number of received FERF cells."
        ::= { atmEndptStatEntry 24 }





--
-- The following describes the MIB variables for the voiceannelConnection.
-- voiceEndptTable contains  detailed information about the channel Endpoint
-- connection information
-- voiceChannelTable shall contain configuration information about each 
-- of voice  Channel.
-- voiceStatTable shall contains voice endpoint related statistics.


voiceEndptTable  OBJECT-TYPE 
    SYNTAX      SEQUENCE OF VoiceEndptEntry
    ACCESS      not-accessible
    STATUS      mandatory
    DESCRIPTION "The voice channel connection table has Channel Connection
    information. This table is used to model a specific Voice 
    Channel connection. This table contains parameters which are 
    requrired to create a Voice conneciton and configure the 
        channel."

    --DEFAULT   test-function   test-voendpttable
    --DEFAULT   next-function   next-voendpttable
    --DEFAULT   get-function    get-voendpttable-%t
    --DEFAULT   view-mask       IPX-VIEW 
        ::= { switchConnection 13  }

voiceEndptEntry OBJECT-TYPE
    SYNTAX      VoiceEndptEntry
    ACCESS      not-accessible
    STATUS      mandatory
    DESCRIPTION "An entry in the voice Endpoint Channel Connection table."
    INDEX   { voiceEndptIndex  }
        ::= { voiceEndptTable 1  }

VoiceEndptEntry ::=
    SEQUENCE {

    voiceEndptIndex              INTEGER,
    voiceOtherEndptIndex         INTEGER,
    voiceEndptDesc               DisplayString,
    voiceOtherEndptDesc          DisplayString,
    voiceEndptConnDesc           DisplayString,
    voiceEndptAdminStatus        INTEGER,
    voiceEndptOperStatus         INTEGER,
    voiceEndptRateType           INTEGER,
    voiceEndPointFailure         INTEGER,
    voiceNoRouteFoundFailure     INTEGER,
    voiceBumpFailure             INTEGER,
    voiceTestFailure             INTEGER,
    voiceEndptTestType           INTEGER,
    voiceEndptLpbkStatus         INTEGER,
    voiceConnPtr                 OBJECT IDENTIFIER,
    voiceChannelPtr              OBJECT IDENTIFIER,
    voiceEndptTrkAvoidType       INTEGER,
    voiceEndptAvoidZCS           INTEGER,
    voiceEndptState              INTEGER,
    voiceEndptAdv                INTEGER,
    voiceOtherEndptAdv           INTEGER,
    voiceEndptEncoding           INTEGER,
    voiceOtherEndptEncoding      INTEGER,
    voiceEndptEndptType          INTEGER,
    voiceEndptLocLpbkState       INTEGER
}

voiceEndptIndex     OBJECT-TYPE
    SYNTAX      INTEGER (0..2047)
    ACCESS      read-only
    STATUS      mandatory
    DESCRIPTION "The index for this Voice Connection. This is the index
                 to this table."
        ::= { voiceEndptEntry 1  }

voiceOtherEndptIndex OBJECT-TYPE
    SYNTAX      INTEGER (0..2047 )
    ACCESS      read-only
    STATUS      mandatory
    DESCRIPTION "Index into remote node's voiceEndptTable for this channel
                 end-point. For local (intra-node) connections, this index 
                 is associated with the local node and will be in the range 
                 of 1024 to 2047."
        ::= { voiceEndptEntry 2  }

voiceEndptDesc  OBJECT-TYPE
    SYNTAX      DisplayString
    ACCESS      read-write
    STATUS      mandatory
    DESCRIPTION "String describing this voice Channel. Contains information 
                 about the domain, nodename, slot, channel, for the 
                 connection. For example, D1.Node1.12.1, is a valid 
                 description.  Domain and nodename need not be given 
                 but slot, channel values must exist; 12.1 is valid. 
                 This variable value has to specified for a Creating 
                 an voiceEndptEntry."
        ::= { voiceEndptEntry 3  }

voiceOtherEndptDesc     OBJECT-TYPE
    SYNTAX      DisplayString
    ACCESS      read-write
    STATUS      mandatory
    DESCRIPTION "String describing the remote channel.  Contains
                 information about the domain, nodename, slot, channel,
                 for the connection.  For example, D2.Node2.10.5, is a valid 
                 description. Nodename, slot, channel values must exist; 
                 Node2.10.5  is valid. This variable value has to be 
                 specified for creating an voiceEndptEntry."
        ::= { voiceEndptEntry 4  }

voiceEndptConnDesc OBJECT-TYPE
    SYNTAX      DisplayString ( SIZE (0..20) )
    ACCESS      read-write
    STATUS      mandatory
    DESCRIPTION "A string that has been defined for the connection to
                 give a more descriptive name.  Connections can be given
                 clear text names in order to make them more human readable."
        ::= { voiceEndptEntry 5  }

voiceEndptAdminStatus     OBJECT-TYPE
    SYNTAX      INTEGER {
                create(1),
                delete(2),
                modify(3),
                test(4),
                writeOnly(5)
        }
    ACCESS      read-write
    STATUS      mandatory
    DESCRIPTION  "User requested state for voice endpoint table row.
                  A user can create / delete / modify this voice channel 
                  connection by setting this object appropriately.  
                  The user also has the capability to test a particular 
                  object.  For this capability,  the user must set this 
                  value to test. If a Get operation is performed on this 
                  variable, -1 shall be returned to the NMS."
        ::= { voiceEndptEntry 6  }

voiceEndptOperStatus          OBJECT-TYPE
    SYNTAX      INTEGER {
                ok(1),
                okPendingDown(2),
                down(3),
                failed(4),
                inTest(5),
                okPendingRoute(6),
                okPendingDelete(7),
                looped(8),
                unknown(9)
        }
    ACCESS      read-only
    STATUS      mandatory
    DESCRIPTION "Actual state of the voice channel.If the state is failed,
                 then look to the objects voiceNoRouteFoundFailure, 
                 voiceBumpFailure, and voiceTestFailure to determine reason 
                 for failure."
        ::= { voiceEndptEntry 7  }

voiceEndptRateType   OBJECT-TYPE
    SYNTAX      INTEGER {
                a32(1),
                a24(2),
                a16(3),
                a16z(4),
                a32d(5),
                c32(6),
                c24(7),
                c16(8),
                c16z(9),
                c32d(10),
                p(11),
                t(12),
                v(13)
        }
    ACCESS      read-write
    STATUS      mandatory
    DESCRIPTION "Represents the type of voice connection. Each of them has
                 been described below briefly.

        Type    Description

        a32    Uses ADPCM only. Can select 32/24/16 Kbps
        a24    compression.
        a16

        a16z    Standard 16Kbps ADPCM only. compressed code can have 
                strings of zeros and should be used on lines that
                have other zero code supression

        c32     Uses both ADPCM and Voice Activity detection (VAD).
        c24     Can select 32/24/16 Kbps ADPCM compression.
        c16
        
        c16z    Standard 16Kbps ADPCM and Voice Activity detection.
                Similar to 16z. Use on ZCS trunks only.
        
        p       64Kbps connection. No compression

        t      Transparent. Clean 64Kbps connection. No Compression.

        This variable value has to be specified for creating an 
        voiceEndptEntry."
        ::= { voiceEndptEntry 8  }

voiceEndPointFailure OBJECT-TYPE
    SYNTAX      INTEGER {
                false(1),
                true(2)
        }
    ACCESS      read-only
    STATUS      mandatory
    DESCRIPTION "End-point is failed because of a remote end-point failure.
                 The remote end-point is on a node that resides in another
                 domain making the connection an inter-domain connection."
        ::= { voiceEndptEntry 9  }

voiceNoRouteFoundFailure OBJECT-TYPE
    SYNTAX      INTEGER {
                false(1),
                true(2)
        }
    ACCESS      read-only
    STATUS      mandatory
    DESCRIPTION "Channel connection is failed is because no route to the
                 remote Channel  could be found."
        ::= { voiceEndptEntry 10 }

voiceBumpFailure OBJECT-TYPE
    SYNTAX      INTEGER {
                false(1),
                true(2)
        }
    ACCESS      read-only
    STATUS      mandatory
    DESCRIPTION "Channel Connection is failed because of insufficient bandwidth
                 to route to the remote Channel.  This may have also
                 been caused because a higher priority connection took
                 this channel's bandwidth.  A higher priority connection
                 is one with the lowest class of service (COS)."
        ::= { voiceEndptEntry 11 }

voiceTestFailure OBJECT-TYPE
    SYNTAX      INTEGER {
                false(1),
                true(2)
        }
    ACCESS      read-only
    STATUS      mandatory
    DESCRIPTION "Channel is failed because of the failure of a connection test."
        ::= { voiceEndptEntry 12 }

voiceEndptTestType OBJECT-TYPE
    SYNTAX      INTEGER {
                testCon(1),
                writeOnly(2)
        }
    ACCESS      read-write
    STATUS      mandatory
    DESCRIPTION "Specifies the type of test the user would like to
                 conduct on this endpoint.  Only testCon is currently
                 defined. TestCon performs a test of voice  path 
                 integrity in the connection. Only write is allowed on this 
                 object. A -1 is returned to the NMS if a GET is recevied on
                 this object" 
        ::= { voiceEndptEntry 13 }


voiceEndptLpbkStatus OBJECT-TYPE
    SYNTAX      INTEGER
    ACCESS      read-only
    STATUS      mandatory
    DESCRIPTION "Specifies the current Loopback State of the endpoint.
                 The value returned from this object is a bitmap
                 of the current loopback states associated with this
                 end point. The bitmap is defined below:
         LP-RMT-RMT   0 /* Remote nodes remote muxbus loopback   */
         LP-RMT-TST   1 /* Remote nodes tstcon loopback          */
         LP-LOC-RMT   2 /* Local  nodes remote muxbus loopback   */
         LP-LOC-TST   3 /* Local  nodes tstcon loopback          */
         LP-LOC-LOC   4 /* Local  nodes local muxbus loopback    */
         LP-LOC-PORT  5 /* Local  nodes port loopback            */
         LP-LOC-TPORT 6 /* Local  nodes port test loopback       */
         LP-RMT-LOC   7 /* Remote nodes local muxbus loopback    */
         LP-RMT-PORT  8 /* Remote nodes port loopback            */
         LP-RMT-TPORT 9 /* Remote nodes port test looback        */
         LP-LOC-CSU 10 /* Local  DDS network requested CSU loopback */
         LP-RMT-CSU 11 /* Remote DDS network requested CSU loopback */
         LP-LOC-DSU 12 /* Local  DDS network requested DSU loopback */
         LP-RMT-DSU 13 /* Remote DDS network requested DSU loopback */
         LP-LOC-EXT 14 /* Local  DDS external loopback          */
         LP-RMT-EXT 15 /* Remote DDS external loopback          */
         "
        ::= { voiceEndptEntry 14 }

voiceConnPtr OBJECT-TYPE
    SYNTAX      OBJECT IDENTIFIER
    ACCESS      read-only
    STATUS      mandatory
    DESCRIPTION "Pointer to general connection information.  Using this
                 pointer the user can obtain connection status, and
                 routing information. Specifically, this is an object
                 identifier specifying the first column of the appropriate
                 row in the connTable."
        ::= { voiceEndptEntry 15 }

voiceChannelPtr OBJECT-TYPE
    SYNTAX      OBJECT IDENTIFIER
    ACCESS      read-only
    STATUS      mandatory
    DESCRIPTION "Pointer to channel configuration information.  Using this
                 pointer the user can obtain all channel configuration 
                 information. Specifically, this is an object
                 identifier specifying the first column of the appropriate
                 row in the voiceChannelTable. "
        ::= { voiceEndptEntry 16 }

voiceEndptTrkAvoidType OBJECT-TYPE
    SYNTAX      INTEGER {
                none(1),
                satellite(2),
                terrestrial(3)
        }
    ACCESS      read-write
    STATUS      mandatory
    DESCRIPTION "User selectable types of trunks to avoid for the
                 transfer of  voice channel data.  Current choices are to 
                 avoid satellite links, terrestrial links, or to not avoid
                 any specific type of link. This object is optional
                 during the creation of the endpoint."
        ::= { voiceEndptEntry 17 }

voiceEndptAvoidZCS OBJECT-TYPE
    SYNTAX      INTEGER {
                false(1),
                true(2)
        }
    ACCESS      read-write
    STATUS      mandatory
    DESCRIPTION "Flag to force the connection to avoid trunks with zero
                 code suppression (ZCS). This object is optional during
                 the creation of the endpoint."
        ::= { voiceEndptEntry 18 }

voiceEndptState OBJECT-TYPE
    SYNTAX      INTEGER {
                offhook (1),
                onhook(2),
                slowmodem(3),
                fastmodem(4),
                notConnected(5)
        }
    ACCESS      read-only
    STATUS      mandatory
    DESCRIPTION "It gives the state of the connection end point."
        ::= { voiceEndptEntry 19 }

voiceEndptAdv OBJECT-TYPE
    SYNTAX      INTEGER {
                false(1),
                true(2)
        }
    ACCESS      read-only
    STATUS      mandatory
    DESCRIPTION "It represents if the endpoint supports Adaptve voice 
                 capability."
        ::= { voiceEndptEntry 20 }

voiceOtherEndptAdv  OBJECT-TYPE
    SYNTAX      INTEGER {
                false(1),
                true(2)
        }
    ACCESS      read-only
    STATUS      mandatory
    DESCRIPTION "It represents if the other endpoint supports Adaptve voice 
                 capability."
        ::= { voiceEndptEntry 21 }

voiceEndptEncoding    OBJECT-TYPE
    SYNTAX      INTEGER {
                alaw(1),
                ulaw(2)
        }
    ACCESS      read-only
    STATUS      mandatory
    DESCRIPTION "It represents the type of Encoding used at this this Endpoint."
        ::= { voiceEndptEntry 22 }

voiceOtherEndptEncoding  OBJECT-TYPE
    SYNTAX      INTEGER {
                alaw(1),
                ulaw(2)
        }
    ACCESS      read-only
    STATUS      mandatory
    DESCRIPTION "It represents the type of Encoding used at the other Endpoint." 
        ::= { voiceEndptEntry 23 }

voiceEndptEndptType  OBJECT-TYPE
    SYNTAX      INTEGER {
                pcm(1),
                adpcm(2),
                adpno(3),
                transp(4),
                unknown(5)
        }
    ACCESS      read-only
    STATUS      mandatory
    DESCRIPTION "It represents the end point type"
        ::= { voiceEndptEntry 24 }
 
voiceEndptLocLpbkState OBJECT-TYPE
    SYNTAX      INTEGER {
                enable(1),
                disable(2),
                writeOnly(3)
        }
    ACCESS      read-write
    STATUS      mandatory
    DESCRIPTION "Specifies the Local Loopback State the user would
                 like to set for the endpoint."
        ::= { voiceEndptEntry 25 }


--
-- Voice End Point Statistics Table 
--
voiceStatTable OBJECT-TYPE
    SYNTAX      SEQUENCE OF VoiceStatEntry
    ACCESS      not-accessible
    STATUS      mandatory
    DESCRIPTION "The voice Statistics Table."
    --DEFAULT   test-function   test-voicestatstable
    --DEFAULT   next-function   next-voicestatstable
    --DEFAULT   get-function    get-voicestatstable-%t
    --DEFAULT   view-mask       IPX-VIEW
        ::= { switchConnection 14  }

voiceStatEntry OBJECT-TYPE
    SYNTAX      VoiceStatEntry
    ACCESS      not-accessible
    STATUS      mandatory
    DESCRIPTION "An entry in the voice channel statistics table."
    INDEX  { voiceEndptIndex  }
        ::= { voiceStatTable 1  }

VoiceStatEntry ::=
    SEQUENCE {
    voiceStatPktsRxs         Counter, 
    voiceStatPktsXmits       Counter, 
    voiceStatRxPktsDscds     Counter, 
    voiceStatSprvPktsXmits   Counter, 
    voiceStatSprvPktsRcvs    Counter, 
    voiceStatV25ModemOns     Counter, 
    voiceStatDsiOns          Counter, 
    voiceStatOffhks          Counter, 
    voiceStatInservices      Counter
    }

voiceStatPktsRxs  OBJECT-TYPE
    SYNTAX      Counter
    ACCESS      read-only
    STATUS      mandatory
    DESCRIPTION "The number of packets received from the muxbus by the local
                 port card."
        ::= { voiceStatEntry 1  }

voiceStatPktsXmits  OBJECT-TYPE
    SYNTAX      Counter
    ACCESS      read-only
    STATUS      mandatory
    DESCRIPTION "The number of packets transmitted from the local port card
                 onto the Mux Bus."
        ::= { voiceStatEntry 2  }

voiceStatRxPktsDscds  OBJECT-TYPE
    SYNTAX      Counter
    ACCESS      read-only
    STATUS      mandatory
    DESCRIPTION "The number of packets received from the muxbus by the local
                 port card which are discarded before being transmitted out
                 to the port."
        ::= { voiceStatEntry 3  }

voiceStatSprvPktsXmits     OBJECT-TYPE
    SYNTAX      Counter
    ACCESS      read-only
    STATUS      mandatory
    DESCRIPTION "The number of supervisory packets transmitted from the local
                 port onto the Muxbus. Supervisory packets reflect signalling
                 bit transitions for voice connections."
        ::= { voiceStatEntry 4  }

voiceStatSprvPktsRcvs OBJECT-TYPE
    SYNTAX      Counter
    ACCESS      read-only
    STATUS      mandatory
    DESCRIPTION "The number of supervisory packets received from Muxbus 
                 associated with a connection."
        ::= { voiceStatEntry 5  }

voiceStatV25ModemOns  OBJECT-TYPE
    SYNTAX      Counter
    ACCESS      read-only
    STATUS      mandatory
    DESCRIPTION "The number of seconds the V.25 modem is detected and the
                 connection is upgraded to PCM."
        ::= { voiceStatEntry 6  }

voiceStatDsiOns    OBJECT-TYPE
    SYNTAX      Counter
    ACCESS      read-only
    STATUS      mandatory
    DESCRIPTION "The number of seconds that a connection is performing 
                 Digital  speech interpolation (DSI)."
        ::= { voiceStatEntry 7  }

voiceStatOffhks    OBJECT-TYPE
    SYNTAX      Counter
    ACCESS      read-only
    STATUS      mandatory
    DESCRIPTION "The number of seconds that a connection is offhook. The 
                 onhook state is determined by onhook A/B/C/D bits defined
                 by variables in the voiceEndpttable. A connection which 
                 is not onhook is treated as offhook."
        ::= { voiceStatEntry 8  }

voiceStatInservices OBJECT-TYPE
    SYNTAX      Counter
    ACCESS      read-only
    STATUS      mandatory
    DESCRIPTION "The number of seconds a connection is inservice. A 
                 connection is said to be in-service if its endpoints are 
                 not in alarm, the cards required to support this connection
                 are present, and the connection is routed."        
        ::= { voiceStatEntry 9  }



--
-- This table describes a mapping between voice endpoints
-- described by slot.channel and corresponding object identifier
-- pointers into connTable and the service specific endptTable.
-- This table allows the user to determine the table indeces associated
-- with the connection defined by the physical attributes of slot and
-- channel.
--

voiceEndptMapTable  OBJECT-TYPE
    SYNTAX      SEQUENCE OF VoiceEndptMapEntry
    ACCESS      not-accessible
    STATUS      mandatory
    DESCRIPTION "The Voice Endpoint-Connection Mapping table."
    --DEFAULT   test-function   test-voendptmaptable
    --DEFAULT   next-function   next-voendptmaptable
    --DEFAULT   get-function    get-voendptmaptable-%t
    --DEFAULT   view-mask       IPX-VIEW
        ::= { switchConnection 15 }
 
voiceEndptMapEntry OBJECT-TYPE
    SYNTAX      VoiceEndptMapEntry
    ACCESS      not-accessible
    STATUS      mandatory
    DESCRIPTION "An entry in the Voice Endpoint Connection Mapping table."
    INDEX   { voiceEndptMapSlot,
              voiceEndptMapChannel }
        ::= { voiceEndptMapTable 1  }
 
VoiceEndptMapEntry ::=
    SEQUENCE {
        voiceEndptMapSlot          INTEGER,
        voiceEndptMapChannel       INTEGER,
        voiceEndptMapEndptPtr      OBJECT IDENTIFIER,
        voiceEndptMapConnPtr       OBJECT IDENTIFIER
    }
 
voiceEndptMapSlot OBJECT-TYPE
    SYNTAX      INTEGER (1..32)
    ACCESS      read-only
    STATUS      mandatory
    DESCRIPTION "This MIB object contains the slot number associated
                 with the requested connection endpoint."
        ::= { voiceEndptMapEntry 1  }
 
voiceEndptMapChannel OBJECT-TYPE
    SYNTAX      INTEGER (1..32)
    ACCESS      read-only
    STATUS      mandatory
    DESCRIPTION "This MIB object contains the channel number associated
                 with the requested connection endpoint."
        ::= { voiceEndptMapEntry 2  }
 
voiceEndptMapEndptPtr OBJECT-TYPE
    SYNTAX      OBJECT IDENTIFIER
    ACCESS      read-only
    STATUS      mandatory
    DESCRIPTION "This MIB object contains a pointer to first column of row
                 in the service specific EndptTable which corresponds to
                 the slot and channel specified in the columns above."
        ::= { voiceEndptMapEntry 3  }
 
voiceEndptMapConnPtr OBJECT-TYPE
    SYNTAX      OBJECT IDENTIFIER
    ACCESS      read-only
    STATUS      mandatory
    DESCRIPTION "This MIB object contains a pointer to first column of row
                 in connTable which corresponds to the slot and channel
                 specified in the columns above."
        ::= { voiceEndptMapEntry 4  }

 

-- The following objects are associated with the switchShelf
-- configuration branch.  These objects are scalar variables 
-- utilized by the network manager to manage the switch shelf
-- wide configuration.
 
shelfCnfgStatMaster  OBJECT-TYPE
    SYNTAX      IpAddress 
    ACCESS      read-only
    STATUS      mandatory
    DESCRIPTION "This object provides the network manager the
                 IP address of the master statistics collection
                 management workstation."
    --DEFAULT    get-function get-shelf-statmaster
        ::= { shelfCnfgObjects 1  }

shelfCnfgStatCollIntvl  OBJECT-TYPE
    SYNTAX      INTEGER
    ACCESS      read-only
    STATUS      mandatory
    DESCRIPTION "This object provides the network manager the
                 current TFTP statistics collection file interval 
                 configured on the switch in minutes."
    --DEFAULT    get-function get-shelf-statparm
        ::= { shelfCnfgObjects 2  }

shelfCnfgStatBcktIntvl  OBJECT-TYPE
    SYNTAX      INTEGER
    ACCESS      read-only
    STATUS      mandatory
    DESCRIPTION "This object provides the network manager the
                 current TFTP statistics collection bucket interval 
                 configured on the switch in minutes."
    --DEFAULT    get-function get-shelf-statparm
        ::= { shelfCnfgObjects 3  }

shelfCnfgStatTimeSync  OBJECT-TYPE
    SYNTAX      DisplayString 
    ACCESS      read-only
    STATUS      mandatory
    DESCRIPTION "This object provides the network manager the
                 current time for TFTP statistics collection. 
                 This object replaces the functionality originally
                 supplied by the daytime handler application."
    --DEFAULT    get-function get-shelf-time
        ::= { shelfCnfgObjects 4  }

shelfCnfgSwError  OBJECT-TYPE
    SYNTAX      INTEGER {
                false(1),
                true(2)
        }
    ACCESS      read-only
    STATUS      mandatory
    DESCRIPTION "This object notifies the network manager that a
                 switch software error has has been logged on this
                 shelf."
    --DEFAULT    get-function get-shelf-errors
        ::= { shelfCnfgObjects 5  }

shelfCnfgCardError  OBJECT-TYPE
    SYNTAX      INTEGER {
                false(1),
                true(2)
        }
    ACCESS      read-only
    STATUS      mandatory
    DESCRIPTION "This object notifies the network manager that a
                 switch card error has has been logged on this
                 shelf."
    --DEFAULT    get-function get-shelf-errors
        ::= { shelfCnfgObjects 6  }

-- END
--
--	Stratacom StrataView Network MIBs
--
--      $RCSfile: SV+Network.mib,v $
--      $Revision: 1.1.4.20 $
--      $Date: 1996/06/26 22:43:28 $
--
--      Consolidated MIB for event, node, filters, rtc and rtm --
--


-- STRATACOM-STRATAVIEW-SVPLUS-MIB
-- DEFINITIONS ::= BEGIN

-- IMPORTS
--         enterprises, Counter, IpAddress  FROM RFC1155-SMI
-- 	DisplayString	FROM RFC1213-MIB
--         TRAP-TYPE       FROM RFC-1215
-- 	OBJECT-TYPE	FROM RFC-1212;

-- stratacom	OBJECT IDENTIFIER ::= { enterprises 351 }
svplus		OBJECT IDENTIFIER ::= { stratacom 1 } 
svnode		OBJECT IDENTIFIER ::= { stratacom 2 } 
-- connSvc	OBJECT IDENTIFIER ::= { stratacom 3 }
-- portSvc	OBJECT IDENTIFIER ::= { stratacom 4 }
rtm		OBJECT IDENTIFIER ::= { stratacom 120 }	
-- strmErrors	OBJECT IDENTIFIER ::= { stratacom 910 }
-- StrataView Plus Generated events. Added br HJ and Sridhar strataviewEvents		OBJECT IDENTIFIER ::= { stratacom 920 }  
--
--	Note that Object identifiers { svplus 1 } through { svplus 10 } 
--	have been depricated.

controlGroup		OBJECT IDENTIFIER ::= { svplus 11 } 
logGroup		OBJECT IDENTIFIER ::= { svplus 12 } 
networkGroup		OBJECT IDENTIFIER ::= { svplus 13 } 
nodeGroup		OBJECT IDENTIFIER ::= { svplus 14 }

svNodeGroup	        OBJECT IDENTIFIER ::= { svnode 1 } 
packetGroup	        OBJECT IDENTIFIER ::= { svnode 2 } 
circuitGroup	        OBJECT IDENTIFIER ::= { svnode 3 } 
frpGroup	        OBJECT IDENTIFIER ::= { svnode 4 } 
connGroup	        OBJECT IDENTIFIER ::= { svnode 5 } 
realTimeCountersGroup	OBJECT IDENTIFIER ::= { svnode 6 } 
trapsConfig 		OBJECT IDENTIFIER ::= { rtm 1 }


Active		::= INTEGER	{
				inactive	(1),
				active		(2)
				}

--	Values currently used for "severity" in log records and 
--	TRAP filters are "Clear", "Info", "Minor", "Major", and 
--	"Updt" (for update).  Others may be used in the future.
--
Severity	::= DisplayString (SIZE (0..5))

nodeGrpName		OBJECT-TYPE
	SYNTAX		DisplayString (SIZE(0..10))
	ACCESS		read-only
			-- C-STRUCT node-cfg, FIELD nodeName
			-- C-LOCATOR-FUNC NodeMibNodeLocator
	STATUS		mandatory
	DESCRIPTION	"IPX node name."
	::=		{ svNodeGroup 1 }

nodeGrpNetName		OBJECT-TYPE
	SYNTAX		DisplayString (SIZE(0..10))
	ACCESS		read-only
			-- C-ACCESS-FUNC NodeMibNetName
	STATUS		mandatory
	DESCRIPTION	"IPX network name."
	::=		{ svNodeGroup 2 }

nodeGrpAlarmState	OBJECT-TYPE
	SYNTAX		INTEGER	{ 
				clear			(1),
				minor			(2),
				major			(3),
				unreachable		(5)
			}
	ACCESS		read-only
			-- C-STRUCT node-cfg, FIELD nodeAlarmState
			-- C-LOCATOR-FUNC NodeMibNodeLocator
	STATUS		mandatory
	DESCRIPTION	"Node Alarm State. Only low 6 bits are
			valid."
	::=		{ svNodeGroup 3 }

nodeGrpGateway		OBJECT-TYPE
	SYNTAX		INTEGER	{
				not-a-gateway	(1),
				gateway		(2)
			}
	ACCESS		read-only
			-- C-STRUCT node-cfg, FIELD nodeGateway
			-- C-LOCATOR-FUNC NodeMibNodeLocator
	STATUS		mandatory
	DESCRIPTION	"Is this node acting as a gateway?"
	::=		{ svNodeGroup 4 }

nodeGrpActive		OBJECT-TYPE
	SYNTAX		Active
	ACCESS		read-only
			-- C-STRUCT node-cfg, FIELD nodeActive
			-- C-LOCATOR-FUNC NodeMibNodeLocator
	STATUS		mandatory
	DESCRIPTION	"Active state of this Node."
	::=		{ svNodeGroup 5 }

nodeGrpPlatform		OBJECT-TYPE
	SYNTAX		INTEGER	{
				ipx-platform	(1),
				bpx-platform	(2),
				axis-platform	(3)
			}
	ACCESS		read-only
			-- C-STRUCT node-cfg, FIELD nodePlatform
			-- C-LOCATOR-FUNC NodeMibNodeLocator
	STATUS		mandatory
	DESCRIPTION	"Platform type."
	::=		{ svNodeGroup 6 }

nodeGrpRelease		OBJECT-TYPE
	SYNTAX		DisplayString (SIZE(0..10))
	ACCESS		read-only
			-- C-STRUCT node-cfg, FIELD nodeRelease
			-- C-LOCATOR-FUNC NodeMibNodeLocator
	STATUS		mandatory
	DESCRIPTION	"StrataView Plus release revison."
	::=		{ svNodeGroup 7 }

nodeFsIncRate		OBJECT-TYPE
	SYNTAX		INTEGER
	ACCESS		read-only
			-- C-STRUCT node-cfg, FIELD nodeFsIncRate
			-- C-LOCATOR-FUNC NodeMibNodeLocator
	STATUS		mandatory
	DESCRIPTION	"FRP Foresight increase rate."
	::=		{ svNodeGroup 8 }

nodeFsDecRate		OBJECT-TYPE
	SYNTAX		INTEGER
	ACCESS		read-only
			-- C-STRUCT node-cfg, FIELD nodeFsDecRate
			-- C-LOCATOR-FUNC NodeMibNodeLocator
	STATUS		mandatory
	DESCRIPTION	"FRP forsight normal decrease rate."
	::=		{ svNodeGroup 9 }

nodeFsFastRate		OBJECT-TYPE
	SYNTAX		INTEGER
	ACCESS		read-only
			-- C-STRUCT node-cfg, FIELD nodeFsFastRate
			-- C-LOCATOR-FUNC NodeMibNodeLocator
	STATUS		mandatory
	DESCRIPTION	"FRP forsight fast decrease rate."
	::=		{ svNodeGroup 10 }

nodeRstTimeout		OBJECT-TYPE
	SYNTAX		INTEGER
	ACCESS		read-only
			-- C-STRUCT node-cfg, FIELD nodeRstTimeout
			-- C-LOCATOR-FUNC NodeMibNodeLocator
	STATUS		mandatory
	DESCRIPTION	"Timeout for resetting PVC rate to QIR."
	::=		{ svNodeGroup 11 }

alarmTrapSequenceNumber	OBJECT-TYPE
	SYNTAX		INTEGER
	ACCESS		read-only
			-- C-STRUCT proxy-ctxt, FIELD 	lastTrapSeqNum
	STATUS		mandatory
	DESCRIPTION	"The Sequence Number of the last trap generated on the SNMP Proxy"
	::=		{ svNodeGroup 12 }


----------------------------------------------------------------------- 
--	Packet Group
-----------------------------------------------------------------------

----------------------------------------------------------------------- 
--	Packet Line Table has been deleted and replaced by the Trunk Table.   
----------------------------------------------------------------------- 
--pktLineTable		OBJECT-TYPE
--	SYNTAX		SEQUENCE OF PktLineEntry
--	ACCESS		not-accessible
--	STATUS		mandatory
--	DESCRIPTION	"The table of Packet Lines." 
--	::=		{ packetGroup 1 }


----------------------------------------------------------------------- 
--	Trunk Table
-----------------------------------------------------------------------

trunkTable		OBJECT-TYPE
	SYNTAX		SEQUENCE OF TrunkEntry
	ACCESS		not-accessible
	STATUS		mandatory
	DESCRIPTION	"The table of Trunk Lines."
	::=		{ packetGroup 2 }

trunkEntry		OBJECT-TYPE
	SYNTAX		TrunkEntry
	ACCESS		not-accessible
	STATUS		mandatory
	DESCRIPTION	"An entry in the Trunk table."
	INDEX		{ trunkLocalSlot, trunkLocalPort }
			-- C-NEXT-FUNC	trunk-next
	::=		{ trunkTable 1 }

TrunkEntry	::=	SEQUENCE {
	trunkLocalSlot				INTEGER,
	trunkLocalPort				INTEGER,
	trunkLocalLine				INTEGER,
	trunkCardType				INTEGER,
	trunkInterface				INTEGER,
	trunkLineLoad				INTEGER,
	trunkRemNodeId				INTEGER,
	trunkRemLineNumber			INTEGER,
	trunkRemSlot				INTEGER,
	trunkRemPort				INTEGER,
	trunkAlarmState				INTEGER,
	trunkComment				DisplayString,
	trunkActive				Active,
	trunkStatus				INTEGER,
	trunkStatReserve			INTEGER,
	trunkBurstyDataBQDepth			INTEGER,
	trunkBurstyDataBQEfcnThreshold		INTEGER,
	trunkClpHighDropThreshold		INTEGER,
	trunkClpLowDropThreshold		INTEGER
}

trunkLocalSlot	OBJECT-TYPE
	SYNTAX		INTEGER
	ACCESS		read-only
			-- C-STRUCT trunk-cfg, FIELD trunkLocalSlot
			-- C-LOCATOR-FUNC trunk-locator
	STATUS		mandatory
	DESCRIPTION	"Local Slot Number.  These are numbered
			starting at 1."
	::=		{ trunkEntry 1 }

trunkLocalPort	OBJECT-TYPE
	SYNTAX		INTEGER
	ACCESS		read-only
			-- C-STRUCT trunk-cfg, FIELD trunkLocalPort
			-- C-LOCATOR-FUNC trunk-locator
	STATUS		mandatory
	DESCRIPTION	"Local Port Number.  These are numbered
			 starting at 1."
	::=		{ trunkEntry 2 }

trunkLocalLine	OBJECT-TYPE
	SYNTAX		INTEGER
	ACCESS		read-only
			-- C-STRUCT trunk-cfg, FIELD trunkLineNumber
			-- C-LOCATOR-FUNC trunk-locator
	STATUS		mandatory
	DESCRIPTION	"Local Line Number.  These are numbered
			 starting at 1."
	::=		{ trunkEntry 3 }

trunkCardType		OBJECT-TYPE
	SYNTAX		INTEGER	{ txr(3),
				  bni(4),
				  ntc(22),
				  atm(31),
				  ait(34),
				  bni-t3(103),
				  bni-e3(104),
				  bni-oc3(110)
				}
	ACCESS		read-only
			-- C-STRUCT trunk-cfg, FIELD trunkCardType
			-- C-LOCATOR-FUNC trunk-locator
	STATUS		mandatory
	DESCRIPTION	"Type of the card supporting the trunk line.
			The card type is dependant on the value
			of nodePlatform.

			Additional types may exist with future 
			hardware."
	::=		{ trunkEntry 4 }

trunkInterface	OBJECT-TYPE
	SYNTAX		INTEGER	{ unknown (1),
				  t1-d4	  (2),
				  t1-esf  (3),
				  e1-30   (4),
				  e1-31   (5),
				  e1-32   (6),
				  subrate (7),
				  atm     (8) }
	ACCESS		read-only
			-- C-STRUCT trunk-cfg, FIELD trunkInterface
			-- C-LOCATOR-FUNC trunk-locator
	STATUS		mandatory
	DESCRIPTION	"Trunk Line Interface Type. Indicates the
			 format of the packet line."
	::=		{ trunkEntry 5 }

trunkLineLoad		OBJECT-TYPE
	SYNTAX		INTEGER
	ACCESS		read-only
			-- C-STRUCT trunk-cfg, FIELD trunkLineLoad
			-- C-LOCATOR-FUNC trunk-locator
	STATUS		mandatory
	DESCRIPTION	"Line Load in packets per second."
	::=		{ trunkEntry 6 }

trunkRemNodeId	OBJECT-TYPE
	SYNTAX		INTEGER
	ACCESS		read-only
			-- C-STRUCT trunk-cfg, FIELD trunkRemNodeId
			-- C-LOCATOR-FUNC trunk-locator
	STATUS		mandatory
	DESCRIPTION	"Remote StrataView Node ID."
	::=		{ trunkEntry 7 }

trunkRemLineNumber	OBJECT-TYPE
	SYNTAX		INTEGER
	ACCESS		read-only
			-- C-STRUCT trunk-cfg, FIELD trunkRemLineNumber
			-- C-LOCATOR-FUNC trunk-locator
	STATUS		mandatory
	DESCRIPTION	"Remote Line Number."
	::=		{ trunkEntry 8 }

trunkRemSlot		OBJECT-TYPE
	SYNTAX		INTEGER
	ACCESS		read-only
			-- C-STRUCT trunk-cfg, FIELD trunkRemSlot
			-- C-LOCATOR-FUNC trunk-locator
	STATUS		mandatory
	DESCRIPTION	"Remote Slot Number."
	::=		{ trunkEntry 9 }

trunkRemPort		OBJECT-TYPE
	SYNTAX		INTEGER
	ACCESS		read-only
			-- C-STRUCT trunk-cfg, FIELD trunkRemPort
			-- C-LOCATOR-FUNC trunk-locator
	STATUS		mandatory
	DESCRIPTION	"Remote Port Number."
	::=		{ trunkEntry 10 }

trunkAlarmState	OBJECT-TYPE
	SYNTAX		INTEGER	{ 
							clear		(1),
				  			minor		(2),
				  			major		(3) 
						}
	ACCESS		read-only
			-- C-STRUCT trunk-cfg, FIELD trunkAlarmState
			-- C-LOCATOR-FUNC trunk-locator
	STATUS		mandatory
	DESCRIPTION	"Trunk Line Alarm State."
	::=		{ trunkEntry 11 }

trunkComment		OBJECT-TYPE
	SYNTAX		DisplayString (SIZE(0..20))
	ACCESS		read-only
			-- C-STRUCT trunk-cfg, FIELD trunkComment
			-- C-LOCATOR-FUNC trunk-locator
	STATUS		mandatory
	DESCRIPTION	"StrataView user entered comment field used to
			further qualify the trunk line."
	::=		{ trunkEntry 12 }

trunkActive		OBJECT-TYPE
	SYNTAX		Active
	ACCESS		read-only
			-- C-STRUCT trunk-cfg, FIELD trunkActive
			-- C-LOCATOR-FUNC trunk-locator
	STATUS		mandatory
	DESCRIPTION	"Active State."
	::=		{ trunkEntry 13 }

trunkStatus		OBJECT-TYPE
	SYNTAX		INTEGER	{
				inactive(1),
				clear(2),
				fail(3),
				down(4)
			}
	ACCESS		read-only
			-- C-STRUCT trunk-cfg, FIELD trunkStatus
			-- C-LOCATOR-FUNC trunk-locator
	STATUS		mandatory
	DESCRIPTION	"Trunk line status."
	::=		{ trunkEntry 14 }

trunkStatReserve	OBJECT-TYPE
	SYNTAX		INTEGER
	ACCESS		read-only
			-- C-STRUCT trunk-cfg, FIELD trunkStatReserve
			-- C-LOCATOR-FUNC trunk-locator
	STATUS		mandatory
	DESCRIPTION	"Trunk Line statistical reserve field."
	::=		{ trunkEntry 15 }

trunkBurstyDataBQDepth	OBJECT-TYPE
	SYNTAX		INTEGER
	ACCESS		read-only
			-- C-STRUCT trunk-cfg, FIELD trunkBurstyDataBQDepth
			-- C-LOCATOR-FUNC trunk-locator
	STATUS		mandatory
	DESCRIPTION	"Trunk Line bursty data B queue depth."
	::=		{ trunkEntry 16 }

trunkBurstyDataBQEfcnThreshold	OBJECT-TYPE
	SYNTAX		INTEGER
	ACCESS		read-only
			-- C-STRUCT trunk-cfg, FIELD trunkBurstyDataBQEfcnThreshold
			-- C-LOCATOR-FUNC trunk-locator
	STATUS		mandatory
	DESCRIPTION	"Trunk Line bursty data B queue EFCN/FFCI threshold."
	::=		{ trunkEntry 17 }

trunkClpHighDropThreshold	OBJECT-TYPE
	SYNTAX		INTEGER
	ACCESS		read-only
			-- C-STRUCT trunk-cfg, FIELD trunkClpHighDropThreshold
			-- C-LOCATOR-FUNC trunk-locator
	STATUS		mandatory
	DESCRIPTION	"Trunk Line CLP high dropping threshold."
	::=		{ trunkEntry 18 }

trunkClpLowDropThreshold	OBJECT-TYPE
	SYNTAX		INTEGER
	ACCESS		read-only
			-- C-STRUCT trunk-cfg, FIELD trunkClpLowDropThreshold
			-- C-LOCATOR-FUNC trunk-locator
	STATUS		mandatory
	DESCRIPTION	"Trunk Line CLP low dropping threshold."
	::=		{ trunkEntry 19 }

----------------------------------------------------------------------- 
--	Circuit Group
-----------------------------------------------------------------------

----------------------------------------------------------------------- 
--	Circuit Line Table
--      ASI Lines are not supported in this MIB table.
----------------------------------------------------------------------- 
cirLineTable		OBJECT-TYPE
	SYNTAX		SEQUENCE OF CirLineEntry
	ACCESS		not-accessible
	STATUS		mandatory
	DESCRIPTION	"The table of Circuit Lines."
	::=		{ circuitGroup 1 }

cirLineEntry		OBJECT-TYPE
	SYNTAX		CirLineEntry
	ACCESS		not-accessible
	STATUS		mandatory
	DESCRIPTION	"An entry in the Circuit Line table."
	INDEX		{ cirLineLineNumber, cirLinePortNumber }
			-- C-NEXT-FUNC	cirLine-next
	::=		{ cirLineTable 1 }

CirLineEntry	::=	SEQUENCE {
	cirLineLineNumber		INTEGER,
	cirLineCardType			INTEGER,
	cirLineInterface		INTEGER,
	cirLineComment			DisplayString,
	cirLineActive			Active,
	cirLineStatus			INTEGER,
	cirLinePortNumber		INTEGER
}

cirLineLineNumber	OBJECT-TYPE
	SYNTAX		INTEGER
	ACCESS		read-only
			-- C-STRUCT cir-line-cfg, FIELD cirLineLineNumber
			-- C-LOCATOR-FUNC cirLine-locator
	STATUS		mandatory
	DESCRIPTION	"Circuit Line Number."
	::=		{ cirLineEntry 3 }

cirLineCardType		OBJECT-TYPE
	SYNTAX		INTEGER	{ txr		(3),
				  cip		(21),
				  frp		(25),
				  cdp		(29) }
	ACCESS		read-only
			-- C-STRUCT cir-line-cfg, FIELD cirLineCardType
			-- C-LOCATOR-FUNC cirLine-locator
	STATUS		mandatory
	DESCRIPTION	"Circuit Card Type."
	::=		{ cirLineEntry 4 }

cirLineInterface	OBJECT-TYPE
	SYNTAX		INTEGER	{ unknown	(1),
				  t1		(2),
				  e1		(3) }
	ACCESS		read-only
			-- C-STRUCT cir-line-cfg, FIELD cirLineInterface
			-- C-LOCATOR-FUNC cirLine-locator
	STATUS		mandatory
	DESCRIPTION	"Circuit Line Interface Type.  Indicates the
			 format of the circuit line."
	::=		{ cirLineEntry 5 }

cirLineComment		OBJECT-TYPE
	SYNTAX		DisplayString (SIZE(0..22))
	ACCESS		read-only
			-- C-STRUCT cir-line-cfg, FIELD cirLineComment
			-- C-LOCATOR-FUNC cirLine-locator
	STATUS		mandatory
	DESCRIPTION	"Comment entered by StrataView user to further
			qualify the Circuit Line."
	::=		{ cirLineEntry 6 }

cirLineActive		OBJECT-TYPE
	SYNTAX		Active
	ACCESS		read-only
			-- C-STRUCT cir-line-cfg, FIELD cirLineActive
			-- C-LOCATOR-FUNC cirLine-locator
	STATUS		mandatory
	DESCRIPTION	"Circuit Line Active State."
	::=		{ cirLineEntry 7 }

cirLineStatus		OBJECT-TYPE
	SYNTAX		INTEGER	{
				inactive(1),
				clear(2),
				fail(3),
				down(4)
			}
	ACCESS		read-only
			-- C-STRUCT cir-line-cfg, FIELD cirLineStatus
			-- C-LOCATOR-FUNC cirLine-locator
	STATUS		mandatory
	DESCRIPTION	"Circuit Line Status."
	::=		{ cirLineEntry 8 }

cirLinePortNumber	OBJECT-TYPE
	SYNTAX		INTEGER
	ACCESS		read-only
			-- C-STRUCT cir-line-cfg, FIELD cirLinePortNumber
			-- C-LOCATOR-FUNC cirLine-locator
	STATUS		mandatory
	DESCRIPTION	"Always returned as 0 for GET requests.
                         ASI port number is filled-in for TRAPs."
	::=		{ cirLineEntry 9 }

----------------------------------------------------------------------- 
--	Frame Relay Port Group
-----------------------------------------------------------------------

----------------------------------------------------------------------- 
--	Frame Relay Port Table
----------------------------------------------------------------------- 
frpTable		OBJECT-TYPE
	SYNTAX		SEQUENCE OF FrpEntry
	ACCESS		not-accessible
	STATUS		mandatory
	DESCRIPTION	"The table of Frame Relay Ports."
	::=		{ frpGroup 1 }

frpEntry		OBJECT-TYPE
	SYNTAX		FrpEntry
	ACCESS		not-accessible
	STATUS		mandatory
	DESCRIPTION	"An entry in the Frame Relay Ports table."
	INDEX		{ frpLocalSlot, frpLocalLine, frpLocalPort }
			-- C-NEXT-FUNC	frp-next
	::=		{ frpTable 1 }

FrpEntry	::=	SEQUENCE {
	frpLocalSlot				INTEGER,
	frpLocalPort				INTEGER,
	frpPortSpeed				INTEGER,
	frpComment				DisplayString,	
	frpActive				Active,
	frpStatus				INTEGER,
	frpQDepth				INTEGER,
	frpEcnThreshold				INTEGER,
	frpDeThreshold				INTEGER,
	frpPortType				INTEGER,
	frpLocalLine			INTEGER
}

frpLocalSlot		OBJECT-TYPE
	SYNTAX		INTEGER
	ACCESS		read-only
			-- C-STRUCT frp-cfg, FIELD frpLocalSlot
			-- C-LOCATOR-FUNC frp-locator
	STATUS		mandatory
	DESCRIPTION	"Local Slot Number."
	::=		{ frpEntry 3 }

frpLocalPort		OBJECT-TYPE
	SYNTAX		INTEGER
	ACCESS		read-only
			-- C-STRUCT frp-cfg, FIELD frpLocalPort
			-- C-LOCATOR-FUNC frp-locator
	STATUS		mandatory
	DESCRIPTION	"Local Port Number.  These are numbered
			 starting at 1."
	::=		{ frpEntry 4 }

frpPortSpeed		OBJECT-TYPE
	SYNTAX		INTEGER
	ACCESS		read-only
			-- C-STRUCT frp-cfg, FIELD frpPortSpeed
			-- C-LOCATOR-FUNC frp-locator
	STATUS		mandatory
	DESCRIPTION	"Port Speed in bits per second."
	::=		{ frpEntry 5 }

frpComment		OBJECT-TYPE
	SYNTAX		DisplayString (SIZE(0..22))
	ACCESS		read-only
			-- C-STRUCT frp-cfg, FIELD frpComment
			-- C-LOCATOR-FUNC frp-locator
	STATUS		mandatory
	DESCRIPTION	"StrataView User comment used to further
			qualify the Frame Relay Port."
	::=		{ frpEntry 6 }

frpActive		OBJECT-TYPE
	SYNTAX		Active
	ACCESS		read-only
			-- C-STRUCT frp-cfg, FIELD frpActive
			-- C-LOCATOR-FUNC frp-locator
	STATUS		mandatory
	DESCRIPTION	"Frame Relay Port Active State."
	::=		{ frpEntry 7 }

frpStatus		OBJECT-TYPE
	SYNTAX		INTEGER	{
				inactive(1),
				clear(2),
				fail(3),
				down(4)
			}
	ACCESS		read-only
			-- C-STRUCT frp-cfg, FIELD frpStatus
			-- C-LOCATOR-FUNC frp-locator
	STATUS		mandatory
	DESCRIPTION	"Frame Relay Port Status."
	::=		{ frpEntry 8 }

frpQDepth		OBJECT-TYPE
	SYNTAX		INTEGER
	ACCESS		read-only
			-- C-STRUCT frp-cfg, FIELD frpQDepth
			-- C-LOCATOR-FUNC frp-locator
	STATUS		mandatory
	DESCRIPTION	"Frame Relay Port queue depth."
	::=		{ frpEntry 9 }

frpEcnThreshold		OBJECT-TYPE
	SYNTAX		INTEGER
	ACCESS		read-only
			-- C-STRUCT frp-cfg, FIELD frpEcnThreshold
			-- C-LOCATOR-FUNC frp-locator
	STATUS		mandatory
	DESCRIPTION	"Frame Relay Port ECN queue threshold."
	::=		{ frpEntry 10 }

frpDeThreshold		OBJECT-TYPE
	SYNTAX		INTEGER
	ACCESS		read-only
			-- C-STRUCT frp-cfg, FIELD frpDeThreshold
			-- C-LOCATOR-FUNC frp-locator
	STATUS		mandatory
	DESCRIPTION	"Frame Relay Port DE threshold."
	::=		{ frpEntry 11 }

frpPortType		OBJECT-TYPE
	SYNTAX		INTEGER	{
				uni(1),
				nni(2),
				aip(3),
				not-defined(4),
				frsm(5),
                                portConcent(6)
			}
	ACCESS		read-only
			-- C-STRUCT frp-cfg, FIELD frpPortType
			-- C-LOCATOR-FUNC frp-locator
	STATUS		mandatory
	DESCRIPTION	"Frame relay port type. "
	::=		{ frpEntry 12 }

frpLocalLine		OBJECT-TYPE
	SYNTAX		INTEGER
	ACCESS		read-only
		-- 	C-STRUCT frp-cfg, FIELD frpLocalLine
		-- 	C-LOCATOR-FUNC frp-locator
	STATUS		mandatory
	DESCRIPTION	"Local Line Number."
	::=		{ frpEntry 13 }

----------------------------------------------------------------------- 
--	Connection Group
-----------------------------------------------------------------------

----------------------------------------------------------------------- 
--	Connection Table
----------------------------------------------------------------------- 
connServerTable		OBJECT-TYPE
	SYNTAX		SEQUENCE OF ConnEntry
	ACCESS		not-accessible
	STATUS		mandatory
	DESCRIPTION	"The table of Connections."
	::=		{ connGroup 1 }

connEntry		OBJECT-TYPE
	SYNTAX		ConnEntry
	ACCESS		not-accessible
	STATUS		mandatory
	DESCRIPTION	"An entry in the Connections table."
	INDEX		{ connLocalSlot, connLocalLine, connLocalChannel, connLocalDLCI }
			-- C-NEXT-FUNC	conn-next
	::=		{ connServerTable 1 }

ConnEntry	::=	SEQUENCE {
	connLocalSlot			INTEGER,
	connLocalChannel		INTEGER,
	connLocalDLCI			INTEGER,
	connRemoteNodeId		INTEGER,
	connRemoteSlot			INTEGER,
	connRemoteChannel		INTEGER,
	connRemoteDLCI			INTEGER,
	connServerType			INTEGER,
	connRate			INTEGER,
	connLocalMaxPkts		INTEGER,
	connRemoteMaxPkts		INTEGER,
	connMinBandwidth		INTEGER,
	connDAX				INTEGER,
	connTXR				INTEGER,
	connComment			DisplayString,
	connActive			Active,
	connStatus			INTEGER,
	connQir				INTEGER,
	connPir				INTEGER,
	connVcQueDepth			INTEGER,
	connVcQueThreshold		INTEGER,
	connCMax			INTEGER,
	connPerUtil			INTEGER,
	connConnInfoFlag		INTEGER,
	connCir				INTEGER,
	connABitStatus			INTEGER,
	connLocalLine			INTEGER
}

connLocalSlot		OBJECT-TYPE
	SYNTAX		INTEGER
	ACCESS		read-only
			-- C-STRUCT connection-cfg, FIELD connLocalSlot
			-- C-LOCATOR-FUNC conn-locator
	STATUS		mandatory
	DESCRIPTION	"Local Slot Number."
	::=		{ connEntry 3 }

connLocalChannel	OBJECT-TYPE
	SYNTAX		INTEGER
	ACCESS		read-only
			-- C-STRUCT connection-cfg, FIELD connLocalChannel
			-- C-LOCATOR-FUNC conn-locator
	STATUS		mandatory
	DESCRIPTION	"Local Channel Number.  These are numbered
			 starting at 1."
	::=		{ connEntry 4 }

connLocalDLCI		OBJECT-TYPE
	SYNTAX		INTEGER
	ACCESS		read-only
			-- C-STRUCT connection-cfg, FIELD connLocalDLCI
			-- C-LOCATOR-FUNC conn-locator
	STATUS		mandatory
	DESCRIPTION	"Local DLCI Number."
	::=		{ connEntry 5 }

connRemoteNodeId	OBJECT-TYPE
	SYNTAX		INTEGER
	ACCESS		read-only
			-- C-STRUCT connection-cfg, FIELD connRemoteNodeId
			-- C-LOCATOR-FUNC conn-locator
	STATUS		mandatory
	DESCRIPTION	"Remote StrataView Node ID."
	::=		{ connEntry 6 }

connRemoteSlot		OBJECT-TYPE
	SYNTAX		INTEGER
	ACCESS		read-only
			-- C-STRUCT connection-cfg, FIELD connRemoteSlot
			-- C-LOCATOR-FUNC conn-locator
	STATUS		mandatory
	DESCRIPTION	"Remote Slot Number."
	::=		{ connEntry 7 }

connRemoteChannel	OBJECT-TYPE
	SYNTAX		INTEGER
	ACCESS		read-only
			-- C-STRUCT connection-cfg, FIELD connRemoteChannel
			-- C-LOCATOR-FUNC conn-locator
	STATUS		mandatory
	DESCRIPTION	"Remote Channel Number.  These are
			 numbered starting at 1."
	::=		{ connEntry 8 }

connRemoteDLCI		OBJECT-TYPE
	SYNTAX		INTEGER
	ACCESS		read-only
			-- C-STRUCT connection-cfg, FIELD connRemoteDLCI
			-- C-LOCATOR-FUNC conn-locator
	STATUS		mandatory
	DESCRIPTION	"Remote DLCI Number."
	::=		{ connEntry 9 }

connServerType		OBJECT-TYPE
	SYNTAX		INTEGER	{ voice-dsi-adpcm	(1),
				  voice-dsi		(2),
				  voice			(3),
				  voice-adpcm		(4),
				  data			(5),
				  frame-relay		(6) }
	ACCESS		read-only
			-- C-STRUCT connection-cfg, FIELD connType
			-- C-LOCATOR-FUNC conn-locator
	STATUS		mandatory
	DESCRIPTION	"Connection Type."
	::=		{ connEntry 10 }

connRate		OBJECT-TYPE
	SYNTAX		INTEGER
	ACCESS		read-only
			-- C-STRUCT connection-cfg, FIELD connRate
			-- C-LOCATOR-FUNC conn-locator
	STATUS		mandatory
	DESCRIPTION	"Combination Field of Rate Info.  The value for
			this variable is generated by ORing together
			the following:
				0x80 ->	Fast Eia Enabled
				0x40 -> DFM Enabled

				0x08 -> 7/8 Encoding
				0x10 -> 8/8 Encoding
				0x18 -> 8/8 Inverted Encoding
				0x20 -> 7/8 Inverted Encoding

				0x01 -> Voice
				0x02 -> Non-Time Stamped
			        0x03 -> Time Stamped
				0x04 -> bursty data
				0x05 -> multicast
			These form four fields: bit 7, bit 6, bits 3-5,
			and bits 0-2."
	::=		{ connEntry 11 }

connLocalMaxPkts	OBJECT-TYPE
	SYNTAX		INTEGER
	ACCESS		read-only
			-- C-STRUCT connection-cfg, FIELD connLocalMaxPkts
			-- C-LOCATOR-FUNC conn-locator
	STATUS		mandatory
	DESCRIPTION	"Local maximum number of packets per second
			allocated."
	::=		{ connEntry 12 }

connRemoteMaxPkts	OBJECT-TYPE
	SYNTAX		INTEGER
	ACCESS		read-only
			-- C-STRUCT connection-cfg, FIELD connRemoteMaxPkts
			-- C-LOCATOR-FUNC conn-locator
	STATUS		mandatory
	DESCRIPTION	"Remote maximum number of packets per second
			allocated."
	::=		{ connEntry 13 }

connMinBandwidth	OBJECT-TYPE
	SYNTAX		INTEGER
	ACCESS		read-only
			-- C-STRUCT connection-cfg, FIELD connMinBandwidth
			-- C-LOCATOR-FUNC conn-locator
	STATUS		mandatory
	DESCRIPTION	"Minimum guaranteed bandwidth in bits per
			second.  Zero if not meaningful."
	::=		{ connEntry 14 }

connDAX			OBJECT-TYPE
	SYNTAX		INTEGER	{ non-dax(1), dax(2) }
	ACCESS		read-only
			-- C-STRUCT connection-cfg, FIELD connDAX
			-- C-LOCATOR-FUNC conn-locator
	STATUS		mandatory
	DESCRIPTION	"Flag to identify DAX connection."
	::=		{ connEntry 15 }

connTXR			OBJECT-TYPE
	SYNTAX		INTEGER	{ non-txr(1), txr(2) }
	ACCESS		read-only
			-- C-STRUCT connection-cfg, FIELD connTXR
			-- C-LOCATOR-FUNC conn-locator
	STATUS		mandatory
	DESCRIPTION	"Flag to identify voice connection end point
			card is TXR card type."
	::=		{ connEntry 16 }

connComment		OBJECT-TYPE
	SYNTAX		DisplayString (SIZE(0..22))
	ACCESS		read-only
			-- C-STRUCT connection-cfg, FIELD connComment
			-- C-LOCATOR-FUNC conn-locator
	STATUS		mandatory
	DESCRIPTION	"StrataView user entered comment field used to
			further qualify the connection."
	::=		{ connEntry 17 }

connActive		OBJECT-TYPE
	SYNTAX		Active
	ACCESS		read-only
			-- C-STRUCT connection-cfg, FIELD connActive
			-- C-LOCATOR-FUNC conn-locator
	STATUS		mandatory
	DESCRIPTION	"Connection Active State."
	::=		{ connEntry 18 }

connStatus		OBJECT-TYPE
	SYNTAX		INTEGER	{
				inactive(1),
				clear(2),
				fail(3),
				down(4)
			}
	ACCESS		read-only
			-- C-STRUCT connection-cfg, FIELD connLineStatus
			-- C-LOCATOR-FUNC conn-locator
	STATUS		mandatory
	DESCRIPTION	"Connection Status."
	::=		{ connEntry 19 }

connQir			OBJECT-TYPE
	SYNTAX		INTEGER
	ACCESS		read-only
			-- C-STRUCT connection-cfg, FIELD connQir
			-- C-LOCATOR-FUNC conn-locator
	STATUS		mandatory
	DESCRIPTION	"Connection QIR.(bits per sec)"
	::=		{ connEntry 20 }

connPir			OBJECT-TYPE
	SYNTAX		INTEGER
	ACCESS		read-only
			-- C-STRUCT connection-cfg, FIELD connPir
			-- C-LOCATOR-FUNC conn-locator
	STATUS		mandatory
	DESCRIPTION	"Connection PIR.(bits per sec)"
	::=		{ connEntry 21 }

connVcQueDepth		OBJECT-TYPE
	SYNTAX		INTEGER
	ACCESS		read-only
			-- C-STRUCT connection-cfg, FIELD connVcQueDepth
			-- C-LOCATOR-FUNC conn-locator
	STATUS		mandatory
	DESCRIPTION	"Connection VcQueDepth."
	::=		{ connEntry 22 }

connVcQueThreshold	OBJECT-TYPE
	SYNTAX		INTEGER
	ACCESS		read-only
			-- C-STRUCT connection-cfg, FIELD connVcQueThresh
			-- C-LOCATOR-FUNC conn-locator
	STATUS		mandatory
	DESCRIPTION	"Connection VcQueThreshold."
	::=		{ connEntry 23 }

connCMax		OBJECT-TYPE
	SYNTAX		INTEGER
	ACCESS		read-only
			-- C-STRUCT connection-cfg, FIELD connCMax
			-- C-LOCATOR-FUNC conn-locator
	STATUS		mandatory
	DESCRIPTION	"Connection maximum threshold for FRP credit
			manager."
	::=		{ connEntry 24 }

connPerUtil		OBJECT-TYPE
	SYNTAX		INTEGER
	ACCESS		read-only
			-- C-STRUCT connection-cfg, FIELD connPerUtil
			-- C-LOCATOR-FUNC conn-locator
	STATUS		mandatory
	DESCRIPTION	"Connection Percent utilization."
	::=		{ connEntry 25 }

connConnInfoFlag	OBJECT-TYPE
	SYNTAX		INTEGER
	ACCESS		read-only
			-- C-STRUCT connection-cfg, FIELD connConnInfoFlag
			-- C-LOCATOR-FUNC conn-locator
	STATUS		mandatory
	DESCRIPTION	"Connection information flags.  The flags are 
			define as:

				bit 6	snaPriorityHigh - decimal 64
				bit 7	forsightEnabled - decimal 128

			A value of 0 indicates no bits are set."
	::=		{ connEntry 26 }

connCir			OBJECT-TYPE
	SYNTAX		INTEGER
	ACCESS		read-only
			-- C-STRUCT connection-cfg, FIELD connCir
			-- C-LOCATOR-FUNC conn-locator
	STATUS		mandatory
	DESCRIPTION	"Connection CIR.(bits per sec)"
	::=		{ connEntry 27 }

connABitStatus		OBJECT-TYPE
	SYNTAX		INTEGER
	ACCESS		read-only
			-- C-STRUCT connection-cfg, FIELD connABitStatus
			-- C-LOCATOR-FUNC conn-locator
	STATUS		mandatory
	DESCRIPTION	"Connection Bit status field.  The fields 
			defined are:
 
				bit 6	remotePacketLine - decimal 64
				bit 7	aBitOk - decimal 128.

			A value of 0 indicates no bits are set."
	::=		{ connEntry 28 }

connLocalLine		OBJECT-TYPE
	SYNTAX		INTEGER
	ACCESS		read-only
		-- 	C-STRUCT connection-cfg, FIELD connLocalLine
		-- 	C-LOCATOR-FUNC conn-locator
	STATUS		mandatory
	DESCRIPTION	"Local Line Number. Valid only for AXIS"
	::=		{ connEntry 29 }

--
--
-- Real Time Counters Group	
--

--
-- packet Line Real Time Counters table has been deleted and replace by
-- the TrunkLine Real Time Counters table beginning with
-- StrataView Plus release ???

--
--PktLineRTCTable	OBJECT-TYPE
--	SYNTAX		SEQUENCE OF PktLineRTCEntry
--	ACCESS		not-accessible
--	STATUS		mandatory
--	DESCRIPTION	"The table of Packet s Line statistics."
--	::=		{ realTimeCountersGroup 1 }


--
-- circuit Line Real Time Counters table --
cirLineRTCTable	OBJECT-TYPE
	SYNTAX		SEQUENCE OF CirLineRTCEntry
	ACCESS		not-accessible
	STATUS		mandatory
	DESCRIPTION	"The table of Circuit Line statistics."
	::=		{ realTimeCountersGroup 2 }

cirLineRTCEntry	OBJECT-TYPE
	SYNTAX		CirLineRTCEntry
	ACCESS		not-accessible
	STATUS		mandatory
	DESCRIPTION	"An entry in the Circuit Line statistics table.
			Each row may be sparse."
	INDEX		{ cirLineRTCLineNumber }
			-- C-NEXT-FUNC	cirLine-next
	::=		{ cirLineRTCTable 1 }

CirLineRTCEntry ::=	SEQUENCE {
	--
	-- All of the Counters in this table can be very time-expensive
	-- to retrieve, taking as much as 10 seconds each.
	-- Manger timeout values should be adjusted accordingly, and
	-- Get-Next walks through this portion of the table should be
	-- avoided.
	--
	cirLineRTCLineNumber		INTEGER,
	cirLineRTCBipolarViolations	Counter,
	cirLineRTCFrameSlips		Counter,
	cirLineRTCOutOfFrames		Counter,
	cirLineRTCLossesOfSignal	Counter,
	cirLineRTCFrameBitErrors	Counter,
	cirLineRTCCrcErrors		Counter,
	cirLineRTCOutOfMultiFrames	Counter,
	cirLineRTCAllOnesInTimeslot16	Counter
}

cirLineRTCLineNumber	OBJECT-TYPE
	SYNTAX		INTEGER
	ACCESS		read-only
			-- C-STRUCT cir-line-cfg, FIELD cirLineLineNumber
			-- C-LOCATOR-FUNC cirLine-locator
	STATUS		mandatory
	DESCRIPTION	"Circuit Line Line Number."
	::=		{ cirLineRTCEntry 1 }

cirLineRTCBipolarViolations
			OBJECT-TYPE
	SYNTAX		Counter
	ACCESS		read-only
			-- C-ACCESS-FUNC cirLineRTCBipolarViolations
			-- C-NEXT-FUNC cirLine-BipolarViolations-next
			-- C-PRE-GET-FUNC PreGet-cirLineRTCBipolarViolations
	STATUS		mandatory
	DESCRIPTION	"The number of bipolar violations which have
			occurred on the line.  This statistic is valid
			for T1 circuits only."
	::=		{ cirLineRTCEntry 4 }

cirLineRTCFrameSlips	OBJECT-TYPE
	SYNTAX		Counter
	ACCESS		read-only
			-- C-ACCESS-FUNC cirLineRTCFrameSlips
			-- C-NEXT-FUNC cirLine-FrameSlips-next
			-- C-PRE-GET-FUNC PreGet-cirLineRTCFrameSlips
	STATUS		mandatory
	DESCRIPTION	"The number of frame slips which have occurred
			on the receive side of the line.  This
			statistic is valid for TXR lines only.  CIP and
			CDP cards do not support this statistic."
	::=		{ cirLineRTCEntry 5 }

cirLineRTCOutOfFrames	OBJECT-TYPE
	SYNTAX		Counter
	ACCESS		read-only
			-- C-ACCESS-FUNC cirLineRTCOutOfFrames
			-- C-NEXT-FUNC cirLine-OutOfFrames-next
			-- C-PRE-GET-FUNC PreGet-cirLineRTCOutOfFrames
	STATUS		mandatory
	DESCRIPTION	"The number of 0 -> 1 transitions of the out of
			frame conditions as detected by the hardware."
	::=		{ cirLineRTCEntry 6 }

cirLineRTCLossesOfSignal
			OBJECT-TYPE
	SYNTAX		Counter
	ACCESS		read-only
			-- C-ACCESS-FUNC cirLineRTCLossesOfSignal
			-- C-NEXT-FUNC cirLine-LossesOfSignal-next
			-- C-PRE-GET-FUNC PreGet-cirLineRTCLossesOfSignal
	STATUS		mandatory
	DESCRIPTION	"The number of 0 -> 1 transitions of the loss
			of signal condition as detected by the hardware.
			This statistic is valid on CIP and CDP lines
			only.  TXR lines do not support this statistic."
	::=		{ cirLineRTCEntry 7 }

cirLineRTCFrameBitErrors
			OBJECT-TYPE
	SYNTAX		Counter
	ACCESS		read-only
			-- C-ACCESS-FUNC cirLineRTCFrameBitErrors
			-- C-NEXT-FUNC cirLine-FrameBitErrors-next
			-- C-PRE-GET-FUNC PreGet-cirLineRTCFrameBitErrors
	STATUS		mandatory
	DESCRIPTION	"The number of frame alignment signal errors
			which are detected on a line.  This statistic
			is valid only on lines supported by CIP and
			CDP cards.  TXR cards do not support this
			statistic."
	::=		{ cirLineRTCEntry 8 }

cirLineRTCCrcErrors	OBJECT-TYPE
	SYNTAX		Counter
	ACCESS		read-only
			-- C-ACCESS-FUNC cirLineRTCCrcErrors
			-- C-NEXT-FUNC cirLine-CrcErrors-next
			-- C-PRE-GET-FUNC PreGet-cirLineRTCCrcErrors
	STATUS		mandatory
	DESCRIPTION	"The number of CRC errors detected on the line.
			This statistic is valid on lines supported by
			CIP and CDP cards.  TXR cards do no support
			this statistic."
	::=		{ cirLineRTCEntry 9 }

cirLineRTCOutOfMultiFrames
			OBJECT-TYPE
	SYNTAX		Counter
	ACCESS		read-only
			-- C-ACCESS-FUNC cirLineRTCOutOfMultiFrames
			-- C-NEXT-FUNC cirLine-OutOfMultiFrames-next
			-- C-PRE-GET-FUNC PreGet-cirLineRTCOutOfMultiFrames
	STATUS		mandatory
	DESCRIPTION	"The number of 0 -> 1 transitions into out of
			multi-frame as detected by the hardware.  This
			statistic is valid only on E1 lines.  T1 lines
			do not support this statistic."
	::=		{ cirLineRTCEntry 10 }

cirLineRTCAllOnesInTimeslot16
			OBJECT-TYPE
	SYNTAX		Counter
	ACCESS		read-only
			-- C-ACCESS-FUNC cirLineRTCAllOnesInTimeslot16
			-- C-NEXT-FUNC cirLine-AllOnesInTimeslot16-next
			-- C-PRE-GET-FUNC PreGet-cirLineRTCAllOnesInTimeslot16
	STATUS		mandatory
	DESCRIPTION	"The number of 0 -> 1 transitions of AIS-16.
			This statistic is valid only for CIP and CDP E1
			format lines."
	::=		{ cirLineRTCEntry 11 }

--
-- Frame relay Real Time Counters table --
frpRTCTable		OBJECT-TYPE
	SYNTAX		SEQUENCE OF FrpRTCEntry
	ACCESS		not-accessible
	STATUS		mandatory
	DESCRIPTION	"The table of frame relay statistics."
	::=		{ realTimeCountersGroup 3 }

frpRTCEntry		OBJECT-TYPE
	SYNTAX		FrpRTCEntry
	ACCESS		not-accessible
	STATUS		mandatory
	DESCRIPTION	"An entry in the frame relay statistics table.
			Each row may be sparse."
	INDEX		{ frpRTCSlot, frpRTCLine, frpRTCPort }
			-- C-NEXT-FUNC	frp-next
	::=		{ frpRTCTable 1 }

FrpRTCEntry	 ::=	SEQUENCE {
	--
	-- All of the Counters in this table can be very time-expensive
	-- to retrieve, taking as much as 10 seconds each.
	-- Manger timeout values should be adjusted accordingly, and
	-- Get-Next walks through this portion of the table should be
	-- avoided.
	--
	frpRTCSlot				INTEGER,
	frpRTCPort				INTEGER,
	frpRTCFramesRcvd			Counter,
	frpRTCFramesXmitted			Counter,
	frpRTCBytesRcvd				Counter,
	frpRTCBytesXmitted			Counter,
	frpRTCFramesXmittedWithFECN		Counter,
	frpRTCFramesXmittedWithBECN		Counter,
	frpRTCFramesRcvdCrcErrors		Counter,
	frpRTCFramesRcvdInvalidFormat		Counter,
	frpRTCFramesRcvdAlignmentErrors		Counter,
	frpRTCFramesRcvdIllegalLen		Counter,
	frpRTCDmaOverruns			Counter,
	frpRTCLmiStatusEnquires			Counter,
	frpRTCLmiStatusXmitRate			Counter,
	frpRTCLmiStatusUpdateRate		Counter,
	frpRTCLmiInvalidStatusEnquires		Counter,
	frpRTCLmiLinkTimeoutErrors		Counter,
	frpRTCLmiKeepaliveSequenceErrors	Counter,
	frpRTCFramesRcvdUndefDlciErrors		Counter,
	frpRTCXmitStatusEnquirey		Counter,
	frpRTCRxStatusCounter			Counter,
	frpRTCAsyncStatusCounter		Counter,
	frpRTCBadSequenceNumberCount		Counter,
	frpRTCTxProtocolTimeOutCount		Counter,
	frpRTCCLLMFramesTx			Counter,
	frpRTCCLLMBytesTx			Counter,
	frpRTCCLLMFramesRx			Counter,
	frpRTCCLLMBytesRx			Counter,
	frpRTCCLLMFailures			Counter,
	frpRTCRxDEFramesDiscarded		Counter,
	frpRTCLine				INTEGER
}

frpRTCSlot		OBJECT-TYPE
	SYNTAX		INTEGER
	ACCESS		read-only
			-- C-STRUCT frp-cfg, FIELD frpLocalSlot
			-- C-LOCATOR-FUNC frp-locator
	STATUS		mandatory
	DESCRIPTION	"Local Slot Number."
	::=		{ frpRTCEntry 1 }

frpRTCPort		OBJECT-TYPE
	SYNTAX		INTEGER
	ACCESS		read-only
			-- C-STRUCT frp-cfg, FIELD frpLocalPort
			-- C-LOCATOR-FUNC frp-locator
	STATUS		mandatory
	DESCRIPTION	"Local Port Number.  These are numbered
			 starting at 1."
	::=		{ frpRTCEntry 2 }

frpRTCFramesRcvd	OBJECT-TYPE
	SYNTAX		Counter
	ACCESS		read-only
			-- C-ACCESS-FUNC frpRTCFramesRcvd
			-- C-NEXT-FUNC frp-FramesRcvd-next
			-- C-PRE-GET-FUNC PreGet-frpRTCFramesRcvd
	STATUS		mandatory	DESCRIPTION	"The number of frames received by the FRP port."
	::=		{ frpRTCEntry 4 }

frpRTCFramesXmitted	OBJECT-TYPE
	SYNTAX		Counter
	ACCESS		read-only
			-- C-ACCESS-FUNC frpRTCFramesXmitted
			-- C-NEXT-FUNC frp-FramesXmitted-next
			-- C-PRE-GET-FUNC PreGet-frpRTCFramesXmitted
	STATUS		mandatory
	DESCRIPTION	"The number of frames transmitted out the FRP
			port."
	::=		{ frpRTCEntry 5 }

frpRTCBytesRcvd	OBJECT-TYPE
	SYNTAX		Counter
	ACCESS		read-only
			-- C-ACCESS-FUNC frpRTCBytesRcvd
			-- C-NEXT-FUNC frp-BytesRcvd-next
			-- C-PRE-GET-FUNC PreGet-frpRTCBytesRcvd
	STATUS		mandatory
	DESCRIPTION	"The number of frame bytes received from the FRP
			port."
	::=		{ frpRTCEntry 6 }

frpRTCBytesXmitted	OBJECT-TYPE
	SYNTAX		Counter
	ACCESS		read-only
			-- C-ACCESS-FUNC frpRTCBytesXmitted
			-- C-NEXT-FUNC frp-BytesXmitted-next
			-- C-PRE-GET-FUNC PreGet-frpRTCBytesXmitted
	STATUS		mandatory
	DESCRIPTION	"The number of frame bytes transmitted out the
			FRP port."
	::=		{ frpRTCEntry 7 }

frpRTCFramesXmittedWithFECN
			OBJECT-TYPE
	SYNTAX		Counter
	ACCESS		read-only
			-- C-ACCESS-FUNC frpRTCFramesXmittedWithFECN
			-- C-NEXT-FUNC frp-FramesXmittedWithFECN-next
			-- C-PRE-GET-FUNC PreGet-frpRTCFramesXmittedWithFECN
	STATUS		mandatory
	DESCRIPTION	"The number of frames transmitted out the FRP
			port with the FECN bit set."
	::=		{ frpRTCEntry 8 }

frpRTCFramesXmittedWithBECN
			OBJECT-TYPE
	SYNTAX		Counter
	ACCESS		read-only
			-- C-ACCESS-FUNC frpRTCFramesXmittedWithBECN
			-- C-NEXT-FUNC frp-FramesXmittedWithBECN-next
			-- C-PRE-GET-FUNC PreGet-frpRTCFramesXmittedWithBECN
	STATUS		mandatory
	DESCRIPTION	"The number of frames transmitted out the FRP
			port with the BECN bit set."
	::=		{ frpRTCEntry 9 }

frpRTCFramesRcvdCrcErrors
			OBJECT-TYPE
	SYNTAX		Counter
	ACCESS		read-only
			-- C-ACCESS-FUNC frpRTCFramesRcvdCrcErrors
			-- C-NEXT-FUNC frp-FramesRcvdCrcErrors-next
			-- C-PRE-GET-FUNC PreGet-frpRTCFramesRcvdCrcErrors
	STATUS		mandatory
	DESCRIPTION	"The number of CRC errors on received frames
			for the FRP port."
	::=		{ frpRTCEntry 10 }

frpRTCFramesRcvdInvalidFormat
			OBJECT-TYPE
	SYNTAX		Counter
	ACCESS		read-only
			-- C-ACCESS-FUNC frpRTCFramesRcvdInvalidFormat
			-- C-NEXT-FUNC frp-FramesRcvdInvalidFormat-next
			-- C-PRE-GET-FUNC PreGet-frpRTCFramesRcvdInvalidFormat
	STATUS		mandatory
	DESCRIPTION	"The number of frames received by the FRP port
			which contain incorrect EA bit settings (1 in
			the first byte and/or 0 in the second byte)."
	::=		{ frpRTCEntry 11 }

frpRTCFramesRcvdAlignmentErrors
			OBJECT-TYPE
	SYNTAX		Counter
	ACCESS		read-only
			-- C-ACCESS-FUNC frpRTCFramesRcvdAlignmentErrors
			-- C-NEXT-FUNC frp-FramesRcvdAlignmentErrors-next
			-- C-PRE-GET-FUNC PreGet-frpRTCFramesRcvdAlignmentErrors
	STATUS		mandatory
	DESCRIPTION	"The number of bit alignment errors on received
			frames for the FRP port."
	::=		{ frpRTCEntry 12 }

frpRTCFramesRcvdIllegalLen
			OBJECT-TYPE
	SYNTAX		Counter
	ACCESS		read-only
			-- C-ACCESS-FUNC frpRTCFramesRcvdIllegalLen
			-- C-NEXT-FUNC frp-FramesRcvdIllegalLen-next
			-- C-PRE-GET-FUNC PreGet-frpRTCFramesRcvdIllegalLen
	STATUS		mandatory
	DESCRIPTION	"The number of frames received by the FRP port
			which exceed the maximum allowed frame length."
	::=		{ frpRTCEntry 13 }

frpRTCDmaOverruns	OBJECT-TYPE
	SYNTAX		Counter
	ACCESS		read-only
			-- C-ACCESS-FUNC frpRTCDmaOverruns
			-- C-NEXT-FUNC frp-DmaOverruns-next
			-- C-PRE-GET-FUNC PreGet-frpRTCDmaOverruns
	STATUS		mandatory
	DESCRIPTION	"The number of DMA overruns on the FRP port."
	::=		{ frpRTCEntry 14 }

frpRTCLmiStatusEnquires
			OBJECT-TYPE
	SYNTAX		Counter
	ACCESS		read-only
			-- C-ACCESS-FUNC frpRTCLmiStatusEnquires
			-- C-NEXT-FUNC frp-LmiStatusEnquires-next
			-- C-PRE-GET-FUNC PreGet-frpRTCLmiStatusEnquires
	STATUS		mandatory
	DESCRIPTION	"The number of LMI status enquires received
			from the user device by the FRP port."
	::=		{ frpRTCEntry 15 }

frpRTCLmiStatusXmitRate
			OBJECT-TYPE
	SYNTAX		Counter
	ACCESS		read-only
			-- C-ACCESS-FUNC frpRTCLmiStatusXmitRate
			-- C-NEXT-FUNC frp-LmiStatusXmitRate-next
			-- C-PRE-GET-FUNC PreGet-frpRTCLmiStatusXmitRate
	STATUS		mandatory
	DESCRIPTION	"The number of LMI status messages transmitted
			to the user device from the FRP port per ??."
	::=		{ frpRTCEntry 16 }

frpRTCLmiStatusUpdateRate
			OBJECT-TYPE
	SYNTAX		Counter
	ACCESS		read-only
			-- C-ACCESS-FUNC frpRTCLmiStatusUpdateRate
			-- C-NEXT-FUNC frp-LmiStatusUpdateRate-next
			-- C-PRE-GET-FUNC PreGet-frpRTCLmiStatusUpdateRate
	STATUS		mandatory
	DESCRIPTION	"The number of LMI update messages transmitted
			to the user device from the FRP port per ??."
	::=		{ frpRTCEntry 17 }

frpRTCLmiInvalidStatusEnquires
			OBJECT-TYPE
	SYNTAX		Counter
	ACCESS		read-only
			-- C-ACCESS-FUNC frpRTCLmiInvalidStatusEnquires
			-- C-NEXT-FUNC frp-LmiInvalidStatusEnquires-next
			-- C-PRE-GET-FUNC PreGet-frpRTCLmiInvalidStatusEnquires
	STATUS		mandatory
	DESCRIPTION	"The number of invalid LMI status enquires
			received from the user device by the FRP port."
	::=		{ frpRTCEntry 18 }

frpRTCLmiLinkTimeoutErrors
			OBJECT-TYPE
	SYNTAX		Counter
	ACCESS		read-only
			-- C-ACCESS-FUNC frpRTCLmiLinkTimeoutErrors
			-- C-NEXT-FUNC frp-LmiLinkTimeoutErrors-next
			-- C-PRE-GET-FUNC PreGet-frpRTCLmiLinkTimeoutErrors
	STATUS		mandatory
	DESCRIPTION	"The number of LMI link timeout errors."
	::=		{ frpRTCEntry 19 }

frpRTCLmiKeepaliveSequenceErrors
			OBJECT-TYPE
	SYNTAX		Counter
	ACCESS		read-only
			-- C-ACCESS-FUNC frpRTCLmiKeepaliveSequenceErrors
			-- C-NEXT-FUNC frp-LmiKeepaliveSequenceErrors-next
			-- C-PRE-GET-FUNC PreGet-frpRTCLmiKeepaliveSequenceErrors
	STATUS		mandatory
	DESCRIPTION	"The number of LMI keepalive sequence number
			errors."
	::=		{ frpRTCEntry 20 }

frpRTCFramesRcvdUndefDlciErrors
			OBJECT-TYPE
	SYNTAX		Counter
	ACCESS		read-only
			-- C-ACCESS-FUNC frpRTCFramesRcvdUndefDlciErrors
			-- C-NEXT-FUNC frp-FramesRcvdUndefDlciErrors-next
			-- C-PRE-GET-FUNC PreGet-frpRTCFramesRcvdUndefDlciErrors
	STATUS		mandatory
	DESCRIPTION	"The number of frames received by the FRP port
			which contain undefined DLCIs."
	::=		{ frpRTCEntry 21 }

frpRTCXmitStatusEnquirey
			OBJECT-TYPE
	SYNTAX		Counter
	ACCESS		read-only
			-- C-ACCESS-FUNC frpRTCXmitStatusEnquirey
			-- C-NEXT-FUNC frp-XmitStatusEnquirey-next
			-- C-PRE-GET-FUNC PreGet-frpRTCXmitStatusEnquirey
	STATUS		mandatory
	DESCRIPTION	"Transmit Status Enquirey."
	::=		{ frpRTCEntry 22 }

frpRTCRxStatusCounter	OBJECT-TYPE
	SYNTAX		Counter
	ACCESS		read-only
			-- C-ACCESS-FUNC frpRTCRxStatusCounter
			-- C-NEXT-FUNC frp-RxStatusCounter-next
			-- C-PRE-GET-FUNC PreGet-frpRTCRxStatusCounter
	STATUS		mandatory
	DESCRIPTION	"Received Status counter."
	::=		{ frpRTCEntry 23 }

 frpRTCAsyncStatusCounter
			OBJECT-TYPE
	SYNTAX		Counter
	ACCESS		read-only
			-- C-ACCESS-FUNC frpRTCAsyncStatusCounter
			-- C-NEXT-FUNC frp-AsyncStatusCounter-next
			-- C-PRE-GET-FUNC PreGet-frpRTCAsyncStatusCounter
	STATUS		mandatory
	DESCRIPTION	"Asynchronous Status Counter."
	::=		{ frpRTCEntry 24 }

 frpRTCBadSequenceNumberCount
			OBJECT-TYPE
	SYNTAX		Counter
	ACCESS		read-only
			-- C-ACCESS-FUNC frpRTCBadSequenceNumberCount
			-- C-NEXT-FUNC frp-BadSequenceNumberCount-next
			-- C-PRE-GET-FUNC PreGet-frpRTCBadSequenceNumberCount
	STATUS		mandatory
	DESCRIPTION	"Invalid Sequence number count."
	::=		{ frpRTCEntry 25 }

 frpRTCTxProtocolTimeOutCount
			OBJECT-TYPE
	SYNTAX		Counter
	ACCESS		read-only
			-- C-ACCESS-FUNC frpRTCTxProtocolTimeOutCount
			-- C-NEXT-FUNC frp-TxProtocolTimeOutCount-next
			-- C-PRE-GET-FUNC PreGet-frpRTCTxProtocolTimeOutCount
	STATUS		mandatory
	DESCRIPTION	"Transmit Protocol timeout count."
	::=		{ frpRTCEntry 26 }

 frpRTCCLLMFramesTx	OBJECT-TYPE
	SYNTAX		Counter
	ACCESS		read-only
			-- C-ACCESS-FUNC frpRTCCLLMFramesTx
			-- C-NEXT-FUNC frp-CLLMFramesTx-next
			-- C-PRE-GET-FUNC PreGet-frpRTCCLLMFramesTx
	STATUS		mandatory
	DESCRIPTION	"CLLM message frames transmited."
	::=		{ frpRTCEntry 27 }

 frpRTCCLLMBytesTx	OBJECT-TYPE
	SYNTAX		Counter
	ACCESS		read-only
			-- C-ACCESS-FUNC frpRTCCLLMBytesTx
			-- C-NEXT-FUNC frp-CLLMBytesTx-next
			-- C-PRE-GET-FUNC PreGet-frpRTCCLLMBytesTx
	STATUS		mandatory
	DESCRIPTION	"CLLM message bytes transmitted."
	::=		{ frpRTCEntry 28 }

 frpRTCCLLMFramesRx	OBJECT-TYPE
	SYNTAX		Counter
	ACCESS		read-only
			-- C-ACCESS-FUNC frpRTCCLLMFramesRx
			-- C-NEXT-FUNC frp-CLLMFramesRx-next
			-- C-PRE-GET-FUNC PreGet-frpRTCCLLMFramesRx
	STATUS		mandatory
	DESCRIPTION	"CLLM Frames received."
	::=		{ frpRTCEntry 29 }

 frpRTCCLLMBytesRx	OBJECT-TYPE
	SYNTAX		Counter
	ACCESS		read-only
			-- C-ACCESS-FUNC frpRTCCLLMBytesRx
			-- C-NEXT-FUNC frp-CLLMBytesRx-next
			-- C-PRE-GET-FUNC PreGet-frpRTCCLLMBytesRx
	STATUS		mandatory
	DESCRIPTION	"CLLM bytes received."
	::=		{ frpRTCEntry 30 }

 frpRTCCLLMFailures	OBJECT-TYPE
	SYNTAX		Counter
	ACCESS		read-only
			-- C-ACCESS-FUNC frpRTCCLLMFailures
			-- C-NEXT-FUNC frp-CLLMFailures-next
			-- C-PRE-GET-FUNC PreGet-frpRTCCLLMFailures
	STATUS		mandatory
	DESCRIPTION	"CLLM failures."
	::=		{ frpRTCEntry 31 }

frpRTCRxDEFramesDiscarded
			OBJECT-TYPE
	SYNTAX		Counter
	ACCESS		read-only
			-- C-ACCESS-FUNC frpRTCRxDEFramesDiscarded
			-- C-NEXT-FUNC frp-RxDEFramesDiscarded-next
			-- C-PRE-GET-FUNC PreGet-frpRTCRxDEFramesDiscarded
	STATUS		mandatory
	DESCRIPTION	"The number of frames with the DE bit set which have
			been dropped by the frame relay port.  IPX software
			versions earlier than IPX 6.1 will report a count
			of zero."
	::=		{ frpRTCEntry 32}

frpRTCLine		OBJECT-TYPE
	SYNTAX		INTEGER
	ACCESS		read-only
			-- C-STRUCT frp-cfg, FIELD frpLocalLine
			-- C-LOCATOR-FUNC frp-locator
	STATUS		mandatory
	DESCRIPTION	"Local Slot Number."
	::=		{ frpRTCEntry 33 }

--
-- Connection Real Time Counters Table
--

connRTCTable		OBJECT-TYPE
	SYNTAX		SEQUENCE OF ConnRTCEntry
	ACCESS		not-accessible
	STATUS		mandatory
	DESCRIPTION	"The table of Connection statistics."
	::=		{ realTimeCountersGroup 4 }

connRTCEntry		OBJECT-TYPE
	SYNTAX		ConnRTCEntry
	ACCESS		not-accessible
	STATUS		mandatory
	DESCRIPTION	"An entry in the Connection statistics table."
	INDEX		{ connRTCSlot, connRTCLine, connRTCChannel, connRTCDLCI }
			-- C-NEXT-FUNC	conn-next
	::=		{ connRTCTable 1 }


ConnRTCEntry	::=	SEQUENCE {
	--
	-- All of the Counters in this table can be very time-expensive
	-- to retrieve, taking as much as 10 seconds each.
	-- Manger timeout values should be adjusted accordingly, and
	-- Get-Next walks through this portion of the table should be
	-- avoided.
	--
	connRTCSlot			INTEGER,
	connRTCChannel			INTEGER,
	connRTCDLCI			INTEGER,
	connRTCRcvdFrames		Counter,
	connRTCRcvdFramesDiscarded	Counter,
	connRTCXmitFrames		Counter,
	connRTCXmitFramesDiscarded	Counter,
	connRTCRcvdPkts			Counter,
	connRTCRcvdPktsDiscarded	Counter,
	connRTCXmitPkts			Counter,
	connRTCXmitPktsProjected	Counter,
	connRTCXmitPktsSupervisory	Counter,
	connRTCRcvdBytes		Counter,
	connRTCRcvdBytesDiscarded	Counter,
	connRTCXmitBytes		Counter,
	connRTCXmitBytesDiscarded	Counter,
	connRTCSecondsV25ModemOn	Counter,
	connRTCSecondsDsiEnabled	Counter,
	connRTCSecondsOffHook		Counter,
	connRTCSecondsInService		Counter,
	connRTCXmitFramesWithFECN	Counter,
	connRTCXmitFramesWithBECN	Counter,
	connRTCRxSupervisoryPkts	Counter,
	connRTCCongestedMinuites	Counter,
	connRTCFramesRxWithDE		Counter,
	connRTCFramesTxWithDE		Counter,
	connRTCFramesDiscardedWithDE	Counter,
	connRTCBytesRxWithDE		Counter,
	connRTCFramesRxExcessCir	Counter,
	connRTCBytesRxExcessCir		Counter,
	connRTCFramesTxExcessCir	Counter,
	connRTCBytesTxExcessCir		Counter,
	connRTCLine			INTEGER
}

connRTCSlot		OBJECT-TYPE
	SYNTAX		INTEGER
	ACCESS		read-only
			-- C-STRUCT connection-cfg, FIELD connLocalSlot
			-- C-LOCATOR-FUNC conn-locator
	STATUS		mandatory
	DESCRIPTION	"Local Slot Number."
	::=		{ connRTCEntry 1 }

connRTCChannel	OBJECT-TYPE
	SYNTAX		INTEGER
	ACCESS		read-only
			-- C-STRUCT connection-cfg, FIELD connLocalChannel
			-- C-LOCATOR-FUNC conn-locator
	STATUS		mandatory
	DESCRIPTION	"Local Channel Number.  These are numbered
			 starting at 1."
	::=		{ connRTCEntry 2 }

connRTCDLCI		OBJECT-TYPE
	SYNTAX		INTEGER
	ACCESS		read-only
			-- C-STRUCT connection-cfg, FIELD connLocalDLCI
			-- C-LOCATOR-FUNC conn-locator
	STATUS		mandatory
	DESCRIPTION	"Local DLCI Number."
	::=		{ connRTCEntry 3 }

connRTCRcvdFrames	OBJECT-TYPE
	SYNTAX		Counter
	ACCESS		read-only
			-- C-ACCESS-FUNC connRTCRcvdFrames
			-- C-NEXT-FUNC conn-RcvdFrames-next
			-- C-PRE-GET-FUNC PreGet-connRTCRcvdFrames
	STATUS		mandatory
	DESCRIPTION	"The number of frames received from the FRP port
			associated with the connection.  This statistic
			is valid for Frame Relay Connections only."
	::=		{ connRTCEntry 4 }

connRTCRcvdFramesDiscarded
			OBJECT-TYPE
	SYNTAX		Counter
	ACCESS		read-only
			-- C-ACCESS-FUNC connRTCRcvdFramesDiscarded
			-- C-NEXT-FUNC conn-RcvdFramesDiscarded-next
			-- C-PRE-GET-FUNC PreGet-connRTCRcvdFramesDiscarded
	STATUS		mandatory
	DESCRIPTION	"The number of frames received from the FRP
			port which are associated with the connection,
			but were discarded before being transmitted
			onto the Muxbus due to the age of the frame
			in the IPX system or the lack of buffer space.
			This statistic is valid for Frame Relay
			Connections only."
	::=		{ connRTCEntry 5 }

connRTCXmitFrames	OBJECT-TYPE
	SYNTAX		Counter
	ACCESS		read-only
			-- C-ACCESS-FUNC connRTCXmitFrames
			-- C-NEXT-FUNC conn-XmitFrames-next
			-- C-PRE-GET-FUNC PreGet-connRTCXmitFrames
	STATUS		mandatory
	DESCRIPTION	"The number of frames transmitted out the FRP
			port which were received from the other
			endpoint of the connection.  This statistic is
			valid for Frame Relay connections only."
	::=		{ connRTCEntry 6 }

connRTCXmitFramesDiscarded
			OBJECT-TYPE
	SYNTAX		Counter
	ACCESS		read-only
			-- C-ACCESS-FUNC connRTCXmitFramesDiscarded
			-- C-NEXT-FUNC conn-XmitFramesDiscarded-next
			-- C-PRE-GET-FUNC PreGet-connRTCXmitFramesDiscarded
	STATUS		mandatory
	DESCRIPTION	"The number of frames to be transmitted out the
			FRP port which were received from the other
			endpoint of the connection, but were discarded
			due to the age of the frame in the IPX system,
			a CRC error, or lack of buffer space.  This
			statistic is valid for Frame Relay Connections
			only."
	::=		{ connRTCEntry 7 }

connRTCRcvdPkts	OBJECT-TYPE
	SYNTAX		Counter
	ACCESS		read-only
			-- C-ACCESS-FUNC connRTCRcvdPkts
			-- C-NEXT-FUNC conn-RcvdPkts-next
			-- C-PRE-GET-FUNC PreGet-connRTCRcvdPkts
	STATUS		mandatory
	DESCRIPTION	"The number of packets received from the Muxbus
			by the FRP port associated with the connection
			endpoint.  This statistic is valid for Frame
			Relay Connections only."
	::=		{ connRTCEntry 8 }

connRTCRcvdPktsDiscarded
			OBJECT-TYPE
	SYNTAX		Counter
	ACCESS		read-only
			-- C-ACCESS-FUNC connRTCRcvdPktsDiscarded
			-- C-NEXT-FUNC conn-RcvdPktsDiscarded-next
			-- C-PRE-GET-FUNC PreGet-connRTCRcvdPktsDiscarded
	STATUS		mandatory
	DESCRIPTION	"The number of packets received from the Muxbus
			at the FRP port associated with the connection
			endpoint, but were discarded before being
			ssembled into frames and transmitted on the
			FRP port.  This statistic is valid for Frame
			Relay Connections only."
	::=		{ connRTCEntry 9 }

connRTCXmitPkts	OBJECT-TYPE
	SYNTAX		Counter
	ACCESS		read-only
			-- C-ACCESS-FUNC connRTCXmitPkts
			-- C-NEXT-FUNC conn-XmitPkts-next
			-- C-PRE-GET-FUNC PreGet-connRTCXmitPkts
	STATUS		mandatory
	DESCRIPTION	"The number of packets transmitted from one
			connection endpoint onto the Muxbus towards
			the other connection endpoint.  This statistic
			is valid for all types of inter-node
			connections, and for CDP Data, FRP, LDP and
			SDP terminated DAX connections."
	::=		{ connRTCEntry 10 }

connRTCXmitPktsProjected
			OBJECT-TYPE
	SYNTAX		Counter
	ACCESS		read-only
			-- C-ACCESS-FUNC connRTCXmitPktsProjected
			-- C-NEXT-FUNC conn-XmitPktsProjected-next
			-- C-PRE-GET-FUNC PreGet-connRTCXmitPktsProjected
	STATUS		mandatory
	DESCRIPTION	"The estimated number of packets which would
			be used if DSI or DFM were enabled for the
			connection.  This statistic is valid for
			inter-node voice connections and with all
			types of data connections.  It is not
			valid for DAX voice connections or Frame
			Relay connections."
	::=		{ connRTCEntry 11 }

connRTCXmitPktsSupervisory
			OBJECT-TYPE
	SYNTAX		Counter
	ACCESS		read-only
			-- C-ACCESS-FUNC connRTCXmitPktsSupervisory
			-- C-NEXT-FUNC conn-XmitPktsSupervisory-next
			-- C-PRE-GET-FUNC PreGet-connRTCXmitPktsSupervisory
	STATUS		mandatory
	DESCRIPTION	"The number of supervisory packets transmitted
			from one connection endpoint to another.
			Supervisory packets reflect signaling bit
			transitions for voice connections, and EIA lead
			transitions for data channels.  This statistic
			is valid on all inter-node 'a', 'c', and 'v'
			voice connections, all inter-node data
			connections, all 'd' type voice connection
			endpoints which are supported by CIP or CDP
			cards, and all DAX data connections.  This
			statistic is not valid for Frame Relay
			connections."
	::=		{ connRTCEntry 12 }

connRTCRcvdBytes	OBJECT-TYPE
	SYNTAX		Counter
	ACCESS		read-only
			-- C-ACCESS-FUNC connRTCRcvdBytes
			-- C-NEXT-FUNC conn-RcvdBytes-next
			-- C-PRE-GET-FUNC PreGet-connRTCRcvdBytes
	STATUS		mandatory
	DESCRIPTION	"The number of frame bytes received from the FRP
			port associated with the connection endpoint.
			This statistic is valid for Frame Relay
			connections only."
	::=		{ connRTCEntry 13 }

connRTCRcvdBytesDiscarded
			OBJECT-TYPE
	SYNTAX		Counter
	ACCESS		read-only
			-- C-ACCESS-FUNC connRTCRcvdBytesDiscarded
			-- C-NEXT-FUNC conn-RcvdBytesDiscarded-next
			-- C-PRE-GET-FUNC PreGet-connRTCRcvdBytesDiscarded
	STATUS		mandatory
	DESCRIPTION	"The number of frame bytes received from the
			FRP port associated with the connection
			endpoint, but were discarded due to the age of
			the frame in the IPX system or the lack of
			buffer space before being transmitted onto the
			Muxbus.  This statistic is valid for Frame
			Relay connections only."
	::=		{ connRTCEntry 14 }

connRTCXmitBytes	OBJECT-TYPE
	SYNTAX		Counter
	ACCESS		read-only
			-- C-ACCESS-FUNC connRTCXmitBytes
			-- C-NEXT-FUNC conn-XmitBytes-next
			-- C-PRE-GET-FUNC PreGet-connRTCXmitBytes
	STATUS		mandatory
	DESCRIPTION	"The number of frame bytes to be received from
			the Muxbus from the remote end of the
			connection, which were actually transmitted
			out the FRP port as frames.  This statistic is
			valid for Frame Relay connections only."
	::=		{ connRTCEntry 15 }

connRTCXmitBytesDiscarded
			OBJECT-TYPE
	SYNTAX		Counter
	ACCESS		read-only
			-- C-ACCESS-FUNC connRTCXmitBytesDiscarded
			-- C-NEXT-FUNC conn-XmitBytesDiscarded-next
			-- C-PRE-GET-FUNC PreGet-connRTCXmitBytesDiscarded
	STATUS		mandatory
	DESCRIPTION	"The number of frame bytes to be received from
			the Muxbus from the remote end of the
			connection, but were discarded due to the age
			of the frame in the IPX system, a CRC error, or
			lack of buffer space.  This statistic is valid
			for Frame Relay connections only."
	::=		{ connRTCEntry 16 }

connRTCSecondsV25ModemOn
			OBJECT-TYPE
	SYNTAX		Counter
	ACCESS		read-only
			-- C-ACCESS-FUNC connRTCSecondsV25ModemOn
			-- C-NEXT-FUNC conn-SecondsV25ModemOn-next
			-- C-PRE-GET-FUNC PreGet-connRTCSecondsV25ModemOn
	STATUS		mandatory
	DESCRIPTION	"The number of seconds the V.25 modem has been
			detected and a connection upgraded from ADPCM
			to PCM.  The status of the V.25 modem detect is
			checked every 3 seconds, so the granularity of
			the data which makes up this statistic is 3
			seconds.  This statistic is valid for inter-
			node type 'a', 'c' and 'v' voice connections
			only."
	::=		{ connRTCEntry 17 }

connRTCSecondsDsiEnabled
			OBJECT-TYPE
	SYNTAX		Counter
	ACCESS		read-only
			-- C-ACCESS-FUNC connRTCSecondsDsiEnabled
			-- C-NEXT-FUNC conn-SecondsDsiEnabled-next
			-- C-PRE-GET-FUNC PreGet-connRTCSecondsDsiEnabled
	STATUS		mandatory
	DESCRIPTION	"The number of seconds that a connection has
			been performing Digital Speech Interpolation
			(DSI).  The status of DSI is checked every 3
			seconds, so the granularity of the data which
			makes up this statistic is 3 seconds.  This
			statistic is valid for inter-node type 'c' and
			'v' voice connections only."
	::=		{ connRTCEntry 18 }

connRTCSecondsOffHook	OBJECT-TYPE
	SYNTAX		Counter
	ACCESS		read-only
			-- C-ACCESS-FUNC connRTCSecondsOffHook
			-- C-NEXT-FUNC conn-SecondsOffHook-next
			-- C-PRE-GET-FUNC PreGet-connRTCSecondsOffHook
	STATUS		mandatory
	DESCRIPTION	"The number of seconds that a voice connection
			has been off-hook.  The on-hook state is
			determined by the signaling bits, as defined by
			the 'cnfchtp' command.  A connection which is
			not on-hook is treated as off-hook for this
			statistic.  The status of the off-hook
			condition is checked every 3 seconds,
			so the granularity of the data which makes up
			this statistic is 3 seconds.  This statistic is
			valid for all 'a', 'c' and 'v' voice
			connections, and for 'd' type voice connection
			endpoints supported by CIP or CDP cards."
	::=		{ connRTCEntry 19 }

connRTCSecondsInService
			OBJECT-TYPE
	SYNTAX		Counter
	ACCESS		read-only
			-- C-ACCESS-FUNC connRTCSecondsInService
			-- C-NEXT-FUNC conn-SecondsInService-next
			-- C-PRE-GET-FUNC PreGet-connRTCSecondsInService
	STATUS		mandatory
	DESCRIPTION	"The number of seconds that a connection has
			been in service.  A conection is considered to
			be in service if its end points are not in
			alarm, that cards required to support the
			connection are present, and the connection is
			routed."
	::=		{ connRTCEntry 20 }

connRTCXmitFramesWithFECN
			OBJECT-TYPE
	SYNTAX		Counter
	ACCESS		read-only
			-- C-ACCESS-FUNC connRTCXmitFramesWithFECN
			-- C-NEXT-FUNC conn-XmitFramesWithFECN-next
			-- C-PRE-GET-FUNC PreGet-connRTCXmitFramesWithFECN
	STATUS		mandatory
	DESCRIPTION	"The number of frames transmitted out the FRP
			port with the FECN bit set.  This statistic is
			valid for Frame Relay connections only."
	::=		{ connRTCEntry 21 }

connRTCXmitFramesWithBECN
			OBJECT-TYPE
	SYNTAX		Counter
	ACCESS		read-only
			-- C-ACCESS-FUNC connRTCXmitFramesWithBECN
			-- C-NEXT-FUNC conn-XmitFramesWithBECN-next
			-- C-PRE-GET-FUNC PreGet-connRTCXmitFramesWithBECN
	STATUS		mandatory
	DESCRIPTION	"The number of frames transmitted out the FRP
			port with the BECN bit set.  This statistic
			is valid for Frame Relay connections only."
	::=		{ connRTCEntry 22 }

connRTCRxSupervisoryPkts
			OBJECT-TYPE
	SYNTAX		Counter
	ACCESS		read-only
			-- C-ACCESS-FUNC connRTCRxSupervisoryPkts
			-- C-NEXT-FUNC conn-RxSupervisoryPkts-next
			-- C-PRE-GET-FUNC PreGet-connRTCRxSupervisoryPkts
	STATUS		mandatory
	DESCRIPTION	"The number of of supervisory packets received."
	::=		{ connRTCEntry 23 }

connRTCCongestedMinuites
			OBJECT-TYPE
	SYNTAX		Counter
	ACCESS		read-only
			-- C-ACCESS-FUNC connRTCCongestedMinuites
			-- C-NEXT-FUNC conn-CongestedMinuites-next
			-- C-PRE-GET-FUNC PreGet-connRTCCongestedMinuites
	STATUS		mandatory
	DESCRIPTION	"The number of minuites in which 50%or more frames
			are tagged FECN by the FRP."
	::=		{ connRTCEntry 24 }

connRTCFramesRxWithDE
			OBJECT-TYPE
	SYNTAX		Counter
	ACCESS		read-only
			-- C-ACCESS-FUNC connRTCFramesRxWithDE
			-- C-NEXT-FUNC conn-FramesRxWithDE-next
			-- C-PRE-GET-FUNC PreGet-connRTCFramesRxWithDE
	STATUS		mandatory
	DESCRIPTION	"The number of frames received from the FRP 
			with the DE bit set."
	::=		{ connRTCEntry 25 }

connRTCFramesTxWithDE
			OBJECT-TYPE
	SYNTAX		Counter
	ACCESS		read-only
			-- C-ACCESS-FUNC connRTCFramesTxWithDE
			-- C-NEXT-FUNC conn-FramesTxWithDE-next
			-- C-PRE-GET-FUNC PreGet-connRTCFramesTxWithDE
	STATUS		mandatory
	DESCRIPTION	"The number of frames transmitted from the FRP 
			with the DE bit set. "
	::=		{ connRTCEntry 26 }

connRTCFramesDiscardedWithDE
			OBJECT-TYPE
	SYNTAX		Counter
	ACCESS		read-only
			-- C-ACCESS-FUNC connRTCFramesDiscardedWithDE
			-- C-NEXT-FUNC conn-FramesDiscardedWithDE-next
			-- C-PRE-GET-FUNC PreGet-connRTCFramesDiscardedWithDE
	STATUS		mandatory
	DESCRIPTION	"The number of frames received from the local
			frame relay port with their DE bit set which are
			discarded before being transmitted onto the Muxbus." 
	::=		{ connRTCEntry 27 }

connRTCBytesRxWithDE
			OBJECT-TYPE
	SYNTAX		Counter
	ACCESS		read-only
			-- C-ACCESS-FUNC connRTCBytesRxWithDE
			-- C-NEXT-FUNC conn-BytesRxWithDE-next
			-- C-PRE-GET-FUNC PreGet-connRTCBytesRxWithDE
	STATUS		mandatory
	DESCRIPTION	"The number of bytes received from the FRP 
			for frames with the DE bit set."
	::=		{ connRTCEntry 28 }

connRTCFramesRxExcessCir
			OBJECT-TYPE
	SYNTAX		Counter
	ACCESS		read-only
			-- C-ACCESS-FUNC connRTCFramesRxExcessCir
			-- C-NEXT-FUNC conn-FramesRxExcessCir-next
			-- C-PRE-GET-FUNC PreGet-connRTCFramesRxExcessCir
	STATUS		mandatory
	DESCRIPTION	"The number of frames received in excess of CIR."
	::=		{ connRTCEntry 29 }

connRTCBytesRxExcessCir
			OBJECT-TYPE
	SYNTAX		Counter
	ACCESS		read-only
			-- C-ACCESS-FUNC connRTCBytesRxExcessCir
			-- C-NEXT-FUNC conn-BytesRxExcessCir-next
			-- C-PRE-GET-FUNC PreGet-connRTCBytesRxExcessCir
	STATUS		mandatory
	DESCRIPTION	"The number of frames received in excess of CIR."
	::=		{ connRTCEntry 30 }

connRTCFramesTxExcessCir
			OBJECT-TYPE
	SYNTAX		Counter
	ACCESS		read-only
			-- C-ACCESS-FUNC connRTCFramesTxExcessCir
			-- C-NEXT-FUNC conn-FramesTxExcessCir-next
			-- C-PRE-GET-FUNC PreGet-connRTCFramesTxExcessCir
	STATUS		mandatory
	DESCRIPTION	"The number of frames transmitted in excess of CIR."
	::=		{ connRTCEntry 31 }

connRTCBytesTxExcessCir
			OBJECT-TYPE
	SYNTAX		Counter
	ACCESS		read-only
			-- C-ACCESS-FUNC connRTCBytesTxExcessCir
			-- C-NEXT-FUNC conn-BytesTxExcessCir-next
			-- C-PRE-GET-FUNC PreGet-connRTCBytesTxExcessCir
	STATUS		mandatory
	DESCRIPTION	"The number of frames transmitted in excess of CIR."
	::=		{ connRTCEntry 32 }

connRTCLine		OBJECT-TYPE
	SYNTAX		INTEGER
	ACCESS		read-only
			-- C-STRUCT connection-cfg, FIELD connLocalLine
			-- C-LOCATOR-FUNC conn-locator
	STATUS		mandatory
	DESCRIPTION	"Line Number, for IPX it is always 0."
	::=		{ connRTCEntry 33 }

--
-- Trunk Real Time Counter Table
--	valid only for SV Plus release ????

trunkRTCTable		OBJECT-TYPE
	SYNTAX		SEQUENCE OF TrunkRTCEntry
	ACCESS		not-accessible
	STATUS		mandatory
	DESCRIPTION	"The table of Trunk Line statistics."
	::=		{ realTimeCountersGroup 5 }

trunkRTCEntry		OBJECT-TYPE
	SYNTAX		TrunkRTCEntry
	ACCESS		not-accessible
	STATUS		mandatory
	DESCRIPTION	"An entry in the Trunk Line statistics table.
			Each row may be sparse."
	INDEX		{ trunkRTCLocalSlot, trunkRTCLocalPort }
			-- C-NEXT-FUNC	trunk-next
	::=		{ trunkRTCTable 1 }

TrunkRTCEntry ::=	SEQUENCE {
	--
	-- All of the Counters in this table can be very time-expensive
	-- to retrieve, taking as much as 10 seconds each.
	-- Manger timeout values should be adjusted accordingly, and
	-- Get-Next walks through this portion of the table should be
	-- avoided.
	--
	trunkRTCLocalSlot			INTEGER,
	trunkRTCLocalPort			INTEGER,
	trunkRTCBipolarViolations		Counter,
	trunkRTCFrameSlips			Counter,
	trunkRTCOutOfFrames			Counter,
	trunkRTCLossOfSignal			Counter,
	trunkRTCFrameBitErrors			Counter,
	trunkRTCCrcErrors			Counter,
	trunkRTCPktOutOfFrames			Counter,
	trunkRTCPktCrcErrors			Counter,
	trunkRTCBadClockErrors			Counter,
	trunkRTCVoicePktsDropped		Counter,
	trunkRTCTimeStampedPktsDropped		Counter,
	trunkRTCNonTimeStampedPktsDropped	Counter,
	trunkRTCHighPriorityPktsDropped		Counter,
	trunkRTCBurstyDataPktsDropped		Counter,
	trunkRTCMulticastPktsDropped		Counter,
	trunkRTCVoicePktsXmitted		Counter,
	trunkRTCTimeStampedPktsXmitted		Counter,
	trunkRTCNonTimeStampedPktsXmitted	Counter,
	trunkRTCHighPriorityPktsXmitted		Counter,
	trunkRTCBurstyDataPktsXmitted		Counter,
	trunkRTCMulticastPktsXmitted		Counter,
	trunkRTCPktsXmitted			Counter,
	trunkRTCTxBurstyDataAClpPktsDropped	Counter,
	trunkRTCTxBurstyDataBClpPktsDropped	Counter,
	trunkRTCBurstyDataAEfcnPktsTx2Line	Counter,
	trunkRTCBurstyDataBEfcnPktsTx2Line	Counter,
	trunkRTCBurstyDataAClpPktsTx2Line	Counter,
	trunkRTCBurstyDataBClpPktsTx2Line	Counter,
	trunkRTCAtmCellHeaderHecErrors		Counter,
	trunkRTCTxVoiceCellsDropped		Counter,
	trunkRTCTxTimeStampCellsDropped		Counter,
	trunkRTCTxNonTStampCellsDropped		Counter,
	trunkRTCTxHighPriorityCellsDropped	Counter,
	trunkRTCTxBurstyDataACellsDropped	Counter,
	trunkRTCTxBurstyDataBCellsDropped	Counter,
	trunkRTCVoiceCellsTx2Line		Counter,
	trunkRTCTimeStampCellsTx2Line		Counter,
	trunkRTCNonTimeStampCellsTx2Line	Counter,
	trunkRTCHighPriorityCellsTx2Line	Counter,
	trunkRTCBurstyDataACellsTx2Line		Counter,
	trunkRTCBurstyDataBCellsTx2Line		Counter,
	trunkRTCTotalCellsTx2Line		Counter,
	trunkRTCTxBurstyDataAClpCellsDropped	Counter,
	trunkRTCTxBurstyDataBClpCellsDropped	Counter,
	trunkRTCBurstyDataAEfcnCellsTx2Line	Counter,
	trunkRTCBurstyDataBEfcnCellsTx2Line	Counter,
	trunkRTCPlcpOutOfFrames			Counter
}

trunkRTCLocalSlot	OBJECT-TYPE
	SYNTAX		INTEGER
	ACCESS		read-only
			-- C-STRUCT trunk-cfg, FIELD trunkLocalSlot
			-- C-LOCATOR-FUNC trunk-locator
	STATUS		mandatory
	DESCRIPTION	"Local Slot Number.  These are numbered
			starting at 1"
	::=		{ trunkRTCEntry 1 }

trunkRTCLocalPort	OBJECT-TYPE
	SYNTAX		INTEGER
	ACCESS		read-only
			-- C-STRUCT trunk-cfg, FIELD trunkLocalPort
			-- C-LOCATOR-FUNC trunk-locator
	STATUS		mandatory
	DESCRIPTION	"Local Port Number.  These are numbered
			 starting at 1."
	::=		{ trunkRTCEntry 2 }

trunkRTCBipolarViolations
			OBJECT-TYPE
	SYNTAX		Counter
	ACCESS		read-only
			-- C-ACCESS-FUNC trunkRTCBipolarViolations
			-- C-NEXT-FUNC trunk-BipolarViolations-next
			-- C-PRE-GET-FUNC PreGet-trunkRTCBipolarViolations
	STATUS		mandatory
	DESCRIPTION	"The signal level for a '1' bit should
			alternate between a positive and a negative
			signal.  If two positive or two negative
			signals are received in a row, a bipolar
			violation has occurred."
	::=		{ trunkRTCEntry 4 }

trunkRTCFrameSlips	OBJECT-TYPE
	SYNTAX		Counter
	ACCESS		read-only
			-- C-ACCESS-FUNC trunkRTCFrameSlips
			-- C-NEXT-FUNC trunk-FrameSlips-next
			-- C-PRE-GET-FUNC PreGet-trunkRTCFrameSlips
	STATUS		mandatory
	DESCRIPTION	"The number of frame slips which have occurred on
			the receive side of the line.  This statistic
			is valid for TXR lines only.  NTC cards do not
			support this statistic."
	::=		{ trunkRTCEntry 5 }

trunkRTCOutOfFrames	OBJECT-TYPE
	SYNTAX		Counter
	ACCESS		read-only
			-- C-ACCESS-FUNC trunkRTCOutOfFrames
			-- C-NEXT-FUNC trunk-OutOfFrames-next
			-- C-PRE-GET-FUNC PreGet-trunkRTCOutOfFrames
	STATUS		mandatory
	DESCRIPTION	"The number of 0 -> 1 transitions of the out of
			frame condition as detected by the hardware.
			This statistic is valid for T1 and E1 lines
			only."
	::=		{ trunkRTCEntry 6 }

trunkRTCLossOfSignal	OBJECT-TYPE
	SYNTAX		Counter
	ACCESS		read-only
			-- C-ACCESS-FUNC trunkRTCLossOfSignal
			-- C-NEXT-FUNC trunk-LossOfSignal-next
			-- C-PRE-GET-FUNC PreGet-trunkRTCLossOfSignal
	STATUS		mandatory
	DESCRIPTION	"The number of 0 -> 1 transitions of the loss
			of signal condition as detected by the
			hardware.  This statistic is valid for NTC
			lines only."
	::=		{ trunkRTCEntry 7 }

trunkRTCFrameBitErrors	OBJECT-TYPE
	SYNTAX		Counter
	ACCESS		read-only
			-- C-ACCESS-FUNC trunkRTCFrameBitErrors
			-- C-NEXT-FUNC trunk-FrameBitErrors-next
			-- C-PRE-GET-FUNC PreGet-trunkRTCFrameBitErrors
	STATUS		mandatory
	DESCRIPTION	"The number of frame alignment signal errors
			which have been detected on this line.  This
			statistic is valid only on lines supported by
			NTC cards.  TXR and Sub-rate lines do not
			support this statistic.  This statistic is
			also not supported by NTC-T1 in ESF framing
			mode."
	::=		{ trunkRTCEntry 8 }

trunkRTCCrcErrors	OBJECT-TYPE
	SYNTAX		Counter
	ACCESS		read-only
			-- C-ACCESS-FUNC trunkRTCCrcErrors
			-- C-NEXT-FUNC trunk-CrcErrors-next
			-- C-PRE-GET-FUNC PreGet-trunkRTCCrcErrors
	STATUS		mandatory
	DESCRIPTION	"The number of CRC errors detected on the line.
			This statistic is valid only on lines supported
			by NTC cards.  TXR cards and Sub-rate lines do
			not support this statistic.  This statistic is
			also not supported by NTC-T1 in D4 framing
			mode."
	::=		{ trunkRTCEntry 9 }

trunkRTCPktOutOfFrames	OBJECT-TYPE
	SYNTAX		Counter
	ACCESS		read-only
			-- C-ACCESS-FUNC trunkRTCPktOutOfFrames
			-- C-NEXT-FUNC trunk-PktOutOfFrames-next
			-- C-PRE-GET-FUNC PreGet-trunkRTCPktOutOfFrames
	STATUS		mandatory
	DESCRIPTION	"The number of packets out of frames on this
			line.  This statistic is only valid on lines
			supported by NTC cards.  TXR cards do not
			support this statistic."
	::=		{ trunkRTCEntry 10 }

trunkRTCPktCrcErrors	OBJECT-TYPE
	SYNTAX		Counter
	ACCESS		read-only
			-- C-ACCESS-FUNC trunkRTCPktCrcErrors
			-- C-NEXT-FUNC trunk-PktCrcErrors-next
			-- C-PRE-GET-FUNC PreGet-trunkRTCPktCrcErrors
	STATUS		mandatory
	DESCRIPTION	"The number of packets received with detected
			CRC errors in the packet headers."
	::=		{ trunkRTCEntry 11 }

trunkRTCBadClockErrors
			OBJECT-TYPE
	SYNTAX		Counter
	ACCESS		read-only
			-- C-ACCESS-FUNC trunkRTCBadClockErrors
			-- C-NEXT-FUNC trunk-BadClockErrors-next
			-- C-PRE-GET-FUNC PreGet-trunkRTCBadClockErrors
	STATUS		mandatory
	DESCRIPTION	"The number of 0 -> 1 transitions of the loss
			of clock condition as detected by the hardware.
			This statistic is valid on NTC Sub-rate lines
			only.  T1 and E1 lines do not support this
			statistic."
	::=		{ trunkRTCEntry 12 }

trunkRTCVoicePktsDropped
			OBJECT-TYPE
	SYNTAX		Counter
	ACCESS		read-only
			-- C-ACCESS-FUNC trunkRTCVoicePktsDropped
			-- C-NEXT-FUNC trunk-FrameSlips-next
			-- C-PRE-GET-FUNC PreGet-trunkRTCVoicePktsDropped
	STATUS		mandatory
	DESCRIPTION	"The number of voice packets dropped on a line."
	::=		{ trunkRTCEntry 13 }

trunkRTCTimeStampedPktsDropped
			OBJECT-TYPE
	SYNTAX		Counter
	ACCESS		read-only
			-- C-ACCESS-FUNC trunkRTCTimeStampedPktsDropped
			-- C-NEXT-FUNC trunk-TimeStampedPktsDropped-next
			-- C-PRE-GET-FUNC PreGet-trunkRTCTimeStampedPktsDropped
	STATUS		mandatory
	DESCRIPTION	"The number of time stamped data packets
			dropped on the line."
	::=		{ trunkRTCEntry 14 }

trunkRTCNonTimeStampedPktsDropped
			OBJECT-TYPE
	SYNTAX		Counter
	ACCESS		read-only
			-- C-ACCESS-FUNC trunkRTCNonTimeStampedPktsDropped
			-- C-NEXT-FUNC trunk-NonTimeStampedPktsDropped-next
			-- C-PRE-GET-FUNC PreGet-trunkRTCNonTimeStampedPktsDropped
	STATUS		mandatory
	DESCRIPTION	"The number of non-time stamped data packets
			dropped on the line."
	::=		{ trunkRTCEntry 15 }

trunkRTCHighPriorityPktsDropped
			OBJECT-TYPE
	SYNTAX		Counter
	ACCESS		read-only
			-- C-ACCESS-FUNC trunkRTCHighPriorityPktsDropped
			-- C-NEXT-FUNC trunk-HighPriorityPktsDropped-next
			-- C-PRE-GET-FUNC PreGet-trunkRTCHighPriorityPktsDropped
	STATUS		mandatory
	DESCRIPTION	"The number of high priority (PCC) packets
			dropped on the line."
	::=		{ trunkRTCEntry 16 }

trunkRTCBurstyDataPktsDropped
			OBJECT-TYPE
	SYNTAX		Counter
	ACCESS		read-only
			-- C-ACCESS-FUNC trunkRTCBurstyDataPktsDropped
			-- C-NEXT-FUNC trunk-BurstyDataPktsDropped-next
			-- C-PRE-GET-FUNC PreGet-trunkRTCBurstyDataPktsDropped
	STATUS		mandatory
	DESCRIPTION	"The number of bursty data packets dropped on
			the line."
	::=		{ trunkRTCEntry 17 }

trunkRTCMulticastPktsDropped
			OBJECT-TYPE
	SYNTAX		Counter
	ACCESS		read-only
			-- C-ACCESS-FUNC trunkRTCMulticastPktsDropped
			-- C-NEXT-FUNC trunk-MulticastPktsDropped-next
			-- C-PRE-GET-FUNC PreGet-trunkRTCMulticastPktsDropped
	STATUS		mandatory
	DESCRIPTION	"The number of Multicast packets dropped on
			the line."
	::=		{ trunkRTCEntry 18 }

trunkRTCVoicePktsXmitted
			OBJECT-TYPE
	SYNTAX		Counter
	ACCESS		read-only
			-- C-ACCESS-FUNC trunkRTCVoicePktsXmitted
			-- C-NEXT-FUNC trunk-VoicePktsXmitted-next
			-- C-PRE-GET-FUNC PreGet-trunkRTCVoicePktsXmitted
	STATUS		mandatory
	DESCRIPTION	"The number of voice packets transmitted onto
			the line."
	::=		{ trunkRTCEntry 19 }

trunkRTCTimeStampedPktsXmitted
			OBJECT-TYPE
	SYNTAX		Counter
	ACCESS		read-only
			-- C-ACCESS-FUNC trunkRTCTimeStampedPktsXmitted
			-- C-NEXT-FUNC trunk-TimeStampedPktsXmitted-next
			-- C-PRE-GET-FUNC PreGet-trunkRTCTimeStampedPktsXmitted
	STATUS		mandatory
	DESCRIPTION	"The number of time stamped packets transmitted
			onto the line."
	::=		{ trunkRTCEntry 20 }

trunkRTCNonTimeStampedPktsXmitted
			OBJECT-TYPE
	SYNTAX		Counter
	ACCESS		read-only
			-- C-ACCESS-FUNC trunkRTCNonTimeStampedPktsXmitted
			-- C-NEXT-FUNC trunk-NonTimeStampedPktsXmitted-next
			-- C-PRE-GET-FUNC PreGet-trunkRTCNonTimeStampedPktsXmitted
	STATUS		mandatory
	DESCRIPTION	"The number of non-time stamped packets
			transmitted onto the line."
	::=		{ trunkRTCEntry 21 }

trunkRTCHighPriorityPktsXmitted
			OBJECT-TYPE
	SYNTAX		Counter
	ACCESS		read-only
			-- C-ACCESS-FUNC trunkRTCHighPriorityPktsXmitted
			-- C-NEXT-FUNC trunk-HighPriorityPktsXmitted-next
			-- C-PRE-GET-FUNC PreGet-trunkRTCHighPriorityPktsXmitted
	STATUS		mandatory
	DESCRIPTION	"The number of high priority packets
			transmitted onto the line."
	::=		{ trunkRTCEntry 22 }

trunkRTCBurstyDataPktsXmitted
			OBJECT-TYPE
	SYNTAX		Counter
	ACCESS		read-only
			-- C-ACCESS-FUNC trunkRTCBurstyDataPktsXmitted
			-- C-NEXT-FUNC trunk-BurstyDataPktsXmitted-next
			-- C-PRE-GET-FUNC PreGet-trunkRTCBurstyDataPktsXmitted
	STATUS		mandatory
	DESCRIPTION	"The number of bursty data packets transmitted
			onto the line."
	::=		{ trunkRTCEntry 23 }

trunkRTCMulticastPktsXmitted
			OBJECT-TYPE
	SYNTAX		Counter
	ACCESS		read-only
			-- C-ACCESS-FUNC trunkRTCMulticastPktsXmitted
			-- C-NEXT-FUNC trunk-MulticastPktsXmitted-next
			-- C-PRE-GET-FUNC PreGet-trunkRTCMulticastPktsXmitted
	STATUS		mandatory
	DESCRIPTION	"The number of Multicast packets transmitted
			onto the line."
	::=		{ trunkRTCEntry 24 }

trunkRTCPktsXmitted	OBJECT-TYPE
	SYNTAX		Counter
	ACCESS		read-only
			-- C-ACCESS-FUNC trunkRTCPktsXmitted
			-- C-NEXT-FUNC trunk-PktsXmitted-next
			-- C-PRE-GET-FUNC PreGet-trunkRTCPktsXmitted
	STATUS		mandatory
	DESCRIPTION	"The total number of packets transmitted onto
			the line."
	::=		{ trunkRTCEntry 25 }

trunkRTCTxBurstyDataAClpPktsDropped
			OBJECT-TYPE
	SYNTAX		Counter
	ACCESS		read-only
			-- C-ACCESS-FUNC trunkRTCTxBurstyDataAClpPktsDropped
			-- C-NEXT-FUNC trunk-TxBurstyDataAClpPktsDropped-next
			-- C-PRE-GET-FUNC PreGet-trunkRTCTxBurstyDataAClpPktsDropped
	STATUS		mandatory
	DESCRIPTION	"The number of packets with the CLP bit set that
			are dropped from the bursty data A queue."
	::=		{ trunkRTCEntry 26 }

trunkRTCTxBurstyDataBClpPktsDropped
			OBJECT-TYPE
	SYNTAX		Counter
	ACCESS		read-only
			-- C-ACCESS-FUNC trunkRTCTxBurstyDataBClpPktsDropped
			-- C-NEXT-FUNC trunk-TxBurstyDataBClpPktsDropped-next
			-- C-PRE-GET-FUNC PreGet-trunkRTCTxBurstyDataBClpPktsDropped
	STATUS		mandatory
	DESCRIPTION	"The number of packets with the CLP bit set that
			are dropped from the bursty data B queue."
	::=		{ trunkRTCEntry 27 }

trunkRTCBurstyDataAEfcnPktsTx2Line
			OBJECT-TYPE
	SYNTAX		Counter
	ACCESS		read-only
			-- C-ACCESS-FUNC trunkRTCBurstyDataAEfcnPktsTx2Line
			-- C-NEXT-FUNC trunk-BurstyDataAEfcnPktsTx2Line-next
			-- C-PRE-GET-FUNC PreGet-trunkRTCBurstyDataAEfcnPktsTx2Line
	STATUS		mandatory
	DESCRIPTION	"The number of packets with the EFCN bit set which
			have been transmitted onto the line from the bursty 
			data A queue."
	::=		{ trunkRTCEntry 28 }

trunkRTCBurstyDataBEfcnPktsTx2Line
			OBJECT-TYPE
	SYNTAX		Counter
	ACCESS		read-only
			-- C-ACCESS-FUNC trunkRTCBurstyDataBEfcnPktsTx2Line
			-- C-NEXT-FUNC trunk-BurstyDataBEfcnPktsTx2Line-next
			-- C-PRE-GET-FUNC PreGet-trunkRTCBurstyDataBEfcnPktsTx2Line
	STATUS		mandatory
	DESCRIPTION	"The number of packets with the EFCN bit set which
			have been transmitted onto the line from the bursty 
			data B queue."
	::=		{ trunkRTCEntry 29 }

trunkRTCBurstyDataAClpPktsTx2Line
			OBJECT-TYPE
	SYNTAX		Counter
	ACCESS		read-only
			-- C-ACCESS-FUNC trunkRTCBurstyDataAClpPktsTx2Line
			-- C-NEXT-FUNC trunk-BurstyDataAClpPktsTx2Line-next
			-- C-PRE-GET-FUNC PreGet-trunkRTCBurstyDataAClpPktsTx2Line
	STATUS		mandatory
	DESCRIPTION	"The number of packets with the CLP bit set which
			have been transmitted onto the line from the bursty 
			data A queue."
	::=		{ trunkRTCEntry 30 }

trunkRTCBurstyDataBClpPktsTx2Line
			OBJECT-TYPE
	SYNTAX		Counter
	ACCESS		read-only
			-- C-ACCESS-FUNC trunkRTCBurstyDataBClpPktsTx2Line
			-- C-NEXT-FUNC trunk-BurstyDataBClpPktsTx2Line-next
			-- C-PRE-GET-FUNC PreGet-trunkRTCBurstyDataBClpPktsTx2Line
	STATUS		mandatory
	DESCRIPTION	"The number of packets with the CLP bit set which
			have been transmitted onto the line from the bursty 
			data B queue."
	::=		{ trunkRTCEntry 31 }

trunkRTCAtmCellHeaderHecErrors
			OBJECT-TYPE
	SYNTAX		Counter
	ACCESS		read-only
			-- C-ACCESS-FUNC trunkRTCAtmCellHeaderHecErrors
			-- C-NEXT-FUNC trunk-AtmCellHeaderHecErrors-next
			-- C-PRE-GET-FUNC PreGet-trunkRTCAtmCellHeaderHecErrors
	STATUS		mandatory
	DESCRIPTION	"The number of ATM cell headers with HEC errors."
	::=		{ trunkRTCEntry 32 }

trunkRTCTxVoiceCellsDropped
			OBJECT-TYPE
	SYNTAX		Counter
	ACCESS		read-only
			-- C-ACCESS-FUNC trunkRTCTxVoiceCellsDropped
			-- C-NEXT-FUNC trunk-TxVoiceCellsDropped-next
			-- C-PRE-GET-FUNC PreGet-trunkRTCTxVoiceCellsDropped
	STATUS		mandatory
	DESCRIPTION	"The number of transmit voice cells dropped."
	::=		{ trunkRTCEntry 33 }

trunkRTCTxTimeStampCellsDropped
			OBJECT-TYPE
	SYNTAX		Counter
	ACCESS		read-only
			-- C-ACCESS-FUNC trunkRTCTxTimeStampCellsDropped
			-- C-NEXT-FUNC trunk-TxTimeStampCellsDropped-next
			-- C-PRE-GET-FUNC PreGet-trunkRTCTxTimeStampCellsDropped
	STATUS		mandatory
	DESCRIPTION	"The number of transmit time stamped cells
			dropped."
	::=		{ trunkRTCEntry 34 }

trunkRTCTxNonTStampCellsDropped
			OBJECT-TYPE
	SYNTAX		Counter
	ACCESS		read-only
			-- C-ACCESS-FUNC trunkRTCTxNonTStampCellsDropped
			-- C-NEXT-FUNC trunk-TxNonTStampCellsDropped-next
			-- C-PRE-GET-FUNC PreGet-trunkRTCTxNonTStampCellsDropped
	STATUS		mandatory
	DESCRIPTION	"The number of transmit non time stamped cells
			dropped."
	::=		{ trunkRTCEntry 35 }

trunkRTCTxHighPriorityCellsDropped
			OBJECT-TYPE
	SYNTAX		Counter
	ACCESS		read-only
			-- C-ACCESS-FUNC trunkRTCTxHighPriorityCellsDropped
			-- C-NEXT-FUNC trunk-TxHighPriorityCellsDropped-next
			-- C-PRE-GET-FUNC PreGet-trunkRTCTxHighPriorityCellsDropped
	STATUS		mandatory
	DESCRIPTION	"The number of transmit high priority cells
			dropped."
	::=		{ trunkRTCEntry 36 }

trunkRTCTxBurstyDataACellsDropped
			OBJECT-TYPE
	SYNTAX		Counter
	ACCESS		read-only
			-- C-ACCESS-FUNC trunkRTCTxBurstyDataACellsDropped
			-- C-NEXT-FUNC trunk-TxBurstyDataACellsDropped-next
			-- C-PRE-GET-FUNC PreGet-trunkRTCTxBurstyDataACellsDropped
	STATUS		mandatory
	DESCRIPTION	"The number of cells dropped from the bursty 
			data A queue."
	::=		{ trunkRTCEntry 37 }

trunkRTCTxBurstyDataBCellsDropped
			OBJECT-TYPE
	SYNTAX		Counter
	ACCESS		read-only
			-- C-ACCESS-FUNC trunkRTCTxBurstyDataBCellsDropped
			-- C-NEXT-FUNC trunk-TxBurstyDataBCellsDropped-next
			-- C-PRE-GET-FUNC PreGet-trunkRTCTxBurstyDataBCellsDropped
	STATUS		mandatory
	DESCRIPTION	"The number of cells dropped from the bursty 
			data B queue."
	::=		{ trunkRTCEntry 38 }

trunkRTCVoiceCellsTx2Line
			OBJECT-TYPE
	SYNTAX		Counter
	ACCESS		read-only
			-- C-ACCESS-FUNC trunkRTCVoiceCellsTx2Line
			-- C-NEXT-FUNC trunk-VoiceCellsTx2Line-next
			-- C-PRE-GET-FUNC PreGet-trunkRTCVoiceCellsTx2Line
	STATUS		mandatory
	DESCRIPTION	"The number of voice cells transmitted onto 
			the line."
	::=		{ trunkRTCEntry 39 }

trunkRTCTimeStampCellsTx2Line
			OBJECT-TYPE
	SYNTAX		Counter
	ACCESS		read-only
			-- C-ACCESS-FUNC trunkRTCTimeStampCellsTx2Line
			-- C-NEXT-FUNC trunk-TimeStampCellsTx2Line-next
			-- C-PRE-GET-FUNC PreGet-trunkRTCTimeStampCellsTx2Line
	STATUS		mandatory
	DESCRIPTION	"The number of time stamped cells tranmsitted
			onto the line."
	::=		{ trunkRTCEntry 40 }

trunkRTCNonTimeStampCellsTx2Line
			OBJECT-TYPE
	SYNTAX		Counter
	ACCESS		read-only
			-- C-ACCESS-FUNC trunkRTCNonTimeStampCellsTx2Line
			-- C-NEXT-FUNC trunk-NonTimeStampCellsTx2Line-next
			-- C-PRE-GET-FUNC PreGet-trunkRTCNonTimeStampCellsTx2Line
	STATUS		mandatory
	DESCRIPTION	"The number of non time stamped cells tranmsitted
			onto the line."
	::=		{ trunkRTCEntry 41 }

trunkRTCHighPriorityCellsTx2Line
			OBJECT-TYPE
	SYNTAX		Counter
	ACCESS		read-only
			-- C-ACCESS-FUNC trunkRTCHighPriorityCellsTx2Line
			-- C-NEXT-FUNC trunk-HighPriorityCellsTx2Line-next
			-- C-PRE-GET-FUNC PreGet-trunkRTCHighPriorityCellsTx2Line
	STATUS		mandatory
	DESCRIPTION	"The number of high priority cells transmitted
			onto the line."
	::=		{ trunkRTCEntry 42 }

trunkRTCBurstyDataACellsTx2Line
			OBJECT-TYPE
	SYNTAX		Counter
	ACCESS		read-only
			-- C-ACCESS-FUNC trunkRTCBurstyDataACellsTx2Line
			-- C-NEXT-FUNC trunk-BurstyDataACellsTx2Line-next
			-- C-PRE-GET-FUNC PreGet-trunkRTCBurstyDataACellsTx2Line
	STATUS		mandatory
	DESCRIPTION	"The number of cells which have been transmitted
			onto the line from the bursty data A queue." 
			
	::=		{ trunkRTCEntry 43 }

trunkRTCBurstyDataBCellsTx2Line
			OBJECT-TYPE
	SYNTAX		Counter
	ACCESS		read-only
			-- C-ACCESS-FUNC trunkRTCBurstyDataBCellsTx2Line
			-- C-NEXT-FUNC trunk-BurstyDataBCellsTx2Line-next
			-- C-PRE-GET-FUNC PreGet-trunkRTCBurstyDataBCellsTx2Line
	STATUS		mandatory
	DESCRIPTION	"The number of cells which have been transmitted
			onto the line from the bursty data B queue."
	::=		{ trunkRTCEntry 44 }

trunkRTCTotalCellsTx2Line
			OBJECT-TYPE
	SYNTAX		Counter
	ACCESS		read-only
			-- C-ACCESS-FUNC trunkRTCTotalCellsTx2Line
			-- C-NEXT-FUNC trunk-TotalCellsTx2Line-next
			-- C-PRE-GET-FUNC PreGet-trunkRTCTotalCellsTx2Line
	STATUS		mandatory
	DESCRIPTION	"The number of cells transmitted onto the
			line."
	::=		{ trunkRTCEntry 45 }

trunkRTCTxBurstyDataAClpCellsDropped
			OBJECT-TYPE
	SYNTAX		Counter
	ACCESS		read-only
			-- C-ACCESS-FUNC trunkRTCTxBurstyDataAClpCellsDropped
			-- C-NEXT-FUNC trunk-TxBurstyDataAClpCellsDropped-next
			-- C-PRE-GET-FUNC PreGet-trunkRTCTxBurstyDataAClpCellsDropped
	STATUS		mandatory
	DESCRIPTION	"The number of cells with the CLP bit set
			which have been dropped from the bursty 
			data A queue."
	::=		{ trunkRTCEntry 46 }

trunkRTCTxBurstyDataBClpCellsDropped
			OBJECT-TYPE
	SYNTAX		Counter
	ACCESS		read-only
			-- C-ACCESS-FUNC trunkRTCTxBurstyDataBClpCellsDropped
			-- C-NEXT-FUNC trunk-TxBurstyDataBClpCellsDropped-next
			-- C-PRE-GET-FUNC PreGet-trunkRTCTxBurstyDataBClpCellsDropped
	STATUS		mandatory
	DESCRIPTION	"The number of cells with the CLP bit set
			which have been dropped from the bursty 
			data B queue."
	::=		{ trunkRTCEntry 47 }

trunkRTCBurstyDataAEfcnCellsTx2Line
			OBJECT-TYPE
	SYNTAX		Counter
	ACCESS		read-only
			-- C-ACCESS-FUNC trunkRTCBurstyDataAEfcnCellsTx2Line
			-- C-NEXT-FUNC trunk-BurstyDataAEfcnCellsTx2Line-next
			-- C-PRE-GET-FUNC PreGet-trunkRTCBurstyDataAEfcnCellsTx2Line
	STATUS		mandatory
	DESCRIPTION	"The number of cells with the EFCN bit set 
			which have been transmitted onto the line 
			from the bursty data A queue."
	::=		{ trunkRTCEntry 48 }

trunkRTCBurstyDataBEfcnCellsTx2Line
			OBJECT-TYPE
	SYNTAX		Counter
	ACCESS		read-only
			-- C-ACCESS-FUNC trunkRTCBurstyDataBEfcnCellsTx2Line
			-- C-NEXT-FUNC trunk-BurstyDataBEfcnCellsTx2Line-next
			-- C-PRE-GET-FUNC PreGet-trunkRTCBurstyDataBEfcnCellsTx2Line
	STATUS		mandatory
	DESCRIPTION	"The number of cells with the EFCN bit set
			which have been transmitted onto the line 
			from the bursty data B queue."
	::=		{ trunkRTCEntry 49 }

trunkRTCPlcpOutOfFrames
			OBJECT-TYPE
	SYNTAX		Counter
	ACCESS		read-only
			-- C-ACCESS-FUNC trunkRTCPlcpOutOfFrames
			-- C-NEXT-FUNC trunk-PlcpOutOfFrames-next
			-- C-PRE-GET-FUNC PreGet-trunkRTCPlcpOutOfFrames
	STATUS		mandatory
	DESCRIPTION	"The number of out of frame conditions."
	::=		{ trunkRTCEntry 50 }


-- ---------------------------------------------------------
--	Trap Config Table
-- ---------------------------------------------------------

trapConfigTable		OBJECT-TYPE
	SYNTAX		SEQUENCE OF TrapConfigEntry
	ACCESS		not-accessible
	STATUS		mandatory
	DESCRIPTION	"The table has the information about the manager 
				 receiving traps"
	::=		{ trapsConfig 1 }

trapConfigEntry		OBJECT-TYPE
	SYNTAX		TrapConfigEntry
	ACCESS		not-accessible
	STATUS		mandatory
	DESCRIPTION	"An entry of the manager table."
	INDEX		{ managerIPaddress }
			-- C-NEXT-FUNC	mgr-next
	::=		{ trapConfigTable 1 }

TrapConfigEntry	::=	SEQUENCE {
	managerIPaddress		IpAddress,
	managerPortNumber		INTEGER,
	managerRowStatus		INTEGER,
	readingTrapFlag			INTEGER,
	nextTrapSeqNum			INTEGER
}

managerIPaddress	OBJECT-TYPE
	SYNTAX		IpAddress
	ACCESS		read-write
			-- C-ACCESS-FUNC ip-address
			-- C-LOCATOR-FUNC mgr-locator
	STATUS		mandatory
	DESCRIPTION	" "
	::=		{ trapConfigEntry 1 }

managerPortNumber	OBJECT-TYPE
	SYNTAX		INTEGER
	ACCESS		read-write
			-- C-ACCESS-FUNC port-number
			-- C-LOCATOR-FUNC mgr-locator
	STATUS		mandatory
	DESCRIPTION	" "
	::=		{ trapConfigEntry 2 }


managerRowStatus	OBJECT-TYPE
	SYNTAX	INTEGER	{ 
			  addRow	(1),
			  delRow	(2)
			  }
	ACCESS		read-write
			-- C-ACCESS-FUNC row-status 
			-- C-LOCATOR-FUNC mgr-locator
	STATUS		mandatory
	DESCRIPTION	"When RowStatus is set to addRow(1), the mgr is registered with the
                         Proxy to receive the new traps generated."
	::=		{  trapConfigEntry 3 }

readingTrapFlag	OBJECT-TYPE
	SYNTAX	INTEGER	{ 
			  false	(1),
			  true	(2)
			  }
	ACCESS		read-write
			-- C-ACCESS-FUNC reading-flag
			-- C-LOCATOR-FUNC mgr-locator
	STATUS		mandatory
	DESCRIPTION	" "
	::=		{ trapConfigEntry 4 }

nextTrapSeqNum	OBJECT-TYPE
	SYNTAX		INTEGER
	ACCESS		read-write
			-- C-ACCESS-FUNC trap-seqnum
			-- C-LOCATOR-FUNC mgr-locator
	STATUS		mandatory
	DESCRIPTION	" "
	::=		{ trapConfigEntry 5 }

managerNumOfValidEntries	OBJECT-TYPE
	SYNTAX		INTEGER(1..8)
	ACCESS		read-only
			-- C-ACCESS-FUNC    manager-entries
	STATUS		mandatory
	DESCRIPTION	"The number of managers in the table that are 
				 programmed to receive traps"
	::=		{ trapsConfig 2 }


lastSequenceNumber	OBJECT-TYPE
	SYNTAX		INTEGER
	ACCESS		read-only
			-- C-STRUCT proxy-ctxt, FIELD 	lastTrapSeqNum
	STATUS		mandatory
	DESCRIPTION	"The Sequence Number of the last trap generated on the SNMP Proxy"
	::=		{ trapsConfig 3 }

-----------------------------------------------------------------------
--	RTM Group
--	
-----------------------------------------------------------------------


trapUploadTable		OBJECT-TYPE
	SYNTAX		SEQUENCE OF TrapUploadEntry
	ACCESS		not-accessible
	STATUS		mandatory
	DESCRIPTION	"The table has the information about the manager 
				 receiving traps"
	::=		{ trapsConfig 4 }

trapUploadEntry		OBJECT-TYPE
	SYNTAX		TrapUploadEntry
	ACCESS		not-accessible
	STATUS		mandatory
	DESCRIPTION	"An entry of the manager table."
	INDEX		{ mgrIpAddress }
			-- C-NEXT-FUNC	trap-next
	::=		{ trapUploadTable 1 }

TrapUploadEntry	::=	SEQUENCE {
	mgrIpAddress		IpAddress,
	trapSequenceNum		INTEGER,
	trapPduString		OCTET STRING,
	endOfQueueFlag		INTEGER
}

mgrIpAddress	OBJECT-TYPE
	SYNTAX		IpAddress
	ACCESS		read-only
			-- C-ACCESS-FUNC mgrIpAddress
			-- C-LOCATOR-FUNC trap-locator
	STATUS		mandatory
	DESCRIPTION	" "
	::=		{ trapUploadEntry 1 }

trapSequenceNum	OBJECT-TYPE
	SYNTAX		INTEGER
	ACCESS		read-only
			-- C-ACCESS-FUNC	trapSequenceNum 
			-- C-LOCATOR-FUNC	trap-locator
	STATUS		mandatory
	DESCRIPTION	"The sequence number associated with tthe trap"
	::=		{ trapUploadEntry 2 }

trapPduString	OBJECT-TYPE
	SYNTAX		OCTET STRING
	ACCESS		read-only
			-- C-ACCESS-FUNC	trapPduString 
			-- C-LOCATOR-FUNC	trap-locator
	STATUS		mandatory
	DESCRIPTION	"The sequence number associated with tthe trap"
	::=		{ trapUploadEntry 3 }

endOfQueueFlag	OBJECT-TYPE
	SYNTAX		INTEGER	{
				false(1),
				true(2)
				}
	ACCESS		read-only
			-- C-ACCESS-FUNC	endOfQueueFlag
			-- C-LOCATOR-FUNC	trap-locator
	STATUS		mandatory
	DESCRIPTION	"The sequence number associated with tthe trap"
	::=		{ trapUploadEntry 4 }


--
--	control Group contains attributes associated with controlling
--	logGroup as a whole.  This group is mandatory

databaseSampleFreq	OBJECT-TYPE
	SYNTAX		INTEGER	(5..86400)
	ACCESS		read-write
			-- C-STRUCT proxy-ctxt, FIELD dbSampleFreq
	STATUS		mandatory
	DESCRIPTION	"The desired rate (in seconds) at which the
			database should be queried for new log
			records that match any of the filter criteria
			from the Event Filter Table.

			The agent may optionally poll more or less
			frequently then specified by this variable.
			The value of this variable is only a suggestion
			to the agent."
	DEFVAL		{ 60 }
	::=		{ controlGroup 1 }


----------------------------------------------------------------------- 
-- Log Group.
-----------------------------------------------------------------------

currentMaxLogIndex	OBJECT-TYPE
	SYNTAX		INTEGER
	ACCESS		read-only
			-- C-ACCESS-FUNC MaxLogIndex
	STATUS		mandatory
	DESCRIPTION	"The current max value of logIndex.  This value
			may change with time."
	::=		{ logGroup 1 }

----------------------------------------------------------------------- 
-- 	Maint Log Table
----------------------------------------------------------------------- 
maintLogTable		OBJECT-TYPE
	SYNTAX		SEQUENCE OF MaintLogEntry
	ACCESS		not-accessible
	STATUS		mandatory
	DESCRIPTION	"The table of log entries."
	::=		{ logGroup 2 }

maintLogEntry		OBJECT-TYPE
	SYNTAX		MaintLogEntry
	ACCESS		not-accessible
	STATUS		mandatory
	DESCRIPTION	"An entry in the log table."
	INDEX		{ logIndex }
			-- C-NEXT-FUNC	log-next
	::=		{ maintLogTable 1 }

MaintLogEntry	::=	SEQUENCE {
	logIndex	INTEGER,
	logNetwork	DisplayString,
	logNodeName	DisplayString,
	logGmtDate	DisplayString,
	logSeverity	Severity,
	logMsg		DisplayString
}

logIndex		OBJECT-TYPE
	SYNTAX		INTEGER	(1..1073741824)
	ACCESS		read-only
			-- C-STRUCT log-record, FIELD logIndex
			-- C-LOCATOR-FUNC log-locator
	STATUS		mandatory
	DESCRIPTION	"Unique index of the Log record."
	::=		{ maintLogEntry 1 }

logNetwork		OBJECT-TYPE
	SYNTAX		DisplayString (SIZE (0..10))
	ACCESS		read-only
			-- C-STRUCT log-record, FIELD logNetwork
			-- C-LOCATOR-FUNC log-locator
	STATUS		mandatory
	DESCRIPTION	"Name of the network for which this log
			entry was generated."
	::=		{ maintLogEntry 2 }

logNodeName		OBJECT-TYPE
	SYNTAX		DisplayString (SIZE (0..10))
	ACCESS		read-only
			-- C-STRUCT log-record, FIELD logNodeName
			-- C-LOCATOR-FUNC log-locator
	STATUS		mandatory
	DESCRIPTION	"Name of the IPX node for this this log
			entry was generated."
	::=		{ maintLogEntry 3 }

logGmtDate		OBJECT-TYPE
	SYNTAX		DisplayString (SIZE (19))
	ACCESS		read-only
			-- C-STRUCT log-record, FIELD logGmtDate
			-- C-LOCATOR-FUNC log-locator
	STATUS		mandatory
	DESCRIPTION	"ASCII formatted string indicating the GMT
			date and time for this log record in the
			format (yyyy-mm-dd hh:mm:ss).  This is the
			time reported by the IPX which generated the
			event."
	::=		{ maintLogEntry 4 }

logSeverity		OBJECT-TYPE
	SYNTAX		Severity
	ACCESS		read-only
			-- C-STRUCT log-record, FIELD logSeverity
			-- C-LOCATOR-FUNC log-locator
	STATUS		mandatory
	DESCRIPTION	"The severity of this log record."
	::=		{ maintLogEntry 5 }

logMsg			OBJECT-TYPE
	SYNTAX		DisplayString (SIZE (0..256))
	ACCESS		read-only
			-- C-STRUCT log-record, FIELD logMsg
			-- C-LOCATOR-FUNC log-locator
	STATUS		mandatory
	DESCRIPTION	"An ASCII message associated with this log
			record."
	::=		{ maintLogEntry 6 }

----------------------------------------------------------------------- 
--	Event Filtering Table
----------------------------------------------------------------------- --
--	In order for a manager to create a row of this table, a 
-- 	single SET request should be sent with all the variables 
--	for every column specified.
--
--	In order for a manager to delete a row of this table, a 
--	single SET requets should be sent to change the 
--	eventFilterStatus column from 'active' to 'invalid'.
--
--  For a new log record to be forwarded as a TRAP the following
--	must be true:
--
--  eventFilterStatus     must be 'active'.
--
--  eventFilterSeverity   must exactly match the logSeverity 
--  of the log record.
--
--  eventFilterSubstring  must contain a string that is 
--  found in the logMsg variable of the 
--  log record.
--
--	To request all events of all severity levels, set both the 
--	eventFilterSeverity and eventFilterSubstring elements to 
--	be zero-length strings.
--
eventFilterTable	OBJECT-TYPE
	SYNTAX		SEQUENCE OF EventFilterEntry
	ACCESS		not-accessible
	STATUS		mandatory
	DESCRIPTION	"The table of Event Filters."
	::=		{ logGroup 3 }

eventFilterEntry	OBJECT-TYPE
	SYNTAX		EventFilterEntry
	ACCESS		not-accessible
	STATUS		mandatory
	DESCRIPTION	"An entry in the Event Filter table.  Each
			entry in this table describes a set of log
			entry criteria, and entries in the log that
			match these criteria will be forwarded
			as SNMP TRAPS."
	INDEX		{ eventFilterIndex }
			-- C-NEXT-FUNC	filter-next
	::=		{ eventFilterTable 1 }

EventFilterEntry ::= SEQUENCE {
	eventFilterIndex		INTEGER,
	eventFilterStatus		INTEGER,
	eventFilterSeverity		Severity,
	eventFilterSubstring		DisplayString }

eventFilterIndex	OBJECT-TYPE
	SYNTAX		INTEGER	( 1 .. 2147483647)
	ACCESS		read-write
			-- C-ACCESS-FUNC filter-index
			-- C-LOCATOR-FUNC filter-locator-ind
	STATUS		mandatory
	DESCRIPTION	"The unique index for each entry of this table.
			This entry can only be written with the first
			SET command to create a new row of this table."
	::=		{ eventFilterEntry 1 }

eventFilterStatus	OBJECT-TYPE
	SYNTAX		INTEGER	{ invalid	(1),
				  active	(2) }
	ACCESS		read-write
			-- C-ACCESS-FUNC filter-status
			-- C-LOCATOR-FUNC filter-locator
	STATUS		mandatory
	DESCRIPTION	"'active' indicates that this row of the table
			is currently generating filtered TRAPs.  When
			in this state, any entry added to the log table
			with logSeverity matching eventFilterSeverity
			and logMsg containing the eventFilterSubstring
			text, this information will be forwarded as a
			TRAP.

			'invalid' indicates that this row of the table
			is no longer generating filtered TRAPs.

			A conforming agent may either leave
			the row with the 'invalid' value in the table,
			or may delete the row from the table."
	DEFVAL		{ active }
	::=		{ eventFilterEntry 2 }

eventFilterSeverity	OBJECT-TYPE
	SYNTAX		Severity
	ACCESS		read-write
			-- C-ACCESS-FUNC filter-severity
			-- C-LOCATOR-FUNC filter-locator
	STATUS		mandatory
	DESCRIPTION	"The eventFilterSeverity specifies the severity
			of log records to be forwarded on as SNMP TRAPS
			by this event filter entry.  The value of
			eventFilterSeverty must exactly match the value
			of logSeverity for there to be a chance that
			a new log record will be forwarded as a TRAP.
			An eventFilterSeverity of length 0 matches all
			severity levels."
	DEFVAL		{ ''h }
	::=		{ eventFilterEntry 3 }

eventFilterSubstring	OBJECT-TYPE
	SYNTAX		DisplayString (SIZE (0..256))
	ACCESS		read-write
			-- C-ACCESS-FUNC filter-substring
			-- C-LOCATOR-FUNC filter-locator
	STATUS		mandatory
	DESCRIPTION	"The eventFilterSubstring variable specifies an
			ASCII substring that must appear in the logMsg
			field of a log record in order for there to be
			a chance that for the log record to forwarded
			as a TRAP.  If this variable contains a zero
			length string, the substring comparison will
			always SUCCEED for this event filter entry."
	DEFVAL		{ ''h }
	::=		{ eventFilterEntry 4 }

--
--	maintLog Table Filter Group
--
--	This group is optional and may be used to support filtering 
--	GetNext requests when retrieving elements from the 
--	mainLogTable.  If the group is supported then all attributes 
--	in the group are mandatory.
--
--

maintLogFilterGroup	OBJECT IDENTIFIER ::= { logGroup 4 }

--	When applying the maintLogFilterGroup attributes during an 
--	SNMP Operation, the order is important.  The attributes will 
--	be applied in the following order:
--		maintLogFilterTimeMin
--		maintLogFilterTimeMax
--		maintLogFilterNetworkName
--		maintLogFilterNodeName
--		maintLogFilterSeverity
--		maintLogFilterWindow
--

maintLogFilterTimeMin		OBJECT-TYPE
	SYNTAX		DisplayString(SIZE(0..22))
	ACCESS		read-write
			-- C-ACCESS-FUNC MaintLogFilterTimeMin
			-- C-LOCATOR-FUNC MaintFilterLocator
	STATUS		mandatory
	DESCRIPTION	"When maintLogFilterTimeMin has a value other than
			a 0 length string, the value is used as a
			minimum value for maintLogFilterGmtDate to
			qualify entries in the maintLogTable.

			The string is formated as yyyy-mm-dd hh:mm:ss"
	DEFVAL		{ ''h }
	::=		{ maintLogFilterGroup 1 }


maintLogFilterTimeMax		OBJECT-TYPE
	SYNTAX		DisplayString(SIZE(0..22)) 
	ACCESS		read-write
			-- C-ACCESS-FUNC MaintLogFilterTimeMax
			-- C-LOCATOR-FUNC MaintFilterLocator
	STATUS		mandatory
	DESCRIPTION	"When maintLogFilterTimeMax has a value other than
			a 0 length string, the value is used as a
			maximum value for maintLogFilterGmtDate to qualify
			entries in the maintLogTable.

			The string is formated as yyyy-mm-dd hh:mm:ss"
	DEFVAL		{ ''h }
	::=		{ maintLogFilterGroup 2 }

maintLogFilterWindow	OBJECT-TYPE
	SYNTAX		INTEGER
	ACCESS		read-write
			-- C-ACCESS-FUNC MaintLogFilterWindow
			-- C-LOCATOR-FUNC MaintFilterLocator
	STATUS		mandatory
	DESCRIPTION	"When maintLogFilterWindow has a value other than
			0, the value is used to qualify entries in the 
			maintLogTable.

			This attribute has the effect of limiting the 
			view in the maintLogTable to the number specified
			by the value of this attribute.

			If after applying the other maintLogFilter attributes,
			the remaining set exceeds the value of
			maintLogFilterWindow then, the set of
			entries which can be viewed is limited to the 
			top N based on the logIndex value."
	DEFVAL		{ 30 }
	::=             { maintLogFilterGroup 3 }

maintLogFilterNetworkName	OBJECT-TYPE
	SYNTAX		DisplayString (SIZE (0..10)) 
	ACCESS		read-write
			-- C-ACCESS-FUNC MaintLogFilterNetwork
			-- C-LOCATOR-FUNC MaintFilterLocator
	STATUS		mandatory
	DESCRIPTION	"When maintLogFilterNetworkName has a value other
			than a 0 length string, then the value of this
			attribute is used to qualify entries in the
			maintLogTable.  This value must match logNetwork
			exactly to pass the filter."
	DEFVAL		{ ''h }
	::=		{ maintLogFilterGroup 4 }

maintLogFilterNodeName	OBJECT-TYPE
	SYNTAX		DisplayString (SIZE (0..10)) 
	ACCESS		read-write
			-- C-ACCESS-FUNC MaintLogFilterNode
			-- C-LOCATOR-FUNC MaintFilterLocator
	STATUS		mandatory
	DESCRIPTION	"When maintLogFilterNodeName has a value other
			than a 0 length string, then the value of this
			attribute is used to qualify entries in the
			maintLogTable.  This value must match logNodeName
			exactly to pass the filter."
	DEFVAL		{ ''h }
	::=		{ maintLogFilterGroup 5 }

maintLogFilterSeverity	OBJECT-TYPE
	SYNTAX		Severity 
	ACCESS		read-write
			-- C-ACCESS-FUNC MaintLogFilterSeverity
			-- C-LOCATOR-FUNC MaintFilterLocator
	STATUS		mandatory
	DESCRIPTION	"When maintLogFilterSeverity has a value other
			than a 0 length string, then the value is used
			to qualify entries in the maintLogTable.  The
			value must match the logSeverity exactly to 
			pass the filter."
	DEFVAL		{ ''h }
	::=		{ maintLogFilterGroup 6 }

----------------------------------------------------------------------- 
--	Network Group
-----------------------------------------------------------------------

----------------------------------------------------------------------- 
--	Network Table
----------------------------------------------------------------------- 
networkTable		OBJECT-TYPE
	SYNTAX		SEQUENCE OF NetworkEntry
	ACCESS		not-accessible
	STATUS		mandatory
	DESCRIPTION	"The table of Networks."
	::=		{ networkGroup 1 }

networkEntry		OBJECT-TYPE
	SYNTAX		NetworkEntry
	ACCESS		not-accessible
	STATUS		mandatory
	DESCRIPTION	"An entry in the Network table."
	INDEX		{ networkName }
			-- C-NEXT-FUNC	net-next
	::=		{ networkTable 1 }

NetworkEntry	::=	SEQUENCE {
	networkName	DisplayString,
	networkId	INTEGER,
	networkIpxId	INTEGER
}

networkName		OBJECT-TYPE
	SYNTAX		DisplayString (SIZE(0..10))
	ACCESS		read-only
			-- C-STRUCT network-cfg, FIELD networkName
			-- C-LOCATOR-FUNC net-locator
	STATUS		mandatory
	DESCRIPTION	"The name of the network as assigned by
			the StrataView User."
	::=		{ networkEntry 1 }

networkId		OBJECT-TYPE
	SYNTAX		INTEGER
	ACCESS		read-only
			-- C-STRUCT network-cfg, FIELD networkId
			-- C-LOCATOR-FUNC net-locator
	STATUS		mandatory
	DESCRIPTION	"The unique ID of the network as assigned
			by the StrataView system."
	::=		{ networkEntry 2 }

networkIpxId		OBJECT-TYPE
	SYNTAX		INTEGER
	ACCESS		read-only
			-- C-STRUCT network-cfg, FIELD networkIpxId
			-- C-LOCATOR-FUNC net-locator
	STATUS		mandatory
	DESCRIPTION	"The IPX network ID."
	::=		{ networkEntry 3 }

----------------------------------------------------------------------- 
--	Node Group
-----------------------------------------------------------------------

----------------------------------------------------------------------- 
--	Node Table
----------------------------------------------------------------------- 
nodeTable		OBJECT-TYPE
	SYNTAX		SEQUENCE OF NodeEntry
	ACCESS		not-accessible
	STATUS		mandatory
	DESCRIPTION	"The table of Nodes."
	::=		{ nodeGroup 1 }

nodeEntry		OBJECT-TYPE
	SYNTAX		NodeEntry
	ACCESS		not-accessible
	STATUS		mandatory
	DESCRIPTION	"An entry in the Node table."
	INDEX		{ nodeNetworkName, nodeName }
			-- C-NEXT-FUNC 	EventNodeNext
	::=		{ nodeTable 1 }

NodeEntry	::=	SEQUENCE {
	nodeNetworkName	DisplayString,
	nodeName	DisplayString
}

nodeNetworkName		OBJECT-TYPE
	SYNTAX		DisplayString (SIZE (0..10))
	ACCESS		read-only
			-- C-STRUCT node-cfg, FIELD nodeNetName
			-- C-LOCATOR-FUNC EventNodeLocator
	STATUS		mandatory
	DESCRIPTION	"The name of the network to which this node is
			attached."
	::=		{ nodeEntry 1 }

nodeName		OBJECT-TYPE
	SYNTAX		DisplayString (SIZE(0..10))
	ACCESS		read-only
			-- C-STRUCT node-cfg, FIELD nodeName
			-- C-LOCATOR-FUNC	EventNodeLocator
	STATUS		mandatory
	DESCRIPTION	"IPX node name."
	::=		{ nodeEntry 2 }

-- 
--      Trap Definitions
--
trunkStatusAlarm       TRAP-TYPE
        ENTERPRISE      svnode
        VARIABLES       {       
				lastSequenceNumber,
				nodeGrpName,
                                nodeGrpNetName,
                                trunkStatus
                        }
        DESCRIPTION     "This trap is generated whenever an ObjectAlarm
			Status message is received containing the trunk status."
        ::= 0

cirLineStatusAlarm       TRAP-TYPE
	ENTERPRISE      svnode
	VARIABLES       {       
				lastSequenceNumber,
				nodeGrpName,
				nodeGrpNetName,
				cirLineStatus
			}
        DESCRIPTION     "This trap is generated whenever an ObjectAlarm
			Status message is received containing the cirLineStatus."
	::= 1

frpStatusAlarm       TRAP-TYPE
        ENTERPRISE      svnode
        VARIABLES       {       
				lastSequenceNumber,
				nodeGrpName,
                                nodeGrpNetName,
                                frpStatus
                        }
        DESCRIPTION     "This trap is generated whenever an ObjectAlarm
			Status message is received containing the frpStatus."
	::= 2

connStatusAlarm     TRAP-TYPE
        ENTERPRISE      svnode
        VARIABLES       {       
				lastSequenceNumber,
				nodeGrpName,
				nodeGrpNetName,
                                connStatus,
				connABitStatus
                        }
        DESCRIPTION     "This trap is generated whenever an ObjectAlarm
			Status message is received containing the connStatus."
        ::= 3


filteredLogRecord	TRAP-TYPE
	ENTERPRISE	svplus
	VARIABLES	{ 	
				lastSequenceNumber,
				logIndex,
				logNetwork,
				logNodeName,
				logGmtDate,
				logSeverity,
				logMsg
			}
	DESCRIPTION	"The 'filteredLogRecord' trap is generated by
			the StrataView system whenever an entry in the
			eventFilterTable matches a log record that is
			added to the StrataView database."
	::= 4

-- END
--
--	Stratacom StrataView Service MIBs
--
--      $RCSfile: SV+Service.mib,v $
--      $Revision: 1.1.4.35 $
--      $Date: 1996/07/25 22:12:54 $
--
--      Consolidated MIB for port and connection services 
--
--      Revision: 8/6/95
--          Corrected the errors pointed out by AT&T.
--
--	    changed name of connTable to connectionTable 
--	    because of conflict with Stratacom Node mib.
--
--          Added line number as an index 
--          into the frEnptPtTable to support AXIS nodes.
--

-- STRATACOM-STRATAVIEW-SVPLUS-MIB
-- DEFINITIONS ::= BEGIN

-- IMPORTS 
--     enterprises, Counter, Gauge, TimeTicks, IpAddress  FROM RFC1155-SMI
--     TRAP-TYPE                           FROM RFC-1215
--     OBJECT-TYPE                         FROM RFC-1212
--     DisplayString                       FROM RFC1213-MIB;

-- stratacom	OBJECT IDENTIFIER ::= { enterprises 351 }
-- svplus		OBJECT IDENTIFIER ::= { stratacom 1 } 
connSvc		OBJECT IDENTIFIER ::= { stratacom 3 }
portSvc		OBJECT IDENTIFIER ::= { stratacom 4 }
-- rtm		OBJECT IDENTIFIER ::= { stratacom 120 } 
--
--
-- This MIB defines tables and attributes creating and maintaining 
-- connections and their end points.  A connection is defined as end to end;
-- each end designated as an user end point, one of which is called 'local'
-- and other is called 'remote'.  The end to end connection consists of 
-- one or more connection segments which are defined in the segment 
-- table.  A key attribute controlling the existence of entries in each of
-- the tables is the 'RowStatus' as defined in RFC 1443 - Textual 
-- Conventions for version 2 of the Simple Network Management Protocol 
-- (SNMPv2).  However, since this MIB is implemented using version 1, 
-- RowStatus is defined below and RFC1443 return error code mappings are:
-- 
--     'inconsistant value' or 'wrong value' then return 'badValue'; 
--     'noSuchObject' or 'noSuchInstance' then return 'noSuchName' 
-- 
-- To create a connection:
-- 
-- 1. The manager creates the entries in the respective end point 
--    table(s)  and the connectionTable, with RowStatus is set to 
--    'createAndGo'.  The required attributes for end points as well as 
--    connectionEntry also can be specified in the same SET request.
--    Note that value 0 must be used as connectionIndex 
--    for creating entry in the connectionTable.
--    [ The actual index is internally generated by Proxy ] -- 
-- 2. Once Step-2 is successful,
--    segmentTable for each connection segment of the connection will exist.  
--    This may consist of 1 or more segments 
--    depending on the underlying network configuration.
--    Note that segment table is read-only.
--
-- Table Entry Deletion
--
-- To delete an entry in any of the tables, set the rowStatus to 
-- 'destroy'. Deleting the connectionEntry will delete all corresponding 
-- entries in the associated EndPoint and Segment Tables.
-- 
-- A protocol specific end point may be deleted only if it is not associated
-- with any connectionEntry or segmentEntry. 
-- 

-- RowStatus 	::= INTEGER {
-- 					active(1),
-- 					createAndGo(4),
-- 					destroy(6)
-- 				}
				
				
connMibUpTime OBJECT-TYPE
    SYNTAX	TimeTicks
    ACCESS	read-only
    		-- C-ACCESS-FUNC connMibUpTime
    STATUS	mandatory
    DESCRIPTION "the equivalent of sysUpTime for this MIB, its the elapsed time 
		since the management entity supporting this mib is started.  If the 
		entity is the same as that supporting MIB II sysUpTime than 
		this attribute is the same as sysUpTime."
	::= { connSvc 1 }


connAvailIndex OBJECT-TYPE
    SYNTAX	INTEGER (0..0)
    ACCESS	read-only
    		-- C-ACCESS-FUNC connAvailIndex
    STATUS	mandatory
    DESCRIPTION "This object is not required any more because
                 now connectionIndex is internally generated by the Proxy itself.
                 User is required to use connectionIndex=0 for adding 
                 connections. This object is kept for the backward compatibilty.
                 GET on this object always returns 0"
	::= { connSvc 2 }


connectionTable OBJECT-TYPE 
    SYNTAX	SEQUENCE OF ConnectionEntry
    ACCESS	not-accessible
    STATUS	mandatory
    DESCRIPTION "A List of Connection Virtual Circuit Entries"
	::= { connSvc 3 }

connectionEntry OBJECT-TYPE
    SYNTAX	ConnectionEntry
    ACCESS	not-accessible
    STATUS	mandatory
    DESCRIPTION	"A General Connection Entry"
    INDEX	{ connectionIndex }
			-- C-NEXT-FUNC	NextConnEntry
	::= { connectionTable 1 }

ConnectionEntry ::=
	SEQUENCE {
		connectionIndex				INTEGER,
		connectionLocalEndPt		OBJECT IDENTIFIER,
		connectionRemoteEndPt		OBJECT IDENTIFIER,
	
		connectionOpStatus			INTEGER,
		connectionAdminStatus		INTEGER,
		connectionRowStatus			INTEGER,
	
		connectionTrkAvoidType		INTEGER,
		connectionTrkAvoidZCS		INTEGER,
		connectionClassOfService	INTEGER,
		connectionForesight			INTEGER,
	
		connectionCurrRouteDesc		DisplayString,
		connectionPrefRouteDesc		DisplayString,
		connRouteMaster				DisplayString,
	
		connectionLocOSpacePkts		INTEGER,
		connectionLocOSpaceBdaCmax	INTEGER,
		connectionLocOSpaceBdbCmax	INTEGER,
		connectionRemOSpacePkts		INTEGER,
		connectionRemOSpaceBdaCmax	INTEGER,
		connectionRemOSpaceBdbCmax	INTEGER,
		connectionTestType		INTEGER,
		connectionTestResult		INTEGER,
		connectionAbitStatus		INTEGER,
		connectionType			INTEGER,
		connectionLocalStr		DisplayString,
		connectionRemoteStr		DisplayString
}

connectionIndex OBJECT-TYPE
    SYNTAX	INTEGER (0..2147483647)
    ACCESS	read-only
			-- C-ACCESS-FUNC connIndex
			-- C-LOCATOR-FUNC LocateConnEntry
    STATUS	mandatory
    DESCRIPTION "A unique value greater than 0 for each entry in the table. 
		The value assigned must remain constant at least from
		one reinitialization of the managment entity and the next.
                Special value 0 must be used for adding new rows in the table.
                The actual index will be generated internally by the Proxy."
	::= { connectionEntry 1 }

connectionLocalEndPt OBJECT-TYPE
    SYNTAX	OBJECT IDENTIFIER
    ACCESS	read-write
			-- C-ACCESS-FUNC connLocalEndPt
			-- C-LOCATOR-FUNC LocateConnEntry
    STATUS	mandatory
    DESCRIPTION "The object identifier of the 1st attribute of the end point 
		 in the associated protocol specific end point table."
	::= { connectionEntry 2 }

connectionRemoteEndPt OBJECT-TYPE
    SYNTAX	OBJECT IDENTIFIER
    ACCESS	read-write
			-- C-ACCESS-FUNC connRemoteEndPt
			-- C-LOCATOR-FUNC LocateConnEntry
    STATUS	mandatory
    DESCRIPTION "The object identifier of the 1st attribute of the end point  
		in the associated protocol specific end point table. "
	::= { connectionEntry 3 }

connectionAdminStatus OBJECT-TYPE
	SYNTAX	INTEGER {
				inactive(1),
				active(2),
				testing(3)
			}
	ACCESS	read-write
    		-- C-ACCESS-FUNC connAdminStatus
    		-- C-LOCATOR-FUNC	LocateConnEntry
	STATUS	mandatory
	DESCRIPTION	" Administrative status of the connection.  This attribute
		may be set to 'testing' only when connectionOpStatus has the value
		'clear'."
	::= { connectionEntry 4 }

connectionOpStatus OBJECT-TYPE
    SYNTAX	INTEGER {
				inactive(1),
				clear(2),
				fail(3),
				down(4),
				incomplete(5)
			}
    ACCESS	read-only
			-- C-ACCESS-FUNC connOpStatus
			-- C-LOCATOR-FUNC LocateConnEntry
    STATUS	mandatory
    DESCRIPTION "A operation status of the connection.  'incomplete' indicates
		that the some segments of the connection exist but others may
		be in an unknown or non-existant state."
	::= { connectionEntry 5 }


connectionRowStatus OBJECT-TYPE
    SYNTAX	INTEGER {
					active(1),
					createAndGo(4),
					destroy(6)
				}
    ACCESS	read-write
			-- C-ACCESS-FUNC connRowStatus
			-- C-LOCATOR-FUNC LocateConnEntry
    STATUS	mandatory
    DESCRIPTION "To create an entry in this table, set the value of this
                 object to 'createAndGo'.
                 To delete the connection and the corresponding end points
                 set the value to 'destroy'.
                 setting the value to active will result in bad value.
                 Other required parameters can also be set in the same request"
	::= { connectionEntry 6 }

connectionTrkAvoidType OBJECT-TYPE
    SYNTAX	INTEGER {
				none(1),
				satellite(2),
				terrestrial(3)
			}
    ACCESS	read-write
			-- C-ACCESS-FUNC connTrkAvoidType
			-- C-LOCATOR-FUNC LocateConnEntry
    STATUS	mandatory
    DESCRIPTION "User selectable types of trunks to avoid for the
		transfer of data.  Current choices are to avoid
		satellite links, terrestrial links, or to not avoid
		any specific type of link."
	DEFVAL	{ none }
	::= { connectionEntry 7 }

connectionTrkAvoidZCS OBJECT-TYPE
    SYNTAX	INTEGER {
				false(1),
				true(2)
			}
    ACCESS	read-write
			-- C-ACCESS-FUNC connTrkAvoidZCS
			-- C-LOCATOR-FUNC LocateConnEntry
    STATUS	mandatory
    DESCRIPTION "Flag to force the connection to avoid trunks with zero
		code suppression (ZCS). "
	DEFVAL	{ false }
	::= { connectionEntry 8 }

connectionForesight OBJECT-TYPE
	SYNTAX      INTEGER {
					enable(1),
					disable(2)
				}
	ACCESS      read-write
			-- C-ACCESS-FUNC connForesight
			-- C-LOCATOR-FUNC LocateConnEntry
	STATUS      mandatory
	DESCRIPTION "Flag to enable/disable foresight."
	DEFVAL	{ disable }
	::= { connectionEntry 9 }

connectionClassOfService OBJECT-TYPE
    SYNTAX	INTEGER (0..15)
    ACCESS	read-write
			-- C-ACCESS-FUNC connClassOfService
			-- C-LOCATOR-FUNC LocateConnEntry
    STATUS	mandatory
    DESCRIPTION "A class of service for this connection.  The lower
		the class value, the higher the routing priority
		of the connection."
    DEFVAL { 0 }
	::= { connectionEntry 10 }
 
connectionCurrRouteDesc OBJECT-TYPE
    SYNTAX	DisplayString (SIZE(0..256))
    ACCESS	read-only
			-- C-ACCESS-FUNC connCurrRouteDesc
			-- C-LOCATOR-FUNC LocateConnEntry
    STATUS	mandatory
    DESCRIPTION "A description of the current route.
		Descriptor gives information about the domain, nodename, slot,
		and possibly a port for each hop in the route.  For
		example, Node1 15 - 15Node2 is a valid route specifying
		a terrestrial link between Node1 slot 15 and Node2
		slot 15.

                 The following describes the general format
                 for connectionCurrRouteDesc:

                     (<node-name>.<TRK>[.0])* - <node-name>
                     (<node-name>.<slot.port>)* - <node-name>

		Some more valid descriptions are:
                     1) Node1.15.1 - Node2.13.1 - Node3
                     2) Node1.15.1-Node2.13.1-Node3
                     3) Node1.15   - Node2.12   - Node3.15   - Node4
                     4) Node1.15.0 - Node2.12.0 - Node3.15.0 - Node4
                     5) Node2

                     NOTE: a> (...)* notation means the description inside
                              parenthesis may repeat any number of times,
                              only limited by the total length which is 255
                              and the [...] notation signifies that it is
                              optional.
                           b> 1) & 2) are equivalent so are 3) & 4).
		"
        ::= { connectionEntry 11 }

connectionPrefRouteDesc OBJECT-TYPE
    SYNTAX	DisplayString (SIZE(0..256))
    ACCESS	read-write
			-- C-ACCESS-FUNC connPrefRouteDesc
			-- C-LOCATOR-FUNC LocateConnEntry
    STATUS	mandatory
    DESCRIPTION "Descriptor of the preferred route (all hops specified).
                 Descriptor gives information about the domain, nodename, slot,
                 and possibly a port for each hop in the route.  For example,
                 Node1.15 - Node2 is a valid route specifying a
                 terrestrial link between Node1 slot 15 and Node2.

                 The following describes the general format
                 for connectionPrefRouteDesc:

                     (<node-name>.<TRK>[.0])* - <node-name>
                     (<node-name>.<slot.port>)* - <node-name>

                 Some more valid descriptions are:
                     1) Node1.15.1 - Node2.13.1 - Node3
                     2) Node1.15.1-Node2.13.1-Node3
                     3) Node1.15   - Node2.12   - Node3.15   - Node4
                     4) Node1.15.0 - Node2.12.0 - Node3.15.0 - Node4
                     5) Node2

                     NOTE: a> (...)* notation means the description inside
                              parenthesis may repeat any number of times,
                              only limited by the total length which is 255
                              and the [...] notation signifies that it is
                              optional.
                           b> 1) & 2) are equivalent so are 3) & 4).
		"
    DEFVAL	{ ''h }
	::= { connectionEntry 12 }

connRouteMaster OBJECT-TYPE
    SYNTAX	DisplayString (SIZE(0..10))
    ACCESS	read-only
			-- C-ACCESS-FUNC connRouteMaster
			-- C-LOCATOR-FUNC LocateConnEntry
    STATUS	mandatory
    DESCRIPTION "The node name of the route master."  	::= { connectionEntry 13 }

connectionLocOSpacePkts OBJECT-TYPE
    SYNTAX      INTEGER (-1..2147483647)
    ACCESS      read-only
    		-- C-ACCESS-FUNC connLocOSpacePkts
			-- C-LOCATOR-FUNC LocateOSpace
    STATUS      mandatory
    DESCRIPTION "This variable provides the minimum packet load 
                 available on the mandatory path of this connection 
                 in local->remote direction. This variable
                 is determined by comparing available bandwidth on
                 every trunk on which the connection is mandatoryly 
                 routed and reporting the minimum available bandwidth. 
                 For interdomain connections this value represents
                 available bandwidth through all domains. This variable
                 is meaningful for routed connections only. 
                 Value (-1) is returned in case of internal errors and
                       (0)  is returned for DAX connections.
                 These values are returned in packets per second."
	::= { connectionEntry 14 }

connectionLocOSpaceBdaCmax OBJECT-TYPE
    SYNTAX      INTEGER (-1..65534)
    ACCESS      read-only
    		-- C-ACCESS-FUNC connLocOSpaceBdaCmax
			-- C-LOCATOR-FUNC LocateOSpace
    STATUS      mandatory
    DESCRIPTION "This variable provides the minimum BData A Cmax 
                 available on the mandatory path of this connection 
                 in local->remote direction. This variable
                 is determined by comparing available BData A Cmax on
                 every trunk on which the connection is mandatoryly 
                 routed and reporting the minumim available.  
                 For interdomain connections this value represents
                 available BData A Cmax through all domains. This variable
                 is meaningful for routed connections only. 
                 Value (-1) is returned in case of internal errors and
                       (0)  is returned for DAX connections.
                 These values are returned in bytes."
	::= { connectionEntry 15 }

connectionLocOSpaceBdbCmax OBJECT-TYPE
    SYNTAX      INTEGER (-1..65534)
    ACCESS      read-only
    		-- C-ACCESS-FUNC connLocOSpaceBdbCmax
			-- C-LOCATOR-FUNC LocateOSpace
    STATUS      mandatory
    DESCRIPTION "This variable provides the minimum BData B Cmax 
                 available on the mandatory path of this connection 
                 in local->remote direction. This variable
                 is determined by comparing available BData B Cmax on
                 every trunk on which the connection is mandatoryly 
                 routed and reporting the minumim available.  
                 For interdomain connections this value represents
                 available BData B Cmax through all domains. This variable
                 is meaningful for routed connections only. 
                 Value (-1) is returned in case of internal errors and
                       (0)  is returned for DAX connections.
                 These values are returned in bytes."
	::= { connectionEntry 16 }

connectionRemOSpacePkts OBJECT-TYPE
    SYNTAX      INTEGER (-1..2147483647)
    ACCESS      read-only
    		-- C-ACCESS-FUNC connRemOSpacePkts
			-- C-LOCATOR-FUNC LocateOSpace
    STATUS      mandatory
    DESCRIPTION "This variable provides the minimum packet load
                 available on the mandatory path of this connection 
                 in remote->local direction. This variable
                 is determined by comparing available bandwidth on
                 every trunk on which the connection is mandatoryly
                 routed and reporting the minumim available bandwidth.
                 For interdomain connections this value represents
                 available bandwidth through all domains. This variable
                 is meaningful for routed connections only.
                 Value (-1) is returned in case of internal errors and
                       (0)  is returned for DAX connections.
                 These values are returned in packets per second."
        ::= { connectionEntry 17 }

connectionRemOSpaceBdaCmax OBJECT-TYPE
    SYNTAX      INTEGER (-1..65534)
    ACCESS      read-only
    		-- C-ACCESS-FUNC connRemOSpaceBdaCmax
			-- C-LOCATOR-FUNC LocateOSpace
    STATUS      mandatory
    DESCRIPTION "This variable provides the minimum BData A Cmax 
                 available on the mandatory path of this connection 
                 in remote->local direction. This variable
                 is determined by comparing available BData A Cmax on
                 every trunk on which the connection is mandatoryly 
                 routed and reporting the minumim available.  
                 For interdomain connections this value represents
                 available BData A Cmax through all domains. This variable
                 is meaningful for routed connections only. 
                 Value (-1) is returned in case of internal errors and
                       (0)  is returned for DAX connections.
                 These values are returned in bytes."
	::= { connectionEntry 18 }

connectionRemOSpaceBdbCmax OBJECT-TYPE
    SYNTAX      INTEGER (-1..65534)
    ACCESS      read-only
    		-- C-ACCESS-FUNC connRemOSpaceBdbCmax
			-- C-LOCATOR-FUNC LocateOSpace
    STATUS      mandatory
    DESCRIPTION "This variable provides the minimum BData B Cmax 
                 available on the mandatory path of this connection 
                 in remote->local direction. This variable
                 is determined by comparing available BData B Cmax on
                 every trunk on which the connection is mandatoryly 
                 routed and reporting the minumim available.  
                 For interdomain connections this value represents
                 available BData B Cmax through all domains. This variable
                 is meaningful for routed connections only. 
                 Value (-1) is returned in case of internal errors and
                       (0)  is returned for DAX connections.
                 These values are returned in bytes."
	::= { connectionEntry 19 }


connectionTestType OBJECT-TYPE
    SYNTAX	INTEGER {
			continuity(1),
			delay(2),
			none(255)
		}
    ACCESS	read-write
    		-- C-ACCESS-FUNC connTestType
    		-- C-LOCATOR-FUNC	LocateConnEntry
    STATUS	mandatory
    DESCRIPTION "Specifies the type of test to be conducted on this connection. 
		The test is executed when both this attribute is set to the appropriate 
		test and connectionAdminStatus is SET to 'testing'.
		
		The 'continuity' test verifies continuity.

		The 'delay' test on successful completion sets the delay in msecs in
		connectionTestResult.
		
		This attribute may be set only when connectionOpStatus has the value
		'clear', 'fail', or 'down'."
	DEFVAL { none }
	::= 	{ connectionEntry 20 }

connectionTestResult OBJECT-TYPE
    SYNTAX	INTEGER 
    ACCESS	read-only
    		-- C-ACCESS-FUNC connTestResult
    		-- C-LOCATOR-FUNC	LocateConnEntry
    STATUS	mandatory
     DESCRIPTION "This object holds the result of an executed connection
		test.

		If a continuity test is executed, this object contains the
		value 0 if successful, or -2 if failed.

		If a delay test successfully executed, this object will indicate
		the round trip delay (in milliseconds) for the connection. If
		the delay test failed this object contains the value -2.

		If no test has been executed, or the connectionTestType is SET,
		then this object will return the value -1."
	::= 	{ connectionEntry 21 }


connectionAbitStatus OBJECT-TYPE
    SYNTAX	INTEGER {
				clear(1),
				fail(2)
			}
    ACCESS	read-only
			-- C-ACCESS-FUNC connAbitStatus
			-- C-LOCATOR-FUNC LocateConnEntry
    STATUS	mandatory
    DESCRIPTION "A-bit status of the connection."
	::= { connectionEntry 22 }


connectionType OBJECT-TYPE
    SYNTAX	INTEGER {
				fr(1),
				atm(2),
				atm-fr(3),
				unknown(20)
			}
    ACCESS	read-only
			-- C-ACCESS-FUNC connType
			-- C-LOCATOR-FUNC LocateConnEntry
    STATUS	mandatory
    DESCRIPTION "Connection Type.
		fr indicates Framerelay to Framerelay connection.
		atm indicates Atm to Atm connection and
                atm-fr indicates Atm to FrameRelay connection.
		unknown indicates incomplete connection."
	::= { connectionEntry 23 }

connectionLocalStr OBJECT-TYPE
    SYNTAX	DisplayString
    ACCESS	read-only
			-- C-ACCESS-FUNC connLocalStr
			-- C-LOCATOR-FUNC LocateConnEntry
    STATUS	mandatory
    DESCRIPTION "The Local EndPt information in string format.
                 i.e., the instance information of the EndPt.
                 Framerelay Endpt is displayed as:
                     node.shelf.slot.line.port.dlci
                 Atm Endpt is displayed as:
                     node.shelf.slot.port.vpi.vci
                 shelf is 0 for Endpt on a routing node."  	::= { connectionEntry 24 }

connectionRemoteStr OBJECT-TYPE
    SYNTAX	DisplayString
    ACCESS	read-only
			-- C-ACCESS-FUNC connRemoteStr
			-- C-LOCATOR-FUNC LocateConnEntry
    STATUS	mandatory
    DESCRIPTION "The Remote EndPt information in string format.
                 i.e., the instance information of the EndPt.
                 Framerelay Endpt is displayed as:
                     node.shelf.slot.line.port.dlci
                 Atm Endpt is displayed as:
                     node.shelf.slot.port.vpi.vci
                 shelf is 0 for Endpt on a routing node."  	::= { connectionEntry 25 }


--
-- The Frame Relay end point table.
--
-- Each connection (virtual circuit or PVC) end-point describes the 
-- particular characteristics of the end-point.  Such information 
-- as bandwidth parameters are maintained in the end-point.
--
frEndPtTable OBJECT-TYPE 
    SYNTAX      SEQUENCE OF FrEndPtEntry
    ACCESS      not-accessible
    STATUS      mandatory
    DESCRIPTION "A List of frame relay virtual circuit end points"
	::= { connSvc 4 }

frEndPtEntry OBJECT-TYPE
    SYNTAX      FrEndPtEntry
    ACCESS      not-accessible
    STATUS      mandatory
    DESCRIPTION "A frame relay end point Entry"
    INDEX   { frEndPtNodeName, frEndPtIfShelf, frEndPtSlot,
			  frEndPtLine, frEndPtPort, frEndPtDlci }
			  -- C-NEXT-FUNC	NextFrEntry
	::= { frEndPtTable 1 }


FrEndPtEntry ::= 
    SEQUENCE {
		frEndPtNodeName		DisplayString,
		frEndPtIfShelf		DisplayString,
		frEndPtSlot			INTEGER,
		frEndPtLine			INTEGER,
		frEndPtPort			INTEGER,
		frEndPtDlci			INTEGER,

		frEndPtConnIndex	INTEGER,
	
		frEndPtAdminStatus	INTEGER,
		frEndPtOpStatus		INTEGER,
		frEndPtRowStatus	INTEGER,
	
		frEndPtMIR			INTEGER,
		frEndPtCIR			INTEGER,
		frEndPtBc			INTEGER,
		frEndPtBe			INTEGER,
		frEndPtVcQSize		INTEGER,
		frEndPtPIR			INTEGER,
		frEndPtCMAX			INTEGER,
		frEndPtEcnQSize		INTEGER,
		frEndPtQIR			INTEGER,
		frEndPtPercUtil		INTEGER,
		frEndPtPriority		INTEGER,
	
		frEndPtInitialBurstSize		INTEGER,
		frEndPtDeTagging			INTEGER,
		frEndPtIngressDeThreshold	INTEGER,
		frEndPtEgressQDepth			INTEGER,
		frEndPtEgressDeThreshold	INTEGER,
		frEndPtEgressEcnThreshold	INTEGER,
		frEndPtEgressQSelect		INTEGER,
		
		frEndPtLpbkState	INTEGER,
		frEndPtType			INTEGER,
		frEndPtchanType        		INTEGER,
		frEndPtchanFECNconfig  		INTEGER,
		frEndPtchanDEtoCLPmap  		INTEGER,
		frEndPtchanCLPtoDEmap  		INTEGER

}

frEndPtNodeName OBJECT-TYPE
    SYNTAX      DisplayString (SIZE(1..10))
    ACCESS      read-write
    		-- C-ACCESS-FUNC	FrEndPtNodeName
    		-- C-LOCATOR-FUNC LocateFrEntry
    STATUS      mandatory
    DESCRIPTION "The node name."
	::= { frEndPtEntry 1 }

frEndPtIfShelf OBJECT-TYPE
    SYNTAX      DisplayString (SIZE(0..10))
    ACCESS      read-write
    		-- C-ACCESS-FUNC	FrEndPtIfShelf
    		-- C-LOCATOR-FUNC LocateFrEntry
    STATUS      mandatory
    DESCRIPTION "String identifying the shelf. This is a null string
		for end points which do not have a shelf name."
	::= { frEndPtEntry 2 }

frEndPtSlot OBJECT-TYPE
    SYNTAX	INTEGER (1..64)
    ACCESS	read-write
    		-- C-ACCESS-FUNC	FrEndPtSlot
    		-- C-LOCATOR-FUNC LocateFrEntry
    STATUS	mandatory
    DESCRIPTION	"Slot Number."
	::= { frEndPtEntry 3 }

frEndPtLine OBJECT-TYPE
    SYNTAX	INTEGER (0..8)
    ACCESS	read-write
    		-- C-ACCESS-FUNC	FrEndPtLine
    		-- C-LOCATOR-FUNC LocateFrEntry
    STATUS	mandatory
    DESCRIPTION	"Line Number. If no line number is associated with the 
    	end point then this value is 0."
	::= { frEndPtEntry 4 }

frEndPtPort OBJECT-TYPE
    SYNTAX	INTEGER (1..64)
	ACCESS	read-write
			-- C-ACCESS-FUNC	FrEndPtPort
		-- C-LOCATOR-FUNC LocateFrEntry
    STATUS	mandatory
    DESCRIPTION	"Port Number. "
	::= { frEndPtEntry 5 }

frEndPtDlci OBJECT-TYPE
    SYNTAX	INTEGER	(0..65535)
    ACCESS	read-write
    		-- C-ACCESS-FUNC	FrEndPtDlci
    		-- C-LOCATOR-FUNC LocateFrEntry
    STATUS	mandatory
    DESCRIPTION	"DLCI."
	::= { frEndPtEntry 6 }

frEndPtConnIndex OBJECT-TYPE
    SYNTAX	INTEGER (0..2147483647)
    ACCESS	read-only
			-- C-ACCESS-FUNC	FrEndPtConnIndex
			-- C-LOCATOR-FUNC LocateFrEntry
    STATUS	mandatory
    DESCRIPTION "If the value of this object is greater than 0 then it is
    	the index identifying the associated connectionEntry.
        Value 0 indicates dangling end point."
	::= { frEndPtEntry 7 }

frEndPtAdminStatus OBJECT-TYPE
	SYNTAX	INTEGER {
				inactive(1),
				active(2),
				testing(3)
			}
	ACCESS	read-write
    		-- C-ACCESS-FUNC	FrEndPtAdminStatus
    		-- C-LOCATOR-FUNC	LocateFrStatus
	STATUS	mandatory
	DESCRIPTION	" Administrative status of the end point."
	::= { frEndPtEntry 8 }

frEndPtOpStatus OBJECT-TYPE
	SYNTAX      INTEGER {
					inactive(1),
					clear(2),
					fail(3),
					down(4),
					alarm(16)
				}
    ACCESS      read-only
    		-- C-ACCESS-FUNC	FrEndPtOpStatus
    		-- C-LOCATOR-FUNC LocateFrEntry
    STATUS      mandatory
    DESCRIPTION " Operational Status of the end point.
    
    	  The value 'alarm' may only occur with and end point whose
    	  frEndPtCardType = 'frsm'.  When frEndPtOpStatus has the value
    	  'alarm' then either the slot, the line, or the port containing this
    	  endpoint has an alarm."
	::= { frEndPtEntry 9 }

frEndPtRowStatus OBJECT-TYPE
    SYNTAX      INTEGER {
					active(1),
					createAndGo(4),
					destroy(6)
				}
    ACCESS      read-write
    		-- C-ACCESS-FUNC	FrEndPtRowStatus
    		-- C-LOCATOR-FUNC LocateFrEntry
    STATUS      mandatory
    DESCRIPTION "The manager must set this to 'createAndGo' when creating
		a new entry.  Other end point parameters also can be set
		in the same request.

		'destroy' is only supported when the end point is not part
		of an end to end connection.
                setting the value to active will result in bad value."
	::= { frEndPtEntry 10 }
 
frEndPtMIR OBJECT-TYPE
    SYNTAX      INTEGER (2400..2048000)
    ACCESS      read-write
    		-- C-ACCESS-FUNC	FrEndPtMIR
    		-- C-LOCATOR-FUNC LocateFrEntry
    STATUS      mandatory
    DESCRIPTION "The minimum transmit bandwidth (MIR) parameter
                 (in bits per second) for this  end-point. This object
		 has the relationship MIR <= CIR.
		 
		 This attribute can only be set to values evenly divisable by 100."
	DEFVAL { 9600 }
	::= { frEndPtEntry 11 }

frEndPtCIR OBJECT-TYPE
    SYNTAX      INTEGER (2400..2048000)
    ACCESS      read-write
    		-- C-ACCESS-FUNC	FrEndPtCIR
    		-- C-LOCATOR-FUNC LocateFrEntry
    STATUS      mandatory
    DESCRIPTION "The value of this object is equal to the committed
                 information rate (CIR) parameter (in bits
                 per second) for this  end-point.  This object holds
		 the relationship MIR < = CIR <= QIR.
		 
		 This attribute can only be set to values evenly divisable by 100."
	DEFVAL { 9600 }
	::= { frEndPtEntry 12 }

frEndPtBc OBJECT-TYPE
    SYNTAX      INTEGER (1..65535)
    ACCESS      read-write
    		-- C-ACCESS-FUNC	FrEndPtBc
    		-- C-LOCATOR-FUNC LocateFrEntry
    STATUS      mandatory
    DESCRIPTION "The value of this object is equal to the committed
                 burst size (Bc) parameter (in bytes) for
                 this  end-point. 
                 
                 When frEndPtCardType is 'fr', this attribute is 
                 calculated as follows and should NOT be set:
                 	    Bc =  (VcQSize/(1 - MIR/port access rate)).
                 	  
                 When frEndPtCardType is 'frsm' the value is NOT calculated
                 and is assigned the default value unless it is set."
    DEFVAL { 5100 }
	::= { frEndPtEntry 13 }

frEndPtBe OBJECT-TYPE
    SYNTAX      INTEGER (0..65535)
    ACCESS      read-write
    		-- C-ACCESS-FUNC	FrEndPtBe
    		-- C-LOCATOR-FUNC LocateFrEntry
    STATUS      mandatory
    DESCRIPTION "The value of this object is equal to the excess
                 burst size (Be) parameter (in bytes) for
                 this  end-point. 
                 
                 When frEndPtCardType is 'fr', this attribute is 
                 calculated as follows and should NOT be set:
                 	    Be = Bc * (PIR/MIR - 1)
                 	  
                 When frEndPtCardType is 'frsm' the value is NOT calculated
                 and is assigned the default value unless it is set."
    DEFVAL { 5100 }
	::= { frEndPtEntry 14 }

frEndPtVcQSize OBJECT-TYPE
    SYNTAX      INTEGER (1..65535)
    ACCESS      read-write
    		-- C-ACCESS-FUNC	FrEndPtVcQSize
    		-- C-LOCATOR-FUNC LocateFrEntry
    STATUS      mandatory
    DESCRIPTION "The value of this object is the maximum queue depth
                 (in bytes) for this  end-point."
	DEFVAL		{ 65535 }
	::= { frEndPtEntry 15 }

frEndPtPIR OBJECT-TYPE
    SYNTAX      INTEGER (2400..2048000)
    ACCESS      read-write
    		-- C-ACCESS-FUNC	FrEndPtPIR
    		-- C-LOCATOR-FUNC LocateFrEntry
    STATUS      mandatory
    DESCRIPTION "The peak transmit bandwidth (PIR) parameter
                 (in bits per second) for this  end-point.
		 
		 This attribute can only be set to values evenly divisable by 100."
	DEFVAL { 9600 }
	::= { frEndPtEntry 16 }

frEndPtCMAX OBJECT-TYPE
    SYNTAX      INTEGER (0..255)
    ACCESS      read-write
    		-- C-ACCESS-FUNC	FrEndPtCMax
    		-- C-LOCATOR-FUNC LocateFrEntry
    STATUS      mandatory
    DESCRIPTION "The maximum credits that can be accrued for this
                 end-point. This is not applicable for AXIS-frsm channels."
    DEFVAL { 10 }
	::= { frEndPtEntry 17 }

frEndPtEcnQSize OBJECT-TYPE
    SYNTAX      INTEGER (0..65535)
    ACCESS      read-write
    		-- C-ACCESS-FUNC	FrEndPtEcnQSize
    		-- C-LOCATOR-FUNC LocateFrEntry
    STATUS      mandatory
    DESCRIPTION "The threshold setting used by the explicit congestion
                 notification feature for this  end-point's
                 transmit queue. This value is specified in bytes.
                 When the frEndPtVcQSize value exceeds this value
                 then the FECN bit will be set in all frames transmitted
                 to the remote  end-point."
    DEFVAL { 6553 }
	::= { frEndPtEntry 18 }

frEndPtQIR OBJECT-TYPE
    SYNTAX      INTEGER (2400..2048000)
    ACCESS      read-write
			-- C-ACCESS-FUNC	FrEndPtQIR
			-- C-LOCATOR-FUNC LocateFrEntry
    STATUS      mandatory
    DESCRIPTION "The transmit quiescent information rate (QIR) parameter
                 (in bits per second) for this  end-point.
                 This value has the relationship CIR <= QIR <= PIR.
		 
		 This attribute can only be set to values evenly divisable by 100."
    DEFVAL { 9600 }
	::= { frEndPtEntry 19 }

frEndPtPercUtil OBJECT-TYPE
    SYNTAX      INTEGER (0..100)
    ACCESS      read-write
    		-- C-ACCESS-FUNC	FrEndPtPercUtil
    		-- C-LOCATOR-FUNC LocateFrEntry
    STATUS      mandatory
    DESCRIPTION "The value of this object is equal to the channel
                 percentage utilization setting for this  end-point.
                 This is the expected long-term utilization of the
                 channel by this  end-point."
    DEFVAL { 100 }
	::= { frEndPtEntry 20 }

frEndPtPriority OBJECT-TYPE
    SYNTAX      INTEGER {
					low(1),
					high(2)
				}
    ACCESS      read-write
    		-- C-ACCESS-FUNC	FrEndPtPriority
    		-- C-LOCATOR-FUNC LocateFrEntry
    STATUS      mandatory
    DESCRIPTION "Priority for the Egress End.
                 The value of this object determines the priority
                 that is given to the data carried by this .  If
                 set to low, then the data is given the standard
                 priority, and if set to high, the  data will be
                 given a higher priority.  Higher priority data
                 is placed at the beginning of the port's queues.

                 NOTE:
                 For a single segment connection(IPX-Routing to IPX-Routing),
                 SET on frEndPtPriority is allowed for the local endpt only.
                 i.e., SET on frEndPtPriority on the remote endpt is ignored.
                 frEndPtPriority for the remote endpt gets the same value as
                 that of the local endpt.

                 This is not applicable for AXIS-frsm channels."
    DEFVAL { low }
	::= { frEndPtEntry 21 }

frEndPtInitialBurstSize OBJECT-TYPE
    SYNTAX	INTEGER (0..65535)
    ACCESS	read-write
    		-- C-ACCESS-FUNC	FrEndPtInitialBurstSize
    		-- C-LOCATOR-FUNC	LocateFrEntry
    STATUS	mandatory
    DESCRIPTION "Initial burst size in bytes.  
                 Note that InitialBurstSize should be less than or equal to Bc.
                 This is valid for frEndPtType of 'frsm'." 
    DEFVAL	{ 5100 }
	::= 	{ frEndPtEntry 22 }

frEndPtDeTagging OBJECT-TYPE
    SYNTAX	INTEGER {
    			enable(1),
    			disable(2)
    		}
    ACCESS	read-write
    		-- C-ACCESS-FUNC	FrEndPtDeTagging
    		-- C-LOCATOR-FUNC	LocateFrEntry
    STATUS	mandatory
    DESCRIPTION "Enable/disable DE tagging in the ingress direction only. 
    		This is valid for frEndPtType of 'frsm'." 
    DEFVAL	{ disable }
	::= 	{ frEndPtEntry 23 }

frEndPtIngressDeThreshold OBJECT-TYPE
    SYNTAX	INTEGER (0..65535)
    ACCESS	read-write
    		-- C-ACCESS-FUNC	FrEndPtDeThreshold
    		-- C-LOCATOR-FUNC	LocateFrEntry
    STATUS	mandatory
    DESCRIPTION "Ingress threshold at which deletion occurs based on DE.
    		This is valid for frEndPtType of 'frsm'." 
    DEFVAL	{ 32768 }
	::= 	{ frEndPtEntry 24 }


frEndPtEgressQDepth OBJECT-TYPE
    SYNTAX	INTEGER (0..65535) 
    ACCESS	read-write
    		-- C-ACCESS-FUNC	FrEndPtEgressQDepth
    		-- C-LOCATOR-FUNC	LocateFrEntry
    STATUS	mandatory
    DESCRIPTION "Egress Q Depth. This is valid for frEndPtType of 'frsm'."
    DEFVAL	{ 65535 }
	::= 	{ frEndPtEntry 25 }


frEndPtEgressDeThreshold OBJECT-TYPE
    SYNTAX	INTEGER (0..65535)
    ACCESS	read-write
    		-- C-ACCESS-FUNC	FrEndPtEgressDeThreshold
    		-- C-LOCATOR-FUNC	LocateFrEntry
    STATUS	mandatory
    DESCRIPTION "Egress threshold at which deletion occurs based on DE. 
    		This is valid for frEndPtType of 'frsm'."
    DEFVAL	{ 32768 }
	::= 	{ frEndPtEntry 26 }


frEndPtEgressEcnThreshold OBJECT-TYPE
    SYNTAX	INTEGER (0..65535)
    ACCESS	read-write
    		-- C-ACCESS-FUNC	FrEndPtEgressEcnThreshold
    		-- C-LOCATOR-FUNC	LocateFrEntry
    STATUS	mandatory
    DESCRIPTION "ECN threshold. This is valid for frEndPtType of 'frsm'."
    DEFVAL	{ 6553 }
	::= 	{ frEndPtEntry 27 }

frEndPtEgressQSelect OBJECT-TYPE
        SYNTAX  INTEGER {
                highPriority(1),
                lowPriority(2)
                }
	ACCESS	read-write
    		-- C-ACCESS-FUNC	FrEndPtEgressQSelect
    		-- C-LOCATOR-FUNC	LocateFrEntry
	STATUS	mandatory
	DESCRIPTION		  
                "Selects one out of two possible port queues.
                 The default port queue number is 2 which is the low
                 priority queue.
                This is only valid for frEndPtType of 'frsm'."
	::= 	{ frEndPtEntry 28 }

frEndPtLpbkState OBJECT-TYPE
    SYNTAX      INTEGER (0..65535)
    ACCESS      read-only
    		-- C-ACCESS-FUNC	FrEndPtLpbkState
    		-- C-LOCATOR-FUNC	LocateFrStatus
    STATUS      mandatory
    DESCRIPTION "The state of loopback mode for the end point. This is a
    	bit mapped integer with the values defined as follows:

			local		1
			remote		2
			port		4
			csu			8
			dsu			16
			external	32
			testcon		64
    	
		"
	::= { frEndPtEntry 29 }

frEndPtType OBJECT-TYPE
    SYNTAX      INTEGER {
    				cdpSdpCard(1),
    				fr(2),
    				ait(3),
    				frsm(4)
    			}
    ACCESS      read-only
    		-- C-ACCESS-FUNC	FrEndPtType
    		-- C-LOCATOR-FUNC	LocateFrEntry
    STATUS      mandatory
    DESCRIPTION "Identifies a type of fr end point which some attributes
    		may not apply.  In particular the attributes 

    		frEndPtInitialBurstSize, frEndPtDeTagging
    		frEndPtIngressDeThreshold, frEndPtEgressQDepth,
    		frEndPtEgressDeThreshold, frEndPtEgressEcnThreshold
                and frEndPtEgressQSelect
    		
    		are valid only when frEndptType has the value 'frsm'. "
	::= { frEndPtEntry 30 }

frEndPtchanType OBJECT-TYPE
    SYNTAX	INTEGER {
		frNIW(1),
		frSIW-transparent(2),
		frSIW-translate(3),
		frFUNI(4)
    		}
    ACCESS	read-write
    		-- C-ACCESS-FUNC	FrEndPtchanType
    		-- C-LOCATOR-FUNC	LocateFrEntry
    STATUS	mandatory
    DESCRIPTION "(1) is frame-relay network interworking,
                 (2) is service interworking with out any SDU translation,
                 (3) is service interworking with SDU translation, and
                 (4) is frame-relay UNI.
                 This is only valid for frEndPtType of 'frsm'.
                 Another restriction is that the other endpt should be
                 an ASI(atmEndPtTable) endpt. If the other endpt is a FR
                 endpt the DEFVAL will over-write the user's input."
    DEFVAL	{ frNIW }
	::= 	{ frEndPtEntry 31 }

frEndPtchanFECNconfig OBJECT-TYPE
    SYNTAX	INTEGER {
		mapEFCI(1),
		setEFCIzero(2)
    		}
    ACCESS	read-write
    		-- C-ACCESS-FUNC	FrEndPtFECNconfig
    		-- C-LOCATOR-FUNC	LocateFrEntry
    STATUS	mandatory
    DESCRIPTION "The FECN bits in frame-relay are mapped to EFCI bit 
                 in the ATM cells. mapEFCI is valid only for SIW.
                 This is only valid for frEndPtType of 'frsm'.
                 Another restriction is that the other endpt should be
                 an ASI(atmEndPtTable) endpt. If the other endpt is a FR
                 endpt the DEFVAL will over-write the user's input."
    DEFVAL	{ setEFCIzero }
	::= 	{ frEndPtEntry 32 }

frEndPtchanDEtoCLPmap OBJECT-TYPE
    SYNTAX	INTEGER {
		mapCLP(1),
		setCLPzero(2),
		setCLPone(3)
    		}
    ACCESS	read-write
    		-- C-ACCESS-FUNC	FrEndPtDEtoCLPmap
    		-- C-LOCATOR-FUNC	LocateFrEntry
    STATUS	mandatory
    DESCRIPTION "For (1), The DE bit is mapped to CLP bit in ATM cell.
                 For (2) and (3), the DE bit is ignored and CLP bit
                 is set to the constant value.
                 This is only valid for frEndPtType of 'frsm'.
                 Another restriction is that the other endpt should be
                 an ASI(atmEndPtTable) endpt. If the other endpt is a FR
                 endpt the DEFVAL will over-write the user's input."
    DEFVAL	{ mapCLP }
	::= 	{ frEndPtEntry 33 }

frEndPtchanCLPtoDEmap OBJECT-TYPE
    SYNTAX	INTEGER {
		mapDE(1),
		setDEzero(2),
		setDEone(3),
		ignoreCLP(4)
    		}
    ACCESS	read-write
    		-- C-ACCESS-FUNC	FrEndPtCLPtoDEmap
    		-- C-LOCATOR-FUNC	LocateFrEntry
    STATUS	mandatory
    DESCRIPTION "Values (1), (2) and (3) are valid for SIW.
                 Values (1) and (4) are valid for NIW.
                 For (1), the CLP bit is mapped to DE bit in frame-relay.
                 For (2) and (3), the CLP bit is ignored and DE bit
                 is set to the constant value.
                 ignoreCLP ignores CLP bit and DE bit remains as received.
                 This is only valid for frEndPtType of 'frsm'.
                 Another restriction is that the other endpt should be
                 an ASI(atmEndPtTable) endpt. If the other endpt is a FR
                 endpt the DEFVAL will over-write the user's input."
    DEFVAL	{ mapDE }
	::= 	{ frEndPtEntry 34 }


--
-- The AIT end point table.
--
-- An AIT end point is a gateway between Frame Relay and ATM.
-- It is an ATM end point with the characteristics of Frame Relay.
--
aitEndPtTable OBJECT-TYPE 
    SYNTAX      SEQUENCE OF AitEndPtEntry
    ACCESS      not-accessible
    STATUS      mandatory
    DESCRIPTION "A List of frame relay virtual circuit end points"
	::= { connSvc 5 }

aitEndPtEntry OBJECT-TYPE
    SYNTAX      AitEndPtEntry
    ACCESS      not-accessible
    STATUS      mandatory
    DESCRIPTION "A frame relay end point Entry"
    INDEX   { aitEndPtNodeName, aitEndPtIfShelf, aitEndPtSlot,
			  aitEndPtVpi, aitEndPtVci }
			  -- C-NEXT-FUNC	NextAitEntry
	::= { aitEndPtTable 1 }


AitEndPtEntry ::= 
    SEQUENCE {
		aitEndPtNodeName	DisplayString,
		aitEndPtIfShelf		DisplayString,
		aitEndPtSlot		INTEGER,
		aitEndPtVpi			INTEGER,
		aitEndPtVci			INTEGER,

		aitEndPtConnIndex	INTEGER,
		aitEndPtAdminStatus	INTEGER,
		aitEndPtOpStatus	INTEGER,
	
		aitEndPtMIR			INTEGER,
		aitEndPtCIR			INTEGER,
		aitEndPtVcQSize		INTEGER,
		aitEndPtPIR			INTEGER,
		aitEndPtCMAX		INTEGER,
		aitEndPtEcnQSize	INTEGER,
		aitEndPtQIR			INTEGER,
		aitEndPtPercUtil	INTEGER,
		aitEndPtPriority	INTEGER
}

aitEndPtNodeName OBJECT-TYPE
    SYNTAX      DisplayString (SIZE(1..10))
    ACCESS      read-only
    		-- C-ACCESS-FUNC	FrEndPtNodeName
    		-- C-LOCATOR-FUNC LocateAitEntry
    STATUS      mandatory
    DESCRIPTION "The node name."
	::= { aitEndPtEntry 1 }

aitEndPtIfShelf OBJECT-TYPE
    SYNTAX      DisplayString (SIZE(0..10))
    ACCESS      read-only
    		-- C-ACCESS-FUNC	FrEndPtIfShelf
    		-- C-LOCATOR-FUNC LocateAitEntry
    STATUS      mandatory
    DESCRIPTION "String identifying the shelf. This is a null string
		for end points which do not have a shelf name."
	::= { aitEndPtEntry 2 }

aitEndPtSlot OBJECT-TYPE
    SYNTAX	INTEGER (1..64)
    ACCESS	read-only
    		-- C-ACCESS-FUNC	FrEndPtSlot
    		-- C-LOCATOR-FUNC LocateAitEntry
    STATUS	mandatory
    DESCRIPTION	"Slot Number."
	::= { aitEndPtEntry 3 }

aitEndPtVpi OBJECT-TYPE
    SYNTAX	INTEGER (1..256)
	ACCESS	read-only
			-- C-ACCESS-FUNC	AitEndPtVpi
			-- C-LOCATOR-FUNC	LocateAitEntry
    STATUS	mandatory
    DESCRIPTION	"VPI. "
	::= { aitEndPtEntry 4 }

aitEndPtVci OBJECT-TYPE
    SYNTAX	INTEGER (1..512)
    ACCESS	read-only
    		-- C-ACCESS-FUNC	AitEndPtVci
    		-- C-LOCATOR-FUNC	LocateAitEntry
    STATUS	mandatory
    DESCRIPTION	"VCI."
	::= { aitEndPtEntry 5 }

aitEndPtConnIndex OBJECT-TYPE
    SYNTAX	INTEGER (0..2147483647)
    ACCESS	read-only
			-- C-ACCESS-FUNC	FrEndPtConnIndex
			-- C-LOCATOR-FUNC LocateAitEntry
    STATUS	mandatory
    DESCRIPTION "If the value of this object is greater than 0 then it is
    	the index identifying the associated connectionEntry."
	::= { aitEndPtEntry 6 }

aitEndPtAdminStatus OBJECT-TYPE
	SYNTAX	INTEGER {
				inactive(1),
				active(2),
				testing(3)
			}
	ACCESS	read-only
    		-- C-ACCESS-FUNC	FrEndPtAdminStatus
    		-- C-LOCATOR-FUNC	LocateAitEntry
	STATUS	mandatory
	DESCRIPTION	" Administrative status of the end point."
	::= { aitEndPtEntry 7 }

aitEndPtOpStatus OBJECT-TYPE
	SYNTAX      INTEGER {
					inactive(1),
					clear(2),
					fail(3),
					down(4)
				}
    ACCESS      read-only
    		-- C-ACCESS-FUNC	FrEndPtOpStatus
    		-- C-LOCATOR-FUNC LocateAitEntry
    STATUS      mandatory
    DESCRIPTION " Operational Status of the end point."
	::= { aitEndPtEntry 8 }

aitEndPtMIR OBJECT-TYPE
    SYNTAX      INTEGER (2400..2048000)
    ACCESS      read-only
    		-- C-ACCESS-FUNC	FrEndPtMIR
    		-- C-LOCATOR-FUNC LocateAitEntry
    STATUS      mandatory
    DESCRIPTION "The minimum transmit bandwidth (MIR) parameter
                 (in bits per second) for this  end-point. This object
		 has the relationship MIR <= CIR.
		 
		 This attribute can only be set to values evenly divisable by 100."
	::= { aitEndPtEntry 9 }

aitEndPtCIR OBJECT-TYPE
    SYNTAX      INTEGER (2400..2048000)
    ACCESS      read-only
    		-- C-ACCESS-FUNC	FrEndPtCIR
    		-- C-LOCATOR-FUNC LocateAitEntry
    STATUS      mandatory
    DESCRIPTION "The value of this object is equal to the committed
                 information rate (CIR) parameter (in bits
                 per second) for this  end-point.  This object holds
		 the relationship MIR < = CIR <= QIR.
		 
		 This attribute can only be set to values evenly divisable by 100."
	::= { aitEndPtEntry 10 }

aitEndPtVcQSize OBJECT-TYPE
    SYNTAX      INTEGER (1..65535)
    ACCESS      read-only
    		-- C-ACCESS-FUNC	FrEndPtVcQSize
    		-- C-LOCATOR-FUNC LocateAitEntry
    STATUS      mandatory
    DESCRIPTION "The value of this object is the maximum queue depth
                 (in bytes) for this  end-point.
                 
		This object is required before row creation is complete."
	::= { aitEndPtEntry 13 }

aitEndPtPIR OBJECT-TYPE
    SYNTAX      INTEGER (2400..2048000)
    ACCESS      read-only
    		-- C-ACCESS-FUNC	FrEndPtPIR
    		-- C-LOCATOR-FUNC LocateAitEntry
    STATUS      mandatory
    DESCRIPTION "The peak transmit bandwidth (PIR) parameter
                 (in bits per second) for this  end-point.
		 
		 This attribute can only be set to values evenly divisable by 100."
	::= { aitEndPtEntry 14 }

aitEndPtCMAX OBJECT-TYPE
    SYNTAX      INTEGER (1..255)
    ACCESS      read-only
    		-- C-ACCESS-FUNC	FrEndPtCMax
    		-- C-LOCATOR-FUNC LocateAitEntry
    STATUS      mandatory
    DESCRIPTION "The maximum credits that can be accrued for this
                 end-point.

		This object is required before row creation is complete."
	::= { aitEndPtEntry 15 }

aitEndPtEcnQSize OBJECT-TYPE
    SYNTAX      INTEGER (0..65535)
    ACCESS      read-only
    		-- C-ACCESS-FUNC	FrEndPtEcnQSize
    		-- C-LOCATOR-FUNC LocateAitEntry
    STATUS      mandatory
    DESCRIPTION "The threshold setting used by the explicit congestion
                 notification feature for this  end-point's
                 transmit queue. This value is specified in bytes.
                 When the aitEndPtVcQSize value exceeds this value
                 then the FECN bit will be set in all frames transmitted
                 to the remote  end-point.

		This object is required before row creation is complete."
	::= { aitEndPtEntry 16 }

aitEndPtQIR OBJECT-TYPE
    SYNTAX      INTEGER (2400..2048000)
    ACCESS      read-only
			-- C-ACCESS-FUNC	FrEndPtQIR
			-- C-LOCATOR-FUNC LocateAitEntry
    STATUS      mandatory
    DESCRIPTION "The transmit quiescent information rate (QIR) parameter
                 (in bits per second) for this  end-point.
                 This value has the relationship CIR <= QIR <= PIR.
		 
		 This attribute can only be set to values evenly divisable by 100. "
	::= { aitEndPtEntry 17 }

aitEndPtPercUtil OBJECT-TYPE
    SYNTAX      INTEGER (0..100)
    ACCESS      read-only
    		-- C-ACCESS-FUNC	FrEndPtPercUtil
    		-- C-LOCATOR-FUNC LocateAitEntry
    STATUS      mandatory
    DESCRIPTION "The value of this object is equal to the channel
                 percentage utilization setting for this  end-point.
                 This is the expected long-term utilization of the
                 channel by this  end-point.

		This object is required before row creation is complete."
	::= { aitEndPtEntry 18 }

aitEndPtPriority OBJECT-TYPE
    SYNTAX      INTEGER {
					low(1),
					high(2)
				}
    ACCESS      read-only
    		-- C-ACCESS-FUNC	FrEndPtPriority
    		-- C-LOCATOR-FUNC LocateAitEntry
    STATUS      mandatory
    DESCRIPTION "connection priority."
	::= { aitEndPtEntry 19 }


--
-- This is the table describing an ATM connection end-point.
-- Each connection (virtual circuit or ) end-point describes the 
-- particular characteristics of the end-point.  Such information 
-- as bandwidth parameters are maintained in the end-point table.  
--

atmEndPtTable OBJECT-TYPE 
    SYNTAX      SEQUENCE OF AtmEndPtEntry
    ACCESS      not-accessible
    STATUS      mandatory
    DESCRIPTION "The ATM End-Point table.  This table
                 is used to model a PVC end-point.  This table
                 contains the traffic parameters for ATM end-point."
	::= { connSvc 6 }

atmEndPtEntry OBJECT-TYPE
    SYNTAX      AtmEndPtEntry
    ACCESS      not-accessible
    STATUS      mandatory
    DESCRIPTION "An entry in the ATM End-point table."
    INDEX   { atmEndPtNodeName, atmEndPtIfShelf, atmEndPtSlot,
			  atmEndPtPort, atmEndPtVpi, atmEndPtVci }
			  -- C-NEXT-FUNC NextAtmEntry
	::= { atmEndPtTable 1 }

AtmEndPtEntry ::=
    SEQUENCE {
		atmEndPtNodeName	DisplayString,
		atmEndPtIfShelf		DisplayString,
		atmEndPtSlot		INTEGER,
		atmEndPtPort		INTEGER,
		atmEndPtVpi			INTEGER,
		atmEndPtVci			INTEGER,
		atmEndPtConnIndex	INTEGER,
    
		atmEndPtAdminStatus	INTEGER,
		atmEndPtOpStatus	INTEGER,
		atmEndPtRowStatus	INTEGER,
    
		atmEndPtCIR			INTEGER,
		atmEndPtMIR			INTEGER,
		atmEndPtPIR			INTEGER,
		atmEndPtQIR			INTEGER,
		atmEndPtPercUtil	INTEGER,
		atmEndPtPriority	INTEGER,
		atmEndPtIBS		INTEGER,
		atmEndPtVcQSize		INTEGER
}

atmEndPtNodeName OBJECT-TYPE
    SYNTAX	DisplayString(SIZE(1..10))
    ACCESS	read-write
    		-- C-ACCESS-FUNC atmEndPtNodeName
    		-- C-LOCATOR-FUNC LocateAtmEntry
    STATUS	mandatory
    DESCRIPTION "Node name of this endpoint."
	::= { atmEndPtEntry 1 }

atmEndPtIfShelf OBJECT-TYPE
    SYNTAX      DisplayString(SIZE(0..10))
    ACCESS      read-write
    		-- C-ACCESS-FUNC atmEndPtShelf
    		-- C-LOCATOR-FUNC LocateAtmEntry
    STATUS      mandatory
    DESCRIPTION "Shelf name of this endpoint.  If no shelf name than this
		value is a NULL string."
	::= { atmEndPtEntry 2 }

atmEndPtSlot OBJECT-TYPE
    SYNTAX	INTEGER (1..64)
    ACCESS	read-write
    		-- C-ACCESS-FUNC atmEndPtSlot
    		-- C-LOCATOR-FUNC LocateAtmEntry
    STATUS	mandatory
    DESCRIPTION	"Local Slot Number."
	::= { atmEndPtEntry 3 }

atmEndPtPort OBJECT-TYPE
    SYNTAX	INTEGER (1..64)
    ACCESS	read-write
    		-- C-ACCESS-FUNC atmEndPtPort
    		-- C-LOCATOR-FUNC LocateAtmEntry
    STATUS	mandatory
    DESCRIPTION	"Local Port Number.  These are numbered starting at 1."
	::= { atmEndPtEntry 4 }

atmEndPtVpi OBJECT-TYPE
    SYNTAX	INTEGER (1..4095)
    ACCESS	read-write
    		-- C-ACCESS-FUNC atmEndPtVpi
    		-- C-LOCATOR-FUNC LocateAtmEntry
    STATUS	mandatory
    DESCRIPTION	"Virtual port index."
	::= { atmEndPtEntry 5 }

atmEndPtVci OBJECT-TYPE
    SYNTAX	INTEGER (1..65535)
    ACCESS	read-write
    		-- C-ACCESS-FUNC atmEndPtVci
    		-- C-LOCATOR-FUNC LocateAtmEntry
    STATUS	mandatory
    DESCRIPTION	"virtual channel index."
	::= { atmEndPtEntry 6 }

atmEndPtConnIndex OBJECT-TYPE
    SYNTAX	INTEGER (0..2147483647)
    ACCESS      read-only
    		-- C-ACCESS-FUNC atmEndPtConnIndex
    		-- C-LOCATOR-FUNC LocateAtmEntry
    STATUS      mandatory
    DESCRIPTION "If the value of this object is greater than 0 then it is
	 	the index identifying the associated connectionEntry."
	::= { atmEndPtEntry 7 }

atmEndPtAdminStatus OBJECT-TYPE
    SYNTAX      INTEGER {
					inactive(1),
					active(2),
					testing(3)
				}
    ACCESS      read-write
    		-- C-ACCESS-FUNC atmEndPtAdminStatus
    		-- C-LOCATOR-FUNC LocateAtmEntry
    STATUS      mandatory
    DESCRIPTION "Admin Status of the end point."
    DEFVAL { inactive }
	::= { atmEndPtEntry 9 }

atmEndPtOpStatus OBJECT-TYPE
    SYNTAX      INTEGER {
					inactive(1),
					clear(2),
					fail(3),
					down(4)
				}
    ACCESS      read-only
    		-- C-ACCESS-FUNC atmEndPtOpStatus
    		-- C-LOCATOR-FUNC LocateAtmEntry
    STATUS      mandatory
    DESCRIPTION "Operational Status of the end point."
	::= { atmEndPtEntry 10 }

atmEndPtRowStatus OBJECT-TYPE
    SYNTAX      INTEGER {
					active(1),
					createAndGo(4),
					destroy(6)
				}
    ACCESS      read-write
    		-- C-ACCESS-FUNC atmEndPtRowStatus
    		-- C-LOCATOR-FUNC LocateAtmEntry
    STATUS      mandatory
    DESCRIPTION "The manager must set this to 'createAndGo' when creating
		a new entry.  Other required elements can also be set in the
		same SET request"
	::= { atmEndPtEntry 11 }

atmEndPtMIR OBJECT-TYPE
    SYNTAX      INTEGER (7..353208)
    ACCESS      read-write
    		-- C-ACCESS-FUNC atmEndPtMir
    		-- C-LOCATOR-FUNC LocateAtmEntry
    STATUS      mandatory
    DESCRIPTION "The minimum transmit bandwidth (MIR) parameter
                 (in bits per second) for this end-point.
                 For ATF without Foresight connections
                 this object corresponds to the Peak Cell Rate(PCR)
                 defined by ATM standard documents.
                 For ATF with Foresight connections this
                 object corresponds to the Minimum Cell Rate (MCR).
                 (in bits per second) for this end-point.
                 The maximum value for this object is the port
                 speed of the associated interface."
	DEFVAL { 9600 }
	::= { atmEndPtEntry 12 }

atmEndPtCIR OBJECT-TYPE
    SYNTAX      INTEGER (7..353208)
    ACCESS      read-write
    		-- C-ACCESS-FUNC atmEndPtCir
    		-- C-LOCATOR-FUNC LocateAtmEntry
    STATUS      mandatory
    DESCRIPTION "The value of this object is equal to the committed
                 information rate (CIR) parameter 
                 (in bits per second) for this end-point.
                 This object corresponds to the Sustainable Cell Rate(SCR)
                 defined by ATM standard documents.
                 The maximum value for this object is the
                 port speed of the associated interface.
                 All values between minimum and maximum for a
                 given interface will be accepted, but they will be
                 internally rounded up to the closest higher value
                 valid for that interface."
	DEFVAL { 9600 }
	::= { atmEndPtEntry 13 }

atmEndPtPIR OBJECT-TYPE
    SYNTAX      INTEGER (10..353208)
    ACCESS      read-write
    		-- C-ACCESS-FUNC atmEndPtPir
    		-- C-LOCATOR-FUNC LocateAtmEntry
    STATUS      mandatory
    DESCRIPTION "The peak transmit bandwidth (PIR) parameter
                 (in bits per second) for this end-point.
                 This object applies only to Foresight connections 
                 and corresponds to the Peak Cell Rate (PCR)
                 defined by ATM standard documents.
                 The maximum value for this object
                 is the port speed of the associated interface."
	DEFVAL { 9600 }
 	::= { atmEndPtEntry 14 }

atmEndPtQIR OBJECT-TYPE
    SYNTAX      INTEGER (10..96000)
    ACCESS      read-write
    		-- C-ACCESS-FUNC atmEndPtQir
    		-- C-LOCATOR-FUNC LocateAtmEntry
    STATUS      mandatory
    DESCRIPTION "The transmit quiescent information rate (QIR) parameter
                 (in bits per second) for this end-point.
                 This parameter applies only to Foresight connections,
                 and corresponds to the Initial Cell Rate (ICR)
                 defined by ATM standard documents.
                 This value can range between the MIR and PIR values."
	DEFVAL { 9600 }
	::= { atmEndPtEntry 15 }

atmEndPtPercUtil OBJECT-TYPE
    SYNTAX      INTEGER (0..100)
    ACCESS      read-write
    		-- C-ACCESS-FUNC atmEndPtPercUtil
    		-- C-LOCATOR-FUNC LocateAtmEntry
    STATUS      mandatory
    DESCRIPTION "The value of this object is equal to the channel
                 percentage utilization setting for this end-point.
                 This is the expected long-term utilization of the
                 channel by this end-point."
    DEFVAL	{ 100 }
	::= { atmEndPtEntry 16 }

atmEndPtPriority OBJECT-TYPE
    SYNTAX      INTEGER {
					low(1),
					high(2)
				}
    ACCESS      read-only
    		-- C-ACCESS-FUNC atmEndPtPriority
    		-- C-LOCATOR-FUNC LocateAtmEntry
    STATUS      mandatory
    DESCRIPTION "queueing priority."
	::= { atmEndPtEntry 17 }


atmEndPtIBS OBJECT-TYPE
    SYNTAX      INTEGER (1..24000)
    ACCESS      read-write
    		-- C-ACCESS-FUNC atmEndPtIBS
    		-- C-LOCATOR-FUNC LocateAtmEntry
    STATUS      mandatory
    DESCRIPTION "The value of this object is equal to the Initial
                 Burst Size in cells for the other end-point. The
                 maximum value for this object on OC3 end points
                 is 1000."
    DEFVAL	{ 900 }
	::= { atmEndPtEntry 18 }

atmEndPtVcQSize OBJECT-TYPE
    SYNTAX      INTEGER (1..64000)
    ACCESS      read-write
    		-- C-ACCESS-FUNC atmEndPtVcQSize
    		-- C-LOCATOR-FUNC LocateAtmEntry
    STATUS      mandatory
    DESCRIPTION "The value of this object is the maximum queue depth
                 (in cells) for this end-point.
                 For ATF without Foresight connections
                 this object corresponds to the maximum Cell Delay
                 Variation (CDV) Tolerance measured in cells."
    DEFVAL	{ 64000 }
	::= { atmEndPtEntry 19 }

--
-- The segment table identifies connection segments. It identifies the two end
-- points of a connection which is not necessarily end to end.  If the 
-- segment is part of a end to end connection, then the connectionEntry is
-- identified as well as the local end point of the next segment.
-- A 'local' end point may not be part of multiple segments.  The table 
-- is indexed by the elements which identify the local end point of the 
-- segment, including the end point table.  The other end point of the 
-- segment and an end point of the next segment are named by their 
-- object identifier.
-- 

segmentTable OBJECT-TYPE 
    SYNTAX      SEQUENCE OF SegmentEntry
    ACCESS      not-accessible
    STATUS      mandatory
    DESCRIPTION "A List of Connection Entries"
	::= { connSvc 7 }

segmentEntry OBJECT-TYPE
    SYNTAX      SegmentEntry
    ACCESS      not-accessible
    STATUS      mandatory
    DESCRIPTION "A generic end point Entry"
    INDEX	{ segEndPtTableId, segNodeName, segShelf, segSlot,
			  segLine, segPort, segSubChn1, segSubChn2}
		-- C-NEXT-FUNC NextSegmentEntry
   	::= { segmentTable 1 }

SegmentEntry ::=
    SEQUENCE {
    	segEndPtTableId	INTEGER,
		segNodeName		DisplayString,
		segShelf		DisplayString,
		segSlot			INTEGER,
		segLine			INTEGER,
		segPort			INTEGER,
		segSubChn1		INTEGER,
		segSubChn2		INTEGER,
		segOeEndPt		OBJECT IDENTIFIER,
		segConnIndex		INTEGER,
		segNextSeg		OBJECT IDENTIFIER
}

segEndPtTableId OBJECT-TYPE
    SYNTAX      INTEGER {
    				frEndPtTable(1),
    				atmEndptTable(2)
       			}
    ACCESS      read-only
    		-- C-ACCESS-FUNC segEndPtTableId
    		-- C-LOCATOR-FUNC LocateSegEntry
    STATUS      mandatory
    DESCRIPTION "The end point table from which the remaining indices are obtained."
	::= { segmentEntry 1 }

segNodeName OBJECT-TYPE
    SYNTAX      DisplayString (SIZE(1..10))
    ACCESS      read-only
			-- C-ACCESS-FUNC segNodeName
    		-- C-LOCATOR-FUNC LocateSegEntry
    STATUS      mandatory
    DESCRIPTION "The node name."
	::= { segmentEntry 2 }

segShelf OBJECT-TYPE
    SYNTAX      DisplayString (SIZE(0..10))
    ACCESS      read-only
			-- C-ACCESS-FUNC segShelf
    		-- C-LOCATOR-FUNC LocateSegEntry
    STATUS      mandatory
    DESCRIPTION "String identifying the shelf. This is a null string
		for end points which do not have a shelf name."
	::= { segmentEntry 3 }

segSlot OBJECT-TYPE
    SYNTAX	INTEGER (1..64)
    ACCESS	read-only
			-- C-ACCESS-FUNC segSlot
    		-- C-LOCATOR-FUNC LocateSegEntry
    STATUS	mandatory
    DESCRIPTION	"Slot Number."
	::= { segmentEntry 4 }

segLine OBJECT-TYPE
    SYNTAX	INTEGER (0..8)
    ACCESS	read-only
			-- C-ACCESS-FUNC segLine
    		-- C-LOCATOR-FUNC LocateSegEntry
    STATUS	mandatory
    DESCRIPTION	"Line Number. If no line number is associated with the 
    	end point then this value is 0."
	::= { segmentEntry 5 }

segPort OBJECT-TYPE
    SYNTAX	INTEGER (1..256)
	ACCESS	read-only
			-- C-ACCESS-FUNC segPort
    		-- C-LOCATOR-FUNC LocateSegEntry
    STATUS	mandatory
    DESCRIPTION	"Port Number. "
	::= { segmentEntry 6 }

segSubChn1 OBJECT-TYPE
    SYNTAX	INTEGER	(0..32767)
    ACCESS	read-only
			-- C-ACCESS-FUNC segSubChn1
    		-- C-LOCATOR-FUNC LocateSegEntry
    STATUS	mandatory
    DESCRIPTION	"The meaning of this attribute is dependant on the value of
    		segTableId. For 'frEndPtTable(1)' this value is the end point DLCI
    		otherwise it is the end point VPI"
	::= { segmentEntry 7 }

segSubChn2 OBJECT-TYPE
    SYNTAX	INTEGER (0..32767)
    ACCESS	read-only
			-- C-ACCESS-FUNC segSubChn2
    		-- C-LOCATOR-FUNC LocateSegEntry
    STATUS	mandatory
    DESCRIPTION "If the value of this attribute is 0, then it has no meaning
    		in identifying the end point. If the value of this attribute is
    		greater than 0 the it identifies the end point VCI."
	::= { segmentEntry 8 }

segOeEndPt OBJECT-TYPE
    SYNTAX	OBJECT IDENTIFIER
    ACCESS	read-only
		-- C-ACCESS-FUNC segOeEndPt
    		-- C-LOCATOR-FUNC LocateSegEntry
    STATUS	mandatory
    DESCRIPTION "The object id of the first attribute in the protocol specific
    	end point table which is the 'remote' end point of the segment.
    	
    	If there is no remote end point then this attribute has the value
    	of the NULL object identifier {0 0}."
	::= { segmentEntry 9 }

segConnIndex OBJECT-TYPE
    SYNTAX	INTEGER (0..2147483647)
    ACCESS	read-only
		-- C-ACCESS-FUNC segConnIndex
    		-- C-LOCATOR-FUNC LocateSegEntry
    STATUS	mandatory
    DESCRIPTION "The connectionIndex value identifying the end to end connection
		of which this segment is a part.  If this value is 0, then
		the segment is not a part of any end to end connection."
	::= { segmentEntry 10 }

segNextSeg OBJECT-TYPE
    SYNTAX	OBJECT IDENTIFIER
    ACCESS	read-only
		-- C-ACCESS-FUNC segNextSeg
    		-- C-LOCATOR-FUNC LocateSegEntry
    STATUS	mandatory
    DESCRIPTION "The object id of the first attribute in the protocol specific
    	end point table which is the 'local' end point of the next segment of
    	the end to end connection identified by segConnIndex. A value of {0 0},
    	the NULL object identifier, indicates there is no next segment."
	::= { segmentEntry 11 }


------------------------------------------------------------------ 
--	ERROR STATUS TABLE for Connections
--
-- This object contains the value of the request id for the latest 
-- entry in the error status table. 
-- This value can be used to retrieve the error code and description 
-- for the last SET operation failed.
--
cmpaErrorLastIndex	OBJECT-TYPE
	SYNTAX	INTEGER 
	ACCESS	read-only
	-- C-ACCESS-FUNC ppaErrorLastIndex
	STATUS	mandatory
	DESCRIPTION "If at least one entry exists in the error status table, 
		     the value of this object contains the index corresponding 
		     to the last entry inserted in the table. If no entries
		     have ever been inserted in the cmpaErrorTable, then
		     the agent will return 0 for a query of this variable.

                     Actually this object is not required any more because
                     of the new objects cmpaErrorLastDesc and cmpaErrorLastEcode.
                     One can do GET directly on cmpaErrorLastDesc/LastEcode."
        ::= { connSvc 8 }

cmpaErrorFlushAll  OBJECT-TYPE
    SYNTAX      INTEGER {
                noOp(1),
		flush(2)
        }
    ACCESS      read-write
	-- C-ACCESS-FUNC ppaErrorFlushAll
    STATUS      mandatory
    DESCRIPTION "Setting this object to the value 'flush' indicates to
		 the agent that a manager would like the cmpaErrorTable
		 to be immediately flushed of all entries.

		 A management retrieval of this object will always return
		 the value 'noOp'.

		 Setting this object to the value 'noOp' is invalid."
        ::= { connSvc 9 }

--
-- The following table is used to maintain status information about 
-- SNMP GET/SET requests from a Manager.  When an SNMP GET/SET fails, an 
-- entry in this table is created and the object cmpaErrorLastIndex 
-- is updated.
--
-- Note that currently only SET errors are updated in this error table.
--
cmpaErrorTable OBJECT-TYPE 
    SYNTAX      SEQUENCE OF CmpaErrorEntry
    ACCESS      not-accessible
    STATUS      mandatory
    DESCRIPTION "A List of recent Errors reported by the 
		 Ports Proxy Agent (PPA)."
        ::= { connSvc 10 }

cmpaErrorEntry OBJECT-TYPE
    SYNTAX      CmpaErrorEntry
    ACCESS      not-accessible
    STATUS      mandatory
    DESCRIPTION "A General Error Status Entry."
    INDEX   { cmpaErrorReqId }
	-- C-NEXT-FUNC NextErrorEntry
        ::= { cmpaErrorTable 1  }

CmpaErrorEntry ::= SEQUENCE {
        cmpaErrorReqId			INTEGER,    
        cmpaErrorDesc			DisplayString,
        cmpaErrorEcode			INTEGER
}

cmpaErrorReqId OBJECT-TYPE
    SYNTAX      INTEGER 
    ACCESS      read-only
	-- C-ACCESS-FUNC ppaErrorReqId
    	-- C-LOCATOR-FUNC  LocateErrorEntry
    STATUS      mandatory
    DESCRIPTION "This object contains the PDU request ID associated with
                 the SET request. The manager must use this information to
		 find the error associated with a particular SNMP request.
	
		 Note that an SNMP request ID may be reused by
		 the same manager.  When this occurs,
	 	 the older entry in the table will be replaced with the
		 new error status.  Managers must be aware that
		 error information may therefore be lost."
        ::= { cmpaErrorEntry 1  }

cmpaErrorDesc OBJECT-TYPE
    SYNTAX      DisplayString (SIZE(1..255))
    ACCESS      read-only
	-- C-ACCESS-FUNC ppaErrorDesc
    	-- C-LOCATOR-FUNC  LocateErrorEntry
    STATUS      mandatory
    DESCRIPTION "This object contains error status information for failed
                 SETS to one or more objects in one or more of the 
		 following tables:

			frPortsCfgTable

		 Rows in this table may be created as the result of
		 a failed SNMP SET operation.

		 Since the SNMP standard allows only limited number of
		 error result codes, the managers can retrieve this
		 variable to get additional information on a failed 
		 SET operation. Typically this object will contain 
		 a user friendly description of the cause of the error."
        ::= { cmpaErrorEntry 2 }

cmpaErrorEcode OBJECT-TYPE
    SYNTAX      INTEGER {
			invalid-network(1),
			-- No such Network(domain) in the Database
			invalid-node(2),
			-- No such Node in the Database
			invalid-shelf(3),
			-- No such Nhelf for the given node
			invalid-release(4),
			-- Unsupported release fot the given Node/Shelf
			node-timeout(5),
			-- Timeout from the given Node/Shelf
			node-busy(6),
			-- Node is busy processing other requests
			no-snmpcomm(7),
			-- The demon process snmpcomm is not running
			snmpcomm-error(8),
			-- Internal error at the demon process snmpcomm
			node-error(9),
			-- Error at the embedded Agent
			bad-value(10),
			-- Bad value for the given Object
			port-not-found(11),
			-- The specified port does not exists
			slot-is-full(12),
			-- AddConn error, no more conns on this slot
			conn-not-found(100),
			-- The specified connection does not exists
			endpt-exists(101),
                        -- AddConn error, Endpt already exists
			lendpt-exists(102),
                        -- AddConn error, Local Endpt already exists
			rendpt-exists(103),
                        -- AddConn error, Remote Endpt already exists
			lendpt-missing(104),
			-- connectionLocalEndPt is missing from the SET request
			rendpt-missing(105),
			-- connectionRemoteEndPt is missing from the SET request
			db-lendpt-not-found(106),
			-- Could not find Local Endpt in Database
			db-rendpt-not-found(107),
			-- Could not find Remote Endpt in Database
			lendpt-not-found(108),
			-- connectionLocalEndPt specified does not exists
			rendpt-not-found(109),
			-- connectionRemoteEndPt specified does not exists
			dangling-endpt(110),
			-- The Endpt is part of an incomplete connection
			endpt-rowstatus-missing(111),
			-- frEndPtRowStatus is missing from the SET request
			conn-rowstatus-missing(112),
			-- connectionRowStatus is missing from the SET request
                        invalid-endpt-rowstatus(113),
			-- End point RowStatus can not be set to Active
                        invalid-conn-rowstatus(114),
			-- connectionRowStatus can not be set to Active
			invalid-connindex(115),
			-- Invalid connection Index used for AddConn
			testtype-missing(116),
			-- connectionTestType is missing from the SET Request
			partial-add(117),
			-- Connection is added, but modification failed
			partial-mod(118),
			-- Endpt is modified, but connection params not modified
			invalid-bw(119),
			-- Invalid BandWidth param relationship.
			not-active(120),
			-- Connection is not in active state
			invalid-adminstatus(121),
			-- connectionAdminStatus can be SET to testing only
			not-clear(122),
			-- connectionOpStatus is not in clear state
			invalid-endpt-comb(123),
			-- Invalid Endpt combination for the connection
			invalid-chantype(124),
			-- Invalid chanType for the given Endpt combination
			cmgrd-timeout(125),
			-- No response from the demon cmgrd
			no-cmgrd(126),
			-- The demon cmgrd is not running
			ronly-for-frp(127),
			-- Object is read-only for FRP(IPX) Endpt
			invalid-chanFECNconfig(128),
			-- Invalid chanFECNconfig for the given chanType
			invalid-chanCLPtoDEmap(129),
			-- Invalid chanCLPtoDEmap for the given chanType
			ibs-less-bc(130),
			-- InitialBurstSize(IBS) should be less than or equal to Bc
			asi-no-remote(131),
			-- ASI can not be used as a remote End point
			frsm-remote(132),
			-- Remote End point must be FRSM for ASI connections
			foresight-disabled(133),
			-- PIR, MIR and QIR can not be Modified for AXIS endpt,
			-- when Foresight is disabled
			no-error-entry(500),
			-- No entries available in the ErrorTable
			not-applicable(501),
			-- Error Code not relevant, rely on Error Description
			invalid-flushall(502)
			-- Can not set to noOp for cmpaErrorFlushAll
			}
    ACCESS      read-only
	-- C-ACCESS-FUNC ppaErrorEcode
    	-- C-LOCATOR-FUNC  LocateErrorEntry
    STATUS      mandatory
    DESCRIPTION "This object contains the error Code of the GET/SET operation.
		 The error Codes from 500 onwards are specific to the
                 Error Table operation itself.
                 Note that currently GET errors are not updated in the
                 error table."
        ::= { cmpaErrorEntry 3  }

cmpaErrorLastDesc	OBJECT-TYPE
    	SYNTAX		DisplayString (SIZE(0..255))
	ACCESS		read-only
			-- C-ACCESS-FUNC ppaErrorLastDesc
	STATUS		mandatory
	DESCRIPTION "This contains the error description of the last error
		 generated. If error table contains no errors, GET on
                 this will return NULL string"
        ::= { connSvc 11 }

cmpaErrorLastEcode	OBJECT-TYPE
    SYNTAX      INTEGER {
			invalid-network(1),
			-- No such Network(domain) in the Database
			invalid-node(2),
			-- No such Node in the Database
			invalid-shelf(3),
			-- No such Nhelf for the given node
			invalid-release(4),
			-- Unsupported release fot the given Node/Shelf
			node-timeout(5),
			-- Timeout from the given Node/Shelf
			node-busy(6),
			-- Node is busy processing other requests
			no-snmpcomm(7),
			-- The demon process snmpcomm is not running
			snmpcomm-error(8),
			-- Internal error at the demon process snmpcomm
			node-error(9),
			-- Error at the embedded Agent
			bad-value(10),
			-- Bad value for the given Object
			port-not-found(11),
			-- The specified port does not exists
			slot-is-full(12),
			-- AddConn error, no more conns on this slot
			conn-not-found(100),
			-- The specified connection does not exists
			endpt-exists(101),
                        -- AddConn error, Endpt already exists
			lendpt-exists(102),
                        -- AddConn error, Local Endpt already exists
			rendpt-exists(103),
                        -- AddConn error, Remote Endpt already exists
			lendpt-missing(104),
			-- connectionLocalEndPt is missing from the SET request
			rendpt-missing(105),
			-- connectionRemoteEndPt is missing from the SET request
			db-lendpt-not-found(106),
			-- Could not find Local Endpt in Database
			db-rendpt-not-found(107),
			-- Could not find Remote Endpt in Database
			lendpt-not-found(108),
			-- connectionLocalEndPt specified does not exists
			rendpt-not-found(109),
			-- connectionRemoteEndPt specified does not exists
			dangling-endpt(110),
			-- The Endpt is part of an incomplete connection
			endpt-rowstatus-missing(111),
			-- frEndPtRowStatus is missing from the SET request
			conn-rowstatus-missing(112),
			-- connectionRowStatus is missing from the SET request
                        invalid-endpt-rowstatus(113),
			-- End point RowStatus can not be set to Active
                        invalid-conn-rowstatus(114),
			-- connectionRowStatus can not be set to Active
			invalid-connindex(115),
			-- Invalid connection Index used for AddConn
			testtype-missing(116),
			-- connectionTestType is missing from the SET Request
			partial-add(117),
			-- Connection is added, but modification failed
			partial-mod(118),
			-- Endpt is modified, but connection params not modified
			invalid-bw(119),
			-- Invalid BandWidth param relationship.
			not-active(120),
			-- Connection is not in active state
			invalid-adminstatus(121),
			-- connectionAdminStatus can be SET to testing only
			not-clear(122),
			-- connectionOpStatus is not in clear state
			invalid-endpt-comb(123),
			-- Invalid Endpt combination for the connection
			invalid-chantype(124),
			-- Invalid chanType for the given Endpt combination
			cmgrd-timeout(125),
			-- No response from the demon cmgrd
			no-cmgrd(126),
			-- The demon cmgrd is not running
			ronly-for-frp(127),
			-- Object is read-only for FRP(IPX) Endpt
			invalid-chanFECNconfig(128),
			-- Invalid chanFECNconfig for the given chanType
			invalid-chanCLPtoDEmap(129),
			-- Invalid chanCLPtoDEmap for the given chanType
			ibs-less-bc(130),
			-- InitialBurstSize(IBS) should be less than or equal to Bc
			asi-no-remote(131),
			-- ASI can not be used as a remote End point
			frsm-remote(132),
			-- Remote End point must be FRSM for ASI connections
			foresight-disabled(133),
			-- PIR, MIR and QIR can not be Modified for AXIS endpt,
			-- when Foresight is disabled
			no-error-entry(500),
			-- No entries available in the ErrorTable
			not-applicable(501),
			-- Error Code not relevant, rely on Error Description
			invalid-flushall(502)
			-- Can not set to noOp for cmpaErrorFlushAll
			}
	ACCESS		read-only
			-- C-ACCESS-FUNC ppaErrorLastEcode
	STATUS		mandatory
	DESCRIPTION "This contains the error code of the last error
		 generated. If error table contains no errors, 
                 GET on this object returns 500"
        ::= { connSvc 12 }

-- portSvc MIB defines tables and attributes for maintaining 
-- fr ports for AXIS and IPX through system manager interface.
-- It also gives information on the configuration state of the ports

-- The following Table portsInfoTable gives the information on the 
-- configuration state of the ports

portsInfoTable OBJECT-TYPE 
    SYNTAX	SEQUENCE OF PortsInfoEntry
    ACCESS	not-accessible
    STATUS	mandatory
    DESCRIPTION "Ports information for the specified line"
	::= { portSvc 1 }

portsInfoEntry OBJECT-TYPE
    SYNTAX	PortsInfoEntry
    ACCESS	not-accessible
    STATUS	mandatory
    DESCRIPTION	"Ports Information Entry"
    INDEX   { portsInfoNode, portsInfoShelf, 
              portsInfoSlot, portsInfoLine, portsInfoPort }
			-- C-NEXT-FUNC	NextPortsEntry
	::= { portsInfoTable 1 }

PortsInfoEntry ::=
	SEQUENCE {
		portsInfoNode		DisplayString,
		portsInfoShelf		DisplayString,
		portsInfoSlot		INTEGER,
		portsInfoLine		INTEGER,
		portsInfoPort		INTEGER,
		portsInfoPortType	INTEGER,
		portsInfoPortState	INTEGER,
		portsInfoPortSpeed	INTEGER
}

portsInfoNode OBJECT-TYPE
    SYNTAX      DisplayString (SIZE(1..10))
    ACCESS      read-only
    		-- C-ACCESS-FUNC	PortsInfoNode
    		-- C-LOCATOR-FUNC  LocatePortsInfoEntry
    STATUS      mandatory
    DESCRIPTION "String identifying the node"
	::= { portsInfoEntry 1 }

portsInfoShelf OBJECT-TYPE
    SYNTAX      DisplayString (SIZE(0..10))
    ACCESS      read-only
    		-- C-ACCESS-FUNC	PortsInfoShelf
    		-- C-LOCATOR-FUNC  LocatePortsInfoEntry
    STATUS      mandatory
    DESCRIPTION "String identifying the shelf"
	::= { portsInfoEntry 2 }

portsInfoSlot OBJECT-TYPE
    SYNTAX	INTEGER (1..64)
    ACCESS	read-only
    		-- C-ACCESS-FUNC	PortsInfoSlot
    		-- C-LOCATOR-FUNC  LocatePortsInfoEntry
    STATUS	mandatory
    DESCRIPTION	"Slot Number"
	::= { portsInfoEntry 3 }

portsInfoLine OBJECT-TYPE
    SYNTAX	INTEGER (0..8)
    ACCESS	read-only
    		-- C-ACCESS-FUNC	PortsInfoLine
    		-- C-LOCATOR-FUNC  LocatePortsInfoEntry
    STATUS	mandatory
    DESCRIPTION	"Line Number. For IPX ports Line Number is always 0"
	::= { portsInfoEntry 4 }

portsInfoPort OBJECT-TYPE
    SYNTAX	INTEGER (1..64)
    ACCESS	read-only
    		-- C-ACCESS-FUNC	PortsInfoPort
    		-- C-LOCATOR-FUNC  LocatePortsInfoEntry
    STATUS	mandatory
    DESCRIPTION	"Port Number"
	::= { portsInfoEntry 5 }

portsInfoPortType OBJECT-TYPE
    SYNTAX      INTEGER {
                        frsm(1),
                        frp (2),
                        ausm(3),
                        atm (4)
                        }
    ACCESS	read-only
    		-- C-ACCESS-FUNC	PortsInfoPortType
    		-- C-LOCATOR-FUNC  LocatePortsInfoEntry
    STATUS	mandatory
    DESCRIPTION	"Port type includes Card type as well as Interface type"
	::= { portsInfoEntry 6 }

portsInfoPortState OBJECT-TYPE
    SYNTAX      INTEGER {
                        active(1),
                        inactive(2),
                        remoteLoopback(3),
                        failed(4)
                        }
    ACCESS	read-only
    		-- C-ACCESS-FUNC	PortsInfoPortState
    		-- C-LOCATOR-FUNC  LocatePortsInfoEntry
    STATUS	mandatory
    DESCRIPTION	"Port state"
	::= { portsInfoEntry 7 }

portsInfoPortSpeed	OBJECT-TYPE
    SYNTAX	INTEGER 
    ACCESS	read-only
    		-- C-ACCESS-FUNC	PortsInfoPortSpeed
    		-- C-LOCATOR-FUNC  LocatePortsInfoEntry
    STATUS	mandatory
    DESCRIPTION
		"Configured speed of port in kbps"
	::= { portsInfoEntry 8 }

-- The following table is used for maintaining 
-- fr ports for AXIS and IPX through system manager interface.
-- Note that the objects with 'frPorts' suffix belong to both 
-- AXIS and IPX nodes. Objects with 'frAxPorts' are specific 
-- to AXIS nodes and objects with 'frIxPorts' are specific to IPX.
-- For AXIS we can add, delete and modify the ports.
-- Fox IPX we can also up and down the ports, in addition 
-- to add, delete and modify.

frPortsCfgTable OBJECT-TYPE 
    SYNTAX	SEQUENCE OF FrPortsCfgEntry
    ACCESS	not-accessible
    STATUS	mandatory
    DESCRIPTION "fr ports updations for AXIS and IPX."
	::= { portSvc 2 }

frPortsCfgEntry OBJECT-TYPE
    SYNTAX	FrPortsCfgEntry
    ACCESS	not-accessible
    STATUS	mandatory
    DESCRIPTION	"Ports Cfgrmation Entry"
    INDEX   { frPortsCfgNode, frPortsCfgShelf, 
              frPortsCfgSlot, frPortsCfgLine, frPortsCfgPort}
			-- C-NEXT-FUNC	NextPortsEntry
	::= { frPortsCfgTable 1 }

FrPortsCfgEntry ::=
    SEQUENCE {
             frPortsCfgNode          DisplayString,
             frPortsCfgShelf         DisplayString,
             frPortsCfgSlot          INTEGER,
             frPortsCfgLine          INTEGER,
             frPortsCfgPort          INTEGER,
             frPortsCfgRowStatus     INTEGER,
             frPortsCfgPortType      INTEGER,
             frPortsCfgPortState     INTEGER,
             frPortsCfgChCnt         INTEGER,
             frPortsCfgPortSpeed     INTEGER,
             frPortsCfgDs0ChSpeed    INTEGER,
             frPortsCfgSigProt       INTEGER,
             frPortsCfgNNIStatus     INTEGER,
             frPortsCfgAsyncUpd      INTEGER,
             frPortsCfgPollVerTimer  INTEGER,
             frPortsCfgErrThresh     INTEGER,
             frPortsCfgMonEveCnt     INTEGER,
             frPortsCfgFrmFlags      INTEGER,
             frPortsCfgLinkTimer     INTEGER,
             frPortsCfgPollCycle     INTEGER,
             frAxPortsCfgSvcRatio    INTEGER,
             frIxPortsCfgClockType   INTEGER,
             frIxPortsCfgVcCount     INTEGER,
             frPortsCfgVcPtr         OBJECT IDENTIFIER,
             frIxPortsCfgMaxTxQDepth INTEGER,
             frIxPortsCfgECNQThresh  INTEGER,
             frIxPortsCfgDEThresh    INTEGER,
             frIxPortsCfgIDEMap      INTEGER,
             frIxPortsCfgCommPri     INTEGER,
             frIxPortsCfgUpRNR       INTEGER,
             frIxPortsCfgLowRNR      INTEGER,
             frIxPortsCfgOamThresh   INTEGER,
             frIxPortsCfgCLLMTimer   INTEGER,
             frIxPortsCfgEFCItoBECN  INTEGER,
             frIxPortsCfgSrRTS       INTEGER,
             frIxPortsCfgSrDTR       INTEGER,
             frIxPortsCfgSrDCD       INTEGER,
             frIxPortsCfgSrCTS       INTEGER,
             frIxPortsCfgSrDSR       INTEGER,
             frIxPortsCfgLoopBack    INTEGER,
             frIxPortsCfgExtConFail  INTEGER,
             frAxPortsCfgLogPort     INTEGER
             }

frPortsCfgNode  OBJECT-TYPE
    SYNTAX      DisplayString (SIZE(1..10))
    ACCESS      read-only
    		-- C-ACCESS-FUNC	FrPortsCfgNode
    		-- C-LOCATOR-FUNC  LocateFrPortsCfgEntry
    STATUS      mandatory
    DESCRIPTION "String identifying the Node"
	::= { frPortsCfgEntry 1 }

frPortsCfgShelf OBJECT-TYPE
    SYNTAX      DisplayString (SIZE(0..10))
    ACCESS      read-only
    		-- C-ACCESS-FUNC	FrPortsCfgShelf
    		-- C-LOCATOR-FUNC  LocateFrPortsCfgEntry
    STATUS      mandatory
    DESCRIPTION "String identifying the shelf"
	::= { frPortsCfgEntry 2 }

frPortsCfgSlot OBJECT-TYPE
    SYNTAX	INTEGER (1..64)
    ACCESS	read-only
    		-- C-ACCESS-FUNC	FrPortsCfgSlot
    		-- C-LOCATOR-FUNC LocateFrPortsCfgEntry
    STATUS	mandatory
    DESCRIPTION	"Slot Number"
	::= { frPortsCfgEntry 3 }

frPortsCfgLine OBJECT-TYPE
    SYNTAX	INTEGER (0..8)
    ACCESS	read-only
    		-- C-ACCESS-FUNC	FrPortsCfgLine
    		-- C-LOCATOR-FUNC  LocateFrPortsCfgEntry
    STATUS	mandatory
    DESCRIPTION	"Line Number. For IPX ports Line Number is always 0"
	::= { frPortsCfgEntry 4 }

frPortsCfgPort OBJECT-TYPE
    SYNTAX	INTEGER (1..64)
    ACCESS	read-only
    		-- C-ACCESS-FUNC	FrPortsCfgPort
    		-- C-LOCATOR-FUNC LocateFrPortsCfgEntry
    STATUS	mandatory
    DESCRIPTION	"Port Number"
	::= { frPortsCfgEntry 5 }

frPortsCfgRowStatus OBJECT-TYPE
    SYNTAX      INTEGER {
			add(1),
			del(2),
			modify(3),
                        up-frp(4),
                        down-frp(5)
			}
    ACCESS	read-write
    		-- C-ACCESS-FUNC	FrPortsCfgRowStatus
    		-- C-LOCATOR-FUNC  LocateFrPortsCfgEntry
    STATUS	mandatory
    DESCRIPTION	"add, del & modify are for both AXIS and IPX ports, but
                 up and down are for IPX only"
	::= { frPortsCfgEntry 6 }

frPortsCfgPortType OBJECT-TYPE
    SYNTAX      INTEGER {
                        frsm(1),
                        frp (2)
                        }
    ACCESS	read-only
    		-- C-ACCESS-FUNC	FrPortsCfgPortType
    		-- C-LOCATOR-FUNC  LocateFrPortsCfgEntry
    STATUS	mandatory
    DESCRIPTION	"Card type, FRP or FRSM"
	::= { frPortsCfgEntry 7 }

frPortsCfgPortState OBJECT-TYPE
    SYNTAX      INTEGER {
                        active(1),
                        inactive(2),
                        remoteLoopback(3),
                        failed(4)
                        }
    ACCESS	read-only
    		-- C-ACCESS-FUNC	FrPortsCfgPortState
    		-- C-LOCATOR-FUNC  LocateFrPortsCfgEntry
    STATUS	mandatory
    DESCRIPTION	"PortState"
	::= { frPortsCfgEntry 8 }

frPortsCfgChCnt	OBJECT-TYPE
    SYNTAX      INTEGER 
    ACCESS      read-only
    		-- C-ACCESS-FUNC	FrPortsCfgChCnt
    		-- C-LOCATOR-FUNC  LocateFrPortsCfgEntry
    STATUS      mandatory
    DESCRIPTION "The number of aggregate channels assigned to this
		port (FRI T1/E1 interface only).
		For subrate ports, this object is always 1."
        ::= { frPortsCfgEntry 9 }

frPortsCfgPortSpeed	OBJECT-TYPE
    SYNTAX	INTEGER 
    ACCESS	read-write
    		-- C-ACCESS-FUNC	FrPortsCfgPortSpeed
    		-- C-LOCATOR-FUNC  LocateFrPortsCfgEntry
    STATUS	mandatory
    DESCRIPTION
		"Configured speed of port in kbps.
                 - Set operation:
                   For subrate(V.35) interface only.
                   For E1/T1, you can set only while adding the port"
	::= { frPortsCfgEntry 10 }

frPortsCfgDs0ChSpeed	OBJECT-TYPE
    SYNTAX	INTEGER 
                       {
                       s56k(1),
                       s64k(2),
                       na(3)
                       }
    ACCESS      read-write
    		-- C-ACCESS-FUNC	FrPortsCfgDs0ChSpeed
    		-- C-LOCATOR-FUNC  LocateFrPortsCfgEntry
    STATUS      mandatory
    DESCRIPTION
		"channel speed.
                 This is not applicable for FRP-V35 subrate ports.
                 Set operation:
                     - Allowed only while adding the port."
	::= { frPortsCfgEntry 11 }

frPortsCfgSigProt	OBJECT-TYPE
    SYNTAX      INTEGER {
 		disabled   (1),
 		lmi-noasyn (2),
 		lmi-asyn   (3),
 		uni-annexA (4),
 		uni-annexD (5),
 		nni-annexA (6),
 		nni-annexD (7)
	}
    ACCESS      read-write
    		-- C-ACCESS-FUNC	FrPortsCfgSigProt
    		-- C-LOCATOR-FUNC  LocateFrPortsCfgEntry
    STATUS      mandatory
    DESCRIPTION "The specified LMI operation mode. The options can be  		1 - (UNI)LMI disabled
                2 - (UNI)LMI enabled but asynchronous update disabled
                3 - (UNI)LMI and asynchronous update enabled
		4 - (UNI)LMI enabled using CCITT O.933 Annex A parameters  		5 - (UNI)LMI enabled using ANSI T1.617 parameters  		6 - (NNI)LMI enabled using CCITT O.933 Annex A parameters  		7 - (NNI)LMI enabled using ANSI T1.617 parameters"
        ::= { frPortsCfgEntry 12 }

frPortsCfgNNIStatus	OBJECT-TYPE
    SYNTAX      INTEGER {
		no  (1),
		yes (2)
	}
    ACCESS      read-only
    		-- C-ACCESS-FUNC	FrPortsCfgNNIStatus
    		-- C-LOCATOR-FUNC  LocateFrPortsCfgEntry
    STATUS      mandatory
    DESCRIPTION "The flag indicating whether NNI is active on the specified
		slot.port.
		- Get Operation:
                This object is always NO if the network manager attempts
                to GET frLportNNIStatus from a disabled or LMI port.
                In other cases, the value of this object is
                determined by whether the port is configured as NNI or not."
        ::= { frPortsCfgEntry 13 }

frPortsCfgAsyncUpd	OBJECT-TYPE
    SYNTAX      INTEGER {
		no(1),
		yes(2)
	}
    ACCESS      read-write
    		-- C-ACCESS-FUNC	FrPortsCfgAsyncUpd
    		-- C-LOCATOR-FUNC  LocateFrPortsCfgEntry
    STATUS      mandatory
    DESCRIPTION "The flag indicating whether the IPX should send unsolicited
                 LMI update messages as they appear or wait for the polling
                 from the user device. This object is applicable to only
                 Annex A/D UNI and Annex A/D NNI protocols for write and
                 LMI, Annex A/D UNI and Annex A/D NNI for read.
                 - Get Operation:
                 This object is always NO for ports without protocols;
                 otherwise, its value is determined by the asynchronous
                 status of the port.
                 - Set Operation:
                 If the network manager attempts to SET this object of a
                 port with none or LMI protocol, an error is reported."

        ::= { frPortsCfgEntry 14 }

frPortsCfgPollVerTimer	OBJECT-TYPE
    SYNTAX      INTEGER
    ACCESS      read-write
    		-- C-ACCESS-FUNC	FrPortsCfgPollVerTimer
    		-- C-LOCATOR-FUNC  LocateFrPortsCfgEntry
    STATUS      mandatory
    DESCRIPTION "The link integrity verification timer heartbeat (keep-alive)
  		period. It should be set to 5 seconds more than the heartbeat
		time in the user device.
                The valid range is (5..30)
		- Get Operation:
		  Since this object is not applicable to disabled protocol,
		  (-1) is returned if the network manager attempts
		  to GET this object from a port without protocols.
		- Set Operation:
		  If the network manager attempts to SET this object 
                  of a port without any protocol, an error is reported."
    DEFVAL { 15 }
        ::= { frPortsCfgEntry 15 }

frPortsCfgErrThresh	OBJECT-TYPE
    SYNTAX      INTEGER
    ACCESS      read-write
    		-- C-ACCESS-FUNC	FrPortsCfgErrThresh
    		-- C-LOCATOR-FUNC  LocateFrPortsCfgEntry
    STATUS      mandatory
    DESCRIPTION "The number of the failures in the monitored events that
		cause the keep-alive process to report an alarm. 
                The valid range is (1..10).
		- Get Operation:
		  Since this object is not applicable to disabled protocol,
		  (-1) is returned if the network manager attempts
		  to GET this object from a port without protocols.
		- Set Operation:
		  If the network manager attempts to SET this object 
                  of a port without any protocol, an error is reported."
        ::= { frPortsCfgEntry 16 }

frPortsCfgMonEveCnt	OBJECT-TYPE
    SYNTAX      INTEGER
    ACCESS      read-write
    		-- C-ACCESS-FUNC	FrPortsCfgMonEveCnt
    		-- C-LOCATOR-FUNC  LocateFrPortsCfgEntry
    STATUS      mandatory
    DESCRIPTION "The number of monitored events for the keep-alive process.
		A port communication fail condition is cleared after this
		number of successful polling cycles. 
                The valid range is (1..10)
		- Get Operation:
		  Since this object is not applicable to disabled protocol,
		  (-1) is returned if the network manager attempts
		  to GET this object from a port without protocols.
		- Set Operation:
		  If the network manager attempts to SET this object 
                  of a port without any protocol, an error is reported."
        ::= { frPortsCfgEntry 17 }

frPortsCfgFrmFlags	OBJECT-TYPE
    SYNTAX      INTEGER 
    ACCESS      read-write
    		-- C-ACCESS-FUNC	FrPortsCfgFrmFlags
    		-- C-LOCATOR-FUNC  LocateFrPortsCfgEntry
    STATUS      mandatory
    DESCRIPTION "The minimum number of flags between frames.
                 The valid range for AXIS-FRSM ports is (1..10)
                 The valid range for IPX-FRP  ports is (1..255)"
    DEFVAL { 1 }
        ::= { frPortsCfgEntry 18 }

frPortsCfgLinkTimer	OBJECT-TYPE
    SYNTAX	INTEGER
    ACCESS	read-write
    		-- C-ACCESS-FUNC	FrPortsCfgLinkTimer
    		-- C-LOCATOR-FUNC  LocateFrPortsCfgEntry
    STATUS	mandatory
    DESCRIPTION	"T391 - Link Integrity Timer (applicable to
	        NNI port only), indicating the interval at which
		a Status Enquiry message is sent.
		The valid range is (5..30)
		- Get Operation:
	          the network manager attempts to GET this object 
                  from a port with a protocol other than NNIs, 
                  (-1) is returned.
		- Set Operation:
		  If the network manager attempts to SET this object 
                  of a port with a protocol other than NNIs, 
                  an error is reported"
    DEFVAL { 10 }
	::= { frPortsCfgEntry 19 }

frPortsCfgPollCycle	OBJECT-TYPE
    SYNTAX	INTEGER (1..255)
    ACCESS	read-write
    		-- C-ACCESS-FUNC	FrPortsCfgPollCycle
    		-- C-LOCATOR-FUNC  LocateFrPortsCfgEntry
    STATUS	mandatory
    DESCRIPTION	"N391 - Full Status Polling Cycle.
                 Applicable to NNI ports only in case of IPX frp.
                 - Get Operation(for IPX-frp):
                   If the network manager attempts to GET this object from
                   a port with a protocol other than NNIs, (-1) is returned.
                 - Set Operation(for IPX-frp):
                   If the network manager attempts to SET this object of a port
                   with a protocol other than NNIs, an error is reported."
	::= { frPortsCfgEntry 20 }

frAxPortsCfgSvcRatio	OBJECT-TYPE
	SYNTAX	INTEGER
	ACCESS	read-write
    		-- C-ACCESS-FUNC	FrPortsCfgSvcRatio
    		-- C-LOCATOR-FUNC  LocateFrPortsCfgEntry
	STATUS	mandatory
	DESCRIPTION
		"Number of times queue 2 is serviced 
		 for every time queue 3 is serviced
                 The valid range is (1..15).
                 Only applicable to AXIS-FRSM ports.
                 The value (-2) will be returned for IPX-FRP ports."
    DEFVAL { 1 }
	::= { frPortsCfgEntry 21 }

frIxPortsCfgClockType	OBJECT-TYPE
    SYNTAX      INTEGER {
		normal (1),
		looped (2),
		none   (3)
	}
    ACCESS      read-write
    		-- C-ACCESS-FUNC	FrPortsCfgClockType
    		-- C-LOCATOR-FUNC  LocateFrPortsCfgEntry
    STATUS      mandatory
    DESCRIPTION "The type of port clock (FRI subrate interface only). 
                 For T1/E1 interface this object should be none.
 		 - Get Operation:
 		   If the network manager attempts to get this object 
                   from a T1/E1 port, none(3) is returned.
 		 - Set Operation:
 		   If the network manager attempts to set this object 
                   on a T1/E1 port an error is returned.
                 Only applicable to IPX-FRP ports.
                 The value (-2) will be returned for AXIS-FRSM ports."
        ::= { frPortsCfgEntry 22 }

frIxPortsCfgVcCount	OBJECT-TYPE
    SYNTAX      INTEGER
    ACCESS      read-only
    		-- C-ACCESS-FUNC	FrPortsCfgVcCount
    		-- C-LOCATOR-FUNC  LocateFrPortsCfgEntry
    STATUS      mandatory
    DESCRIPTION "The number of virtual connections that terminate on  		 this port. Note that there can be up to 252 connections  		 per FRP cards shared among the ports. A port may have up  		 to 252 connections allocated.
                 The valid range is (0..252).
                 Only applicable to IPX-FRP ports.
                 The value (-2) will be returned for AXIS-FRSM ports."
        ::= { frPortsCfgEntry 23 }

frPortsCfgVcPtr	OBJECT-TYPE
    SYNTAX      OBJECT IDENTIFIER 
    ACCESS      read-only
    		-- C-ACCESS-FUNC	FrPortsCfgVcPtr
    		-- C-LOCATOR-FUNC  LocateFrPortsCfgEntry
    STATUS      mandatory
    DESCRIPTION "The object identifier denoting the first endpoint 
                associated with  this port. For current implementation, 
                this OID points to the first frame relay connection
                on the port. It has a NULL OID value (i.e. { 0 0 }) if 
                there is no frame relay connection on this port. The 
                management station can retrieve all the information about 
                the first connection by reading from row pointed to by 
                this OID. Specifically, this OID specifies the first
                column of the appropriate row in the frEndptTable."
        ::= { frPortsCfgEntry 24 }

frIxPortsCfgMaxTxQDepth	OBJECT-TYPE
    SYNTAX      INTEGER
    ACCESS      read-write
    		-- C-ACCESS-FUNC	FrPortsCfgMaxTxQDepth
    		-- C-LOCATOR-FUNC  LocateFrPortsCfgEntry
    STATUS      mandatory
    DESCRIPTION "The maximum bytes queued for transmission from the 
                 FRP port. 
                 The valid range is (0..65535).
                 Only applicable to IPX-FRP ports.
                 The value (-2) will be returned for AXIS-FRSM ports."
    DEFVAL { 65535 }
        ::= { frPortsCfgEntry 25 }

frIxPortsCfgECNQThresh	OBJECT-TYPE
    SYNTAX      INTEGER
    ACCESS      read-write
    		-- C-ACCESS-FUNC	FrPortsCfgECNQThresh
    		-- C-LOCATOR-FUNC  LocateFrPortsCfgEntry
    STATUS      mandatory
    DESCRIPTION "Port explicit congestion notification threshold. 
                 This is the point at which the BECN and FECN bits 
                 will be set in the communications to the user device.
                 The valid range is (0..65535).
                 Only applicable to IPX-FRP ports.
                 The value (-2) will be returned for AXIS-FRSM ports."
    DEFVAL { 65535 }
        ::= { frPortsCfgEntry 26 }

frIxPortsCfgDEThresh	OBJECT-TYPE
    SYNTAX      INTEGER
    ACCESS      read-write
    		-- C-ACCESS-FUNC	FrPortsCfgDEThresh
    		-- C-LOCATOR-FUNC  LocateFrPortsCfgEntry
    STATUS      mandatory
    DESCRIPTION "The percentage of the queue depth above which frames  		 with the Discard Eligibility bit set will be discarded.
 		 An entry of 100% effectively disables DE for the port.
                 The valid range is (0..100)
                 Only applicable to IPX-FRP ports.
                 The value (-2) will be returned for AXIS-FRSM ports."
    DEFVAL { 100 }
        ::= { frPortsCfgEntry 27 }

frIxPortsCfgIDEMap	OBJECT-TYPE
    SYNTAX      INTEGER {
 		no  (1),
 		yes (2)
	}
    ACCESS      read-write
    		-- C-ACCESS-FUNC	FrPortsCfgIDEMap
    		-- C-LOCATOR-FUNC  LocateFrPortsCfgEntry
    STATUS      mandatory
    DESCRIPTION "The flag indicating whether IDE to DE mapping should be  		 performed.
                 Only applicable to IPX-FRP ports.
                 The value (-2) will be returned for AXIS-FRSM ports."
    DEFVAL { yes }
        ::= { frPortsCfgEntry 28 }

frIxPortsCfgCommPri	OBJECT-TYPE
    SYNTAX      INTEGER {
		no   (1),
		yes  (2)
	}
    ACCESS      read-write
    		-- C-ACCESS-FUNC	FrPortsCfgCommPri
    		-- C-LOCATOR-FUNC  LocateFrPortsCfgEntry
    STATUS      mandatory
    DESCRIPTION "The flag specifying if the connection SNA priority should
                 be communicated to the user device attached to the port.
                 - Get Operation:
                   Since this object is specific to LMI protocols,
                   (-1) is returned if the network manager attempts 
                   to GET this object from a non-LMI port.
                 - Set Operation:
                   Likewise, if the network manager attempts to SET 
                   this object of a non-LMI port, an error is reported.
                 Only applicable to IPX-FRP ports.
                 The value (-2) will be returned for AXIS-FRSM ports."
        ::= { frPortsCfgEntry 29 }

frIxPortsCfgUpRNR	OBJECT-TYPE
    SYNTAX      INTEGER
    ACCESS      read-write
    		-- C-ACCESS-FUNC	FrPortsCfgUpRNR
    		-- C-LOCATOR-FUNC  LocateFrPortsCfgEntry
    STATUS      mandatory
    DESCRIPTION "The upper Receiver-Not-Ready threshold. This threshold 
		specifies the number of receiver not ready indications
		from the user equipment before an alarm is generated for
		this connection. 
                The valid range is (1..100)  		- Get Operation:
 		  Since this object is specific to LMI protocols,  		  (-1) is returned if the network manager attempts 
                  to GET this object from a non-LMI port.
 		- Set Operation:
 		  Likewise, if the network manager attempts to SET
                  this object of a non-LMI port, an error is reported.
                Only applicable to IPX-FRP ports.
                The value (-2) will be returned for AXIS-FRSM ports."
    DEFVAL { 75 }
        ::= { frPortsCfgEntry 30 }

frIxPortsCfgLowRNR	OBJECT-TYPE
    SYNTAX      INTEGER 
    ACCESS      read-write
    		-- C-ACCESS-FUNC	FrPortsCfgLowRNR
    		-- C-LOCATOR-FUNC  LocateFrPortsCfgEntry
    STATUS      mandatory
    DESCRIPTION "The Lower Receiver-Not-Ready threshold. This threshold
                 specifies the number of receiver not ready indications
                 from the user equipment before an alarm is cleared for
                 this connection. 
                 The valid range is (1..100)
                 - Get Operation:
                   Since this object is specific to LMI protocols, 
                   (-1) is returned if the network manager attempts
                   to GET this object from a non-LMI port.
                 - Set Operation:
                   Likewise, if the network manager attempts to SET 
                   this object of a non-LMI port, an error is reported.
                 Only applicable to IPX-FRP ports.
                 The value (-2) will be returned for AXIS-FRSM ports."
    DEFVAL { 75 }
        ::= { frPortsCfgEntry 31 }

frIxPortsCfgOamThresh	OBJECT-TYPE
    SYNTAX	INTEGER
    ACCESS	read-write
    		-- C-ACCESS-FUNC	FrPortsCfgOamThresh
    		-- C-LOCATOR-FUNC  LocateFrPortsCfgEntry
    STATUS	mandatory
    DESCRIPTION	"The alarm threshold for number of OAM heartbeat
		 FastPackets missed before propagating A-bit=0.
		 This threshold is applicable to both UNI and NNI
		 Frame Relay ports when the node has FR NNI feature enabled
		 and this FRP firmware supports it.
                 The valid range is (0..15).
		 - Get Operation:
		   Since this object is not applicable to disabled protocol,
		   (-1) is returned if the network manager attempts
		   to GET this object from a port without protocols.
		 - Set Operation:
		   If the network manager attempts to SET this object 
                   of a port without any protocol, an error is reported.
                 Only applicable to IPX-FRP ports.
                 The value (-2) will be returned for AXIS-FRSM ports."
	::= { frPortsCfgEntry 32 }	

frIxPortsCfgCLLMTimer	OBJECT-TYPE
    SYNTAX      INTEGER 
    ACCESS      read-write
    		-- C-ACCESS-FUNC	FrPortsCfgCLLMTimer
    		-- C-LOCATOR-FUNC  LocateFrPortsCfgEntry
    STATUS      mandatory
    DESCRIPTION "The timer for CLLM messages in CLLM intervals. 
                 No CLLM if 0 is configured. If a user configures this 
                 value to be greater than 0 then it should be in the 
                 range 4 to 35. The unit is hundredth of a sec.  
                 Note that ForeSight (CLLM) is available only if the 
                 firmware supports it.
                 - Get Operation:
                   If the network manager attempts to GET this object 
                   from a port where ForeSight is not supported, 
                   (-1) is returned.
                 - Set Operation:
                   If the network manager attempts to SET this object 
                   of a port where ForeSight is not supported, 
                   an error is reported.
                 Only applicable to IPX-FRP ports.
                 The value (-2) will be returned for AXIS-FRSM ports."
    	::= { frPortsCfgEntry 33 }

frIxPortsCfgEFCItoBECN	OBJECT-TYPE
    SYNTAX      INTEGER {
		no  (1),
		yes (2),
                none(3)
	}
    ACCESS      read-write
    		-- C-ACCESS-FUNC	FrPortsCfgEFCItoBECN
    		-- C-LOCATOR-FUNC  LocateFrPortsCfgEntry
    STATUS      mandatory
    DESCRIPTION "This object indicates whether EFCI to BECN mapping
		 is enabled.
                 Only applicable to IPX-FRP ports.
                 The value (-2) will be returned for AXIS-FRSM ports."
        ::= { frPortsCfgEntry 34 }

frIxPortsCfgSrRTS	OBJECT-TYPE
    SYNTAX      INTEGER {
 		off (1),
 		on  (2),
 		none(3)
	}
    ACCESS      read-only
    		-- C-ACCESS-FUNC	FrPortsCfgSrRTS
    		-- C-LOCATOR-FUNC  LocateFrPortsCfgEntry
    STATUS      mandatory
    DESCRIPTION "The current status of the RTS lead (subrated FRI only).
 		 none is used for T1/E1 FRI.
 		 - Get Operation:
		   This object is valid only if the port is subrated 
                   and DTE.  Otherwise, none(3) is returned.
                 Only applicable to IPX-FRP ports.
                 The value (-2) will be returned for AXIS-FRSM ports."
        ::= { frPortsCfgEntry 35 }

frIxPortsCfgSrDTR	OBJECT-TYPE
    SYNTAX      INTEGER {
		off (1),
		on  (2),
		none(3)
	}
    ACCESS      read-only
    		-- C-ACCESS-FUNC	FrPortsCfgSrDTR
    		-- C-LOCATOR-FUNC  LocateFrPortsCfgEntry
    STATUS      mandatory
    DESCRIPTION "The current status of the DTR lead (subrated FRI only).
 		 none is used for T1/E1 FRI.
 		 - Get Operation:
		   This object is valid only if the port is subrated 
                   and DTE.  Otherwise, none(3) is returned.
                 Only applicable to IPX-FRP ports.
                 The value (-2) will be returned for AXIS-FRSM ports."
        ::= { frPortsCfgEntry 36 }

frIxPortsCfgSrDCD	OBJECT-TYPE
    SYNTAX      INTEGER {
		off (1),
		on  (2),
		none(3)
	}
    ACCESS      read-only
    		-- C-ACCESS-FUNC	FrPortsCfgSrDCD
    		-- C-LOCATOR-FUNC  LocateFrPortsCfgEntry
    STATUS      mandatory
    DESCRIPTION "The current status of the DCD lead (subrated FRI only).
 		 none is used for T1/E1 FRI.
 		 - Get Operation:
 		   This object is valid only if the port is subrated 
                   and DCE.  Otherwise, none(3) is returned.
                 Only applicable to IPX-FRP ports.
                 The value (-2) will be returned for AXIS-FRSM ports."
        ::= { frPortsCfgEntry 37 }

frIxPortsCfgSrCTS	OBJECT-TYPE
    SYNTAX      INTEGER {
		off (1),
		on  (2),
		none(3)
	}
    ACCESS      read-only
    		-- C-ACCESS-FUNC	FrPortsCfgSrCTS
    		-- C-LOCATOR-FUNC  LocateFrPortsCfgEntry
    STATUS      mandatory
    DESCRIPTION "The current status of the CTS lead (subrated FRI only).
 		 none is used for T1/E1 FRI.
 		 - Get Operation:
 		   This object is valid only if the port is subrated 
                   and DCE.  Otherwise, none(3) is returned.
                 Only applicable to IPX-FRP ports.
                 The value (-2) will be returned for AXIS-FRSM ports."
        ::= { frPortsCfgEntry 38 }

frIxPortsCfgSrDSR	OBJECT-TYPE
    SYNTAX      INTEGER {
		off (1),
		on  (2),
		none(3)
        }
    ACCESS      read-only
    		-- C-ACCESS-FUNC	FrPortsCfgSrDSR
    		-- C-LOCATOR-FUNC  LocateFrPortsCfgEntry
    STATUS      mandatory
    DESCRIPTION "The current status of the DSR lead (subrated FRI only).
 		 none is used for T1/E1 FRI.
 		 - Get Operation:
 		   This object is valid only if the port is subrated 
                   and DCE.  Otherwise, none(3) is returned.
                 Only applicable to IPX-FRP ports.
                 The value (-2) will be returned for AXIS-FRSM ports."
	::= { frPortsCfgEntry 39 }

frIxPortsCfgLoopBack	OBJECT-TYPE
    SYNTAX      INTEGER {
		none (1),
		local(2)
	}
    ACCESS      read-only
    		-- C-ACCESS-FUNC	FrPortsCfgLoopBack
    		-- C-LOCATOR-FUNC  LocateFrPortsCfgEntry
    STATUS      mandatory
    DESCRIPTION "The loopback mode.
                 Only applicable to IPX-FRP ports.
                 The value (-2) will be returned for AXIS-FRSM ports."
        ::= { frPortsCfgEntry 40 }

frIxPortsCfgExtConFail	OBJECT-TYPE
    SYNTAX      INTEGER {
		false (1),
		true  (2)
	}
    ACCESS      read-only
    		-- C-ACCESS-FUNC	FrPortsCfgExtConFail
    		-- C-LOCATOR-FUNC  LocateFrPortsCfgEntry
    STATUS      mandatory
    DESCRIPTION "The flag indicating if the connection with the external  		 device is lost.
                 Only applicable to IPX-FRP ports.
                 The value (-2) will be returned for AXIS-FRSM ports."
        ::= { frPortsCfgEntry 41 }

frAxPortsCfgLogPort	OBJECT-TYPE
	SYNTAX	INTEGER
	ACCESS	read-only
    		-- C-ACCESS-FUNC	FrPortsCfgLogPort
    		-- C-LOCATOR-FUNC  LocateFrPortsCfgEntry
	STATUS	mandatory
	DESCRIPTION
		"Logical port for the given physical port.
                 Only applicable to AXIS-FRSM ports.
                 The value (-2) will be returned for IPX-FRP ports."
	::= { frPortsCfgEntry 42 }

------------------------------------------------------------------ 
--	ERROR STATUS TABLE
--
-- This object contains the value of the request id for the latest 
-- entry in the error status table. 
-- This value can be used to retrieve the error code and description 
-- for the last SET operation failed.
--
ppaErrorLastIndex	OBJECT-TYPE
	SYNTAX	INTEGER 
	ACCESS	read-only
	-- C-ACCESS-FUNC ppaErrorLastIndex
	STATUS	mandatory
	DESCRIPTION "If at least one entry exists in the error status table, 
		     the value of this object contains the index corresponding 
		     to the last entry inserted in the table. If no entries
		     have ever been inserted in the ppaErrorTable, then
		     the agent will return 0 for a query of this variable.

                     Actually this object is not required any more because
                     of the new objects ppaErrorLastDesc and ppaErrorLastEcode.
                     One can do GET directly on ppaErrorLastDesc/LastEcode."
        ::= { portSvc 8 }

ppaErrorFlushAll  OBJECT-TYPE
    SYNTAX      INTEGER {
                noOp(1),
		flush(2)
        }
    ACCESS      read-write
	-- C-ACCESS-FUNC ppaErrorFlushAll
    STATUS      mandatory
    DESCRIPTION "Setting this object to the value 'flush' indicates to
		 the agent that a manager would like the ppaErrorTable
		 to be immediately flushed of all entries.

		 A management retrieval of this object will always return
		 the value 'noOp'.

		 Setting this object to the value 'noOp' is invalid."
        ::= { portSvc 9 }

--
-- The following table is used to maintain status information about 
-- SNMP GET/SET requests from a Manager.  When an SNMP GET/SET fails, an 
-- entry in this table is created and the object ppaErrorLastIndex 
-- is updated.
--
-- Note that currently only SET errors are updated in this error table.
--
ppaErrorTable OBJECT-TYPE 
    SYNTAX      SEQUENCE OF PpaErrorEntry
    ACCESS      not-accessible
    STATUS      mandatory
    DESCRIPTION "A List of recent Errors reported by the 
		 Ports Proxy Agent (PPA)."
        ::= { portSvc 10 }

ppaErrorEntry OBJECT-TYPE
    SYNTAX      PpaErrorEntry
    ACCESS      not-accessible
    STATUS      mandatory
    DESCRIPTION "A General Error Status Entry."
    INDEX   { ppaErrorReqId }
	-- C-NEXT-FUNC NextErrorEntry
        ::= { ppaErrorTable 1  }

PpaErrorEntry ::= SEQUENCE {
        ppaErrorReqId			INTEGER,    
        ppaErrorDesc			DisplayString,
        ppaErrorEcode			INTEGER
}

ppaErrorReqId OBJECT-TYPE
    SYNTAX      INTEGER 
    ACCESS      read-only
	-- C-ACCESS-FUNC ppaErrorReqId
    	-- C-LOCATOR-FUNC  LocateErrorEntry
    STATUS      mandatory
    DESCRIPTION "This object contains the PDU request ID associated with
                 the SET request. The manager must use this information to
		 find the error associated with a particular SNMP request.
	
		 Note that an SNMP request ID may be reused by
		 the same manager.  When this occurs,
	 	 the older entry in the table will be replaced with the
		 new error status.  Managers must be aware that
		 error information may therefore be lost."
        ::= { ppaErrorEntry 1  }

ppaErrorDesc OBJECT-TYPE
    SYNTAX      DisplayString (SIZE(1..255))
    ACCESS      read-only
	-- C-ACCESS-FUNC ppaErrorDesc
    	-- C-LOCATOR-FUNC  LocateErrorEntry
    STATUS      mandatory
    DESCRIPTION "This object contains error status information for failed
                 SETS to one or more objects in one or more of the 
		 following tables:

			frPortsCfgTable

		 Rows in this table may be created as the result of
		 a failed SNMP SET operation.

		 Since the SNMP standard allows only limited number of
		 error result codes, the managers can retrieve this
		 variable to get additional information on a failed 
		 SET operation. Typically this object will contain 
		 a user friendly description of the cause of the error."
        ::= { ppaErrorEntry 2 }

ppaErrorEcode OBJECT-TYPE
    SYNTAX      INTEGER 
			{   
			invalid-network(1),
			-- No such Network(domain) in the Database
			invalid-node(2),
			-- No such Node in the Database
			invalid-shelf(3),
			-- No such Nhelf for the given node
			invalid-release(4),
			-- Unsupported release fot the given Node/Shelf
			node-timeout(5),
			-- Timeout from the given Node/Shelf
			node-busy(6),
			-- Node is busy processing other requests
			no-snmpcomm(7),
			-- The demon process snmpcomm is not running
			snmpcomm-error(8),
			-- Internal error at the demon process snmpcomm
			node-error(9),
			-- Error at the embedded Agent
			bad-value(10),
			-- Bad value for the given Object
			port-not-found(11),
			-- The specified port does not exists
			slot-is-full(12),
			-- AddPort error, no more ports on this slot
			rowstatus-missing(100),
			-- RowStatus object is missing from the SET request
			port-exists(101),
                        -- AddPort error, port already exists
			invalid-slot(102),
			-- No such slot
			invalid-line(103),
			-- No such line
			line-is-full(104),
			-- AddPort error, no more ports on this line
			multiple-ports(105),
			-- Multiple ports are specified in the request
			port-reserved(106),
			-- Port is Reserved for internal use(Signalling)
			na-frsm(107),
			-- This object is not applicable for FRSM ports
			na-frp(108),
			-- This object is not applicable for FRP ports
			no-up-down-frsm(109),
			-- RowStatus can not be up-frp and down-frp for frsm ports
			invalid-set(110),
			-- SET is allowed for addport only
			illegal-set(111),
			-- Dependency on other parameter values
			partial-add(112),
			-- Added the port, but unable to modify params
			no-error-entry(500),
			-- No entries available in the ErrorTable
			not-applicable(501),
			-- Error Code not relevant, rely on Error Description
			invalid-flushall(502)
			-- Can not set to noOp for ppaErrorFlushAll
			}
    ACCESS      read-only
	-- C-ACCESS-FUNC ppaErrorEcode
    	-- C-LOCATOR-FUNC  LocateErrorEntry
    STATUS      mandatory
    DESCRIPTION "This object contains the error Code of the GET/SET operation.
		 The error Codes from 500 onwards are specific to the
                 Error Table operation itself.
                 Note that currently GET errors are not updated in the
                 error table."
        ::= { ppaErrorEntry 3  }

ppaErrorLastDesc	OBJECT-TYPE
    	SYNTAX		DisplayString (SIZE(0..255))
	ACCESS		read-only
			-- C-ACCESS-FUNC ppaErrorLastDesc
	STATUS		mandatory
	DESCRIPTION "This contains the error description of the last error
		 generated. If error table contains no errors, GET on
                 this will return NULL string"
        ::= { portSvc 11 }

ppaErrorLastEcode	OBJECT-TYPE
    SYNTAX      INTEGER 
			{   
			invalid-network(1),
			-- No such Network(domain) in the Database
			invalid-node(2),
			-- No such Node in the Database
			invalid-shelf(3),
			-- No such Nhelf for the given node
			invalid-release(4),
			-- Unsupported release fot the given Node/Shelf
			node-timeout(5),
			-- Timeout from the given Node/Shelf
			node-busy(6),
			-- Node is busy processing other requests
			no-snmpcomm(7),
			-- The demon process snmpcomm is not running
			snmpcomm-error(8),
			-- Internal error at the demon process snmpcomm
			node-error(9),
			-- Error at the embedded Agent
			bad-value(10),
			-- Bad value for the given Object
			port-not-found(11),
			-- The specified port does not exists
			slot-is-full(12),
			-- AddPort error, no more ports on this slot
			rowstatus-missing(100),
			-- RowStatus object is missing from the SET request
			port-exists(101),
                        -- AddPort error, port already exists
			invalid-slot(102),
			-- No such slot
			invalid-line(103),
			-- No such line
			line-is-full(104),
			-- AddPort error, no more ports on this line
			multiple-ports(105),
			-- Multiple ports are specified in the request
			port-reserved(106),
			-- Port is Reserved for internal use(Signalling)
			na-frsm(107),
			-- This object is not applicable for FRSM ports
			na-frp(108),
			-- This object is not applicable for FRP ports
			no-up-down-frsm(109),
			-- RowStatus can not be up-frp and down-frp for frsm ports
			invalid-set(110),
			-- SET is allowed for addport only
			illegal-set(111),
			-- Dependency on other parameter values
			partial-add(112),
			-- Added the port, but unable to modify params
			no-error-entry(500),
			-- No entries available in the ErrorTable
			not-applicable(501),
			-- Error Code not relevant, rely on Error Description
			invalid-flushall(502)
			-- Can not set to noOp for ppaErrorFlushAll
			}
	ACCESS		read-only
			-- C-ACCESS-FUNC ppaErrorLastEcode
	STATUS		mandatory
	DESCRIPTION "This contains the error code of the last error
		 generated. If error table contains no errors, 
                 GET on this object returns 500"
        ::= { portSvc 12 }


-- The following few defs are duplicate. The same defs have been defined 
-- in the SV+Network.mib. 

-- trapsConfig 		OBJECT IDENTIFIER ::= { rtm 1 }

-- lastSequenceNumber	OBJECT-TYPE
-- 	SYNTAX		INTEGER
-- 	ACCESS		read-only
-- 			C-STRUCT proxy-ctxt, FIELD 	lastTrapSeqNum
-- 	STATUS		mandatory
-- 	DESCRIPTION	"The Sequence Number of the last trap generated on the SNMP Proxy"
-- 	::=		{ trapsConfig 3 }


userConnCleared	TRAP-TYPE
	ENTERPRISE	svplus
	VARIABLES	{ 	
				lastSequenceNumber,
				connectionLocalEndPt,
				connectionLocalStr,
				connectionRemoteEndPt,
				connectionRemoteStr,
				connectionOpStatus,
				connectionAbitStatus,
				connectionType
			}
	DESCRIPTION	"The ' User Connection has recovered from failed/downed state"
	::= 10000

userConnFailed	TRAP-TYPE
	ENTERPRISE	svplus
	VARIABLES	{ 	
				lastSequenceNumber,
				connectionLocalEndPt,
				connectionLocalStr,
				connectionRemoteEndPt,
				connectionRemoteStr,
				connectionOpStatus,
				connectionAbitStatus,
				connectionType
			}
	DESCRIPTION	"The User Connection has failed"
	::= 10001

userConnDown	TRAP-TYPE
	ENTERPRISE	svplus
	VARIABLES	{ 	
				lastSequenceNumber,
				connectionLocalEndPt,
				connectionLocalStr,
				connectionRemoteEndPt,
				connectionRemoteStr,
				connectionOpStatus,
				connectionAbitStatus,
				connectionType
			}
	DESCRIPTION	"The User Connection has been downed"
	::= 10002

-- The following describes the MIB variables for the atmTrunks table. 
--
-- --------------------------------------
--  Configuring a physical/virtual trunk:
-- --------------------------------------
-- -----------------------------------------------------------------------------
--                      |      Before addtrk       |      After addtrk         |
-- -----------------------------------------------------------------------------
--     Trunk Params     |   PHY TRK   |   VIR TRK  |   PHY TRK   |   VIR TRK   |
-- -----------------------------------------------------------------------------
--  atmTrkXmitRate      |     Yes     |    Yes     |     No      |      No     |
--  atmTrksResChans     |     No      |    Yes     |     No      |      Yes    |
--  atmTrkVPI           |     No      |    Yes     |     No      |      No     |
--  atmTrkType          |     No      |    Yes     |     No      |      No     |
--  atmTrkTrfCls        |     Yes     |    Yes     |     Yes     |      Yes    |
--  atmTrkPassSync      |     Yes     |    Yes     |     Yes     |      Yes    |
--  atmTrkStatRes       |     Yes     |    Yes     |     Yes     |      Yes    |
--  atmTrkLoopClock     |     Yes     |    Yes     |     Yes     |      Yes    |
--  atmTrkSvcChannels   |     Yes     |    No      |     No      |      No     |
--  atmTrkSvcBw         |     Yes     |    No      |     No      |      No     |
-- -----------------------------------------------------------------------------      
--      
-- Note: Above table lists ATM trunk parameters which can be configured before 
--       addtrk or after. This table can be refererence before adding a trunk 
--       or after adding a trunk. 
--      
--      

atmTrunks OBJECT-TYPE
    SYNTAX      SEQUENCE OF AtmTrkEntry
    ACCESS      not-accessible
    STATUS      mandatory
    DESCRIPTION "A list of atmTrk interfaces"
    --DEFAULT   test-function test-atmrtetrktable
    --DEFAULT   next-function next-atmrtetrktable
    --DEFAULT   get-function  get-atmrtetrktable-%t
        ::= { trunkServiceObjects 2  }
  
atmTrkEntry OBJECT-TYPE
    SYNTAX      AtmTrkEntry
    ACCESS      not-accessible
    STATUS      mandatory
    DESCRIPTION "A interface entry"
    INDEX       { switchIfIndex }
        ::= { atmTrunks 1  }
  
AtmTrkEntry ::=
    SEQUENCE {
        atmTrkStatus    INTEGER,
        atmTrkAlmEnable INTEGER,
        atmTrkComStatus INTEGER,
        atmTrkRcvRate   INTEGER,
        atmTrkTrnsCap   INTEGER,
        atmTrkTrnsLoad  INTEGER,
        atmTrkRcvCap    INTEGER,
        atmTrkRcvLoad   INTEGER,
        atmTrkType      INTEGER,
        atmTrkVPI       INTEGER,
        atmTrkResChans  INTEGER,
        atmTrkTrafCls   INTEGER,
        atmTrkOeNdType  INTEGER,
        atmTrkOeName    DisplayString,
        atmTrkOeIpAddr  IpAddress,
        atmTrkOeIfIndex INTEGER,
        atmTrkOeDomain  INTEGER,

        atmTrkSvcChannels INTEGER,
        atmTrkShareLcn    INTEGER,
        atmTrkSvcLcnLow   INTEGER,
        atmTrkSvcLcnHigh  INTEGER,
        atmTrkSvcVpiLow   INTEGER,
        atmTrkSvcVpiHigh  INTEGER,
        atmTrkSvcVciLow   INTEGER,
        atmTrkSvcVciHigh  INTEGER,
        atmTrkSvcQbinBitMap  OCTET STRING,
        atmTrkSvcQbinSz   INTEGER,
        atmTrkSvcBw       INTEGER,
        atmTrkSvcInUse    INTEGER,

        atmTrkXmitRate      INTEGER,
        atmTrkPassSync      INTEGER,
        atmTrkStatRes       INTEGER,
        atmTrkLoopClock     INTEGER,
        atmTrkBdataBTxQlen  INTEGER,       
        atmTrkBdataBRxQlen  INTEGER,
        atmTrkBdataBTxEfcn  INTEGER,
        atmTrkBdataBRxEfcn  INTEGER,
        atmTrkBdataBTxHiClp INTEGER,
        atmTrkBdataBRxHiClp INTEGER,
        atmTrkBdataBTxLoClp INTEGER,
        atmTrkBdataBRxLoClp INTEGER,
        atmTrkMaxChanPort   INTEGER,
        atmTrkLinkType      INTEGER,
        atmTrkDerouteDelayTimer INTEGER,
        atmTrkGtwyChCount   INTEGER,
        atmTrkRetainedLinks INTEGER,
        atmTrkImaWindowSize INTEGER,
        atmTrkImaTrnsCnts   INTEGER,
        atmTrkImaReenableTimer INTEGER
    }
           
atmTrkStatus OBJECT-TYPE
    SYNTAX      INTEGER {
                clear(1),
                minor(2),
                major(3),
                down(4),
                deact(5)
        }
    ACCESS      read-only
    STATUS      mandatory
    DESCRIPTION "Alarms state for logical interface table row."
        ::= { atmTrkEntry 1  }
 
atmTrkAlmEnable OBJECT-TYPE
    SYNTAX      INTEGER {
                enable(1),
                disable(2)
        }
    ACCESS      read-write
    STATUS      mandatory
    DESCRIPTION "A writable object to disable a trunk alarm."
    --DEFAULT   test-function test-trkalmenable
        ::= { atmTrkEntry 2  }
 
atmTrkComStatus OBJECT-TYPE
    SYNTAX      INTEGER {
                commOK(1),
                commFAIL(2)
        }
    ACCESS      read-only
    STATUS      mandatory
    DESCRIPTION " The communication status of the protocol on this trunk."
        ::= { atmTrkEntry 3  }

atmTrkRcvRate OBJECT-TYPE
    SYNTAX      INTEGER
    ACCESS      read-write
    STATUS      mandatory
    DESCRIPTION "Unit of ATM Trunk Receive Rate is based on card types.
                 UXM, and ALM-A: cells per second
                 Other cards:    1000 packets per second
                 "
        ::= { atmTrkEntry 4  }

atmTrkTrnsCap OBJECT-TYPE
    SYNTAX      INTEGER
    ACCESS      read-only
    STATUS      mandatory
    DESCRIPTION " The Transmit Capacity on this trunk in cells per second."
        ::= { atmTrkEntry 5  }

atmTrkTrnsLoad OBJECT-TYPE
    SYNTAX      INTEGER
    ACCESS      read-only
    STATUS      mandatory
    DESCRIPTION " The Transmit Load on this trunk in cells per second."
        ::= { atmTrkEntry 6  }

atmTrkRcvCap OBJECT-TYPE
    SYNTAX      INTEGER
    ACCESS      read-only
    STATUS      mandatory
    DESCRIPTION " The Receive Capacity on this trunk in cells per second."
        ::= { atmTrkEntry 7  }

atmTrkRcvLoad OBJECT-TYPE
    SYNTAX      INTEGER
    ACCESS      read-only
    STATUS      mandatory
    DESCRIPTION " The Receive Load on this trunk in cells per second."
        ::= { atmTrkEntry 8  }

atmTrkType OBJECT-TYPE
    SYNTAX      INTEGER {
                trkTypePHY(1),
                trkTypeCBR(2),
                trkTypeVBR(3),
                trkTypeABR(4),
                trkTypeIPXAF(5),
                trkTypeAXISAF(6)
        }
    ACCESS      read-write
    STATUS      mandatory
    DESCRIPTION " The type this trunk. The values of trkTypeCBR(2),
                  trkTypeVBR(3), and trkTypeABR(4) are writable for virtual
                  trunks only. The trkTypePHY(1) value is returned for a
                  get-request on a physical trunk."
        ::= { atmTrkEntry 9  }
 
atmTrkVPI OBJECT-TYPE
    SYNTAX      INTEGER (0..255)
    ACCESS      read-write
    STATUS      mandatory
    DESCRIPTION " The VPI used on this virtual trunk. The maximum value 
                  is 255 for ds3 trunks, and 63 for OC3 trunks. The minimum
                  value for set-request PDUs is 1. This value must be unique
                  on a physical trunk port and also must match the value for
                  the path through the ATM cloud. The object cannot be
                  set in IPX/IGX."
        ::= { atmTrkEntry 10  }
 
atmTrkResChans OBJECT-TYPE
    SYNTAX      INTEGER
    ACCESS      read-write
    STATUS      mandatory
    DESCRIPTION " The number of channels reserved for this trunk."
        ::= { atmTrkEntry 11  }
 
atmTrkTrafCls OBJECT-TYPE
    SYNTAX      INTEGER
    ACCESS      read-write
    STATUS      mandatory
    DESCRIPTION " An integer containing bits representing the 
                  traffic classes of this trunk:
           bit0 Voice,
           bit1 Time Stamped,
           bit2 Non-Time Stamped,
           bit3 Frame Relay,
           bit4 not used,
           bit5 ForeSight,
           bit6 ATM CBR,
           bit7 ATM VBR,
           bit8 ATM ABR. "
        ::= { atmTrkEntry 12  }
 
atmTrkOeNdType OBJECT-TYPE
    SYNTAX      INTEGER {
                ndTypeOther(1),
                ndTypeIPX(2),
                ndTypeBPX(3),
                ndTypeIPXAF(4),
                ndTypeAXIS(5),
                ndTypeIGX(6),
                ndTypeIGXAF(7)
        }
    ACCESS      read-only
    STATUS      mandatory
    DESCRIPTION " The type of node or shelf at the other end of this trunk."
        ::= { atmTrkEntry 13  }
 
atmTrkOeName OBJECT-TYPE
    SYNTAX      DisplayString
    ACCESS      read-only
    STATUS      mandatory
    DESCRIPTION " The name of shelf at the other end of this trunk."
        ::= { atmTrkEntry 14  }
 
atmTrkOeIpAddr OBJECT-TYPE
    SYNTAX      IpAddress
    ACCESS      read-only
    STATUS      mandatory
    DESCRIPTION " The IP address of shelf at the other end of this trunk."
        ::= { atmTrkEntry 15  }
 
atmTrkOeIfIndex OBJECT-TYPE
    SYNTAX      INTEGER
    ACCESS      read-only
    STATUS      mandatory
    DESCRIPTION " The switchIfIndex at the other end of this trunk."
        ::= { atmTrkEntry 16  }
 
atmTrkOeDomain OBJECT-TYPE
    SYNTAX      INTEGER
    ACCESS      read-only
    STATUS      mandatory
    DESCRIPTION " The domain of the shelf at the other end of this trunk."
        ::= { atmTrkEntry 17 }

atmTrkSvcChannels OBJECT-TYPE
    SYNTAX      INTEGER
    ACCESS      read-only
    STATUS      mandatory
    DESCRIPTION "The number of LCN's reserved for the SVC's on this trunk. The 
                  other SVC parms are valid if this object has a non-zero value."
    --DEFAULT   test-function test-atmsvcparm
        ::= { atmTrkEntry 18 }

atmTrkShareLcn OBJECT-TYPE
    SYNTAX      INTEGER {
                 portBased(1),
                 cardBased(2)
    }
    ACCESS      read-only
    STATUS      mandatory
    DESCRIPTION "Whether the LCN's are shared per port basis or per card basis."
    --DEFAULT   test-function test-atmsvcparm
        ::= { atmTrkEntry 19 }

atmTrkSvcLcnLow OBJECT-TYPE
    SYNTAX      INTEGER
    ACCESS      read-only
    STATUS      mandatory
    DESCRIPTION "The lower limit of the LCN value which can be used on this trunk 
    --DEFAULT   test-function test-atmsvcparm
                 for SVC's."
        ::= { atmTrkEntry 20 }

atmTrkSvcLcnHigh OBJECT-TYPE
    SYNTAX      INTEGER
    ACCESS      read-only
    STATUS      mandatory
    DESCRIPTION "The Upper limit of the LCN value which can be used on this trunk 
                 for SVC's."
    --DEFAULT   test-function test-atmsvcparm
        ::= { atmTrkEntry 21 }

atmTrkSvcVpiLow OBJECT-TYPE
    SYNTAX      INTEGER
    ACCESS      read-only
    STATUS      mandatory
    DESCRIPTION "It stores the SVC VPI lower limit. The partitioning is based on 
                 the STI Header VC-format. The 16 bit concatenated VPI/VCI field 
                 is partitioned between PVC and SVC. On a physical trunk a range 
                 will be reserved for SVC's."
    --DEFAULT   test-function test-atmsvcparm
        ::= { atmTrkEntry 22 }


atmTrkSvcVpiHigh OBJECT-TYPE
    SYNTAX      INTEGER
    ACCESS      read-only
    STATUS      mandatory
    DESCRIPTION "It stores the SVC VPI Upper limit. The partitioning is based on 
                 the STI Header VC-format. The 16 bit concatenated VPI/VCI field 
                 is partitioned between PVC and SVC. On a physical trunk a range 
                 will be reserved for SVC's."
    --DEFAULT   test-function test-atmsvcparm
        ::= { atmTrkEntry 23 }

atmTrkSvcVciLow OBJECT-TYPE
    SYNTAX      INTEGER
    ACCESS      read-only
    STATUS      mandatory
    DESCRIPTION "It stores the SVC VCI Lower limit."
    --DEFAULT   test-function test-atmsvcparm
        ::= { atmTrkEntry 24 }

atmTrkSvcVciHigh OBJECT-TYPE
    SYNTAX      INTEGER
    ACCESS      read-only
    STATUS      mandatory
    DESCRIPTION "It stores the SVC VCI Upper limit."
    --DEFAULT   test-function test-atmsvcparm
        ::= { atmTrkEntry 25 }

atmTrkSvcQbinBitMap OBJECT-TYPE
    SYNTAX      OCTET STRING
    ACCESS      read-only
    STATUS      mandatory
    DESCRIPTION "A 32-bit Octet string which represents the queue bin allocation.
                 If the bit is set to 1, it is allocated to SVC's and if 0 it is 
                 allocated to PVC's. The bits are numbered in the BIG endian order,
                 the m.s bit corresponds to Qbin0 and the next m.s bit corresponds 
                 to Qbin 1 etc.For ex. atmTrkSvcQbinMap is set to a value 0x8fff0000
                 to indicate that queues 0 and 4 through 15 are allocated to SVC 's.
                 This object is valid if atmPortSvcChannels is non-zero."
    --DEFAULT   test-function test-atmsvcparm
        ::= { atmTrkEntry 26 }

atmTrkSvcQbinSz OBJECT-TYPE
    SYNTAX      INTEGER
    ACCESS      read-only
    STATUS      mandatory
    DESCRIPTION "The Egress Queue pool size."
    --DEFAULT   test-function test-atmsvcparm
        ::= { atmTrkEntry 27 }

atmTrkSvcBw OBJECT-TYPE
    SYNTAX      INTEGER
    ACCESS      read-only
    STATUS      mandatory
    DESCRIPTION "The bandwidth partition available for SVC's."
    --DEFAULT   test-function test-atmsvcparm
        ::= { atmTrkEntry 28 }

atmTrkSvcInUse OBJECT-TYPE
    SYNTAX      INTEGER {
                inUse (1),
                notInUse(2)
    }
    ACCESS      read-write
    STATUS      mandatory
    DESCRIPTION "This object is set by the INS to indicate that SVC partitioning
                 information is being used by INS. The initial value is notInUse.
                 This object is valid if atmPortSvcChannels is non-zero."
    --DEFAULT   test-function test-atmsvcparm
        ::= { atmTrkEntry 29 }

atmTrkXmitRate OBJECT-TYPE
    SYNTAX      INTEGER 
    ACCESS      read-write
    STATUS      mandatory
    DESCRIPTION "The trunk transmission rate in unit of cells per second.
                 * The default values for this object are,
                 ----------------------------------------------------
                   Back Card Type  |  Physical Trunk | Virtual Trunk
                 ----------------------------------------------------
                   T3              |  96000          | 3000
                   E3              |  80000          | 2500
                   OC3             |  353208         | 32109
                 ----------------------------------------------------
                 * This object can't be set if the routing trunk is added and the
                   trunk is a physical trunk. It can be set if this is a virtual
                   trunk no matter whether the routing trunk is established or not. 
                 * This object can be set with other writable objects in this table
                   except atmRteTrkAlmEnable, atmRteTrkBdataBTxQlen, 
                   atmRteTrkBdataBTxEfcn, atmRteTrkBdataBTxHiClp, 
                   atmRteTrkBdataBTxLoClp.
                "
        ::= { atmTrkEntry 30 }

atmTrkPassSync  OBJECT-TYPE
    SYNTAX      INTEGER {
                yes (1),
                no(2)
    }
    ACCESS      read-write
    STATUS      mandatory
    DESCRIPTION "The selection of this trunk to pass synchronization to the
                 network clock.  
                 * The default value for this object is yes(1).
                 * X.21 subrate trunk cannot pass sync.
                 * V.35 and MIL-188 PLNs can only pass sync if the date rate 
                   is 256, 512, or 1024 kbps, since these are the only rates 
                   for which the NTC-SR accepts clock from the SCC.
                 * This object can be set with other writable objects in this table
                   except atmRteTrkAlmEnable, atmRteTrkBdataBTxQlen, 
                   atmRteTrkBdataBTxEfcn, atmRteTrkBdataBTxHiClp, 
                   atmRteTrkBdataBTxLoClp.
                "
        ::= { atmTrkEntry 31 }

atmTrkStatRes  OBJECT-TYPE
    SYNTAX      INTEGER 
    ACCESS      read-write
    STATUS      mandatory
    DESCRIPTION "The Statistical Reserve in cells per second for this trunk.
                 * The default value for this object is 1000.
                 * This can be set with other writable objects in this table
                   except atmRteTrkAlmEnable, atmRteTrkBdataBTxQlen, 
                   atmRteTrkBdataBTxEfcn, atmRteTrkBdataBTxHiClp, 
                   atmRteTrkBdataBTxLoClp.
                "
        ::= { atmTrkEntry 32 }

atmTrkLoopClock  OBJECT-TYPE
    SYNTAX      INTEGER {
                yes (1),
                no(2)
    }
    ACCESS      read-write
    STATUS      mandatory
    DESCRIPTION "This object indicates if this trunk has been configured to
                 loop receive clock back to transmit.  
                 * If local end is configured to pass sync, don't loop clock;
                 * If the interface is X.21, loop clook is not supported.
                 * The default value for this object is no(2).
                 * This object can be set with other writable objects in this 
                   table except atmRteTrkAlmEnable, atmRteTrkBdataBTxQlen, 
                   atmRteTrkBdataBTxEfcn, atmRteTrkBdataBTxHiClp, 
                   atmRteTrkBdataBTxLoClp,atmRteTrkBdataBRxQlen, 
                   atmRteTrkBdataBRxEfcn, atmRteTrkBdataBRxHiClp 
                   and atmRteTrkBdataBRxLoClp.
                " 
        ::= { atmTrkEntry 33 }

atmTrkBdataBTxQlen  OBJECT-TYPE
    SYNTAX      INTEGER (-1..8000) 
    ACCESS      read-write
    STATUS      mandatory
    DESCRIPTION "The depth of Bursty Data B transmission queue (in decimal).
                 * This object is not applicable (-1) to IPX/IGX ATM trunks.
                 * The default value for this object is 8000.
                 * This object can only be set together with 
                   atmRteTrkBdataBTxEfcn,atmRteTrkBdataBTxHiClp and 
                   atmRteTrkBdataBTxLoClp on BPX ATM trunks.
                 "
    --DEFAULT   test-function  test-atmrtetrkparms
        ::= { atmTrkEntry 34 }

atmTrkBdataBRxQlen  OBJECT-TYPE
    SYNTAX      INTEGER (-1..8000)
    ACCESS      read-write
    STATUS      mandatory
    DESCRIPTION "The depth of Bursty Data B receiving queue (in decimal). 
                 * This object is not applicable (-1) to BPX ATM trunk (BNI or BXM).
                 * The default value for this object is 8000.
                 * This object can only be set together with
                   atmRteTrkBdataBRxEfcn, atmRteTrkBdataBRxHiClp and 
                   atmRteTrkBdataBRxLoClp on IPX ATM trunks 
                 "
    --DEFAULT   test-function  test-atmrtetrkparms
        ::= { atmTrkEntry 35 }

atmTrkBdataBTxEfcn  OBJECT-TYPE
    SYNTAX      INTEGER (-1..8000)
    ACCESS      read-write
    STATUS      mandatory
    DESCRIPTION "The transmission EFCN threshold (in decimal) for Bursty 
                 Data B of this trunk.
                 * This object is not applicable (-1) to IPX/IGX ATM trunks.
                 * The default value for this object is 8000.
                 * This object can only be set together with 
                   atmRteTrkBdataBTxQlen,atmRteTrkBdataBTxHiClp and 
                   atmRteTrkBdataBTxLoClp on BPX ATM trunks.
                 "
    --DEFAULT   test-function  test-atmrtetrkparms
        ::= { atmTrkEntry 36 }

atmTrkBdataBRxEfcn  OBJECT-TYPE
    SYNTAX      INTEGER (-1..8000)
    ACCESS      read-write
    STATUS      mandatory
    DESCRIPTION "The receiving EFCN threshold (in decimal) for Bursty Data 
                 B of this trunk.
                 * This object is not applicable (-1) to BPX ATM trunk (BNI or BXM). 
                 * The default value for this object is 8000.
                 * This object can only be set together with
                   atmRteTrkBdataBRxQlen, atmRteTrkBdataBRxHiClp and 
                   atmRteTrkBdataBRxLoClp on IPX ATM trunks. 
                 "
    --DEFAULT   test-function  test-atmrtetrkparms
        ::= { atmTrkEntry 37 }

atmTrkBdataBTxHiClp OBJECT-TYPE
    SYNTAX      INTEGER (-1..100)
    ACCESS      read-write
    STATUS      mandatory
    DESCRIPTION "The transmission high CLP threshold (in percentage) for 
                 Bursty Data B of this trunk. 
                 * The default value for this object is 75.
                 * This object is not applicable (-1) to IPX/IGX ATM trunks. 
                 * This object can only be set together with 
                   atmRteTrkBdataBTxEfcn,atmRteTrkBdataBTxQlen and 
                   atmRteTrkBdataBTxLoClp on BPX ATM trunks.
                 "
    --DEFAULT   test-function  test-atmrtetrkparms
        ::= { atmTrkEntry 38 }

atmTrkBdataBRxHiClp OBJECT-TYPE
    SYNTAX      INTEGER (-1..100)
    ACCESS      read-write
    STATUS      mandatory
    DESCRIPTION "The receiving high CLP threshold (in percentage) for Bursty Data
                 B of this trunk. This object is not applicable (-1) to BPX
                 ATM trunk (BNI or BXM).
                 * The default value for this object is 75.
                 * This object can only be set together with
                   atmRteTrkBdataBRxEfcn, atmRteTrkBdataBRxQlen and 
                   atmRteTrkBdataBRxLoClp on IPX ATM trunks 
                 "
    --DEFAULT   test-function  test-atmrtetrkparms
        ::= { atmTrkEntry 39 }

atmTrkBdataBTxLoClp OBJECT-TYPE
    SYNTAX      INTEGER (-1..100)
    ACCESS      read-write
    STATUS      mandatory
    DESCRIPTION "The transmission low CLP threshold (in percentage) for Burstry
                 Data B of this trunk.This object is not applicable (-1) to IPX
                 or IGX ATM trunks. 
                 * The default value for this object is 25.
                 * This object can only be set together with 
                   atmRteTrkBdataBTxEfcn,atmRteTrkBdataBTxHiClp and 
                   atmRteTrkBdataBTxQlen on BPX ATM trunks.
                 "
    --DEFAULT   test-function  test-atmrtetrkparms
        ::= { atmTrkEntry 40 }

atmTrkBdataBRxLoClp OBJECT-TYPE
    SYNTAX      INTEGER (-1..100)
    ACCESS      read-write
    STATUS      mandatory
    DESCRIPTION "The receiving low CLP threshold (in percentage ) for Bursty
                 Data B of this trunk. This object is not applicable (-1) to
                 BPX ATM trunk (BNI or BXM).
                 * The default value for this object is 25.
                 * This object can only be set together with
                   atmRteTrkBdataBRxEfcn, atmRteTrkBdataBRxHiClp and 
                   atmRteTrkBdataBRxQlen on IPX ATM trunks 
                 "
    --DEFAULT   test-function  test-atmrtetrkparms
        ::= { atmTrkEntry 41 }

atmTrkMaxChanPort OBJECT-TYPE
    SYNTAX      INTEGER (-1..16320)
    ACCESS      read-write
    STATUS      mandatory
    DESCRIPTION "The maximum number of channels a BXM trunk port can support. 
                 This object is applicable to BXM trunk only.
                 * The default value for this object is 1484.
                 * This object can be set with other writable objects in this 
                   table except atmRteTrkAlmEnable, atmRteTrkBdataBTxQlen, 
                   atmRteTrkBdataBTxEfcn, atmRteTrkBdataBTxHiClp and
                   atmRteTrkBdataBTxLoClp.
                "
    --DEFAULT   view-mask    BPX-VIEW | IGX-VIEW
        ::= { atmTrkEntry 42 }

atmTrkLinkType  OBJECT-TYPE
    SYNTAX      INTEGER {
                terrestrial(1),
                satellite(2)
                }
    ACCESS      read-write
    STATUS      mandatory
    DESCRIPTION "The physical link type of the trunk. The default value for
                 this object is terrestrial(1).
                 * This object can be set with other writable objects in this 
                   table except atmRteTrkAlmEnable, atmRteTrkBdataBTxQlen, 
                   atmRteTrkBdataBTxEfcn, atmRteTrkBdataBTxHiClp and
                   atmRteTrkBdataBTxLoClp.
                "
        ::= { atmTrkEntry 43 }

atmTrkDerouteDelayTimer OBJECT-TYPE
    SYNTAX      INTEGER (0..300)
    ACCESS      read-write
    STATUS      mandatory
    DESCRIPTION "The deroute delay timer of the trunk in unit of second.
                 * The default value for this object is 0.
                 * This object can be set with other writable objects in this 
                   table except atmRteTrkAlmEnable, atmRteTrkBdataBTxQlen, 
                   atmRteTrkBdataBTxEfcn, atmRteTrkBdataBTxHiClp and
                   atmRteTrkBdataBTxLoClp.
                "
       ::= { atmTrkEntry 44 }
atmTrkGtwyChCount OBJECT-TYPE
    SYNTAX      INTEGER 
    ACCESS      read-write
    STATUS      mandatory
    DESCRIPTION "The Gateway Channel count for UXM cards. 
                 * This cannot exceed the total number channels per port."
    --DEFAULT   view-mask     IGX-VIEW
       ::= { atmTrkEntry 45 }

atmTrkRetainedLinks   OBJECT-TYPE
    SYNTAX      INTEGER (1..8)
    ACCESS      read-write
    STATUS      mandatory
    DESCRIPTION "No of retained links, This is for UXM T1-IMA mode only "
    --DEFAULT   view-mask     IGX-VIEW
       ::= { atmTrkEntry 46 }

atmTrkImaWindowSize OBJECT-TYPE
    SYNTAX      INTEGER 
    ACCESS      read-write
    STATUS      mandatory
    DESCRIPTION "If this object which is the Window size is zero then 
                 additional information is not requested, which are the objects given below.  
                 This is for UXM E1/T1-IMA mode only "
    --DEFAULT   view-mask     IGX-VIEW
       ::= { atmTrkEntry 47 }

atmTrkImaTrnsCnts   OBJECT-TYPE
    SYNTAX      INTEGER 
    ACCESS      read-write
    STATUS      mandatory
    DESCRIPTION " This object can be set only if the Window Size is non-zero. This is Maximum transition 
                  counts/window  This is for UXM E1/T1-IMA mode only "
    --DEFAULT   view-mask     IGX-VIEW
       ::= { atmTrkEntry 48 }

atmTrkImaReenableTimer OBJECT-TYPE
    SYNTAX      INTEGER 
    ACCESS      read-write
    STATUS      mandatory
    DESCRIPTION "This object can be set only if the Window Size is non-zero. This is re-enable timer
                 If 0 is disable else it is in 10min units. This is for UXM T1-IMA mode only "
    --DEFAULT   view-mask     IGX-VIEW
       ::= { atmTrkEntry 49 }


-- The following describes the MIB variables for the atmTrunkStatsTable. 

atmTrunkStatsTable OBJECT-TYPE
    SYNTAX      SEQUENCE OF AtmTrkStatsEntry
    ACCESS      not-accessible
    STATUS      mandatory
    DESCRIPTION "A list of ATM trunk statistics object."
    --DEFAULT   test-function test-atmtrkstatstable
    --DEFAULT   next-function next-atmtrkstatstable
    --DEFAULT   get-function  get-atmtrkstatstable-%t
        ::= { trunkServiceObjects 4  }
  
atmTrkStatsEntry OBJECT-TYPE
    SYNTAX      AtmTrkStatsEntry
    ACCESS      not-accessible
    STATUS      mandatory
    DESCRIPTION "A interface entry"
    INDEX       { switchIfIndex }
        ::= { atmTrunkStatsTable 1  }
  
AtmTrkStatsEntry ::=
    SEQUENCE {
        atmTrkStatsTxVoPktDrps          Counter,
        atmTrkStatsTxTsPktDrps          Counter,
        atmTrkStatsTxNonTsPktDrps       Counter,
        atmTrkStatsTxHiPrioPktDrps      Counter,
        atmTrkStatsTxBdataAPktDrps      Counter,
        atmTrkStatsTxBdataBPktDrps      Counter,
        atmTrkStatsRxVoPktDrps          Counter,
        atmTrkStatsRxTsPktDrps          Counter,
        atmTrkStatsRxNonTsPktDrps       Counter,
        atmTrkStatsRxHiPrioPktDrps      Counter,
        atmTrkStatsRxBdataAPktDrps      Counter,
        atmTrkStatsRxBdataBPktDrps      Counter,
        atmTrkStatsSpacerPktsDrps       Counter,
        atmTrkStatsTotalPktsTxtoLns     Counter,
        atmTrkStatsTotalPktsRxFromLns   Counter,

        atmTrkStatsTxVoCellDrps         Counter,
        atmTrkStatsTxTsCellDrps         Counter,
        atmTrkStatsTxNonTsCellDrps      Counter,
        atmTrkStatsTxHiPrioCellDrps     Counter,
        atmTrkStatsTxBdataACellDrps     Counter,
        atmTrkStatsTxBdataBCellDrps     Counter,
        atmTrkStatsTxCbrCellDrps        Counter,
        atmTrkStatsTxVbrCellDrps        Counter,
        atmTrkStatsTxAbrCellDrps        Counter,
        atmTrkStatsTotalCellsTxtoLns    Counter,
        atmTrkStatsTotalCellsRxFromPorts  Counter  
    }
           
atmTrkStatsTxVoPktDrps OBJECT-TYPE
    SYNTAX      Counter
    ACCESS      read-only
    STATUS      mandatory
    DESCRIPTION "The number of transmitted voice fast packet dropped.
                 This statistics is not applicatable to BPX trunks, 0 is
                 returned for BPX trunks.
                 "
        ::= { atmTrkStatsEntry 1  }

atmTrkStatsTxTsPktDrps   OBJECT-TYPE
    SYNTAX      Counter
    ACCESS      read-only
    STATUS      mandatory
    DESCRIPTION "The number of transmitted time-stamped packet dropped.  
                 This statistics is not applicatable to BPX trunks, 0 is
                 returned for BPX trunks.
                 "
        ::= { atmTrkStatsEntry 2  }
    
atmTrkStatsTxNonTsPktDrps    OBJECT-TYPE
    SYNTAX      Counter
    ACCESS      read-only
    STATUS      mandatory
    DESCRIPTION "The number of transmitted non time-stamped packet dropped. 
                 This statistics is not applicatable to BPX trunks, 0 is
                 returned for BPX trunks.
                 "
        ::= { atmTrkStatsEntry 3  }

atmTrkStatsTxHiPrioPktDrps   OBJECT-TYPE
    SYNTAX      Counter
    ACCESS      read-only
    STATUS      mandatory
    DESCRIPTION "The number of transmitted high priority packet dropped.  
                 This statistics is not applicatable to BPX trunks, 0 is
                 returned for BPX trunks.
                 "
        ::= { atmTrkStatsEntry 4  }

atmTrkStatsTxBdataAPktDrps  OBJECT-TYPE
    SYNTAX      Counter
    ACCESS      read-only
    STATUS      mandatory
    DESCRIPTION "The number of transmitted bursty data A packet dropped.  
                 This statistics is not applicatable to BPX trunks, 0 is
                 returned for BPX trunks.
                 "
        ::= { atmTrkStatsEntry 5  }

atmTrkStatsTxBdataBPktDrps  OBJECT-TYPE
    SYNTAX      Counter
    ACCESS      read-only
    STATUS      mandatory
    DESCRIPTION "The number of transmitted bursty data B packet dropped. 
                 This statistics is not applicatable to BPX trunks, 0 is
                 returned for BPX trunks.
                 "
        ::= { atmTrkStatsEntry 6  }

atmTrkStatsRxVoPktDrps  OBJECT-TYPE
    SYNTAX      Counter
    ACCESS      read-only
    STATUS      mandatory
    DESCRIPTION "The number of received voice packet dropped.  
                 This statistics is not applicatable to BPX trunks, 0 is
                 returned for BPX trunks.
                 "
        ::= { atmTrkStatsEntry 7  }

atmTrkStatsRxTsPktDrps  OBJECT-TYPE
    SYNTAX      Counter
    ACCESS      read-only
    STATUS      mandatory
    DESCRIPTION "The number of received time-stamped packet dropped.  
                 This statistics is not applicatable to BPX trunks, 0 is
                 returned for BPX trunks.
                 "
        ::= { atmTrkStatsEntry 8  }

atmTrkStatsRxNonTsPktDrps    OBJECT-TYPE
    SYNTAX      Counter
    ACCESS      read-only
    STATUS      mandatory
    DESCRIPTION "The number of received non time-stamped packet dropped.  
                 This statistics is not applicatable to BPX trunks, 0 is
                 returned for BPX trunks.
                 "
        ::= { atmTrkStatsEntry 9  }

atmTrkStatsRxHiPrioPktDrps   OBJECT-TYPE
    SYNTAX      Counter
    ACCESS      read-only
    STATUS      mandatory
    DESCRIPTION "The number of received high priority packet dropped.  
                 This statistics is not applicatable to BPX trunks, 0 is
                 returned for BPX trunks.
                 "
        ::= { atmTrkStatsEntry 10  }

atmTrkStatsRxBdataAPktDrps  OBJECT-TYPE
    SYNTAX      Counter
    ACCESS      read-only
    STATUS      mandatory
    DESCRIPTION "The number of received bursty data A packet dropped.  
                 This statistics is not applicatable to BPX trunks, 0 is
                 returned for BPX trunks.
                 "
        ::= { atmTrkStatsEntry 11  }

atmTrkStatsRxBdataBPktDrps  OBJECT-TYPE
    SYNTAX      Counter
    ACCESS      read-only
    STATUS      mandatory
    DESCRIPTION "The number of received bursty data B packet dropped.  
                 This statistics is not applicatable to BPX trunks, 0 is
                 returned for BPX trunks.
                 "
        ::= { atmTrkStatsEntry 12  }

atmTrkStatsSpacerPktsDrps        OBJECT-TYPE
    SYNTAX      Counter
    ACCESS      read-only
    STATUS      mandatory
    DESCRIPTION "The number of received Spacer Packet dropped. 
                 This statistics is not applicatable to BPX trunks, 0 is
                 returned for BPX trunks.
                 "
        ::= { atmTrkStatsEntry 13  }

atmTrkStatsTotalPktsTxtoLns     OBJECT-TYPE
    SYNTAX      Counter
    ACCESS      read-only
    STATUS      mandatory
    DESCRIPTION "The number of total packets transmitted to the line.  
                 This statistics is not applicatable to BPX trunks, 0 is
                 returned for BPX trunks.
                 "
        ::= { atmTrkStatsEntry 14  }

atmTrkStatsTotalPktsRxFromLns   OBJECT-TYPE
    SYNTAX      Counter
    ACCESS      read-only
    STATUS      mandatory
    DESCRIPTION "The number of total packets received from the line. 
                 This statistics is not applicatable to BPX trunks, 0 is
                 returned for BPX trunks.
                 "
        ::= { atmTrkStatsEntry 15  }


atmTrkStatsTxVoCellDrps   OBJECT-TYPE
    SYNTAX            Counter
    ACCESS            read-only
    STATUS            mandatory
    DESCRIPTION "The number of transmitted ATM voice cell dropped. This
                 statistics is not applicable to ATM Virtual Trunks, 0 is
                 returned for ATM Virtual trunks.
                 "
        ::= { atmTrkStatsEntry 16  }
    
atmTrkStatsTxTsCellDrps   OBJECT-TYPE
    SYNTAX      Counter
    ACCESS      read-only
    STATUS      mandatory
    DESCRIPTION "The number of transmitted time-stamped ATM cell dropped.
                 This statistics is not applicable to ATM Virtual Trunks. 0 is
                 returned for ATM Virtual trunks.
                 "
        ::= { atmTrkStatsEntry 17  }
    
atmTrkStatsTxNonTsCellDrps    OBJECT-TYPE
    SYNTAX      Counter
    ACCESS      read-only
    STATUS      mandatory
    DESCRIPTION "The number of transmitted non time-stamped ATM cell dropped.
                 This statistics is not applicable to ATM Virtual Trunks. 0 is
                 returned for ATM Virtual trunks.
                 "
        ::= { atmTrkStatsEntry 18  }

atmTrkStatsTxHiPrioCellDrps   OBJECT-TYPE
    SYNTAX      Counter
    ACCESS      read-only
    STATUS      mandatory
    DESCRIPTION "The number of transmitted high priority ATM cell dropped.
                 This statistics is not applicable to ATM Virtual Trunks. 0 is
                 returned for ATM Virtual trunks.
                 " 
        ::= { atmTrkStatsEntry 19  }

atmTrkStatsTxBdataACellDrps  OBJECT-TYPE
    SYNTAX      Counter
    ACCESS      read-only
    STATUS      mandatory
    DESCRIPTION "The number of transmitted bursty data A cell dropped. 
                 This statistics is not applicable to ATM Virtual Trunks. 0 is
                 returned for ATM Virtual trunks.
                 "
        ::= { atmTrkStatsEntry 20  }

atmTrkStatsTxBdataBCellDrps  OBJECT-TYPE
    SYNTAX      Counter
    ACCESS      read-only
    STATUS      mandatory
    DESCRIPTION "The number of transmitted bursty data B cell dropped. 
                 This statistics is not applicable to ATM Virtual Trunks. 0 is
                 returned for ATM Virtual trunks.
                 "
        ::= { atmTrkStatsEntry 21  }

atmTrkStatsTxCbrCellDrps    OBJECT-TYPE
    SYNTAX      Counter
    ACCESS      read-only
    STATUS      mandatory
    DESCRIPTION "The number of transmitted ATM CBR cell dropped. This statistics
                 is not applicable to IPX/IGX ATM trunks. 0 is returned for 
                 IPX/IGX ATM trunks.
                 "
        ::= { atmTrkStatsEntry 22  }

atmTrkStatsTxVbrCellDrps    OBJECT-TYPE
    SYNTAX      Counter
    ACCESS      read-only
    STATUS      mandatory
    DESCRIPTION "The number of transmitted ATM VBR cell dropped. This statistics
                 is not applicable to IPX/IGX ATM trunks. 0 is returned for 
                 IPX/IGX ATM trunks.
                 "
        ::= { atmTrkStatsEntry 23  }

atmTrkStatsTxAbrCellDrps    OBJECT-TYPE
    SYNTAX      Counter
    ACCESS      read-only
    STATUS      mandatory
    DESCRIPTION "The number of transmitted ATM ABR cell dropped. This statistics
                 is not applicable to IPX/IGX ATM trunks. 0 is returned for 
                 IPX/IGX ATM trunks.
                 "
        ::= { atmTrkStatsEntry 24  }

atmTrkStatsTotalCellsTxtoLns    OBJECT-TYPE
    SYNTAX      Counter
    ACCESS      read-only
    STATUS      mandatory
    DESCRIPTION "The number of total cells transmitted to the line."
        ::= { atmTrkStatsEntry 25  }

atmTrkStatsTotalCellsRxFromPorts  OBJECT-TYPE
    SYNTAX      Counter
    ACCESS      read-only
    STATUS      mandatory
    DESCRIPTION "The number of total cells received from the port."
        ::= { atmTrkStatsEntry 26  }

END
