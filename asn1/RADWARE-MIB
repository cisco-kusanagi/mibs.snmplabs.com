RADWARE-MIB DEFINITIONS ::= BEGIN

-- Title:      Radware common MIB
--             This Private MIB supports Radware products
-- Version:    3.0
-- Date:       2/4/2001
-- By:         RMA (Radware MIB Authority)
-- E-mail:     US:            support@radware.com
--             International: support_int@radware.com
--

IMPORTS
       NetworkAddress,
       IpAddress,
       Counter,
       Gauge,
       enterprises
              FROM RFC1155-SMI
      OBJECT-TYPE
              FROM RFC-1212
       DisplayString,
       PhysAddress,
       ipAddrEntry
              FROM RFC1213-MIB
       TRAP-TYPE
                    FROM RFC-1215;
    TruthValue ::= INTEGER {
         true (1),
         false (2)
        }
    RowStatus ::= INTEGER {
        active(1),
        notInService(2),
        notReady(3),
        createAndGo(4),
        createAndWait(5),
        destroy(6)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }
 rnd            OBJECT IDENTIFIER ::= { enterprises 89  }

--   Objects in this MIB are arranged into groups:
--   rndMng        - Management/Action
--   rndDeviceParams- General parameters
--   rndBridge     - RND Bridge/Route parameters (Level 2)
--   rndInterface  - Interface table and RS232 interface parameters
--   rndSlot       - Structure of OpenGate (modular device)
--   rndIpRoute    - Routing Parameters (Level 3)
--   rndRouteSpf   - RND SPF Routing algorith
--   rndMaskTable  - RND Masking tables
--   rndBackup     - RND backup feature, Dial-up parameters.
--   rndFddi       - RND FDDI parameters
--   rndDECnet     - RND DECnet Router parameters
--   rndIPX        - Parameters for management of IPX router
--   rndTR         - Parameters for additional Token Ring support
--   rndTranslation- Parameters for translation between Ethernet, Token Ring
--                   and FDDI
--   rndPCDevices  - Parameters for management for RND PC-based devices
--   rndFACS       - Facility for Access Control and Security
--   rndSNAR       - SDLC/SNA Routing parameters
--   rndSRE        - Parameters for configuration of Source Routing and
--                   Source Routing Encapsulation algorithms
--   rndCOD        - Connect On Demande parameters.
--   rndSPS        - Parameters for configuration of SPS
--   rndBrgHub     _ Remot Bridge HUB paramenets
--   rndAdapter    - parameters for R_dapter, OG-Van
--   rndBootP      - BootP configurgaration.
--   rndOGLoadBalance - Load Balance configuration.
--   ipSpec        IP Specific for VGate, MRT and LRE
--   virtualLan    Virtual LAN definition
--   rsConf        Router Server Configuration
--   rsTunning     Tunning sub group
--   rndISDN       ISDN Parameters for  OG_RAN and Radptor,VAN ans WANgate.
--   rndPPP        PPP Parameters for IPX.
--   rndDial       Dial Parameters for V25 of OpenGate


-- At the end of the MIB there is a definition of all RND-specific traps.


-- rndMng group contains Management Variables for RND devices

rndMng   OBJECT IDENTIFIER ::= { rnd 1  }

rndSysId OBJECT-TYPE
    SYNTAX  INTEGER {
       reb(1),
       ceb(2),
       ceblb(3),
       xeb(4),
       xeb1(5),
       rebsx(6),
       rtb(7),
       ltb(8),
       lte(9),
       iprouter(10),
       ielb(11),
       leb(12),
       openGate12(13),
       openGate4(14),
       ran(15),
       itlb(16),
       gatelinx(17),
       openGate2(18),
       ogRanTR(19),
       stc(20),
       ftc(21),
       armon(22),
       fccs1004(23),    -- RADway
       fccs1012(24),    -- RADway
       rdapter(25),
       ogvan(26),
       wanGate(27),
       ogRubE(28),
       ogRubT(29),
       elX(30),
       vGate4(31),
       mrt(32),
       ogSrubET(33),
       vanXS(34),
       lre(35),
       vGate2(36),
       serverDispatcher4(37),
       serverDispatcher2(38),
       vGate2Fast(39),
       serverDispatcher2Fast(40),
       prt(41),
       mlm(42),
       prt11(43),
       quickOffice(44),
       apollo(45),
       radware(62)
     }
    ACCESS  read-only
    STATUS  mandatory
    DESCRIPTION
      "Identification of an RND device. The device type for each
      integer clarifies the sysObjectID in MIB - II."
    ::= { rndMng 1  }

rndAction OBJECT-TYPE
    SYNTAX  INTEGER {
       reset(1),
       sendNetworkTab(2),
       deleteNetworkTab(3),
       sendRoutingTab(4),    -- Level II
       deleteRoutingTab(5),
       sendLanTab(6),
       deleteLanTab(7),
       deleteArpTab(8),
       sendArpTab(9),
       deleteRouteTab(10),   -- Level III
       sendRouteTab(11),
       backupSPFRoutingTab(12),
       backupIPRoutingTab(13),
       backupNetworkTab(14),
       backupLanTab(15),
       backupArpTab(16),
       backupIPXRipTab(17),
       backupIPXSAPTab(18),
       resetCDB(19),
       eraseCDB(20),
       deleteZeroHopRoutingAllocTab(21)
     }
    ACCESS  read-write
    STATUS  mandatory
    DESCRIPTION
      "This variable enables the operator to perform one of the
      specified actions on the tables maintained by the network device.
      Send actions require support of proprietery File exchange
      protocol."
   ::= { rndMng 2  }


rndFileName OBJECT-TYPE
    SYNTAX OCTET STRING -- SIZE 256
    ACCESS  read-write
    STATUS  mandatory
    DESCRIPTION
      "The name of the file used internally by RND for transferring
      tables maintained by network devices, using a prorietary File
      exchange protocol."
    ::=  { rndMng 3  }


-- rndDeviceParams group contains a number of general variables

rndDeviceParams       OBJECT IDENTIFIER ::= { rnd 2  }

rndBridgeType  OBJECT-TYPE
    SYNTAX  INTEGER {
       reb(1),
       ceb(2),
       ceblb(3),
       xeb(4),
       xeb1(5),
       rebsx(6),
       rtb(7),
       ltb(8),
       tre(9),
       rtre(10),      -- remote TRE
       xtb(11),
       ete(12),
       rete(13),      -- remote ETE
       ielb(30),
       leb(31),
       openGate12(32),
       openGate4(33),
       ran(34),
       itlb(35),
       gatelinx(36),
       openGate2(37),
       ogRanTR(38),
       rdapter(39),
       ogVan(40),
       wanGate(41),
       ogRubE(42),
       ogRubT(43),
       wanGateI(44),
       vGate4(45),
       lre(46),
       mrt(47),
       vGate2(48)
     }
    ACCESS  read-only
    STATUS  mandatory
    DESCRIPTION
      "Identification of the RND bridge type."
    ::= { rndDeviceParams 1  }


rndInactiveArpTimeOut OBJECT-TYPE
    SYNTAX INTEGER
    ACCESS  read-write
    STATUS  mandatory
    DESCRIPTION
      "This variable defines the maximum time period that can pass
       between ARP requests concerning an entry in the ARP table.
       After this time period, the entry is deleted from the table."
    ::= { rndDeviceParams 2  }

-- The following two variables define the format of RND specific
-- error messages issued by the RND devices

rndBridgeAlarm  OBJECT IDENTIFIER ::= { rndDeviceParams 3  }

rndErrorDesc OBJECT-TYPE
    SYNTAX DisplayString
    ACCESS  read-only
    STATUS  mandatory
    DESCRIPTION
       "A textual description of the enterprise-specific trap sent
        to the Network Management Station by the RND managed device."
    ::= { rndBridgeAlarm 1  }

rndErrorSeverity OBJECT-TYPE
    SYNTAX INTEGER
    ACCESS  read-only
    STATUS  mandatory
    DESCRIPTION
      "The severity type of the enterprise-specific trap sent to the
      Network Management Station by the RND managed device."
    ::= { rndBridgeAlarm 2  }

rndBrgVersion OBJECT-TYPE
    SYNTAX  DisplayString
    ACCESS  read-only
    STATUS  mandatory
    DESCRIPTION
      "The bridge version."
   ::= { rndDeviceParams 4  }

rndBrgFeatures OBJECT-TYPE
    SYNTAX   OCTET STRING  -- SIZE 20
    ACCESS  read-only
    STATUS  mandatory
    DESCRIPTION
      "A bit mask that defines the features supported by a particular configuration
       of this network element:
       __________________________________________
       |  Byte 1|Byte 2 |Byte 3 | ....|Byte 20  |
       |87654321|                     | 87654321|
       |________|_______________________________|

 Byte1 :
      bit1: TX Block mask
      bit2: Source Routing Encapulation
      bit3: SNA/SDLC
      bit4: Frame Relay
      bit5: SNMP
      bit6: LAN Manager
      bit7: High Performance
      bit8: Translation
 Byte2 :
      bit1: DEC Router
      bit2: IPX Router
      bit3: IP  Router
 Byte3 :
      bit1: Dial Up Backup
      bit2: COD
      bit3: FACS
      bit4: Load Balance
      bit5: Remote Configuration
      bit6: RIP 2
      bit7: OSPF
      bit8: IPX RIP/SAP Filter
 Byte4 :
      bit1: BootP Server
      bit2: BootP Client
      bit3: Compression
      bit4: V25.bis
      bit5: ISDN
      bit6: CODv2
      bit7: NSPF
      bit8: UDP Relay

 Byte5
      bit1:VirtualLAN
      bit2:Static IP Multicast
      bit3:IP Redundancy
      bit4:CCM2
      bit5:ISDN Bonding
      bit6:Backup Link Selection -- for the  VAN/Rdapter ver 4.0
      bit7:IP/IPX Forwarding     -- for the  WANgate ver 4.0
      bit8:Improved COD

 Byte6
      bit1: Server Disptacher
      bit2: ISDN_US               -- for the  VANSX/WANGATE ver 5.0
      bit3: PPP
      bit4: IP Rip Filter       -- for Vgate3
      bit5: Zero Hop Routing    -- for Vgate3
      bit6: ISDN Japan

 Byte7
     bit1: With unmanaged Switch
     bit2: 2 LANs
     bit3: OSPF Ver 2.0
     bit4: FACS Ver 2.0
     bit5: Multiple WEB Farm
     bit6: Backup Server"

   ::= { rndDeviceParams 5  }

rndBrgLicense OBJECT-TYPE
    SYNTAX   OCTET STRING  -- SIZE 20
    ACCESS  read-write
    STATUS  mandatory
    DESCRIPTION
       "This parameter is used for entering a s/w license number for a device.
        A separate license number is supplied for each device."
   ::= { rndDeviceParams 6  }

-- IP Host Parameters

--All the new parameters under this section will be added to the
-- rndMng group, as rndIpHost sub-group.
--
rndIpHost  OBJECT IDENTIFIER   ::= { rndDeviceParams 7 }
--
--ICMP Transmission Enable\Disable
--The new variable will be


rndICMPTransmitionEnable   OBJECT-TYPE
   SYNTAX INTEGER {
      enable(1),
      disable(2)
   }
   ACCESS  read-write
   STATUS  mandatory
   DESCRIPTION
    "This variable controlls the ability to transmit ICMP frames"
    ::= { rndIpHost 1 }

rndCommunityTable OBJECT-TYPE
   SYNTAX SEQUENCE OF RndCommunityEntry
   ACCESS not-accessible
   STATUS mandatory
   DESCRIPTION
    "The community table of the agent"
     ::= { rndIpHost 2 }

rndCommunityEntry  OBJECT-TYPE
   SYNTAX RndCommunityEntry
   ACCESS not-accessible
   STATUS mandatory
   DESCRIPTION
       " The row definition for this table."
   INDEX { rndCommunityMngStationAddr,
           IMPLIED rndCommunityString }
   ::= { rndCommunityTable 1 }

RndCommunityEntry ::= SEQUENCE {
  rndCommunityMngStationAddr   IpAddress,
  rndCommunityString           DisplayString,
  rndCommunityAccess           INTEGER,
  rndCommunityTrapsEnable      INTEGER,
  rndCommunityStatus           INTEGER
  }


rndCommunityMngStationAddr OBJECT-TYPE
   SYNTAX IpAddress
   ACCESS   read-write
   STATUS mandatory
   DESCRIPTION
    "The management station that will be allowed to
    communicate with the agent IP address"
     ::=  { rndCommunityEntry 1 }

rndCommunityString OBJECT-TYPE
   SYNTAX DisplayString (SIZE(1..20))
   ACCESS read-write
   STATUS mandatory
   DESCRIPTION
    "The community string with which the management
     station will communicate with the agent"
     ::= { rndCommunityEntry 2 }

rndCommunityAccess OBJECT-TYPE
   SYNTAX INTEGER {
    readOnly(1),
    readWrite(2),
    super(3)
      }
   ACCESS read-write
   STATUS mandatory
   DESCRIPTION
    "The allowed access to this management station"
     ::= { rndCommunityEntry 3}

rndCommunityTrapsEnable OBJECT-TYPE
   SYNTAX INTEGER {
    trapsEnable(1),
    trapsDisable(2)
     }
   ACCESS   read-write
   STATUS mandatory
   DESCRIPTION
    "Should the agent send traps to the management station"
      ::= { rndCommunityEntry 4 }

rndCommunityStatus OBJECT-TYPE
   SYNTAX INTEGER {
    enable(1),
    invalid(2)
     }
   ACCESS read-write
   STATUS mandatory
   DESCRIPTION
    "The status of this entry. If the status is invalid the
    community entry will be deleted"
    ::= { rndCommunityEntry 5 }

rndManagedTime  OBJECT-TYPE
   SYNTAX DisplayString (SIZE(6))
   ACCESS read-write
   STATUS mandatory
   DESCRIPTION
    "The time will be sent in the format hhmmss"
   ::= { rndDeviceParams 8 }

rndManagedDate  OBJECT-TYPE
   SYNTAX DisplayString (SIZE(6..8))
   ACCESS read-write
   STATUS mandatory
   DESCRIPTION
    "The date will be sent in the format ddmmyyyy"
    ::= { rndDeviceParams 9 }


genGroup  OBJECT IDENTIFIER   ::= { rndDeviceParams 11 }
genGroupHWVersion OBJECT-TYPE
   SYNTAX  DisplayString
   ACCESS  read-only
   STATUS  mandatory
   DESCRIPTION
        "Defines the HW version of the product."
   ::= { genGroup 1 }

genGroupConfigurationSymbol OBJECT-TYPE
      SYNTAX  DisplayString (SIZE(1))
      ACCESS  read-only
      STATUS  mandatory
      DESCRIPTION
      "Defines the Configuration Symbol attached to any hardware module
      manufactured by LANNET. One single character A..Z defines the CS
      version."
      ::= { genGroup 2 }

genGroupHWStatus OBJECT-TYPE
      SYNTAX  INTEGER {
        ok(1),
        hardwareProblems(2),
        notSupported(255)
      }
      ACCESS  read-only
      STATUS  mandatory
      DESCRIPTION
      "This attribute describes the status of the group hardware as detected
      by the sensors software."
      ::= { genGroup 3 }

rndInterface OBJECT IDENTIFIER ::= { rnd 4  }

-- Channel & LAN Configuration

rndIfTable  OBJECT-TYPE
    SYNTAX SEQUENCE OF  RndIfEntry
    ACCESS  not-accessible
    STATUS  mandatory
    DESCRIPTION
      "RND-specific interface table.  Each table entry includes an
      index, Board number, Network Address, interface status, clock
      indicator and interface cost."
    ::= {  rndInterface 1  }


rndIfEntry  OBJECT-TYPE
    SYNTAX RndIfEntry
    ACCESS  not-accessible
    STATUS  mandatory
    DESCRIPTION
       " The row definition for this table."
    INDEX   { rndIfIndex  }
    ::= {  rndIfTable 1  }


RndIfEntry ::= SEQUENCE {
  rndIfIndex
     INTEGER,
  rndIfBoardNum
     INTEGER,
  rndIfNetAddress
     NetworkAddress,
  rndIfStatus
     INTEGER,
  rndIfClockType
     INTEGER,
 rndIfBaudRate
     INTEGER,
  rndIfCost
     INTEGER,
  rndIfCompression
     INTEGER,
  rndIfCompressionStatus
     INTEGER,
  rndIfCompressionRate
     INTEGER,
  rndIfLATCompression
     INTEGER,
  rndIfCompressionType
     INTEGER,
rndIfFilterMode
     INTEGER,
rndIfChannelType
     INTEGER,
rndIfBridge
     INTEGER,
rndHighPriorityIf    -- New Parameters
     INTEGER,
rndWanHeader   -- New Parameters
     INTEGER,
rndDuplexMode  -- New Parameters
     INTEGER
  }

rndIfIndex OBJECT-TYPE
    SYNTAX   INTEGER
    ACCESS  read-only
    STATUS  mandatory
    DESCRIPTION
     "Index to the RND Interface Table. The interface defined by a
     particular value of this index is the same interface as
     identified by the same value of ifIndex (MIBII)."
         ::= {  rndIfEntry 1  }

rndIfBoardNum OBJECT-TYPE
    SYNTAX   INTEGER
    ACCESS  read-only
    STATUS  mandatory
    DESCRIPTION
     "The interface defined by this entry correspTnds to the board
     defined by the same value of rndSlotBoardNum in the rndSlotTab."
    ::= {  rndIfEntry 2  }

rndIfNetAddress OBJECT-TYPE
    SYNTAX   NetworkAddress
    ACCESS  read-only
    STATUS  mandatory
    DESCRIPTION
     "The IP address of the interface defined by the particular value of
     rndIfIndex."
    ::= {  rndIfEntry 3  }

rndIfStatus  OBJECT-TYPE
    SYNTAX   INTEGER  {
       ok (1),
       okSingleBrg(2),
       okMultiBrg(3),
       connctFault(4),
       rxFault(5),
       txFault(6),
       channelLoopback(7),
       rxClockFault(8),
       t1Alarm(9)
    }
    ACCESS  read-only
    STATUS  mandatory
    DESCRIPTION
     "The current status of the interface."
     ::= {  rndIfEntry 4  }

rndIfClockType   OBJECT-TYPE
    SYNTAX  INTEGER {
       external(1),
       internal(2),
       t1(3),
       g703(4)
    }
    ACCESS  read-write
    STATUS  mandatory
    DESCRIPTION
     "rndIfClockType defines the type of clock each interface
     uses: internal or external."
    ::= {  rndIfEntry 5  }

rndIfBaudRate    OBJECT-TYPE          -- Level II routing
    SYNTAX   INTEGER   -- word
    ACCESS  read-write
    STATUS  mandatory
    DESCRIPTION
     " Defines the baud rate of use by the interface. The valid
      rates are determined by the type of the media for which this
      baud rate is defined."
    ::= { rndIfEntry 6  }


rndIfCost    OBJECT-TYPE          -- Level II routing
    SYNTAX   INTEGER   -- word
    ACCESS  read-write
    STATUS  mandatory
    DESCRIPTION
       "This variable assigns a transmission cost to the interface
        (channel or LAN). These costs are used in Level II routing. The
        costs aretypically inversly proportional to the channel quality."
    ::= { rndIfEntry 7  }

rndIfCompression   OBJECT-TYPE
    SYNTAX  INTEGER {
       enable(1),
       disable(2)
    }
    ACCESS  read-write
    STATUS  mandatory
    DESCRIPTION
       "Defines whether data compression is enabled or disabled for the
       interface."
    ::= {  rndIfEntry 8  }

  rndIfCompressionStatus  OBJECT-TYPE
  SYNTAX  INTEGER {
       not-inserted(1),
       active(2),
       not-active(3),
       disable(4)
    }
    ACCESS  read-only
    STATUS  mandatory
    DESCRIPTION
       "Defines the status of the compression component:
        not-inserted - Compression component is not in the device
        active -     Compression is enabled and operates correctly
        not-active - Compression is enables but does not operate.
                     The reason may be that there is no compression
                     component on the device connected to this interface.
        disabled   - Compression was disabled by management, using
                     variable rndCompression."
    ::= {  rndIfEntry 9  }

  rndIfCompressionRate  OBJECT-TYPE
    SYNTAX  INTEGER
    ACCESS  read-only
    STATUS  mandatory
    DESCRIPTION
  "Percentage of compression. This variable applies only
  if rndCompressionStatus is active."
    ::= {  rndIfEntry 10  }

  rndIfLATCompression  OBJECT-TYPE
    SYNTAX  INTEGER {
       enable(1),
       disable(2)
    }
    ACCESS  read-write
    STATUS  mandatory
    DESCRIPTION
  "Enable/Disable the LAT Compression."
    ::= {  rndIfEntry 11  }

  rndIfCompressionType  OBJECT-TYPE
    SYNTAX  INTEGER {
       none(1),
       lowSpeed(2),
       highSpeed(3)
    }
    ACCESS  read-only
    STATUS  mandatory
    DESCRIPTION
        "This parameter indicates the type of compression option available in the device.
         none(1)     - indicates that there is no compression option in the device
         lowSpeed(2) - indicates a compression option which is  operational up
                       to line speed sof 64 kbps.
         highSpeed(3)- indicates a compression option which is  operational up
                       to line speeds of 2 Mbps."
    ::= {  rndIfEntry 12  }

rndIfFilterMode  OBJECT-TYPE
    SYNTAX  INTEGER {
       destinationOnly(1),
       sourceAndDestination(2),
       none(3)
    }
    ACCESS  read-write
    STATUS  mandatory
    DESCRIPTION
         "This parameter indicates the type of filtering in the device. "
    ::= {  rndIfEntry 13 }

    rndIfChannelType OBJECT-TYPE
      SYNTAX  INTEGER {
         wanChannel(1),
         ogRanPort(2),
         routerToBridge(3),
         spsFramRelay(4),         -- Frame Relay with external SPS.
         dialBackup(5),
         snar(6),
         lan(7),
         spsX25(8),
         frameRelay1490(9),       -- Frame Relay with full  RFC1490 support.
         frameRelay1490CAR(10),   -- Frame Relay with CAR RFC1490 bridge encapsulation.
         frameRelayCAR(11),       -- Frame Relay with CAR and RND's encapsulation
         ppp(12)        -- New Value
        }
      ACCESS   read-write
      STATUS   mandatory
      DESCRIPTION
        " The type of the WAN channel "
   ::= { rndIfEntry 14 }

    rndIfBridge OBJECT-TYPE
      SYNTAX  INTEGER {
         enable(1),
         disable(2)
        }
      ACCESS   read-write
      STATUS   mandatory
      DESCRIPTION
        " This variable indicates  whether this interface forward Layer II pakages."
   ::= { rndIfEntry 15 }

    rndHighPriorityIf  OBJECT-TYPE
      SYNTAX  INTEGER {
         enable(1),
         disable(2)
        }
      ACCESS   read-write
      STATUS   mandatory
      DESCRIPTION
        " This variable indicates  whether this interface will forward pakages
        that fit HighPriority set by the manager."
       ::= { rndIfEntry 16}

    rndWanHeader  OBJECT-TYPE
      SYNTAX  INTEGER {
         regular(1),
         short(2)
        }
      ACCESS   read-write
      STATUS   mandatory
      DESCRIPTION
        " This variable indicates the RND WAN header type used for frames
          which pass through this interface. 'regular' specifies a 14 bytes
          header compatible with older OG versions and 'short' a 4 byte header
          compatible with the RND adapter product family."
       ::= { rndIfEntry 17}

    rndDuplexMode  OBJECT-TYPE
      SYNTAX  INTEGER {
         half(1),
         full(2)
        }
      ACCESS   read-write
      STATUS   mandatory
      DESCRIPTION
        " This variable indicates whether this interface operates in half duplex
          full duplex or auto negotiation mode."
       ::= { rndIfEntry 18}


-- rndIPX group defines the parameters for the IPX Router / removed 5.5.99

rndIPX   OBJECT IDENTIFIER ::= { rnd 12 }

-- This describes the - Facility for Access Control and Security
-- NEW VERSION  OF FACS MIB WITHOUT APP AND WITH SOKET Upgrade
--
rndFACS    OBJECT IDENTIFIER ::=  { rnd 16 }

rndFACSDefaultAction OBJECT-TYPE
  SYNTAX  INTEGER {
    block(1),
    forward(2),
    enable(3),
    disable(4),
    blockAndReport(129)
  }
  ACCESS  read-write
  STATUS  mandatory
  DESCRIPTION
         "Used to define the default action for the device, when no
                FACS statements applicable to a given frame are defined."

 DEFVAL  { 1 }
  ::= { rndFACS 1 }

rndFACSActTable OBJECT-TYPE
        SYNTAX  SEQUENCE OF RndFACSActEntry
        ACCESS  not-accessible
        STATUS  mandatory
        DESCRIPTION
               "The table of  FACS action."
        ::= { rndFACS 2 }

rndFACSActEntry OBJECT-TYPE
        SYNTAX  RndFACSActEntry
        ACCESS  not-accessible
        STATUS  mandatory
        DESCRIPTION
          "Each rndFACSActEntry consist of the following parameters"
        INDEX   {rndFACSActType,
                 rndFACSActIfIndex}
        ::= { rndFACSActTable 1 }

RndFACSActEntry ::= SEQUENCE {
        rndFACSActType
           INTEGER,
        rndFACSActIfIndex
           INTEGER,
        rndFACSAction
           INTEGER
                }

rndFACSActType OBJECT-TYPE
        SYNTAX  INTEGER {
              tx(1),
              rx(2),
              activeDB(4),
              tempDB(5)
            }
        ACCESS  read-only
        STATUS  mandatory
        DESCRIPTION
                "This parameter indicate on which FACS Table the FACS
                 action will preform."
        ::= { rndFACSActEntry 1 }

rndFACSActIfIndex OBJECT-TYPE
        SYNTAX  INTEGER
        ACCESS  read-only
        STATUS  mandatory
        DESCRIPTION
               "The interface to which this FACS entry is applicable."
        ::= { rndFACSActEntry 2 }


rndFACSAction OBJECT-TYPE
        SYNTAX  INTEGER {
                none(1),
                eraseIP(2),
                eraseDECnet(3),
                eraseIPX(4),
                eraseBrg(5),
                replaceIP(6),
                replaceIPX(8),
                replaceBrg(9),
                backupIP(10),
                backupIPX(12),
                backupBrg(13)
        }
        ACCESS  read-write
        STATUS  mandatory
        DESCRIPTION
               "The management station that sends a SET request for one of these actions
                with indexes  rndFACSType and rndFACSIfIndex defines the type and the
                interface  Id for which all FACS statements are to be erased.
                If no interface or no type  is specified, all FACS statements for a
                protocol are erased."
      DEFVAL  { 1 }
        ::= { rndFACSActEntry 3 }


rndFACSTable OBJECT-TYPE
  SYNTAX  SEQUENCE OF RndFACSEntry
  ACCESS  not-accessible
  STATUS  mandatory
  DESCRIPTION
         "The table of  FACS statment."
  ::= { rndFACS 3 }

rndFACSEntry OBJECT-TYPE
  SYNTAX  RndFACSEntry
  ACCESS  not-accessible
  STATUS  mandatory
  DESCRIPTION
         "Each FACS statment consist of the following parameters"
  INDEX  {rndFACSIfIndex,
          rndFACSProtocolType,
          rndFACSType,
          rndFACSIndex }
  ::= { rndFACSTable 1 }

RndFACSEntry ::= SEQUENCE {
     rndFACSIfIndex
        INTEGER,
     rndFACSProtocolType
        INTEGER,
     rndFACSType
        INTEGER,
     rndFACSIndex
        INTEGER,
     rndFACSSrcAdd
        OCTET STRING ,
     rndFACSSrcAddMask
        OCTET STRING,
     rndFACSDesAdd
        OCTET STRING,
     rndFACSDesAddMask
        OCTET STRING,
     rndFACSOperation
        INTEGER,
     rndFACSNetFiltering
        INTEGER,
     rndFACSSoketNum
        INTEGER,
     rndFACSMask1Id
        INTEGER,
     rndFACSMask2Id
        INTEGER,
     rndFACSStatus
        INTEGER
  }

rndFACSIfIndex OBJECT-TYPE
  SYNTAX  INTEGER
  ACCESS  read-only
  STATUS  mandatory
  DESCRIPTION
         "The interface to which this FACS entry is applicable."
  ::= { rndFACSEntry 1 }

rndFACSProtocolType OBJECT-TYPE
  SYNTAX  INTEGER{
                ip(1),
                ipx(2),
                dec(3),
                bridge(4)
        }
  ACCESS  read-only
  STATUS  mandatory
  DESCRIPTION
               "This parameter define the protocol the Security  Access Control
                is applicable."
  ::= { rndFACSEntry 2 }

rndFACSType OBJECT-TYPE
  SYNTAX  INTEGER {
              tx(1),
              rx(2),
              cod(3),
              activeDB(4),
              tempDB(5)
            }
  ACCESS  read-only
  STATUS  mandatory
  DESCRIPTION
                " The Mode of in which this FACS statement operates."
  ::= { rndFACSEntry 3 }

rndFACSIndex OBJECT-TYPE
  SYNTAX  INTEGER
  ACCESS  read-only
  STATUS  mandatory
  DESCRIPTION
               "Index to the FACS  Table. "
  ::= { rndFACSEntry 4 }

rndFACSSrcAdd OBJECT-TYPE
  SYNTAX  OCTET STRING
  ACCESS  read-write
  STATUS  mandatory
  DESCRIPTION
         "The size of the octet string will be according to the protocol type define in
          rndFACSProtocolType."
  ::= { rndFACSEntry 5 }

rndFACSSrcAddMask OBJECT-TYPE
  SYNTAX   OCTET STRING
  ACCESS  read-write
  STATUS  mandatory
  DESCRIPTION
         "Source-address mask ."
  ::= { rndFACSEntry 6 }

rndFACSDesAdd OBJECT-TYPE
        SYNTAX   OCTET STRING
        ACCESS  read-write
        STATUS  mandatory
        DESCRIPTION
           "Destination-address The size of the octet string will be according to the
           protocol type define in rndFACSProtocolType ."
        ::= { rndFACSEntry 7 }


rndFACSDesAddMask OBJECT-TYPE
        SYNTAX   OCTET STRING
        ACCESS  read-write
        STATUS  mandatory
        DESCRIPTION
               "Destination-address mask ."
        ::= { rndFACSEntry 8 }


rndFACSOperation OBJECT-TYPE
        SYNTAX  INTEGER {
               block(1),
               forward(2),
               permit(3),        -- For Connect On demand Only
               deny(4),          -- For Connect On demand Only
               blockZHRP(5),     -- Disable Zhrp for this FAXCS statement
               blockAndReport(129)
        }
        ACCESS  read-write
        STATUS  mandatory
        DESCRIPTION
               "... ."
        ::= { rndFACSEntry 9 }

rndFACSNetFiltering OBJECT-TYPE
        SYNTAX  INTEGER {
                none(1),
                l2multicast(2), --applicable for Bridge protocol
                arp(3),      --applicable for ip protocol
                icmp(4),     --applicable for ip protocol
                ip(5),       --applicable for ip protocol
                udp(6),      --applicable for ip protocol
                tcp(7),      --applicable for ip protocol
                decnet(8),   --applicable for decnet protocol
                ipx(9)      --applicable for ipx protocol
        }
        ACCESS  read-write
        STATUS  mandatory
        DESCRIPTION
               "... ."
        ::= { rndFACSEntry 10 }


rndFACSSoketNum OBJECT-TYPE   --applicable for ip,ipx protocol
        SYNTAX  INTEGER
         --   {none(1),
         --    ftp(21),
         --    telenet(23),
         --    smtp(25),
         --    tftp(69),
         --    snmp(161),
         --    snmpTrape(162),
         --    rip(520),
         --    saPipx(1106),
         --    ripIPX(1107)
         --  }
        ACCESS  read-write
        STATUS  mandatory
        DESCRIPTION
            " Port/socket  number for different applications
              0 is default meaning not applicable."
        ::= { rndFACSEntry 11}

rndFACSMask1Id OBJECT-TYPE
        SYNTAX  INTEGER
        ACCESS  read-write
        STATUS  mandatory
        DESCRIPTION
            " Index into RND mask table FACS/COD Type) ."
        ::= { rndFACSEntry 12}

rndFACSMask2Id OBJECT-TYPE
   SYNTAX  INTEGER
   ACCESS  read-write
   STATUS  mandatory
   DESCRIPTION
       " Index into RND mask table FACS/COD according to
       the value of rndFACSType ."
   ::= { rndFACSEntry 13}


rndFACSStatus OBJECT-TYPE
   SYNTAX  INTEGER {
     valid(1),
     createRequest(2),   --  future use
     underCreation(3),
     invalid(4)          -- logically deleted
   }
   ACCESS  read-write
   STATUS  mandatory
   DESCRIPTION
       "The status of a table entry."
   ::= { rndFACSEntry 14}

rndBootP    OBJECT IDENTIFIER ::=  { rnd 24 }

rndBootPServerAddress  OBJECT-TYPE
    SYNTAX IpAddress
    ACCESS read-write
    STATUS mandatory
    DESCRIPTION
     " The IPAddress of the BOOTP server. the OpenGate will act as a BootP relay if
       this parameter is not equale to 0.0.0.0."
    DEFVAL  {'00000000'H}
      ::= { rndBootP 1 }

rndBootPRelaySecThreshold OBJECT-TYPE
    SYNTAX INTEGER
    ACCESS read-write
    STATUS mandatory
    DESCRIPTION
       "BootP requests are relayed only if their SEC field is greater or
        equal to the threshold value in order to allow local BootP Servers
        to answer first."
    ::= { rndBootP 2 }

-- ip Specific group  Addition parameters to ip group in MIB-2

ipSpec      OBJECT IDENTIFIER ::= { rnd 26 }

rsIpAddrTable OBJECT-TYPE
    SYNTAX  SEQUENCE  OF RsIpAddrEntry
    ACCESS  not-accessible
    STATUS  mandatory
    DESCRIPTION
       "This table is parralel to MIB II IpAddrTable, and is used to
        add/delete entries to/from that table. In addition it contains
        private objects."
    ::=  { ipSpec 1 }

rsIpAddrEntry   OBJECT-TYPE
    SYNTAX  RsIpAddrEntry
    ACCESS  not-accessible
    STATUS  mandatory
    DESCRIPTION
            "The addressing information for one of this
            entity's IP addresses."
    INDEX  {rsIpAdEntAddr}
    ::=  { rsIpAddrTable 1 }

RsIpAddrEntry ::= SEQUENCE {
    rsIpAdEntAddr                IpAddress,
    rsIpAdEntIfIndex             INTEGER,
    rsIpAdEntNetMask             IpAddress,
    rsIpAdEntForwardIpBroadcast  INTEGER,
    rsIpAdEntReasmMaxSize        INTEGER, 
    rsIpAdEntStatus              INTEGER,
    rsIpAdEntBcastAddr           INTEGER,
    rsIpAdEntVlanTag             INTEGER
    }

rsIpAdEntAddr OBJECT-TYPE
    SYNTAX  IpAddress
    ACCESS  read-only
    STATUS  mandatory
    DESCRIPTION
            "The IP address to which this entry's addressing
            information pertains."
    ::= { rsIpAddrEntry 1 }

rsIpAdEntIfIndex OBJECT-TYPE
    SYNTAX  INTEGER
    ACCESS  read-write
    STATUS  mandatory
    DESCRIPTION
            "The index value which uniquely identifies the
            interface to which this entry is applicable.  The
            interface identified by a particular value of this
            index is the same interface as identified by the
            same value of ifIndex."
    ::= { rsIpAddrEntry 2 }

rsIpAdEntNetMask OBJECT-TYPE
    SYNTAX  IpAddress
    ACCESS  read-write
    STATUS  mandatory
    DESCRIPTION
            "The subnet mask associated with the IP address of
            this entry.  The value of the mask is an IP
            address with all the network bits set to 1 and all
            the hosts bits set to 0."
    ::= { rsIpAddrEntry 3 }

rsIpAdEntForwardIpBroadcast OBJECT-TYPE
    SYNTAX INTEGER {
       enable(1),
       disable(2)
       }
    ACCESS  read-write
    STATUS  mandatory
    DESCRIPTION
        " This variable controls forwarding of IP (sub)net-directed
          broadcasts destined for an attached sub(net). "
    DEFVAL  { enable }
    ::=   { rsIpAddrEntry 4 }

rsIpAdEntReasmMaxSize OBJECT-TYPE
    SYNTAX  INTEGER (0..65535)
    ACCESS  read-only
    STATUS  mandatory
    DESCRIPTION
         "The size of the largest IP datagram which this
          entity can re-assemble from incoming IP fragmented
          datagrams received on this interface."
    ::= { rsIpAddrEntry 5 }

rsIpAdEntStatus OBJECT-TYPE
    SYNTAX INTEGER{
       valid(1),
       invalid(2)
       }
    ACCESS  read-write
    STATUS  mandatory
    DESCRIPTION
        " The validity of this entry. Invalid indicates that this entry is
          invalid in IpAddrTable (MIB II)."
    DEFVAL  { valid }
    ::=   { rsIpAddrEntry 6 }

rsIpAdEntBcastAddr OBJECT-TYPE
    SYNTAX INTEGER (0..1)
    ACCESS read-write
    STATUS mandatory
    DESCRIPTION
        " Indicates how the host part of ip subnet broadcast messages will be
          filled:
           0 - host part will be filled by 0
           1 - host part will be filled by 1."
    ::=   { rsIpAddrEntry 7 }

rsIpAdEntVlanTag OBJECT-TYPE
    SYNTAX  INTEGER
    ACCESS  read-write
    STATUS  mandatory
    DESCRIPTION
            "The vlan Tag value that represent this ip interface
             this filed include both vlna tag and vlan priority "
    ::= { rsIpAddrEntry 8 }


icmpSpec               OBJECT IDENTIFIER ::= { ipSpec 2 }

rsIcmpGenErrMsgEnable   OBJECT-TYPE
    SYNTAX INTEGER {
       enable(1),
       disable(2)
   }
    ACCESS  read-write
    STATUS  mandatory
    DESCRIPTION
           "This variable controlls the ability to generate ICMP error messages"
    DEFVAL  { enable }
    ::= { icmpSpec 1 }

rsIcmpRdTable OBJECT-TYPE
    SYNTAX  SEQUENCE  OF RsIcmpRdEntry
    ACCESS  not-accessible
    STATUS  mandatory
    DESCRIPTION
       "This table contains ICMP Router Discovery parameters
        configurated per IP interface."
    ::=  {icmpSpec 2}

rsIcmpRdEntry   OBJECT-TYPE
    SYNTAX  RsIcmpRdEntry
    ACCESS  not-accessible
    STATUS  mandatory
    DESCRIPTION
           "The ICMP parameters configurated for IP interface."
    INDEX  {rsIcmpRdIpAddr}
    ::=  {rsIcmpRdTable 1}

RsIcmpRdEntry ::= SEQUENCE {
    rsIcmpRdIpAddr             IpAddress,
    rsIcmpRdIpAdvertAddr       IpAddress,
    rsIcmpRdMaxAdvertInterval  INTEGER,
    rsIcmpRdMinAdvertInterval  INTEGER,
    rsIcmpRdAdvertLifetime     INTEGER,
    rsIcmpRdAdvertise          INTEGER,
    rsIcmpRdPreferenceLevel    INTEGER,
    rsIcmpRdEntStatus          INTEGER
    }

rsIcmpRdIpAddr OBJECT-TYPE
    SYNTAX  IpAddress
    ACCESS  read-only
    STATUS  mandatory
    DESCRIPTION
            "The IP address to which this entry's information pertains."
    ::= {rsIcmpRdEntry 1}

rsIcmpRdIpAdvertAddr OBJECT-TYPE
    SYNTAX  IpAddress
    ACCESS  read-write
    STATUS  mandatory
    DESCRIPTION
            " The IP destination address to be used for multicast
              Router Advertisements sent from the interface. The
              only permissible values are the all-systems multicast
              address, 224.0.0.1, or the limited-broadcast address,
              255.255.255.255."
    DEFVAL  {'E0000001'H}
    ::= {rsIcmpRdEntry 2}

rsIcmpRdMaxAdvertInterval OBJECT-TYPE
    SYNTAX  INTEGER (4..1800)
    ACCESS  read-write
    STATUS  mandatory
    DESCRIPTION
            "The maximum time allowed between sending multicast
             Router Advertisements from the interface, in seconds.
             Must be no less than 4 seconds and no greater than 1800
             seconds."
    DEFVAL  {600}
    ::= {rsIcmpRdEntry 3}

rsIcmpRdMinAdvertInterval OBJECT-TYPE
    SYNTAX  INTEGER (3..1800)
    ACCESS  read-write
    STATUS  mandatory
    DESCRIPTION
            "The minimum time allowed between sending unsolicited
             multicast Router Advertisements from the interface, in
             seconds.  Must be no less than 3 seconds and no greater
             than rsIcmpRdMaxAdvertInterval.
             Default: 0.75 * rsIcmpRdMaxAdvertInterval."
    ::= {rsIcmpRdEntry 4}

rsIcmpRdAdvertLifetime OBJECT-TYPE
    SYNTAX  INTEGER (4..9000)
    ACCESS  read-write
    STATUS  mandatory
    DESCRIPTION
             "The maximum length of time that the advertised addresses
             are to be considered as valid. Must be no less than
             rsIcmpRdMaxAdvertInterval and no greater than 9000 seconds.
             Default: 3 * rsIcmpRdMaxAdvertInterval."
    ::= {rsIcmpRdEntry 5}

rsIcmpRdAdvertise OBJECT-TYPE
    SYNTAX  INTEGER {
       enable  (1),
       disable (2)
       }
    ACCESS  read-write
    STATUS  mandatory
    DESCRIPTION
             "A flag indicating whether or not the address is to be
              advertised."
    DEFVAL  {enable}
    ::= {rsIcmpRdEntry 6}

rsIcmpRdPreferenceLevel OBJECT-TYPE
    SYNTAX  INTEGER
    ACCESS  read-write
    STATUS  mandatory
    DESCRIPTION
             "The preferability of the address as a default router
             address, relative to other router addresses on the same
             subnet."
    DEFVAL  {0}
    ::= {rsIcmpRdEntry 7}

rsIcmpRdEntStatus  OBJECT-TYPE
    SYNTAX INTEGER
    ACCESS  read-write
    STATUS  mandatory
    DESCRIPTION
            "Setting of any value to this object set values of
             all fields to the default values."
    ::=   {rsIcmpRdEntry 8}


rip2Spec              OBJECT IDENTIFIER ::= { ipSpec  3 }

rsRip2IfConfTable OBJECT-TYPE
    SYNTAX  SEQUENCE  OF RsRip2IfConfEntry
    ACCESS  not-accessible
    STATUS  mandatory
    DESCRIPTION
           "This table is extension of rip2IfConfTable (RFC 1389 ,RIP 2)"
    ::=  { rip2Spec 1  }

rsRip2IfConfEntry   OBJECT-TYPE
    SYNTAX  RsRip2IfConfEntry
    ACCESS  not-accessible
    STATUS  mandatory
    DESCRIPTION " "
    INDEX  { rsRip2IfConfAddress }
    ::=  {  rsRip2IfConfTable 1  }

RsRip2IfConfEntry  ::= SEQUENCE {
    rsRip2IfConfAddress    IpAddress,
    rsRip2IfConfVirtualDis INTEGER,
    rsRip2IfConfAutoSend   INTEGER
    }

rsRip2IfConfAddress  OBJECT-TYPE
    SYNTAX IpAddress
    ACCESS  read-only
    STATUS  mandatory
    DESCRIPTION
      " The IP Address of this system on the indicated subnet. "
    ::=  { rsRip2IfConfEntry 1 }


rsRip2IfConfVirtualDis OBJECT-TYPE
    SYNTAX INTEGER
    ACCESS  read-write
    STATUS  mandatory
    DESCRIPTION
         "This variable defines the virtual number of hops assigned to
          the interface specified by rsIfIpAddrIndex. This enables
          fine-tuning of the RIP routing algorithm."
    DEFVAL  { 1 }
    ::=   { rsRip2IfConfEntry  2  }

rsRip2IfConfAutoSend OBJECT-TYPE
    SYNTAX  INTEGER {
       enable  (1),
       disable (2)
       }
    ACCESS  read-write
    STATUS  mandatory
    DESCRIPTION
         "This variable controls RIP automatic send behavior. If enabled
          and no routers were heard on the interface, RIP will only send
          default route with high metric. Otherwise RIP will send updates
          according to configuration. "
    DEFVAL  {enable}
     ::=   { rsRip2IfConfEntry  3  }


arpSpec                OBJECT IDENTIFIER ::= { ipSpec 4 }

rsArpDeleteTable OBJECT-TYPE
    SYNTAX  INTEGER
    ACCESS  read-write
    STATUS  mandatory
    DESCRIPTION
         "Setting this object to any not-null value has the effect of deleting
          all entries of the ARP table."
    ::= { arpSpec 1  }

rsArpInactiveTimeOut OBJECT-TYPE
    SYNTAX INTEGER
    ACCESS  read-write
    STATUS  mandatory
    DESCRIPTION
         "This variable defines the maximum time period (in second) that can
          pass between ARP requests concerning an entry in the ARP table.
          After this time period, the entry is deleted from the table."
    DEFVAL  { 60000 }
    ::= { arpSpec 2  }

rsArpProxy OBJECT-TYPE
    SYNTAX INTEGER {
       enable(1),
       disable(2)
    }
    ACCESS read-write
    STATUS mandatory
    DESCRIPTION
         "When ARP Proxy is enabled, the router can respond to
          ARP requests for nodes located on a different sub-net,
          provided they are it its network table. The router responds
          with its own MAC address.
          When ARP Proxy is disabled, the router responds only
          to ARP requests for its own IP addresses."
    DEFVAL  { disable }
    ::= { arpSpec 3  }

tftp     OBJECT IDENTIFIER ::= { ipSpec 5 }

rsTftpRetryTimeOut OBJECT-TYPE
    SYNTAX  INTEGER
    ACCESS  read-write
    STATUS  mandatory
    DESCRIPTION
        " General Retransmission time-out value (seconds) "
    DEFVAL  { 15 }
    ::= { tftp 1 }

rsTftpTotalTimeOut OBJECT-TYPE
    SYNTAX  INTEGER
    ACCESS  read-write
    STATUS  mandatory
    DESCRIPTION
        " Total Retransmission time-out value (seconds) "
    DEFVAL  { 60 }
    ::= { tftp 2 }

rsSendConfigFile OBJECT-TYPE
    SYNTAX DisplayString
    ACCESS  read-write
    STATUS  mandatory
    DESCRIPTION
        "The file name include path where the Router Server will put the full
         configuration. The default destination address will be the sender
         address."
    ::= { tftp 3 }

rsGetConfigFile OBJECT-TYPE
    SYNTAX DisplayString
    ACCESS  read-write
    STATUS  mandatory
    DESCRIPTION
        "The file name include path where the Router Server will get the
         configuration. The default source address will be the sender address."
    ::= { tftp 4 }

rsLoadSoftware OBJECT-TYPE
    SYNTAX DisplayString
    ACCESS  read-write
    STATUS  mandatory
    DESCRIPTION
        "The file name include path where the Router Server will get the
         software. The source address will the sender address."
    ::= { tftp 5 }

rsFileServerAddress OBJECT-TYPE
    SYNTAX  IpAddress
    ACCESS  read-write
    STATUS  mandatory
    DESCRIPTION
        "The IP address of the configuration / sw server."
        ::= { tftp 6 }


ipRedundancy    OBJECT IDENTIFIER ::= { ipSpec 6 }

ipRedundAdminStatus OBJECT-TYPE
    SYNTAX  INTEGER {
        enable(1),
        disable(2),
        vrrp(3)
       }
    ACCESS  read-write
    STATUS  mandatory
    DESCRIPTION
     "This variable controls the IP Redundancy method in the device.
      In case the value is enable, it means the ARP redundancy mechanism 
      is running .If the value is vrrp, it means the former redundancy 
      mechanism is disabled, and the vrrp mechanism is enabled. 
      If the value is disable, both redundancy methods are disabled  "
    DEFVAL {disable }
    ::= { ipRedundancy 1 }

ipRedundOperStatus   OBJECT-TYPE
    SYNTAX INTEGER {
       active(1),
       inactive(2)
    }
    ACCESS  read-only
    STATUS  mandatory
    DESCRIPTION
        " obsolete "
    DEFVAL  {inactive}
    ::= { ipRedundancy 2 }

ipRedundRoutersTable OBJECT-TYPE
   SYNTAX SEQUENCE OF IpRedundRoutersEntry
   ACCESS not-accessible
   STATUS mandatory
   DESCRIPTION
    "List of IP addresses backed up by this router."
     ::= {ipRedundancy 3 }

ipRedundRoutersEntry  OBJECT-TYPE
   SYNTAX IpRedundRoutersEntry
   ACCESS not-accessible
   STATUS mandatory
   DESCRIPTION
       " The row definition for this table."
   INDEX {ipRedundRoutersIfAddr, ipRedundRoutersMainRouterAddr}
   ::= {ipRedundRoutersTable  1 }

IpRedundRoutersEntry ::= SEQUENCE {
      ipRedundRoutersIfAddr          IpAddress,
      ipRedundRoutersMainRouterAddr  IpAddress,
      ipRedundRoutersOperStatus      INTEGER,
      ipRedundRoutersPollInterval    INTEGER,
      ipRedundRoutersTimeout         INTEGER,
      ipRedundRoutersStatus          INTEGER
  }

ipRedundRoutersIfAddr OBJECT-TYPE
   SYNTAX IpAddress
   ACCESS read-only
   STATUS mandatory
   DESCRIPTION
    "The Ip address of the IP interface on which the redundancy feature
     is operational."
     ::=  { ipRedundRoutersEntry  1}

ipRedundRoutersMainRouterAddr OBJECT-TYPE
   SYNTAX IpAddress
   ACCESS read-only
   STATUS mandatory
   DESCRIPTION
    "The Ip address of the polled main router."
     ::=  { ipRedundRoutersEntry 2}

ipRedundRoutersOperStatus OBJECT-TYPE
   SYNTAX INTEGER { active(1), inactive(2) }
   ACCESS read-only
   STATUS mandatory
   DESCRIPTION
    "If active, the main router is considered inoperational and the IP
    interface operates as its backup."
     ::=  { ipRedundRoutersEntry 3 }

ipRedundRoutersPollInterval OBJECT-TYPE
   SYNTAX INTEGER
   ACCESS read-write
   STATUS mandatory
   DESCRIPTION
    "Polling interval for this router (in seconds). If 0 the router is not
     polled."
     DEFVAL  { 3 }
     ::=  { ipRedundRoutersEntry 4 }

ipRedundRoutersTimeout OBJECT-TYPE
   SYNTAX INTEGER
   ACCESS read-write
   STATUS mandatory
   DESCRIPTION
    "Interval in seconds during which the backed-up router must signal.
     If it does not signal, it is considered inoperational and the IP
     interface starts operating as backup."
     DEFVAL  { 12 }
     ::=  { ipRedundRoutersEntry  5}

ipRedundRoutersStatus OBJECT-TYPE
   SYNTAX INTEGER {
     active(1),
     notInService(2),
     notReady(3),
     createAndGo(4),
     createAndWait(5),
     destroy(6)
     }
   ACCESS read-write
   STATUS mandatory
   DESCRIPTION
    "Entry status"
     ::=  { ipRedundRoutersEntry 6}

ipRouteLeaking    OBJECT IDENTIFIER ::= { ipSpec 7 }

ipLeakStaticToRip   OBJECT-TYPE
    SYNTAX  INTEGER {
       enable  (1),
       disable (2)
       }
    ACCESS  read-write
    STATUS  mandatory
    DESCRIPTION
        "This parameter controls leaking (redistribution) of static routes
         to RIP. When enabled, all routes inserted to the IP routing table
         via SNMP are advertised into RIP."
    DEFVAL  {enable}
    ::= { ipRouteLeaking 1 }

ipLeakStaticToOspf   OBJECT-TYPE
    SYNTAX  INTEGER {
       enable  (1),
       disable (2)
       }
    ACCESS  read-write
    STATUS  mandatory
    DESCRIPTION
        "This parameter controls leaking (redistribution) of static routes
         into OSPF. When enabled, all routes inserted to the IP routing table
         via SNMP are advertised into OSPF as external routes."
    DEFVAL  {enable}
    ::= { ipRouteLeaking 2 }

ipLeakOspfToRip   OBJECT-TYPE
    SYNTAX  INTEGER {
       enable  (1),
       disable (2)
       }
    ACCESS  read-write
    STATUS  mandatory
    DESCRIPTION
        "This parameter controls leaking (redistribution) of routes
         from OSPF to RIP. If enabled, all routes learned via OSPF
         are advertised into RIP."
    DEFVAL  {disable}
    ::= { ipRouteLeaking 3 }

ipLeakRipToOspf   OBJECT-TYPE
    SYNTAX  INTEGER {
       enable  (1),
       disable (2)
       }
    ACCESS  read-write
    STATUS  mandatory
    DESCRIPTION
        "This parameter controls leaking (redistribution) of routes
         from RIP to OSPF. If enabled, all routes learned via RIP
         are advertised into OSPF as external routes."
    DEFVAL  {disable}
    ::= { ipRouteLeaking 4 }

ipLeakExtDirectToOspf   OBJECT-TYPE
    SYNTAX  INTEGER {
       enable  (1),
       disable (2)
       }
    ACCESS  read-write
    STATUS  mandatory
    DESCRIPTION
        "This parameter controls leaking (redistribution) into OSPF of
         direct routes external to OSPF, i.e. routes to local network
         corresponding to IP interfaces on which OSPF is disabled.
         When enabled, all such direct routes are advertised into OSPF
         as external routes."
    DEFVAL  {enable}
    ::= { ipRouteLeaking 5 }

ipRipFilter    OBJECT IDENTIFIER ::= { ipSpec 8 }

-- Global RIP filter is defined per IP router.

rsIpRipFilterGlbTable OBJECT-TYPE
   SYNTAX SEQUENCE OF RsIpRipFilterGlbEntry
   ACCESS  not-accessible
   STATUS  mandatory
   DESCRIPTION
      "The table of RIP global filters per IP router."
::= { ipRipFilter 1 }

rsIpRipFilterGlbEntry  OBJECT-TYPE
SYNTAX    RsIpRipFilterGlbEntry
ACCESS    not-accessible
STATUS    mandatory
DESCRIPTION
      " An entry in the RIP global filter table "
INDEX  { rsIpRipFilterGlbType,
         rsIpRipFilterGlbNumber }
::= { rsIpRipFilterGlbTable 1 }

RsIpRipFilterGlbEntry  ::= SEQUENCE {
      rsIpRipFilterGlbType            INTEGER,
      rsIpRipFilterGlbNumber          INTEGER,
      rsIpRipFilterGlbStatus          INTEGER,
      rsIpRipFilterGlbIpAddr          IpAddress,
      rsIpRipFilterGlbNetworkMaskBits INTEGER,
      rsIpRipFilterGlbMatchBits       INTEGER,
      rsIpRipFilterGlbAction          INTEGER
}

rsIpRipFilterGlbType  OBJECT-TYPE
SYNTAX INTEGER  {
    input(1),
    output(2)
}
ACCESS  read-only
STATUS  mandatory
DESCRIPTION
    " Type of filter - input/output "
::= {rsIpRipFilterGlbEntry 1}

rsIpRipFilterGlbNumber OBJECT-TYPE
SYNTAX  INTEGER
ACCESS  read-only
STATUS  mandatory
DESCRIPTION
   " Number of RIP filter. "
::= {rsIpRipFilterGlbEntry  2}

rsIpRipFilterGlbStatus OBJECT-TYPE
SYNTAX INTEGER  {
    valid (1),
    invalid (2),
    underCreation (3)
}
ACCESS read-write
STATUS mandatory
DESCRIPTION
   " The validity of this entry. Setting this value to invalid deletes
   the entry, and the entry may be actualy removed from the table."
DEFVAL  { valid }
::= {rsIpRipFilterGlbEntry 3}

rsIpRipFilterGlbIpAddr OBJECT-TYPE
SYNTAX IpAddress
ACCESS  read-write
STATUS  mandatory
DESCRIPTION
   " network prefix IP address, as in the forwarding table. "
DEFVAL {'00000000'H}
::= {rsIpRipFilterGlbEntry  4}

rsIpRipFilterGlbNetworkMaskBits  OBJECT-TYPE
SYNTAX  INTEGER
ACCESS  read-write
STATUS  mandatory
DESCRIPTION
   " the number of bits in the IP Network mask, called network-prefix-length
   in Router Requirements terminology. for example: the value 16 means
   mask 255.255.0.0 "
   DEFVAL {0}
::= {rsIpRipFilterGlbEntry 5}

rsIpRipFilterGlbMatchBits  OBJECT-TYPE
SYNTAX  INTEGER
ACCESS  read-write
STATUS  mandatory
DESCRIPTION
   " the number of bits to match in the Network IP address. A value
   smaller than 32 defines a wildcard. for example: the value 8 means
   all routes whose leftmost 8 bits are equal to those of the network IP
   address. If this variable has a value other than 32, than
   rsIpRipFilterGlbNetworkMaskBits must be 0 and is ignored. "
   DEFVAL {32}
::= {rsIpRipFilterGlbEntry 6}

rsIpRipFilterGlbAction OBJECT-TYPE
SYNTAX INTEGER {
   deny(1),
   permit(2)
}
ACCESS  read-write
STATUS  mandatory
DESCRIPTION
   " Filter action - permit/deny for this network"
DEFVAL { permit }
::= {rsIpRipFilterGlbEntry  7}


-- Intf RIP filter is defined per IP Interface

rsIpRipFilterLclTable OBJECT-TYPE
SYNTAX SEQUENCE OF RsIpRipFilterLclEntry
ACCESS  not-accessible
STATUS  mandatory
DESCRIPTION
   "Table of input/output  RIP filters used per IP Interface."
::= { ipRipFilter 2 }

rsIpRipFilterLclEntry  OBJECT-TYPE
SYNTAX RsIpRipFilterLclEntry
ACCESS not-accessible
STATUS mandatory
DESCRIPTION
   " An entry in the Intf RIP filter table"
INDEX  {rsIpRipFilterLclIpIntf,
        rsIpRipFilterLclType,
        rsIpRipFilterLclNumber}
::= { rsIpRipFilterLclTable 1 }

RsIpRipFilterLclEntry  ::= SEQUENCE {
      rsIpRipFilterLclIpIntf          IpAddress,
      rsIpRipFilterLclType            INTEGER,
      rsIpRipFilterLclNumber          INTEGER,
      rsIpRipFilterLclStatus          INTEGER,
      rsIpRipFilterLclIpAddr          IpAddress,
      rsIpRipFilterLclNetworkMaskBits INTEGER,
      rsIpRipFilterLclMatchBits       INTEGER,
      rsIpRipFilterLclAction          INTEGER
}

rsIpRipFilterLclIpIntf  OBJECT-TYPE
SYNTAX IpAddress
ACCESS  read-only
STATUS  mandatory
DESCRIPTION
   " The IP address identifying the RIP interface for this filter.
   This value corresponds to rsIpAdEntAddr. "
::= {rsIpRipFilterLclEntry 1}


rsIpRipFilterLclType  OBJECT-TYPE
SYNTAX INTEGER  {
   input(1),
   output(2)
}
ACCESS read-only
STATUS mandatory
DESCRIPTION
   " Type of filter - input/output "
::= {rsIpRipFilterLclEntry 2}

rsIpRipFilterLclNumber OBJECT-TYPE
SYNTAX INTEGER
ACCESS read-only
STATUS mandatory
DESCRIPTION
   " Number of RIP filter for this Interface"
::= {rsIpRipFilterLclEntry  3}

rsIpRipFilterLclStatus   OBJECT-TYPE
SYNTAX INTEGER  {
   valid (1),
   invalid (2),
   underCreation (3)
}
ACCESS read-write
STATUS mandatory
DESCRIPTION
   " The validity of this entry. Setting this value to invalid deletes
   the entry, and the entry may be actualy removed from the table."
DEFVAL  { valid }
::= {rsIpRipFilterLclEntry  4}

rsIpRipFilterLclIpAddr OBJECT-TYPE
SYNTAX IpAddress
ACCESS  read-write
STATUS  mandatory
DESCRIPTION
   " network prefix IP address, as in the forwarding table. "
DEFVAL {'00000000'H}
::= {rsIpRipFilterLclEntry  5}

rsIpRipFilterLclNetworkMaskBits  OBJECT-TYPE
SYNTAX  INTEGER
ACCESS  read-write
STATUS  mandatory
DESCRIPTION
   " the number of bits in the IP Network mask, called network-prefix-length
   in Router Requirements terminology. for example: the value 16 means
   mask 255.255.0.0 "
DEFVAL {0}
::= {rsIpRipFilterLclEntry 6}

rsIpRipFilterLclMatchBits  OBJECT-TYPE
SYNTAX  INTEGER
ACCESS  read-write
STATUS  mandatory
DESCRIPTION
   " the number of bits to match in the Network IP address. A value
   smaller than 32 defines a wildcard. for example: the value 8 means
   all routes whose leftmost 8 bits are equal to those of the network IP
   address. If this variable has a value other than 32, than
   rsIpRipFilterLclNetworkMaskBits must be 0 and is ignored. "
DEFVAL {32}
::= {rsIpRipFilterLclEntry 7}

rsIpRipFilterLclAction OBJECT-TYPE
SYNTAX INTEGER  {
   deny(1),
   permit(2)
}
ACCESS read-write
STATUS mandatory
DESCRIPTION
   " Filter action - permit/deny "
DEFVAL { permit }
::= {rsIpRipFilterLclEntry  8}


rsRipEnable OBJECT-TYPE
    SYNTAX  INTEGER {
      enable(1),
      disable(2)
   }
    ACCESS  read-write
    STATUS  mandatory
    DESCRIPTION
           "Enables or disables RIP."
    ::=  { ipSpec 9 }

lreBoxAgentIP OBJECT-TYPE
    SYNTAX IpAddress
    ACCESS  read-write
    STATUS  mandatory
    DESCRIPTION
           ""
    ::=  { ipSpec 10 }

virtualLan  OBJECT IDENTIFIER ::= { rnd 27 }

--
--  virtualLanTable
--
virtualLanTable  OBJECT-TYPE
   SYNTAX  SEQUENCE OF VirtualLanEntry
   ACCESS  not-accessible
   STATUS  mandatory
   DESCRIPTION
         "An entry of this table specifies an new ifIndex with a type of
          propVirtual(53)."
   ::= { virtualLan 1 }

virtualLanEntry OBJECT-TYPE
   SYNTAX  VirtualLanEntry
   ACCESS  not-accessible
   STATUS  mandatory
   DESCRIPTION
         "A list of information for each virtual LAN."
   INDEX  { vlIfIndex}
   ::= { virtualLanTable 1 }

VirtualLanEntry   ::= SEQUENCE {
     vlIfIndex          INTEGER,
     vlProto            INTEGER,
     vlAutoConfigEnable TruthValue,
     vlStatus           RowStatus,
     vlType             INTEGER
   }

vlIfIndex OBJECT-TYPE
   SYNTAX  INTEGER
   ACCESS  read-write
   STATUS  mandatory
   DESCRIPTION
         "An logical interface number, corresponded this VL"
   ::= { virtualLanEntry 1 }

vlProto  OBJECT-TYPE
   SYNTAX  INTEGER {
      other(1),
      ip(2),
      ipmulticast(3),
      ipxRaw(4),
      ipxET(5),
      ipxLLC(6),
      ipxSNAP(7),
      decNET(8),
      decLAT(9),
      netBios(10),
      appleTalk(11),
      xns(12),
      sna(13),
      userDefined(14)
      }
   ACCESS  read-write
   STATUS  mandatory
   DESCRIPTION
         "The protocol, supported by this VL. The meanings of the values are:
      other: none of the following. This VL includes any protocol except the
             following protocols. It  is a bridging VL. RS relies on
             a third-party router to exchange traffic between nodes on different
             virtual LANs of this type.
      IP:    This is a routing VL, RS will route between nodes on
             different virtual LANs.
      IPmulticast: RS will broadcast the message to all  the VL's ports. Used for
             video-conferencing applications.
      ipxRaw: This is a Routing VL, RS will route between nodes on
             different virtual LANs.
      ipxET: This is a routing VL, RS will route between nodes on
             different virtual LANs.
      ipxLLC: This is a routing VL, RS will route between nodes on
             different virtual LANs.
      ipxSNAP: This is a routing VL, RS will route between nodes on
             different virtual LANs.
      decNET: This is a bridging VL, RS relies on a third-party router
             to exchange traffic between nodes on different DECnet virtual
             LANs of this type.
      netBios: This is a Bridging VL, RS relies on a third-party router
             to exchange traffic between nodes on different NetBIOS virtual
             LANs of this type.
      appleTalk: This is a bridging VL, RS relies on a third-party router
             to exchange traffic between nodes on different AppleTalk virtual
             LANs of this type."
   ::= { virtualLanEntry 2 }

vlAutoConfigEnable  OBJECT-TYPE
   SYNTAX  TruthValue
   ACCESS  read-write
   STATUS  mandatory
   DESCRIPTION
         "It is used only in the case of IP. The meanings of the values are:
      true(1):  Autolearning is used for this VL
      false(2): Autolearning isn't used for this VL from ports, specified in
                the table virtualLanAutoConfTable."
   ::= { virtualLanEntry 3 }

vlStatus  OBJECT-TYPE
   SYNTAX  RowStatus
   ACCESS  read-write
   STATUS  mandatory
   DESCRIPTION
         "It is used to delete an entry"
   ::= { virtualLanEntry 4 }

vlType OBJECT-TYPE
   SYNTAX INTEGER {
        regular(1),
        specBroadcast(2),
        specArpReq(3),
        specBroadcastAndUnicast(4),
        specArpReqAndUnicast(5)
        }
   ACCESS  read-write
   STATUS  mandatory
   DESCRIPTION
       "regular       - ordinary type
        specBroadcast - for switches that support VLANs as a set of ports and
                        only as a broadcast domain: broadcast frames do not
                        cross VLAN's bounders, but unicast frames may be
                        transmitted between different VLANs. Permits passing
                        of broadcast frames between Vgate's VLANs.
        specArpReq -    for switches that support VLANs as a set of ports and
                        only as a broadcast domain: broadcast frames do not
                        cross VLAN's bounders, but unicast frames may be
                        transmitted between different VLANs. Permits passing
                        of ARP request frames between Vgate's VLANs.
        specBroadcastAndUnicast -
                        for switches that support VLANs as a set of ports
                        but no frame crosses VLAN's bounders. Permits passing
                        of IP/ARP request broadcast and IP unicast frames
                        between Vgate's VLANs.
        specArpReqAndUnicast -
                        for switches that support VLANs as a set of ports
                        but no frame crosses VLAN's bounders. Permits passing
                        of ARP request broadcast and IP unicast frames between
                        Vgate's VLANs. This type can be used only for IP VLANs."
   ::= { virtualLanEntry 5 }

--
--   virtualLanPortsTable
--
virtualLanPortsTable  OBJECT-TYPE
   SYNTAX SEQUENCE OF VirtualLanPortEntry
   ACCESS  not-accessible
   STATUS  mandatory
   DESCRIPTION
         "For each VL (a ifIndex with a type of propVirtual(53)) an entry of  this
           table specifies a set of ports, which it contains."
   ::= { virtualLan 2 }

virtualLanPortEntry   OBJECT-TYPE
   SYNTAX  VirtualLanPortEntry
   ACCESS  not-accessible
   STATUS  mandatory
   DESCRIPTION
         "A entry of this table specifies a  VL and a port belonging to it"
   INDEX  { vLIfIndex, vLPortIfIndex}
   ::= { virtualLanPortsTable 1 }

VirtualLanPortEntry  ::= SEQUENCE {
     vLIfIndex      INTEGER,
     vLPortIfIndex  INTEGER,
     vLPortType     INTEGER,
     vLPortStatus   RowStatus
   }

vLIfIndex  OBJECT-TYPE
   SYNTAX  INTEGER
   ACCESS  read-write
   STATUS  mandatory
   DESCRIPTION
        "An logical interface number, corresponding to this VL"
   ::= { virtualLanPortEntry 1 }

vLPortIfIndex  OBJECT-TYPE
   SYNTAX  INTEGER
   ACCESS  read-write
   STATUS  mandatory
   DESCRIPTION
         "A physical port belonging to the VL specified by vlIfIndex."
   ::= { virtualLanPortEntry 2 }

vLPortType   OBJECT-TYPE
   SYNTAX  INTEGER {static(1), dynamic(2) }
   ACCESS  read-only
   STATUS  mandatory
   DESCRIPTION
         "static means configured by user dynamic means autoconfigured by the RS"
   ::= { virtualLanPortEntry 3}

vLPortStatus  OBJECT-TYPE
   SYNTAX  RowStatus
   ACCESS  read-write
   STATUS  mandatory
   DESCRIPTION
         "It is used to delete an entry"
   ::= { virtualLanPortEntry 4}

--
--   virtualLanAutoConfTable
--
virtualLanAutoConfTable  OBJECT-TYPE
   SYNTAX SEQUENCE OF VirtualLanAutoConfEntry
   ACCESS  not-accessible
   STATUS  mandatory
   DESCRIPTION
         "This table specifies per a routing protocol a set of ports, from which
           RS will automatically  learning VL in accordance with rules, defined
           by the protocol."
   ::= { virtualLan 3 }

virtualLanAutoConfEntry   OBJECT-TYPE
   SYNTAX  VirtualLanAutoConfEntry
   ACCESS  not-accessible
   STATUS  mandatory
   DESCRIPTION
       "One port, specified by vlAutoConfPortIfIndex, for which the RS will
        automatically  learn its VL in accordance with rules, defined
        by  the protocol specified in vlAutoConfProto."
   INDEX  {vlAutoConfPortIfIndex,
           vlAutoConfProto}
   ::= { virtualLanAutoConfTable 1 }

VirtualLanAutoConfEntry ::= SEQUENCE {
   vlAutoConfProto        INTEGER,
   vlAutoConfPortIfIndex  INTEGER,
   vlAutoConfStatus       RowStatus
   }
vlAutoConfPortIfIndex OBJECT-TYPE
   SYNTAX  INTEGER
   ACCESS  read-write
   STATUS  mandatory
   DESCRIPTION
         "Port on which the autoconfig option should be supported"
   ::= { virtualLanAutoConfEntry 1 }

vlAutoConfProto OBJECT-TYPE
   SYNTAX  INTEGER {
      ip(2)
      }
   ACCESS  read-only
   STATUS  mandatory
   DESCRIPTION
         "Protocol for which the autoconfig option is supported for the port
          specified by vlAutoConfPortIfIndex  "
   ::= {virtualLanAutoConfEntry 2 }

vlAutoConfStatus  OBJECT-TYPE
   SYNTAX  RowStatus
   ACCESS  read-write
   STATUS  mandatory
   DESCRIPTION
         "It is used to delete an entry"
   ::= { virtualLanAutoConfEntry 3 }

virtualLanAutoConfAgingTimeout  OBJECT-TYPE
   SYNTAX  INTEGER
   ACCESS  read-write
   STATUS  mandatory
   DESCRIPTION
         "The units of this MIB object is seconds.
          Its value can be either 0 or in range 10..65535 ."
   DEFVAL  { 3600 }
   ::= { virtualLan 4 }

virtualLanProtocolVlan  OBJECT IDENTIFIER ::= { virtualLan 5 }

virtualLanUserEtherType  OBJECT-TYPE
   SYNTAX OCTET STRING(SIZE(2))
   ACCESS  read-write
   STATUS  mandatory
   DESCRIPTION
         ""
   ::= { virtualLanProtocolVlan 1}

virtualLanUserMask  OBJECT-TYPE
   SYNTAX OCTET STRING(SIZE(2))
   ACCESS  read-write
   STATUS  mandatory
   DESCRIPTION
         ""
   ::= { virtualLanProtocolVlan 2}

--

rsConf  OBJECT IDENTIFIER ::= { rnd 28 }

-- The following MIB group is used by the Management/Configuration
-- station to configure the device interfaces,
-- physicals as well as virtuals Networks..
-- Each entry in the rsConfTable should have one of
-- the extended rsIfType.
-- It will also have a corresponding entry in the standard iftable.
-- The implementation uses these inputs to build the interface
-- layer of the device. The output is reflected in the
-- ifTable and ifStackTable which are implementation dependent.

RsIfType ::= INTEGER
--      STATUS  current
--       DESCRIPTION
--           "This type defines what type of sub-layer is used
--            in each entry of rsIfConfTable.
--            It should contain values from IANAifType
--            type for standard sub-layer, and values (starting from 500
--            decimal) for private sub-layers.
--            The values of ifType field in ifTable should be taken
--            from this type for ifTable entries which have full correlation
--            with entries in rsIfConfTable.
--            Other entries in ifTable should have other
--            ifType values (defined by other type) depend on the specific
--            implementation."
           {
            ppp(23),             -- From IANAifType
            frameRelay(32),      --     "
            virtualNet(500),
            rndWan(1000),        -- Rad/Rnd private
            cod(1001),               --      "
            backup(1002),         --      "
            fr1490(1003),          --      "
            b1isdn(1010),
            b2isdn(1011),
            unknown(1100)
           }


rsIfConfTable OBJECT-TYPE
   SYNTAX SEQUENCE OF RsIfConfEntry
   ACCESS  not-accessible
   STATUS  mandatory
   DESCRIPTION
        "This table enable the user to add interface  to the RS.
           RS will automatically  add the new interface to the interface Table "
   ::= { rsConf 1 }

rsIfConfEntry OBJECT-TYPE
       SYNTAX RsIfConfEntry
       ACCESS  not-accessible
       STATUS  mandatory
       DESCRIPTION
           "Each entry defines a configured interface."
       INDEX { rsIfConfIndex }
      ::= { rsIfConfTable 1 }


RsIfConfEntry ::= SEQUENCE {
   rsIfConfIndex  INTEGER,
   rsIfConfType   RsIfType,
   rsIfConfName   DisplayString,
   rsIfConfStatus RowStatus
      }
rsIfConfIndex OBJECT-TYPE
   SYNTAX  INTEGER
   ACCESS  read-only
   STATUS  mandatory
   DESCRIPTION
       "This variable uniquely identifies the interface.
       It is used as a cross reference in other system tables"
   ::= { rsIfConfEntry 1 }

rsIfConfType  OBJECT-TYPE
   SYNTAX  RsIfType
   ACCESS  read-write
   STATUS  mandatory
   DESCRIPTION
       "This variable identifies the type of the specific
       entry in the rsIfConfTable.
       This field is writable only at creation time
       (i.e., when value of status is underCreation)."
   ::= { rsIfConfEntry 2 }

rsIfConfName  OBJECT-TYPE
   SYNTAX  DisplayString
   ACCESS  read-write
   STATUS  mandatory
   DESCRIPTION
       "This variable provides a logical name to a specific entry in
       rsIfConfTable"
   ::= { rsIfConfEntry 3 }

rsIfConfStatus  OBJECT-TYPE
   SYNTAX  RowStatus
   ACCESS  read-write
   STATUS  mandatory
   DESCRIPTION
       "The status of the ConfigEntry.  The choices are those
       defined in SNMPv2-TC. Only: active, createAndWait, and destroy
       will be used.
       active - The conceptual row is available for use by the managed device.
       createAndWait - A new instance of a conceptual row is desired, but
       not to have it available for use by the managed device.
       destroy - Delete all instances associated with an existing conceptual row."
   ::= { rsIfConfEntry 4 }

rsTunning  OBJECT IDENTIFIER ::= { rnd 29 }

rsHighPriority OBJECT-TYPE
    SYNTAX INTEGER
    ACCESS  read-write
    STATUS  mandatory
    DESCRIPTION
      "This variable indicates the time interval the forwarding task inside the
      RS works in High Priority Mode."
    ::=  { rsTunning 1  }

rsLowPriority OBJECT-TYPE
    SYNTAX INTEGER
    ACCESS  read-write
    STATUS  mandatory
    DESCRIPTION
      "This variable indicates the time interval the forwarding task inside the
      RS works in Low Priority Mode."
    ::=  { rsTunning 2  }

rsDbgLevel OBJECT-TYPE
    SYNTAX INTEGER
    ACCESS  read-write
    STATUS  mandatory
    DESCRIPTION
      "This variable indicates the debug level the Router Server works.
       the range of this variable is 1..100 "
    ::=  { rsTunning 3  }

rsDiagnostic  OBJECT-TYPE
    SYNTAX DisplayString
    ACCESS  read-only
    STATUS  mandatory
    DESCRIPTION
      "This variable  will contain some dignostic information in case on a
       problem ocurs in the RS functinality."
    ::=  { rsTunning 4 }

rsConfirmMessagTab  OBJECT-TYPE
    SYNTAX INTEGER
    ACCESS  read-write
    STATUS  mandatory
    DESCRIPTION
      "This variable  enables the operator to confirm all the message in the
       event Message Table."
    ::=  { rsTunning 5 }

eventMessageTable OBJECT-TYPE
   SYNTAX SEQUENCE OF EventMessageEntry
   ACCESS not-accessible
   STATUS mandatory
   DESCRIPTION
    "The Event Message table of the agent"
     ::= { rsTunning 6 }

eventMessageEntry  OBJECT-TYPE
   SYNTAX EventMessageEntry
   ACCESS not-accessible
   STATUS mandatory
   DESCRIPTION
       " The row definition for this table."
   INDEX { eventNum }
   ::= {eventMessageTable 1}

EventMessageEntry  ::= SEQUENCE {
   eventNum        INTEGER,
   eventDesc       DisplayString
   }

eventNum OBJECT-TYPE
   SYNTAX INTEGER
   ACCESS read-only
   STATUS mandatory
   DESCRIPTION
      "The event number,the index of this table."
   ::= {eventMessageEntry 1}

eventDesc  OBJECT-TYPE
   SYNTAX DisplayString
   ACCESS read-only
   STATUS mandatory
   DESCRIPTION
      "The event discription, this text will include time and severity."
  ::= {eventMessageEntry 2}

reaTunning OBJECT IDENTIFIER ::= { rsTunning 7 }

reaIpRemoteAgingTime OBJECT-TYPE
    SYNTAX INTEGER
    ACCESS  read-write
    STATUS  mandatory
    DESCRIPTION
      "This variable specifies aging time used by the REA for remote
       entries in the Ip Fast Forwarding Table."
    ::=  { reaTunning 1 }

reaFftHashMaxChain OBJECT-TYPE
    SYNTAX INTEGER
    ACCESS  read-write
    STATUS  mandatory
    DESCRIPTION
      "This variable specifies the maximum length of hash chains in
       the Fast Forwarding Tables."
    ::=  { reaTunning 2 }

reaMltcstBitOn OBJECT-TYPE
    SYNTAX INTEGER {
        on  (1),
        off (2)
    }
    ACCESS  read-write
    STATUS  mandatory
    DESCRIPTION
      ""
    ::=  { reaTunning 3 }

reaIpForwardEnable OBJECT-TYPE
    SYNTAX INTEGER {
        enable  (1),
        disable (2)
    }
    ACCESS  read-write
    STATUS  mandatory
    DESCRIPTION
      "The Platform will perform fast IP forwarding if only if this
       variable's value is enable."
    ::=  { reaTunning 4 }

reaIpxForwardEnable OBJECT-TYPE
    SYNTAX INTEGER {
        enable  (1),
        disable (2)
    }
    ACCESS  read-write
    STATUS  mandatory
    DESCRIPTION
      "The Platform will perform fast IPX forwarding if only if this
       variable's value is enable."
    ::=  { reaTunning 5 }

reaBridgeEnable OBJECT-TYPE
    SYNTAX INTEGER {
        enable  (1),
        disable (2)
    }
    ACCESS  read-write
    STATUS  mandatory
    DESCRIPTION
      "The Platform will perform bridging if only if this
       variable's value is enable."
    ::=  { reaTunning 6 }

reaFacsEnable OBJECT-TYPE
    SYNTAX INTEGER {
        enable  (1),
        disable (2)
    }
    ACCESS  read-write
    STATUS  mandatory
    DESCRIPTION
      "The RS and Platform will perform FASC if only if this
       variable's value is enable."
    ::=  { reaTunning 7 }

reaIpForwardDatagrams OBJECT-TYPE
    SYNTAX Counter
    ACCESS  read-only
    STATUS  mandatory
    DESCRIPTION
      "The number of IP datagrams have been forwarded by the Platform."
    ::=  { reaTunning 8 }

reaIpInDiscards OBJECT-TYPE
    SYNTAX Counter
    ACCESS  read-only
    STATUS  mandatory
    DESCRIPTION
      "The number of IP datagrams have been dicarded by the Platform."
    ::=  { reaTunning 9 }

reaIpxForwardDatagrams OBJECT-TYPE
    SYNTAX Counter
    ACCESS  read-only
    STATUS  mandatory
    DESCRIPTION
      "The number of IPX datagrams have been forwarded by the Platform."
    ::=  { reaTunning 10 }

reaIpxInDiscards OBJECT-TYPE
    SYNTAX Counter
    ACCESS  read-only
    STATUS  mandatory
    DESCRIPTION
      "The number of IP datagrams have been dicarded by the Platform."
    ::=  { reaTunning 11 }

reaBridgeFftTable OBJECT-TYPE
    SYNTAX SEQUENCE OF ReaBridgeFftEntry
    ACCESS not-accessible
    STATUS mandatory
    DESCRIPTION
      "The Bridge Fast Forwarding Table"
    ::=  { reaTunning 12 }

reaBridgeFftEntry  OBJECT-TYPE
   SYNTAX ReaBridgeFftEntry
   ACCESS not-accessible
   STATUS mandatory
   DESCRIPTION
       " The row definition for this table."
   INDEX { reaBrgFftEntryNum }
   ::= { reaBridgeFftTable 1 }

ReaBridgeFftEntry ::= SEQUENCE {
        reaBrgFftEntryNum           INTEGER,
        reaBrgFftMacAddr            PhysAddress,    -- from RFC1213
        reaBrgFftReNum              INTEGER,        -- 1..N
        reaBrgFftPortNum            INTEGER,        -- 1..N
        reaBrgFftFacsSrcIndex       INTEGER,
        reaBrgFftFacsDstIndex       INTEGER
   }

reaBrgFftEntryNum OBJECT-TYPE
   SYNTAX INTEGER
   ACCESS   read-only
   STATUS mandatory
   DESCRIPTION
       ""
   ::=  { reaBridgeFftEntry 1 }

reaBrgFftMacAddr OBJECT-TYPE
   SYNTAX PhysAddress
   ACCESS   read-only
   STATUS mandatory
   DESCRIPTION
       ""
   ::=  { reaBridgeFftEntry 2 }

reaBrgFftReNum OBJECT-TYPE
   SYNTAX INTEGER
   ACCESS   read-only
   STATUS mandatory
   DESCRIPTION
       ""
   ::=  { reaBridgeFftEntry 3 }

reaBrgFftPortNum OBJECT-TYPE
   SYNTAX INTEGER
   ACCESS   read-only
   STATUS mandatory
   DESCRIPTION
       ""
   ::=  { reaBridgeFftEntry 4 }

reaBrgFftFacsSrcIndex OBJECT-TYPE
   SYNTAX INTEGER
   ACCESS   read-only
   STATUS mandatory
   DESCRIPTION
       ""
   ::=  { reaBridgeFftEntry 5 }

reaBrgFftFacsDstIndex OBJECT-TYPE
   SYNTAX INTEGER
   ACCESS   read-only
   STATUS mandatory
   DESCRIPTION
       ""
   ::=  { reaBridgeFftEntry 6 }

reaBrgDiscards OBJECT-TYPE
    SYNTAX Counter
    ACCESS  read-only
    STATUS  mandatory
    DESCRIPTION
      "The number of bridging datagrams have been discarded by the Platform."
    ::=  { reaTunning 13 }

reaBrgForwards OBJECT-TYPE
    SYNTAX Counter
    ACCESS  read-only
    STATUS  mandatory
    DESCRIPTION
      "The number of bridging datagrams have been forwarded by the Platform."
    ::=  { reaTunning 14 }

reaIpFftTable OBJECT-TYPE
    SYNTAX SEQUENCE OF ReaIpFftEntry
    ACCESS not-accessible
    STATUS mandatory
    DESCRIPTION
      "The IP Fast Forwarding Table"
    ::=  { reaTunning 15 }

reaIpFftEntry  OBJECT-TYPE
   SYNTAX ReaIpFftEntry
   ACCESS not-accessible
   STATUS mandatory
   DESCRIPTION
       " The row definition for this table."
   INDEX { reaIpFftEntryNum }
   ::= { reaIpFftTable 1 }

ReaIpFftEntry ::= SEQUENCE {
        reaIpFftEntryNum            INTEGER,
        reaIpFftDstIpAddr           IpAddress,
        reaIpFftDstIpMask           IpAddress,
        reaIpFftRangeType           INTEGER,
        reaIpFftSrcMacAddr          PhysAddress,
        reaIpFftDstMacAddr          PhysAddress,
        reaIpFftReNum               INTEGER,        -- 1..N
        reaIpFftPortNum             INTEGER,        -- 1..N
        reaIpFftFacsSrcIndex        INTEGER,
        reaIpFftFacsDstIndex        INTEGER,
        reaIpFftApplFlags           OCTET STRING
   }

reaIpFftEntryNum OBJECT-TYPE
   SYNTAX INTEGER
   ACCESS   read-only
   STATUS mandatory
   DESCRIPTION
       ""
   ::=  { reaIpFftEntry 1 }

reaIpFftDstIpAddr OBJECT-TYPE
   SYNTAX IpAddress
   ACCESS   read-only
   STATUS mandatory
   DESCRIPTION
       ""
   ::=  { reaIpFftEntry 2 }

reaIpFftDstIpMask OBJECT-TYPE
   SYNTAX IpAddress
   ACCESS   read-only
   STATUS mandatory
   DESCRIPTION
       ""
   ::=  { reaIpFftEntry 3 }

reaIpFftRangeType OBJECT-TYPE
   SYNTAX INTEGER {
        direct (1),
        remote (2)
   }
   ACCESS   read-only
   STATUS mandatory
   DESCRIPTION
       ""
   ::=  { reaIpFftEntry 4 }

reaIpFftSrcMacAddr OBJECT-TYPE
   SYNTAX PhysAddress
   ACCESS   read-only
   STATUS mandatory
   DESCRIPTION
       ""
   ::=  { reaIpFftEntry 5 }

reaIpFftDstMacAddr OBJECT-TYPE
   SYNTAX PhysAddress
   ACCESS   read-only
   STATUS mandatory
   DESCRIPTION
       ""
   ::=  { reaIpFftEntry 6 }

reaIpFftReNum OBJECT-TYPE
   SYNTAX INTEGER
   ACCESS   read-only
   STATUS mandatory
   DESCRIPTION
       ""
   ::=  { reaIpFftEntry 7 }

reaIpFftPortNum OBJECT-TYPE
   SYNTAX INTEGER
   ACCESS   read-only
   STATUS mandatory
   DESCRIPTION
       ""
   ::=  { reaIpFftEntry 8 }

reaIpFftFacsSrcIndex OBJECT-TYPE
   SYNTAX INTEGER
   ACCESS   read-only
   STATUS mandatory
   DESCRIPTION
       ""
   ::=  { reaIpFftEntry 9 }

reaIpFftFacsDstIndex OBJECT-TYPE
   SYNTAX INTEGER
   ACCESS   read-only
   STATUS mandatory
   DESCRIPTION
       ""
   ::=  { reaIpFftEntry 10 }

reaIpFftApplFlags OBJECT-TYPE
   SYNTAX OCTET STRING (SIZE(4))
   ACCESS read-only
   STATUS mandatory
   DESCRIPTION
      "A bit mask that defines the applications associated with this entry:
       __________________________________________
       |  Byte 1|Byte 2 |Byte 3 | ....|Byte 20  |
       |87654321|                     | 87654321|
       |________|_______________________________|

 Byte1 :
      bit1: Server Dispatcher Client"
   ::=  { reaIpFftEntry 11 }

reaIpxFftTable OBJECT-TYPE
    SYNTAX SEQUENCE OF ReaIpxFftEntry
    ACCESS not-accessible
    STATUS mandatory
    DESCRIPTION
      "The IPX Fast Forwarding Table"
    ::=  { reaTunning 16 }

reaIpxFftEntry  OBJECT-TYPE
   SYNTAX ReaIpxFftEntry
   ACCESS not-accessible
   STATUS mandatory
   DESCRIPTION
       " The row definition for this table."
   INDEX { reaIpxFftEntryNum }
   ::= { reaIpxFftTable 1 }

ReaIpxFftEntry ::= SEQUENCE {
        reaIpxFftEntryNum             INTEGER,
        reaIpxFftDstNetid             INTEGER,
        reaIpxFftRangeType            INTEGER,
        reaIpxFftSrcMacAddr           PhysAddress,
        reaIpxFftDstMacAddr           PhysAddress,
        reaIpxFftReNum                INTEGER,        -- 1..N
        reaIpxFftPortNum              INTEGER,        -- 1..N
        reaIpxFftFacsSrcIndex         INTEGER,
        reaIpxFftFacsDstIndex         INTEGER
   }

reaIpxFftEntryNum OBJECT-TYPE
   SYNTAX INTEGER
   ACCESS   read-only
   STATUS mandatory
   DESCRIPTION
       ""
   ::=  { reaIpxFftEntry 1 }

reaIpxFftDstNetid OBJECT-TYPE
   SYNTAX INTEGER
   ACCESS   read-only
   STATUS mandatory
   DESCRIPTION
       ""
   ::=  { reaIpxFftEntry 2 }

reaIpxFftRangeType OBJECT-TYPE
   SYNTAX INTEGER {
        direct (1),
        remote (2)
   }
   ACCESS   read-only
   STATUS mandatory
   DESCRIPTION
       ""
   ::=  { reaIpxFftEntry 3 }

reaIpxFftSrcMacAddr OBJECT-TYPE
   SYNTAX PhysAddress
   ACCESS   read-only
   STATUS mandatory
   DESCRIPTION
       ""
   ::=  { reaIpxFftEntry 4 }

reaIpxFftDstMacAddr OBJECT-TYPE
   SYNTAX PhysAddress
   ACCESS   read-only
   STATUS mandatory
   DESCRIPTION
       ""
   ::=  { reaIpxFftEntry 5 }

reaIpxFftReNum OBJECT-TYPE
   SYNTAX INTEGER
   ACCESS   read-only
   STATUS mandatory
   DESCRIPTION
       ""
   ::=  { reaIpxFftEntry 6 }

reaIpxFftPortNum OBJECT-TYPE
   SYNTAX INTEGER
   ACCESS   read-only
   STATUS mandatory
   DESCRIPTION
       ""
   ::=  { reaIpxFftEntry 7 }

reaIpxFftFacsSrcIndex OBJECT-TYPE
   SYNTAX INTEGER
   ACCESS   read-only
   STATUS mandatory
   DESCRIPTION
       ""
   ::=  { reaIpxFftEntry 8 }

reaIpxFftFacsDstIndex OBJECT-TYPE
   SYNTAX INTEGER
   ACCESS   read-only
   STATUS mandatory
   DESCRIPTION
       ""
   ::=  { reaIpxFftEntry 9 }

lreVnResposibilityTable OBJECT-TYPE
    SYNTAX SEQUENCE OF LreVnResposibilityEntry
    ACCESS not-accessible
    STATUS mandatory
    DESCRIPTION
      "The Bridge Responsibility Table"
    ::=  { reaTunning 17 }

lreVnResposibilityEntry  OBJECT-TYPE
   SYNTAX LreVnResposibilityEntry
   ACCESS not-accessible
   STATUS mandatory
   DESCRIPTION
       " The row definition for this table."
   INDEX { lreVnRespVn }
   ::= { lreVnResposibilityTable 1 }

LreVnResposibilityEntry ::= SEQUENCE {
        lreVnRespVn             INTEGER,
        lreVnRespStatus         RowStatus
   }

lreVnRespVn OBJECT-TYPE
   SYNTAX INTEGER
   ACCESS   read-write
   STATUS mandatory
   DESCRIPTION
       ""
   ::=  { lreVnResposibilityEntry 1 }

lreVnRespStatus OBJECT-TYPE
   SYNTAX RowStatus
   ACCESS read-write
   STATUS mandatory
   DESCRIPTION
       ""
   ::=  { lreVnResposibilityEntry 2 }

reaSrcViolationEnable OBJECT-TYPE
    SYNTAX INTEGER {
        enable  (1),
        disable (2)
    }
    ACCESS  read-write
    STATUS  mandatory
    DESCRIPTION
      "The Platform will perform the Source Port Violation Procedure
       if only if this variable's value is enable."
    ::=  { reaTunning 18 }

reaSrcViolationTrapEnable OBJECT-TYPE
    SYNTAX INTEGER {
        enable  (1),
        disable (2)
    }
    ACCESS  read-write
    STATUS  mandatory
    DESCRIPTION
      "The RS will send the Source Port Violation TRAP messages
       if only if this variable's value is enable."
    ::=  { reaTunning 19 }

reaSrcAddrValidationEnable OBJECT-TYPE
    SYNTAX INTEGER {
        enable  (1),
        disable (2)
    }
    ACCESS  read-write
    STATUS  mandatory
    DESCRIPTION
      "The Platform will verify the source address of incoming
       IP datagram."
    ::=  { reaTunning 20 }

reaRsQueueDiscards OBJECT-TYPE
    SYNTAX Counter
    ACCESS read-only
    STATUS mandatory
    DESCRIPTION
      ""
    ::=  { reaTunning 21 }

reaBufFree OBJECT-TYPE
    SYNTAX  INTEGER
    ACCESS  read-only
    STATUS  mandatory
    DESCRIPTION
      "The number of free buffers."
    ::=  { reaTunning 22 }

lreResetDstMacBit46 OBJECT-TYPE
    SYNTAX  INTEGER {
      enable(1),
      disable(2)
   }
    ACCESS  read-write
    STATUS  mandatory
    DESCRIPTION
      ""
    ::=  { reaTunning 23 }

lreQueSourceSelect OBJECT-TYPE
    SYNTAX  INTEGER {
      vNET(1),
      dstMac(2)
   }
    ACCESS  read-write
    STATUS  mandatory
    DESCRIPTION
      ""
    ::=  { reaTunning 24 }

lreResetDstMacBit47 OBJECT-TYPE
    SYNTAX  INTEGER {
      enable(1),
      disable(2)
   }
    ACCESS  read-write
    STATUS  mandatory
    DESCRIPTION
      ""
    ::=  { reaTunning 25 }

rsMaxEntriesTuning OBJECT IDENTIFIER ::= { rsTunning 8 }

rsMaxBridgeForwardingEntriesTuning OBJECT IDENTIFIER ::= { rsMaxEntriesTuning 1}

rsMaxBrgFrwEntries OBJECT-TYPE
    SYNTAX INTEGER
    ACCESS  read-only
    STATUS  mandatory
    DESCRIPTION
      "Maximal number of entries in bridge forwarding table."
    ::=  { rsMaxBridgeForwardingEntriesTuning 1 }

rsMaxBrgFrwEntriesAfterReset OBJECT-TYPE
    SYNTAX INTEGER
    ACCESS  read-write
    STATUS  mandatory
    DESCRIPTION
      "Future maximal number of entries in bridge forwarding table."
    ::=  { rsMaxBridgeForwardingEntriesTuning 2 }

rsMaxIpForwardingEntriesTuning OBJECT IDENTIFIER ::= { rsMaxEntriesTuning 2}

rsMaxIpFrwEntries OBJECT-TYPE
    SYNTAX INTEGER
    ACCESS  read-only
    STATUS  mandatory
    DESCRIPTION
      "Maximal number of entries in Ip forwarding table."
    ::=  { rsMaxIpForwardingEntriesTuning 1 }

rsMaxIpFrwEntriesAfterReset OBJECT-TYPE
    SYNTAX INTEGER
    ACCESS  read-write
    STATUS  mandatory
    DESCRIPTION
      "Future maximal number of entries in Ip forwarding table."
    ::=  { rsMaxIpForwardingEntriesTuning 2 }

rsMaxArpEntriesTuning OBJECT IDENTIFIER ::= { rsMaxEntriesTuning 3}

rsMaxArpEntries OBJECT-TYPE
    SYNTAX INTEGER
    ACCESS  read-only
    STATUS  mandatory
    DESCRIPTION
      "Maximal number of entries in Arp forwarding table."
    ::=  { rsMaxArpEntriesTuning 1 }

rsMaxArpEntriesAfterReset OBJECT-TYPE
    SYNTAX INTEGER
    ACCESS  read-write
    STATUS  mandatory
    DESCRIPTION
      "Future maximal number of entries in Arp forwarding table."
    ::=  { rsMaxArpEntriesTuning 2 }

rsMaxIpxForwardingEntriesTuning OBJECT IDENTIFIER ::= { rsMaxEntriesTuning 4}

rsMaxIpxFrwEntries OBJECT-TYPE
    SYNTAX INTEGER
    ACCESS  read-only
    STATUS  mandatory
    DESCRIPTION
      "Maximal number of entries in Ipx forwarding table."
    ::=  { rsMaxIpxForwardingEntriesTuning 1 }

rsMaxIpxFrwEntriesAfterReset OBJECT-TYPE
    SYNTAX INTEGER
    ACCESS  read-write
    STATUS  mandatory
    DESCRIPTION
      "Future maximal number of entries in Ipx forwarding table."
    ::=  { rsMaxIpxForwardingEntriesTuning 2 }

rsMaxIpxSapEntriesTuning OBJECT IDENTIFIER ::= { rsMaxEntriesTuning 5}

rsMaxIpxSapEntries OBJECT-TYPE
    SYNTAX INTEGER
    ACCESS  read-only
    STATUS  mandatory
    DESCRIPTION
      "Maximal number of entries in IpxSap table."
    ::=  { rsMaxIpxSapEntriesTuning 1 }

rsMaxIpxSapEntriesAfterReset OBJECT-TYPE
    SYNTAX INTEGER
    ACCESS  read-write
    STATUS  mandatory
    DESCRIPTION
      "Future maximal number of entries in IpxSap table."
    ::=  { rsMaxIpxSapEntriesTuning 2 }

rsMaxDspClntEntriesTuning OBJECT IDENTIFIER ::= { rsMaxEntriesTuning 6}

rsMaxDspClntEntries OBJECT-TYPE
    SYNTAX INTEGER
    ACCESS  read-only
    STATUS  mandatory
    DESCRIPTION
      "Maximal number of entries in rsSdClientsTable."
    ::=  { rsMaxDspClntEntriesTuning 1 }

rsMaxDspClntEntriesAfterReset OBJECT-TYPE
    SYNTAX INTEGER
    ACCESS  read-write
    STATUS  mandatory
    DESCRIPTION
      "Future maximal number of entries in rsSdClientsTable."
    ::=  { rsMaxDspClntEntriesTuning 2 }

rsMaxZeroHopRoutEntriesTuning OBJECT IDENTIFIER ::= { rsMaxEntriesTuning 7}

rsMaxZhrConns OBJECT-TYPE
    SYNTAX INTEGER
    ACCESS  read-only
    STATUS  mandatory
    DESCRIPTION
      "The current maximal number of direct Zero-hop routing
       connections."
    ::= { rsMaxZeroHopRoutEntriesTuning 1 }

rsMaxZhrConnsAfterReset OBJECT-TYPE
    SYNTAX INTEGER
    ACCESS  read-write
    STATUS  mandatory
    DESCRIPTION
      "The future (after reset) maximal number of direct Zero-hop routing
       connections."
    ::= { rsMaxZeroHopRoutEntriesTuning 2 }

rsMaxDspFrmEntriesTuning OBJECT IDENTIFIER ::= { rsMaxEntriesTuning 8}

rsMaxDspFrmEntries OBJECT-TYPE
    SYNTAX INTEGER
    ACCESS  read-only
    STATUS  mandatory
    DESCRIPTION
      "Maximal number of entries in rsSdClientsTable."
    ::=  { rsMaxDspFrmEntriesTuning 1 }

rsMaxDspFrmEntriesAfterReset OBJECT-TYPE
    SYNTAX INTEGER
    ACCESS  read-write
    STATUS  mandatory
    DESCRIPTION
      "Future maximal number of entries in rsSdClientsTable."
    ::=  { rsMaxDspFrmEntriesTuning 2 }

rsMaxRoutingEntriesTuning OBJECT IDENTIFIER ::= { rsMaxEntriesTuning 9}

rsMaxRoutingEntries OBJECT-TYPE
    SYNTAX INTEGER
    ACCESS  read-only
    STATUS  mandatory
    DESCRIPTION
      "Maximal number of entries in the routing table."
    ::=  { rsMaxRoutingEntriesTuning 1 }

rsMaxRoutingEntriesAfterReset OBJECT-TYPE
    SYNTAX INTEGER
    ACCESS  read-write
    STATUS  mandatory
    DESCRIPTION
      "Future maximal number of entries in the routing table."
    ::=  { rsMaxRoutingEntriesTuning 2 }

rndApplications  OBJECT IDENTIFIER ::= { rnd 35 }
rsServerDispatcher  OBJECT IDENTIFIER ::= { rndApplications 1}


-- rndMidLevelManagement group contains variables which direct the mid-level
-- management stations how to monitor and manage their domains.

rndMidLevelManagement  OBJECT IDENTIFIER ::= { rndApplications 2} -- NEW Group

-- rndHighLevelNms  OBJECT IDENTIFIER ::= { rndMidLevelManagement 1}

-- rndHighLevelNmsIpAddress OBJECT-TYPE
--    SYNTAX IpAddress
--    ACCESS read-write
--    STATUS mandatory
--    DESCRIPTION
--     "The IP address of the high-level network management station to which the
--      mid-level management station should report"
--      ::=  { rndHighLevelNms 1 }

-- rndHighLevelNmsCommunity OBJECT-TYPE
--    SYNTAX OCTET STRING(SIZE(1..20))
--    ACCESS read-write
--    STATUS mandatory
--    DESCRIPTION
--     "The community of the high-level network management station that should be used
--      by the mid-level management station when reporting"
--  ::=  { rndHighLevelNms 2 }

rndAlarmOptions  OBJECT IDENTIFIER ::= { rndMidLevelManagement 2}

rndAlarmEnabling OBJECT-TYPE
    SYNTAX INTEGER {
        enabled(1),
        disabled(2)
        }
    ACCESS read-write
    STATUS mandatory
    DESCRIPTION
        "Indicates whether alarms should be issued to the high-level
         NMS "
     ::=  { rndAlarmOptions 1 }

rndAlarmInterval OBJECT-TYPE
    SYNTAX INTEGER
    ACCESS read-write
    STATUS mandatory
    DESCRIPTION
        "Indicates the minimal period of time which must pass after issuing
         an alarm before issuing the same alarm again."
     ::=  { rndAlarmOptions 2 }

rndMonitoredElementsTable  OBJECT-TYPE
   SYNTAX SEQUENCE OF RndMonitoredElementEntry
   ACCESS not-accessible
   STATUS mandatory
   DESCRIPTION
    "The table of monitored elements of the network"
    ::= {rndMidLevelManagement 3}

rndMonitoredElementEntry  OBJECT-TYPE
   SYNTAX RndMonitoredElementEntry
   ACCESS not-accessible
   STATUS mandatory
   DESCRIPTION
       " The row definition for this table."
   INDEX { rndMonitoredElementAddress }
    ::= {rndMonitoredElementsTable 1}

RndMonitoredElementEntry ::= SEQUENCE {

rndMonitoredElementAddress    IpAddress,
rndMonitoredElementCommunity  DisplayString(SIZE(1..20)),
rndMonitoredElementLabel      DisplayString(SIZE(1..20)),
rndDefaultPollingInterval     INTEGER,
rndDefaultLogFile             DisplayString,
rndMonitoredElementStatus     RowStatus
}
rndMonitoredElementAddress OBJECT-TYPE
   SYNTAX IpAddress
   ACCESS read-only
   STATUS mandatory
   DESCRIPTION
    "The IP address of the monitored element"
     ::=  {rndMonitoredElementEntry  1 }

rndMonitoredElementCommunity OBJECT-TYPE
   SYNTAX DisplayString(SIZE(1..20))
   ACCESS read-write
   STATUS mandatory
   DESCRIPTION
    "The community of the monitored element"
     ::=  {rndMonitoredElementEntry 2  }

rndMonitoredElementLabel OBJECT-TYPE
   SYNTAX DisplayString(SIZE(1..20))
   ACCESS read-write
   STATUS mandatory
   DESCRIPTION
    "The label assigned by the network manager to the monitored element"
     ::=  {rndMonitoredElementEntry 3}

rndDefaultPollingInterval OBJECT-TYPE
   SYNTAX INTEGER
   ACCESS read-write
   STATUS mandatory
   DESCRIPTION
    "The default period of time between two consecutive pollings of the
     monitored element for the value of an object instance. If no other polling
     interval is specifically assigned to the monitored object instance, this
     one will be used"
     ::=  {rndMonitoredElementEntry 4}

rndDefaultLogFile OBJECT-TYPE
   SYNTAX DisplayString
   ACCESS read-write
   STATUS mandatory
   DESCRIPTION
    "The default file path of the log-file which will contain the polling
     results for the monitored element. If no other file path is specifically
     assigned to the monitored object instance, this log-file will be used."

     ::=  {rndMonitoredElementEntry  5}

rndMonitoredElementStatus OBJECT-TYPE
   SYNTAX RowStatus
   ACCESS read-write
   STATUS mandatory
   DESCRIPTION
         "It is used to manage the monitored elements table and indicates
          the current monitoring status of an element."
     ::=  {rndMonitoredElementEntry  6}

rndMonitoringTable  OBJECT-TYPE
   SYNTAX SEQUENCE OF RndMonitoringEntry
   ACCESS not-accessible
   STATUS mandatory
   DESCRIPTION
    "The table of monitored object instances. Each monitored object instance
     belongs to a monitored element previously entered in the
     rndMonitoredElementsTable. "
    ::= {rndMidLevelManagement 4}

rndMonitoringEntry OBJECT-TYPE
   SYNTAX RndMonitoringEntry
   ACCESS not-accessible
   STATUS mandatory
   DESCRIPTION
       " The row definition for this table."
   INDEX { rndMonitoredElement, rndMonitoredObjectInstanceLabel }
    ::= {rndMonitoringTable 1}

RndMonitoringEntry ::= SEQUENCE {

rndMonitoredElement             DisplayString(SIZE(1..20)),
rndMonitoredObjectInstanceLabel DisplayString,
rndMonitoredObjectName          DisplayString,
rndMonitoredObjectIdentifier    OBJECT IDENTIFIER,
rndMonitoredObjectInstance      OBJECT IDENTIFIER,
rndMonitoredObjectSyntax        INTEGER,
rndMonitoringInterval           INTEGER,
rndAlarmMaxTreshold             INTEGER,
rndAlarmMinTreshold             INTEGER,
rndMonitoringLogfile            DisplayString,
rndMonitoringEntryStatus        RowStatus
}

rndMonitoredElement OBJECT-TYPE
   SYNTAX DisplayString(SIZE(1..20))
   ACCESS read-only
   STATUS mandatory
   DESCRIPTION
    "A label assigned by the network manager to a monitored element to
     which this monitored object instance belongs. This label must have
     been previously entered in an instance of rndMonitoredElementLabel"
    ::=  {rndMonitoringEntry  1}

rndMonitoredObjectInstanceLabel OBJECT-TYPE
   SYNTAX DisplayString(SIZE(1..20))
   ACCESS read-only
   STATUS mandatory
   DESCRIPTION
    "The label assigned by the network manager to the monitored object instance"
    ::=  {rndMonitoringEntry  2}

rndMonitoredObjectName OBJECT-TYPE
   SYNTAX DisplayString(SIZE(0..20))
   ACCESS read-write
   STATUS mandatory
   DESCRIPTION
    "The symbolic object type name of the object to which the monitored object
     instance belongs (as it appears the MIB module definition). In case of
     ambiguity the <MIB module name> : <object type name> format should be used.
     An instance of rndMonitoredObjectName need not be assigned any value, if
     the corresponding instance of rndMonitoredObjectIdentifier is assigned a
     value, since any one of these, together with the object instance
     identifier, suffices to unambigously identify the monitored object
     instance."

    ::=  {rndMonitoringEntry  3}

rndMonitoredObjectIdentifier OBJECT-TYPE
   SYNTAX OBJECT IDENTIFIER
   ACCESS read-write
   STATUS mandatory
   DESCRIPTION
    "The object identifier of the object to which the monitored object
     instance belongs.
     An instance of rndMonitoredObjectIdentifier need not be assigned any value, if
     the corresponding instance of rndMonitoredObjectName is assigned a value,
     since any one of these, together with the object instance identifier,
     suffices to unambigously identify the monitored object instance."

    ::=  {rndMonitoringEntry  4}

rndMonitoredObjectInstance OBJECT-TYPE
   SYNTAX OBJECT IDENTIFIER
   ACCESS read-write
   STATUS mandatory
   DESCRIPTION
        "The instance identifier (key) of the monitored object instance."
    ::=  {rndMonitoringEntry  5}

rndMonitoredObjectSyntax OBJECT-TYPE
   SYNTAX INTEGER {
       integer(1),
       octet-string(2),
       ip-address(3),
       object-identifier(4)
     }

   ACCESS read-write
   STATUS mandatory
   DESCRIPTION
    "The syntax of the monitored object instance (i.e., the syntax of the object
     type of the object to which the monitored instance belongs).
     Need not be assigned any value if the corresponding instance of
     rndMonitoredObjectName has been assigned a value"
    ::=  {rndMonitoringEntry  6}

rndMonitoringInterval OBJECT-TYPE
   SYNTAX INTEGER
   ACCESS read-write
   STATUS mandatory
   DESCRIPTION
    "The period of time between two consecutive retrievals of the monitored
     object instance's value."
    ::=  {rndMonitoringEntry  7}


rndAlarmMaxTreshold OBJECT-TYPE
   SYNTAX INTEGER
   ACCESS read-write
   STATUS mandatory
   DESCRIPTION
    "The value of the monitored object instance, the exceeding of which
     will cause the generation of an alarm to the high-level management
     station."
    ::=  {rndMonitoringEntry 8}

rndAlarmMinTreshold OBJECT-TYPE
   SYNTAX INTEGER
   ACCESS read-write
   STATUS mandatory
   DESCRIPTION
    "If the value of the monitored object instance falls below the value
     assigned to rndAlarmMinTreshold, an alarm to the high-level management
     station will be issued."
    ::=  {rndMonitoringEntry  9}


rndMonitoringLogfile OBJECT-TYPE
   SYNTAX DisplayString
   ACCESS read-write
   STATUS mandatory
   DESCRIPTION
    "The entire path of the file in which the results of the monitoring
     of this object instance should be recorded."
    ::=  {rndMonitoringEntry  10}

rndMonitoringEntryStatus OBJECT-TYPE
   SYNTAX RowStatus
   ACCESS read-write
   STATUS mandatory
   DESCRIPTION
         "It is used to manage the monitored object instances table and
          indicates the current monitoring status of an object instance."
    ::=  {rndMonitoringEntry  11}

rndMibFilesTable  OBJECT-TYPE
   SYNTAX SEQUENCE OF RndMibFileEntry
   ACCESS not-accessible
   STATUS mandatory
   DESCRIPTION
    "The table of monitored object instances. Each monitored object instance
     belongs to a monitored element previously entered in the
     rndMonitoredElementsTable. "
    ::= {rndMidLevelManagement 5}

rndMibFileEntry OBJECT-TYPE
   SYNTAX RndMibFileEntry
   ACCESS not-accessible
   STATUS mandatory
   DESCRIPTION
       " The row definition for this table."
   INDEX { rndMibFileIndex }
    ::= {rndMibFilesTable 1}

RndMibFileEntry ::= SEQUENCE {

rndMibFileIndex                 INTEGER,
rndMibFilePath                  DisplayString,
rndMibFileRefresh               INTEGER,
rndMibFileEntryStatus           RowStatus
}
rndMibFileIndex OBJECT-TYPE
   SYNTAX INTEGER
   ACCESS read-only
   STATUS mandatory
   DESCRIPTION
    "The number of the MIB file in the list MIB files supported by the
     Mid-Level management station. The order of the MIB files in this
     list must reflect the the IMPORT relation between the MIBS contained
     in the MIB files, i.e., if MIB A IMPORTS FROM MIB B, the file containing
     MIB A must have a lesser index in this table than the file containing
     MIB B."
    ::=  {rndMibFileEntry  1}


rndMibFilePath OBJECT-TYPE
   SYNTAX DisplayString
   ACCESS read-write
   STATUS mandatory
   DESCRIPTION
    "The path of the MIB file in the MIB file server."
    ::=  {rndMibFileEntry  2}

rndMibFileRefresh OBJECT-TYPE
   SYNTAX INTEGER {
      no(1),
      yes(2)
   }
   ACCESS read-write
   STATUS mandatory
   DESCRIPTION
    "Indicates if the file should be fetched after setting this entry from the
     MIB file server."
    ::=  {rndMibFileEntry  3}

rndMibFileEntryStatus OBJECT-TYPE
   SYNTAX RowStatus
   ACCESS read-write
   STATUS mandatory
   DESCRIPTION
         "It is used to manage the MIB files table."
    ::=  {rndMibFileEntry  4}

rndHardwareConfiguration OBJECT-TYPE
    SYNTAX TruthValue
    ACCESS read-write
    STATUS mandatory
    DESCRIPTION
        "Indicates whether the current SET SNMP PDU contains hardware
         configuration (i.e., normally read-only variables). SET of such
         variables in the Mid-level management station will be allowed only
         if this variable is included in the SNMP PDU and its value is true.
         Its value as returned in  a GET SNMP PDU will always be false."
    ::= {rndMidLevelManagement 6}

rndEraseSimulatedConfiguration OBJECT-TYPE
    SYNTAX INTEGER {
        eraseSimulatedConfiguration(1),
        simulatedConfigurationPresent(2),
        simulatedConfigurationErased(3)
        }
    ACCESS read-write
    STATUS mandatory
    DESCRIPTION
        "eraseSimulatedConfiguration instructs the MLNMS to erase all the
         simulated configuration from its configuration data-base (CDB). This
         the only accepted value for SNMP SET statements and will never be
         returned in SNMP GET statements.
         simulatedConfigurationPresent indicates that the MLNMS currently has
         a simulated configuration.
         simulatedConfigurationErased indicates that the MLNMS currently has
         no simulated configuration."
    ::= {rndMidLevelManagement 7}

rndDeleteValuesTable  OBJECT-TYPE
   SYNTAX SEQUENCE OF RndDeleteValuesEntry
   ACCESS not-accessible
   STATUS mandatory
   DESCRIPTION
    "This table indicates which MIB variables are row status fields which
     control the status of the entry to which they belong. This table also
     indicates which (integer!) value of these MIB variables will cause, if
     present in a SNMP SET PDU, the deletion of the conceptual row instance
     to which the SET MIB variable instance belongs."
    ::= {rndMidLevelManagement 8}

rndDeleteValuesEntry  OBJECT-TYPE
   SYNTAX RndDeleteValuesEntry
   ACCESS not-accessible
   STATUS mandatory
   DESCRIPTION
       " The row definition for the rndDeleteValuesTable table."
   INDEX { IMPLIED rndRowStatusVariableName }
    ::= {rndDeleteValuesTable 1}

RndDeleteValuesEntry ::= SEQUENCE {

rndRowStatusVariableName    DisplayString,
rndRowStatusObjectId        OBJECT IDENTIFIER,
rndRowDeleteValue           INTEGER,
rndDeleteValueEntryStatus   RowStatus
}

rndRowStatusVariableName OBJECT-TYPE
   SYNTAX DisplayString(SIZE(1..80))
--   ACCESS read-only
   ACCESS read-write
   STATUS mandatory
   DESCRIPTION
    "The name of the row status field. This name may not necessarily be any
     name which is present in the MIBs loaded into the MLNMS station."

     ::=  {rndDeleteValuesEntry 1}

rndRowStatusObjectId OBJECT-TYPE
   SYNTAX OBJECT IDENTIFIER
   ACCESS read-write
   STATUS mandatory
   DESCRIPTION
    "The object id of the row status field. If the rndRowStatusVariableName is
     a name present in the MIBs loaded into the MLNMS, this MIB
     variable is not required, but if given, it must match the object id known
     to the MLNMS.
     The variable identified by rndRowStatusVariableName and/or rndRowStatusObjectId
     must be a read-write MIB variable of type INTEGER which belongs to an
     entry (i.e, is a child of a MIB variable of type SEQUENCE)."

     ::=  {rndDeleteValuesEntry 2}

rndRowDeleteValue OBJECT-TYPE
   SYNTAX INTEGER
   ACCESS read-write
   STATUS mandatory
   DESCRIPTION
    "The value of the variable identified by rndRowStatusVariableName and/or
     rndRowStatusObjectId, which, if present in a SNMP SET PDU, will cause
     the deletion of the conceptual row instance which the SET MIB variable
     instance belongs."
     ::=  {rndDeleteValuesEntry 3}

rndDeleteValueEntryStatus  OBJECT-TYPE
   SYNTAX  RowStatus
   ACCESS  read-write
   STATUS  mandatory
   DESCRIPTION
         "It is used to delete an entry from this table."
     ::=  {rndDeleteValuesEntry 4}

rsIpZeroHopRouting  OBJECT IDENTIFIER ::= { rndApplications 3} -- NEW Group

rsIpZhrGeneralStatus  OBJECT-TYPE
    SYNTAX  INTEGER  {
   enable(1),
   disable(2)
}
    ACCESS  read-write
    STATUS  mandatory
    DESCRIPTION
        "This parameter enables or disables the IP Zero Hop Routing feature
         for all IP interfaces. The IP Zero Hop Routing feature can also be
         enabled or disabled on each IP interface through the
         rsIpZhrStatusTable."
    DEFVAL  {2}
    ::= { rsIpZeroHopRouting 1 }

rsIpZhrAgingTimeout   OBJECT-TYPE
    SYNTAX  INTEGER
    ACCESS  read-write
    STATUS  mandatory
    DESCRIPTION
        "This parameter controls the aging time-out in seconds of direct
         connections which were allocated. The virtual IP address of a direct
         connection whose time-out has expired is eligible for allocation to a
         different connection."
    DEFVAL  {600}
    ::= { rsIpZeroHopRouting 2 }

rsIpZhrStatusTable OBJECT-TYPE
SYNTAX SEQUENCE OF RsIpZhrStatusEntry
ACCESS  not-accessible
STATUS  mandatory
DESCRIPTION
      "The administrative status of the ZHR feature per ip interface."
::= { rsIpZeroHopRouting 3 }


rsIpZhrStatusEntry  OBJECT-TYPE
SYNTAX    RsIpZhrStatusEntry
ACCESS    not-accessible
STATUS    mandatory
DESCRIPTION
      " An entry in the ZHR status table.  "
INDEX  { rsIpZhrStatusIpIntf}
::= { rsIpZhrStatusTable 1 }


RsIpZhrStatusEntry  ::= SEQUENCE {
      rsIpZhrStatusIpIntf                    IpAddress,
      rsIpZhrAdminStatus                     INTEGER
}


rsIpZhrStatusIpIntf       OBJECT-TYPE
SYNTAX IpAddress
ACCESS  read-only
STATUS  mandatory
DESCRIPTION
   " The Ip interface whose ZHR feature status is accessed. "
::= {rsIpZhrStatusEntry  1}

 rsIpZhrAdminStatus OBJECT-TYPE
 SYNTAX INTEGER {
    enable (1),
    disable(2)
}
ACCESS read-write
STATUS mandatory
DESCRIPTION
         "It is used to control whether ZHR will operate on the interface. "
DEFVAL {1}
::=  {rsIpZhrStatusEntry  2}


rsIpZhrVirtAddressTable OBJECT-TYPE
SYNTAX SEQUENCE OF RsIpZhrVirtAddressEntry
ACCESS  not-accessible
STATUS  mandatory
DESCRIPTION
      "The table of free virtual IP addresses which may be allocated
       to establish direct connections   -  Per IP Interface."
::= { rsIpZeroHopRouting 4 }

rsIpZhrVirtAddressEntry  OBJECT-TYPE
SYNTAX    RsIpZhrVirtAddressEntry
ACCESS    not-accessible
STATUS    mandatory
DESCRIPTION
      " An entry in the ZHR virtual IP addresses table "
INDEX  { rsIpZhrVirtAddressIpIntf,
         rsIpZhrVirtAddressTo }
::= { rsIpZhrVirtAddressTable 1 }

RsIpZhrVirtAddressEntry  ::= SEQUENCE {
      rsIpZhrVirtAddressIpIntf         IpAddress,
      rsIpZhrVirtAddressTo             IpAddress,
      rsIpZhrVirtAddressFrom           IpAddress,
      rsIpZhrVirtAddressStatus         RowStatus
}

rsIpZhrVirtAddressIpIntf OBJECT-TYPE
SYNTAX IpAddress
ACCESS  read-only
STATUS  mandatory
DESCRIPTION
   " The Ip Interface to which the IP addresses in this entry are allocated."
::= {rsIpZhrVirtAddressEntry  1}

rsIpZhrVirtAddressTo OBJECT-TYPE
SYNTAX IpAddress
ACCESS  read-only
STATUS  mandatory
DESCRIPTION
   " The last free IP address in the block. "
::= {rsIpZhrVirtAddressEntry  2}

rsIpZhrVirtAddressFrom OBJECT-TYPE
SYNTAX IpAddress
ACCESS  read-write
STATUS  mandatory
DESCRIPTION
   " The first free IP address in the block. "
::= {rsIpZhrVirtAddressEntry  3}

 rsIpZhrVirtAddressStatus OBJECT-TYPE
 SYNTAX RowStatus
ACCESS read-write
STATUS mandatory
DESCRIPTION
         "It is used to manage the virtual address table.
          The supported actions will be active, createAndGo and destroy. "
::=  {rsIpZhrVirtAddressEntry  4}

rsIpZhrConnectionsTable OBJECT-TYPE
SYNTAX SEQUENCE OF RsIpZhrConnectionEntry
ACCESS  not-accessible
STATUS  mandatory
DESCRIPTION
   "Table of the currently active direct connections."
::= { rsIpZeroHopRouting 5}

rsIpZhrConnectionEntry  OBJECT-TYPE
SYNTAX RsIpZhrConnectionEntry
ACCESS not-accessible
STATUS mandatory
DESCRIPTION
   " An entry in the ZHR Connection table"
INDEX  {rsIpZhrConnectionIpIntf,
        rsIpZhrConnectionSrcIp,
        rsIpZhrConnectionDestIp}
::= { rsIpZhrConnectionsTable 1 }

RsIpZhrConnectionEntry  ::= SEQUENCE {
      rsIpZhrConnectionIpIntf          IpAddress,
      rsIpZhrConnectionSrcIp           IpAddress,
      rsIpZhrConnectionDestIp          IpAddress,
      rsIpZhrConnectionVirtualIp       IpAddress,
      rsIpZhrConnectionType            INTEGER,
      rsIpZhrConnectionAge             INTEGER,
      rsIpZhrConnectionStatus          RowStatus
}

rsIpZhrConnectionIpIntf  OBJECT-TYPE
SYNTAX IpAddress
ACCESS  read-only
STATUS  mandatory
DESCRIPTION
   " The IP Interface for which this direct connection was established. "
::= {rsIpZhrConnectionEntry 1}

rsIpZhrConnectionSrcIp   OBJECT-TYPE
SYNTAX IpAddress
ACCESS  read-only
STATUS  mandatory
DESCRIPTION
   " The source IP Address of this direct connection. "
::= {rsIpZhrConnectionEntry 2}


rsIpZhrConnectionDestIp  OBJECT-TYPE
SYNTAX IpAddress
ACCESS  read-only
STATUS  mandatory
DESCRIPTION
   " The destination IP Address of this direct connection. "
::= {rsIpZhrConnectionEntry 3}

rsIpZhrConnectionVirtualIp OBJECT-TYPE
SYNTAX IpAddress
ACCESS  read-only
STATUS  mandatory
DESCRIPTION
   " The virtual IP address allocated for this direct connection. "
::= {rsIpZhrConnectionEntry 4}


rsIpZhrConnectionType   OBJECT-TYPE
SYNTAX INTEGER  {
   static(1),
   dynamic(2),
   disabled(3)
    }
ACCESS  read-only
STATUS  mandatory
DESCRIPTION
   " The type of this direct connection.
     dynamic  - established by the RS.
     disabled - established by the RS.
                The RS detected that the virtual address is already used as
                destination by the source BEFORE its allocation, and therefore
                marked this connection as 'disabled' to prevent a future
                allocation of this virtual address to this source.
     static   - established by user."
 ::= {rsIpZhrConnectionEntry 5}

rsIpZhrConnectionAge   OBJECT-TYPE
SYNTAX INTEGER
ACCESS  read-only
STATUS  mandatory
DESCRIPTION
   " The age of the connection in seconds."
::= {rsIpZhrConnectionEntry 6}

rsIpZhrConnectionStatus OBJECT-TYPE
 SYNTAX RowStatus
ACCESS read-write
STATUS mandatory
DESCRIPTION
         "It is used to manage the connections table.
          The supported actions will be active, createAndGo and destroy. "
::=  {rsIpZhrConnectionEntry  7}


-- Enterprise-specific traps for RND
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rnd
--       VARIABLES   { rndErrorDesc, rndErrorSeverity }
--       DESCRIPTION
--             ""
--       ::=
-- -------------

routeTableOverflow TRAP-TYPE
       ENTERPRISE  rnd
       VARIABLES   { rndErrorDesc, rndErrorSeverity }
       DESCRIPTION
             "An overflow condition has occurred in the Routing Table. The Routing
              Table is used for IP routing algorithm (RIP)."
       ::= 5

resetRequired TRAP-TYPE
       ENTERPRISE  rnd
       VARIABLES   { rndErrorDesc, rndErrorSeverity }
       DESCRIPTION
             "This trap indicates that in order to perform the last SET request, a reset operation
              of the router/bridge is required. This occurs when the layer 2 routing algorithm is
              changed between SPF and Spanning Tree. The reset can be performed manually or
              using the variable rndAction."
       ::=  10

endTftp  TRAP-TYPE
       ENTERPRISE  rnd
       VARIABLES   { rndErrorDesc, rndErrorSeverity }
       DESCRIPTION
             "This trap indicates that in the device finished a TFTP
             transaction with the management station.
             variable rndErrorDesc and rndErrorSeverity provides the actual message
             text and severity respectively."
       ::= 12

abortTftp TRAP-TYPE
       ENTERPRISE  rnd
       VARIABLES   { rndErrorDesc, rndErrorSeverity }
       DESCRIPTION
             "This trap indicates that in the device aborted a TFTP session with the management station.
              variable rndErrorDesc  and rndErrorSeverity  provides the actual  message text  and
              severity  respectively."
       ::= 13

startTftp TRAP-TYPE
       ENTERPRISE  rnd
       VARIABLES   { rndErrorDesc, rndErrorSeverity }
       DESCRIPTION
             "Informational trap indicating that the device has intiated a
             TFTP session. rndErrorDesc will contain the file type in
             question"
       ::=  14

ipxRipTblOverflow    TRAP-TYPE
       ENTERPRISE  rnd
       VARIABLES   { rndErrorDesc, rndErrorSeverity }
       DESCRIPTION
             "This trap indicates that in an OpenGate IPX RIP table overflow.
             The bound variable rndErrorDesc, rndErrorSeverity
             provides the actual  message text and severity respectively."
       ::=  36

ipxSapTblOverflow  TRAP-TYPE
       ENTERPRISE  rnd
       VARIABLES   { rndErrorDesc, rndErrorSeverity }
       DESCRIPTION
             "This trap indicates that in an OpenGate IPX SAP table overflow.
             The bound variable rndErrorDesc, rndErrorSeverity
             provides the actual  message text and severity respectively."
       ::= 37

 facsAccessVoilation TRAP-TYPE
       ENTERPRISE  rnd
       VARIABLES   { rndErrorDesc, rndErrorSeverity }
       DESCRIPTION
           "This trap indicates that message that fits FACS statenebt with operation
            blockAndReport was forward to the interface.The bound variable rndErrorDesc,
               rndErrorSeverity(== info ) and interface Number."
           ::= 49

 autoConfigurationCompleted TRAP-TYPE
       ENTERPRISE  rnd
       VARIABLES   { rndErrorDesc, rndErrorSeverity }
       DESCRIPTION
         "This trap indicates that auto comfiguration completetd succssefully.
           The bound variable rndErrorDesc, rndErrorSeverity(== info )"
           ::= 50

 forwardingTabOverflow  TRAP-TYPE
       ENTERPRISE  rnd
       VARIABLES   { rndErrorDesc, rndErrorSeverity }
       DESCRIPTION
         "This trap indicates that an overflow condition has occurred in the
           layer II Forward Table.
           The bound variable rndErrorDesc, rndErrorSeverity(== warning )"
           ::= 51

errorsDuringInit  TRAP-TYPE
       ENTERPRISE  rnd
       VARIABLES   { rndErrorDesc, rndErrorSeverity }
       DESCRIPTION
             ""
       ::=  61

vlanDynPortAdded  TRAP-TYPE
       ENTERPRISE  rnd
       VARIABLES   { rndErrorDesc, rndErrorSeverity }
       DESCRIPTION
             ""
       ::=  66

vlanDynPortRemoved  TRAP-TYPE
       ENTERPRISE  rnd
       VARIABLES   { rndErrorDesc, rndErrorSeverity }
       DESCRIPTION
             ""
       ::=  67

rsSDclientsTableOverflow  TRAP-TYPE
       ENTERPRISE  rnd
       VARIABLES   { rndErrorDesc, rndErrorSeverity }
       DESCRIPTION
             "This warning is generated when an overflow occurs in the clients table."
       ::=  68

rsSDinactiveServer  TRAP-TYPE
       ENTERPRISE  rnd
       VARIABLES   { rndErrorDesc, rndErrorSeverity }
       DESCRIPTION
             "This warning is generated when a server does not respond to the dispatchers polling
              and is thought to be inactive."
       ::=  69

rsIpZhrConnectionsTableOverflow TRAP-TYPE
       ENTERPRISE  rnd
       VARIABLES   { rndErrorDesc, rndErrorSeverity }
       DESCRIPTION
             "The Zero Hop Routing connections Table has been overflown."
       ::= 70

rsIpZhrReqStaticConnNotAccepted TRAP-TYPE
       ENTERPRISE  rnd
       VARIABLES   { rndErrorDesc, rndErrorSeverity }
       DESCRIPTION
             "The requested static connection was not accepted because there is
              no available IP virtual address to allocate to it."
       ::= 71

rsIpZhrVirtualIpAsSource TRAP-TYPE
       ENTERPRISE  rnd
       VARIABLES   { rndErrorDesc, rndErrorSeverity }
       DESCRIPTION
             "The virtual IP address appeared as a source IP.
              All the connections using it will be deleted and
              it will not be further allocated to new connections."
       ::=  72

rsIpZhrNotAllocVirtualIp TRAP-TYPE
       ENTERPRISE  rnd
       VARIABLES   { rndErrorDesc, rndErrorSeverity }
       DESCRIPTION
             "The source IP address sent an ARP specifying a virtual IP
              which was not allocated for this source.
              This virtual IP will not be allocated to connections of this
              specific source IP."
       ::= 73

rsSnmpSetRequestInSpecialCfgState TRAP-TYPE
       ENTERPRISE  rnd
       VARIABLES   { rndErrorDesc, rndErrorSeverity }
       DESCRIPTION
             "An incoming SNMP SET request was rejected because no such
              requests (except action requests) are accepted after start of
              new configuration reception or during sending the current
              configuration to an NMS."
       ::= 74

rsWSDRedundancySwitch TRAP-TYPE
  ENTERPRISE rnd
  VARIABLES   { rndErrorDesc, rndErrorSeverity }
  DESCRIPTION "Whenever main server fails and backup takes over or server comes
               up after failure a trap of this type is issued."
     ::= 141

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsWSDServerStatTable OBJECT-TYPE
   SYNTAX SEQUENCE OF RsWSDServerStatEntry
   ACCESS not-accessible
   STATUS mandatory
   DESCRIPTION
          "In this table the WSD collects statistics per servers."
   ::= {rsServerDispatcher 12}

rsWSDServerStatEntry OBJECT-TYPE
    SYNTAX RsWSDServerStatEntry
    ACCESS not-accessible
    STATUS  mandatory
    DESCRIPTION
       " The row definition for this table."
   INDEX  {rsWSDSerStatName}
   ::= {rsWSDServerStatTable 1}

RsWSDServerStatEntry  ::= SEQUENCE {
  rsWSDSerStatName                     DisplayString,
  rsWSDSerStatAttUsersNum              INTEGER,
  rsWSDSerStatPeakLoad                 INTEGER,
  rsWSDSerStatFramesRate               INTEGER,
  rsWSDSerStatFramesLoad               Counter,
  rsWSDSerStatRecoveryTime             INTEGER,
  rsWSDSerStatWarmUpTime               INTEGER,
  rsWSDSerStatConnectionLimit          INTEGER,
  rsWSDSerStatAdminStatus              INTEGER,
  rsWSDSerStatConnectionLimitReached   INTEGER
  }

rsWSDSerStatName OBJECT-TYPE
    SYNTAX DisplayString (SIZE(1..30))
    ACCESS  read-only
    STATUS  mandatory
    DESCRIPTION
    "This variable indicate the name assigned by the user to the serve."
    ::= {rsWSDServerStatEntry 1}

rsWSDSerStatAttUsersNum OBJECT-TYPE
    SYNTAX INTEGER
    ACCESS  read-only
    STATUS  mandatory
    DESCRIPTION
      "The total number of currently active users attached to this server."
   ::= {rsWSDServerStatEntry 2}

rsWSDSerStatPeakLoad OBJECT-TYPE
    SYNTAX INTEGER
    ACCESS  read-only
    STATUS  mandatory
    DESCRIPTION
      "Maximal number of frames per second dispatched to server
       since last reset."
   ::= {rsWSDServerStatEntry 3}

rsWSDSerStatFramesRate OBJECT-TYPE
    SYNTAX INTEGER
    ACCESS  read-only
    STATUS  mandatory
    DESCRIPTION
     "Number of frames per second dispatched to server."
   ::= {rsWSDServerStatEntry 4}

rsWSDSerStatFramesLoad OBJECT-TYPE
    SYNTAX Counter
    ACCESS  read-only
    STATUS  mandatory
    DESCRIPTION
      "Number of frames per second dispatched to server."
   ::= {rsWSDServerStatEntry 5}

rsWSDSerStatRecoveryTime OBJECT-TYPE
    SYNTAX INTEGER
    ACCESS  read-write
    STATUS  mandatory
    DESCRIPTION
      "Number of seconds after server initialization during which ISD won't
       send any requests."
   ::= {rsWSDServerStatEntry 6}

rsWSDSerStatWarmUpTime OBJECT-TYPE
    SYNTAX INTEGER
    ACCESS  read-write
    STATUS  mandatory
    DESCRIPTION
      "Number of seconds after server recovery during which the server will get
       less requests than permitted by his weight and load."
   ::= {rsWSDServerStatEntry 7}

rsWSDSerStatConnectionLimit OBJECT-TYPE
    SYNTAX INTEGER
    ACCESS  read-write
    STATUS  mandatory
    DESCRIPTION
      "The maximal number of client sessions which can be opened on this sever."
-- DEFVAL {0}
   ::= {rsWSDServerStatEntry 8}

   rsWSDSerStatAdminStatus  OBJECT-TYPE
    SYNTAX INTEGER {
            enable(1),
            shutdown(2)
    }
    ACCESS  read-write
    STATUS  mandatory
    DESCRIPTION
    "Enable / Shutdown all the applications on this physical server."
    DEFVAL {1}
    ::=  { rsWSDServerStatEntry  9}

   rsWSDSerStatConnectionLimitReached  OBJECT-TYPE
    SYNTAX  INTEGER
    ACCESS  read-only
    STATUS  mandatory
    DESCRIPTION
    "Connection limit reached flag."
    ::=  { rsWSDServerStatEntry  10}

rsWSDdummy2 OBJECT-TYPE
    SYNTAX INTEGER
    ACCESS  read-only
    STATUS  mandatory
    DESCRIPTION
       " Dummy variable for stopping getnext."
    ::=  {rsWSDServerStatTable 2}

wsdRedundTable OBJECT-TYPE
   SYNTAX SEQUENCE OF WsdRedundEntry
   ACCESS not-accessible
   STATUS mandatory
   DESCRIPTION
      "List of Farm IP addresses backed up by this router."
   ::= {rsServerDispatcher 16}

wsdRedundEntry  OBJECT-TYPE
   SYNTAX WsdRedundEntry
   ACCESS not-accessible
   STATUS mandatory
   DESCRIPTION
      "The row definition for this table."
   INDEX {wsdRedundFarmAddr, wsdRedundMainWsdAddr}
   ::= {wsdRedundTable  1 }

WsdRedundEntry ::= SEQUENCE {
   wsdRedundFarmAddr          IpAddress,
   wsdRedundMainWsdAddr   IpAddress,
   wsdRedundOperStatus         INTEGER,
   wsdRedundPollInterval        INTEGER,
   wsdRedundTimeout             INTEGER,
   wsdRedundStatus                 INTEGER
   }

wsdRedundFarmAddr OBJECT-TYPE
   SYNTAX IpAddress
   ACCESS read-only
   STATUS mandatory
   DESCRIPTION
      "The Farm Virtual Ip address on which the redundancy feature operates."
   ::=  { wsdRedundEntry  1}

wsdRedundMainWsdAddr OBJECT-TYPE
   SYNTAX IpAddress
   ACCESS read-only
   STATUS mandatory
   DESCRIPTION
      "The Ip address of the polled main wsd."
   ::=  { wsdRedundEntry 2}

wsdRedundOperStatus OBJECT-TYPE
   SYNTAX INTEGER { active(1), inactive(2) }
   ACCESS read-only
   STATUS mandatory
   DESCRIPTION
      "If active, the main wsd is considered inactive and the IP interface operates as its backup."
   ::=  { wsdRedundEntry 3 }

wsdRedundPollInterval OBJECT-TYPE
   SYNTAX INTEGER
   ACCESS read-write
   STATUS mandatory
   DESCRIPTION
      "Polling interval for the main wsd (in seconds). If 0 the wsd is not
       polled."
-- DEFVAL  { 3 }
   ::=  { wsdRedundEntry 4 }

wsdRedundTimeout OBJECT-TYPE
   SYNTAX INTEGER
   ACCESS read-write
   STATUS mandatory
   DESCRIPTION
      "Interval in seconds during which the backed-up wsd must signal.
       If it does not signal, it is considered inactive and the IP
       interface starts operating as backup."
-- DEFVAL  { 12 }
   ::=  { wsdRedundEntry  5}

wsdRedundStatus OBJECT-TYPE
   SYNTAX INTEGER {
                   active(1),
                   notInService(2),
                   notReady(3),
                   createAndGo(4),
                   createAndWait(5),
                   destroy(6)
                  }
   ACCESS read-write
   STATUS mandatory
   DESCRIPTION
      "Entry status"
   ::=  { wsdRedundEntry 6}

rsWSDdummy5 OBJECT-TYPE
    SYNTAX INTEGER
    ACCESS  read-only
    STATUS  mandatory
    DESCRIPTION
       " Dummy variable for stopping getnext."
    ::=  {wsdRedundTable 2}

rsWSDNewEntryOnSourcePort OBJECT-TYPE
    SYNTAX INTEGER {
      enable(1),
      disable(2)
   }
    ACCESS  read-write
    STATUS  mandatory
    DESCRIPTION
      "Check source port and if different open new client entry."
-- DEFVAL  { disable }
    ::=  {rsServerDispatcher 19}

rsWSDSelectServerOnSourcePort OBJECT-TYPE
    SYNTAX INTEGER {
      enable(1),
      disable(2)
   }
    ACCESS  read-write
    STATUS  mandatory
    DESCRIPTION
      "Check source port and if different select a new server."
-- DEFVAL  { disable }
    ::=  {rsServerDispatcher 20}

rsWSDRedundancyMode OBJECT-TYPE
    SYNTAX INTEGER {
        enable(1),
        disable(2)
    }
    ACCESS  read-write
    STATUS  mandatory
    DESCRIPTION
        "Dose some WSD backup me."
--  DEFVAL { disable }
    ::=  { rsServerDispatcher 21}

rsNsdMode OBJECT-TYPE
    SYNTAX INTEGER {
        slowMode(1),
        fastMode(2)
    }
    ACCESS  read-write
    STATUS  mandatory
    DESCRIPTION
        "The Topology chosen for the NSD.
         Slow mode keeps the servers behind the NSD.
         Fast mode uses retargeting to connect clients directly
         to servers."
--  DEFVAL  {1}
    ::=  {rsServerDispatcher 22}

rsNsdWINSAddr OBJECT-TYPE
    SYNTAX IpAddress
    ACCESS  read-write
    STATUS  mandatory
    DESCRIPTION
        "NetBIOS Name Server IP Address."
    ::=  {rsServerDispatcher 23}

rsWSDSyslogStatus  OBJECT-TYPE
    SYNTAX INTEGER {
                    enable(1),
                    disable(2)
                   }
    ACCESS  read-write
    STATUS  mandatory
    DESCRIPTION
        "Enable/Disable syslog message sending to remote station."
--  DEFVAL { 2 }
    ::=  {rsServerDispatcher 26}

rsWSDSyslogAddress OBJECT-TYPE
    SYNTAX IpAddress
    ACCESS  read-write
    STATUS  mandatory
    DESCRIPTION
        "The IP Address of the syslog station."
    ::= {rsServerDispatcher 27}

rsWSDNTCheckTable OBJECT-TYPE
   SYNTAX SEQUENCE OF RsWSDNTCheckEntry
   ACCESS not-accessible
   STATUS mandatory
   DESCRIPTION
       "In this table the WSD collects NT statistics per servers."
   ::= {rsServerDispatcher 28}

rsWSDNTCheckEntry OBJECT-TYPE
   SYNTAX RsWSDNTCheckEntry
   ACCESS not-accessible
   STATUS  mandatory
   DESCRIPTION
       " The row definition for this table."
   INDEX  {rsWSDNTSerialNum}
   ::= {rsWSDNTCheckTable 1}

RsWSDNTCheckEntry ::= SEQUENCE {
     rsWSDNTSerialNum             INTEGER,
     rsWSDNTFrequentCheckPeriod   INTEGER,
     rsWSDNTOpenSessionsWeight    INTEGER,
     rsWSDNTIncomingTrafficWeight INTEGER,
     rsWSDNTOutgoingTrafficWeight INTEGER,
     rsWSDNTRegularCheckPeriod    INTEGER,
     rsWSDNTAvResponseWeight      INTEGER,
     rsWSDNTUsersLimitWeight      INTEGER,
     rsWSDNTTCPLimitWeight        INTEGER,
     rsWSDNTRetries               INTEGER,
     rsWSDNTCommunity             DisplayString
}

rsWSDNTSerialNum OBJECT-TYPE
   SYNTAX INTEGER
   ACCESS  read-only
   STATUS  mandatory
   DESCRIPTION
       "The serial number of the algorithm."
   ::= {rsWSDNTCheckEntry 1}

rsWSDNTFrequentCheckPeriod OBJECT-TYPE
   SYNTAX INTEGER
   ACCESS  read-write
   STATUS  mandatory
   DESCRIPTION
       "The period for getting the frequent NT variables."
-- DEFVAL {10}
   ::= {rsWSDNTCheckEntry 2}

rsWSDNTOpenSessionsWeight OBJECT-TYPE
   SYNTAX INTEGER
   ACCESS  read-write
   STATUS  mandatory
   DESCRIPTION
       "The weight for currently open sessions consideration."
-- DEFVAL {0}
   ::= {rsWSDNTCheckEntry 3}

rsWSDNTIncomingTrafficWeight OBJECT-TYPE
   SYNTAX INTEGER
   ACCESS  read-write
   STATUS  mandatory
   DESCRIPTION
       "The weight for incoming traffic consideration."
-- DEFVAL {0}
   ::= {rsWSDNTCheckEntry 4}

rsWSDNTOutgoingTrafficWeight OBJECT-TYPE
   SYNTAX INTEGER
   ACCESS  read-write
   STATUS  mandatory
   DESCRIPTION
       "The weight for outgoing traffic consideration."
-- DEFVAL {0}
   ::= {rsWSDNTCheckEntry 5}

rsWSDNTRegularCheckPeriod OBJECT-TYPE
   SYNTAX INTEGER
   ACCESS  read-write
   STATUS  mandatory
   DESCRIPTION
       "The period for getting the regular NT variables."
-- DEFVAL {300}
   ::= {rsWSDNTCheckEntry 6}

rsWSDNTAvResponseWeight   OBJECT-TYPE
   SYNTAX INTEGER
   ACCESS  read-write
   STATUS  mandatory
   DESCRIPTION
       "The weight for average response time."
-- DEFVAL {0}
   ::= {rsWSDNTCheckEntry 7}

rsWSDNTUsersLimitWeight OBJECT-TYPE
   SYNTAX INTEGER
   ACCESS  read-write
   STATUS  mandatory
   DESCRIPTION
       "The weight for the users limit on the server."
-- DEFVAL {0}
   ::= {rsWSDNTCheckEntry 8}

rsWSDNTTCPLimitWeight OBJECT-TYPE
   SYNTAX INTEGER
   ACCESS  read-write
   STATUS  mandatory
   DESCRIPTION
       "The weight for the TCP connections limit on the server."
-- DEFVAL {0}
   ::= {rsWSDNTCheckEntry 9}

rsWSDNTRetries OBJECT-TYPE
   SYNTAX INTEGER
   ACCESS  read-write
   STATUS  mandatory
   DESCRIPTION
       "The number of retries before issuing a trap."
-- DEFVAL {3}
   ::= {rsWSDNTCheckEntry 10}

rsWSDNTCommunity OBJECT-TYPE
    SYNTAX DisplayString (SIZE(1..20))
    ACCESS  read-write
    STATUS  mandatory
    DESCRIPTION
    "The SNMP community name with which we access the servers."
    ::= {rsWSDNTCheckEntry 11}

rsWSDdummy8 OBJECT-TYPE
    SYNTAX INTEGER
    ACCESS  read-only
    STATUS  mandatory
    DESCRIPTION
       " Dummy variable for stopping getnext."
    ::=  {rsWSDNTCheckTable 2}

rsWSDPrivateCheckTable OBJECT-TYPE
   SYNTAX SEQUENCE OF RsWSDPrivateCheckEntry
   ACCESS not-accessible
   STATUS mandatory
   DESCRIPTION
       "In this table the WSD collects private statistics per server."
   ::= {rsServerDispatcher 29}

rsWSDPrivateCheckEntry OBJECT-TYPE
   SYNTAX RsWSDPrivateCheckEntry
   ACCESS not-accessible
   STATUS  mandatory
   DESCRIPTION
       " The row definition for this table."
   INDEX  {rsWSDPrivateSerialNum}
   ::= {rsWSDPrivateCheckTable 1}

RsWSDPrivateCheckEntry  ::= SEQUENCE {
               rsWSDPrivateSerialNum           INTEGER,
               rsWSDPrivateSpecialCheckPeriod  INTEGER,
               rsWSDPrivateExtraVar1ID         OBJECT IDENTIFIER,
               rsWSDPrivateExtraVar1Weight     INTEGER,
               rsWSDPrivateExtraVar2ID         OBJECT IDENTIFIER,
               rsWSDPrivateExtraVar2Weight     INTEGER,
               rsWSDPrivateRetries             INTEGER,
               rsWSDPrivateCommunity           DisplayString,
               rsWSDPrivateExtraVar1Mode       INTEGER,
               rsWSDPrivateExtraVar2Mode       INTEGER
}

rsWSDPrivateSerialNum OBJECT-TYPE
   SYNTAX INTEGER
   ACCESS  read-only
   STATUS  mandatory
   DESCRIPTION
       "The serial number of the algorithm."
   ::= {rsWSDPrivateCheckEntry 1}

rsWSDPrivateSpecialCheckPeriod OBJECT-TYPE
   SYNTAX INTEGER
   ACCESS  read-write
   STATUS  mandatory
   DESCRIPTION
       "The period for getting the private variables."
-- DEFVAL {30}
   ::= {rsWSDPrivateCheckEntry 2}

rsWSDPrivateExtraVar1ID OBJECT-TYPE
   SYNTAX OBJECT IDENTIFIER
   ACCESS read-write
   STATUS mandatory
   DESCRIPTION
       "This MIB variable will be retrieved from the server."
   ::= {rsWSDPrivateCheckEntry 3}

rsWSDPrivateExtraVar1Weight OBJECT-TYPE
   SYNTAX INTEGER
   ACCESS read-write
   STATUS  mandatory
   DESCRIPTION
       "The weight for variable number 1."
-- DEFVAL {3}
   ::= {rsWSDPrivateCheckEntry 4}

rsWSDPrivateExtraVar2ID OBJECT-TYPE
   SYNTAX OBJECT IDENTIFIER
   ACCESS  read-write
   STATUS  mandatory
   DESCRIPTION
       "This MIB variable will be retrieved from the server."
   ::= {rsWSDPrivateCheckEntry 5}

rsWSDPrivateExtraVar2Weight OBJECT-TYPE
   SYNTAX INTEGER
   ACCESS  read-write
   STATUS  mandatory
   DESCRIPTION
       "The weight for variable number 2."
-- DEFVAL {3}
   ::= {rsWSDPrivateCheckEntry 6}

rsWSDPrivateRetries OBJECT-TYPE
  SYNTAX INTEGER
  ACCESS  read-write
  STATUS  mandatory
  DESCRIPTION
      "The number of retries before issuing a trap."
  ::= {rsWSDPrivateCheckEntry 7}

rsWSDPrivateCommunity OBJECT-TYPE
    SYNTAX DisplayString (SIZE(1..20))
    ACCESS  read-write
    STATUS  mandatory
    DESCRIPTION
    "The SNMP community name with which we access the servers."
    ::= {rsWSDPrivateCheckEntry 8}


rsWSDPrivateExtraVar1Mode OBJECT-TYPE
    SYNTAX INTEGER {
      ascending(1),
      descending(2)
   }
    ACCESS  read-write
    STATUS  mandatory
    DESCRIPTION
      "Specify the type of parameter. Ascending means that the value of 100 is the best (Idle CPU percentage). Descending means that the value of 0 is the best (CPU utilization percentage)"
    ::=  {rsWSDPrivateCheckEntry 9}

rsWSDPrivateExtraVar2Mode OBJECT-TYPE
    SYNTAX INTEGER {
      ascending(1),
      descending(2)
   }
    ACCESS  read-write
    STATUS  mandatory
    DESCRIPTION
      "Specify the type of parameter. Ascending means that the value of 100 is the best (Idle CPU percentage). Descending means that the value of 0 is the best (CPU utilization percentage)"
    ::=  {rsWSDPrivateCheckEntry 10}


rsWSDdummy9 OBJECT-TYPE
    SYNTAX INTEGER
    ACCESS  read-only
    STATUS  mandatory
    DESCRIPTION
       " Dummy variable for stopping getnext."
    ::=  {rsWSDPrivateCheckTable 2}

rsWSDDNSResolution  OBJECT-TYPE
   SYNTAX INTEGER {
                   enable(1),
                   disable(2),
                   proximity(3)
                  }
   ACCESS  read-write
   STATUS  mandatory
   DESCRIPTION
       "Enable/Disable DNS resolution for Farm Addresses. In proximity mode, the WSD will give the best proximity address for the farm."
-- DEFVAL { 2 }
   ::=  {rsServerDispatcher 31}

rsWSDUserPassword  OBJECT-TYPE
    	SYNTAX DisplayString (SIZE(1..8))
    	ACCESS  read-write
   	STATUS  mandatory
   	DESCRIPTION
     	 "Software download user provided password."
   	::=  {rsServerDispatcher 33}

rsWSDUserVersion  OBJECT-TYPE
    	SYNTAX DisplayString (SIZE(1..6))
    	ACCESS  read-write
   	STATUS  mandatory
   	DESCRIPTION
     	 "Software download user provided version."
   	::=  {rsServerDispatcher 34}

rsWSDNatStatus  OBJECT-TYPE
    SYNTAX INTEGER {
                    enable(1),
                    disable(2)
                   }
    ACCESS  read-write
    STATUS  mandatory
    DESCRIPTION
        "Enable/Disable NAT - to hide the address of the server in messages send ."
--  DEFVAL { 2 }
    ::=  {rsServerDispatcher 35}


rsWSDRedundancyTakeback  OBJECT-TYPE
   SYNTAX INTEGER {
        automatic(1),
        manual(2)
   }
   ACCESS  read-write
   STATUS  mandatory
   DESCRIPTION
       "Whether to take the interfaces when coming up from redundancy failure automatically or wait for manual terminal command"
-- DEFVAL { 1 }
   ::=  {rsServerDispatcher 37}

rsMLB  OBJECT IDENTIFIER ::= { rsServerDispatcher 38 }

rsCSD  OBJECT IDENTIFIER ::= { rsServerDispatcher 39 }

rsNWSD  OBJECT IDENTIFIER ::= { rsServerDispatcher 40 }


rsWSDIfTable  OBJECT-TYPE
    SYNTAX SEQUENCE OF  RsWSDIfEntry
    ACCESS  not-accessible
    STATUS  mandatory
    DESCRIPTION
      "RND-specific interface table.  Each table entry includes an
      index, Board number, Network Address, interface status, clock
      indicator and interface cost."
    ::= {  rsServerDispatcher  41  }


rsWSDIfEntry  OBJECT-TYPE
    SYNTAX RsWSDIfEntry
    ACCESS  not-accessible
    STATUS  mandatory
    DESCRIPTION
       " The row definition for this table."
    INDEX   { rsWSDIfIndex  }
    ::= {  rsWSDIfTable 1  }


RsWSDIfEntry ::= SEQUENCE {
  rsWSDIfIndex
     INTEGER,
  rsWSDIfBoardNum
     INTEGER,
  rsWSDIfNetAddress
     NetworkAddress,
  rsWSDIfStatus
     INTEGER,
  rsWSDIfClockType
     INTEGER,
 rsWSDIfBaudRate
     INTEGER,
  rsWSDIfCost
     INTEGER,
  rsWSDIfCompression
     INTEGER,
  rsWSDIfCompressionStatus
     INTEGER,
  rsWSDIfCompressionRate
     INTEGER,
  rsWSDIfLATCompression
     INTEGER,
  rsWSDIfCompressionType
     INTEGER,
rsWSDIfFilterMode
     INTEGER,
rsWSDIfChannelType
     INTEGER,
rsWSDIfBridge
     INTEGER,
rsWSDHighPriorityIf    -- New Parameters
     INTEGER,
rsWSDWanHeader   -- New Parameters
     INTEGER,
rsWSDDuplexMode  -- New Parameters
     INTEGER
  }

rsWSDIfIndex OBJECT-TYPE
    SYNTAX   INTEGER
    ACCESS  read-only
    STATUS  mandatory
    DESCRIPTION
     "Index to the RND Interface Table. The interface defined by a
     particular value of this index is the same interface as
     identified by the same value of ifIndex (MIBII)."
         ::= {  rsWSDIfEntry 1  }

rsWSDIfBoardNum OBJECT-TYPE
    SYNTAX   INTEGER
    ACCESS  read-only
    STATUS  mandatory
    DESCRIPTION
     "The interface defined by this entry correspTnds to the board
     defined by the same value of rndSlotBoardNum in the rndSlotTab."
    ::= {  rsWSDIfEntry 2  }

rsWSDIfNetAddress OBJECT-TYPE
    SYNTAX   NetworkAddress
    ACCESS  read-only
    STATUS  mandatory
    DESCRIPTION
     "The IP address of the interface defined by the particular value of
     rsWSDIfIndex."
    ::= {  rsWSDIfEntry 3  }

rsWSDIfStatus  OBJECT-TYPE
    SYNTAX   INTEGER  {
       ok (1),
       okSingleBrg(2),
       okMultiBrg(3),
       connctFault(4),
       rxFault(5),
       txFault(6),
       channelLoopback(7),
       rxClockFault(8),
       t1Alarm(9)
    }
    ACCESS  read-only
    STATUS  mandatory
    DESCRIPTION
     "The current status of the interface."
     ::= {  rsWSDIfEntry 4  }

rsWSDIfClockType   OBJECT-TYPE
    SYNTAX  INTEGER {
       external(1),
       internal(2),
       t1(3),
       g703(4)
    }
    ACCESS  read-write
    STATUS  mandatory
    DESCRIPTION
     "rsWSDIfClockType defines the type of clock each interface
     uses: internal or external."
    ::= {  rsWSDIfEntry 5  }

rsWSDIfBaudRate    OBJECT-TYPE          -- Level II routing
    SYNTAX   INTEGER   -- word
    ACCESS  read-write
    STATUS  mandatory
    DESCRIPTION
     " Defines the baud rate of use by the interface. The valid
      rates are determined by the type of the media for which this
      baud rate is defined."
    ::= { rsWSDIfEntry 6  }


rsWSDIfCost    OBJECT-TYPE          -- Level II routing
    SYNTAX   INTEGER   -- word
    ACCESS  read-write
    STATUS  mandatory
    DESCRIPTION
       "This variable assigns a transmission cost to the interface
        (channel or LAN). These costs are used in Level II routing. The
        costs aretypically inversly proportional to the channel quality."
    ::= { rsWSDIfEntry 7  }

rsWSDIfCompression   OBJECT-TYPE
    SYNTAX  INTEGER {
       enable(1),
       disable(2)
    }
    ACCESS  read-write
    STATUS  mandatory
    DESCRIPTION
       "Defines whether data compression is enabled or disabled for the
       interface."
    ::= {  rsWSDIfEntry 8  }

  rsWSDIfCompressionStatus  OBJECT-TYPE
  SYNTAX  INTEGER {
       not-inserted(1),
       active(2),
       not-active(3),
       disable(4)
    }
    ACCESS  read-only
    STATUS  mandatory
    DESCRIPTION
       "Defines the status of the compression component:
        not-inserted - Compression component is not in the device
        active -     Compression is enabled and operates correctly
        not-active - Compression is enables but does not operate.
                     The reason may be that there is no compression
                     component on the device connected to this interface.
        disabled   - Compression was disabled by management, using
                     variable rndCompression."
    ::= {  rsWSDIfEntry 9  }

  rsWSDIfCompressionRate  OBJECT-TYPE
    SYNTAX  INTEGER
    ACCESS  read-only
    STATUS  mandatory
    DESCRIPTION
  "Percentage of compression. This variable applies only
  if rndCompressionStatus is active."
    ::= {  rsWSDIfEntry 10  }

  rsWSDIfLATCompression  OBJECT-TYPE
    SYNTAX  INTEGER {
       enable(1),
       disable(2)
    }
    ACCESS  read-write
    STATUS  mandatory
    DESCRIPTION
  "Enable/Disable the LAT Compression."
    ::= {  rsWSDIfEntry 11  }

  rsWSDIfCompressionType  OBJECT-TYPE
    SYNTAX  INTEGER {
       none(1),
       lowSpeed(2),
       highSpeed(3)
    }
    ACCESS  read-only
    STATUS  mandatory
    DESCRIPTION
        "This parameter indicates the type of compression option available in the device.
         none(1)     - indicates that there is no compression option in the device
         lowSpeed(2) - indicates a compression option which is  operational up
                       to line speed sof 64 kbps.
         highSpeed(3)- indicates a compression option which is  operational up
                       to line speeds of 2 Mbps."
    ::= {  rsWSDIfEntry 12  }

rsWSDIfFilterMode  OBJECT-TYPE
    SYNTAX  INTEGER {
       destinationOnly(1),
       sourceAndDestination(2),
       none(3)
    }
    ACCESS  read-write
    STATUS  mandatory
    DESCRIPTION
         "This parameter indicates the type of filtering in the device. "
    ::= {  rsWSDIfEntry 13 }

    rsWSDIfChannelType OBJECT-TYPE
      SYNTAX  INTEGER {
         wanChannel(1),
         ogRanPort(2),
         routerToBridge(3),
         spsFramRelay(4),         -- Frame Relay with external SPS.
         dialBackup(5),
         snar(6),
         lan(7),
         spsX25(8),
         frameRelay1490(9),       -- Frame Relay with full  RFC1490 support.
         frameRelay1490CAR(10),   -- Frame Relay with CAR RFC1490 bridge encapsulation.
         frameRelayCAR(11),       -- Frame Relay with CAR and RND's encapsulation
         ppp(12)        -- New Value
        }
      ACCESS   read-write
      STATUS   mandatory
      DESCRIPTION
        " The type of the WAN channel "
   ::= { rsWSDIfEntry 14 }

    rsWSDIfBridge OBJECT-TYPE
      SYNTAX  INTEGER {
         enable(1),
         disable(2)
        }
      ACCESS   read-write
      STATUS   mandatory
      DESCRIPTION
        " This variable indicates  whether this interface forward Layer II pakages."
   ::= { rsWSDIfEntry 15 }

    rsWSDHighPriorityIf  OBJECT-TYPE
      SYNTAX  INTEGER {
         enable(1),
         disable(2)
        }
      ACCESS   read-write
      STATUS   mandatory
      DESCRIPTION
        " This variable indicates  whether this interface will forward pakages
        that fit HighPriority set by the manager."
       ::= { rsWSDIfEntry 16}

    rsWSDWanHeader  OBJECT-TYPE
      SYNTAX  INTEGER {
         regular(1),
         short(2)
        }
      ACCESS   read-write
      STATUS   mandatory
      DESCRIPTION
        " This variable indicates the RND WAN header type used for frames
          which pass through this interface. 'regular' specifies a 14 bytes
          header compatible with older OG versions and 'short' a 4 byte header
          compatible with the RND adapter product family."
       ::= { rsWSDIfEntry 17}

    rsWSDDuplexMode  OBJECT-TYPE
      SYNTAX  INTEGER {
         half(1),
         full(2),
         auto(3)
        }
      ACCESS   read-write
      STATUS   mandatory
      DESCRIPTION
        " This variable indicates whether this interface operates in half duplex
          full duplex or auto negotiation mode."
       ::= { rsWSDIfEntry 18}

-- The following definitions are applicable for the mirroring

rsWSDClientMirrorPercentage OBJECT-TYPE
    SYNTAX  INTEGER  (1..100)
    ACCESS  read-write
    STATUS  mandatory
    DESCRIPTION
      "The percent of client entries to back up."
--  DEFVAL  { 100 }
    ::=  {rsServerDispatcher 42}

rsWSDMirrorStatus OBJECT-TYPE
    SYNTAX  INTEGER {
      enable(1),
      disable(2)
    }
    ACCESS  read-write
    STATUS  mandatory
    DESCRIPTION
      "Enable/Disable mirroring. This enables the allocation of the mirror tables."
    ::=  {rsServerDispatcher 43}

rsWSDMirrorProtocolMode OBJECT-TYPE
    SYNTAX  INTEGER {
      enable(1),
      disable(2)
    }
    ACCESS  read-write
    STATUS  mandatory
    DESCRIPTION
      "Enable/Disable of the mirror protocol. That is whether to send the mirror
       messages."
    ::=  {rsServerDispatcher 44}

rsWSDApplicationMirrorTable OBJECT-TYPE
    SYNTAX SEQUENCE OF RsWSDApplicationMirrorEntry
    ACCESS not-accessible
    STATUS  mandatory
    DESCRIPTION
      "Table containing the list of active mirror entries."
    ::=  {rsServerDispatcher 45}

rsWSDApplicationMirrorEntry OBJECT-TYPE
    SYNTAX RsWSDApplicationMirrorEntry
    ACCESS not-accessible
    STATUS  mandatory
    DESCRIPTION
       "The row definition for this table."
   INDEX { rsWSDMirrorActiveAddress }
    ::=  { rsWSDApplicationMirrorTable 1 }

RsWSDApplicationMirrorEntry ::= SEQUENCE {
  rsWSDMirrorActiveAddress IpAddress,
  rsWSDMirrorActiveStatus  INTEGER
  }

rsWSDMirrorActiveAddress OBJECT-TYPE
    SYNTAX  IpAddress
    ACCESS  read-only
    STATUS  mandatory
    DESCRIPTION
      "The IP address of the active device."
    ::=  {rsWSDApplicationMirrorEntry 1}

rsWSDMirrorActiveStatus OBJECT-TYPE
    SYNTAX INTEGER {
              active(1),
              notInService(2),
              notReady(3),
              createAndGo(4),
              createAndWait(5),
              destroy(6) }
    ACCESS  read-write
    STATUS  mandatory
    DESCRIPTION
       "This variable indicates the administrative status of this entry.
        Used to delete an entry of this table."
    ::=  { rsWSDApplicationMirrorEntry 2 }

rsWSDdummy11 OBJECT-TYPE
    SYNTAX INTEGER
    ACCESS  read-only
    STATUS  mandatory
    DESCRIPTION
       " Dummy variable for stopping getnext."
    ::=  {rsWSDApplicationMirrorTable 2}

rsWSDClientMirrorPollingTime OBJECT-TYPE
    SYNTAX  INTEGER
    ACCESS  read-write
    STATUS  mandatory
    DESCRIPTION
      "The polling time for sending the client entries."
--  DEFVAL  { 10 }
    ::=  {rsServerDispatcher 46}

rsPlatformIdentifier OBJECT-TYPE
   SYNTAX  INTEGER {
        vgate(1),
        vgfe(2),
        onecpu(3),
        onecpuh(4),
        boomer(5),
        cougar(6)
   }
   ACCESS  read-only
   STATUS  mandatory
   DESCRIPTION
        "An administratively-assigned value that identifies managed device platform."
   ::= { rsServerDispatcher 47 }

rsConfigurationIdentifier OBJECT-TYPE
   SYNTAX  INTEGER {
        twoPorts(1),
        fourPorts(2),
        fixed-2(3),
        fixed-8(4),
        fixed-8-2(5),
        fixed-16-5(6),
        chassis(7),
        fixed-7(8)
   }
   ACCESS  read-only
   STATUS  mandatory
   DESCRIPTION
        "An administratively-assigned value that identifies managed device configuration."
   ::= { rsServerDispatcher 48 }

rsSWPasswordStatus OBJECT-TYPE
   SYNTAX  INTEGER {
        statusUnset(1),
        passwordOK(2),
        wrongPassword(3)
   }
   ACCESS  read-write
   STATUS  mandatory
   DESCRIPTION
        "Software download password status."
   DEFVAL {statusUnset}
   ::= { rsServerDispatcher 49 }

rsWSDFlashSize OBJECT-TYPE
   SYNTAX  INTEGER
   ACCESS  read-only
   STATUS  mandatory
   DESCRIPTION
        "Flash Size"
   ::= { rsServerDispatcher 50 }

rsWSDDRAMSize OBJECT-TYPE
   SYNTAX  INTEGER
   ACCESS  read-only
   STATUS  mandatory
   DESCRIPTION
        "DRAM Size"
   ::= { rsServerDispatcher 51 }

rsWSDVLANRedundOperStatus OBJECT-TYPE
    SYNTAX  INTEGER {
        enable(1),
        disable(2)
    }
    ACCESS  read-write
    STATUS  mandatory
    DESCRIPTION
    "Enable/Disable the backup redundant device for a VLAN."
    ::=  { rsServerDispatcher 52 }

rsWSDResourceUtilization OBJECT-TYPE
    SYNTAX  INTEGER  (0..100)
    ACCESS  read-only
    STATUS  mandatory
    DESCRIPTION
      "Resource Utilization of WSD. Considers network utilization and internal CPU utilization"
    DEFVAL  { 0 }
    ::=  { rsServerDispatcher 53 }

rsWSDRSResourceUtilization OBJECT-TYPE
    SYNTAX  INTEGER  (0..100)
    ACCESS  read-only
    STATUS  mandatory
    DESCRIPTION
      "Resource Utilization of internal CPU utilization"
    DEFVAL  { 0 }
    ::=  { rsServerDispatcher 54 }

rsWSDREResourceUtilization OBJECT-TYPE
    SYNTAX  INTEGER  (0..100)
    ACCESS  read-only
    STATUS  mandatory
    DESCRIPTION
      "Resource Utilization of network utilization"
    DEFVAL  { 0 }
    ::=  { rsServerDispatcher 55 }

rsWSDBuildNumber OBJECT-TYPE
    SYNTAX  DisplayString
    ACCESS  read-only
    STATUS  mandatory
    DESCRIPTION
      "Build number"
    ::=  { rsServerDispatcher 56 }

rsWSDUseOneTrap OBJECT-TYPE
    SYNTAX  INTEGER {
        enable(1),
        disable(2)
    }
    ACCESS  read-write
    STATUS  mandatory
    DESCRIPTION
      "When enabled, a single trap is used to indicate server failure. When disabled,
        continuous traps are sent."
    DEFVAL { 2 }
    ::=  { rsServerDispatcher 57 }

rsWSDSecuredComm  OBJECT IDENTIFIER ::= { rsServerDispatcher 58 }

rsWSDSCProtcolsTable OBJECT-TYPE
    SYNTAX SEQUENCE OF RsWSDSCProtcolsEntry
    ACCESS not-accessible
    STATUS mandatory
    DESCRIPTION
      "Table containing the list of ports/protocols for secured (encrypted)
       communication between the device and the management station or other device."
    ::=  { rsWSDSecuredComm 1 }

rsWSDSCProtcolsEntry OBJECT-TYPE
    SYNTAX RsWSDSCProtcolsEntry
    ACCESS not-accessible
    STATUS  mandatory
    DESCRIPTION
       "The row definition for protocol table."
    INDEX { rsWSDSCProtocol }
    ::=  { rsWSDSCProtcolsTable 1}

RsWSDSCProtcolsEntry ::= SEQUENCE {
    rsWSDSCProtocol       INTEGER,
    rsWSDSCProtocolStatus INTEGER
}

rsWSDSCProtocol OBJECT-TYPE
    SYNTAX INTEGER {
      snmp(1),
      tftp(2),
      lrp(3),
      prp(4),
      srp(5),
      mirror(6)
    }
    ACCESS  read-only
    STATUS  mandatory
    DESCRIPTION
      "The protocol that should work in secured mode."
    ::=  { rsWSDSCProtcolsEntry 1}

rsWSDSCProtocolStatus OBJECT-TYPE
    SYNTAX INTEGER {
      encrypted(1),
      notEncrypted(2)
    }
    ACCESS  read-write
    STATUS  mandatory
    DESCRIPTION
      "The status (secured or not secured) of the protocol."
--  DEFVAL  { 2 }
    ::=  { rsWSDSCProtcolsEntry 2}

rsWSDSNMPPortsTable OBJECT-TYPE
    SYNTAX SEQUENCE OF RsWSDSNMPPortsEntry
    ACCESS not-accessible
    STATUS mandatory
    DESCRIPTION
      "The table contains all the physical ports. Each port can be set to
       allow/block SNMP operations to the device."
    ::= { rsServerDispatcher 59 }

rsWSDSNMPPortsEntry OBJECT-TYPE
  SYNTAX RsWSDSNMPPortsEntry
  ACCESS not-accessible
  STATUS mandatory
  DESCRIPTION
    "Row definition for the table."
  INDEX { rsWSDSNMPPhysicalPortNumber }
  ::= { rsWSDSNMPPortsTable 1 }

RsWSDSNMPPortsEntry ::= SEQUENCE {
  rsWSDSNMPPhysicalPortNumber INTEGER,
  rsWSDSNMPPhysicalPortState  INTEGER
}

rsWSDSNMPPhysicalPortNumber OBJECT-TYPE
  SYNTAX INTEGER
  ACCESS read-only
  STATUS mandatory
  DESCRIPTION
    "Physical port number."
  ::= { rsWSDSNMPPortsEntry 1 }

rsWSDSNMPPhysicalPortState OBJECT-TYPE
  SYNTAX INTEGER {
    enable(1),
    disable(2)
  }
  ACCESS read-write
  STATUS mandatory
  DESCRIPTION
    "enable - accept SNMP operations on the physical port. disable -
     ignore SNMP opertaions on the physical port."
  DEFVAL { 1 }
  ::= { rsWSDSNMPPortsEntry 2 }

rsBWM  OBJECT IDENTIFIER ::= { rsServerDispatcher 60 }


rsWSDTelnetUserTable OBJECT-TYPE
  SYNTAX  SEQUENCE OF RsWSDTelnetUserEntry
  ACCESS  not-accessible
  STATUS  mandatory
  DESCRIPTION
    "A table containing the users authorized to use TELNET."
  ::= {rsServerDispatcher 61}

rsWSDTelnetUserEntry OBJECT-TYPE
  SYNTAX  RsWSDTelnetUserEntry
  ACCESS  not-accessible
  STATUS  mandatory
  DESCRIPTION
    "Information about a particular Telnet user."
  INDEX   { rsWSDTelnetUserName }
  ::= { rsWSDTelnetUserTable 1 }

RsWSDTelnetUserEntry ::= SEQUENCE {
    rsWSDTelnetUserName     DisplayString,
    rsWSDTelnetUserPassword DisplayString,
    rsWSDTelnetUserEAddr    DisplayString,
    rsWSDTelnetUserSeverity INTEGER,
    rsWSDTelnetUserStatus   RowStatus,
    rsWSDTelnetUserGroup    DisplayString
  }

rsWSDTelnetUserName OBJECT-TYPE
    SYNTAX DisplayString (SIZE(0..30))
    ACCESS  read-write
    STATUS  mandatory
    DESCRIPTION
    "User Name."
    ::= {rsWSDTelnetUserEntry 1}

rsWSDTelnetUserPassword OBJECT-TYPE
    SYNTAX DisplayString (SIZE(0..30))
    ACCESS  read-write
    STATUS  mandatory
    DESCRIPTION
    "User password."
    ::= {rsWSDTelnetUserEntry 2}

rsWSDTelnetUserEAddr OBJECT-TYPE
    SYNTAX DisplayString (SIZE(0..63))
    ACCESS  read-write
    STATUS  mandatory
    DESCRIPTION
    "User email address."
    ::= {rsWSDTelnetUserEntry 3}

rsWSDTelnetUserSeverity OBJECT-TYPE
   SYNTAX INTEGER {
      none(1),
      info(2),
      warning(3),
      error(4),
      fatal(5)
   }
   ACCESS read-write
   STATUS mandatory
   DESCRIPTION
      "minimum failure severity to be notified by mail"
   ::=  { rsWSDTelnetUserEntry 4}

rsWSDTelnetUserStatus OBJECT-TYPE
   SYNTAX RowStatus
   ACCESS read-write
   STATUS mandatory
   DESCRIPTION
      "Entry status"
   ::=  { rsWSDTelnetUserEntry 5}

rsWSDTelnetUserGroup OBJECT-TYPE
	SYNTAX DisplayString (SIZE(0..30))
	ACCESS read-write
	STATUS mandatory 
	DESCRIPTION 
		"The group to which that user belongs." 
	::= { rsWSDTelnetUserEntry 6}


rsWSDTelnetParams OBJECT IDENTIFIER ::= {rsServerDispatcher 62 }

rsWSDTelnetPort OBJECT-TYPE
    SYNTAX  INTEGER
    ACCESS  read-write
    STATUS  mandatory
    DESCRIPTION
      "The Telnet Server Port."
--  DEFVAL  { 23 }
    ::=  {rsWSDTelnetParams 1}


rsWSDTelnetStatus OBJECT-TYPE
   SYNTAX  INTEGER {
        enable(1),
      	disable(2)
   }
   ACCESS  read-write
   STATUS  mandatory
   DESCRIPTION
        "Telnet Status. Enable/Disable Telnet Terminal operation."
--  DEFVAL  { disable }
   ::= { rsWSDTelnetParams 2 }

rsSSD  OBJECT IDENTIFIER ::= { rsServerDispatcher 63 }

rsSSDvirtualLan  OBJECT IDENTIFIER ::= { rsSSD 1 }

--
--  rsSSDvirtualLanTable
--
rsSSDvirtualLanTable  OBJECT-TYPE
   SYNTAX  SEQUENCE OF RsSSDvirtualLanEntry
   ACCESS  not-accessible
   STATUS  mandatory
   DESCRIPTION
         "An entry of this table specifies an new ifIndex with a type of
          propVirtual(53)."
   ::= { rsSSDvirtualLan 1 }

rsSSDvirtualLanEntry OBJECT-TYPE
   SYNTAX  RsSSDvirtualLanEntry
   ACCESS  not-accessible
   STATUS  mandatory
   DESCRIPTION
         "A list of information for each virtual LAN."
   INDEX  { rsSSDvlIfIndex}
   ::= { rsSSDvirtualLanTable 1 }

RsSSDvirtualLanEntry   ::= SEQUENCE {
     rsSSDvlIfIndex          		INTEGER,
     rsSSDvlProto            		INTEGER,
     rsSSDvlAutoConfigEnable 		TruthValue,
     rsSSDvlStatus           		RowStatus,
     rsSSDvlType             		INTEGER,
     rsSSDvlTag                         INTEGER,
     rsSSDvlPriority                    INTEGER
   }

rsSSDvlIfIndex OBJECT-TYPE
   SYNTAX  INTEGER
   ACCESS  read-write
   STATUS  mandatory
   DESCRIPTION
         "An logical interface number, corresponded this VL"
   ::= { rsSSDvirtualLanEntry 1 }

rsSSDvlProto  OBJECT-TYPE
   SYNTAX  INTEGER {
      other(1),
      ip(2),
      ipmulticast(3),
      ipxRaw(4),
      ipxET(5),
      ipxLLC(6),
      ipxSNAP(7),
      decNET(8),
      decLAT(9),
      netBios(10),
      appleTalk(11),
      xns(12),
      sna(13),
      userDefined(14),
      swVlan(15)
      }
   ACCESS  read-write
   STATUS  mandatory
   DESCRIPTION
         "The protocol, supported by this VL. The meanings of the values are:
      other: none of the following. This VL includes any protocol except the
             following protocols. It  is a bridging VL. RS relies on
             a third-party router to exchange traffic between nodes on different
             virtual LANs of this type.
      IP:    This is a routing VL, RS will route between nodes on
             different virtual LANs.
      IPmulticast: RS will broadcast the message to all  the VL's ports. Used for
             video-conferencing applications.
      ipxRaw: This is a Routing VL, RS will route between nodes on
             different virtual LANs.
      ipxET: This is a routing VL, RS will route between nodes on
             different virtual LANs.
      ipxLLC: This is a routing VL, RS will route between nodes on
             different virtual LANs.
      ipxSNAP: This is a routing VL, RS will route between nodes on
             different virtual LANs.
      decNET: This is a bridging VL, RS relies on a third-party router
             to exchange traffic between nodes on different DECnet virtual
             LANs of this type.
      netBios: This is a Bridging VL, RS relies on a third-party router
             to exchange traffic between nodes on different NetBIOS virtual
             LANs of this type.
      appleTalk: This is a bridging VL, RS relies on a third-party router
             to exchange traffic between nodes on different AppleTalk virtual
             LANs of this type.
      swVlan: This is a Bridging and routing VL (switch VL) , Bridging is
             done on the Hertz/Uhaul level , and the RS route between nodes on
             different virtual LANs and/or between nodes of the switch VL."

   ::= { rsSSDvirtualLanEntry 2 }

rsSSDvlAutoConfigEnable  OBJECT-TYPE
   SYNTAX  TruthValue
   ACCESS  read-write
   STATUS  mandatory
   DESCRIPTION
         "It is used only in the case of IP. The meanings of the values are:
      true(1):  Autolearning is used for this VL
      false(2): Autolearning isn't used for this VL from ports, specified in
                the table virtualLanAutoConfTable."
   ::= { rsSSDvirtualLanEntry 3 }

rsSSDvlStatus  OBJECT-TYPE
   SYNTAX  RowStatus
   ACCESS  read-write
   STATUS  mandatory
   DESCRIPTION
         "It is used to delete an entry"
   ::= { rsSSDvirtualLanEntry 4 }

rsSSDvlType OBJECT-TYPE
   SYNTAX INTEGER {
        regular(1),
        specBroadcast(2),
        specArpReq(3),
        specBroadcastAndUnicast(4),
        specArpReqAndUnicast(5),
	specSwitch(6)
        }
   ACCESS  read-write
   STATUS  mandatory
   DESCRIPTION
       "regular       - ordinary type
        specBroadcast - for switches that support VLANs as a set of ports and
                        only as a broadcast domain: broadcast frames do not
                        cross VLAN's bounders, but unicast frames may be
                        transmitted between different VLANs. Permits passing
                        of broadcast frames between Vgate's VLANs.
        specArpReq -    for switches that support VLANs as a set of ports and
                        only as a broadcast domain: broadcast frames do not
                        cross VLAN's bounders, but unicast frames may be
                        transmitted between different VLANs. Permits passing
                        of ARP request frames between Vgate's VLANs.
        specBroadcastAndUnicast -
                        for switches that support VLANs as a set of ports
                        but no frame crosses VLAN's bounders. Permits passing
                        of IP/ARP request broadcast and IP unicast frames
                        between Vgate's VLANs.
        specArpReqAndUnicast -
                        for switches that support VLANs as a set of ports
                        but no frame crosses VLAN's bounders. Permits passing
                        of ARP request broadcast and IP unicast frames between
                        Vgate's VLANs. This type can be used only for IP VLANs.
	specSwitch -
        		for switches that support VLANs as a set of ports.
                        This VLAN type is for switching when packets do not have
                        to get to the cpu except when an IP interface defined on the VLAN.
                        In Switch VLAN the cpu don't interfere in the bridging action
                        this is done on the Herzts level (L2)."
   ::= { rsSSDvirtualLanEntry 5 }


rsSSDvlTag OBJECT-TYPE
   SYNTAX  INTEGER
   ACCESS  read-write
   STATUS  mandatory
   DESCRIPTION
         "A VLAN tag, used for this VLAN on tagged ports.
          If it's 0, then a value of (rsSSDvlIfIndex-100000+1) is used"
   DEFVAL { 0 }
   ::= { rsSSDvirtualLanEntry 6 }

rsSSDvlPriority OBJECT-TYPE
   SYNTAX  INTEGER {
        low(1),
        high(2)
   }
   ACCESS  read-write
   STATUS  mandatory
   DESCRIPTION
         "A user priority, used for this VLAN on tagged ports."
   DEFVAL { 1 }
   ::= { rsSSDvirtualLanEntry 7 }



--
--   rsSSDvirtualLanPortsTable
--

rsSSDvirtualLanPortsTable  OBJECT-TYPE
   SYNTAX SEQUENCE OF RsSSDvirtualLanPortEntry
   ACCESS  not-accessible
   STATUS  mandatory
   DESCRIPTION
         "For each VL (a ifIndex with a type of propVirtual(53)) an entry of  this
           table specifies a set of ports, which it contains."
   ::= { rsSSDvirtualLan 2 }

rsSSDvirtualLanPortEntry   OBJECT-TYPE
   SYNTAX  RsSSDvirtualLanPortEntry
   ACCESS  not-accessible
   STATUS  mandatory
   DESCRIPTION
         "A entry of this table specifies a  VL and a port belonging to it"
   INDEX  { rsSSDvLIfIndex, rsSSDvLPortIfIndex}
   ::= { rsSSDvirtualLanPortsTable 1 }

RsSSDvirtualLanPortEntry  ::= SEQUENCE {
     rsSSDvLIfIndex      INTEGER,
     rsSSDvLPortIfIndex  INTEGER,
     rsSSDvLPortType     INTEGER,
     rsSSDvLPortStatus   RowStatus,
     rsSSDvLPortTag      INTEGER
 }


rsSSDvLIfIndex  OBJECT-TYPE
   SYNTAX  INTEGER
   ACCESS  read-write
   STATUS  mandatory
   DESCRIPTION
        "An logical interface number, corresponding to this VL"
   ::= { rsSSDvirtualLanPortEntry 1 }

rsSSDvLPortIfIndex  OBJECT-TYPE
   SYNTAX  INTEGER
   ACCESS  read-write
   STATUS  mandatory
   DESCRIPTION
         "A physical port belonging to the VL specified by rsSSDvlIfIndex."
   ::= { rsSSDvirtualLanPortEntry 2 }

rsSSDvLPortType   OBJECT-TYPE
   SYNTAX  INTEGER {
        static(1),
        dynamic(2)
   }
   ACCESS  read-only
   STATUS  mandatory
   DESCRIPTION
         "static means configured by user dynamic means autoconfigured by the RS"
   ::= { rsSSDvirtualLanPortEntry 3}

rsSSDvLPortStatus  OBJECT-TYPE
   SYNTAX  RowStatus
   ACCESS  read-write
   STATUS  mandatory
   DESCRIPTION
         "It is used to delete an entry"
   ::= { rsSSDvirtualLanPortEntry 4}

rsSSDvLPortTag  OBJECT-TYPE
    SYNTAX INTEGER {
        untag(1),
        tag(2)
    }
    ACCESS  read-write
    STATUS  mandatory
    DESCRIPTION
        "This variable indicate if the port is tagged or untagged "
--  DEFVAL { 1 }
    ::= { rsSSDvirtualLanPortEntry 5 }

rsWSDThresholdWarnings  OBJECT IDENTIFIER ::= { rsServerDispatcher 64 }

rsWSDThreshTrapFloodDelay OBJECT-TYPE
    SYNTAX INTEGER (0..3600)
    ACCESS  read-write
    STATUS  mandatory
    DESCRIPTION
       "This variable defines how far (in seconds) will 2 Threshold Warning Traps be
        spaced for the same Threshold Warning Type. Default = 0, i.e. DISABLED"
--  DEFVAL {0}
    ::= { rsWSDThresholdWarnings 1 }

rsWSDCriticalTrapFloodDelay OBJECT-TYPE
    SYNTAX INTEGER (1..3600)
    ACCESS  read-write
    STATUS  mandatory
    DESCRIPTION
       "This variable defines how far (in seconds) will 2 Critical Warning Traps be
        spaced (of any type). Default = 20 seconds."
--  DEFVAL {20}
    ::= { rsWSDThresholdWarnings 2 }

rsIDS OBJECT IDENTIFIER ::= { rsServerDispatcher 65 }

rsWSDLicense OBJECT-TYPE
    SYNTAX DisplayString (SIZE(1..80))
    ACCESS  read-write
    STATUS  mandatory
    DESCRIPTION "The new licence for the device"
--    DEFVAL
    ::=  {rsServerDispatcher 66}

rsErrMailParams OBJECT IDENTIFIER ::= {rsServerDispatcher 67 }


rsErrMailEnable OBJECT-TYPE
   SYNTAX INTEGER {
      enable(1),
      disable(2)
   }
    ACCESS  read-write
    STATUS  mandatory
    DESCRIPTION
      "Send email on errors enable"
--  DEFVAL  { 2 }
    ::=  {rsErrMailParams 1}


rsErrMailGateway OBJECT-TYPE
    SYNTAX IpAddress
    ACCESS  read-write
    STATUS  mandatory
    DESCRIPTION
      "primary SMTP gateway for error mail"
    ::=  {rsErrMailParams 2}

rsErrMailSrcAddress OBJECT-TYPE
   SYNTAX DisplayString (SIZE(1..64))
   ACCESS read-write
   STATUS mandatory
   DESCRIPTION
    "source address to be used by device for outgoing mail"
     ::= {rsErrMailParams 3}


rsWSDWebParams OBJECT IDENTIFIER ::= {rsServerDispatcher 68 }

rsWSDWebPort OBJECT-TYPE
    SYNTAX  INTEGER
    ACCESS  read-write
    STATUS  mandatory
    DESCRIPTION
      "The Web Server Port."
--  DEFVAL  { 80 }
    ::=  {rsWSDWebParams 1}


rsWSDWebStatus OBJECT-TYPE
   SYNTAX  INTEGER {
        enable(1),
      	disable(2)
   }
   ACCESS  read-write
   STATUS  mandatory
   DESCRIPTION
        "Web Status. Enable/Disable Web operation."
--  DEFVAL  { disable }
   ::= { rsWSDWebParams 2 }

rsWSDWebHelpLocation OBJECT-TYPE
   SYNTAX  DisplayString (SIZE(0..80))
   ACCESS  read-write
   STATUS  mandatory
   DESCRIPTION
        "Location of the help files directory."
   ::= { rsWSDWebParams 3 }


rsWSDSysParams OBJECT IDENTIFIER ::= {rsServerDispatcher 69 }

rsWSDSysFlashSize OBJECT-TYPE
    SYNTAX  INTEGER
    ACCESS  read-only
    STATUS  mandatory
    DESCRIPTION
      "The flash size of the device in mega bytes."
--  DEFVAL  { 8 }
    ::=  {rsWSDSysParams 1}


rsWSDSysUpTime OBJECT-TYPE
   SYNTAX  DisplayString
   ACCESS  read-only
   STATUS  mandatory
   DESCRIPTION
        "Time since the system was last reinitialized in a convenient format."
--  DEFVAL  { 0 }
   ::= { rsWSDSysParams 2 }


rsWSDSysManagedTime  OBJECT-TYPE
   SYNTAX DisplayString (SIZE(0..80))
   ACCESS read-write
   STATUS mandatory
   DESCRIPTION
    "The time will be sent in the format hh:mm:ss"
   ::= { rsWSDSysParams 3 }

rsWSDSysManagedDate  OBJECT-TYPE
   SYNTAX DisplayString (SIZE(0..80))
   ACCESS read-write
   STATUS mandatory
   DESCRIPTION
    "The date will be sent in the format dd/mm/yyyy"
    ::= { rsWSDSysParams 4 }


rsWSDLicenseID OBJECT-TYPE
   SYNTAX DisplayString (SIZE(1..80))
   ACCESS  read-only
   STATUS  mandatory
   DESCRIPTION
    "License ID used for license downgrade"
    ::= { rsServerDispatcher 70 }

rsWSDSendFakeArp OBJECT-TYPE
   SYNTAX  INTEGER {
        enable(1),
      	disable(2)
   }
   ACCESS  read-write
   STATUS  mandatory
   DESCRIPTION
        "Controls whether a backup will send a fake ARP, advertising the main box's
         interfaces and VIPs, when the main box returns to service."
--  DEFVAL  { disable }
   ::= { rsServerDispatcher 71 }

rsWSDNTP OBJECT IDENTIFIER ::= { rsServerDispatcher 72 }

rsWSDNTPServerAddr  OBJECT-TYPE
    SYNTAX  IpAddress
    ACCESS  read-write
    STATUS  mandatory
    DESCRIPTION
      "Server IP address."
	::=  { rsWSDNTP 1 }

rsWSDNTPInterval OBJECT-TYPE
    SYNTAX INTEGER
    ACCESS read-write
    STATUS mandatory
    DESCRIPTION
      "Time update interval."
	::=  { rsWSDNTP 2 }

rsWSDNTPStatus OBJECT-TYPE
    SYNTAX INTEGER {
      enable(1),
      disable(2)
    }
    ACCESS read-write
    STATUS mandatory
    DESCRIPTION
      "Enable status for NTP synchronization."
	::=  { rsWSDNTP 3 }

rsWSDNTPTimeZone OBJECT-TYPE
    SYNTAX DisplayString (SIZE(1..6))
    ACCESS read-write
    STATUS mandatory
    DESCRIPTION
      "Offset from Greenwich time (format hh:mm)."
	::=  { rsWSDNTP 4 }

rsWSDNTPPort OBJECT-TYPE
    SYNTAX INTEGER
    ACCESS read-write
    STATUS mandatory
    DESCRIPTION
      " A UDP Port number."
	::=  { rsWSDNTP 5 }


rsStatistics OBJECT IDENTIFIER ::= { rsServerDispatcher 73 }

rsPhysPortMirrorTable OBJECT-TYPE
    SYNTAX SEQUENCE OF RsPhysPortMirrorEntry
    ACCESS not-accessible
    STATUS mandatory
    DESCRIPTION
      "Table containing the list of copy ports "
    ::=  { rsServerDispatcher 74 } 

rsPhysPortMirrorEntry OBJECT-TYPE
    SYNTAX RsPhysPortMirrorEntry
    ACCESS not-accessible   
    STATUS  mandatory
    DESCRIPTION
       " The row definition for physical copy port table."
   INDEX { rsPhysPortMirrorSrcInf, rsPhysPortMirrorDstPort } 
    ::=  { rsPhysPortMirrorTable 1 }

RsPhysPortMirrorEntry ::= SEQUENCE {
    rsPhysPortMirrorSrcInf           INTEGER,
    rsPhysPortMirrorDstPort          INTEGER,
    rsPhysPortMirrorRxTx             INTEGER,	
    rsPhysPortMirrorRxBroadCast      INTEGER,
    rsPhysPortMirrorStatus           RowStatus,
    rsPhysPortMirrorBackupDstPort    INTEGER,
    rsPhysPortMirrorDstStatus        INTEGER,
    rsPhysPortMirrorBackupStatus     INTEGER,
    rsPhysPortMirrorActiveDstPort    INTEGER
  }

rsPhysPortMirrorSrcInf OBJECT-TYPE
    SYNTAX  INTEGER
    ACCESS  read-only
    STATUS  mandatory
    DESCRIPTION
      "The port under sniffing"
    ::= { rsPhysPortMirrorEntry 1 }

rsPhysPortMirrorDstPort OBJECT-TYPE
    SYNTAX  INTEGER
    ACCESS  read-only
    STATUS  mandatory
    DESCRIPTION
      "The destination port - the target sniffer port"
    ::= { rsPhysPortMirrorEntry 2 }

rsPhysPortMirrorRxTx OBJECT-TYPE
    SYNTAX INTEGER {
        copyRxTx(1),
        copyRxOnly(2),
        copyTxOnly (3) 
    }
    ACCESS  read-write
    STATUS  mandatory
    DESCRIPTION
       "Copy Rx/Tx traffic to the copy port ."
--  DEFVAL  { copyRxTx }
    ::=  { rsPhysPortMirrorEntry 3 }

rsPhysPortMirrorRxBroadCast OBJECT-TYPE
    SYNTAX INTEGER {
      enable(1),
      disable(2)
    }
    ACCESS  read-write
    STATUS  mandatory
    DESCRIPTION
      "The copy will include broadcast/unknown or not"
--  DEFVAL  { enable }
    ::=  { rsPhysPortMirrorEntry 4 }

rsPhysPortMirrorStatus OBJECT-TYPE
    SYNTAX  RowStatus
    ACCESS  read-write
    STATUS  mandatory
    DESCRIPTION
       "Used to delete an entry of this table."
    ::=  { rsPhysPortMirrorEntry 5 }

rsPhysPortMirrorBackupDstPort OBJECT-TYPE
    SYNTAX  INTEGER
    ACCESS  read-write
    STATUS  mandatory
    DESCRIPTION
      "The destination port - the target sniffer port"
    ::= { rsPhysPortMirrorEntry 6 }

rsPhysPortMirrorDstStatus OBJECT-TYPE
    SYNTAX INTEGER {
      active(1),
      portDown(2),
      checkIDSFail(3),
      checkIDSFailAndPortDown(4)
    }
    ACCESS  read-only
    STATUS  mandatory
    DESCRIPTION
      "The status of the dest-port according to the health check:
        active - the port is ok and can be used as a destination port for copy-port
        portDown - the port has been recognized as physically DOWN and therefore the traffic
                            will not be copied to this port until it will be recognized as physically UP
        checkIDSFail - the connectivty check of the monitoring port of the IDS failed and therefore 
                        the traffic will not be copied to this port until the check will recognize differently
        checkIDSFailAnd PortDown - both the connectivty check on the IDS failed and the port has 
                        been recognized as physically DOWN."
    ::=  { rsPhysPortMirrorEntry 7 }

rsPhysPortMirrorBackupStatus OBJECT-TYPE
    SYNTAX INTEGER {
      active(1),
      portDown(2),
      checkIDSFail(3),
      checkIDSFailAndPortDown(4),
      none(5)
    }
    ACCESS  read-only
    STATUS  mandatory
    DESCRIPTION
      " The status of the backup-port according to the health check:
        Active - the port is ok and can be used as a destination port for copy-port
        PortDown - the port has been recognized as physically DOWN and therefore the traffic
                            will not be copied to this port until it will be recognized as physically UP
        CheckIDSFail - the connectivty check of the monitoring port of the IDS failed and therefore 
                        the traffic will not be copied to this port until the check will recognize differently
        CheckIDSFailAnd PortDown - both the connectivty check on the IDS failed and the port has 
                        been recognized as physically DOWN
         None - for the case there is no defined backup port."
    ::=  { rsPhysPortMirrorEntry 8 }

rsPhysPortMirrorActiveDstPort OBJECT-TYPE
    SYNTAX INTEGER {
      dstPort(1),
      backupPort(2),
      none(3)
    }
    ACCESS  read-only
    STATUS  mandatory
    DESCRIPTION
      "The active dest-port at a certain time, if it is the dest-port or the backup-port or none of 
        them."
    ::=  { rsPhysPortMirrorEntry 9 }


rsCP OBJECT IDENTIFIER ::= { rsServerDispatcher 75 }

rsVWSD OBJECT IDENTIFIER ::= {rsServerDispatcher 76 }

rsVWSDDataPermissionsTable OBJECT-TYPE 
	SYNTAX SEQUENCE OF RsVWSDDataPermissionsTableEntry 
	ACCESS not-accessible 
	STATUS mandatory 
	DESCRIPTION 
    "Table containing the list of data items to which Farm administrators 
    of the virtual wsd has permissions." 
	::= { rsVWSD 1 } 

rsVWSDDataPermissionsTableEntry OBJECT-TYPE
   SYNTAX RsVWSDDataPermissionsTableEntry
   ACCESS not-accessible
   STATUS mandatory
   DESCRIPTION
       " The row definition for this table."
	INDEX { rsVWSDUserGroup, rsVWSDDataType, rsVWSDDataItems}
  ::= {rsVWSDDataPermissionsTable 1}

RsVWSDDataPermissionsTableEntry ::= SEQUENCE { 
	rsVWSDUserGroup    DisplayString, 
	rsVWSDDataType     OCTET STRING, 
	rsVWSDDataItems    OCTET STRING, 
  rsVWSDDataStatus   RowStatus
} 

rsVWSDUserGroup OBJECT-TYPE 
	SYNTAX DisplayString (SIZE(1..30))
    	ACCESS  read-only
    	STATUS  mandatory
    	DESCRIPTION
    		"The Group of users for whom data permission is given."
	::= { rsVWSDDataPermissionsTableEntry 1} 

rsVWSDDataType OBJECT-TYPE 
	SYNTAX OCTET STRING (SIZE(1..80))
	ACCESS read-only 
	STATUS mandatory 
	DESCRIPTION 
		"Holds a string that identifies the table of the index by which the 
    data filtering is done." 
	::= { rsVWSDDataPermissionsTableEntry 2}

rsVWSDDataItems OBJECT-TYPE 
	SYNTAX OCTET STRING (SIZE(1..80))
	ACCESS read-only 
	STATUS mandatory 
	DESCRIPTION 
		"The Value(s) of the index column for the data item to which permission is set." 
	::= { rsVWSDDataPermissionsTableEntry 3}

rsVWSDDataStatus OBJECT-TYPE
  SYNTAX RowStatus
  ACCESS read-write
  STATUS mandatory
  DESCRIPTION 
    "The row status for the table"
  ::= { rsVWSDDataPermissionsTableEntry 4}

rsWSDManagementPorts OBJECT-TYPE
    SYNTAX INTEGER {
        outOfPath(1),
        switch(2),
        promiscuous(3)
    }
    ACCESS  read-write
    STATUS  mandatory
    DESCRIPTION "The entry indicates the functionality of the device. 
    outOfPath implies that the device will be able to have a management 
    port, and the rest of the ports will be used for sniffing. switch 
    implies the regular functionality of the device (router or VLAN). 
    promiscuous will have static port mappings for forwarding." 
--  DEFVAL  {switch} 
    ::= { rsServerDispatcher 77 }

rsWSDManagementPortsTable OBJECT-TYPE
    SYNTAX SEQUENCE OF RsWSDManagementPortsEntry
    ACCESS not-accessible
    STATUS  mandatory
    DESCRIPTION
      "Table containing the operation of each port.."
    ::= { rsServerDispatcher 78 }

rsWSDManagementPortsEntry OBJECT-TYPE
    SYNTAX RsWSDManagementPortsEntry
    ACCESS not-accessible
    STATUS mandatory
    DESCRIPTION
       "The row definition for this table."
    INDEX { rsWSDPortIndex }
    ::=  { rsWSDManagementPortsTable 1 }

RsWSDManagementPortsEntry ::= SEQUENCE {
    rsWSDPortIndex INTEGER,
    rsWSDPortOperation INTEGER
}

rsWSDPortIndex OBJECT-TYPE
    SYNTAX INTEGER
    ACCESS read-only
    STATUS mandatory
    DESCRIPTION
      "The index of the physical ports."
    ::=  { rsWSDManagementPortsEntry 1 }

rsWSDPortOperation OBJECT-TYPE
    SYNTAX INTEGER {
        management (1),
        sniffer (2)
    }
    ACCESS read-only
    STATUS mandatory
    DESCRIPTION
      "The operation of the particular port."
    DEFVAL { sniffer }
    ::=  { rsWSDManagementPortsEntry 2 }

rsCCK  OBJECT IDENTIFIER ::= { rsServerDispatcher 79 }

rsWSDSshParams OBJECT IDENTIFIER ::= {rsServerDispatcher 80 }

rsWSDSshPort OBJECT-TYPE
    SYNTAX  INTEGER
    ACCESS  read-write
    STATUS  mandatory
    DESCRIPTION
      "The SSH Server Port."
--  DEFVAL  { 22 }
    ::=  {rsWSDSshParams 1}


rsWSDSshStatus OBJECT-TYPE
   SYNTAX  INTEGER {
        enable(1),
      	disable(2)
   }
   ACCESS  read-write
   STATUS  mandatory
   DESCRIPTION
        "SSH Status. Enable/Disable SSH operation."
--  DEFVAL  { disable }
   ::= { rsWSDSshParams 2 }



rsWSDHttpsParams OBJECT IDENTIFIER ::= {rsServerDispatcher 81 }

rsWSDHttpsPort OBJECT-TYPE
    SYNTAX  INTEGER
    ACCESS  read-write
    STATUS  mandatory
    DESCRIPTION
      "The Https Server Port."
--  DEFVAL  { 443 }
    ::=  {rsWSDHttpsParams 1}


rsWSDHttpsStatus OBJECT-TYPE
   SYNTAX  INTEGER {
        enable(1),
      	disable(2)
   }
   ACCESS  read-write
   STATUS  mandatory
   DESCRIPTION
        "Https Status. Enable/Disable Https operation."
--  DEFVAL  { disable }
   ::= { rsWSDHttpsParams 2 }


rsWSDStaticForwardingTable OBJECT-TYPE
    SYNTAX SEQUENCE OF RsWSDStaticForwardingEntry
    ACCESS not-accessible
    STATUS  mandatory
    DESCRIPTION
      "Table containing the static fowarding configration."
    ::= { rsServerDispatcher 82 }

rsWSDStaticForwardingEntry OBJECT-TYPE
    SYNTAX RsWSDStaticForwardingEntry
    ACCESS not-accessible
    STATUS mandatory
    DESCRIPTION
       "The row definition for this table."
    INDEX { rsWSDStaticSourcePort }
    ::=  { rsWSDStaticForwardingTable 1 }

RsWSDStaticForwardingEntry ::= SEQUENCE {
    rsWSDStaticSourcePort INTEGER,
    rsWSDStaticDestinationPort INTEGER,
    rsWSDStaticPortOperation INTEGER,
    rsWSDStaticStatus RowStatus
}

rsWSDStaticSourcePort OBJECT-TYPE
    SYNTAX INTEGER
    ACCESS read-only
    STATUS mandatory
    DESCRIPTION
      "The index of the source port."
    ::=  { rsWSDStaticForwardingEntry 1 }

rsWSDStaticDestinationPort OBJECT-TYPE
    SYNTAX INTEGER
    ACCESS read-write
    STATUS mandatory
    DESCRIPTION
      "The destination port."
    ::=  { rsWSDStaticForwardingEntry 2 }

rsWSDStaticPortOperation OBJECT-TYPE
    SYNTAX INTEGER {
        process(1),
        forward(2)
    }
    ACCESS read-write
    STATUS mandatory
    DESCRIPTION
      "The operation for the specific port. process implies that the packets 
      will be processed (analyzed, filtered etc.) prior to being forwarded. 
      forward implies that the packets will be forwarded."
    ::=  { rsWSDStaticForwardingEntry 3 }

rsWSDStaticStatus OBJECT-TYPE
    SYNTAX RowStatus
    ACCESS read-write
    STATUS mandatory
    DESCRIPTION
       "This variable indicates the administrative status of this entry.
        Used to delete an entry of this table."
    ::=  { rsWSDStaticForwardingEntry 4 }



rsRadiusServer OBJECT IDENTIFIER ::= {rsServerDispatcher 83 }


rsRadiusMainServerAddr OBJECT-TYPE
    SYNTAX IpAddress
    ACCESS  read-write
    STATUS  mandatory
    DESCRIPTION
      "The IP Address of the radius main server."
    ::= {rsRadiusServer 1}

rsRadiusMainServerPort OBJECT-TYPE
    SYNTAX INTEGER
    ACCESS  read-write
    STATUS  mandatory
    DESCRIPTION
       "The port on which the radius main server listens"
--  DEFVAL { 1812 }
    ::= {rsRadiusServer 2}

rsRadiusMainServerSecret OBJECT-TYPE
    SYNTAX  DisplayString (SIZE(0..20))
    ACCESS  read-write
    STATUS  mandatory
    DESCRIPTION
       "The key with which the user's password is encrypted."
    ::= {rsRadiusServer 3}

rsRadiusBackupServerAddr OBJECT-TYPE
    SYNTAX IpAddress
    ACCESS  read-write
    STATUS  mandatory
    DESCRIPTION
      "The IP Address of the backup radius server."
    ::= {rsRadiusServer 4}

rsRadiusBackupServerPort OBJECT-TYPE
    SYNTAX INTEGER
    ACCESS  read-write
    STATUS  mandatory
    DESCRIPTION
       "The port on which the radius backup server listens"
--  DEFVAL { 1812 }
    ::= {rsRadiusServer 5}

rsRadiusBackupServerSecret OBJECT-TYPE
    SYNTAX DisplayString (SIZE(0..20))
    ACCESS  read-write
    STATUS  mandatory
    DESCRIPTION
       "The key with which the user's password is encrypted."
    ::= {rsRadiusServer 6}

rsAuthenticationMethod OBJECT-TYPE
    SYNTAX INTEGER {
        userTable(1),
        radius(2),
        combined(3)}
    ACCESS  read-write
    STATUS  mandatory
    DESCRIPTION
      "Radius authentication method."
--  DEFVAL { 1 }
    ::=  {rsRadiusServer 7}

rsRadiusServerTimeout OBJECT-TYPE
    SYNTAX  INTEGER (1..10)
    ACCESS  read-write
    STATUS  mandatory
    DESCRIPTION
      "Number of seconds to wait for reply from the radius server before 
	   retransmitting the request."
--  DEFVAL  { 1 }
    ::=  {rsRadiusServer 8}

rsRadiusServerRetries OBJECT-TYPE
    SYNTAX  INTEGER (1..5)
    ACCESS  read-write
    STATUS  mandatory
    DESCRIPTION
      "Minimal number of unanswered request attempts before considering the radius
	   server disconnected."
--  DEFVAL  { 2 }
    ::=  {rsRadiusServer 9}


rsIfTable OBJECT-TYPE
    SYNTAX SEQUENCE OF RsIfEntry
    ACCESS not-accessible
    STATUS  mandatory
    DESCRIPTION
      "Device physical interface table"
    ::=  {rsServerDispatcher 84}

rsIfEntry OBJECT-TYPE
    SYNTAX RsIfEntry
    ACCESS not-accessible
    STATUS  mandatory
    DESCRIPTION
       "The row definition for this table"
   INDEX { rsIfIndex }
    ::=  {rsIfTable 1}

RsIfEntry ::= SEQUENCE {
  rsIfIndex         INTEGER,
  rsIfSpeed         INTEGER,
  rsIfDuplex        INTEGER,
  rsIfAutoNegotiate INTEGER,
  rsIfRowStatus     RowStatus
  }

rsIfIndex OBJECT-TYPE
    SYNTAX  INTEGER
    ACCESS read-only
    STATUS  mandatory
    DESCRIPTION
      "interface's index"
    ::=  {rsIfEntry 1}

rsIfSpeed OBJECT-TYPE
    SYNTAX  INTEGER {
       eth10(1),
       fe100(2),
       ge1000(3)
    }
    ACCESS read-write
    STATUS  mandatory
    DESCRIPTION
      "interface's speed"
    ::=  {rsIfEntry 2}

rsIfDuplex OBJECT-TYPE
    SYNTAX  INTEGER {
       half(1),
       full(2)
    }
    ACCESS read-write
    STATUS  mandatory
    DESCRIPTION
      "interface's duplex"
    ::=  {rsIfEntry 3}

rsIfAutoNegotiate OBJECT-TYPE
    SYNTAX  INTEGER {
       on(1),
       off(2)
    }
    ACCESS read-write
    STATUS  mandatory
    DESCRIPTION
      "interface's autonegotiation status"
    ::=  {rsIfEntry 4}

rsIfRowStatus OBJECT-TYPE
    SYNTAX  RowStatus
    ACCESS  read-write
    STATUS  mandatory
    DESCRIPTION
      "interface's rowstatus"
    ::=  {rsIfEntry 5}

rsWSDDeviceOperationMode OBJECT-TYPE
    SYNTAX INTEGER {
        trafficRedirection(1),
        staticForwarding(2)
    }
    ACCESS  read-write
    STATUS  mandatory
    DESCRIPTION 
      "Device operation mode: redirection (load balancing) or static forwarding (IDS, BWM)."
    DEFVAL  {trafficRedirection}
    ::= {rsServerDispatcher 85}

rsWSDVersionStatus OBJECT-TYPE
    SYNTAX INTEGER {
        open(1),
        final(2)
    }
    ACCESS  read-only
    STATUS  mandatory
    DESCRIPTION 
      "Indicates whether the current version is closed or still open (under development)."
    ::= {rsServerDispatcher 86}
 
    
-- Enterprise-specific traps for RADWARE
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsWSDConnectionLimitReached TRAP-TYPE
   ENTERPRISE rsServerDispatcher
   VARIABLES { rndErrorDesc, rndErrorSeverity }
   DESCRIPTION
      "This warning is generated when the users connection limit of an application or a physical server is reached."
   ::= 1

rsWSDReadyForShutDown  TRAP-TYPE
       ENTERPRISE  rsServerDispatcher
       VARIABLES   { rndErrorDesc, rndErrorSeverity }
       DESCRIPTION
             "This warning is generated when all the clients sessions of an application or a physical server are finished and so, the application or server are ready to be shut down."
       ::=  2

rsWSDIllegalReport TRAP-TYPE
       ENTERPRISE  rsServerDispatcher
       VARIABLES   { rndErrorDesc, rndErrorSeverity }
       DESCRIPTION
             "This warning is generated when an LRP message arrives with illegal information."
       ::= 3

rsWSDRemoteWSDUnavailable TRAP-TYPE
       ENTERPRISE  rsServerDispatcher
       VARIABLES   { rndErrorDesc, rndErrorSeverity }
       DESCRIPTION
             "This warning is generated when a remote WSD is in full capacity, not in service or disabled. This server is then unavailable"
       ::= 4

rsWSDCapacityLimitReached TRAP-TYPE
       ENTERPRISE  rsServerDispatcher
       VARIABLES   { rndErrorDesc, rndErrorSeverity }
       DESCRIPTION
             "This warning is generated when WSD capacity limit is reached."
       ::= 5

rsWSDStatusMonitoring TRAP-TYPE
       ENTERPRISE  rsServerDispatcher
       VARIABLES   { rndErrorDesc, rndErrorSeverity }
       DESCRIPTION
             " This warning is generated for unavailable SNMP parameter from a server."
       ::= 6

rsWSDWrongPassword TRAP-TYPE
       ENTERPRISE  rsServerDispatcher
       VARIABLES   { rndErrorDesc, rndErrorSeverity }
       DESCRIPTION
             " This warning is generated when a wrong software download password is provided."
       ::= 7

rsWSDInternalTableOverflow  TRAP-TYPE
         ENTERPRISE  rsServerDispatcher
         VARIABLES   { rndErrorDesc, rndErrorSeverity }
         DESCRIPTION
             "This warning is generated when there are no more free entries in the table."
     ::=  8

rsWSDServerUp  TRAP-TYPE
         ENTERPRISE  rsServerDispatcher
         VARIABLES   { rndErrorDesc, rndErrorSeverity }
         DESCRIPTION
             "This informational trap is sent when a server correctly responds to a connectivity check for the first time."
     ::=  9

rsWSDPoliciesUpdated TRAP-TYPE
         ENTERPRISE rsServerDispatcher
         VARIABLES { rndErrorDesc, rndErrorSeverity }
         DESCRIPTION
             "This informational trap is sent when the rule policies are
             updated."
     ::=  10

rsWSDIntrusionDetected TRAP-TYPE
         ENTERPRISE rsServerDispatcher
         VARIABLES { rndErrorDesc, rndErrorSeverity }
         DESCRIPTION
             "This informational trap is sent when an intrusion is detected."
     ::=  11

   END
