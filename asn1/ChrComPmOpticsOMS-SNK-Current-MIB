ChrComPmOpticsOMS-SNK-Current-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmOptics				FROM  Chromatis-MIB
	chrComIfifIndex					FROM  ChrComIfifTable-MIB
	TruthValue				FROM  ChrTyp-MIB
	Gauge32				FROM  SNMPv2-SMI;

-- chrComPmOpticsOMS-SNK-Current Table

chrComPmOpticsOMS-SNK-CurrentTable		OBJECT-TYPE
	SYNTAX		SEQUENCE OF ChrComPmOpticsOMS-SNK-CurrentEntry
	MAX-ACCESS	not-accessible
	STATUS		current
	DESCRIPTION
	""
	::= { chrComPmOptics 7}

chrComPmOpticsOMS-SNK-CurrentEntry		OBJECT-TYPE
	SYNTAX		ChrComPmOpticsOMS-SNK-CurrentEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "OMS-SNK-Current"
	::= { chrComPmOpticsOMS-SNK-CurrentTable  1 }

ChrComPmOpticsOMS-SNK-CurrentEntry  ::=
	SEQUENCE  {
	chrComPmOpticsSuspectedIntrvl		TruthValue,
	chrComPmOpticsElapsedTime		Unsigned32	(0..4294967295),
	chrComPmOpticsSuppressedIntrvls	Gauge32			(0..4294967295),
	chrComPmOpticsORS			Gauge32			(0..4294967295),
	chrComPmOpticsSES			Gauge32			(0..4294967295),
	chrComPmOpticsUAS			Gauge32			(0..4294967295),
	chrComPmOpticsMean			Integer32	(0..2147483647),
	chrComPmOpticsMax			Integer32	(0..2147483647),
	chrComPmOpticsMin			Integer32	(0..2147483647),
	chrComPmOpticsSD			Integer32	(0..2147483647),
	chrComPmOpticsThresholdProfIndex	Unsigned32	(0..4294967295),
	chrComPmOpticsResetCountersAction	TruthValue
}

chrComPmOpticsSuspectedIntrvl 	OBJECT-TYPE
	SYNTAX		TruthValue
	MAX-ACCESS 	read-only
	STATUS 		current
	DESCRIPTION
	"a flag marking the validity of the entry data"
	::= { chrComPmOpticsOMS-SNK-CurrentEntry  1 }

chrComPmOpticsElapsedTime 	OBJECT-TYPE
	SYNTAX		Unsigned32	(0..4294967295)
	MAX-ACCESS 	read-only
	STATUS 		current
	DESCRIPTION
	"measurment duration, in 0.01 seconds"
	::= { chrComPmOpticsOMS-SNK-CurrentEntry  2 }

chrComPmOpticsSuppressedIntrvls 	OBJECT-TYPE
	SYNTAX		Gauge32			(0..4294967295)
	MAX-ACCESS 	read-only
	STATUS 		current
	DESCRIPTION
	"invalid for first version. indicates how many all-zero periods have passed."
	::= { chrComPmOpticsOMS-SNK-CurrentEntry  3 }

chrComPmOpticsORS 	OBJECT-TYPE
	SYNTAX		Gauge32			(0..4294967295)
	MAX-ACCESS 	read-only
	STATUS 		current
	DESCRIPTION
	""
	::= { chrComPmOpticsOMS-SNK-CurrentEntry  4 }

chrComPmOpticsSES 	OBJECT-TYPE
	SYNTAX		Gauge32			(0..4294967295)
	MAX-ACCESS 	read-only
	STATUS 		current
	DESCRIPTION
	""
	::= { chrComPmOpticsOMS-SNK-CurrentEntry  5 }

chrComPmOpticsUAS 	OBJECT-TYPE
	SYNTAX		Gauge32			(0..4294967295)
	MAX-ACCESS 	read-only
	STATUS 		current
	DESCRIPTION
	""
	::= { chrComPmOpticsOMS-SNK-CurrentEntry  6 }

chrComPmOpticsMean 	OBJECT-TYPE
	SYNTAX		Integer32	(0..2147483647)
	MAX-ACCESS 	read-only
	STATUS 		current
	DESCRIPTION
	""
	::= { chrComPmOpticsOMS-SNK-CurrentEntry  7 }

chrComPmOpticsMax 	OBJECT-TYPE
	SYNTAX		Integer32	(0..2147483647)
	MAX-ACCESS 	read-only
	STATUS 		current
	DESCRIPTION
	""
	::= { chrComPmOpticsOMS-SNK-CurrentEntry  8 }

chrComPmOpticsMin 	OBJECT-TYPE
	SYNTAX		Integer32	(0..2147483647)
	MAX-ACCESS 	read-only
	STATUS 		current
	DESCRIPTION
	""
	::= { chrComPmOpticsOMS-SNK-CurrentEntry  9 }

chrComPmOpticsSD 	OBJECT-TYPE
	SYNTAX		Integer32	(0..2147483647)
	MAX-ACCESS 	read-only
	STATUS 		current
	DESCRIPTION
	""
	::= { chrComPmOpticsOMS-SNK-CurrentEntry  10 }

chrComPmOpticsThresholdProfIndex 	OBJECT-TYPE
	SYNTAX		Unsigned32	(0..4294967295)
	MAX-ACCESS 	read-write
	STATUS 		current
	DESCRIPTION
	""
	::= { chrComPmOpticsOMS-SNK-CurrentEntry  11 }

chrComPmOpticsResetCountersAction 	OBJECT-TYPE
	SYNTAX		TruthValue
	MAX-ACCESS 	read-write
	STATUS 		current
	DESCRIPTION
	""
	::= { chrComPmOpticsOMS-SNK-CurrentEntry  12 }


END
