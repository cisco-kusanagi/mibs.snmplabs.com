-- $Id: it-isis-mib.mib,v 1.1 2000/07/25 14:30:22 sse Exp $
ITOUCH-ISIS-MIB DEFINITIONS ::= BEGIN

   IMPORTS
           Counter, IpAddress
                   FROM RFC1155-SMI
           OBJECT-TYPE
                   FROM RFC-1212
           iTouch
                   FROM ITOUCH-MIB;

           ExistState ::= INTEGER
                             {
                                off(1),
                                on(2)
                             }
              -- Type used in row creation and deletion.

           SupportedProtocol ::= INTEGER
                             {
                               iso8473(129),
                               ip(204)
                             }
             -- Types of network protocol supported by Integrated ISIS.
             -- The values for ISO8473 and IP are those registered for
             -- these protocols in ISO TR9577.

xIsis OBJECT IDENTIFIER ::= { iTouch 26 }

   xIsisSystem    OBJECT IDENTIFIER ::= { xIsis 1 }
   xIsisCirc      OBJECT IDENTIFIER ::= { xIsis 2 }
   xIsisISAdj     OBJECT IDENTIFIER ::= { xIsis 3 }
   xIsisESAdj     OBJECT IDENTIFIER ::= { xIsis 4 }
   xIsisReachAddr OBJECT IDENTIFIER ::= { xIsis 5 }
   xIsisCLNPDest  OBJECT IDENTIFIER ::= { xIsis 7 }

            -- This is a MIB module for all iTouch Communications systems that
            -- implement ISIS.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


-- The System Table

-- The System Table contains one row for each separate instance
-- of the Integrated IS-IS protocol.

xIsisSysTable OBJECT-TYPE
   SYNTAX SEQUENCE OF XIsisSysEntry
   ACCESS not-accessible
   STATUS mandatory
   DESCRIPTION
       "The set of instances of the Integrated IS-IS protocol
       existing on the system."
   ::= { xIsisSystem 1 }

xIsisSysEntry OBJECT-TYPE
   SYNTAX XIsisSysEntry
   ACCESS not-accessible
   STATUS mandatory
   DESCRIPTION
       "Each row defines information specific to a single
       instance of the protocol existing on the system."
   REFERENCE "ANSI {ISIS.poi cLNSISISBasic-P (1)}"
   INDEX { xIsisSysInstance }
   ::= { xIsisSysTable 1 }

XIsisSysEntry ::=
   SEQUENCE {
      xIsisSysInstance
         INTEGER,
      xIsisSysExistState
         INTEGER,
      xIsisSysVersion
         INTEGER,
      xIsisSysType
         INTEGER,
      xIsisSysNET
         OCTET STRING,
      xIsisSysMaxPathSplits
         INTEGER,
      xIsisSysMinLSPTransInt
         INTEGER,
      xIsisSysMaxLSPGenInt
         INTEGER,
      xIsisSysMinBroadLSPTransInt
         INTEGER,
      xIsisSysCompSNPInt
         INTEGER,
      xIsisSysOrigL1LSPBuffSize
         INTEGER,
      xIsisSysMaxAreaAddr
         INTEGER,
      xIsisSysMinLSPGenInt
         INTEGER,
      xIsisSysPollESHelloRate
         INTEGER,
      xIsisSysPartSNPInt
         INTEGER,
      xIsisSysWaitTime
         INTEGER,
      xIsisSysDRISISHelloTimer
         INTEGER,
      xIsisSysOperState
         INTEGER,
      xIsisSysL1State
         INTEGER,
      xIsisSysCorrLSPs
         Counter,
      xIsisSysL1LSPDbaseOloads
         Counter,
      xIsisSysManAddrsDropFromArea
         Counter,
      xIsisSysAttmptsToExMaxSeqNum
         Counter,
      xIsisSysSeqNumSkips
         Counter,
      xIsisSysOwnLSPPurges
         Counter,
      xIsisSysIDFieldLenMismatches
         Counter,
      xIsisSysMaxAreaMis
         Counter,
      xIsisSysOrigL2LSPBuffSize
         INTEGER,
      xIsisSysL2State
         INTEGER,
      xIsisSysL2LSPDbaseOloads
         Counter,
      xIsisSysMaxAreaCheck
         INTEGER
   }


xIsisSysInstance OBJECT-TYPE
   SYNTAX INTEGER
   ACCESS read-only
   STATUS mandatory
   DESCRIPTION
       "The unique identifier of the Integrated IS-IS instance
       to which this row corresponds. This object follows the
       index behaviour."
   ::= { xIsisSysEntry 1 }

xIsisSysExistState OBJECT-TYPE
   SYNTAX INTEGER {
             off(1),
             on(2)
          }
   ACCESS read-only
   STATUS mandatory
   DESCRIPTION
       "The validity of this instance of the Integrated IS-IS
       protocol. This object follows the existenceState
       behaviour."
   ::= { xIsisSysEntry 2 }

xIsisSysVersion OBJECT-TYPE
   SYNTAX INTEGER
   ACCESS read-only
   STATUS mandatory
   DESCRIPTION
       "The version number of the IS-IS protocol to which this
       instance conforms. This value must be set by the
       implementation when the row is valid."
   REFERENCE "ANSI {ISIS.aoi version (1)}"
   ::= { xIsisSysEntry 3 }

xIsisSysType OBJECT-TYPE
   SYNTAX   INTEGER {
               level1IS(1),
               level2IS(2)
            }
   ACCESS read-write
   STATUS mandatory
   DESCRIPTION
       "The type of this instance of the Integrated IS-IS
       protocol. This object follows the
       replaceOnlyWhileDisabled behaviour."
   REFERENCE "ANSI {ISIS.aoi iSType (2)}"
   ::= { xIsisSysEntry 4 }

xIsisSysNET OBJECT-TYPE
   SYNTAX OCTET STRING
   ACCESS read-only
   STATUS mandatory
   DESCRIPTION
       "The ID for this instance of the Integrated IS-IS
       protocol. This value is appended to each of the
       instance's area addresses to form the Network Entity
       Titles valid for this instance. The derivation of a value
       for this object is implementation-specific. Some
       implementations may assign values and not permit write
       access, others may require the value to be set manually."
   REFERENCE "ANSI {ISIS.aoi systemId (119)}"
   ::= { xIsisSysEntry 5 }

xIsisSysMaxPathSplits OBJECT-TYPE
   SYNTAX INTEGER (1..32)
   ACCESS read-write
   STATUS mandatory
   DESCRIPTION
       "Maximum number of paths with equal routing metric value
       which it is permitted to split between. This object
       follows the replaceOnlyWhileDisabled behaviour."
   REFERENCE "ANSI {ISIS.aoi maximumPathSplits (3)}"
   ::= { xIsisSysEntry 6 }

xIsisSysMinLSPTransInt OBJECT-TYPE
   SYNTAX INTEGER (1..65535)
   ACCESS read-write
   STATUS mandatory
   DESCRIPTION
       "Minimum interval, in seconds, between re-transmission of
       an LSP. This object follows the resettingTimer
       behaviour."
   REFERENCE "ANSI {ISIS.aoi minimumLSPTransmissionInterval (5)}"
   ::= { xIsisSysEntry 7 }

xIsisSysMaxLSPGenInt OBJECT-TYPE
   SYNTAX INTEGER (1..65535)
   ACCESS read-write
   STATUS mandatory
   DESCRIPTION
       "Maximum interval, in seconds, between generated LSPs by
       this instance. This object follows the resettingTimer
       behaviour."
   REFERENCE "ANSI {ISIS.aoi maximumLSPGenerationInterval (6)}"
   ::= { xIsisSysEntry 8 }

xIsisSysMinBroadLSPTransInt OBJECT-TYPE
   SYNTAX INTEGER (1..65535)
   ACCESS read-write
   STATUS mandatory
   DESCRIPTION
       "Minimum interval, in milliseconds, between transmission
       of LSPs on a broadcast circuit. This object follows the
       resettingTimer behaviour. This timer shall be capable of
       a resolution not coarser than 10 milliseconds."
   REFERENCE "ANSI {ISIS.aoi
      minimumBroadcastLSPTransmissionInterval (7)}"
   ::= { xIsisSysEntry 9 }

xIsisSysCompSNPInt OBJECT-TYPE
   SYNTAX INTEGER (1..600)
   ACCESS read-write
   STATUS mandatory
   DESCRIPTION
       "Interval, in seconds, between generation of Complete
       Sequence Numbers PDUs by a designated Intermediate System
       on a broadcast circuit. This object follows the
       resettingTimer behaviour."
   REFERENCE "ANSI {ISIS.aoi completeSNPInterval (8)}"
   ::= { xIsisSysEntry 10 }

xIsisSysOrigL1LSPBuffSize OBJECT-TYPE
   SYNTAX INTEGER (512..1492)
   ACCESS read-write
   STATUS mandatory
   DESCRIPTION
       "The maximum size of Level 1 LSPs and SNPs originated by
       this instance. This object follows the
       replaceOnlyWhileDisabled behaviour."
   REFERENCE "ANSI {ISIS.aoi originatingL1LSPBufferSize (9)}"
   ::= { xIsisSysEntry 11 }

xIsisSysMaxAreaAddr OBJECT-TYPE
   SYNTAX INTEGER (0..254)
   ACCESS read-write
   STATUS mandatory
   DESCRIPTION
       "The maximum number of area addresses to be permitted for
       the area in which this instance exists. Note that all
       Intermediate Systems in the same area must have the same
       value configured for this attribute if correct operation
       is to be assumed. This object follows the
       replaceOnlyWhileDisabled behaviour."
   REFERENCE "ANSI {ISIS.aoi maximumAreaAddresses (4)}"
   ::= { xIsisSysEntry 12 }

xIsisSysMinLSPGenInt OBJECT-TYPE
   SYNTAX INTEGER (1..65535)
   ACCESS read-write
   STATUS mandatory
   DESCRIPTION
       "Minimum interval, in seconds, between successive
       generation of LSPs with the same LSPID by this instance.
       This object follows the resettingTimer behaviour."
   REFERENCE "ANSI {ISIS.aoi minimumLSPGenerationInterval (11)}"
   ::= { xIsisSysEntry 13 }

xIsisSysPollESHelloRate OBJECT-TYPE
   SYNTAX INTEGER (1..65535)
   ACCESS read-write
   STATUS mandatory
   DESCRIPTION
       "The value, in seconds, to be used for the suggested ES
       configuration  timer in ISH PDUs when soliciting the ES
       configuration."
   REFERENCE "ANSI {ISIS.aoi pollESHelloRate (13)}"
   ::= { xIsisSysEntry 14 }

xIsisSysPartSNPInt OBJECT-TYPE
   SYNTAX INTEGER (1..65535)
   ACCESS read-write
   STATUS mandatory
   DESCRIPTION
       "Minimum interval between sending Partial Sequence Number
       PDUs. This object follows the resettingTimer behaviour."
   REFERENCE "ANSI {ISIS.aoi partialSNPInterval (14)}"
   ::= { xIsisSysEntry 15 }

xIsisSysWaitTime OBJECT-TYPE
   SYNTAX INTEGER (1..65535)
   ACCESS read-write
   STATUS mandatory
   DESCRIPTION
       "Number of seconds to delay in waiting state before
       entering on state. This object follows the resettingTimer
       behaviour."
   REFERENCE "ANSI {ISIS.aoi waitingTime (15)}"
   ::= { xIsisSysEntry 16 }

xIsisSysDRISISHelloTimer OBJECT-TYPE
   SYNTAX INTEGER (1..65535)
   ACCESS read-write
   STATUS mandatory
   DESCRIPTION
       "The interval, in seconds, between the generation of IIH
       PDUs by the designated IS on a LAN. This object follows
       the resettingTimer behaviour."
   REFERENCE "ANSI {ISIS.aoi dRISISHelloTimer (16)}"
   ::= { xIsisSysEntry 17 }

xIsisSysOperState OBJECT-TYPE
   SYNTAX INTEGER {
		off(1),
		on(2)
		}
   ACCESS read-write
   STATUS mandatory
   DESCRIPTION
       "The operational state of this instance of the Integrated
       IS-IS protocol. Setting this object to the value on when
       its current value is off enables operation of this
       instance of the Integrated IS-IS protocol."
   ::= { xIsisSysEntry 18 }

xIsisSysL1State OBJECT-TYPE
   SYNTAX INTEGER {
		off(1),
		on(2),
		waiting(3)
		}
   ACCESS read-only
   STATUS mandatory
   DESCRIPTION
       "The state of the Level 1 database."
   REFERENCE "ANSI {ISIS.aoi l1State (17)}"
   ::= { xIsisSysEntry 19 }

xIsisSysCorrLSPs OBJECT-TYPE
   SYNTAX Counter
   ACCESS read-only
   STATUS mandatory
   DESCRIPTION
       "Number of corrupted LSPs detected."
   REFERENCE "ANSI {ISIS.aoi corruptedLSPsDetected (19)}"
   ::= { xIsisSysEntry 20 }

xIsisSysL1LSPDbaseOloads OBJECT-TYPE
   SYNTAX Counter
   ACCESS read-only
   STATUS mandatory
   DESCRIPTION
       "Number of times the LSP L1 database has become
       overloaded."
   REFERENCE "ANSI {ISIS.aoi lSPL1DatabaseOverloads (20)}"
   ::= { xIsisSysEntry 21 }

xIsisSysManAddrsDropFromArea OBJECT-TYPE
   SYNTAX Counter
   ACCESS read-only
   STATUS mandatory
   DESCRIPTION
       "Number of times a manual address has been dropped from
       the area."
   REFERENCE "ANSI {ISIS.aoi manualAddressesDroppedFromArea (21)}"
   ::= { xIsisSysEntry 22 }

xIsisSysAttmptsToExMaxSeqNum OBJECT-TYPE
   SYNTAX Counter
   ACCESS read-only
   STATUS mandatory
   DESCRIPTION
       "Number of times the IS has attempted to exceed the
       maximum sequence number."
   REFERENCE "ANSI {ISIS.aoi attemptsToExceedmaximumSequenceNumber (22)}"
   ::= { xIsisSysEntry 23 }

xIsisSysSeqNumSkips OBJECT-TYPE
   SYNTAX Counter
   ACCESS read-only
   STATUS mandatory
   DESCRIPTION
       "Number of times a sequence number skip has occurred."
   REFERENCE "ANSI {ISIS.aoi sequenceNumberSkips (23)}"
   ::= { xIsisSysEntry 24 }

xIsisSysOwnLSPPurges OBJECT-TYPE
   SYNTAX Counter
   ACCESS read-only
   STATUS mandatory
   DESCRIPTION
       "Number of times a zero-aged copy of the system's own LSP
       is received from some other node."
   REFERENCE "ANSI {ISIS.aoi ownLSPPurges (24)}"
   ::= { xIsisSysEntry 25 }

xIsisSysIDFieldLenMismatches OBJECT-TYPE
   SYNTAX Counter
   ACCESS read-only
   STATUS mandatory
   DESCRIPTION
       "Number of times a PDU is received with a different value
       for ID field length to that of the receiving system."
   REFERENCE "ANSI {ISIS.aoi iDFieldLengthMismatches (25)}"
   ::= { xIsisSysEntry 26 }

xIsisSysMaxAreaMis OBJECT-TYPE
   SYNTAX Counter
   ACCESS read-only
   STATUS mandatory
   DESCRIPTION
       "Number of times a PDU is received with a different value
       for MaximumAreaAddresses from that of the receiving
       system."
   REFERENCE "ANSI {ISIS.aoi MaximumAreaAddressesMismatches (118)}"
   ::= { xIsisSysEntry 27 }

-- The following objects map those from the cLNSISISLevel2-P
-- Package

xIsisSysOrigL2LSPBuffSize OBJECT-TYPE
   SYNTAX INTEGER (512..1492)
   ACCESS read-write
   STATUS mandatory
   DESCRIPTION
       "The maximum size of Level 2 LSPs and SNPs originated by
       this system. This object follows the
       replaceOnlyWhileDisabled behaviour."
   REFERENCE "ANSI {ISIS.aoi originatingL2LSPBufferSize (26)}"
   ::= { xIsisSysEntry 28 }

xIsisSysL2State OBJECT-TYPE
   SYNTAX INTEGER 	{
		off(1),
		on(2),
		waiting(3)
		}
   ACCESS read-only
   STATUS mandatory
   DESCRIPTION
       "The state of the Level 2 database."
   REFERENCE "ANSI {ISIS.aoi l2State (28)}"
   ::= { xIsisSysEntry 29 }

xIsisSysL2LSPDbaseOloads OBJECT-TYPE
   SYNTAX Counter
   ACCESS read-only
   STATUS mandatory
   DESCRIPTION
       "Number of times the Level 2 LSP database has become
       overloaded."
   REFERENCE "ANSI {ISIS.aoi lSPL2DatabaseOverloads (32)}"
   ::= { xIsisSysEntry 30 }


xIsisSysMaxAreaCheck OBJECT-TYPE
   SYNTAX INTEGER
   ACCESS read-write
   STATUS mandatory
   DESCRIPTION
       "When on, enables checking of maximum area
       addresses per IS version of ISO10589."
   ::= { xIsisSysEntry 31 }
           
-- The Level 1 Manual Area Address Table

xIsisManAreaAddrTable OBJECT-TYPE
   SYNTAX SEQUENCE OF XIsisManAreaAddrEntry
   ACCESS not-accessible
   STATUS mandatory
   DESCRIPTION
       "The set of manual area addresses configured on this
	       Intermediate System."
	   REFERENCE "ANSI {ISIS.aoi manualAreaAddresses (10)}"
	   ::= { xIsisSystem 2 }

xIsisManAreaAddrEntry OBJECT-TYPE
   SYNTAX XIsisManAreaAddrEntry
   ACCESS not-accessible
   STATUS mandatory
   DESCRIPTION
        "Each entry contains one area address manually configured
       on this system"
   INDEX {  xIsisManAreaAddrSysInstance, xIsisManAreaAddr }
   ::= { xIsisManAreaAddrTable 1 }

XIsisManAreaAddrEntry ::=
   SEQUENCE {
      xIsisManAreaAddrSysInstance
         INTEGER,
      xIsisManAreaAddr
         OCTET STRING,
      xIsisManAreaAddrExistState
         INTEGER
   }

xIsisManAreaAddrSysInstance OBJECT-TYPE
   SYNTAX INTEGER
   ACCESS read-only
   STATUS mandatory
   DESCRIPTION
       "The unique identifier of the Integrated IS-IS instance
       to which this row corresponds. This object follows the
       index behaviour."
   ::= { xIsisManAreaAddrEntry 1 }

xIsisManAreaAddr OBJECT-TYPE
   SYNTAX OCTET STRING
   ACCESS read-only
   STATUS mandatory
   DESCRIPTION
       "A manually configured area address for this system. This
       object follows the index behaviour."
   ::= { xIsisManAreaAddrEntry 2 }

xIsisManAreaAddrExistState OBJECT-TYPE
   SYNTAX INTEGER {
		off(1),
		on(2)
		}
   ACCESS read-write
   STATUS mandatory
   DESCRIPTION
       "The state of the xIsisManAreaAddrEntry. This object
       follows the ExistenceState behaviour. If an attempt is
       made to set this object to the value off when the
       corresponding xIsisManAreaAddrEntry is the only valid
       entry for this instance and when the corresponding ISIS
       instance has xIsisSysOperState set to On then the attempt
       is rejected."
   ::= { xIsisManAreaAddrEntry 3 }


-- The Level 1 Area Address Table

-- The Level 1 Area Address Table contains the
-- union of the sets of area addresses reported in all Level 1
-- LSPs received by this Intermediate System.

xIsisAreaAddrTable OBJECT-TYPE
   SYNTAX SEQUENCE OF XIsisAreaAddrEntry
   ACCESS not-accessible
   STATUS mandatory
   DESCRIPTION
       "The union of the sets of area addresses reported in all
       Level 1 LSPs received by this instance of the protocol."
   REFERENCE "ANSI {ISIS.aoi areaAddresses (18)}"
   ::= { xIsisSystem 3 }

xIsisAreaAddrEntry OBJECT-TYPE
   SYNTAX XIsisAreaAddrEntry
   ACCESS not-accessible
   STATUS mandatory
   DESCRIPTION
       "Each entry contains one area address reported in a
       Level 1 LSP received by this instance of the protocol."
   INDEX {  xIsisAreaAddrSysInstance, xIsisAreaAddr }
   ::= { xIsisAreaAddrTable 1 }
 
XIsisAreaAddrEntry ::=
   SEQUENCE {
      xIsisAreaAddrSysInstance
         INTEGER,
      xIsisAreaAddr
         OCTET STRING
   }

xIsisAreaAddrSysInstance OBJECT-TYPE
   SYNTAX INTEGER
   ACCESS read-only
   STATUS mandatory
   DESCRIPTION
       "The unique identifier of the Integrated IS-IS instance
       to which this row corresponds."
   ::= { xIsisAreaAddrEntry 1 }

xIsisAreaAddr OBJECT-TYPE
   SYNTAX OCTET STRING
   ACCESS read-only
   STATUS mandatory
   DESCRIPTION
       "An area address reported in a Level 1 LSP received by
       this instance of the protocol."
   ::= { xIsisAreaAddrEntry 2 }                    

-- The System Integrated Group

-- The System Integrated Group is present if the system
-- supports Integrated ISIS at Level 1.


-- The System Protocol Supported Table

-- The System Protocol Supported Table contains the manually
-- configured set of protocols supported by each
-- instance of the Integrated ISIS protocol.

xIsisSysProtSuppTable OBJECT-TYPE
   SYNTAX SEQUENCE OF XIsisSysProtSuppEntry
   ACCESS not-accessible
   STATUS mandatory
   DESCRIPTION
       "This table contains the manually configured set of
       protocols supported by each instance of the Integrated
       ISIS protocol."
   ::= { xIsisSystem 4 }

xIsisSysProtSuppEntry OBJECT-TYPE
   SYNTAX XIsisSysProtSuppEntry
   ACCESS not-accessible
   STATUS mandatory
   DESCRIPTION
       "Each entry contains one protocol supported by an
       instance of the Integrated ISIS protocol."
   INDEX {  xIsisSysProtSuppSysInstance,
            xIsisSysProtSuppProtocol }
   ::= { xIsisSysProtSuppTable 1 }

XIsisSysProtSuppEntry ::=
   SEQUENCE {
      xIsisSysProtSuppSysInstance
         INTEGER,
      xIsisSysProtSuppProtocol
         SupportedProtocol,
      xIsisSysProtSuppExistState
         ExistState
   }

xIsisSysProtSuppSysInstance OBJECT-TYPE
   SYNTAX INTEGER
   ACCESS read-only
   STATUS mandatory
   DESCRIPTION
       "The unique identifier of the Integrated IS-IS instance
       to which this row corresponds. This object follows the
       index behaviour."
   ::= { xIsisSysProtSuppEntry 1 }

xIsisSysProtSuppProtocol OBJECT-TYPE
   SYNTAX SupportedProtocol
   ACCESS read-only
   STATUS mandatory
   DESCRIPTION
       "One supported protocol. This object follows the index
       behaviour."
   ::= { xIsisSysProtSuppEntry 2 }

xIsisSysProtSuppExistState OBJECT-TYPE
   SYNTAX ExistState
   ACCESS read-write
   STATUS mandatory
   DESCRIPTION
       "The state of the xIsisSysProtSuppEntry. This object
       follows the ExistenceState and
       ReplaceOnlyWhileInstanceDisabled behaviours."
   DEFVAL { on }
   ::= { xIsisSysProtSuppEntry 3 }


-- The Circuit Group

-- The Circuit Group is mandatory


-- The Circuit Table

-- Each broadcast or point-to-point interface on the system
-- corresponds to one entry in the Circuit table. There may be
-- many X.25 DA circuit entries in the Circuit table for an
-- X.25 interface.

xIsisCircTable OBJECT-TYPE
   SYNTAX SEQUENCE OF XIsisCircEntry
   ACCESS not-accessible
   STATUS mandatory
   DESCRIPTION
       "The table of circuits used by each instance of
       Integrated IS-IS on this system."
   ::= { xIsisCirc 1 }

xIsisCircEntry OBJECT-TYPE
   SYNTAX XIsisCircEntry
   ACCESS not-accessible
   STATUS mandatory
   DESCRIPTION
       "An xIsisCircEntry exists for each circuit used by
       Integrated IS-IS on this system."
   INDEX {  xIsisCircSysInstance, xIsisCircIndex }
   ::= { xIsisCircTable 1 }

XIsisCircEntry ::=
   SEQUENCE {
      xIsisCircSysInstance
         INTEGER,
      xIsisCircIndex
         INTEGER,
      xIsisCircIfIndex
         INTEGER,
      xIsisCircOperState
         INTEGER,
      xIsisCircExistState
         INTEGER,
      xIsisCircType
         INTEGER,
      xIsisCircHelloTimer
         INTEGER,
      xIsisCircL1DefaultMetric
         INTEGER,
      xIsisCircL1DelayMetric
         INTEGER,
      xIsisCircL1ExpenseMetric
         INTEGER,
      xIsisCircL1ErrorMetric
         INTEGER,
      xIsisCircExtDomain
         INTEGER,
      xIsisCircAdjChanges
         Counter,
      xIsisCircInitFails
         Counter,
      xIsisCircRejAdjs
         Counter,
      xIsisCircOutCtrlPDUs
         Counter,
      xIsisCircInCtrlPDUs
         Counter,
      xIsisCircIDFieldLenMismatches
         Counter,
      xIsisCircL2DefaultMetric
         INTEGER,
      xIsisCircL2DelayMetric
         INTEGER,
      xIsisCircL2ExpenseMetric
         INTEGER,
      xIsisCircL2ErrorMetric
         INTEGER,
      xIsisCircManL2Only
         INTEGER,
      xIsisCircL1ISPriority
         INTEGER,
      xIsisCircL1CircID
         OCTET STRING,
      xIsisCircL1DesIS
         OCTET STRING,
      xIsisCircLANL1DesISChanges
         Counter,
      xIsisCircL2ISPriority
         INTEGER,
      xIsisCircL2CircID
         OCTET STRING,
      xIsisCircL2DesIS
         OCTET STRING,
      xIsisCircLANL2DesISChanges
         Counter
   }

xIsisCircSysInstance OBJECT-TYPE
   SYNTAX INTEGER
   ACCESS read-only
   STATUS mandatory
   DESCRIPTION
       "The unique identifier of the Integrated IS-IS instance
       to which this row corresponds. This object follows the
       index behaviour."
   ::= { xIsisCircEntry 1 }

xIsisCircIndex OBJECT-TYPE
   SYNTAX INTEGER (1..255)
   ACCESS read-only
   STATUS mandatory
   DESCRIPTION
       "The identifier of this circuit, unique within the
       instance of the protocol. This object follows the index
       behaviour."
   ::= { xIsisCircEntry 2 }

xIsisCircIfIndex OBJECT-TYPE
   SYNTAX INTEGER
   ACCESS read-only
   STATUS mandatory
   DESCRIPTION
       "The value of ifIndex for the interface to which this
       circuit corresponds. This object follows the
       replaceOnlyWhileDisabled behaviour."
   ::= { xIsisCircEntry 3 }

xIsisCircOperState OBJECT-TYPE
   SYNTAX INTEGER {
                  off(1),
                  on(2)
                  }
   ACCESS read-write
   STATUS mandatory
   DESCRIPTION
       "The operational state of the circuit. This object
       follows the operationalState behaviour."
   ::= { xIsisCircEntry 4 }

xIsisCircExistState OBJECT-TYPE
   SYNTAX INTEGER {
                  off(1),
                  on(2)
                  }
   ACCESS read-only
   STATUS mandatory
   DESCRIPTION
       "The existence state of this circuit. This object follows
       the ExistenceState behaviour."
   ::= { xIsisCircEntry 5 }

xIsisCircType OBJECT-TYPE
   SYNTAX   INTEGER {
               auto(1),
               broadcast(2),
               ptToPt(3)
            }
   ACCESS read-write
   STATUS mandatory
   DESCRIPTION
       "The type of the circuit.  This object follows the
       replaceOnlyWhileDisabled behaviour. The type specified
       must be compatible with the type of the interface defined
       by the value of xIsisCircIfIndex."
   REFERENCE "ANSI {ISIS.aoi type (33)}"
   ::= { xIsisCircEntry 6 }

xIsisCircHelloTimer OBJECT-TYPE
   SYNTAX INTEGER (1..65535)
   ACCESS read-write
   STATUS mandatory
   DESCRIPTION
       "The period, in seconds, between IIH PDUs. It is also
       used as the period between ISH PDUs when polling the ES
       configuration. This object follows the resettingTimer
       behaviour."
   REFERENCE "ANSI {ISIS.aoi iSISHelloTimer (45)}"
   ::= { xIsisCircEntry 7 }

xIsisCircL1DefaultMetric OBJECT-TYPE
   SYNTAX INTEGER (0..63) 
   ACCESS read-write
   STATUS mandatory
   DESCRIPTION
       "The default metric value of this circuit for Level 1
       traffic. 0 means the IS will automatically generate Level 1 default
       metric for the circuit."
   REFERENCE "ANSI {ISIS.aoi l1DefaultMetric (35)}"
   ::= { xIsisCircEntry 8 }

xIsisCircL1DelayMetric OBJECT-TYPE
   SYNTAX INTEGER (0..63) 
   ACCESS read-write
   STATUS mandatory
   DESCRIPTION
       "The delay metric value of this circuit for Level 1
       traffic. The value of zero is reserved to indicate that
       this metric is not supported."
   REFERENCE "ANSI {ISIS.aoi l1DelayMetric (36)}"
   ::= { xIsisCircEntry 9 }

xIsisCircL1ExpenseMetric OBJECT-TYPE
   SYNTAX INTEGER (0..63) 
   ACCESS read-write
   STATUS mandatory
   DESCRIPTION
       "The expense metric value of this circuit for Level 1
       traffic. The value of zero is reserved to indicate that
       this metric is not supported."
   REFERENCE "ANSI {ISIS.aoi l1ExpenseMetric (37)}"
   ::= { xIsisCircEntry 10 }

xIsisCircL1ErrorMetric OBJECT-TYPE
   SYNTAX INTEGER (0..63) 
   ACCESS read-write
   STATUS mandatory
   DESCRIPTION
       "The error metric value of this circuit for Level 1
       traffic. The value of zero is reserved to indicate that
       this metric is not supported."
   REFERENCE "ANSI {ISIS.aoi l1ErrorMetric (38)}"
   ::= { xIsisCircEntry 11 }

xIsisCircExtDomain OBJECT-TYPE
   SYNTAX INTEGER {
                  false(1),
                  true(2)
                  }
   ACCESS read-write
   STATUS mandatory
   DESCRIPTION
       "If true, suppress normal transmission of and
       interpretation of Intra-domain ISIS PDUs on this
       circuit."
   REFERENCE "ANSI {ISIS.aoi externalDomain (46)}"
   ::= { xIsisCircEntry 12 }

xIsisCircAdjChanges OBJECT-TYPE
   SYNTAX Counter
   ACCESS read-only
   STATUS mandatory
   DESCRIPTION
       "The number of times an adjacency state change has
       occurred on this circuit."
   REFERENCE "ANSI {ISIS.aoi changesInAdjacencyState (40)}"
   ::= { xIsisCircEntry 13 }

xIsisCircInitFails OBJECT-TYPE
   SYNTAX Counter
   ACCESS read-only
   STATUS mandatory
   DESCRIPTION
       "The number of times initialization of this circuit has
       failed."
   REFERENCE "ANSI {ISIS.aoi initializationFailures (41)}"
   ::= { xIsisCircEntry 14 }

xIsisCircRejAdjs OBJECT-TYPE
   SYNTAX Counter
   ACCESS read-only
   STATUS mandatory
   DESCRIPTION
       "The number of times an adjacency has been rejected on
       this circuit."
   REFERENCE "ANSI {ISIS.aoi rejectedAdjacencies (42)}"
   ::= { xIsisCircEntry 15 }

xIsisCircOutCtrlPDUs OBJECT-TYPE
   SYNTAX Counter
   ACCESS read-only
   STATUS mandatory
   DESCRIPTION
       "The number of IS-IS control PDUs sent on this circuit."
   REFERENCE "ANSI {ISIS.aoi iSISControlPDUsSent (43)}"
   ::= { xIsisCircEntry 16 }

xIsisCircInCtrlPDUs OBJECT-TYPE
   SYNTAX Counter
   ACCESS read-only
   STATUS mandatory
   DESCRIPTION
       "The number of IS-IS control PDUs received on this
       circuit."
   REFERENCE "ANSI {ISIS.aoi controlPDUsReceived (44)}"
   ::= { xIsisCircEntry 17 }

xIsisCircIDFieldLenMismatches OBJECT-TYPE
   SYNTAX Counter
   ACCESS read-only
   STATUS mandatory
   DESCRIPTION
       "The number of times an IS-IS control PDU with an ID
       field length different to that for this system has been
       received."
   REFERENCE "ANSI {ISIS.aoi iDFieldLengthMismatches (25)}"
   ::= { xIsisCircEntry 18 }

-- The following objects map those from the linkageISISLevel2-P
-- package

xIsisCircL2DefaultMetric OBJECT-TYPE
   SYNTAX INTEGER (0..63) 
   ACCESS read-write
   STATUS mandatory
   DESCRIPTION
       "The default metric value of this circuit for level 2
       traffic. 0 means the IS will automatically generate the Level 2
       default metric for this circuit."
   REFERENCE "ANSI {ISIS.aoi l2DefaultMetric (68)}"
   ::= { xIsisCircEntry 20 }

xIsisCircL2DelayMetric OBJECT-TYPE
   SYNTAX INTEGER (0..63) 
   ACCESS read-write
   STATUS mandatory
   DESCRIPTION
       "The delay metric value of this circuit for level 2
       traffic. The value of zero is reserved to indicate that
       this metric is not supported."
   REFERENCE "ANSI {ISIS.aoi l2DelayMetric (69)}"
   ::= { xIsisCircEntry 21 }

xIsisCircL2ExpenseMetric OBJECT-TYPE
   SYNTAX INTEGER (0..63) 
   ACCESS read-write
   STATUS mandatory
   DESCRIPTION
       "The expense metric value of this circuit for level 2
       traffic. The value of zero is reserved to indicate that
       this metric is not supported."
   REFERENCE "ANSI {ISIS.aoi l2ExpenseMetric (70)}"
   ::= { xIsisCircEntry 22 }

xIsisCircL2ErrorMetric OBJECT-TYPE
   SYNTAX INTEGER (0..63) 
   ACCESS read-write
   STATUS mandatory
   DESCRIPTION
       "The error metric value of this circuit for level 2
       traffic. The value of zero is reserved to indicate that
       this metric is not supported."
   REFERENCE "ANSI {ISIS.aoi l2ErrorMetric (71)}"
   ::= { xIsisCircEntry 23 }

xIsisCircManL2Only OBJECT-TYPE
   SYNTAX INTEGER {
                  false(1),
                  true(2)
                  }
   ACCESS read-write
   STATUS mandatory
   DESCRIPTION
       "When true, indicates that this circuit is to be used
       only for level 2. This object follows the
       replaceOnlyWhileDisabled behaviour."
   REFERENCE "ANSI {ISIS.aoi manualL2OnlyMode (72)}"
   ::= { xIsisCircEntry 24 }

-- The following objects map those from the
-- linkageISISBroadcast-P package

xIsisCircL1ISPriority OBJECT-TYPE
   SYNTAX INTEGER (1..127)
   ACCESS read-write
   STATUS mandatory
   DESCRIPTION
       "The priority for becoming LAN Level 1 Deignated
       Intermediate System on a broadcast circuit."
   REFERENCE "ANSI {ISIS.aoi l1IntermediateSystemPriority (47)}"
   ::= { xIsisCircEntry 25 }

xIsisCircL1CircID OBJECT-TYPE
   SYNTAX OCTET STRING 
   ACCESS read-only
   STATUS mandatory
   DESCRIPTION
       "The LAN ID allocated by the LAN Level 1 Designated
       Intermediate System. Where this system is not aware of
       the value (because it is not participating in the Level 1
       Designated Intermediate System election), this object has
       the value which would be proposed for this circuit (i.e.
       the concatenation of the local system ID and the one
       octet local Circuit ID for this circuit."
   REFERENCE "ANSI {ISIS.aoi l1CircuitID (48)}"
   ::= { xIsisCircEntry 26 }

xIsisCircL1DesIS OBJECT-TYPE
   SYNTAX OCTET STRING
   ACCESS read-only
   STATUS mandatory
   DESCRIPTION
       "The ID of the LAN Level 1 Designated Intermediate System
       on this circuit. If, for any reason this system is not
       partaking in the relevant Designated Intermediate System
       election process, then the value returned is the zero
       length OCTET STRING."
   REFERENCE "ANSI {ISIS.aoi l1DesignatedIntermediateSystem (49)}"
   ::= { xIsisCircEntry 27 }

xIsisCircLANL1DesISChanges OBJECT-TYPE
   SYNTAX Counter
   ACCESS read-only
   STATUS mandatory
   DESCRIPTION
       "The number of times the LAN Level 1 Designated
       Intermediate System has changed."
     REFERENCE "ANSI {ISIS.aoi
       lanL1DesignatedIntermediateSystemChanges (50)}"
   ::= { xIsisCircEntry 28 }

-- The following objects map those from the
-- linkageISISLevel2Broadcast-P package

xIsisCircL2ISPriority OBJECT-TYPE
   SYNTAX INTEGER (1..127)
   ACCESS read-write
   STATUS mandatory
   DESCRIPTION
       "The priority for becoming LAN level 2 Designated
       Intermediate System."
   REFERENCE "ANSI {ISIS.aoi l2IntermediateSystemPriority (73)}"
   ::= { xIsisCircEntry 29 }

xIsisCircL2CircID OBJECT-TYPE
   SYNTAX OCTET STRING 
   ACCESS read-only
   STATUS mandatory
   DESCRIPTION
       "The LAN ID allocated by the LAN Level 2 Designated
       Intermediate System. Where this system is not aware of
       this value (because it is not participating in the Level
       2 Designated Intermediate System election), this object
       has the value which would be proposed for this circuit
       (i.e. the concatenation of the local system ID and the
       one octet local Circuit ID for this circuit."
   REFERENCE "ANSI {ISIS.aoi l2CircuitID (74)}"
   ::= { xIsisCircEntry 30 }

xIsisCircL2DesIS OBJECT-TYPE
   SYNTAX OCTET STRING
   ACCESS read-only
   STATUS mandatory
   DESCRIPTION
       "The ID of the LAN Level 2 Designated Intermediate System
       on this circuit. If, for any reason, this system is not
       partaking in the relevant Designated Intermediate System
       election process, then the value returned is the zero
       length OCTET STRING."
   REFERENCE "ANSI {ISIS.aoi l2DesignatedIntermediateSystem (75)}"
   ::= { xIsisCircEntry 31 }

xIsisCircLANL2DesISChanges OBJECT-TYPE
   SYNTAX Counter
   ACCESS read-only
   STATUS mandatory
   DESCRIPTION
       "The number of times the LAN Level 2 Designated
       Intermediate System has changed."
   REFERENCE "ANSI {ISIS.aoi
      lanL2DesignatedIntermediateSystemChanges (76)}"
   ::= { xIsisCircEntry 32 }

-- The Circuit IS Group

-- The Circuit IS Table


xIsisCircISTable OBJECT-TYPE
   SYNTAX SEQUENCE OF XIsisCircISEntry
   ACCESS not-accessible
   STATUS mandatory
   DESCRIPTION
       "The set of objects controlling the operation of the IS
       functions of the ES-IS protocol (ISO 9542) on each
       circuit over which ISIS is run."
   REFERENCE "ANSI {NLM.poi linkage-ISO9542IS-P (22)}"
   ::= { xIsisCirc 2 }

xIsisCircISEntry OBJECT-TYPE
   SYNTAX XIsisCircISEntry
   ACCESS not-accessible
   STATUS mandatory
   DESCRIPTION
       "Each entry contains objects controlling the operation of
       the IS functions of the ES-IS protocol (ISO 9542) on one
       circuit."
   INDEX {  xIsisCircISIndex }
   ::= { xIsisCircISTable 1 }

XIsisCircISEntry ::=
   SEQUENCE {
      xIsisCircISSysInstance
         INTEGER,
      xIsisCircISIndex
         INTEGER,
      xIsisCircISExistState
         INTEGER,
      xIsisCircISOperState
         INTEGER,
      xIsisCircISHoldTimerMult
         INTEGER,
      xIsisCircISConfTimer
         INTEGER,
      xIsisCircISSuggESConfTimer
         INTEGER,                     
      xIsisCircISRedHoldTime
         INTEGER,
      xIsisCircISESReachChgs
         Counter,
      xIsisCircISInv9542PDUs
         Counter
   }
xIsisCircISSysInstance OBJECT-TYPE
   SYNTAX INTEGER
   ACCESS read-only
   STATUS mandatory
   DESCRIPTION            
       "The identifier of the Integrated IS-IS instance to which
       this row corresponds. This object follows the index and
       manualOrAutomatic behaviours."
   ::= { xIsisCircISEntry 1 }

xIsisCircISIndex OBJECT-TYPE
   SYNTAX INTEGER
   ACCESS read-only
   STATUS mandatory
   DESCRIPTION
       "The unique identifier of this row. This value is the
       same as the value of the ifIndex object which identifies
       the interface which corresponds to this circuit. This
       object follows the index behaviour."
   ::= { xIsisCircISEntry 2 }

xIsisCircISExistState OBJECT-TYPE
   SYNTAX INTEGER {
                  off(1),
                  on(2)
                  }
   ACCESS read-only
   STATUS mandatory
   DESCRIPTION
       "The existence state of this row. This object follows the
       ExistenceState behaviour."
   ::= { xIsisCircISEntry 3 }

xIsisCircISOperState OBJECT-TYPE
   SYNTAX INTEGER {
                  off(1),
                  on(2)
                  }
   ACCESS read-write
   STATUS mandatory
   DESCRIPTION
       "The operational state of the row. This object follows
       the operationalState behaviour."
   ::= { xIsisCircISEntry 4 }

xIsisCircISHoldTimerMult OBJECT-TYPE
   SYNTAX INTEGER (2..63)
   ACCESS read-only
   STATUS mandatory
   DESCRIPTION
       "The factor to derive holding timer from configuration
       timer. This value when multipled by a configuration timer
       yields the value of the holding timer parameter issued
       with configuration information. The semantics of this
       parameter are such that it is permissible to add a delta
       value to the result to compensate for possible delays and
       imprecision of timers. The result of the calculation is
       truncated, upon overflow, to the maximum value for the
       parameter permitted by the protocol (65535)."
   REFERENCE "ANSI {NLM.aoi holdingTimerMutliplier (20)}"
   ::= { xIsisCircISEntry 5 }

xIsisCircISConfTimer OBJECT-TYPE
   SYNTAX INTEGER
   ACCESS read-write
   STATUS mandatory
   DESCRIPTION
       "Value in seconds for the ISO 9542 IS configuration
       timer. It is used to determine how often an IS reports
       configuration information to ESs. This object follows the
       resettingTimer behaviour."
   REFERENCE "ANSI {NLM.aoi iSConfigurationTimer (24)}"
   ::= { xIsisCircISEntry 6 }

xIsisCircISSuggESConfTimer OBJECT-TYPE
   SYNTAX INTEGER
   ACCESS read-write
   STATUS mandatory
   DESCRIPTION
       "Value to be used for the ISO 9542 suggested ES
       configuration timer value (in seconds), advertised in IS
       Hellos generated by the system on this circuit. This
       object follows the resettingTimer behaviour."
   REFERENCE "ANSI {NLM.aoi suggestedESConfigurationTimer (25)}"
   ::= { xIsisCircISEntry 7 }

xIsisCircISRedHoldTime OBJECT-TYPE
   SYNTAX INTEGER (1..65535)
   ACCESS read-write
   STATUS mandatory
   DESCRIPTION
       "The holding time (in seconds) to be specified in
       Redirect PDUs generated by the system on this circuit."
   REFERENCE "ANSI {NLM.aoi redirectHoldingTime (26)}"
   ::= { xIsisCircISEntry 8 }

xIsisCircISESReachChgs OBJECT-TYPE
   SYNTAX Counter
   ACCESS read-only
   STATUS mandatory
   DESCRIPTION
       "Count of the number of changes in reachability of End
       Systems from this circuit."
   REFERENCE "ANSI {NLM.aoi eSReachabilityChanges (27)}"
   ::= { xIsisCircISEntry 9 }

xIsisCircISInv9542PDUs OBJECT-TYPE
   SYNTAX Counter
   ACCESS read-only
   STATUS mandatory
   DESCRIPTION
       "Counter of invalid 9542 PDUs received. This is the
       number of ISO 9452 PDUs received which are discarded as a
       result of the PDU Header Error Detection or Protocol
       Error Processing Functions specified in ISO 9542."
   REFERENCE "ANSI {NLM.aoi invalid9542PDUs (101)}"
   ::= { xIsisCircISEntry 10 }

-- The IS Adjacency Group

-- The IS Adjacency Group is mandatory and contains information
-- about adjacencies to routers maintained by the Integrated
-- IS-IS protocol


-- The IS Adjacency Table

-- Each adjacency to an IS corresponds to one entry in this
-- table.
xIsisISAdjTable OBJECT-TYPE
   SYNTAX SEQUENCE OF XIsisISAdjEntry
   ACCESS not-accessible
   STATUS mandatory
   DESCRIPTION
       "The table of adjacencies to Intermediate Systems."
   ::= { xIsisISAdj 1 }

xIsisISAdjEntry OBJECT-TYPE
   SYNTAX XIsisISAdjEntry
   ACCESS not-accessible
   STATUS mandatory
   DESCRIPTION
       "Each entry corresponds to one adjacency to an
       Intermediate System on this system."
   INDEX {  xIsisISAdjSysInstance, xIsisISAdjCircIndex, xIsisISAdjIndex }
   ::= { xIsisISAdjTable 1 }

XIsisISAdjEntry ::=
   SEQUENCE {
      xIsisISAdjSysInstance
         INTEGER,
      xIsisISAdjCircIndex
         INTEGER,
      xIsisISAdjIndex
         INTEGER,
      xIsisISAdjState
         INTEGER,
      xIsisISAdjNeighSNPAAddress
         OCTET STRING,
      xIsisISAdjNeighSysType
         INTEGER,
      xIsisISAdjNeighSysID
         OCTET STRING,
      xIsisISAdjUsage
         INTEGER,
      xIsisISAdjHoldTimer
         INTEGER,
      xIsisISAdjNeighPriority
         INTEGER
   }

xIsisISAdjSysInstance OBJECT-TYPE
   SYNTAX INTEGER
   ACCESS read-only
   STATUS mandatory
   DESCRIPTION
       "The unique identifier of the Integrated IS-IS instance
       to which this row corresponds."
   ::= { xIsisISAdjEntry 1 }

xIsisISAdjCircIndex OBJECT-TYPE
   SYNTAX INTEGER
   ACCESS read-only
   STATUS mandatory
   DESCRIPTION
       "The identifier of the Circuit which is the parent of the
       IS adjacency."
   ::= { xIsisISAdjEntry 2 }

xIsisISAdjIndex OBJECT-TYPE
   SYNTAX INTEGER
   ACCESS read-only
   STATUS mandatory
   DESCRIPTION
       "A unique value identifying the IS adjacency from all
       other such adjacencies on this circuit. This value is
       assigned by the system when the adjacency is created
       automatically."
   ::= { xIsisISAdjEntry 3 }

xIsisISAdjState OBJECT-TYPE
   SYNTAX   INTEGER {
               initializing(1),
               up(2),
               failed(3),
               down(4)
            }
   ACCESS read-only
   STATUS mandatory
   DESCRIPTION
       "The state of the adjacency"
   REFERENCE "ANSI {ISIS.aoi adjacencyState (78)}"
   ::= { xIsisISAdjEntry 4 }

xIsisISAdjNeighSNPAAddress OBJECT-TYPE
   SYNTAX OCTET STRING
   ACCESS read-only
   STATUS mandatory
   DESCRIPTION
       "The SNPA address of the neighboring system."
   REFERENCE "ANSI {ISIS.aoi neighbourSNPAAddress (79)}"
   ::= { xIsisISAdjEntry 5 }

xIsisISAdjNeighSysType OBJECT-TYPE
   SYNTAX   INTEGER {
               unknown(1),
               intermediateSystem(3),
               l1IntermediateSystem(4),
               l2IntermediateSystem(5)
            }
   ACCESS read-only
   STATUS mandatory
   DESCRIPTION
       "The type of the neighboring system."
   REFERENCE "ANSI {ISIS.aoi neighbourSystemType (80)}"
   ::= { xIsisISAdjEntry 6 }

xIsisISAdjNeighSysID OBJECT-TYPE
   SYNTAX OCTET STRING 
   ACCESS read-only
   STATUS mandatory
   DESCRIPTION
       "The system ID of the neighboring Intermediate System set
       from the source ID field of the neighbor's IIH PDUs."
   REFERENCE "ANSI {ISIS.aoi neighbourSystemIds (83)}"
   ::= { xIsisISAdjEntry 7 }

xIsisISAdjUsage OBJECT-TYPE
   SYNTAX   INTEGER {
               undefined(1),
               level1(2),
               level2(3),
               level1and2(4)
            }
   ACCESS read-only
   STATUS mandatory
   DESCRIPTION
       "The usage of the adjacency. An adjacency of type level1
       will be used for level 1 traffic only. An adjacency of
       type level2 will be used for level 2 traffic only. An
       adjacency of type level1and2 will be used for both level
       1 and level 2 traffic. There may be two adjacencies (of
       types level1 and level2) between the same pair of
       Intermediate Systems."
   REFERENCE "ANSI {ISIS.aoi adjacencyUsage (82)}"
   ::= { xIsisISAdjEntry 8 }

xIsisISAdjHoldTimer OBJECT-TYPE
   SYNTAX INTEGER (1..65535)
   ACCESS read-only
   STATUS mandatory
   DESCRIPTION
       "The holding time for this adjacency updated from
       received IIH PDUs."
   REFERENCE "ANSI {ISIS.aoi holdingTimer (85)}"
   ::= { xIsisISAdjEntry 9 }

xIsisISAdjNeighPriority OBJECT-TYPE
   SYNTAX INTEGER (1..127)
   ACCESS read-only
   STATUS mandatory
   DESCRIPTION
       "Priority of the neighboring Intermediate System for
       becoming the LAN Level 1 Designated Intermediate System
       if the value of xIsisISAdjNeighSysType is
       L1IntermediateSystem or LAN Level 2 Designated
       Intermediate System if the value of
       xIsisISAdjNeighSysType is L2IntermediateSystem."
   REFERENCE "ANSI {ISIS.aoi lANPriority (86)}"
   ::= { xIsisISAdjEntry 10 }

-- The IS Adjacency Area Address Table

-- The IS Adjacency Area Address Table contains the set of
-- Area Addresses of neighboring
-- Intermediate Systems as reported in IIH PDUs.

xIsisISAdjAreaAddrTable OBJECT-TYPE
   SYNTAX SEQUENCE OF XIsisISAdjAreaAddrEntry
   ACCESS not-accessible
   STATUS mandatory
   DESCRIPTION
       "This table contains the set of Area Addresses of
       neighboring Intermediate Systems as reported in received
       IIH PDUs."
   REFERENCE "ANSI {ISIS.aoi areaAddressesOfNeighbour (84)}"
   ::= { xIsisISAdj 2 }

xIsisISAdjAreaAddrEntry OBJECT-TYPE
   SYNTAX XIsisISAdjAreaAddrEntry
   ACCESS not-accessible
   STATUS mandatory
   DESCRIPTION
       "Each entry contains one Area Address reported by a
       neighboring Intermediate System in its IIH PDUs."
   INDEX {  xIsisISAdjAreaAddrSysInstance, xIsisISAdjAreaAddrCircIndex, xIsisISAdjAreaAddrAdjIndex, xIsisISAdjAreaAddress }
   ::= { xIsisISAdjAreaAddrTable 1 }

XIsisISAdjAreaAddrEntry ::=
   SEQUENCE {
      xIsisISAdjAreaAddrSysInstance
         INTEGER,
      xIsisISAdjAreaAddrCircIndex
         INTEGER,
      xIsisISAdjAreaAddrAdjIndex
         INTEGER,
      xIsisISAdjAreaAddress
         OCTET STRING
   }

xIsisISAdjAreaAddrSysInstance OBJECT-TYPE
   SYNTAX INTEGER
   ACCESS read-only
   STATUS mandatory
   DESCRIPTION
       "The unique identifier of the Integrated IS-IS instance
       to which this row corresponds."
   ::= { xIsisISAdjAreaAddrEntry 1 }

xIsisISAdjAreaAddrCircIndex OBJECT-TYPE
   SYNTAX INTEGER
   ACCESS read-only
   STATUS mandatory
   DESCRIPTION
       "The identifier of the Circuit which is the parent of the
       IS adjacency to which this Area Address entry
       corresponds."
   ::= { xIsisISAdjAreaAddrEntry 2 }

xIsisISAdjAreaAddrAdjIndex OBJECT-TYPE
   SYNTAX INTEGER
   ACCESS read-only
   STATUS mandatory
   DESCRIPTION
       "The identifier of the IS adjacency to which this entry
       belongs."
   ::= { xIsisISAdjAreaAddrEntry 3 }

xIsisISAdjAreaAddress OBJECT-TYPE
   SYNTAX OCTET STRING
   ACCESS read-only
   STATUS mandatory
   DESCRIPTION
       "One Area Address as reported in IIH PDUs received from
       the neighbor."
   ::= { xIsisISAdjAreaAddrEntry 4 }


-- The IS Adjacency IP Group

-- The IS Adjacency IP Group is present if the system supports
-- IP Integrated IS-IS


-- The IS Adjacency IP Address Table

-- The IS Adjacency IP Address Table contains the
-- set of IP Addresses of neighboring Intermediate Systems
-- as reported in received IIH PDUs.

xIsisISAdjIPAddrTable OBJECT-TYPE
   SYNTAX SEQUENCE OF XIsisISAdjIPAddrEntry
   ACCESS not-accessible
   STATUS mandatory
   DESCRIPTION
       "This table contains the set of IP Addresses of
       neighboring Intermediate Systems as reported in received
       IIH PDUs."
   ::= { xIsisISAdj 3 }

xIsisISAdjIPAddrEntry OBJECT-TYPE
   SYNTAX XIsisISAdjIPAddrEntry
   ACCESS not-accessible
   STATUS mandatory
   DESCRIPTION
       "Each entry contains one IP Address reported by a
       neighboring Intermediate System in its IIH PDUs."
   INDEX {  xIsisISAdjIPAddrSysInstance,
            xIsisISAdjIPAddrCircIndex,
            xIsisISAdjIPAddrAdjIndex
        			}
   ::= { xIsisISAdjIPAddrTable 1 }

XIsisISAdjIPAddrEntry ::=
   SEQUENCE {
      xIsisISAdjIPAddrSysInstance
         INTEGER,
      xIsisISAdjIPAddrCircIndex
         INTEGER,
      xIsisISAdjIPAddrAdjIndex
         INTEGER,
      xIsisISAdjIPAddress
         IpAddress
   }

xIsisISAdjIPAddrSysInstance OBJECT-TYPE
   SYNTAX INTEGER
   ACCESS read-only
   STATUS mandatory
   DESCRIPTION
       "The unique identifier of the Integrated IS-IS instance
       to which this row corresponds."
   ::= { xIsisISAdjIPAddrEntry 1 }

xIsisISAdjIPAddrCircIndex OBJECT-TYPE
   SYNTAX INTEGER
   ACCESS read-only
   STATUS mandatory
   DESCRIPTION
       "The identifier of the Circuit which is the parent of the
       IS adjacency to which this IP Address entry corresponds."
   ::= { xIsisISAdjIPAddrEntry 2 }

xIsisISAdjIPAddrAdjIndex OBJECT-TYPE
   SYNTAX INTEGER
   ACCESS read-only
   STATUS mandatory
   DESCRIPTION
       "The identifier of the IS adjacency to which this entry
       belongs."
   ::= { xIsisISAdjIPAddrEntry 3 }

xIsisISAdjIPAddress OBJECT-TYPE
   SYNTAX IpAddress
   ACCESS read-only
   STATUS mandatory
   DESCRIPTION
       "One IP Address as reported in IIH PDUs received from the
       neighbor."
   ::= { xIsisISAdjIPAddrEntry 4 }


-- The IS Adjacency Integrated Group

-- The IS Adjacency Integrated Group is present if the system
-- supports Integrated ISIS.


-- The IS Adjacency Protocol Supported Table

-- The IS Adjacency Protocol Supported Table contains the set of
-- protocols supported by neighboring
-- Intermediate Systems as reported in received IIH PDUs.

xIsisISAdjProtSuppTable OBJECT-TYPE
   SYNTAX SEQUENCE OF XIsisISAdjProtSuppEntry
   ACCESS not-accessible
   STATUS mandatory
   DESCRIPTION
       "This table contains the set of protocols supported by
       neighboring Intermediate Systems as reported in received
       IIH PDUs."
   ::= { xIsisISAdj 4 }

xIsisISAdjProtSuppEntry OBJECT-TYPE
   SYNTAX XIsisISAdjProtSuppEntry
   ACCESS not-accessible
   STATUS mandatory
   DESCRIPTION
       "Each entry contains one protocol supported by a
       neighboring Intermediate System as reported in its IIH
       PDUs."
   INDEX {  xIsisISAdjProtSuppSysInstance,
            xIsisISAdjProtSuppCircIndex,
            xIsisISAdjProtSuppAdjIndex,
            xIsisISAdjProtSuppProtocol }
   ::= { xIsisISAdjProtSuppTable 1 }

XIsisISAdjProtSuppEntry ::=
   SEQUENCE {
      xIsisISAdjProtSuppSysInstance
         INTEGER,
      xIsisISAdjProtSuppCircIndex
         INTEGER,
      xIsisISAdjProtSuppAdjIndex
         INTEGER,
      xIsisISAdjProtSuppProtocol
         SupportedProtocol
   }

xIsisISAdjProtSuppSysInstance OBJECT-TYPE
   SYNTAX INTEGER
   ACCESS read-only
   STATUS mandatory
   DESCRIPTION
       "The unique identifier of the Integrated IS-IS instance
       to which this row corresponds."
   ::= { xIsisISAdjProtSuppEntry 1 }

xIsisISAdjProtSuppCircIndex OBJECT-TYPE
   SYNTAX INTEGER
   ACCESS read-only
   STATUS mandatory
   DESCRIPTION
       "The identifier of the Circuit which is the parent of the
       IS adjacency to which this supported protocol entry
       corresponds."
   ::= { xIsisISAdjProtSuppEntry 2 }

xIsisISAdjProtSuppAdjIndex OBJECT-TYPE
   SYNTAX INTEGER
   ACCESS read-only
   STATUS mandatory
   DESCRIPTION
       "The identifier the IS adjacency to which this entry
       corresponds."
   ::= { xIsisISAdjProtSuppEntry 3 }

xIsisISAdjProtSuppProtocol OBJECT-TYPE
   SYNTAX SupportedProtocol
   ACCESS read-only
   STATUS mandatory
   DESCRIPTION
       "One supported protocol as reported in IIH PDUs received
       from the neighbor."
   ::= { xIsisISAdjProtSuppEntry 4 }



-- The ES Adjacency Group

-- The ES Adjacency Group is present if the system supports
-- reception of ES Hellos


-- The ES Adjacency Table

-- The ES Adjacency Table contains one entry for each
-- End System ID of each neighboring End System
-- as reported in ESH PDUs or as configured manually.

xIsisESAdjTable OBJECT-TYPE
   SYNTAX SEQUENCE OF XIsisESAdjEntry
   ACCESS not-accessible
   STATUS mandatory
   DESCRIPTION
       "The table of End System IDs of neighboring End Systems
       as reported in their ESH PDUs or as configured manually"
   ::= { xIsisESAdj 1 }

xIsisESAdjEntry OBJECT-TYPE
   SYNTAX XIsisESAdjEntry
   ACCESS not-accessible
   STATUS mandatory
   DESCRIPTION
       "Each entry contains one End System ID of a neighboring
       End System as reported in an ESH PDU or as configured
       manually."
   INDEX {  xIsisESAdjSysInstance, xIsisESAdjCircIndex, xIsisESAdjIndex,
            xIsisESAdjESID }
   ::= { xIsisESAdjTable 1 }

XIsisESAdjEntry ::=
   SEQUENCE {
      xIsisESAdjSysInstance
         INTEGER,
      xIsisESAdjCircIndex
         INTEGER,
      xIsisESAdjIndex
         INTEGER,
      xIsisESAdjType
         INTEGER,
      xIsisESAdjState
         INTEGER,
      xIsisESAdjNeighSNPAAddress
         OCTET STRING,
      xIsisESAdjExistState
         INTEGER,
      xIsisESAdjESID
         OCTET STRING
   }

xIsisESAdjSysInstance OBJECT-TYPE
   SYNTAX INTEGER
   ACCESS read-only
   STATUS mandatory
   DESCRIPTION
       "The identifier of the Integrated IS-IS instance to which
       this row corresponds. This object follows the index and
       manualOrAutomatic behaviours."
   ::= { xIsisESAdjEntry 1 }

xIsisESAdjCircIndex OBJECT-TYPE
   SYNTAX INTEGER
   ACCESS read-only
   STATUS mandatory
   DESCRIPTION
       "The identifier of the Circuit which is the parent of the
       ES adjacency to which this End System ID entry
       corresponds. This object follows the index and
       manualOrAutomatic behaviours."
   ::= { xIsisESAdjEntry 2 }

xIsisESAdjIndex OBJECT-TYPE
   SYNTAX INTEGER
   ACCESS read-only
   STATUS mandatory
   DESCRIPTION
       "The identifier of the ES adjacency to which this entry
       belongs. This object follows the index and
       manualOrAutomatic behaviours."
   ::= { xIsisESAdjEntry 3 }

xIsisESAdjType OBJECT-TYPE
   SYNTAX   INTEGER  {
               auto(1),
               manual(2)
            }
   ACCESS read-only
   STATUS mandatory
   DESCRIPTION
       "The indication of whether this adjacency was created
       manually by management action or automatically by the
       implementation."
   ::= { xIsisESAdjEntry 4 }

xIsisESAdjState OBJECT-TYPE
   SYNTAX   INTEGER {
               initializing(1),
               up(2),
               failed(3),
               down(4)
            }
   ACCESS read-write
   STATUS mandatory
   DESCRIPTION
       "The state of the adjacency. Adjacencies created manually
       always have this value set to up."
   REFERENCE "ANSI {ISIS.aoi adjacencyState (78)}"
   ::= { xIsisESAdjEntry 5 }

xIsisESAdjNeighSNPAAddress OBJECT-TYPE
   SYNTAX OCTET STRING
   ACCESS read-write
   STATUS mandatory
   DESCRIPTION
       "The SNPA address of the neighboring system. This object
       follows the manualOrAutomatic behaviour."
   REFERENCE "ANSI {ISIS.aoi neighbourSNPAAddress (79)}"
   ::= { xIsisESAdjEntry 6 }

xIsisESAdjExistState OBJECT-TYPE
   SYNTAX INTEGER {
                  off(1),
                  on(2)
                  }
   ACCESS read-write
   STATUS mandatory
   DESCRIPTION
       "The existence state of this ES Adjacency. This object
       follows the ExistenceState behaviour. This object follows
       the manualOrAutomatic behaviour."
   ::= { xIsisESAdjEntry 7 }

xIsisESAdjESID OBJECT-TYPE
   SYNTAX OCTET STRING
   ACCESS read-only
   STATUS mandatory
   DESCRIPTION
       "An End System ID of a neighboring End System. This
       object follows the index and manualOrAutomatic
       behaviour."
   ::= { xIsisESAdjEntry 8 }                     


-- The Reachable Address Group

-- The Reachable Address Group is optional.


-- The Reachable Address Table

-- Each entry records information about a reachable address
-- (NSAP or address prefix) manually configured on the system
-- or learned through another protocol.

xIsisRATable OBJECT-TYPE
   SYNTAX SEQUENCE OF XIsisRAEntry
   ACCESS not-accessible
   STATUS mandatory
   DESCRIPTION
       "The table of Reachable Addresses to NSAPs or Address
       Prefixes."
   ::= { xIsisReachAddr 1 }

xIsisRAEntry OBJECT-TYPE
   SYNTAX XIsisRAEntry
   ACCESS not-accessible
   STATUS mandatory
   DESCRIPTION
       "Each entry defines a Reachable Address to a NSAP or
       Address Prefix."
   INDEX {  xIsisRASysInstance, xIsisRACircIndex, xIsisRAIndex }
   ::= { xIsisRATable 1 }

XIsisRAEntry ::=
   SEQUENCE {
      xIsisRASysInstance
         INTEGER,
      xIsisRACircIndex
         INTEGER,
      xIsisRAIndex
         INTEGER,
      xIsisRAExistState
         INTEGER,
      xIsisRAOperState
         INTEGER,
      xIsisRAAddrPrefix
        OCTET STRING,
      xIsisRAMapType
         INTEGER,
      xIsisRADefMetric
         INTEGER,
      xIsisRADelMetric
         INTEGER,
      xIsisRAExpMetric
         INTEGER,
      xIsisRAErrMetric
         INTEGER,
      xIsisRADefMetricType
         INTEGER,
      xIsisRADelMetricType
         INTEGER,
      xIsisRAExpMetricType
         INTEGER,
      xIsisRAErrMetricType
         INTEGER,
      xIsisRASNPAAddress
         OCTET STRING,
      xIsisRASNPAMask
         OCTET STRING,
      xIsisRASNPAPrefix
         OCTET STRING,
      xIsisRAType
         INTEGER
   }

xIsisRASysInstance OBJECT-TYPE
   SYNTAX INTEGER
   ACCESS read-only
   STATUS mandatory
   DESCRIPTION
       "The identifier of the Integrated IS-IS instance to which
       this row corresponds. This object follows the index and
       manualOrAutomatic behaviours."
   ::= { xIsisRAEntry 1 }

xIsisRACircIndex OBJECT-TYPE
   SYNTAX INTEGER
   ACCESS read-only
   STATUS mandatory
   DESCRIPTION
       "The identifier of the Circuit over which this
       destination is reachable. This object follows the index
       and manualOrAutomatic behaviours."
   ::= { xIsisRAEntry 2 }

xIsisRAIndex OBJECT-TYPE
   SYNTAX INTEGER
   ACCESS read-only
   STATUS mandatory
   DESCRIPTION
       "The identifier for this xIsisRAEntry. This value must be
       unique amongst all Reachable Addresses on the same parent
       Circuit. This object follows the index and
       manualOrAutomatic behaviours."
   ::= { xIsisRAEntry 3 }

xIsisRAExistState OBJECT-TYPE
   SYNTAX INTEGER {
                  off(1),
                  on(2)
                  }
   ACCESS read-write
   STATUS mandatory
   DESCRIPTION
       "The existence state of this Reachable Address. This
       object follows the ExistenceState and manualOrAutomatic
       behaviours."
   ::= { xIsisRAEntry 4 }

xIsisRAOperState OBJECT-TYPE
   SYNTAX INTEGER {
                  off(1),
                  on(2)
                  }
   ACCESS read-write
   STATUS mandatory
   DESCRIPTION
       "The operational state of the Reachable Address. This
       object follows the operationalState and manualOrAutomatic
       behaviours."
   ::= { xIsisRAEntry 5 }

xIsisRAAddrPrefix OBJECT-TYPE
   SYNTAX OCTET STRING
   ACCESS read-write
   STATUS mandatory
   DESCRIPTION
       "The destination of this Reachable Address. This is an
       Address Prefix. This object follows the
       replaceOnlyWhileDisabled and manualOrAutomatic
       behaviours."
   REFERENCE "ANSI {ISIS.aoi addressPrefix (98)}"
   ::= { xIsisRAEntry 6 }


xIsisRAMapType OBJECT-TYPE
   SYNTAX   INTEGER {
               none(1),
               explicit(2),
               extractIDI(3),
               extractDSP(4)
            }
   ACCESS read-write
   STATUS mandatory
   DESCRIPTION
       "The type of mapping to be employed to ascertain the SNPA
       Address which should be used in forwarding PDUs for this
       Reachable Address prefix. This object follows the
       manualOrAutomatic behaviour. The following values of
       mapping type are defined:

          none: The mapping is null because the neighbor SNPA is
          implicit by nature of the subnetwork (e.g. a
          point-to-point linkage).

          explicit: The subnetwork addresses in the object
          xIsisRASNPAAddress is to be used.

          extractIDI: The SNPA is embedded in the IDI of the
          destination NSAP Address. The mapping algorithm
          extracts the SNPA to be used according to the format
          and encoding rules of ISO8473/Add2. This SNPA
          extraction algorithm can be used in conjunction with
          Reachable Address prefixes from the X.121, F.69, E.163
          and E.164 addressing subdomains.

          extractDSP: All, or a suffix, of the SNPA is embedded
          in the DSP of the destination address. This SNPA
          extraction algorithm extracts the embedded subnetwork
          addressing information by performing a logical AND of
          the xIsisRASNPAMask object value with the destination
          address. The part of the SNPA extracted from the
          destination NSAP is appended to the xIsisRASNPAPrefix
          object value to form the next hop subnetwork
          addressing information."
   REFERENCE "ANSI {ISO10589-ISIS.aoi mappingType (107)}"
   ::= { xIsisRAEntry 7 }

xIsisRADefMetric OBJECT-TYPE
   SYNTAX INTEGER (1..63)
   ACCESS read-write
   STATUS mandatory
   DESCRIPTION
       "The default metric value for reaching the specified
       prefix over this circuit. This object follows the
       manualOrAutomatic behaviour."
   REFERENCE "ANSI {ISIS.aoi defaultMetric (99)}"
   ::= { xIsisRAEntry 8 }

xIsisRADelMetric OBJECT-TYPE
   SYNTAX INTEGER (0..63)
   ACCESS read-write
   STATUS mandatory
   DESCRIPTION
       "The delay metric for reaching the specified prefix over
       this circuit. This object follows the manualOrAutomatic
       behaviour. The value zero is reserved to indicate that
       this metric is not supported."
   REFERENCE "ANSI {ISIS.aoi delayMetric (100)}"
   ::= { xIsisRAEntry 9 }

xIsisRAExpMetric OBJECT-TYPE
   SYNTAX INTEGER (0..63)
   ACCESS read-write
   STATUS mandatory
   DESCRIPTION
       "The expense metric for reaching the specified prefix
       over this circuit. This object follows the
       manualOrAutomatic behaviour. The value zero is reserved
       to indicate that this metric is not supported."
   REFERENCE "ANSI {ISIS.aoi expenseMetric (101)}"
   ::= { xIsisRAEntry 10 }

xIsisRAErrMetric OBJECT-TYPE
   SYNTAX INTEGER (0..63)
   ACCESS read-write
   STATUS mandatory
   DESCRIPTION
       "The error metric for reaching the specified prefix over
       this circuit. This object follows the manualOrAutomatic
       behaviour. The value zero is reserved to indicate  that
       this metric is not supported."
   REFERENCE "ANSI {ISIS.aoi errorMetric (102)}"
   ::= { xIsisRAEntry 11 }

xIsisRADefMetricType OBJECT-TYPE
   SYNTAX INTEGER {
                  internal(1),
                  external(2)
                  }
   ACCESS read-write
   STATUS mandatory
   DESCRIPTION
       "Indicates whether the default metric is internal or
       external. This object follows the manualOrAutomatic
       behaviour."
   REFERENCE "ANSI {ISIS.aoi defaultMetricType (103)}"
   ::= { xIsisRAEntry 12 }

xIsisRADelMetricType OBJECT-TYPE
   SYNTAX INTEGER {
                  internal(1),
                  external(2)
                  }
   ACCESS read-write
   STATUS mandatory
   DESCRIPTION
       "Indicates whether the delay metric is internal or
       external. This object follows the manualOrAutomatic
       behaviour."
   REFERENCE "ANSI {ISO10589-ISIS.aoi delayMetricType (104)}"
   ::= { xIsisRAEntry 13 }

xIsisRAExpMetricType OBJECT-TYPE
   SYNTAX INTEGER {
                  internal(1),
                  external(2)
                  }
   ACCESS read-write
   STATUS mandatory
   DESCRIPTION
       "Indicates whether the expense metric is internal or
       external. This object follows the manualOrAutomatic
       behaviour."
   REFERENCE "ANSI {ISIS.aoi expenseMetricType (105)}"
   ::= { xIsisRAEntry 14 }

xIsisRAErrMetricType OBJECT-TYPE
   SYNTAX INTEGER {
                  internal(1),
                  external(2)
                  }
   ACCESS read-write
   STATUS mandatory
   DESCRIPTION
       "Indicates whether the error metric is internal or
       external. This object follows the manualOrAutomatic
       behaviour."
   REFERENCE "ANSI {ISIS.aoi errorMetricType (106)}"
   ::= { xIsisRAEntry 15 }

xIsisRASNPAAddress OBJECT-TYPE
   SYNTAX OCTET STRING
   ACCESS read-write
   STATUS mandatory
   DESCRIPTION
       "The SNPA Address to which a PDU may be forwarded in
       order to reach a destination which matches the address
       prefix of the Reachable Address. This object follows the
       manualOrAutomatic behaviour."
   REFERENCE "ANSI {ISIS.aoi sNPAAddresses (109)}"
-- note only one address may be specified per Reachable Address
-- in the MIB
   ::= { xIsisRAEntry 16 }

xIsisRASNPAMask OBJECT-TYPE
   SYNTAX OCTET STRING
   ACCESS read-write
   STATUS mandatory
   DESCRIPTION
       "A bit mask with 1 bits indicating the positions in the
       effective destination address from which embedded SNPA
       information is to be extracted. For the extraction the
       first octet of the xIsisRASNPAMask object value is aligned
       with the first octet (AFI) of the NSAP Address. If the
       xIsisRASNPAMask object value and NSAP Address are of
       different lengths, the shorter of the two is logically
       padded with zeros before performing the extraction. This
       object follows the manualOrAutomatic behaviour."
   REFERENCE "ANSI {ISIS.aoi sNPAMask (122)}"
   ::= { xIsisRAEntry 17 }

xIsisRASNPAPrefix OBJECT-TYPE
   SYNTAX OCTET STRING
   ACCESS read-write
   STATUS mandatory
   DESCRIPTION
       "A fixed SNPA prefix for use when the xIsisRAMapType is
       extractDSP. The SNPA Address to use is formed by
       concatenating the fixed SNPA prefix with a variable SNPA
       part that is extracted from the effective destination
       address. For Reachable Address prefixes in which the
       entire SNPA is embedded in the DSP the SNPA Prefix shall
       be null. This object follows the manualOrAutomatic
       behaviour."
   REFERENCE "ANSI {ISIS.aoi sNPAPrefix (123)}"
   ::= { xIsisRAEntry 18 }

xIsisRAType OBJECT-TYPE
    SYNTAX INTEGER {
    	manual(1),
	automatic(2)
    }
    ACCESS read-only
    STATUS mandatory
    DESCRIPTION
        "The type of Reachable address. Those of type 
        manual are created by the network manager. Those
        of type automatic are created through propogation
        of routing information from another routing
        protocol (eg. IDRP). "
    ::= { xIsisRAEntry 20 }

        
-- The Level 1 CLNP Destination Group

-- The Level 1 CLNP Destination Group is present if the system
-- supports Level 1 and forwards ISO 8473 packets.


-- The Level 1 CLNP Destination Table

-- The Level 1 CLNP Destination Table records information about
-- each end system ID destination known to the Intermediate
-- System in the system's level 1 forwarding database.

xIsisL1CLNPDestTable OBJECT-TYPE
   SYNTAX SEQUENCE OF XIsisL1CLNPDestEntry
   ACCESS not-accessible
   STATUS mandatory
   DESCRIPTION
       "The Level 1 CLNP Destination Table records information
       about each end system ID destination known to the
       Intermediate System."
   ::= { xIsisCLNPDest 1 }

xIsisL1CLNPDestEntry OBJECT-TYPE
   SYNTAX XIsisL1CLNPDestEntry
   ACCESS not-accessible
   STATUS mandatory
   DESCRIPTION
       "Each entry records information about one CLNP end system
       ID destination known to the Intermediate System."
   INDEX {  xIsisL1CLNPSysInstance, xIsisL1CLNPRouteMetricQOS, xIsisL1CLNPRouteDest, xIsisL1CLNPRouteForw }
   ::= { xIsisL1CLNPDestTable 1 }

XIsisL1CLNPDestEntry ::=
   SEQUENCE {
      xIsisL1CLNPRouteDest
         OCTET STRING,
      xIsisL1CLNPRouteMetricQOS
         INTEGER,
      xIsisL1CLNPRouteMetricType
         INTEGER,
      xIsisL1CLNPRouteMetricValue
         INTEGER,
      xIsisL1CLNPRouteForw
         OBJECT IDENTIFIER,
      xIsisL1CLNPRouteSource
         INTEGER,
      xIsisL1CLNPSysInstance
         INTEGER
   }


xIsisL1CLNPRouteDest OBJECT-TYPE
   SYNTAX OCTET STRING
   ACCESS read-only
   STATUS mandatory
   DESCRIPTION
       "The destination end system ID."
   ::= { xIsisL1CLNPDestEntry 2 }

xIsisL1CLNPRouteMetricQOS OBJECT-TYPE
   SYNTAX INTEGER {
                  default(1),
                  delay(2),
                  expense(3),
                  error(4)
                  }
   ACCESS read-only
   STATUS mandatory
   DESCRIPTION
       "The QOS metric for this destination."
   ::= { xIsisL1CLNPDestEntry 3 }

xIsisL1CLNPRouteMetricType OBJECT-TYPE
   SYNTAX   INTEGER  {
               internal(1),
               external(2)
            }
   ACCESS read-only
   STATUS mandatory
   DESCRIPTION
       "Indicates whether the metric has an external component
       or not"
   ::= { xIsisL1CLNPDestEntry 4 }

xIsisL1CLNPRouteMetricValue OBJECT-TYPE
   SYNTAX INTEGER (0..1023)
   ACCESS read-only
   STATUS mandatory
   DESCRIPTION
       "The path metric value for this destination."
   ::= { xIsisL1CLNPDestEntry 5 }

xIsisL1CLNPRouteForw OBJECT-TYPE
   SYNTAX OBJECT IDENTIFIER
   ACCESS read-only
   STATUS mandatory
   DESCRIPTION
       "The OBJECT IDENTIFIER for the first object in the table
       entry which corresponds to the entry used for forwarding
       packets to this destination. This value is an OBJECT
       IDENTIFIER for an instance of the object:
       xIsisESAdjSysInstance or xIsisISAdjSysInstance."
   ::= { xIsisL1CLNPDestEntry 6 }

xIsisL1CLNPRouteSource OBJECT-TYPE
   SYNTAX   INTEGER {
               manual(1),
               level1(2),
               esis(3)
            }
   ACCESS read-only
   STATUS mandatory
   DESCRIPTION
       "The source of the destination. Manual is used if the
       source is manually configured information on the system.
       Level1 is used if the source is Level 1 LSPs. Esis is
       used if the source is ES Hellos"
   ::= { xIsisL1CLNPDestEntry 7 }


xIsisL1CLNPSysInstance OBJECT-TYPE
   SYNTAX INTEGER
   ACCESS read-only
   STATUS mandatory
   DESCRIPTION
       "If the value of xIsisL1CLNPRouteSource is manual or
       level1 then this is the identifier of the Integrated
       IS-IS Level 1 instance from which this reachability
       information was learned, otherwise this value is zero."
   ::= { xIsisL1CLNPDestEntry 1 }

-- The Level 2 CLNP Destination Group

-- The Level 2 CLNP Destination Group is present if the system
-- supports Level 2 and forwards ISO 8473 packets.


-- The Level 2 CLNP Destination Table

-- The Level 2 CLNP Destination Table records information about
-- each NSAP Address Prefix known to the Intermediate
-- System

xIsisL2CLNPDestTable OBJECT-TYPE
   SYNTAX SEQUENCE OF XIsisL2CLNPDestEntry
   ACCESS not-accessible
   STATUS mandatory
   DESCRIPTION
       "The Level 2 CLNP Destination Table records information
       about each NSAP Address Prefix known to the Intermediate
       System."
   ::= { xIsisCLNPDest 2 }

xIsisL2CLNPDestEntry OBJECT-TYPE
   SYNTAX XIsisL2CLNPDestEntry
   ACCESS not-accessible
   STATUS mandatory
   DESCRIPTION
       "Each entry records information about one NSAP Address
       Prefix known to the Intermediate System."
   INDEX {  xIsisL2CLNPSysInstance, xIsisL2CLNPRouteMetricQOS, xIsisL2CLNPRouteDest, xIsisL2CLNPRouteForw }
   ::= { xIsisL2CLNPDestTable 1 }

XIsisL2CLNPDestEntry ::=
   SEQUENCE {
      xIsisL2CLNPRouteDest
         OCTET STRING,
      xIsisL2CLNPRouteMetricQOS
         INTEGER,
      xIsisL2CLNPRouteMetricType
         INTEGER,
      xIsisL2CLNPRouteMetricValue
         INTEGER,
      xIsisL2CLNPRouteForw
         OBJECT IDENTIFIER,
      xIsisL2CLNPRouteSource
         INTEGER,
      xIsisL2CLNPSysInstance
         INTEGER
   }

xIsisL2CLNPRouteDest OBJECT-TYPE
   SYNTAX OCTET STRING
   ACCESS read-only
   STATUS mandatory
   DESCRIPTION
       "The destination address prefix."
   ::= { xIsisL2CLNPDestEntry 2 }

xIsisL2CLNPRouteMetricQOS OBJECT-TYPE
   SYNTAX INTEGER {
                  default(1),
                  delay(2),
                  expense(3),
                  error(4)
                  }
   ACCESS read-only
   STATUS mandatory
   DESCRIPTION
       "The QOS metric for this destination."
   ::= { xIsisL2CLNPDestEntry 3 }

xIsisL2CLNPRouteMetricType OBJECT-TYPE
   SYNTAX   INTEGER  {
               internal(1),
               external(2)
            }
   ACCESS read-only
   STATUS mandatory
   DESCRIPTION
       "Indicates whether the metric has an external component
       or not"
   ::= { xIsisL2CLNPDestEntry 4 }

xIsisL2CLNPRouteMetricValue OBJECT-TYPE
   SYNTAX INTEGER (0..1023)
   ACCESS read-only
   STATUS mandatory
   DESCRIPTION
       "The path metric value for this destination."
   ::= { xIsisL2CLNPDestEntry 5 }

xIsisL2CLNPRouteForw OBJECT-TYPE
   SYNTAX OBJECT IDENTIFIER
   ACCESS read-only
   STATUS mandatory
   DESCRIPTION
       "The OBJECT IDENTIFIER for the first object in the table
       entry which corresponds to the entry used for forwarding
       packets to this destination. This value is an OBJECT
       IDENTIFIER for an instance of one of the following
       objects: isisVirtSysInstance, xIsisISAdjSysInstance,
       xIsisRASysInstance."
   ::= { xIsisL2CLNPDestEntry 6 }

xIsisL2CLNPRouteSource OBJECT-TYPE
   SYNTAX   INTEGER {
               manual(1),
               level2(2)
            }
   ACCESS read-only
   STATUS mandatory
   DESCRIPTION
       "The source of the destination. Manual is used if the
       source is manually configured information on the system.
       Level2 is used if the source is Level 2 LSPs."
   ::= { xIsisL2CLNPDestEntry 7 }

xIsisL2CLNPSysInstance OBJECT-TYPE
   SYNTAX INTEGER
   ACCESS read-only
   STATUS mandatory
   DESCRIPTION
       "The identifier of the Integrated IS-IS Level 2 instance
       from which this reachability information was learned."
   ::= { xIsisL2CLNPDestEntry 1 }


-- The Level 3 CLNP Destination Group

-- The Level 3 CLNP Destination Group is present if the system
-- supports reachable addresses
--  and forwards ISO 8473 packets.


-- The Level 3 CLNP Destination Table

-- The Level 3 CLNP Destination Table records information about
-- each Reachable Address Prefix known to the Intermediate
-- System

xIsisL3CLNPDestTable OBJECT-TYPE
   SYNTAX SEQUENCE OF XIsisL3CLNPDestEntry
   ACCESS not-accessible
   STATUS mandatory
   DESCRIPTION
       "The Level 3 CLNP Destination Table records information
       about each Reachable Address Prefix known to the Intermediate
       System."
   ::= { xIsisCLNPDest 3 }

xIsisL3CLNPDestEntry OBJECT-TYPE
   SYNTAX XIsisL3CLNPDestEntry
   ACCESS not-accessible
   STATUS mandatory
   DESCRIPTION
       "Each entry records information about one Address
       Prefix known to the Intermediate System."
   INDEX {  xIsisL3CLNPSysInstance, xIsisL3CLNPRouteMetricQOS, xIsisL3CLNPRouteDest, xIsisL3CLNPRouteForw }
   ::= { xIsisL3CLNPDestTable 1 }

XIsisL3CLNPDestEntry ::=
   SEQUENCE {
      xIsisL3CLNPRouteDest
        OCTET STRING,
      xIsisL3CLNPRouteMetricQOS
         INTEGER,
      xIsisL3CLNPRouteMetricType
         INTEGER,
      xIsisL3CLNPRouteMetricValue
         INTEGER,
      xIsisL3CLNPRouteForw
         OBJECT IDENTIFIER,
      xIsisL3CLNPRouteSource
         INTEGER,
      xIsisL3CLNPSysInstance
         INTEGER
   }

xIsisL3CLNPRouteDest OBJECT-TYPE
   SYNTAX OCTET STRING
   ACCESS read-only
   STATUS mandatory
   DESCRIPTION
       "The destination address prefix."
   ::= { xIsisL3CLNPDestEntry 2 }

xIsisL3CLNPRouteMetricQOS OBJECT-TYPE
   SYNTAX INTEGER {
                  default(1),
                  delay(2),
                  expense(3),
                  error(4)
                  }
   ACCESS read-only
   STATUS mandatory
   DESCRIPTION
       "The QOS metric for this destination."
   ::= { xIsisL3CLNPDestEntry 3 }

xIsisL3CLNPRouteMetricType OBJECT-TYPE
   SYNTAX   INTEGER  {
               internal(1),
               external(2)
            }
   ACCESS read-only
   STATUS mandatory
   DESCRIPTION
       "Indicates whether the metric has an external component
       or not"
   ::= { xIsisL3CLNPDestEntry 4 }

xIsisL3CLNPRouteMetricValue OBJECT-TYPE
   SYNTAX INTEGER (0..1023)
   ACCESS read-only
   STATUS mandatory
   DESCRIPTION
       "The path metric value for this destination."
   ::= { xIsisL3CLNPDestEntry 5 }

xIsisL3CLNPRouteForw OBJECT-TYPE
   SYNTAX OBJECT IDENTIFIER
   ACCESS read-only
   STATUS mandatory
   DESCRIPTION
       "The OBJECT IDENTIFIER for the first object in the table
       entry which corresponds to the entry used for forwarding
       packets to this destination. This value is an OBJECT
       IDENTIFIER for an instance of one of the following
       objects: isisVirtSysInstance, xIsisISAdjSysInstance,
       xIsisRASysInstance."
   ::= { xIsisL3CLNPDestEntry 6 }

xIsisL3CLNPRouteSource OBJECT-TYPE
   SYNTAX   INTEGER {
               manual(1),
               level2(2)
            }
   ACCESS read-only
   STATUS mandatory
   DESCRIPTION
       "The source of the destination. Manual is used if the
       source is manually configured information on the system.
       Level3 is used if the source is Level 3 LSPs."
   ::= { xIsisL3CLNPDestEntry 7 }

xIsisL3CLNPSysInstance OBJECT-TYPE
   SYNTAX INTEGER
   ACCESS read-only
   STATUS mandatory
   DESCRIPTION
       "The identifier of the Integrated IS-IS Level 3 instance
       from which this reachability information was learned."
   ::= { xIsisL3CLNPDestEntry 1 }

-- The Circuit CLNS Group

-- The Circuit IS Group is always present.


-- The Circuit CLNS Table

-- The Circuit CLNS Table contains objects controlling the
-- operation of the IS functions of the CLNS protocol
-- (ISO 8473) on each circuit over which ISIS is run.

xIsisCircClnsTable OBJECT-TYPE
   SYNTAX SEQUENCE OF XIsisCircClnsEntry
   ACCESS not-accessible
   STATUS mandatory
   DESCRIPTION
       "The set of objects controlling the operation of the
			  CLNS protocol (ISO 8473) on each
       circuit over which ISIS is run."
   ::= { xIsisCirc 3 }

xIsisCircClnsEntry OBJECT-TYPE
   SYNTAX XIsisCircClnsEntry
   ACCESS not-accessible
   STATUS mandatory
   DESCRIPTION
       "Each entry contains objects controlling the operation of
       the CLNS protocol (ISO 8473) on one
       circuit."
   INDEX {  xIsisCircClnsIndex }
   ::= { xIsisCircClnsTable 1 }

XIsisCircClnsEntry ::=
   SEQUENCE {
      xIsisCircClnsSysInstance
         INTEGER,
      xIsisCircClnsIndex
         INTEGER,
      xIsisCircClnsExistState
         INTEGER,
      xIsisCircClnsOperState
         INTEGER,
      xIsisCircClnsRxPDUs
         Counter,
      xIsisCircClnsTxPDUs
         Counter
   }
xIsisCircClnsSysInstance OBJECT-TYPE
   SYNTAX INTEGER
   ACCESS read-only
   STATUS mandatory
   DESCRIPTION            
       "The identifier of the Integrated IS-IS instance to which
       this row corresponds. This object follows the index and
       manualOrAutomatic behaviours."
   ::= { xIsisCircClnsEntry 1 }

xIsisCircClnsIndex OBJECT-TYPE
   SYNTAX INTEGER
   ACCESS read-only
   STATUS mandatory
   DESCRIPTION
       "The unique identifier of this row. This value is the
       same as the value of the ifIndex object which identifies
       the interface which corresponds to this circuit. This
       object follows the index behaviour."
   ::= { xIsisCircClnsEntry 2 }

xIsisCircClnsExistState OBJECT-TYPE
   SYNTAX INTEGER {
                  off(1),
                  on(2)
                  }
   ACCESS read-only
   STATUS mandatory
   DESCRIPTION
       "The existence state of this row. This object follows the
       ExistenceState behaviour."
   ::= { xIsisCircClnsEntry 3 }

xIsisCircClnsOperState OBJECT-TYPE
   SYNTAX INTEGER {
                  off(1),
                  on(2)
                  }
   ACCESS read-write
   STATUS mandatory
   DESCRIPTION
       "The operational state of the row. This object follows
       the operationalState behaviour."
   ::= { xIsisCircClnsEntry 4 }

xIsisCircClnsRxPDUs OBJECT-TYPE
   SYNTAX Counter
   ACCESS read-only
   STATUS mandatory
   DESCRIPTION
       "Counter of number of CLNS PDUs received on this
	circuit."
   ::= { xIsisCircClnsEntry 5 }

xIsisCircClnsTxPDUs OBJECT-TYPE
   SYNTAX Counter
   ACCESS read-only
   STATUS mandatory
   DESCRIPTION
       "Counter of number of CLNS PDUs transmitted on this
	circuit."
   ::= { xIsisCircClnsEntry 6 }

END
