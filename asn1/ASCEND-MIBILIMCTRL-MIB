--			Ascend mibilimctrl MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBILIMCTRL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibilimCtrlProfile  OBJECT IDENTIFIER ::= { configuration 152}

	-- The mibilimCtrlProfile table
	--
	-- This table contains parameters for the mibilimCtrlProfile profile
	--

    mibilimCtrlProfileTable	OBJECT-TYPE
	SYNTAX		SEQUENCE OF MibilimCtrlProfileEntry
	ACCESS		not-accessible
	STATUS		mandatory
	DESCRIPTION	"A list of mibilimCtrlProfile profile entries."
	::= { mibilimCtrlProfile 1 }

    mibilimCtrlProfileEntry	OBJECT-TYPE
	SYNTAX		MibilimCtrlProfileEntry
	ACCESS		not-accessible
	STATUS		mandatory
	DESCRIPTION	"A mibilimCtrlProfile entry containing objects that
			 maps to the parameters of mibilimCtrlProfile profile."
	INDEX		{ ilimCtrlProfile-Shelf-o, ilimCtrlProfile-Slot-o, ilimCtrlProfile-Item-o }
	::= { mibilimCtrlProfileTable 1 }

    MibilimCtrlProfileEntry ::=
	SEQUENCE {
	    ilimCtrlProfile-Shelf-o
		INTEGER,
	    ilimCtrlProfile-Slot-o
		INTEGER,
	    ilimCtrlProfile-Item-o
		INTEGER,
	    ilimCtrlProfile-PrimaryLpm
		INTEGER,
	    ilimCtrlProfile-ActiveLine
		INTEGER,
	    ilimCtrlProfile-Action-o
		INTEGER
	}

    ilimCtrlProfile-Shelf-o	OBJECT-TYPE
	SYNTAX	INTEGER
	ACCESS	read-only
	STATUS	mandatory
	DESCRIPTION	""
	::= { mibilimCtrlProfileEntry 1 }

    ilimCtrlProfile-Slot-o	OBJECT-TYPE
	SYNTAX	INTEGER
	ACCESS	read-only
	STATUS	mandatory
	DESCRIPTION	""
	::= { mibilimCtrlProfileEntry 2 }

    ilimCtrlProfile-Item-o	OBJECT-TYPE
	SYNTAX	INTEGER
	ACCESS	read-only
	STATUS	mandatory
	DESCRIPTION	""
	::= { mibilimCtrlProfileEntry 3 }

    ilimCtrlProfile-PrimaryLpm	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"Which LPM is the primary control for the interface"
	::= { mibilimCtrlProfileEntry 4 }

    ilimCtrlProfile-ActiveLine	OBJECT-TYPE
	SYNTAX	INTEGER {
		    workingLine (1),
		    protectionLine (2),
		    backupLine (3)
		}
	ACCESS	read-write
	STATUS	mandatory
	DESCRIPTION	"Administrative request for current active line or line interface"
	::= { mibilimCtrlProfileEntry 5 }

    ilimCtrlProfile-Action-o	OBJECT-TYPE
	SYNTAX	INTEGER {
		    noAction (1),
		    createProfile (2),
		    deleteProfile (3)
		}
	ACCESS	read-write
	STATUS	mandatory
	DESCRIPTION	""
	::= { mibilimCtrlProfileEntry 6 }

END
