USR-ATM-1483-PVC-MIB DEFINITIONS ::= BEGIN
  IMPORTS
      OBJECT-TYPE, MODULE-IDENTITY, 
      IpAddress, Integer32
          FROM SNMPv2-SMI
      RowStatus
          FROM SNMPv2-TC
      common, UsrConfigStatus, UsrDisplayString
          FROM USR-DEFINITIONS-MIB
      AtmVpIdentifier, AtmVcIdentifier
	  FROM ATM-TC-MIB;
  usrAtm1483Pvc    MODULE-IDENTITY
                   LAST-UPDATED "200204061409Z"
                   ORGANIZATION "CommWorks Corporation, a 3Com Company"
                   CONTACT-INFO "Customer Support"
                   DESCRIPTION
                           "The commWorks enterprise defined MIB objects for
                            the Netserver ATM."
--                 REVISION     "200204061409Z"
--                 DESCRIPTION  "Added MODULE-IDENTITY and corrected SNMPv2 
--                               syntax."
                   ::= { common 47 }
  usrAtm1483PvcConfigFileName OBJECT-TYPE
      SYNTAX      UsrDisplayString
      MAX-ACCESS  read-only
      STATUS      current
      DESCRIPTION		
	 "The name of a ConfigFile to read/write permanent
	  database records. If the value of this object is an
          empty string, then ATM 1483 uses the default
          name `@file://Atm1483.cfg'. "
     ::= { usrAtm1483Pvc 1 }
  usrAtm1483PvcCFMStatusFlag  OBJECT-TYPE
      SYNTAX	  UsrConfigStatus
      MAX-ACCESS  read-write
      STATUS      current
      DESCRIPTION
	  "Setting the value of this object to `save' causes the values
	   of the ATM ARP MIB objects to be written out to the
           current config file, which is stored in the 
           usrIpoaArpConfigFileName object. While the new
           ConfigFile is being written, ATM ARP
	   will set the value of this flag to `saving''. Any
	   attempts to set the value while it is not `normal'
	   (i.e. the file is currently being written to the
	   ConfigFile) while result in a badValue error being
	   returned. Setting the value to `normal' will result in no
	   action."
     ::= { usrAtm1483Pvc 2 }
  --
  -- The ATM 1483 PVC Table
  --
  usrAtm1483PvcTable OBJECT-TYPE
      SYNTAX      SEQUENCE OF UsrAtm1483PvcEntry
      MAX-ACCESS  not-accessible
      STATUS      current
      DESCRIPTION
          "This usrAtm1483PvcTable keeps a set of PVCs and
           creates a corresponding entry in the appropriate
           protocol ARP cache or equivalent."
      ::= { usrAtm1483Pvc 3 }
  usrAtm1483PvcEntry OBJECT-TYPE
      SYNTAX      UsrAtm1483PvcEntry
      MAX-ACCESS  not-accessible
      STATUS      current
      DESCRIPTION
          "A PVC that this host has opened with another host for
          data transfer of datagrams using the encapsulation
          specified in RFC1483. Additional information
          can be determined about the VC from RFC1695, the AToM MIB.
	  When an entry is added to this table, if the corresponding
          network protocol is IP, an entry is added to the 
          ipNetToMediaTable (ARP Cache) to allow the translation of 
          an IP address to the RFC1483 PVC created in this table, 
          and the PVC created in the RFC1695 AToM MIB."
      INDEX       { usrAtm1483PvcName
                  }
      ::= { usrAtm1483PvcTable 1 }
  UsrAtm1483PvcEntry ::= SEQUENCE {
      usrAtm1483PvcName                 UsrDisplayString,
      usrAtm1483PvcVpi                  AtmVpIdentifier,
      usrAtm1483PvcVci                  AtmVcIdentifier,
      usrAtm1483PvcPort			Integer32,
      usrAtm1483PvcPcr			Integer32,
      usrAtm1483PvcNetworkName          UsrDisplayString,
      usrAtm1483PvcNetworkAddr          IpAddress,
      usrAtm1483PvcProtocol             INTEGER,
      usrAtm1483PvcRowStatus            RowStatus }
  usrAtm1483PvcName OBJECT-TYPE
      SYNTAX      UsrDisplayString (SIZE(0..32))
      MAX-ACCESS  not-accessible
      STATUS      current
      DESCRIPTION
         "A string containing the name of the RFC1483 PVC."
      --CONFIGURABLE
      ::= { usrAtm1483PvcEntry 1 }
  usrAtm1483PvcVpi OBJECT-TYPE
      SYNTAX      AtmVpIdentifier
      MAX-ACCESS  read-create
      STATUS      current
      DESCRIPTION
          "The VPI value for the RFC1483 PVC."
	 --CONFIGURABLE
      ::= { usrAtm1483PvcEntry 2 }
  usrAtm1483PvcVci OBJECT-TYPE
      SYNTAX      AtmVcIdentifier
      MAX-ACCESS  read-create
      STATUS      current
      DESCRIPTION
          "The VCI value for the RFC1483 PVC."
	 --CONFIGURABLE
      ::= { usrAtm1483PvcEntry 3 }
  usrAtm1483PvcPort OBJECT-TYPE
      SYNTAX Integer32(1..2)
      MAX-ACCESS  read-create
      STATUS      current
      DESCRIPTION
         "The port number for the RFC1483 PVC."
      --CONFIGURABLE
      ::= { usrAtm1483PvcEntry 4 }
  usrAtm1483PvcPcr OBJECT-TYPE
      SYNTAX Integer32(1000..100000)
      MAX-ACCESS  read-create
      STATUS      current
      DESCRIPTION
         "The peak cell rate value to use when creating this PVC."
      --CONFIGURABLE
      ::= { usrAtm1483PvcEntry 5 }
  usrAtm1483PvcNetworkName OBJECT-TYPE
      SYNTAX      UsrDisplayString (SIZE(0..32))
      MAX-ACCESS  read-create
      STATUS      current
      DESCRIPTION
         "A string containing the name of the network of this RFC1483 PVC."
      --CONFIGURABLE
      ::= { usrAtm1483PvcEntry 6 }
  usrAtm1483PvcNetworkAddr OBJECT-TYPE
      SYNTAX IpAddress
      MAX-ACCESS  read-create
      STATUS      current
      DESCRIPTION
         "The network layer address of the end station that this
          RFC1483 PVC connects to.  This value is placed in the 
          ARP cache as a static entry so that the IP forwarder
          may map traffic destined for this network address to 
          this RFC1483 PVC."
      --CONFIGURABLE
      ::= { usrAtm1483PvcEntry 7 }
  usrAtm1483PvcProtocol OBJECT-TYPE
      SYNTAX INTEGER {
		     ip(1),
		     ipx(2),
		     at(3)
		     }
      MAX-ACCESS  read-only
      STATUS      current
      DESCRIPTION
         "The Level 3 protocol running over this RFC1483 PVC."
      --CONFIGURABLE
      ::= { usrAtm1483PvcEntry 8 }
  usrAtm1483PvcRowStatus OBJECT-TYPE
      SYNTAX      RowStatus
      MAX-ACCESS  read-create
      STATUS      current
      DESCRIPTION
         "This object allows rows to be created and deleted in the
          usrAtm1483PvcTable. For a PVC on an IP network, an entry 
          in this table will have a corresponding ipNetToMediaEntry 
          to allow the translation of an IP address to this PVC. Setting 
          this object to destroy(6) removes the corresponding 
          ipNetToMediaTable entry, if any."
     REFERENCE
         "RFC 1903, 'Textual Conventions for version 2 of the Simple
         Network Management Protocol (SNMPv2).'"
	 --CONFIGURABLE
     ::= { usrAtm1483PvcEntry 9 }
  usrAtm1483PvcDefaultPcr OBJECT-TYPE
      SYNTAX Integer32
      MAX-ACCESS  read-only
      STATUS      current
      DESCRIPTION
         "An integer containing the default peak cell rate to use
	  when establishing VCs.  This value is one tenth the speed
          of the physical interface expressed as a cell rate."
      ::= { usrAtm1483Pvc 4 }
  END -- End of USR-ATM-1483-PVC-MIB DEFINITIONS
-- ************************************************************************
--
--	usr_atm_1577_pvc.mib - MIB defined for supporting CLI commands for
--                             1577 PVCs.
--
-- Author:         
--
