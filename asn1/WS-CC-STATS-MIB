WS-CC-STATS-MIB DEFINITIONS ::= BEGIN
 
		IMPORTS
			OBJECT-GROUP, MODULE-COMPLIANCE			
				FROM SNMPv2-CONF			
			TimeTicks, Integer32, Unsigned32, Gauge32, Counter32, 
			Counter64, OBJECT-TYPE, MODULE-IDENTITY			
				FROM SNMPv2-SMI			
			DisplayString, TruthValue, PhysAddress, TEXTUAL-CONVENTION			
				FROM SNMPv2-TC			
			wsCcStats			
				FROM WS-CC-SMI			
			DoActionNow, RadioType			
				FROM WS-TYPE-MIB;

		-- 1.3.6.1.4.1.388.14.3.3.1
		wsCcStatsMIB MODULE-IDENTITY 
			LAST-UPDATED "200809260455Z"		-- September 26, 2008 at 04:55 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200809261517Z"		-- September 26, 2008 at 15:17 GMT
			DESCRIPTION 
				"01a26
				Added the object wsCcStatsMeshRadioIndex."
			REVISION "200808251023Z"		-- August 25, 2008 at 10:23 GMT
			DESCRIPTION 
				"01a24
				The object wsCcStatsMeshAbsSnr was named incorrectly.
				It was meant to contain the average bit speed.
				Renamed the object wsCcStatsMeshAvgBitSpeed and
				made required corrections in the object."
			REVISION "200808121118Z"		-- August 12, 2008 at 11:18 GMT
			DESCRIPTION 
				"01a23
				Changed the syntax of wsCcStatsMeshRadioType to RadioType."
			REVISION "200807241924Z"		-- July 24, 2008 at 19:24 GMT
			DESCRIPTION 
				"01a22
				Added objects for Voice Statistics."
			REVISION "200807011307Z"		-- July 01, 2008 at 13:07 GMT
			DESCRIPTION 
				"01a21
				
				Made the following changes in wsCcStatsMeshTable:
				1. Removed the columns:
				- wsCcStatsMeshTxPktsUcast
				- wsCcStatsMeshRxPktsUcast
				- wsCcStatsMeshTxOctetsUcast
				- wsCcStatsMeshRxOctetsUcast
				- wsCcStatsMeshRxUndecryptablePkts
				
				2. Added the columns:
				- wsCcStatsMeshThroughput
				- wsCcStatsMeshAbsSnr
				- wsCcStatsMeshRetries100"
			REVISION "200806041713Z"		-- June 04, 2008 at 17:13 GMT
			DESCRIPTION 
				"01a20
				Added Mesh Statistics under wsCcStatsMesh."
			REVISION "200712171634Z"		-- December 17, 2007 at 16:34 GMT
			DESCRIPTION 
				"01a19
				Added UNITS for wsCcStatsRadioExtDownLinkThroughput and
				wsCcStatsRadioExtUpLinkThroughput."
			REVISION "200710171055Z"		-- October 17, 2007 at 10:55 GMT
			DESCRIPTION 
				"01a18
				Added wsCcStatsRadioExtTable."
			REVISION "200709261254Z"		-- September 26, 2007 at 12:54 GMT
			DESCRIPTION 
				"01a17
				Added new index thresholdAvgPortalNoiseSuddenChange 
				to wsCcStatsTrapCtrlConfIndex"
			REVISION "200705301306Z"		-- May 30, 2007 at 13:06 GMT
			DESCRIPTION 
				"01a16"
			REVISION "200605241618Z"		-- May 24, 2006 at 16:18 GMT
			DESCRIPTION 
				"01a15"
			REVISION "200512271846Z"		-- December 27, 2005 at 18:46 GMT
			DESCRIPTION 
				"01a14"
			REVISION "200512271538Z"		-- December 27, 2005 at 15:38 GMT
			DESCRIPTION 
				"01a13"
			REVISION "200511141902Z"		-- November 14, 2005 at 19:02 GMT
			DESCRIPTION 
				"01a12"
			REVISION "200510241838Z"		-- October 24, 2005 at 18:38 GMT
			DESCRIPTION 
				"01a11"
			REVISION "200509161338Z"		-- September 16, 2005 at 13:38 GMT
			DESCRIPTION 
				"01a10"
			REVISION "200509161227Z"		-- September 16, 2005 at 12:27 GMT
			DESCRIPTION 
				"01a09"
			REVISION "200509151748Z"		-- September 15, 2005 at 17:48 GMT
			DESCRIPTION 
				"01a08"
			REVISION "200509151645Z"		-- September 15, 2005 at 16:45 GMT
			DESCRIPTION 
				"01a07"
			REVISION "200509151425Z"		-- September 15, 2005 at 14:25 GMT
			DESCRIPTION 
				"01a06"
			REVISION "200509141654Z"		-- September 14, 2005 at 16:54 GMT
			DESCRIPTION 
				"01a05"
			REVISION "200507191043Z"		-- July 19, 2005 at 10:43 GMT
			DESCRIPTION 
				"01a04"
			REVISION "200507191022Z"		-- July 19, 2005 at 10:22 GMT
			DESCRIPTION 
				"01a03"
			REVISION "200507141647Z"		-- July 14, 2005 at 16:47 GMT
			DESCRIPTION 
				"01a02"
			REVISION "200507071355Z"		-- July 07, 2005 at 13:55 GMT
			DESCRIPTION 
				"01a01"
			::= { wsCcStats 1 }

		SinglePointer ::= INTEGER (0..255)

-- Values of this type are passwords.  They can be written,
-- but when read, they return a 0-length string.
		Password ::= OCTET STRING (SIZE (0..255))

-- In order to make the switch's implementation of 
-- numerous tables simpler, tables using this datatype
-- have a fixed number of entries with fixed indices.
-- In such tables, no entries may be added or deleted, 
-- but the pre-existing rows can be enabled or disabled 
-- using the value declared with this datatype.
		StaticRowEnable ::= INTEGER
			{
			enable(1),
			disable(2)
			}

		PartsPer10k ::= Unsigned32 (0..10000)
-- This datatype is used for all percentage values that have
-- interesting tenths and hundreths, (such as 1.37%).  SNMP
-- cannot report decimals, only whole numbers.  Values of 
-- this datatype are expressed not as parts-per-100, (percent),
-- but as parts-per-10000.
-- 
-- Said another way, values of this type are percent 
-- multiplied by 100.
-- 
-- For example, 1.37% would be reported as 137.
-- 
		ScaleBy100 ::= Unsigned32
-- This datatype is used for all values that have interesting 
-- tenths and hundreths, (such as 2.48).  SNMP cannot report 
-- decimals, only whole numbers.  Values of this datatype are 
-- scaled (muliplied) by 100.
-- 
-- For example, 2.48 would be reported as 248.
-- In order to make the switch's implementation of some
-- dynamic tables simpler, tables using this datatype
-- use an abbreviated form of RowStatus.
-- 
-- Only CreateAndGo and Destroy states are supported.
-- 
-- On row creation, a single SET-PDU must contain all
-- the required values, including this value set to
-- createAndGo.  (This greatly simplifies row validation
-- for the switch).
-- 
-- Setting this value to Destroy causes the corresponding
-- row to be deleted.
-- 
		AbbrevRowStatus ::= INTEGER
			{
			createAndGo(4),
			destroy(6)
			}

-- This datatype always means that the MIB variable is
-- a simple ENUM that when written to 'doActionRightNow', 
-- causes the described action to take place, (much like 
-- a button pressed in a UI).
-- 
-- Such a value DOES remain in state 'doActionRightNow'
-- while the operation is in-process;  when the operation is
-- completed, it will then return the value 'idleState'.
		DoActionShowProgress ::= INTEGER
			{
			doActionRightNow(1),
			idleState(2)
			}

-- Values of this type are keys, expressed in hexadecimal as
-- a sequence of characters '0'..'9' plus 'A'..'F'.
-- 
-- Unless otherwise noted, the default value for variables of
-- this type is all-0s.
-- 
-- Values of this type are passwords.  They can be written,
-- but when read, they return a 0-length string.
		HexPassword ::= OCTET STRING (SIZE (0..255))

	
--
-- Textual conventions
--
	
		RowStatus ::= TEXTUAL-CONVENTION
			STATUS current
			DESCRIPTION 
				"The RowStatus textual convention is used to manage the
				creation and deletion of conceptual rows, and is used as the
				value of the SYNTAX clause for the status column of a
				conceptual row (as described in Section 7.7.1 of [2].)
				
				The status column has six defined values:
				
				     - `active', which indicates that the conceptual row is
				     available for use by the managed device;
				
				     - `notInService', which indicates that the conceptual
				     row exists in the agent, but is unavailable for use by
				     the managed device (see NOTE below);
				
				     - `notReady', which indicates that the conceptual row
				     exists in the agent, but is missing information
				     necessary in order to be available for use by the
				     managed device;
				
				     - `createAndGo', which is supplied by a management
				     station wishing to create a new instance of a
				     conceptual row and to have its status automatically set
				     to active, making it available for use by the managed
				     device;
				
				     - `createAndWait', which is supplied by a management
				     station wishing to create a new instance of a
				     conceptual row (but not make it available for use by
				     the managed device); and,
				
				     - `destroy', which is supplied by a management station
				     wishing to delete all of the instances associated with
				     an existing conceptual row.
				
				Whereas five of the six values (all except `notReady') may
				be specified in a management protocol set operation, only
				three values will be returned in response to a management
				protocol retrieval operation:  `notReady', `notInService' or
				`active'.  That is, when queried, an existing conceptual row
				has only three states:  it is either available for use by
				the managed device (the status column has value `active');
				it is not available for use by the managed device, though
				the agent has sufficient information to make it so (the
				status column has value `notInService'); or, it is not
				available for use by the managed device, and an attempt to
				make it so would fail because the agent has insufficient
				information (the state column has value `notReady').
				
				                         NOTE WELL
				
				     This textual convention may be used for a MIB table,
				     irrespective of whether the values of that table's
				     conceptual rows are able to be modified while it is
				     active, or whether its conceptual rows must be taken
				     out of service in order to be modified.  That is, it is
				     the responsibility of the DESCRIPTION clause of the
				     status column to specify whether the status column must
				     not be `active' in order for the value of some other
				     column of the same conceptual row to be modified.  If
				     such a specification is made, affected columns may be
				     changed by an SNMP set PDU if the RowStatus would not
				     be equal to `active' either immediately before or after
				     processing the PDU.  In other words, if the PDU also
				     contained a varbind that would change the RowStatus
				     value, the column in question may be changed if the
				     RowStatus was not equal to `active' as the PDU was
				     received, or if the varbind sets the status to a value
				     other than 'active'.
				
				
				Also note that whenever any elements of a row exist, the
				RowStatus column must also exist.
				
				To summarize the effect of having a conceptual row with a
				status column having a SYNTAX clause value of RowStatus,
				consider the following state diagram:
				
				
				                                           STATE
				                +--------------+-----------+-------------+-------------
				                |      A       |     B     |      C      |      D
				                |              |status col.|status column|
				                |status column |    is     |      is     |status column
				      ACTION    |does not exist|  notReady | notInService|  is active
				  --------------+--------------+-----------+-------------+-------------
				  set status    |noError    ->D|inconsist- |inconsistent-|inconsistent-
				  column to     |       or     |   entValue|        Value|        Value
				  createAndGo   |inconsistent- |           |             |
				                |         Value|           |             |
				  --------------+--------------+-----------+-------------+-------------
				  set status    |noError  see 1|inconsist- |inconsistent-|inconsistent-
				  column to     |       or     |   entValue|        Value|        Value
				  createAndWait |wrongValue    |           |             |
				  --------------+--------------+-----------+-------------+-------------
				  set status    |inconsistent- |inconsist- |noError      |noError
				  column to     |         Value|   entValue|             |
				  active        |              |           |             |
				                |              |     or    |             |
				                |              |           |             |
				                |              |see 2   ->D|          ->D|          ->D
				  --------------+--------------+-----------+-------------+-------------
				  set status    |inconsistent- |inconsist- |noError      |noError   ->C
				  column to     |         Value|   entValue|             |
				  notInService  |              |           |             |
				                |              |     or    |             |      or
				                |              |           |             |
				                |              |see 3   ->C|          ->C|wrongValue
				  --------------+--------------+-----------+-------------+-------------
				  set status    |noError       |noError    |noError      |noError
				  column to     |              |           |             |
				  destroy       |           ->A|        ->A|          ->A|          ->A
				  --------------+--------------+-----------+-------------+-------------
				  set any other |see 4         |noError    |noError      |see 5
				  column to some|              |           |             |
				  value         |              |      see 1|          ->C|          ->D
				  --------------+--------------+-----------+-------------+-------------
				  
				(1) goto B or C, depending on information available to the
				agent.
				
				(2) if other variable bindings included in the same PDU,
				provide values for all columns which are missing but
				required, then return noError and goto D.
				
				(3) if other variable bindings included in the same PDU,
				provide values for all columns which are missing but
				required, then return noError and goto C.
				
				(4) at the discretion of the agent, the return value may be
				either:
				
				     inconsistentName:  because the agent does not choose to
				     create such an instance when the corresponding
				     RowStatus instance does not exist, or
				
				     inconsistentValue:  if the supplied value is
				     inconsistent with the state of some other MIB object's
				     value, or
				
				     noError: because the agent chooses to create the
				     instance.
				
				If noError is returned, then the instance of the status
				column must also be created, and the new state is B or C,
				depending on the information available to the agent.  If
				inconsistentName or inconsistentValue is returned, the row
				remains in state A.
				
				(5) depending on the MIB definition for the column/table,
				either noError or inconsistentValue may be returned.
				
				NOTE: Other processing of the set request may result in a
				response other than noError being returned, e.g.,
				wrongValue, noCreation, etc.
				
				
				                  Conceptual Row Creation
				
				There are four potential interactions when creating a
				conceptual row:  selecting an instance-identifier which is
				not in use; creating the conceptual row; initializing any
				objects for which the agent does not supply a default; and,
				making the conceptual row available for use by the managed
				device.
				
				Interaction 1: Selecting an Instance-Identifier
				
				The algorithm used to select an instance-identifier varies
				for each conceptual row.  In some cases, the instance-
				identifier is semantically significant, e.g., the
				destination address of a route, and a management station
				selects the instance-identifier according to the semantics.
				
				In other cases, the instance-identifier is used solely to
				distinguish conceptual rows, and a management station
				without specific knowledge of the conceptual row might
				examine the instances present in order to determine an
				unused instance-identifier.  (This approach may be used, but
				it is often highly sub-optimal; however, it is also a
				questionable practice for a naive management station to
				attempt conceptual row creation.)
				
				Alternately, the MIB module which defines the conceptual row
				might provide one or more objects which provide assistance
				in determining an unused instance-identifier.  For example,
				if the conceptual row is indexed by an integer-value, then
				an object having an integer-valued SYNTAX clause might be
				defined for such a purpose, allowing a management station to
				issue a management protocol retrieval operation.  In order
				to avoid unnecessary collisions between competing management
				stations, `adjacent' retrievals of this object should be
				different.
				
				Finally, the management station could select a pseudo-random
				number to use as the index.  In the event that this index
				was already in use and an inconsistentValue was returned in
				response to the management protocol set operation, the
				management station should simply select a new pseudo-random
				number and retry the operation.
				
				A MIB designer should choose between the two latter
				algorithms based on the size of the table (and therefore the
				efficiency of each algorithm).  For tables in which a large
				number of entries are expected, it is recommended that a MIB
				object be defined that returns an acceptable index for
				creation.  For tables with small numbers of entries, it is
				recommended that the latter pseudo-random index mechanism be
				used.
				
				
				Interaction 2: Creating the Conceptual Row
				
				Once an unused instance-identifier has been selected, the
				management station determines if it wishes to create and
				activate the conceptual row in one transaction or in a
				negotiated set of interactions.
				
				Interaction 2a: Creating and Activating the Conceptual Row
				
				The management station must first determine the column
				requirements, i.e., it must determine those columns for
				which it must or must not provide values.  Depending on the
				complexity of the table and the management station's
				knowledge of the agent's capabilities, this determination
				can be made locally by the management station.  Alternately,
				the management station issues a management protocol get
				operation to examine all columns in the conceptual row that
				it wishes to create.  In response, for each column, there
				are three possible outcomes:
				
				     - a value is returned, indicating that some other
				     management station has already created this conceptual
				     row.  We return to interaction 1.
				
				     - the exception `noSuchInstance' is returned,
				     indicating that the agent implements the object-type
				     associated with this column, and that this column in at
				     least one conceptual row would be accessible in the MIB
				     view used by the retrieval were it to exist. For those
				     columns to which the agent provides read-create access,
				     the `noSuchInstance' exception tells the management
				     station that it should supply a value for this column
				     when the conceptual row is to be created.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				Once the column requirements have been determined, a
				management protocol set operation is accordingly issued.
				This operation also sets the new instance of the status
				column to `createAndGo'.
				
				When the agent processes the set operation, it verifies that
				it has sufficient information to make the conceptual row
				available for use by the managed device.  The information
				available to the agent is provided by two sources:  the
				management protocol set operation which creates the
				conceptual row, and, implementation-specific defaults
				supplied by the agent (note that an agent must provide
				implementation-specific defaults for at least those objects
				which it implements as read-only).  If there is sufficient
				information available, then the conceptual row is created, a
				`noError' response is returned, the status column is set to
				`active', and no further interactions are necessary (i.e.,
				interactions 3 and 4 are skipped).  If there is insufficient
				information, then the conceptual row is not created, and the
				set operation fails with an error of `inconsistentValue'.
				On this error, the management station can issue a management
				protocol retrieval operation to determine if this was
				because it failed to specify a value for a required column,
				or, because the selected instance of the status column
				already existed.  In the latter case, we return to
				interaction 1.  In the former case, the management station
				can re-issue the set operation with the additional
				information, or begin interaction 2 again using
				`createAndWait' in order to negotiate creation of the
				conceptual row.
				
				                         NOTE WELL
				
				     Regardless of the method used to determine the column
				     requirements, it is possible that the management
				     station might deem a column necessary when, in fact,
				     the agent will not allow that particular columnar
				     instance to be created or written.  In this case, the
				     management protocol set operation will fail with an
				     error such as `noCreation' or `notWritable'.  In this
				     case, the management station decides whether it needs
				     to be able to set a value for that particular columnar
				     instance.  If not, the management station re-issues the
				     management protocol set operation, but without setting
				     a value for that particular columnar instance;
				     otherwise, the management station aborts the row
				     creation algorithm.
				
				Interaction 2b: Negotiating the Creation of the Conceptual
				Row
				
				The management station issues a management protocol set
				operation which sets the desired instance of the status
				column to `createAndWait'.  If the agent is unwilling to
				process a request of this sort, the set operation fails with
				an error of `wrongValue'.  (As a consequence, such an agent
				must be prepared to accept a single management protocol set
				operation, i.e., interaction 2a above, containing all of the
				columns indicated by its column requirements.)  Otherwise,
				the conceptual row is created, a `noError' response is
				returned, and the status column is immediately set to either
				`notInService' or `notReady', depending on whether it has
				sufficient information to make the conceptual row available
				for use by the managed device.  If there is sufficient
				information available, then the status column is set to
				`notInService'; otherwise, if there is insufficient
				information, then the status column is set to `notReady'.
				Regardless, we proceed to interaction 3.
				
				Interaction 3: Initializing non-defaulted Objects
				
				The management station must now determine the column
				requirements.  It issues a management protocol get operation
				to examine all columns in the created conceptual row.  In
				the response, for each column, there are three possible
				outcomes:
				
				     - a value is returned, indicating that the agent
				     implements the object-type associated with this column
				     and had sufficient information to provide a value.  For
				     those columns to which the agent provides read-create
				     access (and for which the agent allows their values to
				     be changed after their creation), a value return tells
				     the management station that it may issue additional
				     management protocol set operations, if it desires, in
				     order to change the value associated with this column.
				
				     - the exception `noSuchInstance' is returned,
				     indicating that the agent implements the object-type
				     associated with this column, and that this column in at
				     least one conceptual row would be accessible in the MIB
				     view used by the retrieval were it to exist. However,
				     the agent does not have sufficient information to
				     provide a value, and until a value is provided, the
				     conceptual row may not be made available for use by the
				     managed device.  For those columns to which the agent
				     provides read-create access, the `noSuchInstance'
				     exception tells the management station that it must
				     issue additional management protocol set operations, in
				     order to provide a value associated with this column.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				If the value associated with the status column is
				`notReady', then the management station must first deal with
				all `noSuchInstance' columns, if any.  Having done so, the
				value of the status column becomes `notInService', and we
				proceed to interaction 4.
				
				Interaction 4: Making the Conceptual Row Available
				
				Once the management station is satisfied with the values
				associated with the columns of the conceptual row, it issues
				a management protocol set operation to set the status column
				to `active'.  If the agent has sufficient information to
				make the conceptual row available for use by the managed
				device, the management protocol set operation succeeds (a
				`noError' response is returned).  Otherwise, the management
				protocol set operation fails with an error of
				`inconsistentValue'.
				
				
				                         NOTE WELL
				
				     A conceptual row having a status column with value
				     `notInService' or `notReady' is unavailable to the
				     managed device.  As such, it is possible for the
				     managed device to create its own instances during the
				     time between the management protocol set operation
				     which sets the status column to `createAndWait' and the
				     management protocol set operation which sets the status
				     column to `active'.  In this case, when the management
				     protocol set operation is issued to set the status
				     column to `active', the values held in the agent
				     supersede those used by the managed device.
				
				If the management station is prevented from setting the
				status column to `active' (e.g., due to management station
				or network failure) the conceptual row will be left in the
				`notInService' or `notReady' state, consuming resources
				indefinitely.  The agent must detect conceptual rows that
				have been in either state for an abnormally long period of
				time and remove them.  It is the responsibility of the
				DESCRIPTION clause of the status column to indicate what an
				abnormally long period of time would be.  This period of
				time should be long enough to allow for human response time
				(including `think time') between the creation of the
				conceptual row and the setting of the status to `active'.
				In the absense of such information in the DESCRIPTION
				clause, it is suggested that this period be approximately 5
				minutes in length.  This removal action applies not only to
				newly-created rows, but also to previously active rows which
				are set to, and left in, the notInService state for a
				prolonged period exceeding that which is considered normal
				for such a conceptual row.
				
				
				                 Conceptual Row Suspension
				
				When a conceptual row is `active', the management station
				may issue a management protocol set operation which sets the
				instance of the status column to `notInService'.  If the
				agent is unwilling to do so, the set operation fails with an
				error of `wrongValue'.  Otherwise, the conceptual row is
				taken out of service, and a `noError' response is returned.
				It is the responsibility of the DESCRIPTION clause of the
				status column to indicate under what circumstances the
				status column should be taken out of service (e.g., in order
				for the value of some other column of the same conceptual
				row to be modified).
				
				
				                  Conceptual Row Deletion
				
				For deletion of conceptual rows, a management protocol set
				operation is issued which sets the instance of the status
				column to `destroy'.  This request may be made regardless of
				the current value of the status column (e.g., it is possible
				to delete conceptual rows which are either `notReady',
				`notInService' or `active'.)  If the operation succeeds,
				then all instances associated with the conceptual row are
				immediately removed."
			SYNTAX INTEGER
				{
				active(1),
				notInService(2),
				notReady(3),
				createAndGo(4),
				createAndWait(5),
				destroy(6)
				}

		DateAndTime ::= TEXTUAL-CONVENTION
			STATUS current
			DESCRIPTION 
				"A date-time specification.
				
				field  octets  contents                  range
				-----  ------  --------                  -----
				  1      1-2   year                      0..65536
				  2       3    month                     1..12
				  3       4    day                       1..31
				  4       5    hour                      0..23
				  5       6    minutes                   0..59
				  6       7    seconds                   0..60
				               (use 60 for leap-second)
				  7       8    deci-seconds              0..9
				  8       9    direction from UTC        '+' / '-'
				  9      10    hours from UTC            0..11
				 10      11    minutes from UTC          0..59
				
				For example, Tuesday May 26, 1992 at 1:30:15 PM EDT would be
				displayed as:
				
				                1992-5-26,13:30:15.0,-4:0
				
				Note that if only local time is known, then timezone
				information (fields 8-10) is not present."
			SYNTAX OCTET STRING (SIZE (0..255))

	
--
-- Node definitions
--
	
		-- 1.3.6.1.4.1.388.14.3.3.1.1
		wsCcStatsConf OBJECT IDENTIFIER ::= { wsCcStatsMIB 1 }

		
		-- 1.3.6.1.4.1.388.14.3.3.1.1.1
		wsCcStatsConfShortWindow OBJECT-TYPE
			SYNTAX Integer32
			UNITS "seconds"
			MAX-ACCESS read-only
			STATUS current
			DESCRIPTION
				"The number of seconds backwards from the specified 
				timestamp that the the 'Short' window extends backwards in
				time."
			::= { wsCcStatsConf 1 }

		
		-- 1.3.6.1.4.1.388.14.3.3.1.1.2
		wsCcStatsConfShortUpdateInterval OBJECT-TYPE
			SYNTAX Integer32
			UNITS "seconds"
			MAX-ACCESS read-only
			STATUS current
			DESCRIPTION
				"The frequency at which the 'Short' summary stats are 
				updated."
			::= { wsCcStatsConf 2 }

		
		-- 1.3.6.1.4.1.388.14.3.3.1.1.3
		wsCcStatsConfLongWindow OBJECT-TYPE
			SYNTAX Integer32
			UNITS "minutes"
			MAX-ACCESS read-only
			STATUS current
			DESCRIPTION
				"Same as corresponding 'Short' value, for the 'Long' window."
			::= { wsCcStatsConf 3 }

		
		-- 1.3.6.1.4.1.388.14.3.3.1.1.4
		wsCcStatsConfLongUpdateInterval OBJECT-TYPE
			SYNTAX Integer32
			UNITS "minutes"
			MAX-ACCESS read-only
			STATUS current
			DESCRIPTION
				"Same as corresponding 'Short' value, for the 'Long' window."
			::= { wsCcStatsConf 4 }

		
		-- 1.3.6.1.4.1.388.14.3.3.1.1.5
		wsCcStatsConfReset OBJECT-TYPE
			SYNTAX DoActionNow
			MAX-ACCESS read-write
			STATUS current
			DESCRIPTION
				"Writing this value resets all counters in the
				ccRf sub-tree except for the ccPortalSystemStatsTable and 
				ccPortalTable
				"
			::= { wsCcStatsConf 5 }

		
-- This group contains MIB values that describe the
-- Portals known to and adopted by this WS2000.
-- 
-- An Access Port will contain 1, 2, (and in the 
-- future, possibly more), 'Portals'.  Such Portals
-- may be thought of as the radio portion of an
-- Access Port.
-- 
-- Descriptions of each data item are only provided here in 
-- the Portal tables, (since it occurs first in the MIB).
-- For the nearly identical values in the MU and WLAN tables,
-- refer back to the descriptions found here.  (Did this to 
-- avoid massive cut-and-paste which later leads to 
-- discrepencies and inconsistencies when changes are 
-- incorrectly made to the descriptions in one location but 
-- not the others).
		-- 1.3.6.1.4.1.388.14.3.3.1.2
		wsCcStatsRadio OBJECT IDENTIFIER ::= { wsCcStatsMIB 2 }

		
		-- 1.3.6.1.4.1.388.14.3.3.1.2.2
		wsCcStatsRadioTable OBJECT-TYPE
			SYNTAX SEQUENCE OF WsCcStatsRadioEntry
			MAX-ACCESS not-accessible
			STATUS current
			DESCRIPTION
				"This table describes general statistics about
				packets sent/recieved via each Portal on the switch."
			::= { wsCcStatsRadio 2 }

		
		-- 1.3.6.1.4.1.388.14.3.3.1.2.2.1
		wsCcStatsRadioEntry OBJECT-TYPE
			SYNTAX WsCcStatsRadioEntry
			MAX-ACCESS not-accessible
			STATUS current
			DESCRIPTION
				" "
			INDEX { wsCcStatsRadioIndex }
			::= { wsCcStatsRadioTable 1 }

		
		WsCcStatsRadioEntry ::=
			SEQUENCE { 
				wsCcStatsRadioIndex
					Integer32,
				wsCcStatsRadioTxPktsUcast
					Counter32,
				wsCcStatsRadioRxPktsUcast
					Counter32,
				wsCcStatsRadioRxPktsNUcast
					Counter32,
				wsCcStatsRadioTxOctetsUcast
					Counter32,
				wsCcStatsRadioRxOctetsUcast
					Counter32,
				wsCcStatsRadioRxOctetsNUcast
					Counter32,
				wsCcStatsRadioRxUndecryptablePkts
					Counter32,
				wsCcStatsRadioLastActivity
					TimeTicks,
				wsCcStatsRadioTxRetriesPacketsFailed
					Counter32,
				wsCcStatsRadioRxErrors
					Counter32,
				wsCcStatsRadioTxRetriesVoicePktsFailed
					Counter32
			 }

-- Simple Index
		-- 1.3.6.1.4.1.388.14.3.3.1.2.2.1.1
		wsCcStatsRadioIndex OBJECT-TYPE
			SYNTAX Integer32 (1..1000)
			MAX-ACCESS accessible-for-notify
			STATUS current
			DESCRIPTION
				"Small, arbitrary integer index."
			::= { wsCcStatsRadioEntry 1 }

		
		-- 1.3.6.1.4.1.388.14.3.3.1.2.2.1.2
		wsCcStatsRadioTxPktsUcast OBJECT-TYPE
			SYNTAX Counter32
			MAX-ACCESS read-only
			STATUS current
			DESCRIPTION
				"Count of unicast packets sent via the Portal."
			::= { wsCcStatsRadioEntry 2 }

		
		-- 1.3.6.1.4.1.388.14.3.3.1.2.2.1.3
		wsCcStatsRadioRxPktsUcast OBJECT-TYPE
			SYNTAX Counter32
			MAX-ACCESS read-only
			STATUS current
			DESCRIPTION
				"Count of unicast packets received via the Portal."
			::= { wsCcStatsRadioEntry 3 }

		
		-- 1.3.6.1.4.1.388.14.3.3.1.2.2.1.4
		wsCcStatsRadioRxPktsNUcast OBJECT-TYPE
			SYNTAX Counter32
			MAX-ACCESS read-only
			STATUS current
			DESCRIPTION
				"Count of non-unicast (broadcast & multicast) 
				packets received via the Portal."
			::= { wsCcStatsRadioEntry 4 }

		
		-- 1.3.6.1.4.1.388.14.3.3.1.2.2.1.5
		wsCcStatsRadioTxOctetsUcast OBJECT-TYPE
			SYNTAX Counter32
			MAX-ACCESS read-only
			STATUS current
			DESCRIPTION
				"Count of unicast octets sent via the Portal."
			::= { wsCcStatsRadioEntry 5 }

		
		-- 1.3.6.1.4.1.388.14.3.3.1.2.2.1.6
		wsCcStatsRadioRxOctetsUcast OBJECT-TYPE
			SYNTAX Counter32
			MAX-ACCESS read-only
			STATUS current
			DESCRIPTION
				"Count of unicast octets received via the Portal."
			::= { wsCcStatsRadioEntry 6 }

		
		-- 1.3.6.1.4.1.388.14.3.3.1.2.2.1.7
		wsCcStatsRadioRxOctetsNUcast OBJECT-TYPE
			SYNTAX Counter32
			MAX-ACCESS read-only
			STATUS current
			DESCRIPTION
				"Count of non-unicast (broadcast & multicast) 
				octets received via the Portal."
			::= { wsCcStatsRadioEntry 7 }

		
		-- 1.3.6.1.4.1.388.14.3.3.1.2.2.1.8
		wsCcStatsRadioRxUndecryptablePkts OBJECT-TYPE
			SYNTAX Counter32
			MAX-ACCESS read-only
			STATUS current
			DESCRIPTION
				"Count of packets received via the Portal that could
				not be decrypted."
			::= { wsCcStatsRadioEntry 8 }

		
		-- 1.3.6.1.4.1.388.14.3.3.1.2.2.1.9
		wsCcStatsRadioLastActivity OBJECT-TYPE
			SYNTAX TimeTicks
			MAX-ACCESS read-only
			STATUS current
			DESCRIPTION
				"A snapshot of the switch's sysUpTime at the time
				of the last activity (packet sent or received)
				via the Portal."
			::= { wsCcStatsRadioEntry 9 }

		
		-- 1.3.6.1.4.1.388.14.3.3.1.2.2.1.10
		wsCcStatsRadioTxRetriesPacketsFailed OBJECT-TYPE
			SYNTAX Counter32
			MAX-ACCESS read-only
			STATUS current
			DESCRIPTION
				"Number of pkts that never were successfully 
				transmitted to via this Portal because the max retry
				count was exceeded"
			::= { wsCcStatsRadioEntry 10 }

		
		-- 1.3.6.1.4.1.388.14.3.3.1.2.2.1.11
		wsCcStatsRadioRxErrors OBJECT-TYPE
			SYNTAX Counter32
			MAX-ACCESS read-only
			STATUS current
			DESCRIPTION
				"The count of receive errors for this radio."
			::= { wsCcStatsRadioEntry 11 }

		
		-- 1.3.6.1.4.1.388.14.3.3.1.2.2.1.12
		wsCcStatsRadioTxRetriesVoicePktsFailed OBJECT-TYPE
			SYNTAX Counter32
			MAX-ACCESS read-only
			STATUS current
			DESCRIPTION
				"Number of voice pkts that never were successfully 
				transmitted to via this Portal because the max retry
				count was exceeded"
			::= { wsCcStatsRadioEntry 12 }

		
		-- 1.3.6.1.4.1.388.14.3.3.1.2.3
		wsCcStatsRadioRxPktsTable OBJECT-TYPE
			SYNTAX SEQUENCE OF WsCcStatsRadioRxPktsEntry
			MAX-ACCESS not-accessible
			STATUS deprecated
			DESCRIPTION
				"For each Portal on the switch, this table 
				describes counts of packets received at each 
				possible speed, (1Mb, 2Mb, 5.5Mb, 6Mb...)."
			::= { wsCcStatsRadio 3 }

		
		-- 1.3.6.1.4.1.388.14.3.3.1.2.3.1
		wsCcStatsRadioRxPktsEntry OBJECT-TYPE
			SYNTAX WsCcStatsRadioRxPktsEntry
			MAX-ACCESS not-accessible
			STATUS deprecated
			DESCRIPTION
				" "
			INDEX { wsCcStatsRadioIndex }
			::= { wsCcStatsRadioRxPktsTable 1 }

		
		WsCcStatsRadioRxPktsEntry ::=
			SEQUENCE { 
				wsCcStatsRadioRxPktsAt1Mb
					Counter32,
				wsCcStatsRadioRxPktsAt2Mb
					Counter32,
				wsCcStatsRadioRxPktsAt5pt5Mb
					Counter32,
				wsCcStatsRadioRxPktsAt6Mb
					Counter32,
				wsCcStatsRadioRxPktsAt9Mb
					Counter32,
				wsCcStatsRadioRxPktsAt11Mb
					Counter32,
				wsCcStatsRadioRxPktsAt12Mb
					Counter32,
				wsCcStatsRadioRxPktsAt18Mb
					Counter32,
				wsCcStatsRadioRxPktsAt22Mb
					Counter32,
				wsCcStatsRadioRxPktsAt24Mb
					Counter32,
				wsCcStatsRadioRxPktsAt36Mb
					Counter32,
				wsCcStatsRadioRxPktsAt48Mb
					Counter32,
				wsCcStatsRadioRxPktsAt54Mb
					Counter32
			 }

		-- 1.3.6.1.4.1.388.14.3.3.1.2.3.1.1
		wsCcStatsRadioRxPktsAt1Mb OBJECT-TYPE
			SYNTAX Counter32
			MAX-ACCESS read-only
			STATUS deprecated
			DESCRIPTION
				"Number of pkts received via this Portal at 1 Mb."
			::= { wsCcStatsRadioRxPktsEntry 1 }

		
		-- 1.3.6.1.4.1.388.14.3.3.1.2.3.1.2
		wsCcStatsRadioRxPktsAt2Mb OBJECT-TYPE
			SYNTAX Counter32
			MAX-ACCESS read-only
			STATUS deprecated
			DESCRIPTION
				"Number of pkts received via this Portal at 2 Mb."
			::= { wsCcStatsRadioRxPktsEntry 2 }

		
		-- 1.3.6.1.4.1.388.14.3.3.1.2.3.1.3
		wsCcStatsRadioRxPktsAt5pt5Mb OBJECT-TYPE
			SYNTAX Counter32
			MAX-ACCESS read-only
			STATUS deprecated
			DESCRIPTION
				"Number of pkts received via this Portal at 5.5 Mb."
			::= { wsCcStatsRadioRxPktsEntry 3 }

		
		-- 1.3.6.1.4.1.388.14.3.3.1.2.3.1.4
		wsCcStatsRadioRxPktsAt6Mb OBJECT-TYPE
			SYNTAX Counter32
			MAX-ACCESS read-only
			STATUS deprecated
			DESCRIPTION
				"Number of pkts received via this Portal at 6 Mb."
			::= { wsCcStatsRadioRxPktsEntry 4 }

		
		-- 1.3.6.1.4.1.388.14.3.3.1.2.3.1.5
		wsCcStatsRadioRxPktsAt9Mb OBJECT-TYPE
			SYNTAX Counter32
			MAX-ACCESS read-only
			STATUS deprecated
			DESCRIPTION
				"Number of pkts received via this Portal at 9 Mb."
			::= { wsCcStatsRadioRxPktsEntry 5 }

		
		-- 1.3.6.1.4.1.388.14.3.3.1.2.3.1.6
		wsCcStatsRadioRxPktsAt11Mb OBJECT-TYPE
			SYNTAX Counter32
			MAX-ACCESS read-only
			STATUS deprecated
			DESCRIPTION
				"Number of pkts received via this Portal at 11 Mb."
			::= { wsCcStatsRadioRxPktsEntry 6 }

		
		-- 1.3.6.1.4.1.388.14.3.3.1.2.3.1.7
		wsCcStatsRadioRxPktsAt12Mb OBJECT-TYPE
			SYNTAX Counter32
			MAX-ACCESS read-only
			STATUS deprecated
			DESCRIPTION
				"Number of pkts received via this Portal at 12 Mb."
			::= { wsCcStatsRadioRxPktsEntry 7 }

		
		-- 1.3.6.1.4.1.388.14.3.3.1.2.3.1.8
		wsCcStatsRadioRxPktsAt18Mb OBJECT-TYPE
			SYNTAX Counter32
			MAX-ACCESS read-only
			STATUS deprecated
			DESCRIPTION
				"Number of pkts received via this Portal at 18 Mb."
			::= { wsCcStatsRadioRxPktsEntry 8 }

		
		-- 1.3.6.1.4.1.388.14.3.3.1.2.3.1.9
		wsCcStatsRadioRxPktsAt22Mb OBJECT-TYPE
			SYNTAX Counter32
			MAX-ACCESS read-only
			STATUS deprecated
			DESCRIPTION
				"Number of pkts received via this Portal at 22 Mb."
			::= { wsCcStatsRadioRxPktsEntry 9 }

		
		-- 1.3.6.1.4.1.388.14.3.3.1.2.3.1.10
		wsCcStatsRadioRxPktsAt24Mb OBJECT-TYPE
			SYNTAX Counter32
			MAX-ACCESS read-only
			STATUS deprecated
			DESCRIPTION
				"Number of pkts received via this Portal at 24 Mb."
			::= { wsCcStatsRadioRxPktsEntry 10 }

		
		-- 1.3.6.1.4.1.388.14.3.3.1.2.3.1.11
		wsCcStatsRadioRxPktsAt36Mb OBJECT-TYPE
			SYNTAX Counter32
			MAX-ACCESS read-only
			STATUS deprecated
			DESCRIPTION
				"Number of pkts received via this Portal at 36 Mb."
			::= { wsCcStatsRadioRxPktsEntry 11 }

		
		-- 1.3.6.1.4.1.388.14.3.3.1.2.3.1.12
		wsCcStatsRadioRxPktsAt48Mb OBJECT-TYPE
			SYNTAX Counter32
			MAX-ACCESS read-only
			STATUS deprecated
			DESCRIPTION
				"Number of pkts received via this Portal at 48 Mb."
			::= { wsCcStatsRadioRxPktsEntry 12 }

		
		-- 1.3.6.1.4.1.388.14.3.3.1.2.3.1.13
		wsCcStatsRadioRxPktsAt54Mb OBJECT-TYPE
			SYNTAX Counter32
			MAX-ACCESS read-only
			STATUS deprecated
			DESCRIPTION
				"Number of pkts received via this Portal at 54 Mb."
			::= { wsCcStatsRadioRxPktsEntry 13 }

		
		-- 1.3.6.1.4.1.388.14.3.3.1.2.4
		wsCcStatsRadioTxPktsTable OBJECT-TYPE
			SYNTAX SEQUENCE OF WsCcStatsRadioTxPktsEntry
			MAX-ACCESS not-accessible
			STATUS deprecated
			DESCRIPTION
				"For each Portal on the switch, this table 
				describes counts of packets transmitted at each 
				possible speed, (1Mb, 2Mb, 5.5Mb, 6Mb...)."
			::= { wsCcStatsRadio 4 }

		
		-- 1.3.6.1.4.1.388.14.3.3.1.2.4.1
		wsCcStatsRadioTxPktsEntry OBJECT-TYPE
			SYNTAX WsCcStatsRadioTxPktsEntry
			MAX-ACCESS not-accessible
			STATUS deprecated
			DESCRIPTION
				" "
			INDEX { wsCcStatsRadioIndex }
			::= { wsCcStatsRadioTxPktsTable 1 }

		
		WsCcStatsRadioTxPktsEntry ::=
			SEQUENCE { 
				wsCcStatsRadioTxPktsAt1Mb
					Counter32,
				wsCcStatsRadioTxPktsAt2Mb
					Counter32,
				wsCcStatsRadioTxPktsAt5pt5Mb
					Counter32,
				wsCcStatsRadioTxPktsAt6Mb
					Counter32,
				wsCcStatsRadioTxPktsAt9Mb
					Counter32,
				wsCcStatsRadioTxPktsAt11Mb
					Counter32,
				wsCcStatsRadioTxPktsAt12Mb
					Counter32,
				wsCcStatsRadioTxPktsAt18Mb
					Counter32,
				wsCcStatsRadioTxPktsAt22Mb
					Counter32,
				wsCcStatsRadioTxPktsAt24Mb
					Counter32,
				wsCcStatsRadioTxPktsAt36Mb
					Counter32,
				wsCcStatsRadioTxPktsAt48Mb
					Counter32,
				wsCcStatsRadioTxPktsAt54Mb
					Counter32
			 }

		-- 1.3.6.1.4.1.388.14.3.3.1.2.4.1.1
		wsCcStatsRadioTxPktsAt1Mb OBJECT-TYPE
			SYNTAX Counter32
			MAX-ACCESS read-only
			STATUS deprecated
			DESCRIPTION
				"Number of pkts transmitted via this Portal at 1 Mb."
			::= { wsCcStatsRadioTxPktsEntry 1 }

		
		-- 1.3.6.1.4.1.388.14.3.3.1.2.4.1.2
		wsCcStatsRadioTxPktsAt2Mb OBJECT-TYPE
			SYNTAX Counter32
			MAX-ACCESS read-only
			STATUS deprecated
			DESCRIPTION
				"Number of pkts transmitted via this Portal at 2 Mb."
			::= { wsCcStatsRadioTxPktsEntry 2 }

		
		-- 1.3.6.1.4.1.388.14.3.3.1.2.4.1.3
		wsCcStatsRadioTxPktsAt5pt5Mb OBJECT-TYPE
			SYNTAX Counter32
			MAX-ACCESS read-only
			STATUS deprecated
			DESCRIPTION
				"Number of pkts transmitted via this Portal at 5.5 Mb."
			::= { wsCcStatsRadioTxPktsEntry 3 }

		
		-- 1.3.6.1.4.1.388.14.3.3.1.2.4.1.4
		wsCcStatsRadioTxPktsAt6Mb OBJECT-TYPE
			SYNTAX Counter32
			MAX-ACCESS read-only
			STATUS deprecated
			DESCRIPTION
				"Number of pkts transmitted via this Portal at 6 Mb."
			::= { wsCcStatsRadioTxPktsEntry 4 }

		
		-- 1.3.6.1.4.1.388.14.3.3.1.2.4.1.5
		wsCcStatsRadioTxPktsAt9Mb OBJECT-TYPE
			SYNTAX Counter32
			MAX-ACCESS read-only
			STATUS deprecated
			DESCRIPTION
				"Number of pkts transmitted via this Portal at 9 Mb."
			::= { wsCcStatsRadioTxPktsEntry 5 }

		
		-- 1.3.6.1.4.1.388.14.3.3.1.2.4.1.6
		wsCcStatsRadioTxPktsAt11Mb OBJECT-TYPE
			SYNTAX Counter32
			MAX-ACCESS read-only
			STATUS deprecated
			DESCRIPTION
				"Number of pkts transmitted via this Portal at 11 Mb."
			::= { wsCcStatsRadioTxPktsEntry 6 }

		
		-- 1.3.6.1.4.1.388.14.3.3.1.2.4.1.7
		wsCcStatsRadioTxPktsAt12Mb OBJECT-TYPE
			SYNTAX Counter32
			MAX-ACCESS read-only
			STATUS deprecated
			DESCRIPTION
				"Number of pkts transmitted via this Portal at 12 Mb."
			::= { wsCcStatsRadioTxPktsEntry 7 }

		
		-- 1.3.6.1.4.1.388.14.3.3.1.2.4.1.8
		wsCcStatsRadioTxPktsAt18Mb OBJECT-TYPE
			SYNTAX Counter32
			MAX-ACCESS read-only
			STATUS deprecated
			DESCRIPTION
				"Number of pkts transmitted via this Portal at 18 Mb."
			::= { wsCcStatsRadioTxPktsEntry 8 }

		
		-- 1.3.6.1.4.1.388.14.3.3.1.2.4.1.10
		wsCcStatsRadioTxPktsAt22Mb OBJECT-TYPE
			SYNTAX Counter32
			MAX-ACCESS read-only
			STATUS deprecated
			DESCRIPTION
				"Number of pkts transmitted via this Portal at 22 Mb."
			::= { wsCcStatsRadioTxPktsEntry 10 }

		
		-- 1.3.6.1.4.1.388.14.3.3.1.2.4.1.11
		wsCcStatsRadioTxPktsAt24Mb OBJECT-TYPE
			SYNTAX Counter32
			MAX-ACCESS read-only
			STATUS deprecated
			DESCRIPTION
				"Number of pkts transmitted via this Portal at 24 Mb."
			::= { wsCcStatsRadioTxPktsEntry 11 }

		
		-- 1.3.6.1.4.1.388.14.3.3.1.2.4.1.12
		wsCcStatsRadioTxPktsAt36Mb OBJECT-TYPE
			SYNTAX Counter32
			MAX-ACCESS read-only
			STATUS deprecated
			DESCRIPTION
				"Number of pkts transmitted via this Portal at 36 Mb."
			::= { wsCcStatsRadioTxPktsEntry 12 }

		
		-- 1.3.6.1.4.1.388.14.3.3.1.2.4.1.13
		wsCcStatsRadioTxPktsAt48Mb OBJECT-TYPE
			SYNTAX Counter32
			MAX-ACCESS read-only
			STATUS deprecated
			DESCRIPTION
				"Number of pkts transmitted via this Portal at 48 Mb."
			::= { wsCcStatsRadioTxPktsEntry 13 }

		
		-- 1.3.6.1.4.1.388.14.3.3.1.2.4.1.14
		wsCcStatsRadioTxPktsAt54Mb OBJECT-TYPE
			SYNTAX Counter32
			MAX-ACCESS read-only
			STATUS deprecated
			DESCRIPTION
				"Number of pkts transmitted via this Portal at 54 Mb."
			::= { wsCcStatsRadioTxPktsEntry 14 }

		
		-- 1.3.6.1.4.1.388.14.3.3.1.2.5
		wsCcStatsRadioRxOctetsTable OBJECT-TYPE
			SYNTAX SEQUENCE OF WsCcStatsRadioRxOctetsEntry
			MAX-ACCESS not-accessible
			STATUS deprecated
			DESCRIPTION
				"For each Portal on this switch, this table 
				describes counts of octets received at each 
				possible speed, (1Mb, 2Mb, 5.5Mb, 6Mb...)."
			::= { wsCcStatsRadio 5 }

		
		-- 1.3.6.1.4.1.388.14.3.3.1.2.5.1
		wsCcStatsRadioRxOctetsEntry OBJECT-TYPE
			SYNTAX WsCcStatsRadioRxOctetsEntry
			MAX-ACCESS not-accessible
			STATUS deprecated
			DESCRIPTION
				" "
			INDEX { wsCcStatsRadioIndex }
			::= { wsCcStatsRadioRxOctetsTable 1 }

		
		WsCcStatsRadioRxOctetsEntry ::=
			SEQUENCE { 
				wsCcStatsRadioRxOctetsAt1Mb
					Counter32,
				wsCcStatsRadioRxOctetsAt2Mb
					Counter32,
				wsCcStatsRadioRxOctetsAt5pt5Mb
					Counter32,
				wsCcStatsRadioRxOctetsAt6Mb
					Counter32,
				wsCcStatsRadioRxOctetsAt9Mb
					Counter32,
				wsCcStatsRadioRxOctetsAt11Mb
					Counter32,
				wsCcStatsRadioRxOctetsAt12Mb
					Counter32,
				wsCcStatsRadioRxOctetsAt18Mb
					Counter32,
				wsCcStatsRadioRxOctetsAt22Mb
					Counter32,
				wsCcStatsRadioRxOctetsAt24Mb
					Counter32,
				wsCcStatsRadioRxOctetsAt36Mb
					Counter32,
				wsCcStatsRadioRxOctetsAt48Mb
					Counter32,
				wsCcStatsRadioRxOctetsAt54Mb
					Counter32
			 }

		-- 1.3.6.1.4.1.388.14.3.3.1.2.5.1.1
		wsCcStatsRadioRxOctetsAt1Mb OBJECT-TYPE
			SYNTAX Counter32
			MAX-ACCESS read-only
			STATUS deprecated
			DESCRIPTION
				"Number of octets received via this Portal at 1 Mb."
			::= { wsCcStatsRadioRxOctetsEntry 1 }

		
		-- 1.3.6.1.4.1.388.14.3.3.1.2.5.1.2
		wsCcStatsRadioRxOctetsAt2Mb OBJECT-TYPE
			SYNTAX Counter32
			MAX-ACCESS read-only
			STATUS deprecated
			DESCRIPTION
				"Number of octets received via this Portal at 2 Mb."
			::= { wsCcStatsRadioRxOctetsEntry 2 }

		
		-- 1.3.6.1.4.1.388.14.3.3.1.2.5.1.3
		wsCcStatsRadioRxOctetsAt5pt5Mb OBJECT-TYPE
			SYNTAX Counter32
			MAX-ACCESS read-only
			STATUS deprecated
			DESCRIPTION
				"Number of octets received via this Portal at 5.5 Mb."
			::= { wsCcStatsRadioRxOctetsEntry 3 }

		
		-- 1.3.6.1.4.1.388.14.3.3.1.2.5.1.4
		wsCcStatsRadioRxOctetsAt6Mb OBJECT-TYPE
			SYNTAX Counter32
			MAX-ACCESS read-only
			STATUS deprecated
			DESCRIPTION
				"Number of octets received via this Portal at 6 Mb."
			::= { wsCcStatsRadioRxOctetsEntry 4 }

		
		-- 1.3.6.1.4.1.388.14.3.3.1.2.5.1.5
		wsCcStatsRadioRxOctetsAt9Mb OBJECT-TYPE
			SYNTAX Counter32
			MAX-ACCESS read-only
			STATUS deprecated
			DESCRIPTION
				"Number of octets received via this Portal at 9 Mb."
			::= { wsCcStatsRadioRxOctetsEntry 5 }

		
		-- 1.3.6.1.4.1.388.14.3.3.1.2.5.1.6
		wsCcStatsRadioRxOctetsAt11Mb OBJECT-TYPE
			SYNTAX Counter32
			MAX-ACCESS read-only
			STATUS deprecated
			DESCRIPTION
				"Number of octets received via this Portal at 11 Mb."
			::= { wsCcStatsRadioRxOctetsEntry 6 }

		
		-- 1.3.6.1.4.1.388.14.3.3.1.2.5.1.7
		wsCcStatsRadioRxOctetsAt12Mb OBJECT-TYPE
			SYNTAX Counter32
			MAX-ACCESS read-only
			STATUS deprecated
			DESCRIPTION
				"Number of octets received via this Portal at 12 Mb."
			::= { wsCcStatsRadioRxOctetsEntry 7 }

		
		-- 1.3.6.1.4.1.388.14.3.3.1.2.5.1.8
		wsCcStatsRadioRxOctetsAt18Mb OBJECT-TYPE
			SYNTAX Counter32
			MAX-ACCESS read-only
			STATUS deprecated
			DESCRIPTION
				"Number of octets received via this Portal at 18 Mb."
			::= { wsCcStatsRadioRxOctetsEntry 8 }

		
		-- 1.3.6.1.4.1.388.14.3.3.1.2.5.1.9
		wsCcStatsRadioRxOctetsAt22Mb OBJECT-TYPE
			SYNTAX Counter32
			MAX-ACCESS read-only
			STATUS deprecated
			DESCRIPTION
				"Number of octets received via this Portal at 22 Mb."
			::= { wsCcStatsRadioRxOctetsEntry 9 }

		
		-- 1.3.6.1.4.1.388.14.3.3.1.2.5.1.10
		wsCcStatsRadioRxOctetsAt24Mb OBJECT-TYPE
			SYNTAX Counter32
			MAX-ACCESS read-only
			STATUS deprecated
			DESCRIPTION
				"Number of octets received via this Portal at 24 Mb."
			::= { wsCcStatsRadioRxOctetsEntry 10 }

		
		-- 1.3.6.1.4.1.388.14.3.3.1.2.5.1.11
		wsCcStatsRadioRxOctetsAt36Mb OBJECT-TYPE
			SYNTAX Counter32
			MAX-ACCESS read-only
			STATUS deprecated
			DESCRIPTION
				"Number of octets received via this Portal at 36 Mb."
			::= { wsCcStatsRadioRxOctetsEntry 11 }

		
		-- 1.3.6.1.4.1.388.14.3.3.1.2.5.1.12
		wsCcStatsRadioRxOctetsAt48Mb OBJECT-TYPE
			SYNTAX Counter32
			MAX-ACCESS read-only
			STATUS deprecated
			DESCRIPTION
				"Number of octets received via this Portal at 48 Mb."
			::= { wsCcStatsRadioRxOctetsEntry 12 }

		
		-- 1.3.6.1.4.1.388.14.3.3.1.2.5.1.13
		wsCcStatsRadioRxOctetsAt54Mb OBJECT-TYPE
			SYNTAX Counter32
			MAX-ACCESS read-only
			STATUS deprecated
			DESCRIPTION
				"Number of octets received via this Portal at 54 Mb."
			::= { wsCcStatsRadioRxOctetsEntry 13 }

		
		-- 1.3.6.1.4.1.388.14.3.3.1.2.6
		wsCcStatsRadioTxOctetsTable OBJECT-TYPE
			SYNTAX SEQUENCE OF WsCcStatsRadioTxOctetsEntry
			MAX-ACCESS not-accessible
			STATUS deprecated
			DESCRIPTION
				"For each Portal on this switch, this table 
				describes counts of octets transmitted at each 
				possible speed, (1Mb, 2Mb, 5.5Mb, 6Mb...)."
			::= { wsCcStatsRadio 6 }

		
		-- 1.3.6.1.4.1.388.14.3.3.1.2.6.1
		wsCcStatsRadioTxOctetsEntry OBJECT-TYPE
			SYNTAX WsCcStatsRadioTxOctetsEntry
			MAX-ACCESS not-accessible
			STATUS deprecated
			DESCRIPTION
				" "
			INDEX { wsCcStatsRadioIndex }
			::= { wsCcStatsRadioTxOctetsTable 1 }

		
		WsCcStatsRadioTxOctetsEntry ::=
			SEQUENCE { 
				wsCcStatsRadioTxOctetsAt1Mb
					Counter32,
				wsCcStatsRadioTxOctetsAt2Mb
					Counter32,
				wsCcStatsRadioTxOctetsAt5pt5Mb
					Counter32,
				wsCcStatsRadioTxOctetsAt6Mb
					Counter32,
				wsCcStatsRadioTxOctetsAt9Mb
					Counter32,
				wsCcStatsRadioTxOctetsAt11Mb
					Counter32,
				wsCcStatsRadioTxOctetsAt12Mb
					Counter32,
				wsCcStatsRadioTxOctetsAt18Mb
					Counter32,
				wsCcStatsRadioTxOctetsAt22Mb
					Counter32,
				wsCcStatsRadioTxOctetsAt24Mb
					Counter32,
				wsCcStatsRadioTxOctetsAt36Mb
					Counter32,
				wsCcStatsRadioTxOctetsAt48Mb
					Counter32,
				wsCcStatsRadioTxOctetsAt54Mb
					Counter32
			 }

		-- 1.3.6.1.4.1.388.14.3.3.1.2.6.1.1
		wsCcStatsRadioTxOctetsAt1Mb OBJECT-TYPE
			SYNTAX Counter32
			MAX-ACCESS read-only
			STATUS deprecated
			DESCRIPTION
				"Number octets transmitted via this Portal at 1 Mb."
			::= { wsCcStatsRadioTxOctetsEntry 1 }

		
		-- 1.3.6.1.4.1.388.14.3.3.1.2.6.1.2
		wsCcStatsRadioTxOctetsAt2Mb OBJECT-TYPE
			SYNTAX Counter32
			MAX-ACCESS read-only
			STATUS deprecated
			DESCRIPTION
				"Number octets transmitted via this Portal at 2 Mb."
			::= { wsCcStatsRadioTxOctetsEntry 2 }

		
		-- 1.3.6.1.4.1.388.14.3.3.1.2.6.1.3
		wsCcStatsRadioTxOctetsAt5pt5Mb OBJECT-TYPE
			SYNTAX Counter32
			MAX-ACCESS read-only
			STATUS deprecated
			DESCRIPTION
				"Number octets transmitted via this Portal at 5.5 Mb."
			::= { wsCcStatsRadioTxOctetsEntry 3 }

		
		-- 1.3.6.1.4.1.388.14.3.3.1.2.6.1.4
		wsCcStatsRadioTxOctetsAt6Mb OBJECT-TYPE
			SYNTAX Counter32
			MAX-ACCESS read-only
			STATUS deprecated
			DESCRIPTION
				"Number octets transmitted via this Portal at 6 Mb."
			::= { wsCcStatsRadioTxOctetsEntry 4 }

		
		-- 1.3.6.1.4.1.388.14.3.3.1.2.6.1.5
		wsCcStatsRadioTxOctetsAt9Mb OBJECT-TYPE
			SYNTAX Counter32
			MAX-ACCESS read-only
			STATUS deprecated
			DESCRIPTION
				"Number octets transmitted via this Portal at 9 Mb."
			::= { wsCcStatsRadioTxOctetsEntry 5 }

		
		-- 1.3.6.1.4.1.388.14.3.3.1.2.6.1.6
		wsCcStatsRadioTxOctetsAt11Mb OBJECT-TYPE
			SYNTAX Counter32
			MAX-ACCESS read-only
			STATUS deprecated
			DESCRIPTION
				"Number octets transmitted via this Portal at 11 Mb."
			::= { wsCcStatsRadioTxOctetsEntry 6 }

		
		-- 1.3.6.1.4.1.388.14.3.3.1.2.6.1.7
		wsCcStatsRadioTxOctetsAt12Mb OBJECT-TYPE
			SYNTAX Counter32
			MAX-ACCESS read-only
			STATUS deprecated
			DESCRIPTION
				"Number octets transmitted via this Portal at 12 Mb."
			::= { wsCcStatsRadioTxOctetsEntry 7 }

		
		-- 1.3.6.1.4.1.388.14.3.3.1.2.6.1.8
		wsCcStatsRadioTxOctetsAt18Mb OBJECT-TYPE
			SYNTAX Counter32
			MAX-ACCESS read-only
			STATUS deprecated
			DESCRIPTION
				"Number octets transmitted via this Portal at 18 Mb."
			::= { wsCcStatsRadioTxOctetsEntry 8 }

		
		-- 1.3.6.1.4.1.388.14.3.3.1.2.6.1.9
		wsCcStatsRadioTxOctetsAt22Mb OBJECT-TYPE
			SYNTAX Counter32
			MAX-ACCESS read-only
			STATUS deprecated
			DESCRIPTION
				"Number octets transmitted via this Portal at 22 Mb."
			::= { wsCcStatsRadioTxOctetsEntry 9 }

		
		-- 1.3.6.1.4.1.388.14.3.3.1.2.6.1.10
		wsCcStatsRadioTxOctetsAt24Mb OBJECT-TYPE
			SYNTAX Counter32
			MAX-ACCESS read-only
			STATUS deprecated
			DESCRIPTION
				"Number octets transmitted via this Portal at 24 Mb."
			::= { wsCcStatsRadioTxOctetsEntry 10 }

		
		-- 1.3.6.1.4.1.388.14.3.3.1.2.6.1.11
		wsCcStatsRadioTxOctetsAt36Mb OBJECT-TYPE
			SYNTAX Counter32
			MAX-ACCESS read-only
			STATUS deprecated
			DESCRIPTION
				"Number octets transmitted via this Portal at 36 Mb."
			::= { wsCcStatsRadioTxOctetsEntry 11 }

		
		-- 1.3.6.1.4.1.388.14.3.3.1.2.6.1.12
		wsCcStatsRadioTxOctetsAt48Mb OBJECT-TYPE
			SYNTAX Counter32
			MAX-ACCESS read-only
			STATUS deprecated
			DESCRIPTION
				"Number octets transmitted via this Portal at 48 Mb."
			::= { wsCcStatsRadioTxOctetsEntry 12 }

		
		-- 1.3.6.1.4.1.388.14.3.3.1.2.6.1.13
		wsCcStatsRadioTxOctetsAt54Mb OBJECT-TYPE
			SYNTAX Counter32
			MAX-ACCESS read-only
			STATUS deprecated
			DESCRIPTION
				"Number octets transmitted via this Portal at 54 Mb."
			::= { wsCcStatsRadioTxOctetsEntry 13 }

		
		-- 1.3.6.1.4.1.388.14.3.3.1.2.7
		wsCcStatsRadioTxRetriesPktsTable OBJECT-TYPE
			SYNTAX SEQUENCE OF WsCcStatsRadioTxRetriesPktsEntry
			MAX-ACCESS not-accessible
			STATUS deprecated
			DESCRIPTION
				"For each Portal on the switch, this table describes 
				counts of the number of packets affected by transmit 
				retries, (no retries, 1 retry, 2 retries,... gave-up)."
			::= { wsCcStatsRadio 7 }

		
		-- 1.3.6.1.4.1.388.14.3.3.1.2.7.1
		wsCcStatsRadioTxRetriesPktsEntry OBJECT-TYPE
			SYNTAX WsCcStatsRadioTxRetriesPktsEntry
			MAX-ACCESS not-accessible
			STATUS deprecated
			DESCRIPTION
				" "
			INDEX { wsCcStatsRadioIndex }
			::= { wsCcStatsRadioTxRetriesPktsTable 1 }

		
		WsCcStatsRadioTxRetriesPktsEntry ::=
			SEQUENCE { 
				wsCcStatsRadioTxRetriesPktsNone
					Counter32,
				wsCcStatsRadioTxRetriesPkts01
					Counter32,
				wsCcStatsRadioTxRetriesPkts02
					Counter32,
				wsCcStatsRadioTxRetriesPkts03
					Counter32,
				wsCcStatsRadioTxRetriesPkts04
					Counter32,
				wsCcStatsRadioTxRetriesPkts05
					Counter32,
				wsCcStatsRadioTxRetriesPkts06
					Counter32,
				wsCcStatsRadioTxRetriesPkts07
					Counter32,
				wsCcStatsRadioTxRetriesPkts08
					Counter32,
				wsCcStatsRadioTxRetriesPkts09
					Counter32,
				wsCcStatsRadioTxRetriesPkts10
					Counter32,
				wsCcStatsRadioTxRetriesPkts11
					Counter32,
				wsCcStatsRadioTxRetriesPkts12
					Counter32,
				wsCcStatsRadioTxRetriesPkts13
					Counter32,
				wsCcStatsRadioTxRetriesPkts14
					Counter32,
				wsCcStatsRadioTxRetriesPkts15
					Counter32,
				wsCcStatsRadioTxRetriesPktsFailed
					Counter32
			 }

		-- 1.3.6.1.4.1.388.14.3.3.1.2.7.1.1
		wsCcStatsRadioTxRetriesPktsNone OBJECT-TYPE
			SYNTAX Counter32
			MAX-ACCESS read-only
			STATUS deprecated
			DESCRIPTION
				"Number of pkts successfully transmitted via this
				Portal with no retries."
			::= { wsCcStatsRadioTxRetriesPktsEntry 1 }

		
		-- 1.3.6.1.4.1.388.14.3.3.1.2.7.1.2
		wsCcStatsRadioTxRetriesPkts01 OBJECT-TYPE
			SYNTAX Counter32
			MAX-ACCESS read-only
			STATUS deprecated
			DESCRIPTION
				"Number of pkts successfully transmitted via this
				Portal with exactly 1 retry."
			::= { wsCcStatsRadioTxRetriesPktsEntry 2 }

		
		-- 1.3.6.1.4.1.388.14.3.3.1.2.7.1.3
		wsCcStatsRadioTxRetriesPkts02 OBJECT-TYPE
			SYNTAX Counter32
			MAX-ACCESS read-only
			STATUS deprecated
			DESCRIPTION
				"Number of pkts successfully transmitted via this
				Portal with exactly 2 retries."
			::= { wsCcStatsRadioTxRetriesPktsEntry 3 }

		
		-- 1.3.6.1.4.1.388.14.3.3.1.2.7.1.4
		wsCcStatsRadioTxRetriesPkts03 OBJECT-TYPE
			SYNTAX Counter32
			MAX-ACCESS read-only
			STATUS deprecated
			DESCRIPTION
				"Number of pkts successfully transmitted via this
				Portal with exactly 3 retries."
			::= { wsCcStatsRadioTxRetriesPktsEntry 4 }

		
		-- 1.3.6.1.4.1.388.14.3.3.1.2.7.1.5
		wsCcStatsRadioTxRetriesPkts04 OBJECT-TYPE
			SYNTAX Counter32
			MAX-ACCESS read-only
			STATUS deprecated
			DESCRIPTION
				"Number of pkts successfully transmitted via this
				Portal with exactly 4 retries."
			::= { wsCcStatsRadioTxRetriesPktsEntry 5 }

		
		-- 1.3.6.1.4.1.388.14.3.3.1.2.7.1.6
		wsCcStatsRadioTxRetriesPkts05 OBJECT-TYPE
			SYNTAX Counter32
			MAX-ACCESS read-only
			STATUS deprecated
			DESCRIPTION
				"Number of pkts successfully transmitted via this
				Portal with exactly 5 retries."
			::= { wsCcStatsRadioTxRetriesPktsEntry 6 }

		
		-- 1.3.6.1.4.1.388.14.3.3.1.2.7.1.7
		wsCcStatsRadioTxRetriesPkts06 OBJECT-TYPE
			SYNTAX Counter32
			MAX-ACCESS read-only
			STATUS deprecated
			DESCRIPTION
				"Number of pkts successfully transmitted via this
				Portal with exactly 6 retries."
			::= { wsCcStatsRadioTxRetriesPktsEntry 7 }

		
		-- 1.3.6.1.4.1.388.14.3.3.1.2.7.1.8
		wsCcStatsRadioTxRetriesPkts07 OBJECT-TYPE
			SYNTAX Counter32
			MAX-ACCESS read-only
			STATUS deprecated
			DESCRIPTION
				"Number of pkts successfully transmitted via this
				Portal with exactly 7 retries."
			::= { wsCcStatsRadioTxRetriesPktsEntry 8 }

		
		-- 1.3.6.1.4.1.388.14.3.3.1.2.7.1.9
		wsCcStatsRadioTxRetriesPkts08 OBJECT-TYPE
			SYNTAX Counter32
			MAX-ACCESS read-only
			STATUS deprecated
			DESCRIPTION
				"Number of pkts successfully transmitted via this
				Portal with exactly 8 retries."
			::= { wsCcStatsRadioTxRetriesPktsEntry 9 }

		
		-- 1.3.6.1.4.1.388.14.3.3.1.2.7.1.10
		wsCcStatsRadioTxRetriesPkts09 OBJECT-TYPE
			SYNTAX Counter32
			MAX-ACCESS read-only
			STATUS deprecated
			DESCRIPTION
				"Number of pkts successfully transmitted via this
				Portal with exactly 9 retries."
			::= { wsCcStatsRadioTxRetriesPktsEntry 10 }

		
		-- 1.3.6.1.4.1.388.14.3.3.1.2.7.1.11
		wsCcStatsRadioTxRetriesPkts10 OBJECT-TYPE
			SYNTAX Counter32
			MAX-ACCESS read-only
			STATUS deprecated
			DESCRIPTION
				"Number of pkts successfully transmitted via this
				Portal with exactly 10 retries."
			::= { wsCcStatsRadioTxRetriesPktsEntry 11 }

		
		-- 1.3.6.1.4.1.388.14.3.3.1.2.7.1.12
		wsCcStatsRadioTxRetriesPkts11 OBJECT-TYPE
			SYNTAX Counter32
			MAX-ACCESS read-only
			STATUS deprecated
			DESCRIPTION
				"Number of pkts successfully transmitted via this
				Portal with exactly 11 retries."
			::= { wsCcStatsRadioTxRetriesPktsEntry 12 }

		
		-- 1.3.6.1.4.1.388.14.3.3.1.2.7.1.13
		wsCcStatsRadioTxRetriesPkts12 OBJECT-TYPE
			SYNTAX Counter32
			MAX-ACCESS read-only
			STATUS deprecated
			DESCRIPTION
				"Number of pkts successfully transmitted via this
				Portal with exactly 12 retries."
			::= { wsCcStatsRadioTxRetriesPktsEntry 13 }

		
		-- 1.3.6.1.4.1.388.14.3.3.1.2.7.1.14
		wsCcStatsRadioTxRetriesPkts13 OBJECT-TYPE
			SYNTAX Counter32
			MAX-ACCESS read-only
			STATUS deprecated
			DESCRIPTION
				"Number of pkts successfully transmitted via this
				Portal with exactly 13 retries."
			::= { wsCcStatsRadioTxRetriesPktsEntry 14 }

		
		-- 1.3.6.1.4.1.388.14.3.3.1.2.7.1.15
		wsCcStatsRadioTxRetriesPkts14 OBJECT-TYPE
			SYNTAX Counter32
			MAX-ACCESS read-only
			STATUS deprecated
			DESCRIPTION
				"Number of pkts successfully transmitted via this
				Portal with exactly 14 retries."
			::= { wsCcStatsRadioTxRetriesPktsEntry 15 }

		
		-- 1.3.6.1.4.1.388.14.3.3.1.2.7.1.16
		wsCcStatsRadioTxRetriesPkts15 OBJECT-TYPE
			SYNTAX Counter32
			MAX-ACCESS read-only
			STATUS deprecated
			DESCRIPTION
				"Number of pkts successfully transmitted via this
				Portal with exactly 15 retries."
			::= { wsCcStatsRadioTxRetriesPktsEntry 16 }

		
		-- 1.3.6.1.4.1.388.14.3.3.1.2.7.1.17
		wsCcStatsRadioTxRetriesPktsFailed OBJECT-TYPE
			SYNTAX Counter32
			MAX-ACCESS read-only
			STATUS deprecated
			DESCRIPTION
				"Number of pkts that never were successfully 
				transmitted to via this Portal because the max retry
				count was exceeded."
			::= { wsCcStatsRadioTxRetriesPktsEntry 17 }

		
		-- 1.3.6.1.4.1.388.14.3.3.1.2.8
		wsCcStatsRadioTxRetriesOctetsTable OBJECT-TYPE
			SYNTAX SEQUENCE OF WsCcStatsRadioTxRetriesOctetsEntry
			MAX-ACCESS not-accessible
			STATUS deprecated
			DESCRIPTION
				"For each Portal on the switch, this table describes 
				counts of the number of octets affected by transmit 
				retries, (no retries, 1 retry, 2 retries,... gave-up)."
			::= { wsCcStatsRadio 8 }

		
		-- 1.3.6.1.4.1.388.14.3.3.1.2.8.1
		wsCcStatsRadioTxRetriesOctetsEntry OBJECT-TYPE
			SYNTAX WsCcStatsRadioTxRetriesOctetsEntry
			MAX-ACCESS not-accessible
			STATUS deprecated
			DESCRIPTION
				" "
			INDEX { wsCcStatsRadioIndex }
			::= { wsCcStatsRadioTxRetriesOctetsTable 1 }

		
		WsCcStatsRadioTxRetriesOctetsEntry ::=
			SEQUENCE { 
				wsCcStatsRadioTxRetriesOctetsNone
					Counter32,
				wsCcStatsRadioTxRetriesOctets01
					Counter32,
				wsCcStatsRadioTxRetriesOctets02
					Counter32,
				wsCcStatsRadioTxRetriesOctets03
					Counter32,
				wsCcStatsRadioTxRetriesOctets04
					Counter32,
				wsCcStatsRadioTxRetriesOctets05
					Counter32,
				wsCcStatsRadioTxRetriesOctets06
					Counter32,
				wsCcStatsRadioTxRetriesOctets07
					Counter32,
				wsCcStatsRadioTxRetriesOctets08
					Counter32,
				wsCcStatsRadioTxRetriesOctets09
					Counter32,
				wsCcStatsRadioTxRetriesOctets10
					Counter32,
				wsCcStatsRadioTxRetriesOctets11
					Counter32,
				wsCcStatsRadioTxRetriesOctets12
					Counter32,
				wsCcStatsRadioTxRetriesOctets13
					Counter32,
				wsCcStatsRadioTxRetriesOctets14
					Counter32,
				wsCcStatsRadioTxRetriesOctets15
					Counter32,
				wsCcStatsRadioTxRetriesOctetsFailed
					Counter32
			 }

		-- 1.3.6.1.4.1.388.14.3.3.1.2.8.1.1
		wsCcStatsRadioTxRetriesOctetsNone OBJECT-TYPE
			SYNTAX Counter32
			MAX-ACCESS read-only
			STATUS deprecated
			DESCRIPTION
				"Number of octets successfully transmitted via this
				Portal with no retries."
			::= { wsCcStatsRadioTxRetriesOctetsEntry 1 }

		
		-- 1.3.6.1.4.1.388.14.3.3.1.2.8.1.2
		wsCcStatsRadioTxRetriesOctets01 OBJECT-TYPE
			SYNTAX Counter32
			MAX-ACCESS read-only
			STATUS deprecated
			DESCRIPTION
				"Number of octets successfully transmitted via this
				Portal with exactly 1 retry."
			::= { wsCcStatsRadioTxRetriesOctetsEntry 2 }

		
		-- 1.3.6.1.4.1.388.14.3.3.1.2.8.1.3
		wsCcStatsRadioTxRetriesOctets02 OBJECT-TYPE
			SYNTAX Counter32
			MAX-ACCESS read-only
			STATUS deprecated
			DESCRIPTION
				"Number of octets successfully transmitted via this
				Portal with exactly 2 retries."
			::= { wsCcStatsRadioTxRetriesOctetsEntry 3 }

		
		-- 1.3.6.1.4.1.388.14.3.3.1.2.8.1.4
		wsCcStatsRadioTxRetriesOctets03 OBJECT-TYPE
			SYNTAX Counter32
			MAX-ACCESS read-only
			STATUS deprecated
			DESCRIPTION
				"Number of octets successfully transmitted via this
				Portal with exactly 3 retries."
			::= { wsCcStatsRadioTxRetriesOctetsEntry 4 }

		
		-- 1.3.6.1.4.1.388.14.3.3.1.2.8.1.5
		wsCcStatsRadioTxRetriesOctets04 OBJECT-TYPE
			SYNTAX Counter32
			MAX-ACCESS read-only
			STATUS deprecated
			DESCRIPTION
				"Number of octets successfully transmitted via this
				Portal with exactly 4 retries."
			::= { wsCcStatsRadioTxRetriesOctetsEntry 5 }

		
		-- 1.3.6.1.4.1.388.14.3.3.1.2.8.1.6
		wsCcStatsRadioTxRetriesOctets05 OBJECT-TYPE
			SYNTAX Counter32
			MAX-ACCESS read-only
			STATUS deprecated
			DESCRIPTION
				"Number of octets successfully transmitted via this
				Portal with exactly 5 retries."
			::= { wsCcStatsRadioTxRetriesOctetsEntry 6 }

		
		-- 1.3.6.1.4.1.388.14.3.3.1.2.8.1.7
		wsCcStatsRadioTxRetriesOctets06 OBJECT-TYPE
			SYNTAX Counter32
			MAX-ACCESS read-only
			STATUS deprecated
			DESCRIPTION
				"Number of octets successfully transmitted via this
				Portal with exactly 6 retries."
			::= { wsCcStatsRadioTxRetriesOctetsEntry 7 }

		
		-- 1.3.6.1.4.1.388.14.3.3.1.2.8.1.8
		wsCcStatsRadioTxRetriesOctets07 OBJECT-TYPE
			SYNTAX Counter32
			MAX-ACCESS read-only
			STATUS deprecated
			DESCRIPTION
				"Number of octets successfully transmitted via this
				Portal with exactly 7 retries."
			::= { wsCcStatsRadioTxRetriesOctetsEntry 8 }

		
		-- 1.3.6.1.4.1.388.14.3.3.1.2.8.1.9
		wsCcStatsRadioTxRetriesOctets08 OBJECT-TYPE
			SYNTAX Counter32
			MAX-ACCESS read-only
			STATUS deprecated
			DESCRIPTION
				"Number of octets successfully transmitted via this
				Portal with exactly 8 retries."
			::= { wsCcStatsRadioTxRetriesOctetsEntry 9 }

		
		-- 1.3.6.1.4.1.388.14.3.3.1.2.8.1.10
		wsCcStatsRadioTxRetriesOctets09 OBJECT-TYPE
			SYNTAX Counter32
			MAX-ACCESS read-only
			STATUS deprecated
			DESCRIPTION
				"Number of octets successfully transmitted via this
				Portal with exactly 9 retries."
			::= { wsCcStatsRadioTxRetriesOctetsEntry 10 }

		
		-- 1.3.6.1.4.1.388.14.3.3.1.2.8.1.11
		wsCcStatsRadioTxRetriesOctets10 OBJECT-TYPE
			SYNTAX Counter32
			MAX-ACCESS read-only
			STATUS deprecated
			DESCRIPTION
				"Number of octets successfully transmitted via this
				Portal with exactly 10 retries."
			::= { wsCcStatsRadioTxRetriesOctetsEntry 11 }

		
		-- 1.3.6.1.4.1.388.14.3.3.1.2.8.1.12
		wsCcStatsRadioTxRetriesOctets11 OBJECT-TYPE
			SYNTAX Counter32
			MAX-ACCESS read-only
			STATUS deprecated
			DESCRIPTION
				"Number of octets successfully transmitted via this
				Portal with exactly 11 retries."
			::= { wsCcStatsRadioTxRetriesOctetsEntry 12 }

		
		-- 1.3.6.1.4.1.388.14.3.3.1.2.8.1.13
		wsCcStatsRadioTxRetriesOctets12 OBJECT-TYPE
			SYNTAX Counter32
			MAX-ACCESS read-only
			STATUS deprecated
			DESCRIPTION
				"Number of octets successfully transmitted via this
				Portal with exactly 12 retries."
			::= { wsCcStatsRadioTxRetriesOctetsEntry 13 }

		
		-- 1.3.6.1.4.1.388.14.3.3.1.2.8.1.14
		wsCcStatsRadioTxRetriesOctets13 OBJECT-TYPE
			SYNTAX Counter32
			MAX-ACCESS read-only
			STATUS deprecated
			DESCRIPTION
				"Number of octets successfully transmitted via this
				Portal with exactly 13 retries."
			::= { wsCcStatsRadioTxRetriesOctetsEntry 14 }

		
		-- 1.3.6.1.4.1.388.14.3.3.1.2.8.1.15
		wsCcStatsRadioTxRetriesOctets14 OBJECT-TYPE
			SYNTAX Counter32
			MAX-ACCESS read-only
			STATUS deprecated
			DESCRIPTION
				"Number of octets successfully transmitted via this
				Portal with exactly 14 retries."
			::= { wsCcStatsRadioTxRetriesOctetsEntry 15 }

		
		-- 1.3.6.1.4.1.388.14.3.3.1.2.8.1.16
		wsCcStatsRadioTxRetriesOctets15 OBJECT-TYPE
			SYNTAX Counter32
			MAX-ACCESS read-only
			STATUS deprecated
			DESCRIPTION
				"Number of octets successfully transmitted via this
				Portal with exactly 15 retries."
			::= { wsCcStatsRadioTxRetriesOctetsEntry 16 }

		
		-- 1.3.6.1.4.1.388.14.3.3.1.2.8.1.17
		wsCcStatsRadioTxRetriesOctetsFailed OBJECT-TYPE
			SYNTAX Counter32
			MAX-ACCESS read-only
			STATUS deprecated
			DESCRIPTION
				"Number of octets that never were successfully 
				transmitted to via this Portal because the max retry
				count was exceeded."
			::= { wsCcStatsRadioTxRetriesOctetsEntry 17 }

		
-- ??-TW: Note that these values have been split-out from the
-- _StatsTable for Portal/MU/WLAN.  The resulting new tables
-- _SigStatsTable for Portal/MU/WLAN are symmetrical, but they
-- have been added before other v1.5 tables, and so have 
-- caused their location to move.
-- 
-- Also, note that the four RSSI values still remain in the 
-- ccMuStats table, since to delete them would be an 
-- inconsistant change.  For symmetry, they have been 
-- duplicated.
		-- 1.3.6.1.4.1.388.14.3.3.1.2.9
		wsCcStatsRadioSigTable OBJECT-TYPE
			SYNTAX SEQUENCE OF WsCcStatsRadioSigEntry
			MAX-ACCESS not-accessible
			STATUS deprecated
			DESCRIPTION
				"This table describes statistics about RSSI, Signal, Noise,
				and SNR for packets recieved via each Portal on the switch."
			::= { wsCcStatsRadio 9 }

		
		-- 1.3.6.1.4.1.388.14.3.3.1.2.9.1
		wsCcStatsRadioSigEntry OBJECT-TYPE
			SYNTAX WsCcStatsRadioSigEntry
			MAX-ACCESS not-accessible
			STATUS deprecated
			DESCRIPTION
				" "
			INDEX { wsCcStatsRadioIndex }
			::= { wsCcStatsRadioSigTable 1 }

		
		WsCcStatsRadioSigEntry ::=
			SEQUENCE { 
				wsCcStatsRadioSigNumPkts
					Counter32,
				wsCcStatsRadioSigSignalBest
					Integer32,
				wsCcStatsRadioSigSignalWorst
					Integer32,
				wsCcStatsRadioSigSignalSum
					Integer32,
				wsCcStatsRadioSigSignalSumSquares
					Counter64,
				wsCcStatsRadioSigSignalMostRecent
					Integer32,
				wsCcStatsRadioSigNoiseBest
					Integer32,
				wsCcStatsRadioSigNoiseWorst
					Integer32,
				wsCcStatsRadioSigNoiseSum
					Integer32,
				wsCcStatsRadioSigNoiseSumSquares
					Counter64,
				wsCcStatsRadioSigNoiseMostRecent
					Integer32,
				wsCcStatsRadioSigSnrBest
					Integer32,
				wsCcStatsRadioSigSnrWorst
					Integer32,
				wsCcStatsRadioSigSnrSum
					Integer32,
				wsCcStatsRadioSigSnrSumSquares
					Counter64,
				wsCcStatsRadioSigSnrMostRecent
					Integer32
			 }

		-- 1.3.6.1.4.1.388.14.3.3.1.2.9.1.1
		wsCcStatsRadioSigNumPkts OBJECT-TYPE
			SYNTAX Counter32
			MAX-ACCESS read-only
			STATUS deprecated
			DESCRIPTION
				"Total packets received via the Portal included in
				all the other counters reported in this row."
			::= { wsCcStatsRadioSigEntry 1 }

		
		-- 1.3.6.1.4.1.388.14.3.3.1.2.9.1.2
		wsCcStatsRadioSigSignalBest OBJECT-TYPE
			SYNTAX Integer32
			UNITS "dBm"
			MAX-ACCESS read-only
			STATUS deprecated
			DESCRIPTION
				"The best Signal value seen from the Portal so far.
				(Remember that a -20dBm Signal is better than -60dBm).
				
				This value is initialized to -500dBm.
				"
			::= { wsCcStatsRadioSigEntry 2 }

		
		-- 1.3.6.1.4.1.388.14.3.3.1.2.9.1.3
		wsCcStatsRadioSigSignalWorst OBJECT-TYPE
			SYNTAX Integer32
			UNITS "dBm"
			MAX-ACCESS read-only
			STATUS deprecated
			DESCRIPTION
				"The worst Signal value seen from the Portal so far.
				(Remember that a -80dBm Signal is worse than -60dBm).
				
				This value is initialized to 500dBm."
			::= { wsCcStatsRadioSigEntry 3 }

		
		-- 1.3.6.1.4.1.388.14.3.3.1.2.9.1.4
		wsCcStatsRadioSigSignalSum OBJECT-TYPE
			SYNTAX Integer32
			UNITS "dBm"
			MAX-ACCESS read-only
			STATUS deprecated
			DESCRIPTION
				"A running sum of all Signal values calculated by the
				switch (using reported RSSI values), for packets 
				received via this Portal.
				
				Note that this value is normally a negative value
				ranging from -10dBm to -80dBm.  It is possible for this
				value to be positive, but that would be rare, and would
				signal an exceptionally strong signal.
				
				(This value divided by ccPortalSigStatsNumPkts yields
				the average Signal value for all packets received
				from this MU)."
			::= { wsCcStatsRadioSigEntry 4 }

		
		-- 1.3.6.1.4.1.388.14.3.3.1.2.9.1.5
		wsCcStatsRadioSigSignalSumSquares OBJECT-TYPE
			SYNTAX Counter64
			UNITS "dBm"
			MAX-ACCESS read-only
			STATUS deprecated
			DESCRIPTION
				"A sum of the squares of each Signal value calculated
				for packets received via this Portal.
				
				Unlike _SignalSum, this value is never negative, since
				the square of a negative number is a positive.
				
				(This value can be used to calculate the standard
				deviation for Signal values calculated for packets
				from this Portal)."
			::= { wsCcStatsRadioSigEntry 5 }

		
		-- 1.3.6.1.4.1.388.14.3.3.1.2.9.1.6
		wsCcStatsRadioSigSignalMostRecent OBJECT-TYPE
			SYNTAX Integer32
			UNITS "dBm"
			MAX-ACCESS read-only
			STATUS deprecated
			DESCRIPTION
				"The best Signal value seen from the Portal so far.
				(Remember that a -20dBm Signal is better than -60dBm).
				
				This value does not make sense when ccPortalSigStatsNumPkts 
				equals to 0."
			::= { wsCcStatsRadioSigEntry 6 }

		
		-- 1.3.6.1.4.1.388.14.3.3.1.2.9.1.7
		wsCcStatsRadioSigNoiseBest OBJECT-TYPE
			SYNTAX Integer32
			UNITS "dBm"
			MAX-ACCESS read-only
			STATUS deprecated
			DESCRIPTION
				"The best Noise value seen from the Portal so far.
				(Remember that -80dBm Noise is better than -70dBm).
				
				This value is initialized to 500dBm."
			::= { wsCcStatsRadioSigEntry 7 }

		
		-- 1.3.6.1.4.1.388.14.3.3.1.2.9.1.8
		wsCcStatsRadioSigNoiseWorst OBJECT-TYPE
			SYNTAX Integer32
			UNITS "dBm"
			MAX-ACCESS read-only
			STATUS deprecated
			DESCRIPTION
				"The worst Noise value seen from the Portal so far.
				(Remember that -50dBm Noise is worse than -60dBm).
				
				This value is initialized to -500dBm."
			::= { wsCcStatsRadioSigEntry 8 }

		
		-- 1.3.6.1.4.1.388.14.3.3.1.2.9.1.9
		wsCcStatsRadioSigNoiseSum OBJECT-TYPE
			SYNTAX Integer32
			UNITS "dBm"
			MAX-ACCESS read-only
			STATUS deprecated
			DESCRIPTION
				"A running sum of all Noise values calculated by the
				switch (using reported RSSI values), for packets
				received via this Portal.
				
				Like _SignalSum, this value is normally a negative value.
				
				(This value divided by ccPortalSigStatsNumPkts yields
				the average Noise value for all packets received
				from this MU)."
			::= { wsCcStatsRadioSigEntry 9 }

		
		-- 1.3.6.1.4.1.388.14.3.3.1.2.9.1.10
		wsCcStatsRadioSigNoiseSumSquares OBJECT-TYPE
			SYNTAX Counter64
			UNITS "dBm"
			MAX-ACCESS read-only
			STATUS deprecated
			DESCRIPTION
				"A sum of the squares of each Noise value calculated
				for packets received via this Portal.
				
				As with _SignalSumSquares, this value is never negative.
				
				(This value can be used to calculate the standard
				deviation for Noise values calculated for packets
				from this Portal)."
			::= { wsCcStatsRadioSigEntry 10 }

		
		-- 1.3.6.1.4.1.388.14.3.3.1.2.9.1.11
		wsCcStatsRadioSigNoiseMostRecent OBJECT-TYPE
			SYNTAX Integer32
			UNITS "dBm"
			MAX-ACCESS read-only
			STATUS deprecated
			DESCRIPTION
				"The best Noise value seen from the Portal so far.
				(Remember that -80dBm Noise is better than -70dBm).
				
				This value does not make sense when ccPortalSigStatsNumPkts 
				equals to 0."
			::= { wsCcStatsRadioSigEntry 11 }

		
		-- 1.3.6.1.4.1.388.14.3.3.1.2.9.1.12
		wsCcStatsRadioSigSnrBest OBJECT-TYPE
			SYNTAX Integer32
			UNITS "dB"
			MAX-ACCESS read-only
			STATUS deprecated
			DESCRIPTION
				"The best SNR value seen from the Portal so far.
				(Remember that +30dBm SNR is better than +20dBm).
				
				This value is initialized to -500dB."
			::= { wsCcStatsRadioSigEntry 12 }

		
		-- 1.3.6.1.4.1.388.14.3.3.1.2.9.1.13
		wsCcStatsRadioSigSnrWorst OBJECT-TYPE
			SYNTAX Integer32
			UNITS "dB"
			MAX-ACCESS read-only
			STATUS deprecated
			DESCRIPTION
				"The worst SNR value seen from the Portal so far.
				(Remember that +10dBm SNR is worse than +20dBm).
				
				This value is initialized to 500dB."
			::= { wsCcStatsRadioSigEntry 13 }

		
		-- 1.3.6.1.4.1.388.14.3.3.1.2.9.1.14
		wsCcStatsRadioSigSnrSum OBJECT-TYPE
			SYNTAX Integer32
			UNITS "dB"
			MAX-ACCESS read-only
			STATUS deprecated
			DESCRIPTION
				"A running sum of all SNR values calculated by the
				switch (using reported RSSI values), for packets 
				received via this Portal.
				
				Unlike _Signal and _Noise, this value is never negative.
				
				(This value divided by ccPortalSigStatsNumPkts yields
				the average SNR value for all packets received
				from this MU)."
			::= { wsCcStatsRadioSigEntry 14 }

		
		-- 1.3.6.1.4.1.388.14.3.3.1.2.9.1.15
		wsCcStatsRadioSigSnrSumSquares OBJECT-TYPE
			SYNTAX Counter64
			UNITS "dB"
			MAX-ACCESS read-only
			STATUS deprecated
			DESCRIPTION
				"A sum of the squares of each SNR value calculated
				for packets received via this Portal.
				
				This value is never negative.
				
				(This value can be used to calculate the standard
				deviation for SNR values calculated for packets
				from this Portal)."
			::= { wsCcStatsRadioSigEntry 15 }

		
		-- 1.3.6.1.4.1.388.14.3.3.1.2.9.1.16
		wsCcStatsRadioSigSnrMostRecent OBJECT-TYPE
			SYNTAX Integer32
			UNITS "dB"
			MAX-ACCESS read-only
			STATUS deprecated
			DESCRIPTION
				"The best SNR value seen from the Portal so far.
				(Remember that +30dBm SNR is better than +20dBm).
				
				This value does not make sense when ccPortalSigStatsNumPkts 
				equals to 0."
			::= { wsCcStatsRadioSigEntry 16 }

		
-- ??-TW: all the stats in this table are reported in WISP
-- 'Status' messages reported from the Portal to the switch
-- every 5sec.  Note that these are counters newly added to
-- the Portals.  In each case, they are cumulative counters,
-- (since Portal reset), so the swith should NOT add them up.
		-- 1.3.6.1.4.1.388.14.3.3.1.2.10
		wsCcStatsRadioSysTable OBJECT-TYPE
			SYNTAX SEQUENCE OF WsCcStatsRadioSysEntry
			MAX-ACCESS not-accessible
			STATUS deprecated
			DESCRIPTION
				"This table includes statistics for 802.11 system packets
				transmitted/received at each Portal."
			::= { wsCcStatsRadio 10 }

		
		-- 1.3.6.1.4.1.388.14.3.3.1.2.10.1
		wsCcStatsRadioSysEntry OBJECT-TYPE
			SYNTAX WsCcStatsRadioSysEntry
			MAX-ACCESS not-accessible
			STATUS deprecated
			DESCRIPTION
				" "
			INDEX { wsCcStatsRadioIndex }
			::= { wsCcStatsRadioSysTable 1 }

		
		WsCcStatsRadioSysEntry ::=
			SEQUENCE { 
				wsCcStatsRadioSysBeaconsTx
					Unsigned32,
				wsCcStatsRadioSysBeaconsTxOctets
					Unsigned32,
				wsCcStatsRadioSysProbeReqRx
					Unsigned32,
				wsCcStatsRadioSysProbeReqRxOctets
					Unsigned32,
				wsCcStatsRadioSysProbeRespRetriesNone
					Unsigned32,
				wsCcStatsRadioSysProbeRespRetries1
					Unsigned32,
				wsCcStatsRadioSysProbeRespRetries2
					Unsigned32,
				wsCcStatsRadioSysProbeRespRetries3OrMore
					Unsigned32,
				wsCcStatsRadioSysProbeRespRetriesFailed
					Unsigned32,
				wsCcStatsRadioSysProbeRespTxOctets
					Unsigned32
			 }

		-- 1.3.6.1.4.1.388.14.3.3.1.2.10.1.1
		wsCcStatsRadioSysBeaconsTx OBJECT-TYPE
			SYNTAX Unsigned32
			MAX-ACCESS read-only
			STATUS deprecated
			DESCRIPTION
				"The number of Beacons sent."
			::= { wsCcStatsRadioSysEntry 1 }

		
		-- 1.3.6.1.4.1.388.14.3.3.1.2.10.1.2
		wsCcStatsRadioSysBeaconsTxOctets OBJECT-TYPE
			SYNTAX Unsigned32
			MAX-ACCESS read-only
			STATUS deprecated
			DESCRIPTION
				"The number of octets sent in Beacons."
			::= { wsCcStatsRadioSysEntry 2 }

		
		-- 1.3.6.1.4.1.388.14.3.3.1.2.10.1.3
		wsCcStatsRadioSysProbeReqRx OBJECT-TYPE
			SYNTAX Unsigned32
			MAX-ACCESS read-only
			STATUS deprecated
			DESCRIPTION
				"The number of Probe Request packets received."
			::= { wsCcStatsRadioSysEntry 3 }

		
		-- 1.3.6.1.4.1.388.14.3.3.1.2.10.1.4
		wsCcStatsRadioSysProbeReqRxOctets OBJECT-TYPE
			SYNTAX Unsigned32
			MAX-ACCESS read-only
			STATUS deprecated
			DESCRIPTION
				"The number of octets received in Probe Request packets."
			::= { wsCcStatsRadioSysEntry 4 }

		
		-- 1.3.6.1.4.1.388.14.3.3.1.2.10.1.5
		wsCcStatsRadioSysProbeRespRetriesNone OBJECT-TYPE
			SYNTAX Unsigned32
			MAX-ACCESS read-only
			STATUS deprecated
			DESCRIPTION
				"The number of Probe Response packets sent with no retries."
			::= { wsCcStatsRadioSysEntry 5 }

		
		-- 1.3.6.1.4.1.388.14.3.3.1.2.10.1.6
		wsCcStatsRadioSysProbeRespRetries1 OBJECT-TYPE
			SYNTAX Unsigned32
			MAX-ACCESS read-only
			STATUS deprecated
			DESCRIPTION
				"The number of Probe Response packets sent with exactly
				1 retry."
			::= { wsCcStatsRadioSysEntry 6 }

		
		-- 1.3.6.1.4.1.388.14.3.3.1.2.10.1.7
		wsCcStatsRadioSysProbeRespRetries2 OBJECT-TYPE
			SYNTAX Unsigned32
			MAX-ACCESS read-only
			STATUS deprecated
			DESCRIPTION
				"The number of Probe Response packets sent with exactly
				2 retries."
			::= { wsCcStatsRadioSysEntry 7 }

		
		-- 1.3.6.1.4.1.388.14.3.3.1.2.10.1.8
		wsCcStatsRadioSysProbeRespRetries3OrMore OBJECT-TYPE
			SYNTAX Unsigned32
			MAX-ACCESS read-only
			STATUS deprecated
			DESCRIPTION
				"The number of Probe Response packets sent with exactly
				3 retries or more retries.
				"
			::= { wsCcStatsRadioSysEntry 8 }

		
		-- 1.3.6.1.4.1.388.14.3.3.1.2.10.1.9
		wsCcStatsRadioSysProbeRespRetriesFailed OBJECT-TYPE
			SYNTAX Unsigned32
			MAX-ACCESS read-only
			STATUS deprecated
			DESCRIPTION
				"The number of Probe Response packets that were never
				successfully transmitted because the max retry count was
				reached."
			::= { wsCcStatsRadioSysEntry 9 }

		
		-- 1.3.6.1.4.1.388.14.3.3.1.2.10.1.10
		wsCcStatsRadioSysProbeRespTxOctets OBJECT-TYPE
			SYNTAX Unsigned32
			MAX-ACCESS read-only
			STATUS deprecated
			DESCRIPTION
				"The number of octets successfully transmitted in Probe 
				Response packets.  (For example, the octets in a Probe 
				Response that is transmitted twice - one retry - only 
				counts once in this sum)."
			::= { wsCcStatsRadioSysEntry 10 }

		
		-- 1.3.6.1.4.1.388.14.3.3.1.2.11
		wsCcStatsRadioSumShortTable OBJECT-TYPE
			SYNTAX SEQUENCE OF WsCcStatsRadioSumShortEntry
			MAX-ACCESS not-accessible
			STATUS current
			DESCRIPTION
				"Averages and rates calculated over the SHORT window for
				each Portal."
			::= { wsCcStatsRadio 11 }

		
		-- 1.3.6.1.4.1.388.14.3.3.1.2.11.1
		wsCcStatsRadioSumShortEntry OBJECT-TYPE
			SYNTAX WsCcStatsRadioSumShortEntry
			MAX-ACCESS not-accessible
			STATUS current
			DESCRIPTION
				" "
			INDEX { wsCcStatsRadioIndex }
			::= { wsCcStatsRadioSumShortTable 1 }

		
		WsCcStatsRadioSumShortEntry ::=
			SEQUENCE { 
				wsCcStatsRadioSumShortTimestamp
					TimeTicks,
				wsCcStatsRadioSumShortNumPkts
					Unsigned32,
				wsCcStatsRadioSumShortPktsPerSec100
					ScaleBy100,
				wsCcStatsRadioSumShortPktsPerSecTx100
					ScaleBy100,
				wsCcStatsRadioSumShortPktsPerSecRx100
					ScaleBy100,
				wsCcStatsRadioSumShortThroughput
					Unsigned32,
				wsCcStatsRadioSumShortThroughputTx
					Unsigned32,
				wsCcStatsRadioSumShortThroughputRx
					Unsigned32,
				wsCcStatsRadioSumShortAvgBitSpeed
					Unsigned32,
				wsCcStatsRadioSumShortAvgMuSignal
					Integer32,
				wsCcStatsRadioSumShortAvgMuNoise
					Integer32,
				wsCcStatsRadioSumShortAvgMuSnr
					Integer32,
				wsCcStatsRadioSumShortPp10kNUcastPkts
					PartsPer10k,
				wsCcStatsRadioSumShortPp10kTxWithRetries
					PartsPer10k,
				wsCcStatsRadioSumShortPp10kTxMaxRetries
					PartsPer10k,
				wsCcStatsRadioSumShortTxAvgRetries100
					ScaleBy100,
				wsCcStatsRadiolSumShortPp10kRxUndecrypt
					PartsPer10k,
				wsCcStatsRadioSumShortTotalMus
					Unsigned32,
				wsCcStatsRadioSumShortPp10kRfUtil
					PartsPer10k,
				wsCcStatsRadioSumShortPp10kDropped
					PartsPer10k,
				wsCcStatsRadioSumShortCurrVoiceMuCount
					Unsigned32,
				wsCcStatsRadioSumShortMaxVoiceMuCount
					Unsigned32,
				wsCcStatsRadioSumShortAvgVoiceMuCount
					ScaleBy100,
				wsCcStatsRadioSumShortPp10kVoiceRfUtil
					PartsPer10k,
				wsCcStatsRadioSumShortPp10kVoiceDropped
					PartsPer10k
			 }

		-- 1.3.6.1.4.1.388.14.3.3.1.2.11.1.1
		wsCcStatsRadioSumShortTimestamp OBJECT-TYPE
			SYNTAX TimeTicks
			MAX-ACCESS read-only
			STATUS current
			DESCRIPTION
				"Snapshot of sysUpTime as of the END of the 'window' of 
				time that this entry of values represents."
			::= { wsCcStatsRadioSumShortEntry 1 }

		
		-- 1.3.6.1.4.1.388.14.3.3.1.2.11.1.2
		wsCcStatsRadioSumShortNumPkts OBJECT-TYPE
			SYNTAX Unsigned32
			UNITS "packets"
			MAX-ACCESS read-only
			STATUS current
			DESCRIPTION
				"The number of packets used to calculate the statistics in
				this window."
			::= { wsCcStatsRadioSumShortEntry 2 }

		
		-- 1.3.6.1.4.1.388.14.3.3.1.2.11.1.3
		wsCcStatsRadioSumShortPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100."
			::= { wsCcStatsRadioSumShortEntry 3 }

		
		-- 1.3.6.1.4.1.388.14.3.3.1.2.11.1.4
		wsCcStatsRadioSumShortPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100."
			::= { wsCcStatsRadioSumShortEntry 4 }

		
		-- 1.3.6.1.4.1.388.14.3.3.1.2.11.1.5
		wsCcStatsRadioSumShortPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100."
			::= { wsCcStatsRadioSumShortEntry 5 }

		
		-- 1.3.6.1.4.1.388.14.3.3.1.2.11.1.6
		wsCcStatsRadioSumShortThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries)."
			::= { wsCcStatsRadioSumShortEntry 6 }

		
		-- 1.3.6.1.4.1.388.14.3.3.1.2.11.1.7
		wsCcStatsRadioSumShortThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries)."
			::= { wsCcStatsRadioSumShortEntry 7 }

		
		-- 1.3.6.1.4.1.388.14.3.3.1.2.11.1.8
		wsCcStatsRadioSumShortThroughputRx OBJECT-TYPE
			SYNTAX Unsigned32
			UNITS "bits per second"
			MAX-ACCESS read-only
			STATUS current
			DESCRIPTION
				"Actual number of bits RX over the window,
				divided by the number of seconds in the window."
			::= { wsCcStatsRadioSumShortEntry 8 }

		
		-- 1.3.6.1.4.1.388.14.3.3.1.2.11.1.9
		wsCcStatsRadioSumShortAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { wsCcStatsRadioSumShortEntry 9 }

		
		-- 1.3.6.1.4.1.388.14.3.3.1.2.11.1.10
		wsCcStatsRadioSumShortAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values.  PO"
			::= { wsCcStatsRadioSumShortEntry 10 }

		
		-- 1.3.6.1.4.1.388.14.3.3.1.2.11.1.11
		wsCcStatsRadioSumShortAvgMuNoise OBJECT-TYPE
			SYNTAX Integer32
			UNITS "dBm"
			MAX-ACCESS read-only
			STATUS current
			DESCRIPTION
				"The average of all noise values over the window."
			::= { wsCcStatsRadioSumShortEntry 11 }

		
		-- 1.3.6.1.4.1.388.14.3.3.1.2.11.1.12
		wsCcStatsRadioSumShortAvgMuSnr OBJECT-TYPE
			SYNTAX Integer32
			UNITS "dB"
			MAX-ACCESS read-only
			STATUS current
			DESCRIPTION
				"The average of all SNR values over the window."
			::= { wsCcStatsRadioSumShortEntry 12 }

		
		-- 1.3.6.1.4.1.388.14.3.3.1.2.11.1.13
		wsCcStatsRadioSumShortPp10kNUcastPkts OBJECT-TYPE
			SYNTAX PartsPer10k
			UNITS "parts-per-10000"
			MAX-ACCESS read-only
			STATUS current
			DESCRIPTION
				"Ratio of packets that were NOT unicast.
				
				Expressed as parts-per-10000.
				"
			::= { wsCcStatsRadioSumShortEntry 13 }

		
		-- 1.3.6.1.4.1.388.14.3.3.1.2.11.1.14
		wsCcStatsRadioSumShortPp10kTxWithRetries OBJECT-TYPE
			SYNTAX PartsPer10k
			UNITS "parts-per-10000"
			MAX-ACCESS read-only
			STATUS current
			DESCRIPTION
				"Ratio of TX packets that experienced one or more retries.
				
				Expressed as parts-per-10000.
				"
			::= { wsCcStatsRadioSumShortEntry 14 }

		
		-- 1.3.6.1.4.1.388.14.3.3.1.2.11.1.15
		wsCcStatsRadioSumShortPp10kTxMaxRetries OBJECT-TYPE
			SYNTAX PartsPer10k
			UNITS "parts-per-10000"
			MAX-ACCESS read-only
			STATUS current
			DESCRIPTION
				"Ratio of TX packets that were dropped due to excessive.
				
				Expressed as parts-per-10000.
				"
			::= { wsCcStatsRadioSumShortEntry 15 }

		
		-- 1.3.6.1.4.1.388.14.3.3.1.2.11.1.16
		wsCcStatsRadioSumShortTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00)."
			::= { wsCcStatsRadioSumShortEntry 16 }

		
		-- 1.3.6.1.4.1.388.14.3.3.1.2.11.1.17
		wsCcStatsRadiolSumShortPp10kRxUndecrypt OBJECT-TYPE
			SYNTAX PartsPer10k
			UNITS "parts-per-10000"
			MAX-ACCESS read-only
			STATUS current
			DESCRIPTION
				"Ratio of RX packets that were undecryptable.
				
				Expressed as parts-per-10000.
				"
			::= { wsCcStatsRadioSumShortEntry 17 }

		
		-- 1.3.6.1.4.1.388.14.3.3.1.2.11.1.18
		wsCcStatsRadioSumShortTotalMus OBJECT-TYPE
			SYNTAX Unsigned32 (0..1024)
			UNITS "number of MUs"
			MAX-ACCESS read-only
			STATUS current
			DESCRIPTION
				"The total number of MUs associated to the given Portal."
			::= { wsCcStatsRadioSumShortEntry 18 }

		
		-- 1.3.6.1.4.1.388.14.3.3.1.2.11.1.19
		wsCcStatsRadioSumShortPp10kRfUtil OBJECT-TYPE
			SYNTAX PartsPer10k
			UNITS "parts-per-10000"
			MAX-ACCESS read-only
			STATUS current
			DESCRIPTION
				"The approximate utilization of the Portal's RF port.  
				Calculated as Throughput divided by AvgBitSpeed.
				
				Expressed as parts-per-10000.
				"
			::= { wsCcStatsRadioSumShortEntry 19 }

		
		-- 1.3.6.1.4.1.388.14.3.3.1.2.11.1.20
		wsCcStatsRadioSumShortPp10kDropped OBJECT-TYPE
			SYNTAX PartsPer10k
			MAX-ACCESS read-only
			STATUS current
			DESCRIPTION
				"Packets dropped divided by packets sent.  Dropped here 
				means dropped intentionally due to the appropriate QoS 
				queue being full.  Other reasons for dropped packets are 
				not counted in this ratio.
				
				Calculated as an average for all WLANs implemented on 
				this Portal.
				
				Expressed as parts-per-10000.
				"
			::= { wsCcStatsRadioSumShortEntry 20 }

		
		-- 1.3.6.1.4.1.388.14.3.3.1.2.11.1.21
		wsCcStatsRadioSumShortCurrVoiceMuCount OBJECT-TYPE
			SYNTAX Unsigned32
			MAX-ACCESS read-only
			STATUS current
			DESCRIPTION
				"The current number of devices identified as
				voice associated."
			::= { wsCcStatsRadioSumShortEntry 21 }

		
		-- 1.3.6.1.4.1.388.14.3.3.1.2.11.1.22
		wsCcStatsRadioSumShortMaxVoiceMuCount OBJECT-TYPE
			SYNTAX Unsigned32
			MAX-ACCESS read-only
			STATUS current
			DESCRIPTION
				"The maximum number of devices identified as
				voice associated."
			::= { wsCcStatsRadioSumShortEntry 22 }

		
		-- 1.3.6.1.4.1.388.14.3.3.1.2.11.1.23
		wsCcStatsRadioSumShortAvgVoiceMuCount OBJECT-TYPE
			SYNTAX ScaleBy100
			UNITS "average x100"
			MAX-ACCESS read-only
			STATUS current
			DESCRIPTION
				"The average number of devices identified as
				voice associated."
			::= { wsCcStatsRadioSumShortEntry 23 }

		
		-- 1.3.6.1.4.1.388.14.3.3.1.2.11.1.24
		wsCcStatsRadioSumShortPp10kVoiceRfUtil OBJECT-TYPE
			SYNTAX PartsPer10k
			UNITS "parts-per-10000"
			MAX-ACCESS read-only
			STATUS current
			DESCRIPTION
				"The approximate utilization of the Portal's RF port
				for voice traffic.
				Calculated as Throughput divided by AvgBitSpeed.
				
				Expressed as parts-per-10000."
			::= { wsCcStatsRadioSumShortEntry 24 }

		
		-- 1.3.6.1.4.1.388.14.3.3.1.2.11.1.25
		wsCcStatsRadioSumShortPp10kVoiceDropped OBJECT-TYPE
			SYNTAX PartsPer10k
			MAX-ACCESS read-only
			STATUS current
			DESCRIPTION
				"Packets dropped divided by packets sent for voice.
				Dropped here  means dropped intentionally due to
				the appropriate QoS queue being full.
				Other reasons for dropped packets are not counted in
				this ratio.
				
				Calculated as an average for all WLANs implemented on
				this Portal.
				
				Expressed as parts-per-10000."
			::= { wsCcStatsRadioSumShortEntry 25 }

		
		-- 1.3.6.1.4.1.388.14.3.3.1.2.12
		wsCcStatsRadioSumLongTable OBJECT-TYPE
			SYNTAX SEQUENCE OF WsCcStatsRadioSumLongEntry
			MAX-ACCESS not-accessible
			STATUS current
			DESCRIPTION
				"Averages and rates calculated over the LONG window for
				each Portal.
				
				(Refer to ccPortalSumStatsShortTable for descriptions)."
			::= { wsCcStatsRadio 12 }

		
		-- 1.3.6.1.4.1.388.14.3.3.1.2.12.1
		wsCcStatsRadioSumLongEntry OBJECT-TYPE
			SYNTAX WsCcStatsRadioSumLongEntry
			MAX-ACCESS not-accessible
			STATUS current
			DESCRIPTION
				" "
			INDEX { wsCcStatsRadioIndex }
			::= { wsCcStatsRadioSumLongTable 1 }

		
		WsCcStatsRadioSumLongEntry ::=
			SEQUENCE { 
				wsCcStatsRadioSumLongTimestamp
					TimeTicks,
				wsCcStatsRadioSumLongNumPkts
					Unsigned32,
				wsCcStatsRadioSumLongPktsPerSec100
					ScaleBy100,
				wsCcStatsRadioSumLongPktsPerSecTx100
					ScaleBy100,
				wsCcStatsRadioSumLongPktsPerSecRx100
					ScaleBy100,
				wsCcStatsRadioSumLongThroughput
					Unsigned32,
				wsCcStatsRadioSumLongThroughputTx
					Unsigned32,
				wsCcStatsRadioSumLongThroughputRx
					Unsigned32,
				wsCcStatsRadioSumLongAvgBitSpeed
					Unsigned32,
				wsCcStatsRadioSumLongAvgMuSignal
					Integer32,
				wsCcStatsRadioSumLongAvgMuNoise
					Integer32,
				wsCcStatsRadioSumLongAvgMuSnr
					Integer32,
				wsCcStatsRadioSumLongPp10kNUcastPkts
					PartsPer10k,
				wsCcStatsRadioSumLongPp10kTxWithRetries
					PartsPer10k,
				wsCcStatsRadioSumLongPp10kTxMaxRetries
					PartsPer10k,
				wsCcStatsRadioSumLongTxAvgRetries100
					ScaleBy100,
				wsCcStatsRadioSumLongPp10kRxUndecrypt
					PartsPer10k,
				wsCcStatsRadioSumLongTotalMus
					Unsigned32,
				wsCcStatsRadioSumLongPp10kRfUtil
					PartsPer10k,
				wsCcStatsRadioSumLongPp10kDropped
					PartsPer10k,
				wsCcStatsRadioSumLongCurrVoiceMuCount
					Unsigned32,
				wsCcStatsRadioSumLongMaxVoiceMuCount
					Unsigned32,
				wsCcStatsRadioSumLongAvgVoiceMuCount
					ScaleBy100,
				wsCcStatsRadioSumLongPp10kVoiceRfUtil
					PartsPer10k,
				wsCcStatsRadioSumLongPp10kVoiceDropped
					PartsPer10k
			 }

		-- 1.3.6.1.4.1.388.14.3.3.1.2.12.1.1
		wsCcStatsRadioSumLongTimestamp OBJECT-TYPE
			SYNTAX TimeTicks
			MAX-ACCESS read-only
			STATUS current
			DESCRIPTION
				" "
			::= { wsCcStatsRadioSumLongEntry 1 }

		
		-- 1.3.6.1.4.1.388.14.3.3.1.2.12.1.2
		wsCcStatsRadioSumLongNumPkts OBJECT-TYPE
			SYNTAX Unsigned32
			UNITS "packets"
			MAX-ACCESS read-only
			STATUS current
			DESCRIPTION
				" "
			::= { wsCcStatsRadioSumLongEntry 2 }

		
		-- 1.3.6.1.4.1.388.14.3.3.1.2.12.1.3
		wsCcStatsRadioSumLongPktsPerSec100 OBJECT-TYPE
			SYNTAX ScaleBy100
			UNITS "pkts per sec x100"
			MAX-ACCESS read-only
			STATUS current
			DESCRIPTION
				" "
			::= { wsCcStatsRadioSumLongEntry 3 }

		
		-- 1.3.6.1.4.1.388.14.3.3.1.2.12.1.4
		wsCcStatsRadioSumLongPktsPerSecTx100 OBJECT-TYPE
			SYNTAX ScaleBy100
			UNITS "pkts per sec x100"
			MAX-ACCESS read-only
			STATUS current
			DESCRIPTION
				" "
			::= { wsCcStatsRadioSumLongEntry 4 }

		
		-- 1.3.6.1.4.1.388.14.3.3.1.2.12.1.5
		wsCcStatsRadioSumLongPktsPerSecRx100 OBJECT-TYPE
			SYNTAX ScaleBy100
			UNITS "pkts per sec x100"
			MAX-ACCESS read-only
			STATUS current
			DESCRIPTION
				" "
			::= { wsCcStatsRadioSumLongEntry 5 }

		
		-- 1.3.6.1.4.1.388.14.3.3.1.2.12.1.6
		wsCcStatsRadioSumLongThroughput OBJECT-TYPE
			SYNTAX Unsigned32
			UNITS "bits per second"
			MAX-ACCESS read-only
			STATUS current
			DESCRIPTION
				" "
			::= { wsCcStatsRadioSumLongEntry 6 }

		
		-- 1.3.6.1.4.1.388.14.3.3.1.2.12.1.7
		wsCcStatsRadioSumLongThroughputTx OBJECT-TYPE
			SYNTAX Unsigned32
			UNITS "bits per second"
			MAX-ACCESS read-only
			STATUS current
			DESCRIPTION
				" "
			::= { wsCcStatsRadioSumLongEntry 7 }

		
		-- 1.3.6.1.4.1.388.14.3.3.1.2.12.1.8
		wsCcStatsRadioSumLongThroughputRx OBJECT-TYPE
			SYNTAX Unsigned32
			UNITS "bits per second"
			MAX-ACCESS read-only
			STATUS current
			DESCRIPTION
				" "
			::= { wsCcStatsRadioSumLongEntry 8 }

		
		-- 1.3.6.1.4.1.388.14.3.3.1.2.12.1.9
		wsCcStatsRadioSumLongAvgBitSpeed OBJECT-TYPE
			SYNTAX Unsigned32
			UNITS "bits per second"
			MAX-ACCESS read-only
			STATUS current
			DESCRIPTION
				" "
			::= { wsCcStatsRadioSumLongEntry 9 }

		
		-- 1.3.6.1.4.1.388.14.3.3.1.2.12.1.10
		wsCcStatsRadioSumLongAvgMuSignal OBJECT-TYPE
			SYNTAX Integer32
			UNITS "dBm"
			MAX-ACCESS read-only
			STATUS current
			DESCRIPTION
				" "
			::= { wsCcStatsRadioSumLongEntry 10 }

		
		-- 1.3.6.1.4.1.388.14.3.3.1.2.12.1.11
		wsCcStatsRadioSumLongAvgMuNoise OBJECT-TYPE
			SYNTAX Integer32
			UNITS "dBm"
			MAX-ACCESS read-only
			STATUS current
			DESCRIPTION
				" "
			::= { wsCcStatsRadioSumLongEntry 11 }

		
		-- 1.3.6.1.4.1.388.14.3.3.1.2.12.1.12
		wsCcStatsRadioSumLongAvgMuSnr OBJECT-TYPE
			SYNTAX Integer32
			UNITS "dB"
			MAX-ACCESS read-only
			STATUS current
			DESCRIPTION
				" "
			::= { wsCcStatsRadioSumLongEntry 12 }

		
		-- 1.3.6.1.4.1.388.14.3.3.1.2.12.1.13
		wsCcStatsRadioSumLongPp10kNUcastPkts OBJECT-TYPE
			SYNTAX PartsPer10k
			UNITS "parts-per-10000"
			MAX-ACCESS read-only
			STATUS current
			DESCRIPTION
				" "
			::= { wsCcStatsRadioSumLongEntry 13 }

		
		-- 1.3.6.1.4.1.388.14.3.3.1.2.12.1.14
		wsCcStatsRadioSumLongPp10kTxWithRetries OBJECT-TYPE
			SYNTAX PartsPer10k
			UNITS "parts-per-10000"
			MAX-ACCESS read-only
			STATUS current
			DESCRIPTION
				" "
			::= { wsCcStatsRadioSumLongEntry 14 }

		
		-- 1.3.6.1.4.1.388.14.3.3.1.2.12.1.15
		wsCcStatsRadioSumLongPp10kTxMaxRetries OBJECT-TYPE
			SYNTAX PartsPer10k
			UNITS "parts-per-10000"
			MAX-ACCESS read-only
			STATUS current
			DESCRIPTION
				" "
			::= { wsCcStatsRadioSumLongEntry 15 }

		
		-- 1.3.6.1.4.1.388.14.3.3.1.2.12.1.16
		wsCcStatsRadioSumLongTxAvgRetries100 OBJECT-TYPE
			SYNTAX ScaleBy100
			UNITS "average x100"
			MAX-ACCESS read-only
			STATUS current
			DESCRIPTION
				" "
			::= { wsCcStatsRadioSumLongEntry 16 }

		
		-- 1.3.6.1.4.1.388.14.3.3.1.2.12.1.17
		wsCcStatsRadioSumLongPp10kRxUndecrypt OBJECT-TYPE
			SYNTAX PartsPer10k
			UNITS "parts-per-10000"
			MAX-ACCESS read-only
			STATUS current
			DESCRIPTION
				" "
			::= { wsCcStatsRadioSumLongEntry 17 }

		
		-- 1.3.6.1.4.1.388.14.3.3.1.2.12.1.18
		wsCcStatsRadioSumLongTotalMus OBJECT-TYPE
			SYNTAX Unsigned32 (0..1024)
			UNITS "number of MUs"
			MAX-ACCESS read-only
			STATUS current
			DESCRIPTION
				" "
			::= { wsCcStatsRadioSumLongEntry 18 }

		
		-- 1.3.6.1.4.1.388.14.3.3.1.2.12.1.19
		wsCcStatsRadioSumLongPp10kRfUtil OBJECT-TYPE
			SYNTAX PartsPer10k
			UNITS "parts-per-10000"
			MAX-ACCESS read-only
			STATUS current
			DESCRIPTION
				" "
			::= { wsCcStatsRadioSumLongEntry 19 }

		
		-- 1.3.6.1.4.1.388.14.3.3.1.2.12.1.20
		wsCcStatsRadioSumLongPp10kDropped OBJECT-TYPE
			SYNTAX PartsPer10k
			MAX-ACCESS read-only
			STATUS current
			DESCRIPTION
				" "
			::= { wsCcStatsRadioSumLongEntry 20 }

		
		-- 1.3.6.1.4.1.388.14.3.3.1.2.12.1.21
		wsCcStatsRadioSumLongCurrVoiceMuCount OBJECT-TYPE
			SYNTAX Unsigned32
			MAX-ACCESS read-only
			STATUS current
			DESCRIPTION
				"The current number of devices identified as
				voice associated."
			::= { wsCcStatsRadioSumLongEntry 21 }

		
		-- 1.3.6.1.4.1.388.14.3.3.1.2.12.1.22
		wsCcStatsRadioSumLongMaxVoiceMuCount OBJECT-TYPE
			SYNTAX Unsigned32
			MAX-ACCESS read-only
			STATUS current
			DESCRIPTION
				"The maximum number of devices identified as
				voice associated."
			::= { wsCcStatsRadioSumLongEntry 22 }

		
		-- 1.3.6.1.4.1.388.14.3.3.1.2.12.1.23
		wsCcStatsRadioSumLongAvgVoiceMuCount OBJECT-TYPE
			SYNTAX ScaleBy100
			UNITS "average x100"
			MAX-ACCESS read-only
			STATUS current
			DESCRIPTION
				"The average number of devices identified as
				voice associated."
			::= { wsCcStatsRadioSumLongEntry 23 }

		
		-- 1.3.6.1.4.1.388.14.3.3.1.2.12.1.24
		wsCcStatsRadioSumLongPp10kVoiceRfUtil OBJECT-TYPE
			SYNTAX PartsPer10k
			UNITS "parts-per-10000"
			MAX-ACCESS read-only
			STATUS current
			DESCRIPTION
				"The approximate utilization of the Portal's RF port
				for voice traffic.
				Calculated as Throughput divided by AvgBitSpeed.
				
				Expressed as parts-per-10000."
			::= { wsCcStatsRadioSumLongEntry 24 }

		
		-- 1.3.6.1.4.1.388.14.3.3.1.2.12.1.25
		wsCcStatsRadioSumLongPp10kVoiceDropped OBJECT-TYPE
			SYNTAX PartsPer10k
			MAX-ACCESS read-only
			STATUS current
			DESCRIPTION
				"Packets dropped divided by packets sent for voice.
				Dropped here  means dropped intentionally due to
				the appropriate QoS queue being full.
				Other reasons for dropped packets are not counted in
				this ratio.
				
				Calculated as an average for all WLANs implemented on
				this Portal.
				
				Expressed as parts-per-10000."
			::= { wsCcStatsRadioSumLongEntry 25 }

		
-- This group contains MIB values that describe the
-- MUs (Mobile Units) known to this wireless switch. 
-- All counters displayed in this group are from the switch's
-- perspective. For example, Tx means Switch to MU. 
		-- 1.3.6.1.4.1.388.14.3.3.1.3
		wsCcStatsMu OBJECT IDENTIFIER ::= { wsCcStatsMIB 3 }

		
		-- 1.3.6.1.4.1.388.14.3.3.1.3.1
		wsCcStatsMuTable OBJECT-TYPE
			SYNTAX SEQUENCE OF WsCcStatsMuEntry
			MAX-ACCESS not-accessible
			STATUS current
			DESCRIPTION
				"This table describes general statistics about
				packets sent/recieved via each MU serviced by the switch."
			::= { wsCcStatsMu 1 }
-- All 
		
		-- 1.3.6.1.4.1.388.14.3.3.1.3.1.1
		wsCcStatsMuEntry OBJECT-TYPE
			SYNTAX WsCcStatsMuEntry
			MAX-ACCESS not-accessible
			STATUS current
			DESCRIPTION
				" "
			INDEX { wsCcStatsMuMac }
			::= { wsCcStatsMuTable 1 }

		
		WsCcStatsMuEntry ::=
			SEQUENCE { 
				wsCcStatsMuMac
					PhysAddress,
				wsCcStatsMuTxPktsUcast
					Counter32,
				wsCcStatsMuRxPktsUcast
					Counter32,
				wsCcStatsMuTxOctetsUcast
					Counter32,
				wsCcStatsMuRxOctetsUcast
					Counter32,
				wsCcStatsMuRxUndecryptablePkts
					Counter32,
				wsCcStatsMuRxRssiNumPkts
					Counter32,
				wsCcStatsMuRxRssiSum
					Counter32,
				wsCcStatsMuRxRssiSumSquares
					Counter64,
				wsCcStatsMuRxRssiMostRecent
					INTEGER,
				wsCcStatsMuLastActivity
					TimeTicks,
				wsCcStatsMuSigNumPackets
					Counter32,
				wsCcStatsMuSignalMostRecent
					Integer32
			 }

-- Simple Index
		-- 1.3.6.1.4.1.388.14.3.3.1.3.1.1.1
		wsCcStatsMuMac OBJECT-TYPE
			SYNTAX PhysAddress
			MAX-ACCESS read-only
			STATUS current
			DESCRIPTION
				"MAC address of the MU."
			::= { wsCcStatsMuEntry 1 }

		
		-- 1.3.6.1.4.1.388.14.3.3.1.3.1.1.2
		wsCcStatsMuTxPktsUcast OBJECT-TYPE
			SYNTAX Counter32
			MAX-ACCESS read-only
			STATUS current
			DESCRIPTION
				"Count of unicast packets sent."
			::= { wsCcStatsMuEntry 2 }

		
		-- 1.3.6.1.4.1.388.14.3.3.1.3.1.1.3
		wsCcStatsMuRxPktsUcast OBJECT-TYPE
			SYNTAX Counter32
			MAX-ACCESS read-only
			STATUS current
			DESCRIPTION
				"Count of unicast packets received."
			::= { wsCcStatsMuEntry 3 }

		
		-- 1.3.6.1.4.1.388.14.3.3.1.3.1.1.4
		wsCcStatsMuTxOctetsUcast OBJECT-TYPE
			SYNTAX Counter32
			MAX-ACCESS read-only
			STATUS current
			DESCRIPTION
				"Count of unicast octets sent."
			::= { wsCcStatsMuEntry 4 }

		
		-- 1.3.6.1.4.1.388.14.3.3.1.3.1.1.5
		wsCcStatsMuRxOctetsUcast OBJECT-TYPE
			SYNTAX Counter32
			MAX-ACCESS read-only
			STATUS current
			DESCRIPTION
				"Count of unicast octets received."
			::= { wsCcStatsMuEntry 5 }

		
		-- 1.3.6.1.4.1.388.14.3.3.1.3.1.1.6
		wsCcStatsMuRxUndecryptablePkts OBJECT-TYPE
			SYNTAX Counter32
			MAX-ACCESS read-only
			STATUS current
			DESCRIPTION
				"Count of packets received that could
				not be decrypted."
			::= { wsCcStatsMuEntry 6 }

		
-- This value is duplicated by ccMuSigStatsNumPkts, but this
-- one is retained for backwards-compatibility.
		-- 1.3.6.1.4.1.388.14.3.3.1.3.1.1.7
		wsCcStatsMuRxRssiNumPkts OBJECT-TYPE
			SYNTAX Counter32
			MAX-ACCESS read-only
			STATUS current
			DESCRIPTION
				"Total RSSI packets received."
			::= { wsCcStatsMuEntry 7 }

		
-- This value is duplicated by ccMuSigStatsRssiSum, but this
-- one is retained for backwards-compatibility.
		-- 1.3.6.1.4.1.388.14.3.3.1.3.1.1.8
		wsCcStatsMuRxRssiSum OBJECT-TYPE
			SYNTAX Counter32
			MAX-ACCESS read-only
			STATUS current
			DESCRIPTION
				"A running sum of all RSSI values calculated by the
				switch for packets."
			::= { wsCcStatsMuEntry 8 }

		
-- This value is duplicated by ccMuSigStatsRssiSumSquares, 
-- but this one is retained for backwards-compatibility.
		-- 1.3.6.1.4.1.388.14.3.3.1.3.1.1.9
		wsCcStatsMuRxRssiSumSquares OBJECT-TYPE
			SYNTAX Counter64
			MAX-ACCESS read-only
			STATUS current
			DESCRIPTION
				"A sum of the squares of each RSSI value calculated
				for packets received.
				
				This value is never negative."
			::= { wsCcStatsMuEntry 9 }

		
-- This value is duplicated by ccMuSigStatsRssiMostRecent, 
-- but this one is retained for backwards-compatibility.
-- 
-- ??-CM: this should be Uint32 - would chaning this be an
-- incompatible change?  Any diff on wire Int32 vs Unit32 ?
		-- 1.3.6.1.4.1.388.14.3.3.1.3.1.1.10
		wsCcStatsMuRxRssiMostRecent OBJECT-TYPE
			SYNTAX INTEGER (0..255)
			MAX-ACCESS read-only
			STATUS current
			DESCRIPTION
				"The best RSSI value seen so far.
				(Remember that -80dBm Noise is better than -70dBm).
				
				This value does not make sense when ccMuRxRssiNumPkts 
				equals to 0."
			::= { wsCcStatsMuEntry 10 }

		
		-- 1.3.6.1.4.1.388.14.3.3.1.3.1.1.11
		wsCcStatsMuLastActivity OBJECT-TYPE
			SYNTAX TimeTicks
			MAX-ACCESS read-only
			STATUS current
			DESCRIPTION
				"A snapshot of the switch's sysUpTime at the time
				of the last activity (packet sent or received)."
			::= { wsCcStatsMuEntry 11 }

		
		-- 1.3.6.1.4.1.388.14.3.3.1.3.1.1.12
		wsCcStatsMuSigNumPackets OBJECT-TYPE
			SYNTAX Counter32
			MAX-ACCESS read-only
			STATUS current
			DESCRIPTION
				"Number of packets received during the last sampling period (5 seconds)."
			::= { wsCcStatsMuEntry 12 }

		
		-- 1.3.6.1.4.1.388.14.3.3.1.3.1.1.13
		wsCcStatsMuSignalMostRecent OBJECT-TYPE
			SYNTAX Integer32
			UNITS "dBm"
			MAX-ACCESS read-only
			STATUS current
			DESCRIPTION
				"The most recent signal level for this mobile station in dbm; 
				typical values range from -80 dbm (weak) to -20 dbm (strong).
				
				Note that if wsCcStatsMuSigNumPackets equals to 0, 
				the value returned would represent a stale value 
				that is older than the sampling period (5 seconds)."
			::= { wsCcStatsMuEntry 13 }

		
		-- 1.3.6.1.4.1.388.14.3.3.1.3.2
		wsCcStatsMuRxPktsTable OBJECT-TYPE
			SYNTAX SEQUENCE OF WsCcStatsMuRxPktsEntry
			MAX-ACCESS not-accessible
			STATUS deprecated
			DESCRIPTION
				"For each MU serviced by the switch, this table 
				describes counts of packets received at each 
				possible speed, (1Mb, 2Mb, 5.5Mb, 6Mb...)."
			::= { wsCcStatsMu 2 }

		
		-- 1.3.6.1.4.1.388.14.3.3.1.3.2.1
		wsCcStatsMuRxPktsEntry OBJECT-TYPE
			SYNTAX WsCcStatsMuRxPktsEntry
			MAX-ACCESS not-accessible
			STATUS deprecated
			DESCRIPTION
				" "
			INDEX { wsCcStatsMuMac }
			::= { wsCcStatsMuRxPktsTable 1 }

		
		WsCcStatsMuRxPktsEntry ::=
			SEQUENCE { 
				wsCcStatsMuRxPktsAt1Mb
					Counter32,
				wsCcStatsMuRxPktsAt2Mb
					Counter32,
				wsCcStatsMuRxPktsAt5pt5Mb
					Counter32,
				wsCcStatsMuRxPktsAt6Mb
					Counter32,
				wsCcStatsMuRxPktsAt9Mb
					Counter32,
				wsCcStatsMuRxPktsAt11Mb
					Counter32,
				wsCcStatsMuRxPktsAt12Mb
					Counter32,
				wsCcStatsMuRxPktsAt18Mb
					Counter32,
				wsCcStatsMuRxPktsAt22Mb
					Counter32,
				wsCcStatsMuRxPktsAt24Mb
					Counter32,
				wsCcStatsMuRxPktsAt36Mb
					Counter32,
				wsCcStatsMuRxPktsAt48Mb
					Counter32,
				wsCcStatsMuRxPktsAt54Mb
					Counter32
			 }

		-- 1.3.6.1.4.1.388.14.3.3.1.3.2.1.1
		wsCcStatsMuRxPktsAt1Mb OBJECT-TYPE
			SYNTAX Counter32
			MAX-ACCESS read-only
			STATUS deprecated
			DESCRIPTION
				"Number of pkts received at 1 Mb."
			::= { wsCcStatsMuRxPktsEntry 1 }

		
		-- 1.3.6.1.4.1.388.14.3.3.1.3.2.1.2
		wsCcStatsMuRxPktsAt2Mb OBJECT-TYPE
			SYNTAX Counter32
			MAX-ACCESS read-only
			STATUS deprecated
			DESCRIPTION
				"Number of pkts received at 2 Mb."
			::= { wsCcStatsMuRxPktsEntry 2 }

		
		-- 1.3.6.1.4.1.388.14.3.3.1.3.2.1.3
		wsCcStatsMuRxPktsAt5pt5Mb OBJECT-TYPE
			SYNTAX Counter32
			MAX-ACCESS read-only
			STATUS deprecated
			DESCRIPTION
				"Number of pkts received at 5.5 Mb."
			::= { wsCcStatsMuRxPktsEntry 3 }

		
		-- 1.3.6.1.4.1.388.14.3.3.1.3.2.1.4
		wsCcStatsMuRxPktsAt6Mb OBJECT-TYPE
			SYNTAX Counter32
			MAX-ACCESS read-only
			STATUS deprecated
			DESCRIPTION
				"Number of pkts received at 6 Mb."
			::= { wsCcStatsMuRxPktsEntry 4 }

		
		-- 1.3.6.1.4.1.388.14.3.3.1.3.2.1.5
		wsCcStatsMuRxPktsAt9Mb OBJECT-TYPE
			SYNTAX Counter32
			MAX-ACCESS read-only
			STATUS deprecated
			DESCRIPTION
				"Number of pkts received at 9 Mb."
			::= { wsCcStatsMuRxPktsEntry 5 }

		
		-- 1.3.6.1.4.1.388.14.3.3.1.3.2.1.6
		wsCcStatsMuRxPktsAt11Mb OBJECT-TYPE
			SYNTAX Counter32
			MAX-ACCESS read-only
			STATUS deprecated
			DESCRIPTION
				"Number of pkts received at 11 Mb."
			::= { wsCcStatsMuRxPktsEntry 6 }

		
		-- 1.3.6.1.4.1.388.14.3.3.1.3.2.1.7
		wsCcStatsMuRxPktsAt12Mb OBJECT-TYPE
			SYNTAX Counter32
			MAX-ACCESS read-only
			STATUS deprecated
			DESCRIPTION
				"Number of pkts received at 12 Mb."
			::= { wsCcStatsMuRxPktsEntry 7 }

		
		-- 1.3.6.1.4.1.388.14.3.3.1.3.2.1.8
		wsCcStatsMuRxPktsAt18Mb OBJECT-TYPE
			SYNTAX Counter32
			MAX-ACCESS read-only
			STATUS deprecated
			DESCRIPTION
				"Number of pkts received at 18 Mb."
			::= { wsCcStatsMuRxPktsEntry 8 }

		
		-- 1.3.6.1.4.1.388.14.3.3.1.3.2.1.9
		wsCcStatsMuRxPktsAt22Mb OBJECT-TYPE
			SYNTAX Counter32
			MAX-ACCESS read-only
			STATUS deprecated
			DESCRIPTION
				"Number of pkts received at 22 Mb."
			::= { wsCcStatsMuRxPktsEntry 9 }

		
		-- 1.3.6.1.4.1.388.14.3.3.1.3.2.1.10
		wsCcStatsMuRxPktsAt24Mb OBJECT-TYPE
			SYNTAX Counter32
			MAX-ACCESS read-only
			STATUS deprecated
			DESCRIPTION
				"Number of pkts received at 24 Mb."
			::= { wsCcStatsMuRxPktsEntry 10 }

		
		-- 1.3.6.1.4.1.388.14.3.3.1.3.2.1.11
		wsCcStatsMuRxPktsAt36Mb OBJECT-TYPE
			SYNTAX Counter32
			MAX-ACCESS read-only
			STATUS deprecated
			DESCRIPTION
				"Number of pkts received at 36 Mb."
			::= { wsCcStatsMuRxPktsEntry 11 }

		
		-- 1.3.6.1.4.1.388.14.3.3.1.3.2.1.12
		wsCcStatsMuRxPktsAt48Mb OBJECT-TYPE
			SYNTAX Counter32
			MAX-ACCESS read-only
			STATUS deprecated
			DESCRIPTION
				"Number of pkts received at 48 Mb."
			::= { wsCcStatsMuRxPktsEntry 12 }

		
		-- 1.3.6.1.4.1.388.14.3.3.1.3.2.1.13
		wsCcStatsMuRxPktsAt54Mb OBJECT-TYPE
			SYNTAX Counter32
			MAX-ACCESS read-only
			STATUS deprecated
			DESCRIPTION
				"Number of pkts received at 54 Mb."
			::= { wsCcStatsMuRxPktsEntry 13 }

		
		-- 1.3.6.1.4.1.388.14.3.3.1.3.3
		wsCcStatsMuTxPktsTable OBJECT-TYPE
			SYNTAX SEQUENCE OF WsCcStatsMuTxPktsEntry
			MAX-ACCESS not-accessible
			STATUS deprecated
			DESCRIPTION
				"For each MU serviced by the switch, this table 
				describes counts of packets transmitted at each 
				possible speed, (1Mb, 2Mb, 5.5Mb, 6Mb...)."
			::= { wsCcStatsMu 3 }

		
		-- 1.3.6.1.4.1.388.14.3.3.1.3.3.1
		wsCcStatsMuTxPktsEntry OBJECT-TYPE
			SYNTAX WsCcStatsMuTxPktsEntry
			MAX-ACCESS not-accessible
			STATUS deprecated
			DESCRIPTION
				" "
			INDEX { wsCcStatsMuMac }
			::= { wsCcStatsMuTxPktsTable 1 }

		
		WsCcStatsMuTxPktsEntry ::=
			SEQUENCE { 
				wsCcStatsMuTxPktsAt1Mb
					Counter32,
				wsCcStatsMuTxPktsAt2Mb
					Counter32,
				wsCcStatsMuTxPktsAt5pt5Mb
					Counter32,
				wsCcStatsMuTxPktsAt6Mb
					Counter32,
				wsCcStatsMuTxPktsAt9Mb
					Counter32,
				wsCcStatsMuTxPktsAt11Mb
					Counter32,
				wsCcStatsMuTxPktsAt12Mb
					Counter32,
				wsCcStatsMuTxPktsAt18Mb
					Counter32,
				wsCcStatsMuTxPktsAt22Mb
					Counter32,
				wsCcStatsMuTxPktsAt24Mb
					Counter32,
				wsCcStatsMuTxPktsAt36Mb
					Counter32,
				wsCcStatsMuTxPktsAt48Mb
					Counter32,
				wsCcStatsMuTxPktsAt54Mb
					Counter32
			 }

		-- 1.3.6.1.4.1.388.14.3.3.1.3.3.1.1
		wsCcStatsMuTxPktsAt1Mb OBJECT-TYPE
			SYNTAX Counter32
			MAX-ACCESS read-only
			STATUS deprecated
			DESCRIPTION
				"Number of pkts transmitted at 1 Mb."
			::= { wsCcStatsMuTxPktsEntry 1 }

		
		-- 1.3.6.1.4.1.388.14.3.3.1.3.3.1.2
		wsCcStatsMuTxPktsAt2Mb OBJECT-TYPE
			SYNTAX Counter32
			MAX-ACCESS read-only
			STATUS deprecated
			DESCRIPTION
				"Number of pkts transmitted at 2 Mb."
			::= { wsCcStatsMuTxPktsEntry 2 }

		
		-- 1.3.6.1.4.1.388.14.3.3.1.3.3.1.3
		wsCcStatsMuTxPktsAt5pt5Mb OBJECT-TYPE
			SYNTAX Counter32
			MAX-ACCESS read-only
			STATUS deprecated
			DESCRIPTION
				"Number of pkts transmitted at 5.5 Mb."
			::= { wsCcStatsMuTxPktsEntry 3 }

		
		-- 1.3.6.1.4.1.388.14.3.3.1.3.3.1.4
		wsCcStatsMuTxPktsAt6Mb OBJECT-TYPE
			SYNTAX Counter32
			MAX-ACCESS read-only
			STATUS deprecated
			DESCRIPTION
				"Number of pkts transmitted at 6 Mb."
			::= { wsCcStatsMuTxPktsEntry 4 }

		
		-- 1.3.6.1.4.1.388.14.3.3.1.3.3.1.5
		wsCcStatsMuTxPktsAt9Mb OBJECT-TYPE
			SYNTAX Counter32
			MAX-ACCESS read-only
			STATUS deprecated
			DESCRIPTION
				"Number of pkts transmitted at 9 Mb."
			::= { wsCcStatsMuTxPktsEntry 5 }

		
		-- 1.3.6.1.4.1.388.14.3.3.1.3.3.1.6
		wsCcStatsMuTxPktsAt11Mb OBJECT-TYPE
			SYNTAX Counter32
			MAX-ACCESS read-only
			STATUS deprecated
			DESCRIPTION
				"Number of pkts transmitted at 11 Mb."
			::= { wsCcStatsMuTxPktsEntry 6 }

		
		-- 1.3.6.1.4.1.388.14.3.3.1.3.3.1.7
		wsCcStatsMuTxPktsAt12Mb OBJECT-TYPE
			SYNTAX Counter32
			MAX-ACCESS read-only
			STATUS deprecated
			DESCRIPTION
				"Number of pkts transmitted at 12 Mb."
			::= { wsCcStatsMuTxPktsEntry 7 }

		
		-- 1.3.6.1.4.1.388.14.3.3.1.3.3.1.8
		wsCcStatsMuTxPktsAt18Mb OBJECT-TYPE
			SYNTAX Counter32
			MAX-ACCESS read-only
			STATUS deprecated
			DESCRIPTION
				"Number of pkts transmitted at 18 Mb."
			::= { wsCcStatsMuTxPktsEntry 8 }

		
		-- 1.3.6.1.4.1.388.14.3.3.1.3.3.1.9
		wsCcStatsMuTxPktsAt22Mb OBJECT-TYPE
			SYNTAX Counter32
			MAX-ACCESS read-only
			STATUS deprecated
			DESCRIPTION
				"Number of pkts transmitted at 22 Mb."
			::= { wsCcStatsMuTxPktsEntry 9 }

		
		-- 1.3.6.1.4.1.388.14.3.3.1.3.3.1.10
		wsCcStatsMuTxPktsAt24Mb OBJECT-TYPE
			SYNTAX Counter32
			MAX-ACCESS read-only
			STATUS deprecated
			DESCRIPTION
				"Number of pkts transmitted at 24 Mb."
			::= { wsCcStatsMuTxPktsEntry 10 }

		
		-- 1.3.6.1.4.1.388.14.3.3.1.3.3.1.11
		wsCcStatsMuTxPktsAt36Mb OBJECT-TYPE
			SYNTAX Counter32
			MAX-ACCESS read-only
			STATUS deprecated
			DESCRIPTION
				"Number of pkts transmitted at 36 Mb."
			::= { wsCcStatsMuTxPktsEntry 11 }

		
		-- 1.3.6.1.4.1.388.14.3.3.1.3.3.1.12
		wsCcStatsMuTxPktsAt48Mb OBJECT-TYPE
			SYNTAX Counter32
			MAX-ACCESS read-only
			STATUS deprecated
			DESCRIPTION
				"Number of pkts transmitted at 48 Mb."
			::= { wsCcStatsMuTxPktsEntry 12 }

		
		-- 1.3.6.1.4.1.388.14.3.3.1.3.3.1.13
		wsCcStatsMuTxPktsAt54Mb OBJECT-TYPE
			SYNTAX Counter32
			MAX-ACCESS read-only
			STATUS deprecated
			DESCRIPTION
				"Number of pkts transmitted at 54 Mb."
			::= { wsCcStatsMuTxPktsEntry 13 }

		
		-- 1.3.6.1.4.1.388.14.3.3.1.3.4
		wsCcStatsMuRxOctetsTable OBJECT-TYPE
			SYNTAX SEQUENCE OF WsCcStatsMuRxOctetsEntry
			MAX-ACCESS not-accessible
			STATUS deprecated
			DESCRIPTION
				"For each MU serviced by this switch, this table 
				describes counts of octets received at each 
				possible speed, (1Mb, 2Mb, 5.5Mb, 6Mb...)."
			::= { wsCcStatsMu 4 }

		
		-- 1.3.6.1.4.1.388.14.3.3.1.3.4.1
		wsCcStatsMuRxOctetsEntry OBJECT-TYPE
			SYNTAX WsCcStatsMuRxOctetsEntry
			MAX-ACCESS not-accessible
			STATUS deprecated
			DESCRIPTION
				" "
			INDEX { wsCcStatsMuMac }
			::= { wsCcStatsMuRxOctetsTable 1 }

		
		WsCcStatsMuRxOctetsEntry ::=
			SEQUENCE { 
				wsCcStatsMuRxOctetsAt1Mb
					Counter32,
				wsCcStatsMuRxOctetsAt2Mb
					Counter32,
				wsCcStatsMuRxOctetsAt5pt5Mb
					Counter32,
				wsCcStatsMuRxOctetsAt6Mb
					Counter32,
				wsCcStatsMuRxOctetsAt9Mb
					Counter32,
				wsCcStatsMuRxOctetsAt11Mb
					Counter32,
				wsCcStatsMuRxOctetsAt12Mb
					Counter32,
				wsCcStatsMuRxOctetsAt18Mb
					Counter32,
				wsCcStatsMuRxOctetsAt22Mb
					Counter32,
				wsCcStatsMuRxOctetsAt24Mb
					Counter32,
				wsCcStatsMuRxOctetsAt36Mb
					Counter32,
				wsCcStatsMuRxOctetsAt48Mb
					Counter32,
				wsCcStatsMuRxOctetsAt54Mb
					Counter32
			 }

		-- 1.3.6.1.4.1.388.14.3.3.1.3.4.1.1
		wsCcStatsMuRxOctetsAt1Mb OBJECT-TYPE
			SYNTAX Counter32
			MAX-ACCESS read-only
			STATUS deprecated
			DESCRIPTION
				"Number of octets received at 1 Mb."
			::= { wsCcStatsMuRxOctetsEntry 1 }

		
		-- 1.3.6.1.4.1.388.14.3.3.1.3.4.1.2
		wsCcStatsMuRxOctetsAt2Mb OBJECT-TYPE
			SYNTAX Counter32
			MAX-ACCESS read-only
			STATUS deprecated
			DESCRIPTION
				"Number of octets received at 2 Mb."
			::= { wsCcStatsMuRxOctetsEntry 2 }

		
		-- 1.3.6.1.4.1.388.14.3.3.1.3.4.1.3
		wsCcStatsMuRxOctetsAt5pt5Mb OBJECT-TYPE
			SYNTAX Counter32
			MAX-ACCESS read-only
			STATUS deprecated
			DESCRIPTION
				"Number of octets received at 5.5 Mb."
			::= { wsCcStatsMuRxOctetsEntry 3 }

		
		-- 1.3.6.1.4.1.388.14.3.3.1.3.4.1.4
		wsCcStatsMuRxOctetsAt6Mb OBJECT-TYPE
			SYNTAX Counter32
			MAX-ACCESS read-only
			STATUS deprecated
			DESCRIPTION
				"Number of octets received at 6 Mb."
			::= { wsCcStatsMuRxOctetsEntry 4 }

		
		-- 1.3.6.1.4.1.388.14.3.3.1.3.4.1.5
		wsCcStatsMuRxOctetsAt9Mb OBJECT-TYPE
			SYNTAX Counter32
			MAX-ACCESS read-only
			STATUS deprecated
			DESCRIPTION
				"Number of octets received at 9 Mb."
			::= { wsCcStatsMuRxOctetsEntry 5 }

		
		-- 1.3.6.1.4.1.388.14.3.3.1.3.4.1.6
		wsCcStatsMuRxOctetsAt11Mb OBJECT-TYPE
			SYNTAX Counter32
			MAX-ACCESS read-only
			STATUS deprecated
			DESCRIPTION
				"Number of octets received at 11 Mb."
			::= { wsCcStatsMuRxOctetsEntry 6 }

		
		-- 1.3.6.1.4.1.388.14.3.3.1.3.4.1.7
		wsCcStatsMuRxOctetsAt12Mb OBJECT-TYPE
			SYNTAX Counter32
			MAX-ACCESS read-only
			STATUS deprecated
			DESCRIPTION
				"Number of octets received at 12 Mb."
			::= { wsCcStatsMuRxOctetsEntry 7 }

		
		-- 1.3.6.1.4.1.388.14.3.3.1.3.4.1.8
		wsCcStatsMuRxOctetsAt18Mb OBJECT-TYPE
			SYNTAX Counter32
			MAX-ACCESS read-only
			STATUS deprecated
			DESCRIPTION
				"Number of octets received at 18 Mb."
			::= { wsCcStatsMuRxOctetsEntry 8 }

		
		-- 1.3.6.1.4.1.388.14.3.3.1.3.4.1.9
		wsCcStatsMuRxOctetsAt22Mb OBJECT-TYPE
			SYNTAX Counter32
			MAX-ACCESS read-only
			STATUS deprecated
			DESCRIPTION
				"Number of octets received at 22 Mb."
			::= { wsCcStatsMuRxOctetsEntry 9 }

		
		-- 1.3.6.1.4.1.388.14.3.3.1.3.4.1.10
		wsCcStatsMuRxOctetsAt24Mb OBJECT-TYPE
			SYNTAX Counter32
			MAX-ACCESS read-only
			STATUS deprecated
			DESCRIPTION
				"Number of octets received at 24 Mb."
			::= { wsCcStatsMuRxOctetsEntry 10 }

		
		-- 1.3.6.1.4.1.388.14.3.3.1.3.4.1.11
		wsCcStatsMuRxOctetsAt36Mb OBJECT-TYPE
			SYNTAX Counter32
			MAX-ACCESS read-only
			STATUS deprecated
			DESCRIPTION
				"Number of octets received at 36 Mb."
			::= { wsCcStatsMuRxOctetsEntry 11 }

		
		-- 1.3.6.1.4.1.388.14.3.3.1.3.4.1.12
		wsCcStatsMuRxOctetsAt48Mb OBJECT-TYPE
			SYNTAX Counter32
			MAX-ACCESS read-only
			STATUS deprecated
			DESCRIPTION
				"Number of octets received at 48 Mb."
			::= { wsCcStatsMuRxOctetsEntry 12 }

		
		-- 1.3.6.1.4.1.388.14.3.3.1.3.4.1.13
		wsCcStatsMuRxOctetsAt54Mb OBJECT-TYPE
			SYNTAX Counter32
			MAX-ACCESS read-only
			STATUS deprecated
			DESCRIPTION
				"Number of octets received at 54 Mb."
			::= { wsCcStatsMuRxOctetsEntry 13 }

		
		-- 1.3.6.1.4.1.388.14.3.3.1.3.5
		wsCcStatsMuTxOctetsTable OBJECT-TYPE
			SYNTAX SEQUENCE OF WsCcStatsMuTxOctetsEntry
			MAX-ACCESS not-accessible
			STATUS deprecated
			DESCRIPTION
				"For each MU serviced by this switch, this table 
				describes counts of octets transmitted at each 
				possible speed, (1Mb, 2Mb, 5.5Mb, 6Mb...)."
			::= { wsCcStatsMu 5 }

		
		-- 1.3.6.1.4.1.388.14.3.3.1.3.5.1
		wsCcStatsMuTxOctetsEntry OBJECT-TYPE
			SYNTAX WsCcStatsMuTxOctetsEntry
			MAX-ACCESS not-accessible
			STATUS deprecated
			DESCRIPTION
				" "
			INDEX { wsCcStatsMuMac }
			::= { wsCcStatsMuTxOctetsTable 1 }

		
		WsCcStatsMuTxOctetsEntry ::=
			SEQUENCE { 
				wsCcStatsMuTxOctetsAt1Mb
					Counter32,
				wsCcStatsMuTxOctetsAt2Mb
					Counter32,
				wsCcStatsMuTxOctetsAt5pt5Mb
					Counter32,
				wsCcStatsMuTxOctetsAt6Mb
					Counter32,
				wsCcStatsMuTxOctetsAt9Mb
					Counter32,
				wsCcStatsMuTxOctetsAt11Mb
					Counter32,
				wsCcStatsMuTxOctetsAt12Mb
					Counter32,
				wsCcStatsMuTxOctetsAt18Mb
					Counter32,
				wsCcStatsMuTxOctetsAt22Mb
					Counter32,
				wsCcStatsMuTxOctetsAt24Mb
					Counter32,
				wsCcStatsMuTxOctetsAt36Mb
					Counter32,
				wsCcStatsMuTxOctetsAt48Mb
					Counter32,
				wsCcStatsMuTxOctetsAt54Mb
					Counter32
			 }

		-- 1.3.6.1.4.1.388.14.3.3.1.3.5.1.1
		wsCcStatsMuTxOctetsAt1Mb OBJECT-TYPE
			SYNTAX Counter32
			MAX-ACCESS read-only
			STATUS deprecated
			DESCRIPTION
				"Number of octets transmitted at 1 Mb."
			::= { wsCcStatsMuTxOctetsEntry 1 }

		
		-- 1.3.6.1.4.1.388.14.3.3.1.3.5.1.2
		wsCcStatsMuTxOctetsAt2Mb OBJECT-TYPE
			SYNTAX Counter32
			MAX-ACCESS read-only
			STATUS deprecated
			DESCRIPTION
				"Number of octets transmitted at 2 Mb."
			::= { wsCcStatsMuTxOctetsEntry 2 }

		
		-- 1.3.6.1.4.1.388.14.3.3.1.3.5.1.3
		wsCcStatsMuTxOctetsAt5pt5Mb OBJECT-TYPE
			SYNTAX Counter32
			MAX-ACCESS read-only
			STATUS deprecated
			DESCRIPTION
				"Number of octets transmitted at 5.5 Mb."
			::= { wsCcStatsMuTxOctetsEntry 3 }

		
		-- 1.3.6.1.4.1.388.14.3.3.1.3.5.1.4
		wsCcStatsMuTxOctetsAt6Mb OBJECT-TYPE
			SYNTAX Counter32
			MAX-ACCESS read-only
			STATUS deprecated
			DESCRIPTION
				"Number of octets transmitted at 6 Mb."
			::= { wsCcStatsMuTxOctetsEntry 4 }

		
		-- 1.3.6.1.4.1.388.14.3.3.1.3.5.1.5
		wsCcStatsMuTxOctetsAt9Mb OBJECT-TYPE
			SYNTAX Counter32
			MAX-ACCESS read-only
			STATUS deprecated
			DESCRIPTION
				"Number of octets transmitted at 9 Mb."
			::= { wsCcStatsMuTxOctetsEntry 5 }

		
		-- 1.3.6.1.4.1.388.14.3.3.1.3.5.1.6
		wsCcStatsMuTxOctetsAt11Mb OBJECT-TYPE
			SYNTAX Counter32
			MAX-ACCESS read-only
			STATUS deprecated
			DESCRIPTION
				"Number of octets transmitted at 11 Mb."
			::= { wsCcStatsMuTxOctetsEntry 6 }

		
		-- 1.3.6.1.4.1.388.14.3.3.1.3.5.1.7
		wsCcStatsMuTxOctetsAt12Mb OBJECT-TYPE
			SYNTAX Counter32
			MAX-ACCESS read-only
			STATUS deprecated
			DESCRIPTION
				"Number of octets transmitted at 12 Mb."
			::= { wsCcStatsMuTxOctetsEntry 7 }

		
		-- 1.3.6.1.4.1.388.14.3.3.1.3.5.1.8
		wsCcStatsMuTxOctetsAt18Mb OBJECT-TYPE
			SYNTAX Counter32
			MAX-ACCESS read-only
			STATUS deprecated
			DESCRIPTION
				"Number of octets transmitted at 18 Mb."
			::= { wsCcStatsMuTxOctetsEntry 8 }

		
		-- 1.3.6.1.4.1.388.14.3.3.1.3.5.1.9
		wsCcStatsMuTxOctetsAt22Mb OBJECT-TYPE
			SYNTAX Counter32
			MAX-ACCESS read-only
			STATUS deprecated
			DESCRIPTION
				"Number of octets transmitted at 22 Mb."
			::= { wsCcStatsMuTxOctetsEntry 9 }

		
		-- 1.3.6.1.4.1.388.14.3.3.1.3.5.1.10
		wsCcStatsMuTxOctetsAt24Mb OBJECT-TYPE
			SYNTAX Counter32
			MAX-ACCESS read-only
			STATUS deprecated
			DESCRIPTION
				"Number of octets transmitted at 24 Mb."
			::= { wsCcStatsMuTxOctetsEntry 10 }

		
		-- 1.3.6.1.4.1.388.14.3.3.1.3.5.1.11
		wsCcStatsMuTxOctetsAt36Mb OBJECT-TYPE
			SYNTAX Counter32
			MAX-ACCESS read-only
			STATUS deprecated
			DESCRIPTION
				"Number of octets transmitted at 36 Mb."
			::= { wsCcStatsMuTxOctetsEntry 11 }

		
		-- 1.3.6.1.4.1.388.14.3.3.1.3.5.1.12
		wsCcStatsMuTxOctetsAt48Mb OBJECT-TYPE
			SYNTAX Counter32
			MAX-ACCESS read-only
			STATUS deprecated
			DESCRIPTION
				"Number of octets transmitted at 48 Mb."
			::= { wsCcStatsMuTxOctetsEntry 12 }

		
		-- 1.3.6.1.4.1.388.14.3.3.1.3.5.1.13
		wsCcStatsMuTxOctetsAt54Mb OBJECT-TYPE
			SYNTAX Counter32
			MAX-ACCESS read-only
			STATUS deprecated
			DESCRIPTION
				"Number of octets transmitted at 54 Mb."
			::= { wsCcStatsMuTxOctetsEntry 13 }

		
		-- 1.3.6.1.4.1.388.14.3.3.1.3.6
		wsCcStatsMuTxRetriesTable OBJECT-TYPE
			SYNTAX SEQUENCE OF WsCcStatsMuTxRetriesEntry
			MAX-ACCESS not-accessible
			STATUS deprecated
			DESCRIPTION
				"For each MU serviced by the switch, this table describes 
				counts of the number of packets affected by transmit 
				retries, (no retries, 1 retry, 2 retries,... gave-up)."
			::= { wsCcStatsMu 6 }

		
		-- 1.3.6.1.4.1.388.14.3.3.1.3.6.1
		wsCcStatsMuTxRetriesEntry OBJECT-TYPE
			SYNTAX WsCcStatsMuTxRetriesEntry
			MAX-ACCESS not-accessible
			STATUS deprecated
			DESCRIPTION
				" "
			INDEX { wsCcStatsMuMac }
			::= { wsCcStatsMuTxRetriesTable 1 }

		
		WsCcStatsMuTxRetriesEntry ::=
			SEQUENCE { 
				wsCcStatsMuTxRetriesNone
					Counter32,
				wsCcStatsMuTxRetries01
					Counter32,
				wsCcStatsMuTxRetries02
					Counter32,
				wsCcStatsMuTxRetries03
					Counter32,
				wsCcStatsMuTxRetries04
					Counter32,
				wsCcStatsMuTxRetries05
					Counter32,
				wsCcStatsMuTxRetries06
					Counter32,
				wsCcStatsMuTxRetries07
					Counter32,
				wsCcStatsMuTxRetries08
					Counter32,
				wsCcStatsMuTxRetries09
					Counter32,
				wsCcStatsMuTxRetries10
					Counter32,
				wsCcStatsMuTxRetries11
					Counter32,
				wsCcStatsMuTxRetries12
					Counter32,
				wsCcStatsMuTxRetries13
					Counter32,
				wsCcStatsMuTxRetries14
					Counter32,
				wsCcStatsMuTxRetries15
					Counter32,
				wsCcStatsMuTxRetriesFailed
					Counter32,
				wsCcStatsMuTxRetriesTotal
					Counter32,
				wsCcStatsMuTxRetriesMostRecent
					INTEGER
			 }

		-- 1.3.6.1.4.1.388.14.3.3.1.3.6.1.1
		wsCcStatsMuTxRetriesNone OBJECT-TYPE
			SYNTAX Counter32
			MAX-ACCESS read-only
			STATUS deprecated
			DESCRIPTION
				"Number of pkts successfully transmitted with no retries."
			::= { wsCcStatsMuTxRetriesEntry 1 }

		
		-- 1.3.6.1.4.1.388.14.3.3.1.3.6.1.2
		wsCcStatsMuTxRetries01 OBJECT-TYPE
			SYNTAX Counter32
			MAX-ACCESS read-only
			STATUS deprecated
			DESCRIPTION
				"Number of pkts successfully transmitted with exactly 1 retries."
			::= { wsCcStatsMuTxRetriesEntry 2 }

		
		-- 1.3.6.1.4.1.388.14.3.3.1.3.6.1.3
		wsCcStatsMuTxRetries02 OBJECT-TYPE
			SYNTAX Counter32
			MAX-ACCESS read-only
			STATUS deprecated
			DESCRIPTION
				"Number of pkts successfully transmitted with exactly 2 retries."
			::= { wsCcStatsMuTxRetriesEntry 3 }

		
		-- 1.3.6.1.4.1.388.14.3.3.1.3.6.1.4
		wsCcStatsMuTxRetries03 OBJECT-TYPE
			SYNTAX Counter32
			MAX-ACCESS read-only
			STATUS deprecated
			DESCRIPTION
				"Number of pkts successfully transmitted with exactly 3 retries."
			::= { wsCcStatsMuTxRetriesEntry 4 }

		
		-- 1.3.6.1.4.1.388.14.3.3.1.3.6.1.5
		wsCcStatsMuTxRetries04 OBJECT-TYPE
			SYNTAX Counter32
			MAX-ACCESS read-only
			STATUS deprecated
			DESCRIPTION
				"Number of pkts successfully transmitted with exactly 4 retries."
			::= { wsCcStatsMuTxRetriesEntry 5 }

		
		-- 1.3.6.1.4.1.388.14.3.3.1.3.6.1.6
		wsCcStatsMuTxRetries05 OBJECT-TYPE
			SYNTAX Counter32
			MAX-ACCESS read-only
			STATUS deprecated
			DESCRIPTION
				"Number of pkts successfully transmitted with exactly 5 retries."
			::= { wsCcStatsMuTxRetriesEntry 6 }

		
		-- 1.3.6.1.4.1.388.14.3.3.1.3.6.1.7
		wsCcStatsMuTxRetries06 OBJECT-TYPE
			SYNTAX Counter32
			MAX-ACCESS read-only
			STATUS deprecated
			DESCRIPTION
				"Number of pkts successfully transmitted with exactly 6 retries."
			::= { wsCcStatsMuTxRetriesEntry 7 }

		
		-- 1.3.6.1.4.1.388.14.3.3.1.3.6.1.8
		wsCcStatsMuTxRetries07 OBJECT-TYPE
			SYNTAX Counter32
			MAX-ACCESS read-only
			STATUS deprecated
			DESCRIPTION
				"Number of pkts successfully transmitted with exactly 7 retries."
			::= { wsCcStatsMuTxRetriesEntry 8 }

		
		-- 1.3.6.1.4.1.388.14.3.3.1.3.6.1.9
		wsCcStatsMuTxRetries08 OBJECT-TYPE
			SYNTAX Counter32
			MAX-ACCESS read-only
			STATUS deprecated
			DESCRIPTION
				"Number of pkts successfully transmitted with exactly 8 retries."
			::= { wsCcStatsMuTxRetriesEntry 9 }

		
		-- 1.3.6.1.4.1.388.14.3.3.1.3.6.1.10
		wsCcStatsMuTxRetries09 OBJECT-TYPE
			SYNTAX Counter32
			MAX-ACCESS read-only
			STATUS deprecated
			DESCRIPTION
				"Number of pkts successfully transmitted with exactly 9 retries."
			::= { wsCcStatsMuTxRetriesEntry 10 }

		
		-- 1.3.6.1.4.1.388.14.3.3.1.3.6.1.11
		wsCcStatsMuTxRetries10 OBJECT-TYPE
			SYNTAX Counter32
			MAX-ACCESS read-only
			STATUS deprecated
			DESCRIPTION
				"Number of pkts successfully transmitted with exactly 10 retries."
			::= { wsCcStatsMuTxRetriesEntry 11 }

		
		-- 1.3.6.1.4.1.388.14.3.3.1.3.6.1.12
		wsCcStatsMuTxRetries11 OBJECT-TYPE
			SYNTAX Counter32
			MAX-ACCESS read-only
			STATUS deprecated
			DESCRIPTION
				"Number of pkts successfully transmitted with exactly 11 retries."
			::= { wsCcStatsMuTxRetriesEntry 12 }

		
		-- 1.3.6.1.4.1.388.14.3.3.1.3.6.1.13
		wsCcStatsMuTxRetries12 OBJECT-TYPE
			SYNTAX Counter32
			MAX-ACCESS read-only
			STATUS deprecated
			DESCRIPTION
				"Number of pkts successfully transmitted with exactly 12 retries."
			::= { wsCcStatsMuTxRetriesEntry 13 }

		
		-- 1.3.6.1.4.1.388.14.3.3.1.3.6.1.14
		wsCcStatsMuTxRetries13 OBJECT-TYPE
			SYNTAX Counter32
			MAX-ACCESS read-only
			STATUS deprecated
			DESCRIPTION
				"Number of pkts successfully transmitted with exactly 13 retries."
			::= { wsCcStatsMuTxRetriesEntry 14 }

		
		-- 1.3.6.1.4.1.388.14.3.3.1.3.6.1.15
		wsCcStatsMuTxRetries14 OBJECT-TYPE
			SYNTAX Counter32
			MAX-ACCESS read-only
			STATUS deprecated
			DESCRIPTION
				"Number of pkts successfully transmitted with exactly 14 retries."
			::= { wsCcStatsMuTxRetriesEntry 15 }

		
		-- 1.3.6.1.4.1.388.14.3.3.1.3.6.1.16
		wsCcStatsMuTxRetries15 OBJECT-TYPE
			SYNTAX Counter32
			MAX-ACCESS read-only
			STATUS deprecated
			DESCRIPTION
				"Number of pkts successfully transmitted with exactly 15 retries."
			::= { wsCcStatsMuTxRetriesEntry 16 }

		
		-- 1.3.6.1.4.1.388.14.3.3.1.3.6.1.17
		wsCcStatsMuTxRetriesFailed OBJECT-TYPE
			SYNTAX Counter32
			MAX-ACCESS read-only
			STATUS deprecated
			DESCRIPTION
				"Number of pkts that never were successfully 
				transmitted to because the max retry count was exceeded."
			::= { wsCcStatsMuTxRetriesEntry 17 }

		
		-- 1.3.6.1.4.1.388.14.3.3.1.3.6.1.18
		wsCcStatsMuTxRetriesTotal OBJECT-TYPE
			SYNTAX Counter32
			MAX-ACCESS read-only
			STATUS deprecated
			DESCRIPTION
				"A total sum of all retries across all packets sent
				to this MU.
				
				For example, if 4 packets have been sent, with the
				following number of retires: 2, 0, 5, gave-up,
				this value would be 2+0+5+16 = 23."
			::= { wsCcStatsMuTxRetriesEntry 18 }

		
		-- 1.3.6.1.4.1.388.14.3.3.1.3.6.1.19
		wsCcStatsMuTxRetriesMostRecent OBJECT-TYPE
			SYNTAX INTEGER (0..16)
			MAX-ACCESS read-only
			STATUS deprecated
			DESCRIPTION
				"Most recent retry done by MU."
			::= { wsCcStatsMuTxRetriesEntry 19 }

		
		-- 1.3.6.1.4.1.388.14.3.3.1.3.7
		wsCcStatsMuTxRetriesOctetsTable OBJECT-TYPE
			SYNTAX SEQUENCE OF WsCcStatsMuTxRetriesOctetsEntry
			MAX-ACCESS not-accessible
			STATUS deprecated
			DESCRIPTION
				"For each MU serviced by the switch, this table describes 
				counts of the number of octets affected by transmit 
				retries, (no retries, 1 retry, 2 retries,... gave-up)."
			::= { wsCcStatsMu 7 }

		
		-- 1.3.6.1.4.1.388.14.3.3.1.3.7.1
		wsCcStatsMuTxRetriesOctetsEntry OBJECT-TYPE
			SYNTAX WsCcStatsMuTxRetriesOctetsEntry
			MAX-ACCESS not-accessible
			STATUS deprecated
			DESCRIPTION
				" "
			INDEX { wsCcStatsMuMac }
			::= { wsCcStatsMuTxRetriesOctetsTable 1 }

		
		WsCcStatsMuTxRetriesOctetsEntry ::=
			SEQUENCE { 
				wsCcStatsMuTxRetriesOctetsNone
					Counter32,
				wsCcStatsMuTxRetriesOctets01
					Counter32,
				wsCcStatsMuTxRetriesOctets02
					Counter32,
				wsCcStatsMuTxRetriesOctets03
					Counter32,
				wsCcStatsMuTxRetriesOctets04
					Counter32,
				wsCcStatsMuTxRetriesOctets05
					Counter32,
				wsCcStatsMuTxRetriesOctets06
					Counter32,
				wsCcStatsMuTxRetriesOctets07
					Counter32,
				wsCcStatsMuTxRetriesOctets08
					Counter32,
				wsCcStatsMuTxRetriesOctets09
					Counter32,
				wsCcStatsMuTxRetriesOctets10
					Counter32,
				wsCcStatsMuTxRetriesOctets11
					Counter32,
				wsCcStatsMuTxRetriesOctets12
					Counter32,
				wsCcStatsMuTxRetriesOctets13
					Counter32,
				wsCcStatsMuTxRetriesOctets14
					Counter32,
				wsCcStatsMuTxRetriesOctets15
					Counter32,
				wsCcStatsMuTxRetriesOctetsFailed
					Counter32
			 }

		-- 1.3.6.1.4.1.388.14.3.3.1.3.7.1.1
		wsCcStatsMuTxRetriesOctetsNone OBJECT-TYPE
			SYNTAX Counter32
			MAX-ACCESS read-only
			STATUS deprecated
			DESCRIPTION
				"Number of octets successfully transmitted with no retries."
			::= { wsCcStatsMuTxRetriesOctetsEntry 1 }

		
		-- 1.3.6.1.4.1.388.14.3.3.1.3.7.1.2
		wsCcStatsMuTxRetriesOctets01 OBJECT-TYPE
			SYNTAX Counter32
			MAX-ACCESS read-only
			STATUS deprecated
			DESCRIPTION
				"Number of octets successfully transmitted with exactly 1 retries."
			::= { wsCcStatsMuTxRetriesOctetsEntry 2 }

		
		-- 1.3.6.1.4.1.388.14.3.3.1.3.7.1.3
		wsCcStatsMuTxRetriesOctets02 OBJECT-TYPE
			SYNTAX Counter32
			MAX-ACCESS read-only
			STATUS deprecated
			DESCRIPTION
				"Number of octets successfully transmitted with exactly 2 retries."
			::= { wsCcStatsMuTxRetriesOctetsEntry 3 }

		
		-- 1.3.6.1.4.1.388.14.3.3.1.3.7.1.4
		wsCcStatsMuTxRetriesOctets03 OBJECT-TYPE
			SYNTAX Counter32
			MAX-ACCESS read-only
			STATUS deprecated
			DESCRIPTION
				"Number of octets successfully transmitted with exactly 3 retries."
			::= { wsCcStatsMuTxRetriesOctetsEntry 4 }

		
		-- 1.3.6.1.4.1.388.14.3.3.1.3.7.1.5
		wsCcStatsMuTxRetriesOctets04 OBJECT-TYPE
			SYNTAX Counter32
			MAX-ACCESS read-only
			STATUS deprecated
			DESCRIPTION
				"Number of octets successfully transmitted with exactly 4 retries."
			::= { wsCcStatsMuTxRetriesOctetsEntry 5 }

		
		-- 1.3.6.1.4.1.388.14.3.3.1.3.7.1.6
		wsCcStatsMuTxRetriesOctets05 OBJECT-TYPE
			SYNTAX Counter32
			MAX-ACCESS read-only
			STATUS deprecated
			DESCRIPTION
				"Number of octets successfully transmitted with exactly 5 retries."
			::= { wsCcStatsMuTxRetriesOctetsEntry 6 }

		
		-- 1.3.6.1.4.1.388.14.3.3.1.3.7.1.7
		wsCcStatsMuTxRetriesOctets06 OBJECT-TYPE
			SYNTAX Counter32
			MAX-ACCESS read-only
			STATUS deprecated
			DESCRIPTION
				"Number of octets successfully transmitted with exactly 6 retries."
			::= { wsCcStatsMuTxRetriesOctetsEntry 7 }

		
		-- 1.3.6.1.4.1.388.14.3.3.1.3.7.1.8
		wsCcStatsMuTxRetriesOctets07 OBJECT-TYPE
			SYNTAX Counter32
			MAX-ACCESS read-only
			STATUS deprecated
			DESCRIPTION
				"Number of octets successfully transmitted with exactly 7 retries."
			::= { wsCcStatsMuTxRetriesOctetsEntry 8 }

		
		-- 1.3.6.1.4.1.388.14.3.3.1.3.7.1.9
		wsCcStatsMuTxRetriesOctets08 OBJECT-TYPE
			SYNTAX Counter32
			MAX-ACCESS read-only
			STATUS deprecated
			DESCRIPTION
				"Number of octets successfully transmitted with exactly 8 retries."
			::= { wsCcStatsMuTxRetriesOctetsEntry 9 }

		
		-- 1.3.6.1.4.1.388.14.3.3.1.3.7.1.10
		wsCcStatsMuTxRetriesOctets09 OBJECT-TYPE
			SYNTAX Counter32
			MAX-ACCESS read-only
			STATUS deprecated
			DESCRIPTION
				"Number of octets successfully transmitted with exactly 9 retries."
			::= { wsCcStatsMuTxRetriesOctetsEntry 10 }

		
		-- 1.3.6.1.4.1.388.14.3.3.1.3.7.1.11
		wsCcStatsMuTxRetriesOctets10 OBJECT-TYPE
			SYNTAX Counter32
			MAX-ACCESS read-only
			STATUS deprecated
			DESCRIPTION
				"Number of octets successfully transmitted with exactly 10 retries."
			::= { wsCcStatsMuTxRetriesOctetsEntry 11 }

		
		-- 1.3.6.1.4.1.388.14.3.3.1.3.7.1.12
		wsCcStatsMuTxRetriesOctets11 OBJECT-TYPE
			SYNTAX Counter32
			MAX-ACCESS read-only
			STATUS deprecated
			DESCRIPTION
				"Number of octets successfully transmitted with exactly 11 retries."
			::= { wsCcStatsMuTxRetriesOctetsEntry 12 }

		
		-- 1.3.6.1.4.1.388.14.3.3.1.3.7.1.13
		wsCcStatsMuTxRetriesOctets12 OBJECT-TYPE
			SYNTAX Counter32
			MAX-ACCESS read-only
			STATUS deprecated
			DESCRIPTION
				"Number of octets successfully transmitted with exactly 12 retries."
			::= { wsCcStatsMuTxRetriesOctetsEntry 13 }

		
		-- 1.3.6.1.4.1.388.14.3.3.1.3.7.1.14
		wsCcStatsMuTxRetriesOctets13 OBJECT-TYPE
			SYNTAX Counter32
			MAX-ACCESS read-only
			STATUS deprecated
			DESCRIPTION
				"Number of octets successfully transmitted with exactly 13 retries."
			::= { wsCcStatsMuTxRetriesOctetsEntry 14 }

		
		-- 1.3.6.1.4.1.388.14.3.3.1.3.7.1.15
		wsCcStatsMuTxRetriesOctets14 OBJECT-TYPE
			SYNTAX Counter32
			MAX-ACCESS read-only
			STATUS deprecated
			DESCRIPTION
				"Number of octets successfully transmitted with exactly 14 retries."
			::= { wsCcStatsMuTxRetriesOctetsEntry 15 }

		
		-- 1.3.6.1.4.1.388.14.3.3.1.3.7.1.16
		wsCcStatsMuTxRetriesOctets15 OBJECT-TYPE
			SYNTAX Counter32
			MAX-ACCESS read-only
			STATUS deprecated
			DESCRIPTION
				"Number of octets successfully transmitted with exactly 15 retries."
			::= { wsCcStatsMuTxRetriesOctetsEntry 16 }

		
		-- 1.3.6.1.4.1.388.14.3.3.1.3.7.1.17
		wsCcStatsMuTxRetriesOctetsFailed OBJECT-TYPE
			SYNTAX Counter32
			MAX-ACCESS read-only
			STATUS deprecated
			DESCRIPTION
				"Number of octets that never were successfully 
				transmitted to because the max retry count was exceeded."
			::= { wsCcStatsMuTxRetriesOctetsEntry 17 }

		
		-- 1.3.6.1.4.1.388.14.3.3.1.3.8
		wsCcStatsMuSigTable OBJECT-TYPE
			SYNTAX SEQUENCE OF WsCcStatsMuSigEntry
			MAX-ACCESS not-accessible
			STATUS deprecated
			DESCRIPTION
				"This table describes statistics about RSSI, Signal, Noise,
				and SNR for packets recieved via each MU serviced by the switch."
			::= { wsCcStatsMu 8 }

		
		-- 1.3.6.1.4.1.388.14.3.3.1.3.8.1
		wsCcStatsMuSigEntry OBJECT-TYPE
			SYNTAX WsCcStatsMuSigEntry
			MAX-ACCESS not-accessible
			STATUS deprecated
			DESCRIPTION
				" "
			INDEX { wsCcStatsMuMac }
			::= { wsCcStatsMuSigTable 1 }

		
		WsCcStatsMuSigEntry ::=
			SEQUENCE { 
				wsCcStatsMuSigNumPkts
					Counter32,
				wsCcStatsMuSigSignalBest
					Integer32,
				wsCcStatsMuSigSignalWorst
					Integer32,
				wsCcStatsMuSigSignalSum
					Integer32,
				wsCcStatsMuSigSignalSumSquares
					Counter64,
				wsCcStatsMuSigSignalMostRecent
					Integer32,
				wsCcStatsMuSigNoiseBest
					Integer32,
				wsCcStatsMuSigNoiseWorst
					Integer32,
				wsCcStatsMuSigNoiseSum
					Integer32,
				wsCcStatsMuSigStatsNoiseSumSquares
					Counter64,
				wsCcStatsMuSigNoiseMostRecent
					Integer32,
				wsCcStatsMuSigSnrBest
					Integer32,
				wsCcStatsMuSigSnrWorst
					Integer32,
				wsCcStatsMuSigSnrSum
					Integer32,
				wsCcStatsMuSigSnrSumSquares
					Counter64,
				wsCcStatsMuSigSnrMostRecent
					Integer32
			 }

		-- 1.3.6.1.4.1.388.14.3.3.1.3.8.1.1
		wsCcStatsMuSigNumPkts OBJECT-TYPE
			SYNTAX Counter32
			MAX-ACCESS read-only
			STATUS deprecated
			DESCRIPTION
				"Total packets received included in
				all the other counters reported in this row."
			::= { wsCcStatsMuSigEntry 1 }

		
		-- 1.3.6.1.4.1.388.14.3.3.1.3.8.1.2
		wsCcStatsMuSigSignalBest OBJECT-TYPE
			SYNTAX Integer32
			UNITS "dBm"
			MAX-ACCESS read-only
			STATUS deprecated
			DESCRIPTION
				"The best Signal value seen so far.
				(Remember that a -20dBm Signal is better than -60dBm).
				
				This value is initialized to -500dBm.
				"
			::= { wsCcStatsMuSigEntry 2 }

		
		-- 1.3.6.1.4.1.388.14.3.3.1.3.8.1.3
		wsCcStatsMuSigSignalWorst OBJECT-TYPE
			SYNTAX Integer32
			UNITS "dBm"
			MAX-ACCESS read-only
			STATUS deprecated
			DESCRIPTION
				"The worst Signal value seen so far.
				(Remember that a -80dBm Signal is worse than -60dBm).
				
				This value is initialized to 500dBm."
			::= { wsCcStatsMuSigEntry 3 }

		
		-- 1.3.6.1.4.1.388.14.3.3.1.3.8.1.4
		wsCcStatsMuSigSignalSum OBJECT-TYPE
			SYNTAX Integer32
			UNITS "dBm"
			MAX-ACCESS read-only
			STATUS deprecated
			DESCRIPTION
				"A running sum of all Signal values calculated by the
				switch (using reported RSSI values), for packets received.
				
				Note that this value is normally a negative value
				ranging from -10dBm to -80dBm.  It is possible for this
				value to be positive, but that would be rare, and would
				signal an exceptionally strong signal."
			::= { wsCcStatsMuSigEntry 4 }

		
		-- 1.3.6.1.4.1.388.14.3.3.1.3.8.1.5
		wsCcStatsMuSigSignalSumSquares OBJECT-TYPE
			SYNTAX Counter64
			UNITS "dBm"
			MAX-ACCESS read-only
			STATUS deprecated
			DESCRIPTION
				"A sum of the squares of each Signal value calculated
				for packets received.
				
				Unlike _SignalSum, this value is never negative, since
				the square of a negative number is a positive."
			::= { wsCcStatsMuSigEntry 5 }

		
		-- 1.3.6.1.4.1.388.14.3.3.1.3.8.1.6
		wsCcStatsMuSigSignalMostRecent OBJECT-TYPE
			SYNTAX Integer32
			UNITS "dBm"
			MAX-ACCESS read-only
			STATUS deprecated
			DESCRIPTION
				"The best Signal value seen so far.
				(Remember that a -20dBm Signal is better than -60dBm).
				
				This value does not make sense when ccMuSigStatsNumPkts 
				equals to 0."
			::= { wsCcStatsMuSigEntry 6 }

		
		-- 1.3.6.1.4.1.388.14.3.3.1.3.8.1.7
		wsCcStatsMuSigNoiseBest OBJECT-TYPE
			SYNTAX Integer32
			UNITS "dBm"
			MAX-ACCESS read-only
			STATUS deprecated
			DESCRIPTION
				"The best Noise value seen so far.
				(Remember that -80dBm Noise is better than -70dBm).
				
				This value is initialized to 500dBm."
			::= { wsCcStatsMuSigEntry 7 }

		
		-- 1.3.6.1.4.1.388.14.3.3.1.3.8.1.8
		wsCcStatsMuSigNoiseWorst OBJECT-TYPE
			SYNTAX Integer32
			UNITS "dBm"
			MAX-ACCESS read-only
			STATUS deprecated
			DESCRIPTION
				"The worst Noise value seen so far.
				(Remember that -50dBm Noise is worse than -60dBm).
				
				This value is initialized to -500dBm."
			::= { wsCcStatsMuSigEntry 8 }

		
		-- 1.3.6.1.4.1.388.14.3.3.1.3.8.1.9
		wsCcStatsMuSigNoiseSum OBJECT-TYPE
			SYNTAX Integer32
			UNITS "dBm"
			MAX-ACCESS read-only
			STATUS deprecated
			DESCRIPTION
				"A running sum of all Noise values calculated by the
				switch (using reported RSSI values), for packets.
				
				Like _SignalSum, this value is normally a negative value."
			::= { wsCcStatsMuSigEntry 9 }

		
		-- 1.3.6.1.4.1.388.14.3.3.1.3.8.1.10
		wsCcStatsMuSigStatsNoiseSumSquares OBJECT-TYPE
			SYNTAX Counter64
			UNITS "dBm"
			MAX-ACCESS read-only
			STATUS deprecated
			DESCRIPTION
				"A sum of the squares of each Noise value calculated
				for packets received.
				
				As with _SignalSumSquares, this value is never negative."
			::= { wsCcStatsMuSigEntry 10 }

		
		-- 1.3.6.1.4.1.388.14.3.3.1.3.8.1.11
		wsCcStatsMuSigNoiseMostRecent OBJECT-TYPE
			SYNTAX Integer32
			UNITS "dBm"
			MAX-ACCESS read-only
			STATUS deprecated
			DESCRIPTION
				"The best Noise value seen so far.
				(Remember that -80dBm Noise is better than -70dBm).
				
				This value does not make sense when ccMuSigStatsNumPkts 
				equals to 0."
			::= { wsCcStatsMuSigEntry 11 }

		
		-- 1.3.6.1.4.1.388.14.3.3.1.3.8.1.12
		wsCcStatsMuSigSnrBest OBJECT-TYPE
			SYNTAX Integer32
			UNITS "dB"
			MAX-ACCESS read-only
			STATUS deprecated
			DESCRIPTION
				"The best SNR value seen so far.
				(Remember that +30dBm SNR is better than +20dBm).
				
				This value is initialized to -500dB."
			::= { wsCcStatsMuSigEntry 12 }

		
		-- 1.3.6.1.4.1.388.14.3.3.1.3.8.1.13
		wsCcStatsMuSigSnrWorst OBJECT-TYPE
			SYNTAX Integer32
			UNITS "dB"
			MAX-ACCESS read-only
			STATUS deprecated
			DESCRIPTION
				"The worst SNR value seen so far.
				(Remember that +10dBm SNR is worse than +20dBm).
				
				This value is initialized to 500dB."
			::= { wsCcStatsMuSigEntry 13 }

		
		-- 1.3.6.1.4.1.388.14.3.3.1.3.8.1.14
		wsCcStatsMuSigSnrSum OBJECT-TYPE
			SYNTAX Integer32
			UNITS "dB"
			MAX-ACCESS read-only
			STATUS deprecated
			DESCRIPTION
				"A running sum of all SNR values calculated by the
				switch (using reported RSSI values), for packets received.
				
				Unlike _Signal and _Noise, this value is never negative."
			::= { wsCcStatsMuSigEntry 14 }

		
		-- 1.3.6.1.4.1.388.14.3.3.1.3.8.1.15
		wsCcStatsMuSigSnrSumSquares OBJECT-TYPE
			SYNTAX Counter64
			UNITS "dB"
			MAX-ACCESS read-only
			STATUS deprecated
			DESCRIPTION
				"A sum of the squares of each SNR value calculated
				for packets received.
				
				This value is never negative."
			::= { wsCcStatsMuSigEntry 15 }

		
		-- 1.3.6.1.4.1.388.14.3.3.1.3.8.1.16
		wsCcStatsMuSigSnrMostRecent OBJECT-TYPE
			SYNTAX Integer32
			UNITS "dB"
			MAX-ACCESS read-only
			STATUS deprecated
			DESCRIPTION
				"The best SNR value seen so far.
				(Remember that +30dBm SNR is better than +20dBm).
				
				This value does not make sense when ccMuSigStatsNumPkts 
				equals to 0."
			::= { wsCcStatsMuSigEntry 16 }

		
		-- 1.3.6.1.4.1.388.14.3.3.1.3.9
		wsCcStatsMuSumShortTable OBJECT-TYPE
			SYNTAX SEQUENCE OF WsCcStatsMuSumShortEntry
			MAX-ACCESS not-accessible
			STATUS current
			DESCRIPTION
				"Averages and rates calculated over the SHORT window for
				each MU."
			::= { wsCcStatsMu 9 }

		
		-- 1.3.6.1.4.1.388.14.3.3.1.3.9.1
		wsCcStatsMuSumShortEntry OBJECT-TYPE
			SYNTAX WsCcStatsMuSumShortEntry
			MAX-ACCESS not-accessible
			STATUS current
			DESCRIPTION
				" "
			INDEX { wsCcStatsMuMac }
			::= { wsCcStatsMuSumShortTable 1 }

		
		WsCcStatsMuSumShortEntry ::=
			SEQUENCE { 
				wsCcStatsMuSumShortTimestamp
					TimeTicks,
				wsCcStatsMuSumShortNumPkts
					Unsigned32,
				wsCcStatsMuSumShortPktsPerSec100
					ScaleBy100,
				wsCcStatsMuSumShortPktsPerSecTx100
					ScaleBy100,
				wsCcStatsMuSumShortPktsPerSecRx100
					ScaleBy100,
				wsCcStatsMuSumShortThroughput
					Unsigned32,
				wsCcStatsMuSumShortThroughputTx
					Unsigned32,
				wsCcStatsMuSumShortThroughputRx
					Unsigned32,
				wsCcStatsMuSumShortAvgBitSpeed
					Unsigned32,
				wsCcStatsMuSumShortAvgMuSignal
					Integer32,
				wsCcStatsMuSumShortAvgMuNoise
					Integer32,
				wsCcStatsMuSumShortAvgMuSnr
					Integer32,
				wsCcStatsMuSumShortPp10kNUcastPkts
					PartsPer10k,
				wsCcStatsMuSumShortPp10kTxWithRetries
					PartsPer10k,
				wsCcStatsMuSumShortPp10kDropped
					PartsPer10k,
				wsCcStatsMuSumShortTxAvgRetries100
					ScaleBy100,
				wsCcStatsMuSumShortPp10kRxUndecrypt
					PartsPer10k
			 }

		-- 1.3.6.1.4.1.388.14.3.3.1.3.9.1.1
		wsCcStatsMuSumShortTimestamp OBJECT-TYPE
			SYNTAX TimeTicks
			MAX-ACCESS read-only
			STATUS current
			DESCRIPTION
				"Snapshot of sysUpTime as of the END of the 'window' of 
				time that this entry of values represents."
			::= { wsCcStatsMuSumShortEntry 1 }

		
		-- 1.3.6.1.4.1.388.14.3.3.1.3.9.1.2
		wsCcStatsMuSumShortNumPkts OBJECT-TYPE
			SYNTAX Unsigned32
			UNITS "packets"
			MAX-ACCESS read-only
			STATUS current
			DESCRIPTION
				"The number of packets used to calculate the statistics in
				this window."
			::= { wsCcStatsMuSumShortEntry 2 }

		
		-- 1.3.6.1.4.1.388.14.3.3.1.3.9.1.3
		wsCcStatsMuSumShortPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100."
			::= { wsCcStatsMuSumShortEntry 3 }

		
		-- 1.3.6.1.4.1.388.14.3.3.1.3.9.1.4
		wsCcStatsMuSumShortPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100."
			::= { wsCcStatsMuSumShortEntry 4 }

		
		-- 1.3.6.1.4.1.388.14.3.3.1.3.9.1.5
		wsCcStatsMuSumShortPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100."
			::= { wsCcStatsMuSumShortEntry 5 }

		
		-- 1.3.6.1.4.1.388.14.3.3.1.3.9.1.6
		wsCcStatsMuSumShortThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries)."
			::= { wsCcStatsMuSumShortEntry 6 }

		
		-- 1.3.6.1.4.1.388.14.3.3.1.3.9.1.7
		wsCcStatsMuSumShortThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries)."
			::= { wsCcStatsMuSumShortEntry 7 }

		
		-- 1.3.6.1.4.1.388.14.3.3.1.3.9.1.8
		wsCcStatsMuSumShortThroughputRx OBJECT-TYPE
			SYNTAX Unsigned32
			UNITS "bits per second"
			MAX-ACCESS read-only
			STATUS current
			DESCRIPTION
				"Actual number of bits RX over the window,
				divided by the number of seconds in the window."
			::= { wsCcStatsMuSumShortEntry 8 }

		
		-- 1.3.6.1.4.1.388.14.3.3.1.3.9.1.9
		wsCcStatsMuSumShortAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { wsCcStatsMuSumShortEntry 9 }

		
		-- 1.3.6.1.4.1.388.14.3.3.1.3.9.1.10
		wsCcStatsMuSumShortAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values.  PO"
			::= { wsCcStatsMuSumShortEntry 10 }

		
		-- 1.3.6.1.4.1.388.14.3.3.1.3.9.1.11
		wsCcStatsMuSumShortAvgMuNoise OBJECT-TYPE
			SYNTAX Integer32
			UNITS "dBm"
			MAX-ACCESS read-only
			STATUS current
			DESCRIPTION
				"The average of all noise values over the window."
			::= { wsCcStatsMuSumShortEntry 11 }

		
		-- 1.3.6.1.4.1.388.14.3.3.1.3.9.1.12
		wsCcStatsMuSumShortAvgMuSnr OBJECT-TYPE
			SYNTAX Integer32
			UNITS "dB"
			MAX-ACCESS read-only
			STATUS current
			DESCRIPTION
				"The average of all SNR values over the window."
			::= { wsCcStatsMuSumShortEntry 12 }

		
		-- 1.3.6.1.4.1.388.14.3.3.1.3.9.1.13
		wsCcStatsMuSumShortPp10kNUcastPkts OBJECT-TYPE
			SYNTAX PartsPer10k
			UNITS "parts-per-10000"
			MAX-ACCESS read-only
			STATUS current
			DESCRIPTION
				"Ratio of packets that were NOT unicast.
				
				Expressed as parts-per-10000."
			::= { wsCcStatsMuSumShortEntry 13 }

		
		-- 1.3.6.1.4.1.388.14.3.3.1.3.9.1.14
		wsCcStatsMuSumShortPp10kTxWithRetries OBJECT-TYPE
			SYNTAX PartsPer10k
			UNITS "parts-per-10000"
			MAX-ACCESS read-only
			STATUS current
			DESCRIPTION
				"Ratio of TX packets that experienced one or more retries.
				
				Expressed as parts-per-10000."
			::= { wsCcStatsMuSumShortEntry 14 }

		
		-- 1.3.6.1.4.1.388.14.3.3.1.3.9.1.15
		wsCcStatsMuSumShortPp10kDropped OBJECT-TYPE
			SYNTAX PartsPer10k
			UNITS "parts-per-10000"
			MAX-ACCESS read-only
			STATUS current
			DESCRIPTION
				"Packets dropped divided by packets sent.  Dropped here 
				means dropped intentionally due to the appropriate QoS 
				queue being full.  Other reasons for dropped packets are 
				not counted in this ratio.
				
				Calculated as an average for all WLANs implemented on 
				this MU."
			::= { wsCcStatsMuSumShortEntry 15 }

		
		-- 1.3.6.1.4.1.388.14.3.3.1.3.9.1.16
		wsCcStatsMuSumShortTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00)."
			::= { wsCcStatsMuSumShortEntry 16 }

		
		-- 1.3.6.1.4.1.388.14.3.3.1.3.9.1.17
		wsCcStatsMuSumShortPp10kRxUndecrypt OBJECT-TYPE
			SYNTAX PartsPer10k
			UNITS "parts-per-10000"
			MAX-ACCESS read-only
			STATUS current
			DESCRIPTION
				"Ratio of RX packets that were undecryptable.
				
				Expressed as parts-per-10000.
				"
			::= { wsCcStatsMuSumShortEntry 17 }

		
		-- 1.3.6.1.4.1.388.14.3.3.1.3.10
		wsCcStatsMuSumLongTable OBJECT-TYPE
			SYNTAX SEQUENCE OF WsCcStatsMuSumLongEntry
			MAX-ACCESS not-accessible
			STATUS current
			DESCRIPTION
				"Averages and rates calculated over the LONG window for
				each MU.
				
				(Refer to ccMuSumStatsShortTable for descriptions)."
			::= { wsCcStatsMu 10 }

		
		-- 1.3.6.1.4.1.388.14.3.3.1.3.10.1
		wsCcStatsMuSumLongEntry OBJECT-TYPE
			SYNTAX WsCcStatsMuSumLongEntry
			MAX-ACCESS not-accessible
			STATUS current
			DESCRIPTION
				" "
			INDEX { wsCcStatsMuMac }
			::= { wsCcStatsMuSumLongTable 1 }

		
		WsCcStatsMuSumLongEntry ::=
			SEQUENCE { 
				wsCcStatsMuSumLongTimestamp
					TimeTicks,
				wsCcStatsMuSumLongNumPkts
					Unsigned32,
				wsCcStatsMuSumLongPktsPerSec100
					ScaleBy100,
				wsCcStatsMuSumLongPktsPerSecTx100
					ScaleBy100,
				wsCcStatsMuSumLongPktsPerSecRx100
					ScaleBy100,
				wsCcStatsMuSumLongThroughput
					Unsigned32,
				wsCcStatsMuSumLongThroughputTx
					Unsigned32,
				wsCcStatsMuSumLongThroughputRx
					Unsigned32,
				wsCcStatsMuSumLongAvgBitSpeed
					Unsigned32,
				wsCcStatsMuSumLongAvgMuSignal
					Integer32,
				wsCcStatsMuSumLongAvgMuNoise
					Integer32,
				wsCcStatsMuSumLongAvgMuSnr
					Integer32,
				wsCcStatsMuSumLongPp10kNUcastPkts
					PartsPer10k,
				wsCcStatsMuSumLongPp10kTxWithRetries
					PartsPer10k,
				wsCcStatsMuSumLongPp10kDropped
					PartsPer10k,
				wsCcStatsMuSumLongTxAvgRetries100
					ScaleBy100,
				wsCcStatsMuSumLongPp10kRxUndecrypt
					PartsPer10k
			 }

		-- 1.3.6.1.4.1.388.14.3.3.1.3.10.1.1
		wsCcStatsMuSumLongTimestamp OBJECT-TYPE
			SYNTAX TimeTicks
			MAX-ACCESS read-only
			STATUS current
			DESCRIPTION
				" "
			::= { wsCcStatsMuSumLongEntry 1 }

		
		-- 1.3.6.1.4.1.388.14.3.3.1.3.10.1.2
		wsCcStatsMuSumLongNumPkts OBJECT-TYPE
			SYNTAX Unsigned32
			UNITS "packets"
			MAX-ACCESS read-only
			STATUS current
			DESCRIPTION
				" "
			::= { wsCcStatsMuSumLongEntry 2 }

		
		-- 1.3.6.1.4.1.388.14.3.3.1.3.10.1.3
		wsCcStatsMuSumLongPktsPerSec100 OBJECT-TYPE
			SYNTAX ScaleBy100
			UNITS "pkts per sec x100"
			MAX-ACCESS read-only
			STATUS current
			DESCRIPTION
				" "
			::= { wsCcStatsMuSumLongEntry 3 }

		
		-- 1.3.6.1.4.1.388.14.3.3.1.3.10.1.4
		wsCcStatsMuSumLongPktsPerSecTx100 OBJECT-TYPE
			SYNTAX ScaleBy100
			UNITS "pkts per sec x100"
			MAX-ACCESS read-only
			STATUS current
			DESCRIPTION
				" "
			::= { wsCcStatsMuSumLongEntry 4 }

		
		-- 1.3.6.1.4.1.388.14.3.3.1.3.10.1.5
		wsCcStatsMuSumLongPktsPerSecRx100 OBJECT-TYPE
			SYNTAX ScaleBy100
			UNITS "pkts per sec x100"
			MAX-ACCESS read-only
			STATUS current
			DESCRIPTION
				" "
			::= { wsCcStatsMuSumLongEntry 5 }

		
		-- 1.3.6.1.4.1.388.14.3.3.1.3.10.1.6
		wsCcStatsMuSumLongThroughput OBJECT-TYPE
			SYNTAX Unsigned32
			UNITS "bits per second"
			MAX-ACCESS read-only
			STATUS current
			DESCRIPTION
				" "
			::= { wsCcStatsMuSumLongEntry 6 }

		
		-- 1.3.6.1.4.1.388.14.3.3.1.3.10.1.7
		wsCcStatsMuSumLongThroughputTx OBJECT-TYPE
			SYNTAX Unsigned32
			UNITS "bits per second"
			MAX-ACCESS read-only
			STATUS current
			DESCRIPTION
				" "
			::= { wsCcStatsMuSumLongEntry 7 }

		
		-- 1.3.6.1.4.1.388.14.3.3.1.3.10.1.8
		wsCcStatsMuSumLongThroughputRx OBJECT-TYPE
			SYNTAX Unsigned32
			UNITS "bits per second"
			MAX-ACCESS read-only
			STATUS current
			DESCRIPTION
				" "
			::= { wsCcStatsMuSumLongEntry 8 }

		
		-- 1.3.6.1.4.1.388.14.3.3.1.3.10.1.9
		wsCcStatsMuSumLongAvgBitSpeed OBJECT-TYPE
			SYNTAX Unsigned32
			UNITS "bits per second"
			MAX-ACCESS read-only
			STATUS current
			DESCRIPTION
				" "
			::= { wsCcStatsMuSumLongEntry 9 }

		
		-- 1.3.6.1.4.1.388.14.3.3.1.3.10.1.10
		wsCcStatsMuSumLongAvgMuSignal OBJECT-TYPE
			SYNTAX Integer32
			UNITS "dBm"
			MAX-ACCESS read-only
			STATUS current
			DESCRIPTION
				" "
			::= { wsCcStatsMuSumLongEntry 10 }

		
		-- 1.3.6.1.4.1.388.14.3.3.1.3.10.1.11
		wsCcStatsMuSumLongAvgMuNoise OBJECT-TYPE
			SYNTAX Integer32
			UNITS "dBm"
			MAX-ACCESS read-only
			STATUS current
			DESCRIPTION
				" "
			::= { wsCcStatsMuSumLongEntry 11 }

		
		-- 1.3.6.1.4.1.388.14.3.3.1.3.10.1.12
		wsCcStatsMuSumLongAvgMuSnr OBJECT-TYPE
			SYNTAX Integer32
			UNITS "dB"
			MAX-ACCESS read-only
			STATUS current
			DESCRIPTION
				" "
			::= { wsCcStatsMuSumLongEntry 12 }

		
		-- 1.3.6.1.4.1.388.14.3.3.1.3.10.1.13
		wsCcStatsMuSumLongPp10kNUcastPkts OBJECT-TYPE
			SYNTAX PartsPer10k
			UNITS "parts-per-10000"
			MAX-ACCESS read-only
			STATUS current
			DESCRIPTION
				" "
			::= { wsCcStatsMuSumLongEntry 13 }

		
		-- 1.3.6.1.4.1.388.14.3.3.1.3.10.1.14
		wsCcStatsMuSumLongPp10kTxWithRetries OBJECT-TYPE
			SYNTAX PartsPer10k
			UNITS "parts-per-10000"
			MAX-ACCESS read-only
			STATUS current
			DESCRIPTION
				" "
			::= { wsCcStatsMuSumLongEntry 14 }

		
		-- 1.3.6.1.4.1.388.14.3.3.1.3.10.1.15
		wsCcStatsMuSumLongPp10kDropped OBJECT-TYPE
			SYNTAX PartsPer10k
			UNITS "parts-per-10000"
			MAX-ACCESS read-only
			STATUS current
			DESCRIPTION
				" "
			::= { wsCcStatsMuSumLongEntry 15 }

		
		-- 1.3.6.1.4.1.388.14.3.3.1.3.10.1.16
		wsCcStatsMuSumLongTxAvgRetries100 OBJECT-TYPE
			SYNTAX ScaleBy100
			UNITS "average x100"
			MAX-ACCESS read-only
			STATUS current
			DESCRIPTION
				" "
			::= { wsCcStatsMuSumLongEntry 16 }

		
		-- 1.3.6.1.4.1.388.14.3.3.1.3.10.1.17
		wsCcStatsMuSumLongPp10kRxUndecrypt OBJECT-TYPE
			SYNTAX PartsPer10k
			UNITS "parts-per-10000"
			MAX-ACCESS read-only
			STATUS current
			DESCRIPTION
				" "
			::= { wsCcStatsMuSumLongEntry 17 }

		
-- This group describes all wireless LANs on the switch,
-- and their corresponding security settings.
		-- 1.3.6.1.4.1.388.14.3.3.1.4
		wsCcStatsWlan OBJECT IDENTIFIER ::= { wsCcStatsMIB 4 }

		
		-- 1.3.6.1.4.1.388.14.3.3.1.4.2
		wsCcStatsWlanTable OBJECT-TYPE
			SYNTAX SEQUENCE OF WsCcStatsWlanEntry
			MAX-ACCESS not-accessible
			STATUS current
			DESCRIPTION
				"This table describes general statistics about
				packets sent/recieved via each WLAN on the switch."
			::= { wsCcStatsWlan 2 }

		
		-- 1.3.6.1.4.1.388.14.3.3.1.4.2.1
		wsCcStatsWlanEntry OBJECT-TYPE
			SYNTAX WsCcStatsWlanEntry
			MAX-ACCESS not-accessible
			STATUS current
			DESCRIPTION
				" "
			INDEX { wsCcStatsWlanIndex }
			::= { wsCcStatsWlanTable 1 }

		
		WsCcStatsWlanEntry ::=
			SEQUENCE { 
				wsCcStatsWlanIndex
					Integer32,
				wsCcStatsWlanTxPktsUcast
					Counter32,
				wsCcStatsWlanRxPktsUcast
					Counter32,
				wsCcStatsWlanRxPktsNUcast
					Counter32,
				wsCcStatsWlanTxOctetsUcast
					Counter32,
				wsCcStatsWlanRxOctetsUcast
					Counter32,
				wsCcStatsWlanRxOctetsNUcast
					Counter32,
				wsCcStatsWlanRxUndecryptablePkts
					Counter32,
				wsCcStatsWlanLastActivity
					TimeTicks
			 }

-- Simple Index
		-- 1.3.6.1.4.1.388.14.3.3.1.4.2.1.1
		wsCcStatsWlanIndex OBJECT-TYPE
			SYNTAX Integer32 (1..1001)
			MAX-ACCESS accessible-for-notify
			STATUS current
			DESCRIPTION
				"Simple index."
			::= { wsCcStatsWlanEntry 1 }

		
		-- 1.3.6.1.4.1.388.14.3.3.1.4.2.1.2
		wsCcStatsWlanTxPktsUcast OBJECT-TYPE
			SYNTAX Counter32
			MAX-ACCESS read-only
			STATUS current
			DESCRIPTION
				"Count of unicast packets sent."
			::= { wsCcStatsWlanEntry 2 }

		
		-- 1.3.6.1.4.1.388.14.3.3.1.4.2.1.3
		wsCcStatsWlanRxPktsUcast OBJECT-TYPE
			SYNTAX Counter32
			MAX-ACCESS read-only
			STATUS current
			DESCRIPTION
				"Count of unicast packets received."
			::= { wsCcStatsWlanEntry 3 }

		
		-- 1.3.6.1.4.1.388.14.3.3.1.4.2.1.4
		wsCcStatsWlanRxPktsNUcast OBJECT-TYPE
			SYNTAX Counter32
			MAX-ACCESS read-only
			STATUS current
			DESCRIPTION
				"Count of non-unicast (broadcast & multicast) 
				packets received."
			::= { wsCcStatsWlanEntry 4 }

		
		-- 1.3.6.1.4.1.388.14.3.3.1.4.2.1.5
		wsCcStatsWlanTxOctetsUcast OBJECT-TYPE
			SYNTAX Counter32
			MAX-ACCESS read-only
			STATUS current
			DESCRIPTION
				"Count of unicast octets sent."
			::= { wsCcStatsWlanEntry 5 }

		
		-- 1.3.6.1.4.1.388.14.3.3.1.4.2.1.6
		wsCcStatsWlanRxOctetsUcast OBJECT-TYPE
			SYNTAX Counter32
			MAX-ACCESS read-only
			STATUS current
			DESCRIPTION
				"Count of unicast octets received."
			::= { wsCcStatsWlanEntry 6 }

		
		-- 1.3.6.1.4.1.388.14.3.3.1.4.2.1.7
		wsCcStatsWlanRxOctetsNUcast OBJECT-TYPE
			SYNTAX Counter32
			MAX-ACCESS read-only
			STATUS current
			DESCRIPTION
				"Count of non-unicast (broadcast & multicast) 
				octets received."
			::= { wsCcStatsWlanEntry 7 }

		
		-- 1.3.6.1.4.1.388.14.3.3.1.4.2.1.8
		wsCcStatsWlanRxUndecryptablePkts OBJECT-TYPE
			SYNTAX Counter32
			MAX-ACCESS read-only
			STATUS current
			DESCRIPTION
				"Count of packets received that could
				not be decrypted."
			::= { wsCcStatsWlanEntry 8 }

		
		-- 1.3.6.1.4.1.388.14.3.3.1.4.2.1.9
		wsCcStatsWlanLastActivity OBJECT-TYPE
			SYNTAX TimeTicks
			MAX-ACCESS read-only
			STATUS current
			DESCRIPTION
				"A snapshot of the switch's sysUpTime at the time
				of the last activity (packet sent or received)."
			::= { wsCcStatsWlanEntry 9 }

		
		-- 1.3.6.1.4.1.388.14.3.3.1.4.3
		wsCcStatsWlanRxPktsTable OBJECT-TYPE
			SYNTAX SEQUENCE OF WsCcStatsWlanRxPktsEntry
			MAX-ACCESS not-accessible
			STATUS deprecated
			DESCRIPTION
				"For each WLAN on the switch, this table 
				describes counts of packets received at each 
				possible speed, (1Mb, 2Mb, 5.5Mb, 6Mb...)."
			::= { wsCcStatsWlan 3 }

		
		-- 1.3.6.1.4.1.388.14.3.3.1.4.3.1
		wsCcStatsWlanRxPktsEntry OBJECT-TYPE
			SYNTAX WsCcStatsWlanRxPktsEntry
			MAX-ACCESS not-accessible
			STATUS deprecated
			DESCRIPTION
				" "
			INDEX { wsCcStatsWlanIndex }
			::= { wsCcStatsWlanRxPktsTable 1 }

		
		WsCcStatsWlanRxPktsEntry ::=
			SEQUENCE { 
				wsCcStatsWlanRxPktsAt1Mb
					Counter32,
				wsCcStatsWlanRxPktsAt2Mb
					Counter32,
				wsCcStatsWlanRxPktsAt5pt5Mb
					Counter32,
				wsCcStatsWlanRxPktsAt6Mb
					Counter32,
				wsCcStatsWlanRxPktsAt9Mb
					Counter32,
				wsCcStatsWlanRxPktsAt11Mb
					Counter32,
				wsCcStatsWlanRxPktsAt12Mb
					Counter32,
				wsCcStatsWlanRxPktsAt18Mb
					Counter32,
				wsCcStatsWlanRxPktsAt22Mb
					Counter32,
				wsCcStatsWlanRxPktsAt24Mb
					Counter32,
				wsCcStatsWlanRxPktsAt36Mb
					Counter32,
				wsCcStatsWlanRxPktsAt48Mb
					Counter32,
				wsCcStatsWlanRxPktsAt54Mb
					Counter32
			 }

		-- 1.3.6.1.4.1.388.14.3.3.1.4.3.1.1
		wsCcStatsWlanRxPktsAt1Mb OBJECT-TYPE
			SYNTAX Counter32
			MAX-ACCESS read-only
			STATUS deprecated
			DESCRIPTION
				"Number of pkts received at 1 Mb."
			::= { wsCcStatsWlanRxPktsEntry 1 }

		
		-- 1.3.6.1.4.1.388.14.3.3.1.4.3.1.2
		wsCcStatsWlanRxPktsAt2Mb OBJECT-TYPE
			SYNTAX Counter32
			MAX-ACCESS read-only
			STATUS deprecated
			DESCRIPTION
				"Number of pkts received at 2 Mb."
			::= { wsCcStatsWlanRxPktsEntry 2 }

		
		-- 1.3.6.1.4.1.388.14.3.3.1.4.3.1.3
		wsCcStatsWlanRxPktsAt5pt5Mb OBJECT-TYPE
			SYNTAX Counter32
			MAX-ACCESS read-only
			STATUS deprecated
			DESCRIPTION
				"Number of pkts received at 5.5 Mb."
			::= { wsCcStatsWlanRxPktsEntry 3 }

		
		-- 1.3.6.1.4.1.388.14.3.3.1.4.3.1.4
		wsCcStatsWlanRxPktsAt6Mb OBJECT-TYPE
			SYNTAX Counter32
			MAX-ACCESS read-only
			STATUS deprecated
			DESCRIPTION
				"Number of pkts received at 6 Mb."
			::= { wsCcStatsWlanRxPktsEntry 4 }

		
		-- 1.3.6.1.4.1.388.14.3.3.1.4.3.1.5
		wsCcStatsWlanRxPktsAt9Mb OBJECT-TYPE
			SYNTAX Counter32
			MAX-ACCESS read-only
			STATUS deprecated
			DESCRIPTION
				"Number of pkts received at 9 Mb."
			::= { wsCcStatsWlanRxPktsEntry 5 }

		
		-- 1.3.6.1.4.1.388.14.3.3.1.4.3.1.6
		wsCcStatsWlanRxPktsAt11Mb OBJECT-TYPE
			SYNTAX Counter32
			MAX-ACCESS read-only
			STATUS deprecated
			DESCRIPTION
				"Number of pkts received at 11 Mb."
			::= { wsCcStatsWlanRxPktsEntry 6 }

		
		-- 1.3.6.1.4.1.388.14.3.3.1.4.3.1.7
		wsCcStatsWlanRxPktsAt12Mb OBJECT-TYPE
			SYNTAX Counter32
			MAX-ACCESS read-only
			STATUS deprecated
			DESCRIPTION
				"Number of pkts received at 12 Mb."
			::= { wsCcStatsWlanRxPktsEntry 7 }

		
		-- 1.3.6.1.4.1.388.14.3.3.1.4.3.1.8
		wsCcStatsWlanRxPktsAt18Mb OBJECT-TYPE
			SYNTAX Counter32
			MAX-ACCESS read-only
			STATUS deprecated
			DESCRIPTION
				"Number of pkts received at 18 Mb."
			::= { wsCcStatsWlanRxPktsEntry 8 }

		
		-- 1.3.6.1.4.1.388.14.3.3.1.4.3.1.9
		wsCcStatsWlanRxPktsAt22Mb OBJECT-TYPE
			SYNTAX Counter32
			MAX-ACCESS read-only
			STATUS deprecated
			DESCRIPTION
				"Number of pkts received at 22 Mb."
			::= { wsCcStatsWlanRxPktsEntry 9 }

		
		-- 1.3.6.1.4.1.388.14.3.3.1.4.3.1.10
		wsCcStatsWlanRxPktsAt24Mb OBJECT-TYPE
			SYNTAX Counter32
			MAX-ACCESS read-only
			STATUS deprecated
			DESCRIPTION
				"Number of pkts received at 24 Mb."
			::= { wsCcStatsWlanRxPktsEntry 10 }

		
		-- 1.3.6.1.4.1.388.14.3.3.1.4.3.1.11
		wsCcStatsWlanRxPktsAt36Mb OBJECT-TYPE
			SYNTAX Counter32
			MAX-ACCESS read-only
			STATUS deprecated
			DESCRIPTION
				"Number of pkts received at 36 Mb."
			::= { wsCcStatsWlanRxPktsEntry 11 }

		
		-- 1.3.6.1.4.1.388.14.3.3.1.4.3.1.12
		wsCcStatsWlanRxPktsAt48Mb OBJECT-TYPE
			SYNTAX Counter32
			MAX-ACCESS read-only
			STATUS deprecated
			DESCRIPTION
				"Number of pkts received at 48 Mb."
			::= { wsCcStatsWlanRxPktsEntry 12 }

		
		-- 1.3.6.1.4.1.388.14.3.3.1.4.3.1.13
		wsCcStatsWlanRxPktsAt54Mb OBJECT-TYPE
			SYNTAX Counter32
			MAX-ACCESS read-only
			STATUS deprecated
			DESCRIPTION
				"Number of pkts received at 54 Mb."
			::= { wsCcStatsWlanRxPktsEntry 13 }

		
		-- 1.3.6.1.4.1.388.14.3.3.1.4.4
		wsCcStatsWlanTxPktsTable OBJECT-TYPE
			SYNTAX SEQUENCE OF WsCcStatsWlanTxPktsEntry
			MAX-ACCESS not-accessible
			STATUS deprecated
			DESCRIPTION
				"For each MU serviced by the switch, this table 
				describes counts of packets transmitted at each 
				possible speed, (1Mb, 2Mb, 5.5Mb, 6Mb...)."
			::= { wsCcStatsWlan 4 }

		
		-- 1.3.6.1.4.1.388.14.3.3.1.4.4.1
		wsCcStatsWlanTxPktsEntry OBJECT-TYPE
			SYNTAX WsCcStatsWlanTxPktsEntry
			MAX-ACCESS not-accessible
			STATUS deprecated
			DESCRIPTION
				" "
			INDEX { wsCcStatsWlanIndex }
			::= { wsCcStatsWlanTxPktsTable 1 }

		
		WsCcStatsWlanTxPktsEntry ::=
			SEQUENCE { 
				wsCcStatsWlanTxPktsAt1Mb
					Counter32,
				wsCcStatsWlanTxPktsAt2Mb
					Counter32,
				wsCcStatsWlanTxPktsAt5pt5Mb
					Counter32,
				wsCcStatsWlanTxPktsAt6Mb
					Counter32,
				wsCcStatsWlanTxPktsAt9Mb
					Counter32,
				wsCcStatsWlanTxPktsAt11Mb
					Counter32,
				wsCcStatsWlanTxPktsAt12Mb
					Counter32,
				wsCcStatsWlanTxPktsAt18Mb
					Counter32,
				wsCcStatsWlanTxPktsAt22Mb
					Counter32,
				wsCcStatsWlanTxPktsAt24Mb
					Counter32,
				wsCcStatsWlanTxPktsAt36Mb
					Counter32,
				wsCcStatsWlanTxPktsAt48Mb
					Counter32,
				wsCcStatsWlanTxPktsAt54Mb
					Counter32
			 }

		-- 1.3.6.1.4.1.388.14.3.3.1.4.4.1.1
		wsCcStatsWlanTxPktsAt1Mb OBJECT-TYPE
			SYNTAX Counter32
			MAX-ACCESS read-only
			STATUS deprecated
			DESCRIPTION
				"Number of pkts transmitted at 1 Mb."
			::= { wsCcStatsWlanTxPktsEntry 1 }

		
		-- 1.3.6.1.4.1.388.14.3.3.1.4.4.1.2
		wsCcStatsWlanTxPktsAt2Mb OBJECT-TYPE
			SYNTAX Counter32
			MAX-ACCESS read-only
			STATUS deprecated
			DESCRIPTION
				"Number of pkts transmitted at 2 Mb."
			::= { wsCcStatsWlanTxPktsEntry 2 }

		
		-- 1.3.6.1.4.1.388.14.3.3.1.4.4.1.3
		wsCcStatsWlanTxPktsAt5pt5Mb OBJECT-TYPE
			SYNTAX Counter32
			MAX-ACCESS read-only
			STATUS deprecated
			DESCRIPTION
				"Number of pkts transmitted at 5.5 Mb."
			::= { wsCcStatsWlanTxPktsEntry 3 }

		
		-- 1.3.6.1.4.1.388.14.3.3.1.4.4.1.4
		wsCcStatsWlanTxPktsAt6Mb OBJECT-TYPE
			SYNTAX Counter32
			MAX-ACCESS read-only
			STATUS deprecated
			DESCRIPTION
				"Number of pkts transmitted at 6 Mb."
			::= { wsCcStatsWlanTxPktsEntry 4 }

		
		-- 1.3.6.1.4.1.388.14.3.3.1.4.4.1.5
		wsCcStatsWlanTxPktsAt9Mb OBJECT-TYPE
			SYNTAX Counter32
			MAX-ACCESS read-only
			STATUS deprecated
			DESCRIPTION
				"Number of pkts transmitted at 9 Mb."
			::= { wsCcStatsWlanTxPktsEntry 5 }

		
		-- 1.3.6.1.4.1.388.14.3.3.1.4.4.1.6
		wsCcStatsWlanTxPktsAt11Mb OBJECT-TYPE
			SYNTAX Counter32
			MAX-ACCESS read-only
			STATUS deprecated
			DESCRIPTION
				"Number of pkts transmitted at 11 Mb."
			::= { wsCcStatsWlanTxPktsEntry 6 }

		
		-- 1.3.6.1.4.1.388.14.3.3.1.4.4.1.7
		wsCcStatsWlanTxPktsAt12Mb OBJECT-TYPE
			SYNTAX Counter32
			MAX-ACCESS read-only
			STATUS deprecated
			DESCRIPTION
				"Number of pkts transmitted at 12 Mb."
			::= { wsCcStatsWlanTxPktsEntry 7 }

		
		-- 1.3.6.1.4.1.388.14.3.3.1.4.4.1.8
		wsCcStatsWlanTxPktsAt18Mb OBJECT-TYPE
			SYNTAX Counter32
			MAX-ACCESS read-only
			STATUS deprecated
			DESCRIPTION
				"Number of pkts transmitted at 18 Mb."
			::= { wsCcStatsWlanTxPktsEntry 8 }

		
		-- 1.3.6.1.4.1.388.14.3.3.1.4.4.1.9
		wsCcStatsWlanTxPktsAt22Mb OBJECT-TYPE
			SYNTAX Counter32
			MAX-ACCESS read-only
			STATUS deprecated
			DESCRIPTION
				"Number of pkts transmitted at 22 Mb."
			::= { wsCcStatsWlanTxPktsEntry 9 }

		
		-- 1.3.6.1.4.1.388.14.3.3.1.4.4.1.10
		wsCcStatsWlanTxPktsAt24Mb OBJECT-TYPE
			SYNTAX Counter32
			MAX-ACCESS read-only
			STATUS deprecated
			DESCRIPTION
				"Number of pkts transmitted at 24 Mb."
			::= { wsCcStatsWlanTxPktsEntry 10 }

		
		-- 1.3.6.1.4.1.388.14.3.3.1.4.4.1.11
		wsCcStatsWlanTxPktsAt36Mb OBJECT-TYPE
			SYNTAX Counter32
			MAX-ACCESS read-only
			STATUS deprecated
			DESCRIPTION
				"Number of pkts transmitted at 36 Mb."
			::= { wsCcStatsWlanTxPktsEntry 11 }

		
		-- 1.3.6.1.4.1.388.14.3.3.1.4.4.1.12
		wsCcStatsWlanTxPktsAt48Mb OBJECT-TYPE
			SYNTAX Counter32
			MAX-ACCESS read-only
			STATUS deprecated
			DESCRIPTION
				"Number of pkts transmitted at 48 Mb."
			::= { wsCcStatsWlanTxPktsEntry 12 }

		
		-- 1.3.6.1.4.1.388.14.3.3.1.4.4.1.13
		wsCcStatsWlanTxPktsAt54Mb OBJECT-TYPE
			SYNTAX Counter32
			MAX-ACCESS read-only
			STATUS deprecated
			DESCRIPTION
				"Number of pkts transmitted at 54 Mb."
			::= { wsCcStatsWlanTxPktsEntry 13 }

		
		-- 1.3.6.1.4.1.388.14.3.3.1.4.5
		wsCcStatsWlanRxOctetsTable OBJECT-TYPE
			SYNTAX SEQUENCE OF WsCcStatsWlanRxOctetsEntry
			MAX-ACCESS not-accessible
			STATUS deprecated
			DESCRIPTION
				"For each MU serviced by this switch, this table 
				describes counts of octets received at each 
				possible speed, (1Mb, 2Mb, 5.5Mb, 6Mb...)."
			::= { wsCcStatsWlan 5 }

		
		-- 1.3.6.1.4.1.388.14.3.3.1.4.5.1
		wsCcStatsWlanRxOctetsEntry OBJECT-TYPE
			SYNTAX WsCcStatsWlanRxOctetsEntry
			MAX-ACCESS not-accessible
			STATUS deprecated
			DESCRIPTION
				" "
			INDEX { wsCcStatsWlanIndex }
			::= { wsCcStatsWlanRxOctetsTable 1 }

		
		WsCcStatsWlanRxOctetsEntry ::=
			SEQUENCE { 
				wsCcStatsWlanRxOctetsAt1Mb
					Counter32,
				wsCcStatsWlanRxOctetsAt2Mb
					Counter32,
				wsCcStatsWlanRxOctetsAt5pt5Mb
					Counter32,
				wsCcStatsWlanRxOctetsAt6Mb
					Counter32,
				wsCcStatsWlanRxOctetsAt9Mb
					Counter32,
				wsCcStatsWlanRxOctetsAt11Mb
					Counter32,
				wsCcStatsWlanRxOctetsAt12Mb
					Counter32,
				wsCcStatsWlanRxOctetsAt18Mb
					Counter32,
				wsCcStatsWlanRxOctetsAt22Mb
					Counter32,
				wsCcStatsWlanRxOctetsAt24Mb
					Counter32,
				wsCcStatsWlanRxOctetsAt36Mb
					Counter32,
				wsCcStatsWlanRxOctetsAt48Mb
					Counter32,
				wsCcStatsWlanRxOctetsAt54Mb
					Counter32
			 }

		-- 1.3.6.1.4.1.388.14.3.3.1.4.5.1.1
		wsCcStatsWlanRxOctetsAt1Mb OBJECT-TYPE
			SYNTAX Counter32
			MAX-ACCESS read-only
			STATUS deprecated
			DESCRIPTION
				"Number of octets received at 1 Mb."
			::= { wsCcStatsWlanRxOctetsEntry 1 }

		
		-- 1.3.6.1.4.1.388.14.3.3.1.4.5.1.2
		wsCcStatsWlanRxOctetsAt2Mb OBJECT-TYPE
			SYNTAX Counter32
			MAX-ACCESS read-only
			STATUS deprecated
			DESCRIPTION
				"Number of octets received at 2 Mb."
			::= { wsCcStatsWlanRxOctetsEntry 2 }

		
		-- 1.3.6.1.4.1.388.14.3.3.1.4.5.1.3
		wsCcStatsWlanRxOctetsAt5pt5Mb OBJECT-TYPE
			SYNTAX Counter32
			MAX-ACCESS read-only
			STATUS deprecated
			DESCRIPTION
				"Number of octets received at 5.5 Mb."
			::= { wsCcStatsWlanRxOctetsEntry 3 }

		
		-- 1.3.6.1.4.1.388.14.3.3.1.4.5.1.4
		wsCcStatsWlanRxOctetsAt6Mb OBJECT-TYPE
			SYNTAX Counter32
			MAX-ACCESS read-only
			STATUS deprecated
			DESCRIPTION
				"Number of octets received at 6 Mb."
			::= { wsCcStatsWlanRxOctetsEntry 4 }

		
		-- 1.3.6.1.4.1.388.14.3.3.1.4.5.1.5
		wsCcStatsWlanRxOctetsAt9Mb OBJECT-TYPE
			SYNTAX Counter32
			MAX-ACCESS read-only
			STATUS deprecated
			DESCRIPTION
				"Number of octets received at 9 Mb."
			::= { wsCcStatsWlanRxOctetsEntry 5 }

		
		-- 1.3.6.1.4.1.388.14.3.3.1.4.5.1.6
		wsCcStatsWlanRxOctetsAt11Mb OBJECT-TYPE
			SYNTAX Counter32
			MAX-ACCESS read-only
			STATUS deprecated
			DESCRIPTION
				"Number of octets received at 11 Mb."
			::= { wsCcStatsWlanRxOctetsEntry 6 }

		
		-- 1.3.6.1.4.1.388.14.3.3.1.4.5.1.7
		wsCcStatsWlanRxOctetsAt12Mb OBJECT-TYPE
			SYNTAX Counter32
			MAX-ACCESS read-only
			STATUS deprecated
			DESCRIPTION
				"Number of octets received at 12 Mb."
			::= { wsCcStatsWlanRxOctetsEntry 7 }

		
		-- 1.3.6.1.4.1.388.14.3.3.1.4.5.1.8
		wsCcStatsWlanRxOctetsAt18Mb OBJECT-TYPE
			SYNTAX Counter32
			MAX-ACCESS read-only
			STATUS deprecated
			DESCRIPTION
				"Number of octets received at 18 Mb."
			::= { wsCcStatsWlanRxOctetsEntry 8 }

		
		-- 1.3.6.1.4.1.388.14.3.3.1.4.5.1.9
		wsCcStatsWlanRxOctetsAt22Mb OBJECT-TYPE
			SYNTAX Counter32
			MAX-ACCESS read-only
			STATUS deprecated
			DESCRIPTION
				"Number of octets received at 22 Mb."
			::= { wsCcStatsWlanRxOctetsEntry 9 }

		
		-- 1.3.6.1.4.1.388.14.3.3.1.4.5.1.10
		wsCcStatsWlanRxOctetsAt24Mb OBJECT-TYPE
			SYNTAX Counter32
			MAX-ACCESS read-only
			STATUS deprecated
			DESCRIPTION
				"Number of octets received at 24 Mb."
			::= { wsCcStatsWlanRxOctetsEntry 10 }

		
		-- 1.3.6.1.4.1.388.14.3.3.1.4.5.1.11
		wsCcStatsWlanRxOctetsAt36Mb OBJECT-TYPE
			SYNTAX Counter32
			MAX-ACCESS read-only
			STATUS deprecated
			DESCRIPTION
				"Number of octets received at 36 Mb."
			::= { wsCcStatsWlanRxOctetsEntry 11 }

		
		-- 1.3.6.1.4.1.388.14.3.3.1.4.5.1.12
		wsCcStatsWlanRxOctetsAt48Mb OBJECT-TYPE
			SYNTAX Counter32
			MAX-ACCESS read-only
			STATUS deprecated
			DESCRIPTION
				"Number of octets received at 48 Mb."
			::= { wsCcStatsWlanRxOctetsEntry 12 }

		
		-- 1.3.6.1.4.1.388.14.3.3.1.4.5.1.13
		wsCcStatsWlanRxOctetsAt54Mb OBJECT-TYPE
			SYNTAX Counter32
			MAX-ACCESS read-only
			STATUS deprecated
			DESCRIPTION
				"Number of octets received at 54 Mb."
			::= { wsCcStatsWlanRxOctetsEntry 13 }

		
		-- 1.3.6.1.4.1.388.14.3.3.1.4.6
		wsCcStatsWlanTxOctetsTable OBJECT-TYPE
			SYNTAX SEQUENCE OF WsCcStatsWlanTxOctetsEntry
			MAX-ACCESS not-accessible
			STATUS deprecated
			DESCRIPTION
				"For each WLAN on this switch, this table 
				describes counts of octets transmitted at each 
				possible speed, (1Mb, 2Mb, 5.5Mb, 6Mb...)."
			::= { wsCcStatsWlan 6 }

		
		-- 1.3.6.1.4.1.388.14.3.3.1.4.6.1
		wsCcStatsWlanTxOctetsEntry OBJECT-TYPE
			SYNTAX WsCcStatsWlanTxOctetsEntry
			MAX-ACCESS not-accessible
			STATUS deprecated
			DESCRIPTION
				" "
			INDEX { wsCcStatsWlanIndex }
			::= { wsCcStatsWlanTxOctetsTable 1 }

		
		WsCcStatsWlanTxOctetsEntry ::=
			SEQUENCE { 
				wsCcStatsWlanTxOctetsAt1Mb
					Counter32,
				wsCcStatsWlanTxOctetsAt2Mb
					Counter32,
				wsCcStatsWlanTxOctetsAt5pt5Mb
					Counter32,
				wsCcStatsWlanTxOctetsAt6Mb
					Counter32,
				wsCcStatsWlanTxOctetsAt9Mb
					Counter32,
				wsCcStatsWlanTxOctetsAt11Mb
					Counter32,
				wsCcStatsWlanTxOctetsAt12Mb
					Counter32,
				wsCcStatsWlanTxOctetsAt18Mb
					Counter32,
				wsCcStatsWlanTxOctetsAt22Mb
					Counter32,
				wsCcStatsWlanTxOctetsAt24Mb
					Counter32,
				wsCcStatsWlanTxOctetsAt36Mb
					Counter32,
				wsCcStatsWlanTxOctetsAt48Mb
					Counter32,
				wsCcStatsWlanTxOctetsAt54Mb
					Counter32
			 }

		-- 1.3.6.1.4.1.388.14.3.3.1.4.6.1.1
		wsCcStatsWlanTxOctetsAt1Mb OBJECT-TYPE
			SYNTAX Counter32
			MAX-ACCESS read-only
			STATUS deprecated
			DESCRIPTION
				"Number of octets transmitted at 1 Mb."
			::= { wsCcStatsWlanTxOctetsEntry 1 }

		
		-- 1.3.6.1.4.1.388.14.3.3.1.4.6.1.2
		wsCcStatsWlanTxOctetsAt2Mb OBJECT-TYPE
			SYNTAX Counter32
			MAX-ACCESS read-only
			STATUS deprecated
			DESCRIPTION
				"Number of octets transmitted at 2 Mb."
			::= { wsCcStatsWlanTxOctetsEntry 2 }

		
		-- 1.3.6.1.4.1.388.14.3.3.1.4.6.1.3
		wsCcStatsWlanTxOctetsAt5pt5Mb OBJECT-TYPE
			SYNTAX Counter32
			MAX-ACCESS read-only
			STATUS deprecated
			DESCRIPTION
				"Number of octets transmitted at 5.5 Mb."
			::= { wsCcStatsWlanTxOctetsEntry 3 }

		
		-- 1.3.6.1.4.1.388.14.3.3.1.4.6.1.4
		wsCcStatsWlanTxOctetsAt6Mb OBJECT-TYPE
			SYNTAX Counter32
			MAX-ACCESS read-only
			STATUS deprecated
			DESCRIPTION
				"Number of octets transmitted at 6 Mb."
			::= { wsCcStatsWlanTxOctetsEntry 4 }

		
		-- 1.3.6.1.4.1.388.14.3.3.1.4.6.1.5
		wsCcStatsWlanTxOctetsAt9Mb OBJECT-TYPE
			SYNTAX Counter32
			MAX-ACCESS read-only
			STATUS deprecated
			DESCRIPTION
				"Number of octets transmitted at 9 Mb."
			::= { wsCcStatsWlanTxOctetsEntry 5 }

		
		-- 1.3.6.1.4.1.388.14.3.3.1.4.6.1.6
		wsCcStatsWlanTxOctetsAt11Mb OBJECT-TYPE
			SYNTAX Counter32
			MAX-ACCESS read-only
			STATUS deprecated
			DESCRIPTION
				"Number of octets transmitted at 11 Mb."
			::= { wsCcStatsWlanTxOctetsEntry 6 }

		
		-- 1.3.6.1.4.1.388.14.3.3.1.4.6.1.7
		wsCcStatsWlanTxOctetsAt12Mb OBJECT-TYPE
			SYNTAX Counter32
			MAX-ACCESS read-only
			STATUS deprecated
			DESCRIPTION
				"Number of octets transmitted at 12 Mb."
			::= { wsCcStatsWlanTxOctetsEntry 7 }

		
		-- 1.3.6.1.4.1.388.14.3.3.1.4.6.1.8
		wsCcStatsWlanTxOctetsAt18Mb OBJECT-TYPE
			SYNTAX Counter32
			MAX-ACCESS read-only
			STATUS deprecated
			DESCRIPTION
				"Number of octets transmitted at 18 Mb."
			::= { wsCcStatsWlanTxOctetsEntry 8 }

		
		-- 1.3.6.1.4.1.388.14.3.3.1.4.6.1.9
		wsCcStatsWlanTxOctetsAt22Mb OBJECT-TYPE
			SYNTAX Counter32
			MAX-ACCESS read-only
			STATUS deprecated
			DESCRIPTION
				"Number of octets transmitted at 22 Mb."
			::= { wsCcStatsWlanTxOctetsEntry 9 }

		
		-- 1.3.6.1.4.1.388.14.3.3.1.4.6.1.10
		wsCcStatsWlanTxOctetsAt24Mb OBJECT-TYPE
			SYNTAX Counter32
			MAX-ACCESS read-only
			STATUS deprecated
			DESCRIPTION
				"Number of octets transmitted at 24 Mb."
			::= { wsCcStatsWlanTxOctetsEntry 10 }

		
		-- 1.3.6.1.4.1.388.14.3.3.1.4.6.1.11
		wsCcStatsWlanTxOctetsAt36Mb OBJECT-TYPE
			SYNTAX Counter32
			MAX-ACCESS read-only
			STATUS deprecated
			DESCRIPTION
				"Number of octets transmitted at 36 Mb."
			::= { wsCcStatsWlanTxOctetsEntry 11 }

		
		-- 1.3.6.1.4.1.388.14.3.3.1.4.6.1.12
		wsCcStatsWlanTxOctetsAt48Mb OBJECT-TYPE
			SYNTAX Counter32
			MAX-ACCESS read-only
			STATUS deprecated
			DESCRIPTION
				"Number of octets transmitted at 48 Mb."
			::= { wsCcStatsWlanTxOctetsEntry 12 }

		
		-- 1.3.6.1.4.1.388.14.3.3.1.4.6.1.13
		wsCcStatsWlanTxOctetsAt54Mb OBJECT-TYPE
			SYNTAX Counter32
			MAX-ACCESS read-only
			STATUS deprecated
			DESCRIPTION
				"Number of octets transmitted at 54 Mb."
			::= { wsCcStatsWlanTxOctetsEntry 13 }

		
		-- 1.3.6.1.4.1.388.14.3.3.1.4.7
		wsCcStatsWlanTxRetriesPktsTable OBJECT-TYPE
			SYNTAX SEQUENCE OF WsCcStatsWlanTxRetriesPktsEntry
			MAX-ACCESS not-accessible
			STATUS deprecated
			DESCRIPTION
				"For each WLAN on the switch, this table describes 
				counts of the number of packets affected by transmit 
				retries, (no retries, 1 retry, 2 retries,... gave-up)."
			::= { wsCcStatsWlan 7 }

		
		-- 1.3.6.1.4.1.388.14.3.3.1.4.7.1
		wsCcStatsWlanTxRetriesPktsEntry OBJECT-TYPE
			SYNTAX WsCcStatsWlanTxRetriesPktsEntry
			MAX-ACCESS not-accessible
			STATUS deprecated
			DESCRIPTION
				" "
			INDEX { wsCcStatsWlanIndex }
			::= { wsCcStatsWlanTxRetriesPktsTable 1 }

		
		WsCcStatsWlanTxRetriesPktsEntry ::=
			SEQUENCE { 
				wsCcStatsWlanTxRetriesPktsNone
					Counter32,
				wsCcStatsWlanTxRetriesPkts01
					Counter32,
				wsCcStatsWlanTxRetriesPkts02
					Counter32,
				wsCcStatsWlanTxRetriesPkts03
					Counter32,
				wsCcStatsWlanTxRetriesPkts04
					Counter32,
				wsCcStatsWlanTxRetriesPkts05
					Counter32,
				wsCcStatsWlanTxRetriesPkts06
					Counter32,
				wsCcStatsWlanTxRetriesPkts07
					Counter32,
				wsCcStatsWlanTxRetriesPkts08
					Counter32,
				wsCcStatsWlanTxRetriesPkts09
					Counter32,
				wsCcStatsWlanTxRetriesPkts10
					Counter32,
				wsCcStatsWlanTxRetriesPkts11
					Counter32,
				wsCcStatsWlanTxRetriesPkts12
					Counter32,
				wsCcStatsWlanTxRetriesPkts13
					Counter32,
				wsCcStatsWlanTxRetriesPkts14
					Counter32,
				wsCcStatsWlanTxRetriesPkts15
					Counter32,
				wsCcStatsWlanTxRetriesPktsFailed
					Counter32
			 }

		-- 1.3.6.1.4.1.388.14.3.3.1.4.7.1.1
		wsCcStatsWlanTxRetriesPktsNone OBJECT-TYPE
			SYNTAX Counter32
			MAX-ACCESS read-only
			STATUS deprecated
			DESCRIPTION
				"Number of pkts successfully transmitted with no retries."
			::= { wsCcStatsWlanTxRetriesPktsEntry 1 }

		
		-- 1.3.6.1.4.1.388.14.3.3.1.4.7.1.2
		wsCcStatsWlanTxRetriesPkts01 OBJECT-TYPE
			SYNTAX Counter32
			MAX-ACCESS read-only
			STATUS deprecated
			DESCRIPTION
				"Number of pkts successfully transmitted with exactly 1 retries."
			::= { wsCcStatsWlanTxRetriesPktsEntry 2 }

		
		-- 1.3.6.1.4.1.388.14.3.3.1.4.7.1.3
		wsCcStatsWlanTxRetriesPkts02 OBJECT-TYPE
			SYNTAX Counter32
			MAX-ACCESS read-only
			STATUS deprecated
			DESCRIPTION
				"Number of pkts successfully transmitted with exactly 2 retries."
			::= { wsCcStatsWlanTxRetriesPktsEntry 3 }

		
		-- 1.3.6.1.4.1.388.14.3.3.1.4.7.1.4
		wsCcStatsWlanTxRetriesPkts03 OBJECT-TYPE
			SYNTAX Counter32
			MAX-ACCESS read-only
			STATUS deprecated
			DESCRIPTION
				"Number of pkts successfully transmitted with exactly 3 retries."
			::= { wsCcStatsWlanTxRetriesPktsEntry 4 }

		
		-- 1.3.6.1.4.1.388.14.3.3.1.4.7.1.5
		wsCcStatsWlanTxRetriesPkts04 OBJECT-TYPE
			SYNTAX Counter32
			MAX-ACCESS read-only
			STATUS deprecated
			DESCRIPTION
				"Number of pkts successfully transmitted with exactly 4 retries."
			::= { wsCcStatsWlanTxRetriesPktsEntry 5 }

		
		-- 1.3.6.1.4.1.388.14.3.3.1.4.7.1.6
		wsCcStatsWlanTxRetriesPkts05 OBJECT-TYPE
			SYNTAX Counter32
			MAX-ACCESS read-only
			STATUS deprecated
			DESCRIPTION
				"Number of pkts successfully transmitted with exactly 5 retries."
			::= { wsCcStatsWlanTxRetriesPktsEntry 6 }

		
		-- 1.3.6.1.4.1.388.14.3.3.1.4.7.1.7
		wsCcStatsWlanTxRetriesPkts06 OBJECT-TYPE
			SYNTAX Counter32
			MAX-ACCESS read-only
			STATUS deprecated
			DESCRIPTION
				"Number of pkts successfully transmitted with exactly 6 retries."
			::= { wsCcStatsWlanTxRetriesPktsEntry 7 }

		
		-- 1.3.6.1.4.1.388.14.3.3.1.4.7.1.8
		wsCcStatsWlanTxRetriesPkts07 OBJECT-TYPE
			SYNTAX Counter32
			MAX-ACCESS read-only
			STATUS deprecated
			DESCRIPTION
				"Number of pkts successfully transmitted with exactly 7 retries."
			::= { wsCcStatsWlanTxRetriesPktsEntry 8 }

		
		-- 1.3.6.1.4.1.388.14.3.3.1.4.7.1.9
		wsCcStatsWlanTxRetriesPkts08 OBJECT-TYPE
			SYNTAX Counter32
			MAX-ACCESS read-only
			STATUS deprecated
			DESCRIPTION
				"Number of pkts successfully transmitted with exactly 8 retries."
			::= { wsCcStatsWlanTxRetriesPktsEntry 9 }

		
		-- 1.3.6.1.4.1.388.14.3.3.1.4.7.1.10
		wsCcStatsWlanTxRetriesPkts09 OBJECT-TYPE
			SYNTAX Counter32
			MAX-ACCESS read-only
			STATUS deprecated
			DESCRIPTION
				"Number of pkts successfully transmitted with exactly 9 retries."
			::= { wsCcStatsWlanTxRetriesPktsEntry 10 }

		
		-- 1.3.6.1.4.1.388.14.3.3.1.4.7.1.11
		wsCcStatsWlanTxRetriesPkts10 OBJECT-TYPE
			SYNTAX Counter32
			MAX-ACCESS read-only
			STATUS deprecated
			DESCRIPTION
				"Number of pkts successfully transmitted with exactly 10 retries."
			::= { wsCcStatsWlanTxRetriesPktsEntry 11 }

		
		-- 1.3.6.1.4.1.388.14.3.3.1.4.7.1.12
		wsCcStatsWlanTxRetriesPkts11 OBJECT-TYPE
			SYNTAX Counter32
			MAX-ACCESS read-only
			STATUS deprecated
			DESCRIPTION
				"Number of pkts successfully transmitted with exactly 11 retries."
			::= { wsCcStatsWlanTxRetriesPktsEntry 12 }

		
		-- 1.3.6.1.4.1.388.14.3.3.1.4.7.1.13
		wsCcStatsWlanTxRetriesPkts12 OBJECT-TYPE
			SYNTAX Counter32
			MAX-ACCESS read-only
			STATUS deprecated
			DESCRIPTION
				"Number of pkts successfully transmitted with exactly 12 retries."
			::= { wsCcStatsWlanTxRetriesPktsEntry 13 }

		
		-- 1.3.6.1.4.1.388.14.3.3.1.4.7.1.14
		wsCcStatsWlanTxRetriesPkts13 OBJECT-TYPE
			SYNTAX Counter32
			MAX-ACCESS read-only
			STATUS deprecated
			DESCRIPTION
				"Number of pkts successfully transmitted with exactly 13 retries."
			::= { wsCcStatsWlanTxRetriesPktsEntry 14 }

		
		-- 1.3.6.1.4.1.388.14.3.3.1.4.7.1.15
		wsCcStatsWlanTxRetriesPkts14 OBJECT-TYPE
			SYNTAX Counter32
			MAX-ACCESS read-only
			STATUS deprecated
			DESCRIPTION
				"Number of pkts successfully transmitted with exactly 14 retries."
			::= { wsCcStatsWlanTxRetriesPktsEntry 15 }

		
		-- 1.3.6.1.4.1.388.14.3.3.1.4.7.1.16
		wsCcStatsWlanTxRetriesPkts15 OBJECT-TYPE
			SYNTAX Counter32
			MAX-ACCESS read-only
			STATUS deprecated
			DESCRIPTION
				"Number of pkts successfully transmitted with exactly 15 retries."
			::= { wsCcStatsWlanTxRetriesPktsEntry 16 }

		
		-- 1.3.6.1.4.1.388.14.3.3.1.4.7.1.17
		wsCcStatsWlanTxRetriesPktsFailed OBJECT-TYPE
			SYNTAX Counter32
			MAX-ACCESS read-only
			STATUS deprecated
			DESCRIPTION
				"Number of pkts that never were successfully 
				transmitted to because the max retry count was exceeded."
			::= { wsCcStatsWlanTxRetriesPktsEntry 17 }

		
		-- 1.3.6.1.4.1.388.14.3.3.1.4.8
		wsCcStatsWlanTxRetriesOctetsTable OBJECT-TYPE
			SYNTAX SEQUENCE OF WsCcStatsWlanTxRetriesOctetsEntry
			MAX-ACCESS not-accessible
			STATUS deprecated
			DESCRIPTION
				"For each WLAN on the switch, this table describes 
				counts of the number of octets affected by transmit 
				retries, (no retries, 1 retry, 2 retries,... gave-up)."
			::= { wsCcStatsWlan 8 }

		
		-- 1.3.6.1.4.1.388.14.3.3.1.4.8.1
		wsCcStatsWlanTxRetriesOctetsEntry OBJECT-TYPE
			SYNTAX WsCcStatsWlanTxRetriesOctetsEntry
			MAX-ACCESS not-accessible
			STATUS deprecated
			DESCRIPTION
				" "
			INDEX { wsCcStatsWlanIndex }
			::= { wsCcStatsWlanTxRetriesOctetsTable 1 }

		
		WsCcStatsWlanTxRetriesOctetsEntry ::=
			SEQUENCE { 
				wsCcStatsWlanTxRetriesOctetsNone
					Counter32,
				wsCcStatsWlanTxRetriesOctets01
					Counter32,
				wsCcStatsWlanTxRetriesOctets02
					Counter32,
				wsCcStatsWlanTxRetriesOctets03
					Counter32,
				wsCcStatsWlanTxRetriesOctets04
					Counter32,
				wsCcStatsWlanTxRetriesOctets05
					Counter32,
				wsCcStatsWlanTxRetriesOctets06
					Counter32,
				wsCcStatsWlanTxRetriesOctets07
					Counter32,
				wsCcStatsWlanTxRetriesOctets08
					Counter32,
				wsCcStatsWlanTxRetriesOctets09
					Counter32,
				wsCcStatsWlanTxRetriesOctets10
					Counter32,
				wsCcStatsWlanTxRetriesOctets11
					Counter32,
				wsCcStatsWlanTxRetriesOctets12
					Counter32,
				wsCcStatsWlanTxRetriesOctets13
					Counter32,
				wsCcStatsWlanTxRetriesOctets14
					Counter32,
				wsCcStatsWlanTxRetriesOctets15
					Counter32,
				wsCcStatsWlanTxRetriesOctetsFailed
					Counter32
			 }

		-- 1.3.6.1.4.1.388.14.3.3.1.4.8.1.1
		wsCcStatsWlanTxRetriesOctetsNone OBJECT-TYPE
			SYNTAX Counter32
			MAX-ACCESS read-only
			STATUS deprecated
			DESCRIPTION
				"Number of octets successfully transmitted with no retries."
			::= { wsCcStatsWlanTxRetriesOctetsEntry 1 }

		
		-- 1.3.6.1.4.1.388.14.3.3.1.4.8.1.2
		wsCcStatsWlanTxRetriesOctets01 OBJECT-TYPE
			SYNTAX Counter32
			MAX-ACCESS read-only
			STATUS deprecated
			DESCRIPTION
				"Number of octets successfully transmitted with exactly 1 retries."
			::= { wsCcStatsWlanTxRetriesOctetsEntry 2 }

		
		-- 1.3.6.1.4.1.388.14.3.3.1.4.8.1.3
		wsCcStatsWlanTxRetriesOctets02 OBJECT-TYPE
			SYNTAX Counter32
			MAX-ACCESS read-only
			STATUS deprecated
			DESCRIPTION
				"Number of octets successfully transmitted with exactly 2 retries."
			::= { wsCcStatsWlanTxRetriesOctetsEntry 3 }

		
		-- 1.3.6.1.4.1.388.14.3.3.1.4.8.1.4
		wsCcStatsWlanTxRetriesOctets03 OBJECT-TYPE
			SYNTAX Counter32
			MAX-ACCESS read-only
			STATUS deprecated
			DESCRIPTION
				"Number of octets successfully transmitted with exactly 3 retries."
			::= { wsCcStatsWlanTxRetriesOctetsEntry 4 }

		
		-- 1.3.6.1.4.1.388.14.3.3.1.4.8.1.5
		wsCcStatsWlanTxRetriesOctets04 OBJECT-TYPE
			SYNTAX Counter32
			MAX-ACCESS read-only
			STATUS deprecated
			DESCRIPTION
				"Number of octets successfully transmitted with exactly 4 retries."
			::= { wsCcStatsWlanTxRetriesOctetsEntry 5 }

		
		-- 1.3.6.1.4.1.388.14.3.3.1.4.8.1.6
		wsCcStatsWlanTxRetriesOctets05 OBJECT-TYPE
			SYNTAX Counter32
			MAX-ACCESS read-only
			STATUS deprecated
			DESCRIPTION
				"Number of octets successfully transmitted with exactly 5 retries."
			::= { wsCcStatsWlanTxRetriesOctetsEntry 6 }

		
		-- 1.3.6.1.4.1.388.14.3.3.1.4.8.1.7
		wsCcStatsWlanTxRetriesOctets06 OBJECT-TYPE
			SYNTAX Counter32
			MAX-ACCESS read-only
			STATUS deprecated
			DESCRIPTION
				"Number of octets successfully transmitted with exactly 6 retries."
			::= { wsCcStatsWlanTxRetriesOctetsEntry 7 }

		
		-- 1.3.6.1.4.1.388.14.3.3.1.4.8.1.8
		wsCcStatsWlanTxRetriesOctets07 OBJECT-TYPE
			SYNTAX Counter32
			MAX-ACCESS read-only
			STATUS deprecated
			DESCRIPTION
				"Number of octets successfully transmitted with exactly 7 retries."
			::= { wsCcStatsWlanTxRetriesOctetsEntry 8 }

		
		-- 1.3.6.1.4.1.388.14.3.3.1.4.8.1.9
		wsCcStatsWlanTxRetriesOctets08 OBJECT-TYPE
			SYNTAX Counter32
			MAX-ACCESS read-only
			STATUS deprecated
			DESCRIPTION
				"Number of octets successfully transmitted with exactly 8 retries."
			::= { wsCcStatsWlanTxRetriesOctetsEntry 9 }

		
		-- 1.3.6.1.4.1.388.14.3.3.1.4.8.1.10
		wsCcStatsWlanTxRetriesOctets09 OBJECT-TYPE
			SYNTAX Counter32
			MAX-ACCESS read-only
			STATUS deprecated
			DESCRIPTION
				"Number of octets successfully transmitted with exactly 9 retries."
			::= { wsCcStatsWlanTxRetriesOctetsEntry 10 }

		
		-- 1.3.6.1.4.1.388.14.3.3.1.4.8.1.11
		wsCcStatsWlanTxRetriesOctets10 OBJECT-TYPE
			SYNTAX Counter32
			MAX-ACCESS read-only
			STATUS deprecated
			DESCRIPTION
				"Number of octets successfully transmitted with exactly 10 retries."
			::= { wsCcStatsWlanTxRetriesOctetsEntry 11 }

		
		-- 1.3.6.1.4.1.388.14.3.3.1.4.8.1.13
		wsCcStatsWlanTxRetriesOctets11 OBJECT-TYPE
			SYNTAX Counter32
			MAX-ACCESS read-only
			STATUS deprecated
			DESCRIPTION
				"Number of octets successfully transmitted with exactly 11 retries."
			::= { wsCcStatsWlanTxRetriesOctetsEntry 13 }

		
		-- 1.3.6.1.4.1.388.14.3.3.1.4.8.1.14
		wsCcStatsWlanTxRetriesOctets12 OBJECT-TYPE
			SYNTAX Counter32
			MAX-ACCESS read-only
			STATUS deprecated
			DESCRIPTION
				"Number of octets successfully transmitted with exactly 12 retries."
			::= { wsCcStatsWlanTxRetriesOctetsEntry 14 }

		
		-- 1.3.6.1.4.1.388.14.3.3.1.4.8.1.15
		wsCcStatsWlanTxRetriesOctets13 OBJECT-TYPE
			SYNTAX Counter32
			MAX-ACCESS read-only
			STATUS deprecated
			DESCRIPTION
				"Number of octets successfully transmitted with exactly 13 retries."
			::= { wsCcStatsWlanTxRetriesOctetsEntry 15 }

		
		-- 1.3.6.1.4.1.388.14.3.3.1.4.8.1.16
		wsCcStatsWlanTxRetriesOctets14 OBJECT-TYPE
			SYNTAX Counter32
			MAX-ACCESS read-only
			STATUS deprecated
			DESCRIPTION
				"Number of octets successfully transmitted with exactly 14 retries."
			::= { wsCcStatsWlanTxRetriesOctetsEntry 16 }

		
		-- 1.3.6.1.4.1.388.14.3.3.1.4.8.1.17
		wsCcStatsWlanTxRetriesOctets15 OBJECT-TYPE
			SYNTAX Counter32
			MAX-ACCESS read-only
			STATUS deprecated
			DESCRIPTION
				"Number of octets successfully transmitted with exactly 15 retries."
			::= { wsCcStatsWlanTxRetriesOctetsEntry 17 }

		
		-- 1.3.6.1.4.1.388.14.3.3.1.4.8.1.18
		wsCcStatsWlanTxRetriesOctetsFailed OBJECT-TYPE
			SYNTAX Counter32
			MAX-ACCESS read-only
			STATUS deprecated
			DESCRIPTION
				"Number of octets that never were successfully 
				transmitted to because the max retry count was exceeded."
			::= { wsCcStatsWlanTxRetriesOctetsEntry 18 }

		
		-- 1.3.6.1.4.1.388.14.3.3.1.4.9
		wsCcStatsWlanSigTable OBJECT-TYPE
			SYNTAX SEQUENCE OF WsCcStatsWlanSigEntry
			MAX-ACCESS not-accessible
			STATUS deprecated
			DESCRIPTION
				"This table describes statistics about RSSI, Signal, Noise,
				and SNR for packets recieved via each WLAN on the switch."
			::= { wsCcStatsWlan 9 }

		
		-- 1.3.6.1.4.1.388.14.3.3.1.4.9.1
		wsCcStatsWlanSigEntry OBJECT-TYPE
			SYNTAX WsCcStatsWlanSigEntry
			MAX-ACCESS not-accessible
			STATUS deprecated
			DESCRIPTION
				" "
			INDEX { wsCcStatsWlanIndex }
			::= { wsCcStatsWlanSigTable 1 }

		
		WsCcStatsWlanSigEntry ::=
			SEQUENCE { 
				wsCcStatsWlanSigStatsNumPkts
					Counter32,
				wsCcStatsWlanSigStatsSignalBest
					Integer32,
				wsCcStatsWlanSigStatsSignalWorst
					Integer32,
				wsCcStatsWlanSigStatsSignalSum
					Integer32,
				wsCcStatsWlanSigStatsSignalSumSquares
					Counter64,
				wsCcStatsWlanSigStatsNoiseBest
					Integer32,
				wsCcStatsWlanSigStatsNoiseWorst
					Integer32,
				wsCcStatsWlanSigNoiseSum
					Integer32,
				wsCcStatsWlanSigNoiseSumSquares
					Counter64,
				wsCcStatsWlanSigSnrBest
					Integer32,
				wsCcStatsWlanSigSnrWorst
					Integer32,
				wsCcStatsWlanSigSnrSum
					Integer32,
				wsCcStatsWlanSigSnrSumSquares
					Counter64
			 }

		-- 1.3.6.1.4.1.388.14.3.3.1.4.9.1.1
		wsCcStatsWlanSigStatsNumPkts OBJECT-TYPE
			SYNTAX Counter32
			MAX-ACCESS read-only
			STATUS deprecated
			DESCRIPTION
				"Total packets received included in
				all the other counters reported in this row."
			::= { wsCcStatsWlanSigEntry 1 }

		
		-- 1.3.6.1.4.1.388.14.3.3.1.4.9.1.2
		wsCcStatsWlanSigStatsSignalBest OBJECT-TYPE
			SYNTAX Integer32
			UNITS "dBm"
			MAX-ACCESS read-only
			STATUS deprecated
			DESCRIPTION
				"The best Signal value seen so far.
				(Remember that a -20dBm Signal is better than -60dBm).
				
				This value is initialized to -500dBm."
			::= { wsCcStatsWlanSigEntry 2 }

		
		-- 1.3.6.1.4.1.388.14.3.3.1.4.9.1.3
		wsCcStatsWlanSigStatsSignalWorst OBJECT-TYPE
			SYNTAX Integer32
			UNITS "dBm"
			MAX-ACCESS read-only
			STATUS deprecated
			DESCRIPTION
				"The worst Signal value seen so far.
				(Remember that a -80dBm Signal is worse than -60dBm).
				
				This value is initialized to 500dBm."
			::= { wsCcStatsWlanSigEntry 3 }

		
		-- 1.3.6.1.4.1.388.14.3.3.1.4.9.1.4
		wsCcStatsWlanSigStatsSignalSum OBJECT-TYPE
			SYNTAX Integer32
			UNITS "dBm"
			MAX-ACCESS read-only
			STATUS deprecated
			DESCRIPTION
				"A running sum of all Signal values calculated by the
				switch (using reported RSSI values), for packets received.
				
				Note that this value is normally a negative value
				ranging from -10dBm to -80dBm.  It is possible for this
				value to be positive, but that would be rare, and would
				signal an exceptionally strong signal."
			::= { wsCcStatsWlanSigEntry 4 }

		
		-- 1.3.6.1.4.1.388.14.3.3.1.4.9.1.5
		wsCcStatsWlanSigStatsSignalSumSquares OBJECT-TYPE
			SYNTAX Counter64
			UNITS "dBm"
			MAX-ACCESS read-only
			STATUS deprecated
			DESCRIPTION
				"A sum of the squares of each Signal value calculated
				for packets received.
				
				Unlike _SignalSum, this value is never negative, since
				the square of a negative number is a positive."
			::= { wsCcStatsWlanSigEntry 5 }

		
		-- 1.3.6.1.4.1.388.14.3.3.1.4.9.1.6
		wsCcStatsWlanSigStatsNoiseBest OBJECT-TYPE
			SYNTAX Integer32
			UNITS "dBm"
			MAX-ACCESS read-only
			STATUS deprecated
			DESCRIPTION
				"The best Noise value seen so far.
				(Remember that -80dBm Noise is better than -70dBm).
				
				This value is initialized to 500dBm."
			::= { wsCcStatsWlanSigEntry 6 }

		
		-- 1.3.6.1.4.1.388.14.3.3.1.4.9.1.7
		wsCcStatsWlanSigStatsNoiseWorst OBJECT-TYPE
			SYNTAX Integer32
			UNITS "dBm"
			MAX-ACCESS read-only
			STATUS deprecated
			DESCRIPTION
				"The worst Noise value seen so far.
				(Remember that -50dBm Noise is worse than -60dBm).
				
				This value is initialized to -500dBm."
			::= { wsCcStatsWlanSigEntry 7 }

		
		-- 1.3.6.1.4.1.388.14.3.3.1.4.9.1.8
		wsCcStatsWlanSigNoiseSum OBJECT-TYPE
			SYNTAX Integer32
			UNITS "dBm"
			MAX-ACCESS read-only
			STATUS deprecated
			DESCRIPTION
				"A running sum of all Noise values calculated by the
				switch (using reported RSSI values), for packets.
				
				Like _SignalSum, this value is normally a negative value."
			::= { wsCcStatsWlanSigEntry 8 }

		
		-- 1.3.6.1.4.1.388.14.3.3.1.4.9.1.9
		wsCcStatsWlanSigNoiseSumSquares OBJECT-TYPE
			SYNTAX Counter64
			UNITS "dBm"
			MAX-ACCESS read-only
			STATUS deprecated
			DESCRIPTION
				"A sum of the squares of each Noise value calculated
				for packets received.
				
				As with _SignalSumSquares, this value is never negative."
			::= { wsCcStatsWlanSigEntry 9 }

		
		-- 1.3.6.1.4.1.388.14.3.3.1.4.9.1.10
		wsCcStatsWlanSigSnrBest OBJECT-TYPE
			SYNTAX Integer32
			UNITS "dB"
			MAX-ACCESS read-only
			STATUS deprecated
			DESCRIPTION
				"The best SNR value seen so far.
				(Remember that +30dBm SNR is better than +20dBm).
				
				This value is initialized to -500dB."
			::= { wsCcStatsWlanSigEntry 10 }

		
		-- 1.3.6.1.4.1.388.14.3.3.1.4.9.1.11
		wsCcStatsWlanSigSnrWorst OBJECT-TYPE
			SYNTAX Integer32
			UNITS "dB"
			MAX-ACCESS read-only
			STATUS deprecated
			DESCRIPTION
				"The worst SNR value seen so far.
				(Remember that +10dBm SNR is worse than +20dBm).
				
				This value is initialized to 500dB."
			::= { wsCcStatsWlanSigEntry 11 }

		
		-- 1.3.6.1.4.1.388.14.3.3.1.4.9.1.12
		wsCcStatsWlanSigSnrSum OBJECT-TYPE
			SYNTAX Integer32
			UNITS "dB"
			MAX-ACCESS read-only
			STATUS deprecated
			DESCRIPTION
				"A running sum of all SNR values calculated by the
				switch (using reported RSSI values), for packets received.
				
				Unlike _Signal and _Noise, this value is never negative."
			::= { wsCcStatsWlanSigEntry 12 }

		
		-- 1.3.6.1.4.1.388.14.3.3.1.4.9.1.13
		wsCcStatsWlanSigSnrSumSquares OBJECT-TYPE
			SYNTAX Counter64
			UNITS "dB"
			MAX-ACCESS read-only
			STATUS deprecated
			DESCRIPTION
				"A sum of the squares of each SNR value calculated
				for packets received.
				
				This value is never negative."
			::= { wsCcStatsWlanSigEntry 13 }

		
-- The switch roll-up values are reported at entry/instance
-- 1001, as with the other ccWlanRfSum tables.  Note, however,
-- that the switch reports very few of the values that WLANs
-- report, and will return NO-SUCH for those values on GET,
-- and will 'skip-over' those columns for GET-NEXT.
		-- 1.3.6.1.4.1.388.14.3.3.1.4.10
		wsCcStatsWlanSumShortTable OBJECT-TYPE
			SYNTAX SEQUENCE OF WsCcStatsWlanSumShortEntry
			MAX-ACCESS not-accessible
			STATUS current
			DESCRIPTION
				"Averages and rates calculated over the SHORT window for
				each WLAN."
			::= { wsCcStatsWlan 10 }

		
		-- 1.3.6.1.4.1.388.14.3.3.1.4.10.1
		wsCcStatsWlanSumShortEntry OBJECT-TYPE
			SYNTAX WsCcStatsWlanSumShortEntry
			MAX-ACCESS not-accessible
			STATUS current
			DESCRIPTION
				" "
			INDEX { wsCcStatsWlanIndex }
			::= { wsCcStatsWlanSumShortTable 1 }

		
		WsCcStatsWlanSumShortEntry ::=
			SEQUENCE { 
				wsCcStatsWlanSumShortTimestamp
					TimeTicks,
				wsCcStatsWlanSumShortNumPkts
					Unsigned32,
				wsCcStatsWlanSumShortPktsPerSec100
					ScaleBy100,
				wsCcStatsWlanSumShortPktsPerSecTx100
					ScaleBy100,
				wsCcStatsWlanSumShortPktsPerSecRx100
					ScaleBy100,
				wsCcStatsWlanSumShortThroughput
					Unsigned32,
				wsCcStatsWlanSumShortThroughputTx
					Unsigned32,
				wsCcStatsWlanSumShortThroughputRx
					Unsigned32,
				wsCcStatsWlanSumShortAvgBitSpeed
					Unsigned32,
				wsCcStatsWlanSumShortAvgMuSignal
					Integer32,
				wsCcStatsWlanSumShortAvgMuNoise
					Integer32,
				wsCcStatsWlanSumShortAvgMuSnr
					Integer32,
				wsCcStatsWlanSumShortPp10kNUcastPkts
					PartsPer10k,
				wsCcStatsWlanSumShortPp10kTxWithRetries
					PartsPer10k,
				wsCcStatsWlanSumShortPp10kDropped
					PartsPer10k,
				wsCcStatsWlanSumShortTxAvgRetries100
					ScaleBy100,
				wsCcStatsWlanSumShortPp10kRxUndecrypt
					PartsPer10k,
				wsCcStatsWlanSumShortTotalMus
					Unsigned32
			 }

		-- 1.3.6.1.4.1.388.14.3.3.1.4.10.1.1
		wsCcStatsWlanSumShortTimestamp OBJECT-TYPE
			SYNTAX TimeTicks
			MAX-ACCESS read-only
			STATUS current
			DESCRIPTION
				"Snapshot of sysUpTime as of the END of the 'window' of 
				time that this entry of values represents."
			::= { wsCcStatsWlanSumShortEntry 1 }

		
		-- 1.3.6.1.4.1.388.14.3.3.1.4.10.1.2
		wsCcStatsWlanSumShortNumPkts OBJECT-TYPE
			SYNTAX Unsigned32
			UNITS "packets"
			MAX-ACCESS read-only
			STATUS current
			DESCRIPTION
				"The number of packets used to calculate the statistics in
				this window."
			::= { wsCcStatsWlanSumShortEntry 2 }

		
		-- 1.3.6.1.4.1.388.14.3.3.1.4.10.1.3
		wsCcStatsWlanSumShortPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100."
			::= { wsCcStatsWlanSumShortEntry 3 }

		
		-- 1.3.6.1.4.1.388.14.3.3.1.4.10.1.4
		wsCcStatsWlanSumShortPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100."
			::= { wsCcStatsWlanSumShortEntry 4 }

		
		-- 1.3.6.1.4.1.388.14.3.3.1.4.10.1.5
		wsCcStatsWlanSumShortPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100."
			::= { wsCcStatsWlanSumShortEntry 5 }

		
		-- 1.3.6.1.4.1.388.14.3.3.1.4.10.1.6
		wsCcStatsWlanSumShortThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries)."
			::= { wsCcStatsWlanSumShortEntry 6 }

		
		-- 1.3.6.1.4.1.388.14.3.3.1.4.10.1.7
		wsCcStatsWlanSumShortThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries)."
			::= { wsCcStatsWlanSumShortEntry 7 }

		
		-- 1.3.6.1.4.1.388.14.3.3.1.4.10.1.8
		wsCcStatsWlanSumShortThroughputRx OBJECT-TYPE
			SYNTAX Unsigned32
			UNITS "bits per second"
			MAX-ACCESS read-only
			STATUS current
			DESCRIPTION
				"Actual number of bits RX over the window,
				divided by the number of seconds in the window."
			::= { wsCcStatsWlanSumShortEntry 8 }

		
		-- 1.3.6.1.4.1.388.14.3.3.1.4.10.1.9
		wsCcStatsWlanSumShortAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { wsCcStatsWlanSumShortEntry 9 }

		
		-- 1.3.6.1.4.1.388.14.3.3.1.4.10.1.10
		wsCcStatsWlanSumShortAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values.  PO"
			::= { wsCcStatsWlanSumShortEntry 10 }

		
		-- 1.3.6.1.4.1.388.14.3.3.1.4.10.1.11
		wsCcStatsWlanSumShortAvgMuNoise OBJECT-TYPE
			SYNTAX Integer32
			UNITS "dBm"
			MAX-ACCESS read-only
			STATUS current
			DESCRIPTION
				"The average of all noise values over the window."
			::= { wsCcStatsWlanSumShortEntry 11 }

		
		-- 1.3.6.1.4.1.388.14.3.3.1.4.10.1.12
		wsCcStatsWlanSumShortAvgMuSnr OBJECT-TYPE
			SYNTAX Integer32
			UNITS "dB"
			MAX-ACCESS read-only
			STATUS current
			DESCRIPTION
				"The average of all SNR values over the window."
			::= { wsCcStatsWlanSumShortEntry 12 }

		
		-- 1.3.6.1.4.1.388.14.3.3.1.4.10.1.13
		wsCcStatsWlanSumShortPp10kNUcastPkts OBJECT-TYPE
			SYNTAX PartsPer10k
			UNITS "parts-per-10000"
			MAX-ACCESS read-only
			STATUS current
			DESCRIPTION
				"Ratio of packets that were NOT unicast.
				
				Expressed as parts-per-10000."
			::= { wsCcStatsWlanSumShortEntry 13 }

		
		-- 1.3.6.1.4.1.388.14.3.3.1.4.10.1.14
		wsCcStatsWlanSumShortPp10kTxWithRetries OBJECT-TYPE
			SYNTAX PartsPer10k
			UNITS "parts-per-10000"
			MAX-ACCESS read-only
			STATUS current
			DESCRIPTION
				"Ratio of TX packets that experienced one or more retries.
				
				Expressed as parts-per-10000."
			::= { wsCcStatsWlanSumShortEntry 14 }

		
		-- 1.3.6.1.4.1.388.14.3.3.1.4.10.1.15
		wsCcStatsWlanSumShortPp10kDropped OBJECT-TYPE
			SYNTAX PartsPer10k
			UNITS "parts-per-10000"
			MAX-ACCESS read-only
			STATUS current
			DESCRIPTION
				"Packets dropped divided by packets sent.  Dropped here 
				means dropped intentionally due to the appropriate QoS 
				queue being full.  Other reasons for dropped packets are 
				not counted in this ratio."
			::= { wsCcStatsWlanSumShortEntry 15 }

		
		-- 1.3.6.1.4.1.388.14.3.3.1.4.10.1.16
		wsCcStatsWlanSumShortTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00)."
			::= { wsCcStatsWlanSumShortEntry 16 }

		
		-- 1.3.6.1.4.1.388.14.3.3.1.4.10.1.17
		wsCcStatsWlanSumShortPp10kRxUndecrypt OBJECT-TYPE
			SYNTAX PartsPer10k
			UNITS "parts-per-10000"
			MAX-ACCESS read-only
			STATUS current
			DESCRIPTION
				"Ratio of RX packets that were undecryptable.
				
				Expressed as parts-per-10000."
			::= { wsCcStatsWlanSumShortEntry 17 }

		
		-- 1.3.6.1.4.1.388.14.3.3.1.4.10.1.18
		wsCcStatsWlanSumShortTotalMus OBJECT-TYPE
			SYNTAX Unsigned32 (0..1000)
			UNITS "number of MUs"
			MAX-ACCESS read-only
			STATUS current
			DESCRIPTION
				"The number of packets used to calculate the statistics in
				this window for all MUs associated with WLAN."
			::= { wsCcStatsWlanSumShortEntry 18 }

		
-- The switch roll-up values are reported at entry/instance
-- 1001, as with the other ccWlanRfSum tables.  Note, however,
-- that the switch reports very few of the values that WLANs
-- report, and will return NO-SUCH for those values on GET,
-- and will 'skip-over' those columns for GET-NEXT.
		-- 1.3.6.1.4.1.388.14.3.3.1.4.11
		wsCcStatsWlanSumLongTable OBJECT-TYPE
			SYNTAX SEQUENCE OF WsCcStatsWlanSumLongEntry
			MAX-ACCESS not-accessible
			STATUS current
			DESCRIPTION
				"Averages and rates calculated over the LONG window for
				each WLAN.
				
				(Refer to ccWlanSumStatsShortTable for descriptions)."
			::= { wsCcStatsWlan 11 }

		
		-- 1.3.6.1.4.1.388.14.3.3.1.4.11.1
		wsCcStatsWlanSumLongEntry OBJECT-TYPE
			SYNTAX WsCcStatsWlanSumLongEntry
			MAX-ACCESS not-accessible
			STATUS current
			DESCRIPTION
				" "
			INDEX { wsCcStatsWlanIndex }
			::= { wsCcStatsWlanSumLongTable 1 }

		
		WsCcStatsWlanSumLongEntry ::=
			SEQUENCE { 
				wsCcStatsWlanSumLongTimestamp
					TimeTicks,
				wsCcStatsWlanSumLongNumPkts
					Unsigned32,
				wsCcStatsWlanSumLongPktsPerSec100
					ScaleBy100,
				wsCcStatsWlanSumLongPktsPerSecTx100
					ScaleBy100,
				wsCcStatsWlanSumLongPktsPerSecRx100
					ScaleBy100,
				wsCcStatsWlanSumLongThroughput
					Unsigned32,
				wsCcStatsWlanSumLongThroughputTx
					Unsigned32,
				wsCcStatsWlanSumLongThroughputRx
					Unsigned32,
				wsCcStatsWlanSumLongAvgBitSpeed
					Unsigned32,
				wsCcStatsWlanSumLongAvgMuSignal
					Integer32,
				wsCcStatsWlanSumLongAvgMuNoise
					Integer32,
				wsCcStatsWlanSumLongAvgMuSnr
					Integer32,
				wsCcStatsWlanSumLongPp10kNUcastPkts
					PartsPer10k,
				wsCcStatsWlanSumLongPp10kTxWithRetries
					PartsPer10k,
				wsCcStatsWlanSumLongPp10kDropped
					PartsPer10k,
				wsCcStatsWlanSumLongTxAvgRetries100
					ScaleBy100,
				wsCcStatsWlanSumLongPp10kRxUndecrypt
					PartsPer10k,
				wsCcStatsWlanSumLongTotalMus
					Unsigned32
			 }

		-- 1.3.6.1.4.1.388.14.3.3.1.4.11.1.1
		wsCcStatsWlanSumLongTimestamp OBJECT-TYPE
			SYNTAX TimeTicks
			MAX-ACCESS read-only
			STATUS current
			DESCRIPTION
				" "
			::= { wsCcStatsWlanSumLongEntry 1 }

		
		-- 1.3.6.1.4.1.388.14.3.3.1.4.11.1.2
		wsCcStatsWlanSumLongNumPkts OBJECT-TYPE
			SYNTAX Unsigned32
			UNITS "packets"
			MAX-ACCESS read-only
			STATUS current
			DESCRIPTION
				" "
			::= { wsCcStatsWlanSumLongEntry 2 }

		
		-- 1.3.6.1.4.1.388.14.3.3.1.4.11.1.3
		wsCcStatsWlanSumLongPktsPerSec100 OBJECT-TYPE
			SYNTAX ScaleBy100
			UNITS "pkts per sec x100"
			MAX-ACCESS read-only
			STATUS current
			DESCRIPTION
				" "
			::= { wsCcStatsWlanSumLongEntry 3 }

		
		-- 1.3.6.1.4.1.388.14.3.3.1.4.11.1.4
		wsCcStatsWlanSumLongPktsPerSecTx100 OBJECT-TYPE
			SYNTAX ScaleBy100
			UNITS "pkts per sec x100"
			MAX-ACCESS read-only
			STATUS current
			DESCRIPTION
				" "
			::= { wsCcStatsWlanSumLongEntry 4 }

		
		-- 1.3.6.1.4.1.388.14.3.3.1.4.11.1.5
		wsCcStatsWlanSumLongPktsPerSecRx100 OBJECT-TYPE
			SYNTAX ScaleBy100
			UNITS "pkts per sec x100"
			MAX-ACCESS read-only
			STATUS current
			DESCRIPTION
				" "
			::= { wsCcStatsWlanSumLongEntry 5 }

		
		-- 1.3.6.1.4.1.388.14.3.3.1.4.11.1.6
		wsCcStatsWlanSumLongThroughput OBJECT-TYPE
			SYNTAX Unsigned32
			UNITS "bits per second"
			MAX-ACCESS read-only
			STATUS current
			DESCRIPTION
				" "
			::= { wsCcStatsWlanSumLongEntry 6 }

		
		-- 1.3.6.1.4.1.388.14.3.3.1.4.11.1.7
		wsCcStatsWlanSumLongThroughputTx OBJECT-TYPE
			SYNTAX Unsigned32
			UNITS "bits per second"
			MAX-ACCESS read-only
			STATUS current
			DESCRIPTION
				" "
			::= { wsCcStatsWlanSumLongEntry 7 }

		
		-- 1.3.6.1.4.1.388.14.3.3.1.4.11.1.8
		wsCcStatsWlanSumLongThroughputRx OBJECT-TYPE
			SYNTAX Unsigned32
			UNITS "bits per second"
			MAX-ACCESS read-only
			STATUS current
			DESCRIPTION
				" "
			::= { wsCcStatsWlanSumLongEntry 8 }

		
		-- 1.3.6.1.4.1.388.14.3.3.1.4.11.1.9
		wsCcStatsWlanSumLongAvgBitSpeed OBJECT-TYPE
			SYNTAX Unsigned32
			UNITS "bits per second"
			MAX-ACCESS read-only
			STATUS current
			DESCRIPTION
				" "
			::= { wsCcStatsWlanSumLongEntry 9 }

		
		-- 1.3.6.1.4.1.388.14.3.3.1.4.11.1.10
		wsCcStatsWlanSumLongAvgMuSignal OBJECT-TYPE
			SYNTAX Integer32
			UNITS "dBm"
			MAX-ACCESS read-only
			STATUS current
			DESCRIPTION
				" "
			::= { wsCcStatsWlanSumLongEntry 10 }

		
		-- 1.3.6.1.4.1.388.14.3.3.1.4.11.1.11
		wsCcStatsWlanSumLongAvgMuNoise OBJECT-TYPE
			SYNTAX Integer32
			UNITS "dBm"
			MAX-ACCESS read-only
			STATUS current
			DESCRIPTION
				" "
			::= { wsCcStatsWlanSumLongEntry 11 }

		
		-- 1.3.6.1.4.1.388.14.3.3.1.4.11.1.12
		wsCcStatsWlanSumLongAvgMuSnr OBJECT-TYPE
			SYNTAX Integer32
			UNITS "dB"
			MAX-ACCESS read-only
			STATUS current
			DESCRIPTION
				" "
			::= { wsCcStatsWlanSumLongEntry 12 }

		
		-- 1.3.6.1.4.1.388.14.3.3.1.4.11.1.13
		wsCcStatsWlanSumLongPp10kNUcastPkts OBJECT-TYPE
			SYNTAX PartsPer10k
			UNITS "parts-per-10000"
			MAX-ACCESS read-only
			STATUS current
			DESCRIPTION
				" "
			::= { wsCcStatsWlanSumLongEntry 13 }

		
		-- 1.3.6.1.4.1.388.14.3.3.1.4.11.1.14
		wsCcStatsWlanSumLongPp10kTxWithRetries OBJECT-TYPE
			SYNTAX PartsPer10k
			UNITS "parts-per-10000"
			MAX-ACCESS read-only
			STATUS current
			DESCRIPTION
				" "
			::= { wsCcStatsWlanSumLongEntry 14 }

		
		-- 1.3.6.1.4.1.388.14.3.3.1.4.11.1.15
		wsCcStatsWlanSumLongPp10kDropped OBJECT-TYPE
			SYNTAX PartsPer10k
			UNITS "parts-per-10000"
			MAX-ACCESS read-only
			STATUS current
			DESCRIPTION
				" "
			::= { wsCcStatsWlanSumLongEntry 15 }

		
		-- 1.3.6.1.4.1.388.14.3.3.1.4.11.1.16
		wsCcStatsWlanSumLongTxAvgRetries100 OBJECT-TYPE
			SYNTAX ScaleBy100
			UNITS "average x100"
			MAX-ACCESS read-only
			STATUS current
			DESCRIPTION
				" "
			::= { wsCcStatsWlanSumLongEntry 16 }

		
		-- 1.3.6.1.4.1.388.14.3.3.1.4.11.1.17
		wsCcStatsWlanSumLongPp10kRxUndecrypt OBJECT-TYPE
			SYNTAX PartsPer10k
			UNITS "parts-per-10000"
			MAX-ACCESS read-only
			STATUS current
			DESCRIPTION
				" "
			::= { wsCcStatsWlanSumLongEntry 17 }

		
		-- 1.3.6.1.4.1.388.14.3.3.1.4.11.1.18
		wsCcStatsWlanSumLongTotalMus OBJECT-TYPE
			SYNTAX Unsigned32 (0..1000)
			UNITS "number of MUs"
			MAX-ACCESS read-only
			STATUS current
			DESCRIPTION
				" "
			::= { wsCcStatsWlanSumLongEntry 18 }

		
		-- 1.3.6.1.4.1.388.14.3.3.1.5
		wsCcStatsTrapCtrlConf OBJECT IDENTIFIER ::= { wsCcStatsMIB 5 }

		
		-- 1.3.6.1.4.1.388.14.3.3.1.5.1
		wsCcStatsTrapCtrlConfTable OBJECT-TYPE
			SYNTAX SEQUENCE OF WsCcStatsTrapCtrlConfEntry
			MAX-ACCESS not-accessible
			STATUS current
			DESCRIPTION
				"This table configures thresholds that can be monitored for:
				- all MUs and/or 
				- all Portals  and/or 
				- all WLANs    and/or 
				- for the entire switch
						
				When a given threshold is crossed, it generates the 
				appropriate corresponding notification, (ccSumStats_:
				_MU, _Portal, _WLAN, or _Switch).
								
				Some thresholds result in notifications when exceeded, 
				and some when the current value sinks below the 
				threshold. This is indicated by the wording of the 
				entry in the entry's _Descr value.
								
				In all cases, the summary stat being monitored is the
				Short value, never the Long value.
								
				Note that for thresholds of type thresholdsAvgMuSignal & 
				thresholdsAvgMuNoise, the values being 'watched' are 
				actually negative.  In these cases the threshold is 
				specified as a Unsigned32.  For example, if you wish to
				trap on Signal being worse than -75dBm, enter '70'.  This
				works since a user would never want to trap on a threshold
				of Sinal worse than +10dBm.  (SNR is not an issue, since
				that is a positive value).
								
				Any values reported as var-binds in the resultant trap(s)
				are likewise reported as positive values.
				
				Finally, since SNMP does not support decimals, 
				all the threshold values are 100 times their 
				actual values. So, a value of 563 means 5.63. 
				Likewise, when the user wants to set the
				thresholds, he should set the value to 1000 
				for an actual value of 10."
			::= { wsCcStatsTrapCtrlConf 1 }

		
		-- 1.3.6.1.4.1.388.14.3.3.1.5.1.1
		wsCcStatsTrapCtrlConfEntry OBJECT-TYPE
			SYNTAX WsCcStatsTrapCtrlConfEntry
			MAX-ACCESS not-accessible
			STATUS current
			DESCRIPTION
				"The rows/instances in this table occur at the exact same
				indices as the corresponding monitored data occurs in the
				_SumStats tables.
								
				For example, row #2 / instance .2 represents the
				threshold(s) for the _PktsPerSec values for MU, Portal,
				WLAN, and Switch.
								
				If a given threshold does not make sense for one of those
				4 entities, its corresponding TruthValue will be false."
			INDEX { wsCcStatsTrapCtrlConfIndex }
			::= { wsCcStatsTrapCtrlConfTable 1 }

		
		WsCcStatsTrapCtrlConfEntry ::=
			SEQUENCE { 
				wsCcStatsTrapCtrlConfIndex
					INTEGER,
				wsCcStatsTrapCtrlConfDescr
					DisplayString,
				wsCcStatsTrapCtrlConfUnits
					DisplayString,
				wsCcStatsTrapCtrlConfCanBeSetMu
					TruthValue,
				wsCcStatsTrapCtrlConfThresholdMus
					Integer32,
				wsCcStatsTrapCtrlConfCanBeSetPortal
					TruthValue,
				wsCcStatsTrapCtrlConfThresholdPortals
					Integer32,
				wsCcStatsTrapCtrlConfCanBeSetWlan
					TruthValue,
				wsCcStatsTrapCtrlConfThresholdWlans
					Integer32,
				wsCcStatsTrapCtrlConfCanBeSetSwitch
					TruthValue,
				wsCcStatsTrapCtrlConfThresholdSwitch
					Integer32
			 }

		-- 1.3.6.1.4.1.388.14.3.3.1.5.1.1.1
		wsCcStatsTrapCtrlConfIndex OBJECT-TYPE
			SYNTAX INTEGER
				{
				unusedTimestamp(1),
				unusedNumPkts(2),
				thresholdsPktsPerSec(3),
				unusedPktsPerSecTx(4),
				unusedPktsPerSecRx(5),
				thresholdsThroughput(6),
				unusedThroughputTx(7),
				unusedThroughputRx(8),
				thresholdsAvgBitSpeed(9),
				thresholdsAvgMuSignal(10),
				thresholdsAvgMuNoise(11),
				thresholdsAvgMuSnr(12),
				thresholdsPctNUcastPkts(13),
				thresholdsPpmTxWithRetires(14),
				thresholdsPpmTxDropped(15),
				thresholdsTxAvgRetries(16),
				thresholdsPpmRxUndecrypt(17),
				thresholdsTotalMus(18),
				thresholdsPctRfUtil(19),
				thresholdsPctDropped(20),
				thresholdAvgPortalNoiseSuddenChange(21)
				}
			MAX-ACCESS accessible-for-notify
			STATUS current
			DESCRIPTION
				"Index into table.  Note that specific thresholds occur
				at specific instance values as denoted by the enumeration
				values assigned to this variable."
			::= { wsCcStatsTrapCtrlConfEntry 1 }

		
		-- 1.3.6.1.4.1.388.14.3.3.1.5.1.1.2
		wsCcStatsTrapCtrlConfDescr OBJECT-TYPE
			SYNTAX DisplayString
			MAX-ACCESS read-only
			STATUS current
			DESCRIPTION
				"Description of the threshold."
			::= { wsCcStatsTrapCtrlConfEntry 2 }

		
		-- 1.3.6.1.4.1.388.14.3.3.1.5.1.1.3
		wsCcStatsTrapCtrlConfUnits OBJECT-TYPE
			SYNTAX DisplayString
			MAX-ACCESS read-only
			STATUS current
			DESCRIPTION
				"Units of the the threshold."
			::= { wsCcStatsTrapCtrlConfEntry 3 }

		
		-- 1.3.6.1.4.1.388.14.3.3.1.5.1.1.4
		wsCcStatsTrapCtrlConfCanBeSetMu OBJECT-TYPE
			SYNTAX TruthValue
			MAX-ACCESS read-only
			STATUS current
			DESCRIPTION
				"If true, the threshold can be set for MUs.
				If false, attempting the threshold will return a READ-ONLY."
			::= { wsCcStatsTrapCtrlConfEntry 4 }

		
		-- 1.3.6.1.4.1.388.14.3.3.1.5.1.1.5
		wsCcStatsTrapCtrlConfThresholdMus OBJECT-TYPE
			SYNTAX Integer32
			MAX-ACCESS read-write
			STATUS current
			DESCRIPTION
				"The threshold for all MUs.
				If 0, no threshold checking is performed."
			::= { wsCcStatsTrapCtrlConfEntry 5 }

		
		-- 1.3.6.1.4.1.388.14.3.3.1.5.1.1.6
		wsCcStatsTrapCtrlConfCanBeSetPortal OBJECT-TYPE
			SYNTAX TruthValue
			MAX-ACCESS read-only
			STATUS current
			DESCRIPTION
				"If true, the threshold can be set for Portals.
				If false, attempting the threshold will return a READ-ONLY."
			::= { wsCcStatsTrapCtrlConfEntry 6 }

		
		-- 1.3.6.1.4.1.388.14.3.3.1.5.1.1.7
		wsCcStatsTrapCtrlConfThresholdPortals OBJECT-TYPE
			SYNTAX Integer32
			MAX-ACCESS read-write
			STATUS current
			DESCRIPTION
				"The threshold for all Portals.  
				If 0, no threshold checking is performed."
			::= { wsCcStatsTrapCtrlConfEntry 7 }

		
		-- 1.3.6.1.4.1.388.14.3.3.1.5.1.1.8
		wsCcStatsTrapCtrlConfCanBeSetWlan OBJECT-TYPE
			SYNTAX TruthValue
			MAX-ACCESS read-only
			STATUS current
			DESCRIPTION
				"If true, the threshold can be set for Wlans.
				If false, attempting the threshold will return a READ-ONLY."
			::= { wsCcStatsTrapCtrlConfEntry 8 }

		
		-- 1.3.6.1.4.1.388.14.3.3.1.5.1.1.9
		wsCcStatsTrapCtrlConfThresholdWlans OBJECT-TYPE
			SYNTAX Integer32
			MAX-ACCESS read-write
			STATUS current
			DESCRIPTION
				"The threshold for all Wlans.  
				If 0, no threshold checking is performed."
			::= { wsCcStatsTrapCtrlConfEntry 9 }

		
		-- 1.3.6.1.4.1.388.14.3.3.1.5.1.1.10
		wsCcStatsTrapCtrlConfCanBeSetSwitch OBJECT-TYPE
			SYNTAX TruthValue
			MAX-ACCESS read-only
			STATUS current
			DESCRIPTION
				"If true, the threshold can be set for the entire switch.
				If false, attempting the threshold will return a READ-ONLY."
			::= { wsCcStatsTrapCtrlConfEntry 10 }

		
		-- 1.3.6.1.4.1.388.14.3.3.1.5.1.1.11
		wsCcStatsTrapCtrlConfThresholdSwitch OBJECT-TYPE
			SYNTAX Integer32
			MAX-ACCESS read-write
			STATUS current
			DESCRIPTION
				"The threshold for the entire Switch.  
				If 0, no threshold checking is performed."
			::= { wsCcStatsTrapCtrlConfEntry 11 }

		
		-- 1.3.6.1.4.1.388.14.3.3.1.5.2
		wsCcStatsTrapCtrlConfMinPktsForTrap OBJECT-TYPE
			SYNTAX Unsigned32
			MAX-ACCESS read-write
			STATUS current
			DESCRIPTION
				"The minimum number of packets that must be in a
				window/dataset before any of the threshold traps 
				will 'fire'."
			::= { wsCcStatsTrapCtrlConf 2 }

		
		-- 1.3.6.1.4.1.388.14.3.3.1.6
		wsCcStatsSwitch OBJECT IDENTIFIER ::= { wsCcStatsMIB 6 }

		
		-- 1.3.6.1.4.1.388.14.3.3.1.6.1
		wsCcStatsSwitchTxRetriesPktsTable OBJECT-TYPE
			SYNTAX SEQUENCE OF WsCcStatsSwitchTxRetriesPktsEntry
			MAX-ACCESS not-accessible
			STATUS current
			DESCRIPTION
				"This table describes counts of packets transmitted via various 
				number of retries, (1 retry, 2 retries, 3 retries...)from the switch"
			::= { wsCcStatsSwitch 1 }

		
		-- 1.3.6.1.4.1.388.14.3.3.1.6.1.1
		wsCcStatsSwitchTxRetriesPktsEntry OBJECT-TYPE
			SYNTAX WsCcStatsSwitchTxRetriesPktsEntry
			MAX-ACCESS not-accessible
			STATUS current
			DESCRIPTION
				"Description."
			INDEX { wsCcStatsSwitchTxRetriesPktsIndex }
			::= { wsCcStatsSwitchTxRetriesPktsTable 1 }

		
		WsCcStatsSwitchTxRetriesPktsEntry ::=
			SEQUENCE { 
				wsCcStatsSwitchTxRetriesPktsIndex
					Integer32,
				wsCcStatsSwitchTxRetriesPkts01
					Counter32,
				wsCcStatsSwitchTxRetriesPkts02
					Counter32,
				wsCcStatsSwitchTxRetriesPkts03
					Counter32,
				wsCcStatsSwitchTxRetriesPkts04
					Counter32,
				wsCcStatsSwitchTxRetriesPkts05
					Counter32,
				wsCcStatsSwitchTxRetriesPkts06
					Counter32,
				wsCcStatsSwitchTxRetriesPkts07
					Counter32,
				wsCcStatsSwitchTxRetriesPkts08
					Counter32,
				wsCcStatsSwitchTxRetriesPkts09
					Counter32,
				wsCcStatsSwitchTxRetriesPkts10
					Counter32,
				wsCcStatsSwitchTxRetriesPkts11
					Counter32,
				wsCcStatsSwitchTxRetriesPkts12
					Counter32,
				wsCcStatsSwitchTxRetriesPkts13
					Counter32,
				wsCcStatsSwitchTxRetriesPkts14
					Counter32,
				wsCcStatsSwitchTxRetriesPkts15
					Counter32,
				wsCcStatsSwitchTxRetriesPktsFailed
					Counter32,
				wsCcStatsSwitchTxRetriesPktsNone
					Counter32
			 }

		-- 1.3.6.1.4.1.388.14.3.3.1.6.1.1.1
		wsCcStatsSwitchTxRetriesPktsIndex OBJECT-TYPE
			SYNTAX Integer32 (1)
			MAX-ACCESS read-only
			STATUS current
			DESCRIPTION
				"Index for this table"
			::= { wsCcStatsSwitchTxRetriesPktsEntry 1 }

		
		-- 1.3.6.1.4.1.388.14.3.3.1.6.1.1.2
		wsCcStatsSwitchTxRetriesPkts01 OBJECT-TYPE
			SYNTAX Counter32
			MAX-ACCESS read-only
			STATUS current
			DESCRIPTION
				"Number of pkts successfully transmitted with exactly 1 retry"
			::= { wsCcStatsSwitchTxRetriesPktsEntry 2 }

		
		-- 1.3.6.1.4.1.388.14.3.3.1.6.1.1.3
		wsCcStatsSwitchTxRetriesPkts02 OBJECT-TYPE
			SYNTAX Counter32
			MAX-ACCESS read-only
			STATUS current
			DESCRIPTION
				"Number of pkts successfully transmitted with exactly 2 retries"
			::= { wsCcStatsSwitchTxRetriesPktsEntry 3 }

		
		-- 1.3.6.1.4.1.388.14.3.3.1.6.1.1.4
		wsCcStatsSwitchTxRetriesPkts03 OBJECT-TYPE
			SYNTAX Counter32
			MAX-ACCESS read-only
			STATUS current
			DESCRIPTION
				"Number of pkts successfully transmitted with exactly 3 retries"
			::= { wsCcStatsSwitchTxRetriesPktsEntry 4 }

		
		-- 1.3.6.1.4.1.388.14.3.3.1.6.1.1.5
		wsCcStatsSwitchTxRetriesPkts04 OBJECT-TYPE
			SYNTAX Counter32
			MAX-ACCESS read-only
			STATUS current
			DESCRIPTION
				"Number of pkts successfully transmitted with exactly 4 retries"
			::= { wsCcStatsSwitchTxRetriesPktsEntry 5 }

		
		-- 1.3.6.1.4.1.388.14.3.3.1.6.1.1.6
		wsCcStatsSwitchTxRetriesPkts05 OBJECT-TYPE
			SYNTAX Counter32
			MAX-ACCESS read-only
			STATUS current
			DESCRIPTION
				"Number of pkts successfully transmitted with exactly 5 retries"
			::= { wsCcStatsSwitchTxRetriesPktsEntry 6 }

		
		-- 1.3.6.1.4.1.388.14.3.3.1.6.1.1.7
		wsCcStatsSwitchTxRetriesPkts06 OBJECT-TYPE
			SYNTAX Counter32
			MAX-ACCESS read-only
			STATUS current
			DESCRIPTION
				"Number of pkts successfully transmitted with exactly 6 retries"
			::= { wsCcStatsSwitchTxRetriesPktsEntry 7 }

		
		-- 1.3.6.1.4.1.388.14.3.3.1.6.1.1.8
		wsCcStatsSwitchTxRetriesPkts07 OBJECT-TYPE
			SYNTAX Counter32
			MAX-ACCESS read-only
			STATUS current
			DESCRIPTION
				"Number of pkts successfully transmitted with exactly 7 retries"
			::= { wsCcStatsSwitchTxRetriesPktsEntry 8 }

		
		-- 1.3.6.1.4.1.388.14.3.3.1.6.1.1.9
		wsCcStatsSwitchTxRetriesPkts08 OBJECT-TYPE
			SYNTAX Counter32
			MAX-ACCESS read-only
			STATUS current
			DESCRIPTION
				"Number of pkts successfully transmitted with exactly 8 retries"
			::= { wsCcStatsSwitchTxRetriesPktsEntry 9 }

		
		-- 1.3.6.1.4.1.388.14.3.3.1.6.1.1.10
		wsCcStatsSwitchTxRetriesPkts09 OBJECT-TYPE
			SYNTAX Counter32
			MAX-ACCESS read-only
			STATUS current
			DESCRIPTION
				"Number of pkts successfully transmitted with exactly 9 retries"
			::= { wsCcStatsSwitchTxRetriesPktsEntry 10 }

		
		-- 1.3.6.1.4.1.388.14.3.3.1.6.1.1.11
		wsCcStatsSwitchTxRetriesPkts10 OBJECT-TYPE
			SYNTAX Counter32
			MAX-ACCESS read-only
			STATUS current
			DESCRIPTION
				"Number of pkts successfully transmitted with exactly 10 retries"
			::= { wsCcStatsSwitchTxRetriesPktsEntry 11 }

		
		-- 1.3.6.1.4.1.388.14.3.3.1.6.1.1.12
		wsCcStatsSwitchTxRetriesPkts11 OBJECT-TYPE
			SYNTAX Counter32
			MAX-ACCESS read-only
			STATUS current
			DESCRIPTION
				"Number of pkts successfully transmitted with exactly 11 retries"
			::= { wsCcStatsSwitchTxRetriesPktsEntry 12 }

		
		-- 1.3.6.1.4.1.388.14.3.3.1.6.1.1.13
		wsCcStatsSwitchTxRetriesPkts12 OBJECT-TYPE
			SYNTAX Counter32
			MAX-ACCESS read-only
			STATUS current
			DESCRIPTION
				"Number of pkts successfully transmitted with exactly 12 retries"
			::= { wsCcStatsSwitchTxRetriesPktsEntry 13 }

		
		-- 1.3.6.1.4.1.388.14.3.3.1.6.1.1.14
		wsCcStatsSwitchTxRetriesPkts13 OBJECT-TYPE
			SYNTAX Counter32
			MAX-ACCESS read-only
			STATUS current
			DESCRIPTION
				"Number of pkts successfully transmitted with exactly 13 retries"
			::= { wsCcStatsSwitchTxRetriesPktsEntry 14 }

		
		-- 1.3.6.1.4.1.388.14.3.3.1.6.1.1.15
		wsCcStatsSwitchTxRetriesPkts14 OBJECT-TYPE
			SYNTAX Counter32
			MAX-ACCESS read-only
			STATUS current
			DESCRIPTION
				"Number of pkts successfully transmitted with exactly 14 retries"
			::= { wsCcStatsSwitchTxRetriesPktsEntry 15 }

		
		-- 1.3.6.1.4.1.388.14.3.3.1.6.1.1.16
		wsCcStatsSwitchTxRetriesPkts15 OBJECT-TYPE
			SYNTAX Counter32
			MAX-ACCESS read-only
			STATUS current
			DESCRIPTION
				"Number of pkts successfully transmitted with exactly 15 retries"
			::= { wsCcStatsSwitchTxRetriesPktsEntry 16 }

		
--  
-- 
		-- 1.3.6.1.4.1.388.14.3.3.1.6.1.1.17
		wsCcStatsSwitchTxRetriesPktsFailed OBJECT-TYPE
			SYNTAX Counter32
			MAX-ACCESS read-only
			STATUS current
			DESCRIPTION
				"Number of pkts that never were successfully 
				transmitted to because the max retry count was exceeded"
			::= { wsCcStatsSwitchTxRetriesPktsEntry 17 }

		
		-- 1.3.6.1.4.1.388.14.3.3.1.6.1.1.18
		wsCcStatsSwitchTxRetriesPktsNone OBJECT-TYPE
			SYNTAX Counter32
			MAX-ACCESS read-only
			STATUS current
			DESCRIPTION
				"Number of pkts successfully transmitted without retries"
			::= { wsCcStatsSwitchTxRetriesPktsEntry 18 }

		
		-- 1.3.6.1.4.1.388.14.3.3.1.6.2
		wsCcStatsSwitchRxPktsTable OBJECT-TYPE
			SYNTAX SEQUENCE OF WsCcStatsSwitchRxPktsEntry
			MAX-ACCESS not-accessible
			STATUS current
			DESCRIPTION
				"This table describes counts of packets received at each 
				possible speed, (1Mb, 2Mb, 5.5Mb, 6Mb...)by the switch"
			::= { wsCcStatsSwitch 2 }

		
		-- 1.3.6.1.4.1.388.14.3.3.1.6.2.1
		wsCcStatsSwitchRxPktsEntry OBJECT-TYPE
			SYNTAX WsCcStatsSwitchRxPktsEntry
			MAX-ACCESS not-accessible
			STATUS current
			DESCRIPTION
				"Description."
			INDEX { wsCcStatsSwitchRxPktsIndex }
			::= { wsCcStatsSwitchRxPktsTable 1 }

		
		WsCcStatsSwitchRxPktsEntry ::=
			SEQUENCE { 
				wsCcStatsSwitchRxPktsIndex
					Unsigned32,
				wsCcStatsSwitchRxPktsAt1Mb
					Counter32,
				wsCcStatsSwitchRxPktsAt2Mb
					Counter32,
				wsCcStatsSwitchRxPktsAt5pt5Mb
					Counter32,
				wsCcStatsSwitchRxPktsAt6Mb
					Counter32,
				wsCcStatsSwitchRxPktsAt9Mb
					Counter32,
				wsCcStatsSwitchRxPktsAt11Mb
					Counter32,
				wsCcStatsSwitchRxPktsAt12Mb
					Counter32,
				wsCcStatsSwitchRxPktsAt18Mb
					Counter32,
				wsCcStatsSwitchRxPktsAt22Mb
					Counter32,
				wsCcStatsSwitchRxPktsAt24Mb
					Counter32,
				wsCcStatsSwitchRxPktsAt36Mb
					Counter32,
				wsCcStatsSwitchRxPktsAt48Mb
					Counter32,
				wsCcStatsSwitchRxPktsAt54Mb
					Counter32
			 }

		-- 1.3.6.1.4.1.388.14.3.3.1.6.2.1.1
		wsCcStatsSwitchRxPktsIndex OBJECT-TYPE
			SYNTAX Unsigned32 (1)
			MAX-ACCESS read-only
			STATUS current
			DESCRIPTION
				"Index for this table"
			::= { wsCcStatsSwitchRxPktsEntry 1 }

		
		-- 1.3.6.1.4.1.388.14.3.3.1.6.2.1.2
		wsCcStatsSwitchRxPktsAt1Mb OBJECT-TYPE
			SYNTAX Counter32
			MAX-ACCESS read-only
			STATUS current
			DESCRIPTION
				"Number of pkts received at 1 Mb"
			::= { wsCcStatsSwitchRxPktsEntry 2 }

		
		-- 1.3.6.1.4.1.388.14.3.3.1.6.2.1.3
		wsCcStatsSwitchRxPktsAt2Mb OBJECT-TYPE
			SYNTAX Counter32
			MAX-ACCESS read-only
			STATUS current
			DESCRIPTION
				"Number of pkts received at 2 Mb"
			::= { wsCcStatsSwitchRxPktsEntry 3 }

		
		-- 1.3.6.1.4.1.388.14.3.3.1.6.2.1.4
		wsCcStatsSwitchRxPktsAt5pt5Mb OBJECT-TYPE
			SYNTAX Counter32
			MAX-ACCESS read-only
			STATUS current
			DESCRIPTION
				"Number of pkts received at 5.5 Mb"
			::= { wsCcStatsSwitchRxPktsEntry 4 }

		
		-- 1.3.6.1.4.1.388.14.3.3.1.6.2.1.5
		wsCcStatsSwitchRxPktsAt6Mb OBJECT-TYPE
			SYNTAX Counter32
			MAX-ACCESS read-only
			STATUS current
			DESCRIPTION
				"Number of pkts received at 6 Mb"
			::= { wsCcStatsSwitchRxPktsEntry 5 }

		
		-- 1.3.6.1.4.1.388.14.3.3.1.6.2.1.6
		wsCcStatsSwitchRxPktsAt9Mb OBJECT-TYPE
			SYNTAX Counter32
			MAX-ACCESS read-only
			STATUS current
			DESCRIPTION
				"Number of pkts received at 9 Mb"
			::= { wsCcStatsSwitchRxPktsEntry 6 }

		
		-- 1.3.6.1.4.1.388.14.3.3.1.6.2.1.7
		wsCcStatsSwitchRxPktsAt11Mb OBJECT-TYPE
			SYNTAX Counter32
			MAX-ACCESS read-only
			STATUS current
			DESCRIPTION
				"Number of pkts received at 11 Mb"
			::= { wsCcStatsSwitchRxPktsEntry 7 }

		
		-- 1.3.6.1.4.1.388.14.3.3.1.6.2.1.8
		wsCcStatsSwitchRxPktsAt12Mb OBJECT-TYPE
			SYNTAX Counter32
			MAX-ACCESS read-only
			STATUS current
			DESCRIPTION
				"Number of pkts received at 12 Mb"
			::= { wsCcStatsSwitchRxPktsEntry 8 }

		
		-- 1.3.6.1.4.1.388.14.3.3.1.6.2.1.9
		wsCcStatsSwitchRxPktsAt18Mb OBJECT-TYPE
			SYNTAX Counter32
			MAX-ACCESS read-only
			STATUS current
			DESCRIPTION
				"Number of pkts received at 18 Mb"
			::= { wsCcStatsSwitchRxPktsEntry 9 }

		
		-- 1.3.6.1.4.1.388.14.3.3.1.6.2.1.10
		wsCcStatsSwitchRxPktsAt22Mb OBJECT-TYPE
			SYNTAX Counter32
			MAX-ACCESS read-only
			STATUS current
			DESCRIPTION
				"Number of pkts received at 22 Mb"
			::= { wsCcStatsSwitchRxPktsEntry 10 }

		
		-- 1.3.6.1.4.1.388.14.3.3.1.6.2.1.11
		wsCcStatsSwitchRxPktsAt24Mb OBJECT-TYPE
			SYNTAX Counter32
			MAX-ACCESS read-only
			STATUS current
			DESCRIPTION
				"Number of pkts received at 24 Mb"
			::= { wsCcStatsSwitchRxPktsEntry 11 }

		
		-- 1.3.6.1.4.1.388.14.3.3.1.6.2.1.12
		wsCcStatsSwitchRxPktsAt36Mb OBJECT-TYPE
			SYNTAX Counter32
			MAX-ACCESS read-only
			STATUS current
			DESCRIPTION
				"Number of pkts received at 36 Mb"
			::= { wsCcStatsSwitchRxPktsEntry 12 }

		
		-- 1.3.6.1.4.1.388.14.3.3.1.6.2.1.13
		wsCcStatsSwitchRxPktsAt48Mb OBJECT-TYPE
			SYNTAX Counter32
			MAX-ACCESS read-only
			STATUS current
			DESCRIPTION
				"Number of pkts received at 48 Mb"
			::= { wsCcStatsSwitchRxPktsEntry 13 }

		
		-- 1.3.6.1.4.1.388.14.3.3.1.6.2.1.14
		wsCcStatsSwitchRxPktsAt54Mb OBJECT-TYPE
			SYNTAX Counter32
			MAX-ACCESS read-only
			STATUS current
			DESCRIPTION
				"Number of pkts received at 54 Mb"
			::= { wsCcStatsSwitchRxPktsEntry 14 }

		
		-- 1.3.6.1.4.1.388.14.3.3.1.6.3
		wsCcStatsSwitchTxPktsTable OBJECT-TYPE
			SYNTAX SEQUENCE OF WsCcStatsSwitchTxPktsEntry
			MAX-ACCESS not-accessible
			STATUS current
			DESCRIPTION
				"This table describes counts of packets transmitted at each 
				possible speed, (1Mb, 2Mb, 5.5Mb, 6Mb...)from the switch
				"
			::= { wsCcStatsSwitch 3 }

		
		-- 1.3.6.1.4.1.388.14.3.3.1.6.3.1
		wsCcStatsSwitchTxPktsEntry OBJECT-TYPE
			SYNTAX WsCcStatsSwitchTxPktsEntry
			MAX-ACCESS not-accessible
			STATUS current
			DESCRIPTION
				"Description."
			INDEX { wsCcStatsSwitchTxPktsIndex }
			::= { wsCcStatsSwitchTxPktsTable 1 }

		
		WsCcStatsSwitchTxPktsEntry ::=
			SEQUENCE { 
				wsCcStatsSwitchTxPktsIndex
					Unsigned32,
				wsCcStatsSwitchTxPktsAt1Mb
					Counter32,
				wsCcStatsSwitchTxPktsAt2Mb
					Counter32,
				wsCcStatsSwitchTxPktsAt5pt5Mb
					Counter32,
				wsCcStatsSwitchTxPktsAt6Mb
					Counter32,
				wsCcStatsSwitchTxPktsAt9Mb
					Counter32,
				wsCcStatsSwitchTxPktsAt11Mb
					Counter32,
				wsCcStatsSwitchTxPktsAt12Mb
					Counter32,
				wsCcStatsSwitchTxPktsAt18Mb
					Counter32,
				wsCcStatsSwitchTxPktsAt22Mb
					Counter32,
				wsCcStatsSwitchTxPktsAt24Mb
					Counter32,
				wsCcStatsSwitchTxPktsAt36Mb
					Counter32,
				wsCcStatsSwitchTxPktsAt48Mb
					Counter32,
				wsCcStatsSwitchTxPktsAt54Mb
					Counter32
			 }

		-- 1.3.6.1.4.1.388.14.3.3.1.6.3.1.1
		wsCcStatsSwitchTxPktsIndex OBJECT-TYPE
			SYNTAX Unsigned32 (1)
			MAX-ACCESS read-only
			STATUS current
			DESCRIPTION
				"Index of this table"
			::= { wsCcStatsSwitchTxPktsEntry 1 }

		
		-- 1.3.6.1.4.1.388.14.3.3.1.6.3.1.2
		wsCcStatsSwitchTxPktsAt1Mb OBJECT-TYPE
			SYNTAX Counter32
			MAX-ACCESS read-only
			STATUS current
			DESCRIPTION
				"Number of pkts transmitted at 1 Mb"
			::= { wsCcStatsSwitchTxPktsEntry 2 }

		
		-- 1.3.6.1.4.1.388.14.3.3.1.6.3.1.3
		wsCcStatsSwitchTxPktsAt2Mb OBJECT-TYPE
			SYNTAX Counter32
			MAX-ACCESS read-only
			STATUS current
			DESCRIPTION
				"Number of pkts transmitted at 2 Mb"
			::= { wsCcStatsSwitchTxPktsEntry 3 }

		
		-- 1.3.6.1.4.1.388.14.3.3.1.6.3.1.4
		wsCcStatsSwitchTxPktsAt5pt5Mb OBJECT-TYPE
			SYNTAX Counter32
			MAX-ACCESS read-only
			STATUS current
			DESCRIPTION
				"Number of pkts transmitted at 5.5 Mb"
			::= { wsCcStatsSwitchTxPktsEntry 4 }

		
		-- 1.3.6.1.4.1.388.14.3.3.1.6.3.1.5
		wsCcStatsSwitchTxPktsAt6Mb OBJECT-TYPE
			SYNTAX Counter32
			MAX-ACCESS read-only
			STATUS current
			DESCRIPTION
				"Number of pkts transmitted at 6 Mb"
			::= { wsCcStatsSwitchTxPktsEntry 5 }

		
		-- 1.3.6.1.4.1.388.14.3.3.1.6.3.1.6
		wsCcStatsSwitchTxPktsAt9Mb OBJECT-TYPE
			SYNTAX Counter32
			MAX-ACCESS read-only
			STATUS current
			DESCRIPTION
				"Number of pkts transmitted at 9 Mb"
			::= { wsCcStatsSwitchTxPktsEntry 6 }

		
		-- 1.3.6.1.4.1.388.14.3.3.1.6.3.1.7
		wsCcStatsSwitchTxPktsAt11Mb OBJECT-TYPE
			SYNTAX Counter32
			MAX-ACCESS read-only
			STATUS current
			DESCRIPTION
				"Number of pkts transmitted at 11 Mb"
			::= { wsCcStatsSwitchTxPktsEntry 7 }

		
		-- 1.3.6.1.4.1.388.14.3.3.1.6.3.1.8
		wsCcStatsSwitchTxPktsAt12Mb OBJECT-TYPE
			SYNTAX Counter32
			MAX-ACCESS read-only
			STATUS current
			DESCRIPTION
				"Number of pkts transmitted at 12 Mb"
			::= { wsCcStatsSwitchTxPktsEntry 8 }

		
		-- 1.3.6.1.4.1.388.14.3.3.1.6.3.1.9
		wsCcStatsSwitchTxPktsAt18Mb OBJECT-TYPE
			SYNTAX Counter32
			MAX-ACCESS read-only
			STATUS current
			DESCRIPTION
				"Number of pkts transmitted at 18 Mb"
			::= { wsCcStatsSwitchTxPktsEntry 9 }

		
		-- 1.3.6.1.4.1.388.14.3.3.1.6.3.1.10
		wsCcStatsSwitchTxPktsAt22Mb OBJECT-TYPE
			SYNTAX Counter32
			MAX-ACCESS read-only
			STATUS current
			DESCRIPTION
				"Number of pkts transmitted at 22 Mb"
			::= { wsCcStatsSwitchTxPktsEntry 10 }

		
		-- 1.3.6.1.4.1.388.14.3.3.1.6.3.1.11
		wsCcStatsSwitchTxPktsAt24Mb OBJECT-TYPE
			SYNTAX Counter32
			MAX-ACCESS read-only
			STATUS current
			DESCRIPTION
				"Number of pkts transmitted at 24 Mb"
			::= { wsCcStatsSwitchTxPktsEntry 11 }

		
		-- 1.3.6.1.4.1.388.14.3.3.1.6.3.1.12
		wsCcStatsSwitchTxPktsAt36Mb OBJECT-TYPE
			SYNTAX Counter32
			MAX-ACCESS read-only
			STATUS current
			DESCRIPTION
				"Number of pkts transmitted at 36 Mb"
			::= { wsCcStatsSwitchTxPktsEntry 12 }

		
		-- 1.3.6.1.4.1.388.14.3.3.1.6.3.1.13
		wsCcStatsSwitchTxPktsAt48Mb OBJECT-TYPE
			SYNTAX Counter32
			MAX-ACCESS read-only
			STATUS current
			DESCRIPTION
				"Number of pkts transmitted at 48 Mb"
			::= { wsCcStatsSwitchTxPktsEntry 13 }

		
		-- 1.3.6.1.4.1.388.14.3.3.1.6.3.1.14
		wsCcStatsSwitchTxPktsAt54Mb OBJECT-TYPE
			SYNTAX Counter32
			MAX-ACCESS read-only
			STATUS current
			DESCRIPTION
				"Number of pkts transmitted at 54 Mb"
			::= { wsCcStatsSwitchTxPktsEntry 14 }

		
		-- 1.3.6.1.4.1.388.14.3.3.1.7
		wsCcStatsRadioExt OBJECT IDENTIFIER ::= { wsCcStatsMIB 7 }

		
		-- 1.3.6.1.4.1.388.14.3.3.1.7.1
		wsCcStatsRadioExtTable OBJECT-TYPE
			SYNTAX SEQUENCE OF WsCcStatsRadioExtEntry
			MAX-ACCESS not-accessible
			STATUS current
			DESCRIPTION
				"Description."
			::= { wsCcStatsRadioExt 1 }

		
		-- 1.3.6.1.4.1.388.14.3.3.1.7.1.1
		wsCcStatsRadioExtEntry OBJECT-TYPE
			SYNTAX WsCcStatsRadioExtEntry
			MAX-ACCESS not-accessible
			STATUS current
			DESCRIPTION
				"Description."
			INDEX { wsCcStatsRadioIndex }
			::= { wsCcStatsRadioExtTable 1 }

		
		WsCcStatsRadioExtEntry ::=
			SEQUENCE { 
				wsCcStatsRadioExtDownLinkThroughput
					Gauge32,
				wsCcStatsRadioExtUpLinkThroughput
					Gauge32
			 }

		-- 1.3.6.1.4.1.388.14.3.3.1.7.1.1.1
		wsCcStatsRadioExtDownLinkThroughput OBJECT-TYPE
			SYNTAX Gauge32
			UNITS "Kbps"
			MAX-ACCESS read-only
			STATUS current
			DESCRIPTION
				"The data throughput of the ethernet down link of this radio."
			::= { wsCcStatsRadioExtEntry 1 }

		
		-- 1.3.6.1.4.1.388.14.3.3.1.7.1.1.2
		wsCcStatsRadioExtUpLinkThroughput OBJECT-TYPE
			SYNTAX Gauge32
			UNITS "Kbps"
			MAX-ACCESS read-only
			STATUS current
			DESCRIPTION
				"The data throughput of the ethernet up link of this radio."
			::= { wsCcStatsRadioExtEntry 2 }

		
-- Mesh Statistics.
		-- 1.3.6.1.4.1.388.14.3.3.1.8
		wsCcStatsMesh OBJECT IDENTIFIER ::= { wsCcStatsMIB 8 }

		
		-- 1.3.6.1.4.1.388.14.3.3.1.8.1
		wsCcStatsMeshTable OBJECT-TYPE
			SYNTAX SEQUENCE OF WsCcStatsMeshEntry
			MAX-ACCESS not-accessible
			STATUS current
			DESCRIPTION
				"This table contains general statistics about
				packets sent/recieved via each mesh on the switch."
			::= { wsCcStatsMesh 1 }

		
		-- 1.3.6.1.4.1.388.14.3.3.1.8.1.1
		wsCcStatsMeshEntry OBJECT-TYPE
			SYNTAX WsCcStatsMeshEntry
			MAX-ACCESS not-accessible
			STATUS current
			DESCRIPTION
				" An entry in the table."
			INDEX { wsCcStatsMeshIndex }
			::= { wsCcStatsMeshTable 1 }

		
		WsCcStatsMeshEntry ::=
			SEQUENCE { 
				wsCcStatsMeshIndex
					Unsigned32,
				wsCcStatsMeshConnType
					INTEGER,
				wsCcStatsMeshMac
					PhysAddress,
				wsCcStatsMeshWlanEssid
					DisplayString,
				wsCcStatsMeshRadioType
					RadioType,
				wsCcStatsMeshThroughput
					Unsigned32,
				wsCcStatsMeshAvgBitSpeed
					Unsigned32,
				wsCcStatsMeshRetries100
					ScaleBy100,
				wsCcStatsMeshRadioIndex
					Unsigned32
			 }

		-- 1.3.6.1.4.1.388.14.3.3.1.8.1.1.1
		wsCcStatsMeshIndex OBJECT-TYPE
			SYNTAX Unsigned32 (1..1001)
			MAX-ACCESS accessible-for-notify
			STATUS current
			DESCRIPTION
				"Index of the radio corresponding to the mesh."
			::= { wsCcStatsMeshEntry 1 }

		
		-- 1.3.6.1.4.1.388.14.3.3.1.8.1.1.2
		wsCcStatsMeshConnType OBJECT-TYPE
			SYNTAX INTEGER
				{
				none(1),
				baseBridge(2),
				clientBridge(3)
				}
			MAX-ACCESS read-only
			STATUS current
			DESCRIPTION
				"Mesh Connection Type."
			::= { wsCcStatsMeshEntry 2 }

		
		-- 1.3.6.1.4.1.388.14.3.3.1.8.1.1.3
		wsCcStatsMeshMac OBJECT-TYPE
			SYNTAX PhysAddress
			MAX-ACCESS read-only
			STATUS current
			DESCRIPTION
				"MAC Address."
			::= { wsCcStatsMeshEntry 3 }

		
		-- 1.3.6.1.4.1.388.14.3.3.1.8.1.1.4
		wsCcStatsMeshWlanEssid OBJECT-TYPE
			SYNTAX DisplayString
			MAX-ACCESS read-only
			STATUS current
			DESCRIPTION
				"ESSID of associated WLAN."
			::= { wsCcStatsMeshEntry 4 }

		
		-- 1.3.6.1.4.1.388.14.3.3.1.8.1.1.5
		wsCcStatsMeshRadioType OBJECT-TYPE
			SYNTAX RadioType
			MAX-ACCESS read-only
			STATUS current
			DESCRIPTION
				"Radio Type."
			::= { wsCcStatsMeshEntry 5 }

		
		-- 1.3.6.1.4.1.388.14.3.3.1.8.1.1.6
		wsCcStatsMeshThroughput OBJECT-TYPE
			SYNTAX Unsigned32
			UNITS "bits per second"
			MAX-ACCESS read-only
			STATUS current
			DESCRIPTION
				"Actual number of bits sent and received.
				
				For transmitted packets, each packet sucessfully sent
				counts as 1, (not N, where N is the number of retries)."
			::= { wsCcStatsMeshEntry 6 }

		
		-- 1.3.6.1.4.1.388.14.3.3.1.8.1.1.7
		wsCcStatsMeshAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { wsCcStatsMeshEntry 7 }

		
		-- 1.3.6.1.4.1.388.14.3.3.1.8.1.1.8
		wsCcStatsMeshRetries100 OBJECT-TYPE
			SYNTAX ScaleBy100
			UNITS "average x100"
			MAX-ACCESS read-only
			STATUS current
			DESCRIPTION
				"For all transmit packets (those that experienced some
				retries, those that were successfully transmitted with
				only 1 transmission, and those that attempted max times
				and gave-up), the average number of RE-transmission
				attempts.
				
				Said another (though identical) way: the sum of all
				tranmission attempts divided by the number of unique
				packets attempted to be sent.
				
				Since SNMP does not convey decimal values, the result
				above is multiplied by 100.
				
				If there were no RE-transmissions, this value would be 0.
				If every single packet required exactly two tranmissions,
				this value would be 100, (representing 1.00)."
			::= { wsCcStatsMeshEntry 8 }

		
		-- 1.3.6.1.4.1.388.14.3.3.1.8.1.1.9
		wsCcStatsMeshRadioIndex OBJECT-TYPE
			SYNTAX Unsigned32
			MAX-ACCESS read-only
			STATUS current
			DESCRIPTION
				"Radio index of the assoicated mesh statistic."
			::= { wsCcStatsMeshEntry 9 }

		
-- The switch roll-up values are reported at entry/instance
-- 1001, as with the other wsCcStatsSum tables.  Note, however,
-- that the switch reports very few of the values that mesh
-- report, and will return NO-SUCH for those values on GET,
-- and will 'skip-over' those columns for GET-NEXT.
		-- 1.3.6.1.4.1.388.14.3.3.1.8.2
		wsCcStatsMeshSumShortTable OBJECT-TYPE
			SYNTAX SEQUENCE OF WsCcStatsMeshSumShortEntry
			MAX-ACCESS not-accessible
			STATUS current
			DESCRIPTION
				"Averages and rates calculated over the SHORT window for
				each mesh."
			::= { wsCcStatsMesh 2 }

		
		-- 1.3.6.1.4.1.388.14.3.3.1.8.2.1
		wsCcStatsMeshSumShortEntry OBJECT-TYPE
			SYNTAX WsCcStatsMeshSumShortEntry
			MAX-ACCESS not-accessible
			STATUS current
			DESCRIPTION
				"An entry in the table."
			INDEX { wsCcStatsMeshIndex }
			::= { wsCcStatsMeshSumShortTable 1 }

		
		WsCcStatsMeshSumShortEntry ::=
			SEQUENCE { 
				wsCcStatsMeshSumShortTimestamp
					TimeTicks,
				wsCcStatsMeshSumShortNumPkts
					Counter32,
				wsCcStatsMeshSumShortPktsPerSec100
					ScaleBy100,
				wsCcStatsMeshSumShortPktsPerSecTx100
					ScaleBy100,
				wsCcStatsMeshSumShortPktsPerSecRx100
					ScaleBy100,
				wsCcStatsMeshSumShortThroughput
					Unsigned32,
				wsCcStatsMeshSumShortThroughputTx
					Unsigned32,
				wsCcStatsMeshSumShortThroughputRx
					Unsigned32,
				wsCcStatsMeshSumShortAvgBitSpeed
					Unsigned32,
				wsCcStatsMeshSumShortAvgMuSignal
					Integer32,
				wsCcStatsMeshSumShortAvgMuNoise
					Integer32,
				wsCcStatsMeshSumShortAvgMuSnr
					Integer32,
				wsCcStatsMeshSumShortPp10kTxWithRetries
					PartsPer10k,
				wsCcStatsMeshSumShortPp10kDropped
					PartsPer10k,
				wsCcStatsMeshSumShortTxAvgRetries100
					ScaleBy100,
				wsCcStatsMeshSumShortPp10kRxUndecrypt
					PartsPer10k
			 }

		-- 1.3.6.1.4.1.388.14.3.3.1.8.2.1.1
		wsCcStatsMeshSumShortTimestamp OBJECT-TYPE
			SYNTAX TimeTicks
			MAX-ACCESS read-only
			STATUS current
			DESCRIPTION
				"Snapshot of sysUpTime as of the END of the 'window' of 
				time that this entry of values represents."
			::= { wsCcStatsMeshSumShortEntry 1 }

		
		-- 1.3.6.1.4.1.388.14.3.3.1.8.2.1.2
		wsCcStatsMeshSumShortNumPkts OBJECT-TYPE
			SYNTAX Counter32
			MAX-ACCESS read-only
			STATUS current
			DESCRIPTION
				"The number of packets used to calculate the statistics in
				this window."
			::= { wsCcStatsMeshSumShortEntry 2 }

		
		-- 1.3.6.1.4.1.388.14.3.3.1.8.2.1.3
		wsCcStatsMeshSumShortPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100."
			::= { wsCcStatsMeshSumShortEntry 3 }

		
		-- 1.3.6.1.4.1.388.14.3.3.1.8.2.1.4
		wsCcStatsMeshSumShortPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100."
			::= { wsCcStatsMeshSumShortEntry 4 }

		
		-- 1.3.6.1.4.1.388.14.3.3.1.8.2.1.5
		wsCcStatsMeshSumShortPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100."
			::= { wsCcStatsMeshSumShortEntry 5 }

		
		-- 1.3.6.1.4.1.388.14.3.3.1.8.2.1.6
		wsCcStatsMeshSumShortThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries)."
			::= { wsCcStatsMeshSumShortEntry 6 }

		
		-- 1.3.6.1.4.1.388.14.3.3.1.8.2.1.7
		wsCcStatsMeshSumShortThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries)."
			::= { wsCcStatsMeshSumShortEntry 7 }

		
		-- 1.3.6.1.4.1.388.14.3.3.1.8.2.1.8
		wsCcStatsMeshSumShortThroughputRx OBJECT-TYPE
			SYNTAX Unsigned32
			UNITS "bits per second"
			MAX-ACCESS read-only
			STATUS current
			DESCRIPTION
				"Actual number of bits RX over the window,
				divided by the number of seconds in the window."
			::= { wsCcStatsMeshSumShortEntry 8 }

		
		-- 1.3.6.1.4.1.388.14.3.3.1.8.2.1.9
		wsCcStatsMeshSumShortAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { wsCcStatsMeshSumShortEntry 9 }

		
		-- 1.3.6.1.4.1.388.14.3.3.1.8.2.1.10
		wsCcStatsMeshSumShortAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values."
			::= { wsCcStatsMeshSumShortEntry 10 }

		
		-- 1.3.6.1.4.1.388.14.3.3.1.8.2.1.11
		wsCcStatsMeshSumShortAvgMuNoise OBJECT-TYPE
			SYNTAX Integer32
			UNITS "dBm"
			MAX-ACCESS read-only
			STATUS current
			DESCRIPTION
				"The average of all noise values over the window."
			::= { wsCcStatsMeshSumShortEntry 11 }

		
		-- 1.3.6.1.4.1.388.14.3.3.1.8.2.1.12
		wsCcStatsMeshSumShortAvgMuSnr OBJECT-TYPE
			SYNTAX Integer32
			UNITS "dB"
			MAX-ACCESS read-only
			STATUS current
			DESCRIPTION
				"The average of all SNR values over the window."
			::= { wsCcStatsMeshSumShortEntry 12 }

		
		-- 1.3.6.1.4.1.388.14.3.3.1.8.2.1.13
		wsCcStatsMeshSumShortPp10kTxWithRetries OBJECT-TYPE
			SYNTAX PartsPer10k
			UNITS "parts-per-10000"
			MAX-ACCESS read-only
			STATUS current
			DESCRIPTION
				"Ratio of TX packets that experienced one or more retries.
				
				Expressed as parts-per-10000."
			::= { wsCcStatsMeshSumShortEntry 13 }

		
		-- 1.3.6.1.4.1.388.14.3.3.1.8.2.1.14
		wsCcStatsMeshSumShortPp10kDropped OBJECT-TYPE
			SYNTAX PartsPer10k
			UNITS "parts-per-10000"
			MAX-ACCESS read-only
			STATUS current
			DESCRIPTION
				"Packets dropped divided by packets sent.  Dropped here 
				means dropped intentionally due to the appropriate QoS 
				queue being full.  Other reasons for dropped packets are 
				not counted in this ratio."
			::= { wsCcStatsMeshSumShortEntry 14 }

		
		-- 1.3.6.1.4.1.388.14.3.3.1.8.2.1.15
		wsCcStatsMeshSumShortTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00)."
			::= { wsCcStatsMeshSumShortEntry 15 }

		
		-- 1.3.6.1.4.1.388.14.3.3.1.8.2.1.16
		wsCcStatsMeshSumShortPp10kRxUndecrypt OBJECT-TYPE
			SYNTAX PartsPer10k
			UNITS "parts-per-10000"
			MAX-ACCESS read-only
			STATUS current
			DESCRIPTION
				"Ratio of RX packets that were undecryptable.
				
				Expressed as parts-per-10000."
			::= { wsCcStatsMeshSumShortEntry 16 }

		
-- The switch roll-up values are reported at entry/instance
-- 1001, as with the other wsCcStatsSum tables.  Note, however,
-- that the switch reports very few of the values that mesh
-- report, and will return NO-SUCH for those values on GET,
-- and will 'skip-over' those columns for GET-NEXT.
		-- 1.3.6.1.4.1.388.14.3.3.1.8.3
		wsCcStatsMeshSumLongTable OBJECT-TYPE
			SYNTAX SEQUENCE OF WsCcStatsMeshSumLongEntry
			MAX-ACCESS not-accessible
			STATUS current
			DESCRIPTION
				"Averages and rates calculated over the LONG window for
				each mesh.
				
				(Please refer to wsCcStatsMeshSumShortTable for descriptions)."
			::= { wsCcStatsMesh 3 }

		
		-- 1.3.6.1.4.1.388.14.3.3.1.8.3.1
		wsCcStatsMeshSumLongEntry OBJECT-TYPE
			SYNTAX WsCcStatsMeshSumLongEntry
			MAX-ACCESS not-accessible
			STATUS current
			DESCRIPTION
				"An entry in the table."
			INDEX { wsCcStatsMeshIndex }
			::= { wsCcStatsMeshSumLongTable 1 }

		
		WsCcStatsMeshSumLongEntry ::=
			SEQUENCE { 
				wsCcStatsMeshSumLongTimestamp
					TimeTicks,
				wsCcStatsMeshSumLongNumPkts
					Counter32,
				wsCcStatsMeshSumLongPktsPerSec100
					ScaleBy100,
				wsCcStatsMeshSumLongPktsPerSecTx100
					ScaleBy100,
				wsCcStatsMeshSumLongPktsPerSecRx100
					ScaleBy100,
				wsCcStatsMeshSumLongThroughput
					Unsigned32,
				wsCcStatsMeshSumLongThroughputTx
					Unsigned32,
				wsCcStatsMeshSumLongThroughputRx
					Unsigned32,
				wsCcStatsMeshSumLongAvgBitSpeed
					Unsigned32,
				wsCcStatsMeshSumLongAvgMuSignal
					Integer32,
				wsCcStatsMeshSumLongAvgMuNoise
					Integer32,
				wsCcStatsMeshSumLongAvgMuSnr
					Integer32,
				wsCcStatsMeshSumLongPp10kTxWithRetries
					PartsPer10k,
				wsCcStatsMeshSumLongPp10kDropped
					PartsPer10k,
				wsCcStatsMeshSumLongTxAvgRetries100
					ScaleBy100,
				wsCcStatsMeshSumLongPp10kRxUndecrypt
					PartsPer10k
			 }

		-- 1.3.6.1.4.1.388.14.3.3.1.8.3.1.1
		wsCcStatsMeshSumLongTimestamp OBJECT-TYPE
			SYNTAX TimeTicks
			MAX-ACCESS read-only
			STATUS current
			DESCRIPTION
				"Snapshot of sysUpTime as of the END of the 'window' of 
				time that this entry of values represents. "
			::= { wsCcStatsMeshSumLongEntry 1 }

		
		-- 1.3.6.1.4.1.388.14.3.3.1.8.3.1.2
		wsCcStatsMeshSumLongNumPkts OBJECT-TYPE
			SYNTAX Counter32
			MAX-ACCESS read-only
			STATUS current
			DESCRIPTION
				"The number of packets used to calculate the statistics in
				this window. "
			::= { wsCcStatsMeshSumLongEntry 2 }

		
		-- 1.3.6.1.4.1.388.14.3.3.1.8.3.1.3
		wsCcStatsMeshSumLongPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100. "
			::= { wsCcStatsMeshSumLongEntry 3 }

		
		-- 1.3.6.1.4.1.388.14.3.3.1.8.3.1.4
		wsCcStatsMeshSumLongPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100. "
			::= { wsCcStatsMeshSumLongEntry 4 }

		
		-- 1.3.6.1.4.1.388.14.3.3.1.8.3.1.5
		wsCcStatsMeshSumLongPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100. "
			::= { wsCcStatsMeshSumLongEntry 5 }

		
		-- 1.3.6.1.4.1.388.14.3.3.1.8.3.1.6
		wsCcStatsMeshSumLongThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries). "
			::= { wsCcStatsMeshSumLongEntry 6 }

		
		-- 1.3.6.1.4.1.388.14.3.3.1.8.3.1.7
		wsCcStatsMeshSumLongThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries). "
			::= { wsCcStatsMeshSumLongEntry 7 }

		
		-- 1.3.6.1.4.1.388.14.3.3.1.8.3.1.8
		wsCcStatsMeshSumLongThroughputRx OBJECT-TYPE
			SYNTAX Unsigned32
			UNITS "bits per second"
			MAX-ACCESS read-only
			STATUS current
			DESCRIPTION
				"Actual number of bits RX over the window,
				divided by the number of seconds in the window. "
			::= { wsCcStatsMeshSumLongEntry 8 }

		
		-- 1.3.6.1.4.1.388.14.3.3.1.8.3.1.9
		wsCcStatsMeshSumLongAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received. "
			::= { wsCcStatsMeshSumLongEntry 9 }

		
		-- 1.3.6.1.4.1.388.14.3.3.1.8.3.1.10
		wsCcStatsMeshSumLongAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values. "
			::= { wsCcStatsMeshSumLongEntry 10 }

		
		-- 1.3.6.1.4.1.388.14.3.3.1.8.3.1.11
		wsCcStatsMeshSumLongAvgMuNoise OBJECT-TYPE
			SYNTAX Integer32
			UNITS "dBm"
			MAX-ACCESS read-only
			STATUS current
			DESCRIPTION
				"The average of all noise values over the window. "
			::= { wsCcStatsMeshSumLongEntry 11 }

		
		-- 1.3.6.1.4.1.388.14.3.3.1.8.3.1.12
		wsCcStatsMeshSumLongAvgMuSnr OBJECT-TYPE
			SYNTAX Integer32
			UNITS "dB"
			MAX-ACCESS read-only
			STATUS current
			DESCRIPTION
				"The average of all SNR values over the window. "
			::= { wsCcStatsMeshSumLongEntry 12 }

		
		-- 1.3.6.1.4.1.388.14.3.3.1.8.3.1.13
		wsCcStatsMeshSumLongPp10kTxWithRetries OBJECT-TYPE
			SYNTAX PartsPer10k
			UNITS "parts-per-10000"
			MAX-ACCESS read-only
			STATUS current
			DESCRIPTION
				"Ratio of TX packets that experienced one or more retries.
				
				Expressed as parts-per-10000. "
			::= { wsCcStatsMeshSumLongEntry 13 }

		
		-- 1.3.6.1.4.1.388.14.3.3.1.8.3.1.14
		wsCcStatsMeshSumLongPp10kDropped OBJECT-TYPE
			SYNTAX PartsPer10k
			UNITS "parts-per-10000"
			MAX-ACCESS read-only
			STATUS current
			DESCRIPTION
				"Packets dropped divided by packets sent.  Dropped here 
				means dropped intentionally due to the appropriate QoS 
				queue being full.  Other reasons for dropped packets are 
				not counted in this ratio. "
			::= { wsCcStatsMeshSumLongEntry 14 }

		
		-- 1.3.6.1.4.1.388.14.3.3.1.8.3.1.15
		wsCcStatsMeshSumLongTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00). "
			::= { wsCcStatsMeshSumLongEntry 15 }

		
		-- 1.3.6.1.4.1.388.14.3.3.1.8.3.1.16
		wsCcStatsMeshSumLongPp10kRxUndecrypt OBJECT-TYPE
			SYNTAX PartsPer10k
			UNITS "parts-per-10000"
			MAX-ACCESS read-only
			STATUS current
			DESCRIPTION
				"Ratio of RX packets that were undecryptable.
				
				Expressed as parts-per-10000. "
			::= { wsCcStatsMeshSumLongEntry 16 }

		
		-- 1.3.6.1.4.1.388.14.3.3.1.100
		wsCcStatsMIBConformance OBJECT IDENTIFIER ::= { wsCcStatsMIB 100 }

		
		-- 1.3.6.1.4.1.388.14.3.3.1.100.1
		wsCcStatsMIBCompliances OBJECT IDENTIFIER ::= { wsCcStatsMIBConformance 1 }

		
		-- 1.3.6.1.4.1.388.14.3.3.1.100.1.1
		wsCcStatsMIBCompliance MODULE-COMPLIANCE
			STATUS current
			DESCRIPTION 
				"CC stats MIB compliance."
			MODULE -- this module
				MANDATORY-GROUPS { wsCcStatsMIBConfGroup, wsCcStatsMIBMuGroup, wsCcStatsMIBWlanGroup, wsCcStatsMIBRadioGroup }
			::= { wsCcStatsMIBCompliances 1 }

		
		-- 1.3.6.1.4.1.388.14.3.3.1.100.2
		wsCcStatsMIBGroups OBJECT IDENTIFIER ::= { wsCcStatsMIBConformance 2 }

		
		-- 1.3.6.1.4.1.388.14.3.3.1.100.2.1
		wsCcStatsMIBConfGroup OBJECT-GROUP
			OBJECTS { wsCcStatsConfShortWindow, wsCcStatsConfShortUpdateInterval, wsCcStatsConfLongWindow, wsCcStatsConfLongUpdateInterval, wsCcStatsConfReset, 
				wsCcStatsSwitchRxPktsAt11Mb, wsCcStatsSwitchRxPktsAt18Mb, wsCcStatsSwitchRxPktsAt12Mb, wsCcStatsSwitchRxPktsAt24Mb, wsCcStatsSwitchRxPktsAt22Mb, 
				wsCcStatsSwitchRxPktsAt36Mb, wsCcStatsSwitchRxPktsAt54Mb, wsCcStatsSwitchRxPktsAt48Mb, wsCcStatsSwitchTxPktsIndex, wsCcStatsSwitchTxPktsAt1Mb, 
				wsCcStatsSwitchTxPktsAt2Mb, wsCcStatsSwitchTxPktsAt5pt5Mb, wsCcStatsSwitchTxPktsAt6Mb, wsCcStatsSwitchTxPktsAt9Mb, wsCcStatsSwitchTxPktsAt11Mb, 
				wsCcStatsSwitchTxPktsAt12Mb, wsCcStatsSwitchTxPktsAt18Mb, wsCcStatsSwitchTxPktsAt22Mb, wsCcStatsSwitchTxPktsAt24Mb, wsCcStatsSwitchTxPktsAt36Mb, 
				wsCcStatsSwitchRxPktsAt6Mb, wsCcStatsSwitchRxPktsAt9Mb, wsCcStatsSwitchTxPktsAt48Mb, wsCcStatsSwitchTxPktsAt54Mb, wsCcStatsSwitchRxPktsIndex, 
				wsCcStatsSwitchRxPktsAt1Mb, wsCcStatsSwitchRxPktsAt2Mb, wsCcStatsSwitchRxPktsAt5pt5Mb, wsCcStatsSwitchTxRetriesPkts13, wsCcStatsSwitchTxRetriesPkts14, 
				wsCcStatsSwitchTxRetriesPkts15, wsCcStatsSwitchTxRetriesPktsFailed, wsCcStatsSwitchTxRetriesPkts09, wsCcStatsSwitchTxRetriesPkts10, wsCcStatsSwitchTxRetriesPkts11, 
				wsCcStatsSwitchTxRetriesPkts12, wsCcStatsSwitchTxRetriesPkts05, wsCcStatsSwitchTxRetriesPkts07, wsCcStatsSwitchTxRetriesPkts08, wsCcStatsSwitchTxRetriesPkts01, 
				wsCcStatsSwitchTxRetriesPkts02, wsCcStatsSwitchTxRetriesPkts03, wsCcStatsSwitchTxRetriesPktsNone, wsCcStatsSwitchTxRetriesPkts04, wsCcStatsSwitchTxRetriesPktsIndex, 
				wsCcStatsSwitchTxRetriesPkts06 }
			STATUS current
			DESCRIPTION 
				"Cell Controller Statistics MIB Configuration Group."
			::= { wsCcStatsMIBGroups 1 }

		
		-- 1.3.6.1.4.1.388.14.3.3.1.100.2.2
		wsCcStatsMIBRadioGroup OBJECT-GROUP
			OBJECTS { wsCcStatsRadioLastActivity, wsCcStatsRadioRxUndecryptablePkts, wsCcStatsRadioRxOctetsNUcast, wsCcStatsRadioRxOctetsUcast, wsCcStatsRadioTxOctetsUcast, 
				wsCcStatsRadioRxPktsNUcast, wsCcStatsRadioRxPktsUcast, wsCcStatsRadioTxPktsUcast, wsCcStatsRadioSumShortTimestamp, wsCcStatsRadioSumShortNumPkts, 
				wsCcStatsRadioSumShortPktsPerSec100, wsCcStatsRadioSumShortPktsPerSecTx100, wsCcStatsRadioSumShortPktsPerSecRx100, wsCcStatsRadioSumShortThroughput, wsCcStatsRadioSumShortThroughputTx, 
				wsCcStatsRadioSumShortThroughputRx, wsCcStatsRadioSumShortAvgBitSpeed, wsCcStatsRadioSumShortAvgMuSignal, wsCcStatsRadioSumShortAvgMuNoise, wsCcStatsRadioSumShortAvgMuSnr, 
				wsCcStatsRadioSumShortPp10kNUcastPkts, wsCcStatsRadioSumShortPp10kTxWithRetries, wsCcStatsRadioSumShortPp10kTxMaxRetries, wsCcStatsRadioSumShortTxAvgRetries100, wsCcStatsRadiolSumShortPp10kRxUndecrypt, 
				wsCcStatsRadioSumShortTotalMus, wsCcStatsRadioSumShortPp10kRfUtil, wsCcStatsRadioSumShortPp10kDropped, wsCcStatsRadioSumLongNumPkts, wsCcStatsRadioSumLongPktsPerSec100, 
				wsCcStatsRadioSumLongPktsPerSecTx100, wsCcStatsRadioSumLongPktsPerSecRx100, wsCcStatsRadioSumLongThroughput, wsCcStatsRadioSumLongThroughputTx, wsCcStatsRadioSumLongThroughputRx, 
				wsCcStatsRadioSumLongAvgBitSpeed, wsCcStatsRadioSumLongAvgMuSignal, wsCcStatsRadioSumLongAvgMuNoise, wsCcStatsRadioSumLongAvgMuSnr, wsCcStatsRadioSumLongPp10kNUcastPkts, 
				wsCcStatsRadioSumLongPp10kTxWithRetries, wsCcStatsRadioSumLongPp10kTxMaxRetries, wsCcStatsRadioSumLongTxAvgRetries100, wsCcStatsRadioSumLongPp10kRxUndecrypt, wsCcStatsRadioSumLongTotalMus, 
				wsCcStatsRadioRxErrors, wsCcStatsRadioTxRetriesPacketsFailed, wsCcStatsRadioExtDownLinkThroughput, wsCcStatsRadioExtUpLinkThroughput, wsCcStatsRadioSumShortPp10kVoiceDropped, 
				wsCcStatsRadioSumShortPp10kVoiceRfUtil, wsCcStatsRadioSumShortAvgVoiceMuCount, wsCcStatsRadioSumShortMaxVoiceMuCount, wsCcStatsRadioSumShortCurrVoiceMuCount, wsCcStatsRadioSumLongPp10kRfUtil, 
				wsCcStatsRadioIndex, wsCcStatsRadioSumLongTimestamp, wsCcStatsRadioSumLongPp10kVoiceDropped, wsCcStatsRadioSumLongPp10kVoiceRfUtil, wsCcStatsRadioSumLongAvgVoiceMuCount, 
				wsCcStatsRadioSumLongMaxVoiceMuCount, wsCcStatsRadioSumLongCurrVoiceMuCount, wsCcStatsRadioSumLongPp10kDropped, wsCcStatsRadioTxRetriesVoicePktsFailed }
			STATUS current
			DESCRIPTION 
				"Cell Controller Statistics MIB Radio Group."
			::= { wsCcStatsMIBGroups 2 }

		
		-- 1.3.6.1.4.1.388.14.3.3.1.100.2.3
		wsCcStatsMIBMuGroup OBJECT-GROUP
			OBJECTS { wsCcStatsMuTxPktsUcast, wsCcStatsMuRxPktsUcast, wsCcStatsMuTxOctetsUcast, wsCcStatsMuRxOctetsUcast, wsCcStatsMuRxUndecryptablePkts, 
				wsCcStatsMuRxRssiNumPkts, wsCcStatsMuRxRssiSum, wsCcStatsMuRxRssiSumSquares, wsCcStatsMuRxRssiMostRecent, wsCcStatsMuLastActivity, 
				wsCcStatsMuSumShortTimestamp, wsCcStatsMuSumShortNumPkts, wsCcStatsMuSumShortPktsPerSec100, wsCcStatsMuSumShortPktsPerSecTx100, wsCcStatsMuSumShortPktsPerSecRx100, 
				wsCcStatsMuSumShortThroughput, wsCcStatsMuSumShortThroughputTx, wsCcStatsMuSumShortThroughputRx, wsCcStatsMuSumShortAvgBitSpeed, wsCcStatsMuSumShortAvgMuSignal, 
				wsCcStatsMuSumShortAvgMuNoise, wsCcStatsMuSumShortAvgMuSnr, wsCcStatsMuSumShortPp10kNUcastPkts, wsCcStatsMuSumShortPp10kTxWithRetries, wsCcStatsMuSumShortPp10kDropped, 
				wsCcStatsMuSumShortTxAvgRetries100, wsCcStatsMuSumShortPp10kRxUndecrypt, wsCcStatsMuSumLongTimestamp, wsCcStatsMuSumLongNumPkts, wsCcStatsMuSumLongPktsPerSec100, 
				wsCcStatsMuSumLongPktsPerSecTx100, wsCcStatsMuSumLongPktsPerSecRx100, wsCcStatsMuSumLongThroughput, wsCcStatsMuSumLongThroughputTx, wsCcStatsMuSumLongThroughputRx, 
				wsCcStatsMuSumLongAvgBitSpeed, wsCcStatsMuSumLongAvgMuSignal, wsCcStatsMuSumLongAvgMuNoise, wsCcStatsMuSumLongAvgMuSnr, wsCcStatsMuSumLongPp10kNUcastPkts, 
				wsCcStatsMuSumLongPp10kTxWithRetries, wsCcStatsMuSumLongPp10kDropped, wsCcStatsMuSumLongTxAvgRetries100, wsCcStatsSwitchTxPktsAt11Mb, wsCcStatsSwitchTxPktsAt12Mb, 
				wsCcStatsSwitchTxPktsAt18Mb, wsCcStatsSwitchTxPktsAt22Mb, wsCcStatsSwitchTxRetriesPkts01, wsCcStatsSwitchTxRetriesPkts14, wsCcStatsSwitchTxRetriesPkts15, 
				wsCcStatsSwitchTxRetriesPktsFailed, wsCcStatsSwitchTxRetriesPkts10, wsCcStatsSwitchTxRetriesPkts11, wsCcStatsSwitchTxRetriesPkts12, wsCcStatsSwitchTxRetriesPkts13, 
				wsCcStatsSwitchTxRetriesPkts07, wsCcStatsSwitchTxRetriesPkts08, wsCcStatsSwitchTxRetriesPkts09, wsCcStatsSwitchTxRetriesPkts02, wsCcStatsSwitchTxRetriesPkts03, 
				wsCcStatsSwitchTxRetriesPkts04, wsCcStatsSwitchTxRetriesPkts05, wsCcStatsSwitchTxPktsAt24Mb, wsCcStatsSwitchTxPktsAt36Mb, wsCcStatsSwitchTxPktsAt48Mb, 
				wsCcStatsSwitchTxPktsAt54Mb, wsCcStatsSwitchTxRetriesPktsIndex, wsCcStatsSwitchRxPktsAt48Mb, wsCcStatsSwitchRxPktsAt54Mb, wsCcStatsSwitchTxPktsIndex, 
				wsCcStatsSwitchTxPktsAt1Mb, wsCcStatsSwitchTxPktsAt2Mb, wsCcStatsSwitchTxPktsAt5pt5Mb, wsCcStatsSwitchTxPktsAt6Mb, wsCcStatsSwitchTxPktsAt9Mb, 
				wsCcStatsSwitchRxPktsAt11Mb, wsCcStatsSwitchRxPktsAt12Mb, wsCcStatsSwitchRxPktsAt18Mb, wsCcStatsSwitchRxPktsAt22Mb, wsCcStatsSwitchRxPktsAt24Mb, 
				wsCcStatsSwitchRxPktsAt2Mb, wsCcStatsSwitchRxPktsAt5pt5Mb, wsCcStatsSwitchRxPktsAt6Mb, wsCcStatsSwitchRxPktsAt9Mb, wsCcStatsSwitchRxPktsAt1Mb, 
				wsCcStatsSwitchRxPktsIndex, wsCcStatsMuSignalMostRecent, wsCcStatsMuSigNumPackets, wsCcStatsMuSumLongPp10kRxUndecrypt, wsCcStatsMuMac
				 }
			STATUS current
			DESCRIPTION 
				"Cell Controller Statistics MIB MU Group."
			::= { wsCcStatsMIBGroups 3 }

		
		-- 1.3.6.1.4.1.388.14.3.3.1.100.2.4
		wsCcStatsMIBWlanGroup OBJECT-GROUP
			OBJECTS { wsCcStatsWlanTxPktsUcast, wsCcStatsWlanRxPktsUcast, wsCcStatsWlanRxPktsNUcast, wsCcStatsWlanTxOctetsUcast, wsCcStatsWlanRxOctetsUcast, 
				wsCcStatsWlanRxOctetsNUcast, wsCcStatsWlanRxUndecryptablePkts, wsCcStatsWlanLastActivity, wsCcStatsWlanSumShortTimestamp, wsCcStatsWlanSumShortNumPkts, 
				wsCcStatsWlanSumShortPktsPerSec100, wsCcStatsWlanSumShortPktsPerSecTx100, wsCcStatsWlanSumShortPktsPerSecRx100, wsCcStatsWlanSumShortThroughput, wsCcStatsWlanSumShortThroughputTx, 
				wsCcStatsWlanSumShortThroughputRx, wsCcStatsWlanSumShortAvgBitSpeed, wsCcStatsWlanSumShortAvgMuSignal, wsCcStatsWlanSumShortAvgMuNoise, wsCcStatsWlanSumShortAvgMuSnr, 
				wsCcStatsWlanSumShortPp10kNUcastPkts, wsCcStatsWlanSumShortPp10kTxWithRetries, wsCcStatsWlanSumShortPp10kDropped, wsCcStatsWlanSumShortTxAvgRetries100, wsCcStatsWlanSumShortPp10kRxUndecrypt, 
				wsCcStatsWlanIndex, wsCcStatsConfShortWindow, wsCcStatsWlanSumShortTotalMus, wsCcStatsWlanSumLongTimestamp, wsCcStatsWlanSumLongNumPkts, 
				wsCcStatsWlanSumLongPktsPerSec100, wsCcStatsWlanSumLongPktsPerSecTx100, wsCcStatsWlanSumLongPktsPerSecRx100, wsCcStatsWlanSumLongThroughput, wsCcStatsWlanSumLongThroughputTx, 
				wsCcStatsWlanSumLongThroughputRx, wsCcStatsWlanSumLongAvgBitSpeed, wsCcStatsWlanSumLongAvgMuSignal, wsCcStatsWlanSumLongAvgMuNoise, wsCcStatsWlanSumLongAvgMuSnr, 
				wsCcStatsWlanSumLongPp10kNUcastPkts, wsCcStatsWlanSumLongPp10kTxWithRetries, wsCcStatsWlanSumLongPp10kDropped, wsCcStatsWlanSumLongTxAvgRetries100, wsCcStatsWlanSumLongPp10kRxUndecrypt, 
				wsCcStatsWlanSumLongTotalMus }
			STATUS current
			DESCRIPTION 
				"Cell Controller Statistics MIB WLAN Group."
			::= { wsCcStatsMIBGroups 4 }

		
		-- 1.3.6.1.4.1.388.14.3.3.1.100.2.5
		wsCcStatsMIBTrapCtrlConfGroup OBJECT-GROUP
			OBJECTS { wsCcStatsTrapCtrlConfIndex, wsCcStatsTrapCtrlConfDescr, wsCcStatsTrapCtrlConfUnits, wsCcStatsTrapCtrlConfCanBeSetMu, wsCcStatsTrapCtrlConfThresholdMus, 
				wsCcStatsTrapCtrlConfCanBeSetPortal, wsCcStatsTrapCtrlConfThresholdPortals, wsCcStatsTrapCtrlConfCanBeSetWlan, wsCcStatsTrapCtrlConfThresholdWlans, wsCcStatsTrapCtrlConfCanBeSetSwitch, 
				wsCcStatsTrapCtrlConfThresholdSwitch, wsCcStatsTrapCtrlConfMinPktsForTrap }
			STATUS current
			DESCRIPTION 
				"Cell Controller Statistics MIB Trap Control Configuration Group."
			::= { wsCcStatsMIBGroups 5 }

		
		-- 1.3.6.1.4.1.388.14.3.3.1.100.2.6
		wsCcStatsMIBDeprecateGroup OBJECT-GROUP
			OBJECTS { wsCcStatsRadioRxPktsAt1Mb, wsCcStatsRadioRxPktsAt2Mb, wsCcStatsRadioRxPktsAt5pt5Mb, wsCcStatsRadioRxPktsAt6Mb, wsCcStatsRadioRxPktsAt9Mb, 
				wsCcStatsRadioRxPktsAt11Mb, wsCcStatsRadioRxPktsAt12Mb, wsCcStatsRadioRxPktsAt18Mb, wsCcStatsRadioRxPktsAt22Mb, wsCcStatsRadioRxPktsAt24Mb, 
				wsCcStatsRadioRxPktsAt36Mb, wsCcStatsRadioRxPktsAt48Mb, wsCcStatsRadioRxPktsAt54Mb, wsCcStatsRadioTxPktsAt1Mb, wsCcStatsRadioTxPktsAt2Mb, 
				wsCcStatsRadioTxPktsAt5pt5Mb, wsCcStatsRadioTxPktsAt6Mb, wsCcStatsRadioTxPktsAt9Mb, wsCcStatsRadioTxPktsAt11Mb, wsCcStatsRadioTxPktsAt12Mb, 
				wsCcStatsRadioTxPktsAt18Mb, wsCcStatsRadioTxPktsAt22Mb, wsCcStatsRadioTxPktsAt24Mb, wsCcStatsRadioTxPktsAt36Mb, wsCcStatsRadioTxPktsAt48Mb, 
				wsCcStatsRadioTxPktsAt54Mb, wsCcStatsRadioRxOctetsAt1Mb, wsCcStatsRadioRxOctetsAt2Mb, wsCcStatsRadioRxOctetsAt5pt5Mb, wsCcStatsRadioRxOctetsAt6Mb, 
				wsCcStatsRadioRxOctetsAt9Mb, wsCcStatsRadioRxOctetsAt11Mb, wsCcStatsRadioRxOctetsAt12Mb, wsCcStatsRadioRxOctetsAt18Mb, wsCcStatsRadioRxOctetsAt22Mb, 
				wsCcStatsRadioRxOctetsAt24Mb, wsCcStatsRadioRxOctetsAt36Mb, wsCcStatsRadioRxOctetsAt48Mb, wsCcStatsRadioRxOctetsAt54Mb, wsCcStatsRadioTxOctetsAt1Mb, 
				wsCcStatsRadioTxOctetsAt2Mb, wsCcStatsRadioTxOctetsAt5pt5Mb, wsCcStatsRadioTxOctetsAt6Mb, wsCcStatsRadioTxOctetsAt9Mb, wsCcStatsRadioTxOctetsAt11Mb, 
				wsCcStatsRadioTxOctetsAt12Mb, wsCcStatsRadioTxOctetsAt18Mb, wsCcStatsRadioTxOctetsAt22Mb, wsCcStatsRadioTxOctetsAt24Mb, wsCcStatsRadioTxOctetsAt36Mb, 
				wsCcStatsRadioTxOctetsAt48Mb, wsCcStatsRadioTxOctetsAt54Mb, wsCcStatsRadioTxRetriesPktsNone, wsCcStatsRadioTxRetriesPkts01, wsCcStatsRadioTxRetriesPkts02, 
				wsCcStatsRadioTxRetriesPkts03, wsCcStatsRadioTxRetriesPkts04, wsCcStatsRadioTxRetriesPkts05, wsCcStatsRadioTxRetriesPkts06, wsCcStatsRadioTxRetriesPkts07, 
				wsCcStatsRadioTxRetriesPkts08, wsCcStatsRadioTxRetriesPkts09, wsCcStatsRadioTxRetriesPkts10, wsCcStatsRadioTxRetriesPkts11, wsCcStatsRadioTxRetriesPkts12, 
				wsCcStatsRadioTxRetriesPkts13, wsCcStatsRadioTxRetriesPkts14, wsCcStatsRadioTxRetriesPkts15, wsCcStatsRadioTxRetriesPktsFailed, wsCcStatsRadioTxRetriesOctetsNone, 
				wsCcStatsRadioTxRetriesOctets01, wsCcStatsRadioTxRetriesOctets02, wsCcStatsRadioTxRetriesOctets03, wsCcStatsRadioTxRetriesOctets04, wsCcStatsRadioTxRetriesOctets05, 
				wsCcStatsRadioTxRetriesOctets06, wsCcStatsRadioTxRetriesOctets07, wsCcStatsRadioTxRetriesOctets08, wsCcStatsRadioTxRetriesOctets09, wsCcStatsRadioTxRetriesOctets10, 
				wsCcStatsRadioTxRetriesOctets11, wsCcStatsRadioTxRetriesOctets12, wsCcStatsRadioTxRetriesOctets13, wsCcStatsRadioTxRetriesOctets14, wsCcStatsRadioTxRetriesOctets15, 
				wsCcStatsRadioTxRetriesOctetsFailed, wsCcStatsRadioSigNumPkts, wsCcStatsRadioSigSignalBest, wsCcStatsRadioSigSignalWorst, wsCcStatsRadioSigSignalSum, 
				wsCcStatsRadioSigSignalSumSquares, wsCcStatsRadioSigSignalMostRecent, wsCcStatsRadioSigNoiseBest, wsCcStatsRadioSigNoiseWorst, wsCcStatsRadioSigNoiseSum, 
				wsCcStatsRadioSigNoiseSumSquares, wsCcStatsRadioSigNoiseMostRecent, wsCcStatsRadioSigSnrBest, wsCcStatsRadioSigSnrWorst, wsCcStatsRadioSigSnrSum, 
				wsCcStatsRadioSigSnrSumSquares, wsCcStatsRadioSigSnrMostRecent, wsCcStatsRadioSysBeaconsTx, wsCcStatsRadioSysBeaconsTxOctets, wsCcStatsRadioSysProbeReqRx, 
				wsCcStatsRadioSysProbeReqRxOctets, wsCcStatsRadioSysProbeRespRetriesNone, wsCcStatsRadioSysProbeRespRetries1, wsCcStatsRadioSysProbeRespRetries2, wsCcStatsRadioSysProbeRespRetries3OrMore, 
				wsCcStatsRadioSysProbeRespRetriesFailed, wsCcStatsRadioSysProbeRespTxOctets, wsCcStatsMuRxPktsAt1Mb, wsCcStatsMuRxPktsAt2Mb, wsCcStatsMuRxPktsAt5pt5Mb, 
				wsCcStatsMuRxPktsAt6Mb, wsCcStatsMuRxPktsAt9Mb, wsCcStatsMuRxPktsAt11Mb, wsCcStatsMuRxPktsAt12Mb, wsCcStatsMuRxPktsAt18Mb, 
				wsCcStatsMuRxPktsAt22Mb, wsCcStatsMuRxPktsAt24Mb, wsCcStatsMuRxPktsAt36Mb, wsCcStatsMuRxPktsAt48Mb, wsCcStatsMuRxPktsAt54Mb, 
				wsCcStatsMuTxPktsAt1Mb, wsCcStatsMuTxPktsAt2Mb, wsCcStatsMuTxPktsAt5pt5Mb, wsCcStatsMuTxPktsAt6Mb, wsCcStatsMuTxPktsAt9Mb, 
				wsCcStatsMuTxPktsAt11Mb, wsCcStatsMuTxPktsAt12Mb, wsCcStatsMuTxPktsAt18Mb, wsCcStatsMuTxPktsAt22Mb, wsCcStatsMuTxPktsAt24Mb, 
				wsCcStatsMuTxPktsAt36Mb, wsCcStatsMuTxPktsAt48Mb, wsCcStatsMuTxPktsAt54Mb, wsCcStatsMuRxOctetsAt1Mb, wsCcStatsMuRxOctetsAt2Mb, 
				wsCcStatsMuRxOctetsAt5pt5Mb, wsCcStatsMuRxOctetsAt6Mb, wsCcStatsMuRxOctetsAt9Mb, wsCcStatsMuRxOctetsAt11Mb, wsCcStatsMuRxOctetsAt12Mb, 
				wsCcStatsMuRxOctetsAt18Mb, wsCcStatsMuRxOctetsAt22Mb, wsCcStatsMuRxOctetsAt24Mb, wsCcStatsMuRxOctetsAt36Mb, wsCcStatsMuRxOctetsAt48Mb, 
				wsCcStatsMuRxOctetsAt54Mb, wsCcStatsMuTxOctetsAt1Mb, wsCcStatsMuTxOctetsAt2Mb, wsCcStatsMuTxOctetsAt5pt5Mb, wsCcStatsMuTxOctetsAt6Mb, 
				wsCcStatsMuTxOctetsAt9Mb, wsCcStatsMuTxOctetsAt11Mb, wsCcStatsMuTxOctetsAt12Mb, wsCcStatsMuTxOctetsAt18Mb, wsCcStatsMuTxOctetsAt22Mb, 
				wsCcStatsMuTxOctetsAt24Mb, wsCcStatsMuTxOctetsAt36Mb, wsCcStatsMuTxOctetsAt48Mb, wsCcStatsMuTxOctetsAt54Mb, wsCcStatsMuTxRetriesNone, 
				wsCcStatsMuTxRetries01, wsCcStatsMuTxRetries02, wsCcStatsMuTxRetries03, wsCcStatsMuTxRetries04, wsCcStatsMuTxRetries05, 
				wsCcStatsMuTxRetries06, wsCcStatsMuTxRetries07, wsCcStatsMuTxRetries08, wsCcStatsMuTxRetries09, wsCcStatsMuTxRetries10, 
				wsCcStatsMuTxRetries11, wsCcStatsMuTxRetries12, wsCcStatsMuTxRetries13, wsCcStatsMuTxRetries14, wsCcStatsMuTxRetries15, 
				wsCcStatsMuTxRetriesFailed, wsCcStatsMuTxRetriesTotal, wsCcStatsMuTxRetriesMostRecent, wsCcStatsMuTxRetriesOctetsNone, wsCcStatsMuTxRetriesOctets01, 
				wsCcStatsMuTxRetriesOctets02, wsCcStatsMuTxRetriesOctets03, wsCcStatsMuTxRetriesOctets04, wsCcStatsMuTxRetriesOctets05, wsCcStatsMuTxRetriesOctets06, 
				wsCcStatsMuTxRetriesOctets07, wsCcStatsMuTxRetriesOctets08, wsCcStatsMuTxRetriesOctets09, wsCcStatsMuTxRetriesOctets10, wsCcStatsMuTxRetriesOctets11, 
				wsCcStatsMuTxRetriesOctets12, wsCcStatsMuTxRetriesOctets13, wsCcStatsMuTxRetriesOctets14, wsCcStatsMuTxRetriesOctets15, wsCcStatsMuTxRetriesOctetsFailed, 
				wsCcStatsMuSigNumPkts, wsCcStatsMuSigSignalBest, wsCcStatsMuSigSignalWorst, wsCcStatsMuSigSignalSum, wsCcStatsMuSigSignalSumSquares, 
				wsCcStatsMuSigSignalMostRecent, wsCcStatsMuSigNoiseBest, wsCcStatsMuSigNoiseWorst, wsCcStatsMuSigNoiseSum, wsCcStatsMuSigStatsNoiseSumSquares, 
				wsCcStatsMuSigNoiseMostRecent, wsCcStatsMuSigSnrBest, wsCcStatsMuSigSnrWorst, wsCcStatsMuSigSnrSum, wsCcStatsMuSigSnrSumSquares, 
				wsCcStatsMuSigSnrMostRecent, wsCcStatsWlanRxPktsAt1Mb, wsCcStatsWlanRxPktsAt2Mb, wsCcStatsWlanRxPktsAt5pt5Mb, wsCcStatsWlanRxPktsAt6Mb, 
				wsCcStatsWlanRxPktsAt9Mb, wsCcStatsWlanRxPktsAt11Mb, wsCcStatsWlanRxPktsAt12Mb, wsCcStatsWlanRxPktsAt18Mb, wsCcStatsWlanRxPktsAt22Mb, 
				wsCcStatsWlanRxPktsAt24Mb, wsCcStatsWlanRxPktsAt36Mb, wsCcStatsWlanRxPktsAt48Mb, wsCcStatsWlanRxPktsAt54Mb, wsCcStatsWlanTxPktsAt1Mb, 
				wsCcStatsWlanTxPktsAt2Mb, wsCcStatsWlanTxPktsAt5pt5Mb, wsCcStatsWlanTxPktsAt6Mb, wsCcStatsWlanTxPktsAt9Mb, wsCcStatsWlanTxPktsAt11Mb, 
				wsCcStatsWlanTxPktsAt12Mb, wsCcStatsWlanTxPktsAt18Mb, wsCcStatsWlanTxPktsAt22Mb, wsCcStatsWlanTxPktsAt24Mb, wsCcStatsWlanTxPktsAt36Mb, 
				wsCcStatsWlanTxPktsAt48Mb, wsCcStatsWlanTxPktsAt54Mb, wsCcStatsWlanRxOctetsAt1Mb, wsCcStatsWlanRxOctetsAt2Mb, wsCcStatsWlanRxOctetsAt5pt5Mb, 
				wsCcStatsWlanRxOctetsAt6Mb, wsCcStatsWlanRxOctetsAt9Mb, wsCcStatsWlanRxOctetsAt11Mb, wsCcStatsWlanRxOctetsAt12Mb, wsCcStatsWlanRxOctetsAt18Mb, 
				wsCcStatsWlanRxOctetsAt22Mb, wsCcStatsWlanRxOctetsAt24Mb, wsCcStatsWlanRxOctetsAt36Mb, wsCcStatsWlanRxOctetsAt48Mb, wsCcStatsWlanRxOctetsAt54Mb, 
				wsCcStatsWlanTxOctetsAt1Mb, wsCcStatsWlanTxOctetsAt2Mb, wsCcStatsWlanTxOctetsAt5pt5Mb, wsCcStatsWlanTxOctetsAt6Mb, wsCcStatsWlanTxOctetsAt9Mb, 
				wsCcStatsWlanTxOctetsAt11Mb, wsCcStatsWlanTxOctetsAt12Mb, wsCcStatsWlanTxOctetsAt18Mb, wsCcStatsWlanTxOctetsAt22Mb, wsCcStatsWlanTxOctetsAt24Mb, 
				wsCcStatsWlanTxOctetsAt36Mb, wsCcStatsWlanTxOctetsAt48Mb, wsCcStatsWlanTxOctetsAt54Mb, wsCcStatsWlanTxRetriesPktsNone, wsCcStatsWlanTxRetriesPkts01, 
				wsCcStatsWlanTxRetriesPkts02, wsCcStatsWlanTxRetriesPkts03, wsCcStatsWlanTxRetriesPkts04, wsCcStatsWlanTxRetriesPkts05, wsCcStatsWlanTxRetriesPkts06, 
				wsCcStatsWlanTxRetriesPkts07, wsCcStatsWlanTxRetriesPkts08, wsCcStatsWlanTxRetriesPkts09, wsCcStatsWlanTxRetriesPkts10, wsCcStatsWlanTxRetriesPkts11, 
				wsCcStatsWlanTxRetriesPkts12, wsCcStatsWlanTxRetriesPkts13, wsCcStatsWlanTxRetriesPkts14, wsCcStatsWlanTxRetriesPkts15, wsCcStatsWlanTxRetriesPktsFailed, 
				wsCcStatsWlanTxRetriesOctetsNone, wsCcStatsWlanTxRetriesOctets01, wsCcStatsWlanTxRetriesOctets02, wsCcStatsWlanTxRetriesOctets03, wsCcStatsWlanTxRetriesOctets04, 
				wsCcStatsWlanTxRetriesOctets05, wsCcStatsWlanTxRetriesOctets06, wsCcStatsWlanTxRetriesOctets07, wsCcStatsWlanTxRetriesOctets08, wsCcStatsWlanTxRetriesOctets09, 
				wsCcStatsWlanTxRetriesOctets10, wsCcStatsWlanTxRetriesOctets11, wsCcStatsWlanTxRetriesOctets12, wsCcStatsWlanTxRetriesOctets13, wsCcStatsWlanTxRetriesOctets14, 
				wsCcStatsWlanTxRetriesOctets15, wsCcStatsWlanTxRetriesOctetsFailed, wsCcStatsWlanSigStatsNumPkts, wsCcStatsWlanSigStatsSignalBest, wsCcStatsWlanSigStatsSignalWorst, 
				wsCcStatsWlanSigStatsSignalSum, wsCcStatsWlanSigStatsSignalSumSquares, wsCcStatsWlanSigStatsNoiseBest, wsCcStatsWlanSigStatsNoiseWorst, wsCcStatsWlanSigNoiseSum, 
				wsCcStatsWlanSigNoiseSumSquares, wsCcStatsWlanSigSnrBest, wsCcStatsWlanSigSnrWorst, wsCcStatsWlanSigSnrSum, wsCcStatsWlanSigSnrSumSquares
				 }
			STATUS deprecated
			DESCRIPTION 
				"Description."
			::= { wsCcStatsMIBGroups 6 }

		
		-- 1.3.6.1.4.1.388.14.3.3.1.100.2.7
		wsCcStatsMIBMeshGroup OBJECT-GROUP
			OBJECTS { wsCcStatsMeshIndex, wsCcStatsMeshSumShortTimestamp, wsCcStatsMeshSumShortNumPkts, wsCcStatsMeshSumShortPktsPerSec100, wsCcStatsMeshSumShortPktsPerSecTx100, 
				wsCcStatsMeshSumShortPktsPerSecRx100, wsCcStatsMeshSumShortThroughput, wsCcStatsMeshSumShortThroughputTx, wsCcStatsMeshSumShortThroughputRx, wsCcStatsMeshSumShortAvgBitSpeed, 
				wsCcStatsMeshSumShortAvgMuSignal, wsCcStatsMeshSumShortAvgMuNoise, wsCcStatsMeshSumShortAvgMuSnr, wsCcStatsMeshSumShortPp10kTxWithRetries, wsCcStatsMeshSumShortPp10kDropped, 
				wsCcStatsMeshSumShortTxAvgRetries100, wsCcStatsMeshSumShortPp10kRxUndecrypt, wsCcStatsMeshSumLongTimestamp, wsCcStatsMeshSumLongNumPkts, wsCcStatsMeshSumLongPktsPerSec100, 
				wsCcStatsMeshSumLongPktsPerSecTx100, wsCcStatsMeshSumLongPktsPerSecRx100, wsCcStatsMeshSumLongThroughput, wsCcStatsMeshSumLongThroughputTx, wsCcStatsMeshSumLongThroughputRx, 
				wsCcStatsMeshSumLongAvgBitSpeed, wsCcStatsMeshSumLongAvgMuSignal, wsCcStatsMeshSumLongAvgMuNoise, wsCcStatsMeshSumLongAvgMuSnr, wsCcStatsMeshSumLongPp10kTxWithRetries, 
				wsCcStatsMeshSumLongPp10kDropped, wsCcStatsMeshSumLongTxAvgRetries100, wsCcStatsMeshWlanEssid, wsCcStatsMeshSumLongPp10kRxUndecrypt, wsCcStatsMeshConnType, 
				wsCcStatsMeshMac, wsCcStatsMeshRadioType, wsCcStatsMeshThroughput, wsCcStatsMeshRetries100, wsCcStatsMeshAvgBitSpeed, wsCcStatsMeshRadioIndex
				 }
			STATUS current
			DESCRIPTION 
				"Cell Controller Statistics MIB Mesh Group."
			::= { wsCcStatsMIBGroups 7 }

		
	
	END

--
-- WS-CC-STATS-MIB.my
--
