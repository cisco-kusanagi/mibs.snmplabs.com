--			Ascend mibvoip MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBVOIP-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibvoipProfile  OBJECT IDENTIFIER ::= { configuration 138}

	-- The mibvoipProfile table
	--
	-- This table contains parameters for the mibvoipProfile profile
	--

    mibvoipProfileTable	OBJECT-TYPE
	SYNTAX		SEQUENCE OF MibvoipProfileEntry
	ACCESS		not-accessible
	STATUS		mandatory
	DESCRIPTION	"A list of mibvoipProfile profile entries."
	::= { mibvoipProfile 1 }

    mibvoipProfileEntry	OBJECT-TYPE
	SYNTAX		MibvoipProfileEntry
	ACCESS		not-accessible
	STATUS		mandatory
	DESCRIPTION	"A mibvoipProfile entry containing objects that
			 maps to the parameters of mibvoipProfile profile."
	INDEX		{ voipProfile-VoipIndex-GatewayAccessNumber, voipProfile-VoipIndex-FarEndNumber }
	::= { mibvoipProfileTable 1 }

    MibvoipProfileEntry ::=
	SEQUENCE {
	    voipProfile-VoipIndex-GatewayAccessNumber
		DisplayString,
	    voipProfile-VoipIndex-FarEndNumber
		DisplayString,
	    voipProfile-GatekeeperIp
		IpAddress,
	    voipProfile-GkMlgControl
		INTEGER,
	    voipProfile-VpnMode
		INTEGER,
	    voipProfile-SingleDialEnable
		INTEGER,
	    voipProfile-PacketAudioMode
		INTEGER,
	    voipProfile-FramesPerPacket
		INTEGER,
	    voipProfile-TosOptions-Active
		INTEGER,
	    voipProfile-TosOptions-Precedence
		INTEGER,
	    voipProfile-TosOptions-TypeOfService
		INTEGER,
	    voipProfile-TosOptions-ApplyTo
		INTEGER,
	    voipProfile-TosOptions-MarkingType
		INTEGER,
	    voipProfile-TosOptions-Dscp
		DisplayString,
	    voipProfile-SilenceDetCng
		INTEGER,
	    voipProfile-GatekeeperIpSec
		IpAddress,
	    voipProfile-GatekeeperKeepalive
		INTEGER,
	    voipProfile-RegistrationRetries
		INTEGER,
	    voipProfile-RegistrationRetryTimer
		INTEGER,
	    voipProfile-PrimaryRetries
		INTEGER,
	    voipProfile-PinDnisRetries
		INTEGER,
	    voipProfile-MlgPinRetries
		INTEGER,
	    voipProfile-MlgDnisRetries
		INTEGER,
	    voipProfile-EnaAdapJitterBuffer
		INTEGER,
	    voipProfile-MaxJitterBufferSize
		INTEGER,
	    voipProfile-InitialJitterBufferSize
		INTEGER,
	    voipProfile-Maxcalls
		INTEGER,
	    voipProfile-CutThruEnableNearend
		INTEGER,
	    voipProfile-H323VoiceAnnEnabled
		INTEGER,
	    voipProfile-VoiceAnnDir
		DisplayString,
	    voipProfile-VoiceAnnEnc
		INTEGER,
	    voipProfile-CallInterDigitTimeout
		INTEGER,
	    voipProfile-SilenceThreshold
		INTEGER,
	    voipProfile-DtmfTonePassing
		INTEGER,
	    voipProfile-VoiceAnnServIp
		IpAddress,
	    voipProfile-VoiceAnnFileSpec
		DisplayString,
	    voipProfile-RtFaxOptions-RtFaxEnable
		INTEGER,
	    voipProfile-RtFaxOptions-EcmEnable
		INTEGER,
	    voipProfile-RtFaxOptions-LowLatencyMode
		INTEGER,
	    voipProfile-RtFaxOptions-CommandSpoof
		INTEGER,
	    voipProfile-RtFaxOptions-LocalRetransmitLsf
		INTEGER,
	    voipProfile-RtFaxOptions-PacketRedundancy
		INTEGER,
	    voipProfile-RtFaxOptions-FixedPackets
		INTEGER,
	    voipProfile-RtFaxOptions-MaxDataRate
		INTEGER,
	    voipProfile-RtFaxOptions-AllowCtc
		INTEGER,
	    voipProfile-CallHairpin
		INTEGER,
	    voipProfile-CallKeepAliveTimeout
		INTEGER,
	    voipProfile-ClidSuppress
		INTEGER,
	    voipProfile-TrueConnectEnable
		INTEGER,
	    voipProfile-G711TransparentData
		INTEGER,
	    voipProfile-AllowG711Fallback
		INTEGER,
	    voipProfile-AllowCoderFallback
		INTEGER,
	    voipProfile-ChooseDspVia
		INTEGER,
	    voipProfile-TrunkQuiesceEnable
		INTEGER,
	    voipProfile-EarlyRingbackEnable
		INTEGER,
	    voipProfile-TrunkPrefixEnable
		INTEGER,
	    voipProfile-SignalingModel
		INTEGER,
	    voipProfile-OperatorAssist
		DisplayString,
	    voipProfile-PstnAttribute-CauseCodeTransparency
		INTEGER,
	    voipProfile-PstnAttribute-AlertProgressIndicator
		INTEGER,
	    voipProfile-PstnAttribute-ProceedProgressIndicator
		INTEGER,
	    voipProfile-PstnAttribute-BearerCapability
		INTEGER,
	    voipProfile-SequentialCallEnable
		INTEGER,
	    voipProfile-Ss7voipCallPersistence
		INTEGER,
	    voipProfile-NextCall
		DisplayString,
	    voipProfile-RtpqosPollingEnable
		INTEGER,
	    voipProfile-FaststartEnable
		INTEGER,
	    voipProfile-SignalingTos-Active
		INTEGER,
	    voipProfile-SignalingTos-Precedence
		INTEGER,
	    voipProfile-SignalingTos-TypeOfService
		INTEGER,
	    voipProfile-SignalingTos-ApplyTo
		INTEGER,
	    voipProfile-SignalingTos-MarkingType
		INTEGER,
	    voipProfile-SignalingTos-Dscp
		DisplayString,
	    voipProfile-Action-o
		INTEGER
	}

    voipProfile-VoipIndex-GatewayAccessNumber	OBJECT-TYPE
	SYNTAX	DisplayString
	ACCESS	read-only
	STATUS	mandatory
	DESCRIPTION	"The access number for the gateway. Set to `0' for the VOIP default profile."
	::= { mibvoipProfileEntry 1 }

    voipProfile-VoipIndex-FarEndNumber	OBJECT-TYPE
	SYNTAX	DisplayString
	ACCESS	read-only
	STATUS	mandatory
	DESCRIPTION	"The phone number of the far end device to be called. Set to `0' to indicate a default profile for either the system or a particular gateway."
	::= { mibvoipProfileEntry 2 }

    voipProfile-GatekeeperIp	OBJECT-TYPE
	SYNTAX	IpAddress
	ACCESS	read-write
	STATUS	mandatory
	DESCRIPTION	"IP address for the GateKeeper."
	::= { mibvoipProfileEntry 3 }

    voipProfile-GkMlgControl	OBJECT-TYPE
	SYNTAX	INTEGER {
		    no (1),
		    yes (2)
		}
	ACCESS	read-write
	STATUS	mandatory
	DESCRIPTION	"Gatekeeper Multiple-Logical-Gateway control."
	::= { mibvoipProfileEntry 4 }

    voipProfile-VpnMode	OBJECT-TYPE
	SYNTAX	INTEGER {
		    no (1),
		    yes (2)
		}
	ACCESS	read-write
	STATUS	mandatory
	DESCRIPTION	"Virtual Private Network Toggle Switch."
	::= { mibvoipProfileEntry 5 }

    voipProfile-SingleDialEnable	OBJECT-TYPE
	SYNTAX	INTEGER {
		    no (1),
		    yes (2)
		}
	ACCESS	read-write
	STATUS	mandatory
	DESCRIPTION	"Enable Single Stage Dialing"
	::= { mibvoipProfileEntry 6 }

    voipProfile-PacketAudioMode	OBJECT-TYPE
	SYNTAX	INTEGER {
		    g711Ulaw (1),
		    g711Alaw (2),
		    g723 (3),
		    g729 (4),
		    g72364kps (5),
		    rt24 (6),
		    g728 (7),
		    frgsm (8),
		    evrc (9)
		}
	ACCESS	read-write
	STATUS	mandatory
	DESCRIPTION	"Audio Coder to be used for voice packetization."
	::= { mibvoipProfileEntry 7 }

    voipProfile-FramesPerPacket	OBJECT-TYPE
	SYNTAX	INTEGER
	ACCESS	read-write
	STATUS	mandatory
	DESCRIPTION	"Voice Frames Per RTP Packet. One (1) through ten (10) are valid values but should be at least two (2) if packet audio mode was set to one of the flavors of G.711."
	::= { mibvoipProfileEntry 8 }

    voipProfile-TosOptions-Active	OBJECT-TYPE
	SYNTAX	INTEGER {
		    no (1),
		    yes (2)
		}
	ACCESS	read-write
	STATUS	mandatory
	DESCRIPTION	"Activate type of service for this connection."
	::= { mibvoipProfileEntry 9 }

    voipProfile-TosOptions-Precedence	OBJECT-TYPE
	SYNTAX	INTEGER {
		    n-000 (1),
		    n-001 (33),
		    n-010 (65),
		    n-011 (97),
		    n-100 (129),
		    n-101 (161),
		    n-110 (193),
		    n-111 (225)
		}
	ACCESS	read-write
	STATUS	mandatory
	DESCRIPTION	"Tag the precedence bits (priority bits) in the TOS octet of IP datagram header with this value when match occurs."
	::= { mibvoipProfileEntry 10 }

    voipProfile-TosOptions-TypeOfService	OBJECT-TYPE
	SYNTAX	INTEGER {
		    normal (1),
		    cost (3),
		    reliability (5),
		    throughput (9),
		    latency (17)
		}
	ACCESS	read-write
	STATUS	mandatory
	DESCRIPTION	"Tag the type of service field in the TOS octet of IP datagram header with this value when match occurs."
	::= { mibvoipProfileEntry 11 }

    voipProfile-TosOptions-ApplyTo	OBJECT-TYPE
	SYNTAX	INTEGER {
		    incoming (1025),
		    outgoing (2049),
		    both (3073)
		}
	ACCESS	read-write
	STATUS	mandatory
	DESCRIPTION	"Define how the type-of-service applies to data flow for this connection."
	::= { mibvoipProfileEntry 12 }

    voipProfile-TosOptions-MarkingType	OBJECT-TYPE
	SYNTAX	INTEGER {
		    precedenceTos (1),
		    dscp (2)
		}
	ACCESS	read-write
	STATUS	mandatory
	DESCRIPTION	"Select type of packet marking."
	::= { mibvoipProfileEntry 60 }

    voipProfile-TosOptions-Dscp	OBJECT-TYPE
	SYNTAX	DisplayString
	ACCESS	read-write
	STATUS	mandatory
	DESCRIPTION	"DSCP tag to be used in marking of the packets (if marking-type = dscp)."
	::= { mibvoipProfileEntry 61 }

    voipProfile-SilenceDetCng	OBJECT-TYPE
	SYNTAX	INTEGER {
		    no (1),
		    yes (2),
		    cngOnly (3)
		}
	ACCESS	read-write
	STATUS	mandatory
	DESCRIPTION	"Silence Detection and Comfort Noise Generation selection."
	::= { mibvoipProfileEntry 13 }

    voipProfile-GatekeeperIpSec	OBJECT-TYPE
	SYNTAX	IpAddress
	ACCESS	read-write
	STATUS	mandatory
	DESCRIPTION	"IP address for the Secondary GateKeeper."
	::= { mibvoipProfileEntry 14 }

    voipProfile-GatekeeperKeepalive	OBJECT-TYPE
	SYNTAX	INTEGER
	ACCESS	read-write
	STATUS	mandatory
	DESCRIPTION	"Registration Keepalive."
	::= { mibvoipProfileEntry 15 }

    voipProfile-RegistrationRetries	OBJECT-TYPE
	SYNTAX	INTEGER
	ACCESS	read-write
	STATUS	mandatory
	DESCRIPTION	"Registration Retries."
	::= { mibvoipProfileEntry 16 }

    voipProfile-RegistrationRetryTimer	OBJECT-TYPE
	SYNTAX	INTEGER
	ACCESS	read-write
	STATUS	mandatory
	DESCRIPTION	"Registration Retry Timer."
	::= { mibvoipProfileEntry 17 }

    voipProfile-PrimaryRetries	OBJECT-TYPE
	SYNTAX	INTEGER
	ACCESS	read-write
	STATUS	mandatory
	DESCRIPTION	"Primary Retries."
	::= { mibvoipProfileEntry 18 }

    voipProfile-PinDnisRetries	OBJECT-TYPE
	SYNTAX	INTEGER
	ACCESS	read-write
	STATUS	mandatory
	DESCRIPTION	"Pin/Dnis Retries"
	::= { mibvoipProfileEntry 62 }

    voipProfile-MlgPinRetries	OBJECT-TYPE
	SYNTAX	INTEGER
	ACCESS	read-write
	STATUS	mandatory
	DESCRIPTION	"MLG Pin Retries"
	::= { mibvoipProfileEntry 63 }

    voipProfile-MlgDnisRetries	OBJECT-TYPE
	SYNTAX	INTEGER
	ACCESS	read-write
	STATUS	mandatory
	DESCRIPTION	"MLG Dnis Retries"
	::= { mibvoipProfileEntry 64 }

    voipProfile-EnaAdapJitterBuffer	OBJECT-TYPE
	SYNTAX	INTEGER {
		    no (1),
		    yes (2)
		}
	ACCESS	read-write
	STATUS	mandatory
	DESCRIPTION	"Enable Adaptive Jtr Buf"
	::= { mibvoipProfileEntry 19 }

    voipProfile-MaxJitterBufferSize	OBJECT-TYPE
	SYNTAX	INTEGER
	ACCESS	read-write
	STATUS	mandatory
	DESCRIPTION	"Max Jtr Buf Size"
	::= { mibvoipProfileEntry 20 }

    voipProfile-InitialJitterBufferSize	OBJECT-TYPE
	SYNTAX	INTEGER
	ACCESS	read-write
	STATUS	mandatory
	DESCRIPTION	"Initial Jtr Buf Size"
	::= { mibvoipProfileEntry 21 }

    voipProfile-Maxcalls	OBJECT-TYPE
	SYNTAX	INTEGER
	ACCESS	read-write
	STATUS	mandatory
	DESCRIPTION	"Maximum Voip Calls"
	::= { mibvoipProfileEntry 22 }

    voipProfile-CutThruEnableNearend	OBJECT-TYPE
	SYNTAX	INTEGER {
		    no (1),
		    yes (2)
		}
	ACCESS	read-write
	STATUS	mandatory
	DESCRIPTION	"Enable Near End Cut Through"
	::= { mibvoipProfileEntry 23 }

    voipProfile-H323VoiceAnnEnabled	OBJECT-TYPE
	SYNTAX	INTEGER {
		    no (1),
		    yes (2)
		}
	ACCESS	read-write
	STATUS	mandatory
	DESCRIPTION	"Enable Voice Announcements For H.323 VOIP calls"
	::= { mibvoipProfileEntry 24 }

    voipProfile-VoiceAnnDir	OBJECT-TYPE
	SYNTAX	DisplayString
	ACCESS	read-write
	STATUS	mandatory
	DESCRIPTION	"Pc Flash Card Voice Announcement Directory"
	::= { mibvoipProfileEntry 25 }

    voipProfile-VoiceAnnEnc	OBJECT-TYPE
	SYNTAX	INTEGER {
		    g711Ulaw (1),
		    g729 (4)
		}
	ACCESS	read-write
	STATUS	mandatory
	DESCRIPTION	"Voice announcement file encoding"
	::= { mibvoipProfileEntry 26 }

    voipProfile-CallInterDigitTimeout	OBJECT-TYPE
	SYNTAX	INTEGER
	ACCESS	read-write
	STATUS	mandatory
	DESCRIPTION	"Inter Digit Timeout"
	::= { mibvoipProfileEntry 27 }

    voipProfile-SilenceThreshold	OBJECT-TYPE
	SYNTAX	INTEGER
	ACCESS	read-write
	STATUS	mandatory
	DESCRIPTION	"Silence Thresh (dB inc)"
	::= { mibvoipProfileEntry 28 }

    voipProfile-DtmfTonePassing	OBJECT-TYPE
	SYNTAX	INTEGER {
		    dtmfTonePassedInband (1),
		    dtmfTonePassedOutofband (2),
		    rfc2833 (3)
		}
	ACCESS	read-write
	STATUS	mandatory
	DESCRIPTION	"DTMF Tone Passing"
	::= { mibvoipProfileEntry 29 }

    voipProfile-VoiceAnnServIp	OBJECT-TYPE
	SYNTAX	IpAddress
	ACCESS	read-write
	STATUS	mandatory
	DESCRIPTION	"IP address for Voice Announcement Server if not using Filesystem"
	::= { mibvoipProfileEntry 30 }

    voipProfile-VoiceAnnFileSpec	OBJECT-TYPE
	SYNTAX	DisplayString
	ACCESS	read-write
	STATUS	mandatory
	DESCRIPTION	"If not using filesystem, voice ann specification file to tftp from server "
	::= { mibvoipProfileEntry 31 }

    voipProfile-RtFaxOptions-RtFaxEnable	OBJECT-TYPE
	SYNTAX	INTEGER {
		    no (1),
		    yes (2)
		}
	ACCESS	read-write
	STATUS	mandatory
	DESCRIPTION	"Enable/Disable the Real-Time Fax Feature."
	::= { mibvoipProfileEntry 32 }

    voipProfile-RtFaxOptions-EcmEnable	OBJECT-TYPE
	SYNTAX	INTEGER {
		    no (1),
		    yes (2)
		}
	ACCESS	read-write
	STATUS	mandatory
	DESCRIPTION	"Enable/Disable Error Correction Mode."
	::= { mibvoipProfileEntry 33 }

    voipProfile-RtFaxOptions-LowLatencyMode	OBJECT-TYPE
	SYNTAX	INTEGER {
		    no (1),
		    yes (2)
		}
	ACCESS	read-write
	STATUS	mandatory
	DESCRIPTION	"Enable/Disable Low Latency Mode."
	::= { mibvoipProfileEntry 34 }

    voipProfile-RtFaxOptions-CommandSpoof	OBJECT-TYPE
	SYNTAX	INTEGER {
		    no (1),
		    yes (2)
		}
	ACCESS	read-write
	STATUS	mandatory
	DESCRIPTION	"Enable/Disable a particular T.30 command spoof."
	::= { mibvoipProfileEntry 35 }

    voipProfile-RtFaxOptions-LocalRetransmitLsf	OBJECT-TYPE
	SYNTAX	INTEGER {
		    no (1),
		    yes (2)
		}
	ACCESS	read-write
	STATUS	mandatory
	DESCRIPTION	"Enable/Disable local low speed frame retransmission"
	::= { mibvoipProfileEntry 36 }

    voipProfile-RtFaxOptions-PacketRedundancy	OBJECT-TYPE
	SYNTAX	INTEGER
	ACCESS	read-write
	STATUS	mandatory
	DESCRIPTION	"UDP Packet Redundancy."
	::= { mibvoipProfileEntry 37 }

    voipProfile-RtFaxOptions-FixedPackets	OBJECT-TYPE
	SYNTAX	INTEGER {
		    no (1),
		    yes (2)
		}
	ACCESS	read-write
	STATUS	mandatory
	DESCRIPTION	"Use fixed size image data packets"
	::= { mibvoipProfileEntry 38 }

    voipProfile-RtFaxOptions-MaxDataRate	OBJECT-TYPE
	SYNTAX	INTEGER {
		    n-2400 (2401),
		    n-4800 (4801),
		    n-9600 (9601),
		    n-14400 (14401)
		}
	ACCESS	read-write
	STATUS	mandatory
	DESCRIPTION	"Maximum Negotiated Data Rate"
	::= { mibvoipProfileEntry 39 }

    voipProfile-RtFaxOptions-AllowCtc	OBJECT-TYPE
	SYNTAX	INTEGER {
		    no (1),
		    yes (2)
		}
	ACCESS	read-write
	STATUS	mandatory
	DESCRIPTION	"Enable extended ECM correction beyond four retransmissions"
	::= { mibvoipProfileEntry 68 }

    voipProfile-CallHairpin	OBJECT-TYPE
	SYNTAX	INTEGER {
		    no (1),
		    yes (2)
		}
	ACCESS	read-write
	STATUS	mandatory
	DESCRIPTION	"Hairpin"
	::= { mibvoipProfileEntry 40 }

    voipProfile-CallKeepAliveTimeout	OBJECT-TYPE
	SYNTAX	INTEGER
	ACCESS	read-write
	STATUS	mandatory
	DESCRIPTION	"Keep Alive Timeout"
	::= { mibvoipProfileEntry 41 }

    voipProfile-ClidSuppress	OBJECT-TYPE
	SYNTAX	INTEGER {
		    no (1),
		    yes (2)
		}
	ACCESS	read-write
	STATUS	mandatory
	DESCRIPTION	"Suppress Outbound CLID"
	::= { mibvoipProfileEntry 42 }

    voipProfile-TrueConnectEnable	OBJECT-TYPE
	SYNTAX	INTEGER {
		    no (1),
		    yes (2)
		}
	ACCESS	read-write
	STATUS	mandatory
	DESCRIPTION	"Enable PSTN Connect to Match VOIP Signaling Connect"
	::= { mibvoipProfileEntry 43 }

    voipProfile-G711TransparentData	OBJECT-TYPE
	SYNTAX	INTEGER {
		    no (1),
		    yes (2)
		}
	ACCESS	read-write
	STATUS	mandatory
	DESCRIPTION	"G711 Transparent Data for Fax/Modem or T.38 Fallback"
	::= { mibvoipProfileEntry 44 }

    voipProfile-AllowG711Fallback	OBJECT-TYPE
	SYNTAX	INTEGER {
		    no (1),
		    yes (2)
		}
	ACCESS	read-write
	STATUS	mandatory
	DESCRIPTION	"Allow coder to fallback to G.711"
	::= { mibvoipProfileEntry 45 }

    voipProfile-AllowCoderFallback	OBJECT-TYPE
	SYNTAX	INTEGER {
		    no (1),
		    yes (2)
		}
	ACCESS	read-write
	STATUS	mandatory
	DESCRIPTION	"Allow coder to fallback to non-preferred"
	::= { mibvoipProfileEntry 46 }

    voipProfile-ChooseDspVia	OBJECT-TYPE
	SYNTAX	INTEGER {
		    voipCentric (1),
		    dataCentric (2)
		}
	ACCESS	read-write
	STATUS	mandatory
	DESCRIPTION	"Strategy for choosing next VOIP DSP"
	::= { mibvoipProfileEntry 47 }

    voipProfile-TrunkQuiesceEnable	OBJECT-TYPE
	SYNTAX	INTEGER {
		    no (1),
		    yes (2)
		}
	ACCESS	read-write
	STATUS	mandatory
	DESCRIPTION	"VOIP Trunk Quiesce Enable"
	::= { mibvoipProfileEntry 48 }

    voipProfile-EarlyRingbackEnable	OBJECT-TYPE
	SYNTAX	INTEGER {
		    no (1),
		    yes (2)
		}
	ACCESS	read-write
	STATUS	mandatory
	DESCRIPTION	"Enables early ringback generation. Recommended for high-latency ip networks."
	::= { mibvoipProfileEntry 49 }

    voipProfile-TrunkPrefixEnable	OBJECT-TYPE
	SYNTAX	INTEGER {
		    no (1),
		    yes (2)
		}
	ACCESS	read-write
	STATUS	mandatory
	DESCRIPTION	"Enables trunk prefixing to DNIS. For egress trunk selection."
	::= { mibvoipProfileEntry 50 }

    voipProfile-SignalingModel	OBJECT-TYPE
	SYNTAX	INTEGER {
		    earlyAlerting (1),
		    slowProceeding (2),
		    fastProceeding (3)
		}
	ACCESS	read-write
	STATUS	mandatory
	DESCRIPTION	"Signaling Model"
	::= { mibvoipProfileEntry 51 }

    voipProfile-OperatorAssist	OBJECT-TYPE
	SYNTAX	DisplayString
	ACCESS	read-write
	STATUS	mandatory
	DESCRIPTION	"Transfer call to operator (* default)"
	::= { mibvoipProfileEntry 52 }

    voipProfile-PstnAttribute-CauseCodeTransparency	OBJECT-TYPE
	SYNTAX	INTEGER {
		    no (1),
		    yes (2)
		}
	ACCESS	read-write
	STATUS	mandatory
	DESCRIPTION	"Enable/Disable PSTN Cause Code Transparency Feature."
	::= { mibvoipProfileEntry 54 }

    voipProfile-PstnAttribute-AlertProgressIndicator	OBJECT-TYPE
	SYNTAX	INTEGER {
		    noProgressIndicator (1),
		    noneEnd2endIsdn (2),
		    destNonIsdn (3),
		    origNonIsdn (4),
		    returnToIsdn (5),
		    interworkingOccured (6),
		    inbandInfoAvailable (9)
		}
	ACCESS	read-write
	STATUS	mandatory
	DESCRIPTION	"Call Progress Indicator in Alerting"
	::= { mibvoipProfileEntry 55 }

    voipProfile-PstnAttribute-ProceedProgressIndicator	OBJECT-TYPE
	SYNTAX	INTEGER {
		    noProgressIndicator (1),
		    noneEnd2endIsdn (2),
		    destNonIsdn (3),
		    origNonIsdn (4),
		    returnToIsdn (5),
		    interworkingOccured (6),
		    inbandInfoAvailable (9)
		}
	ACCESS	read-write
	STATUS	mandatory
	DESCRIPTION	"Call Progress Indicator in Proceeding"
	::= { mibvoipProfileEntry 56 }

    voipProfile-PstnAttribute-BearerCapability	OBJECT-TYPE
	SYNTAX	INTEGER {
		    speech (1),
		    unrestrictedDigitalInfo (9),
		    restrictedDigitalInfo (10),
		    audio3100hz (17),
		    video (25)
		}
	ACCESS	read-write
	STATUS	mandatory
	DESCRIPTION	"Bearer Capability "
	::= { mibvoipProfileEntry 57 }

    voipProfile-SequentialCallEnable	OBJECT-TYPE
	SYNTAX	INTEGER {
		    no (1),
		    yes (2)
		}
	ACCESS	read-write
	STATUS	mandatory
	DESCRIPTION	"Sequential call enable"
	::= { mibvoipProfileEntry 53 }

    voipProfile-Ss7voipCallPersistence	OBJECT-TYPE
	SYNTAX	INTEGER {
		    no (1),
		    yes (2)
		}
	ACCESS	read-write
	STATUS	mandatory
	DESCRIPTION	"If enabled, a VOIP call route persists across IPDC requests for a given call, until the call is released."
	::= { mibvoipProfileEntry 58 }

    voipProfile-NextCall	OBJECT-TYPE
	SYNTAX	DisplayString
	ACCESS	read-write
	STATUS	mandatory
	DESCRIPTION	"Next Call Key Entry (**9 default)"
	::= { mibvoipProfileEntry 65 }

    voipProfile-RtpqosPollingEnable	OBJECT-TYPE
	SYNTAX	INTEGER {
		    no (1),
		    yes (2)
		}
	ACCESS	read-write
	STATUS	mandatory
	DESCRIPTION	"RTP QoS Polling Enable"
	::= { mibvoipProfileEntry 66 }

    voipProfile-FaststartEnable	OBJECT-TYPE
	SYNTAX	INTEGER {
		    no (1),
		    yes (2)
		}
	ACCESS	read-write
	STATUS	mandatory
	DESCRIPTION	"Faststart Procedure Enable."
	::= { mibvoipProfileEntry 67 }

    voipProfile-SignalingTos-Active	OBJECT-TYPE
	SYNTAX	INTEGER {
		    no (1),
		    yes (2)
		}
	ACCESS	read-write
	STATUS	mandatory
	DESCRIPTION	"Activate type of service for this connection."
	::= { mibvoipProfileEntry 71 }

    voipProfile-SignalingTos-Precedence	OBJECT-TYPE
	SYNTAX	INTEGER {
		    n-000 (1),
		    n-001 (33),
		    n-010 (65),
		    n-011 (97),
		    n-100 (129),
		    n-101 (161),
		    n-110 (193),
		    n-111 (225)
		}
	ACCESS	read-write
	STATUS	mandatory
	DESCRIPTION	"Tag the precedence bits (priority bits) in the TOS octet of IP datagram header with this value when match occurs."
	::= { mibvoipProfileEntry 72 }

    voipProfile-SignalingTos-TypeOfService	OBJECT-TYPE
	SYNTAX	INTEGER {
		    normal (1),
		    cost (3),
		    reliability (5),
		    throughput (9),
		    latency (17)
		}
	ACCESS	read-write
	STATUS	mandatory
	DESCRIPTION	"Tag the type of service field in the TOS octet of IP datagram header with this value when match occurs."
	::= { mibvoipProfileEntry 73 }

    voipProfile-SignalingTos-ApplyTo	OBJECT-TYPE
	SYNTAX	INTEGER {
		    incoming (1025),
		    outgoing (2049),
		    both (3073)
		}
	ACCESS	read-write
	STATUS	mandatory
	DESCRIPTION	"Define how the type-of-service applies to data flow for this connection."
	::= { mibvoipProfileEntry 74 }

    voipProfile-SignalingTos-MarkingType	OBJECT-TYPE
	SYNTAX	INTEGER {
		    precedenceTos (1),
		    dscp (2)
		}
	ACCESS	read-write
	STATUS	mandatory
	DESCRIPTION	"Select type of packet marking."
	::= { mibvoipProfileEntry 75 }

    voipProfile-SignalingTos-Dscp	OBJECT-TYPE
	SYNTAX	DisplayString
	ACCESS	read-write
	STATUS	mandatory
	DESCRIPTION	"DSCP tag to be used in marking of the packets (if marking-type = dscp)."
	::= { mibvoipProfileEntry 76 }

    voipProfile-Action-o	OBJECT-TYPE
	SYNTAX	INTEGER {
		    noAction (1),
		    createProfile (2),
		    deleteProfile (3)
		}
	ACCESS	read-write
	STATUS	mandatory
	DESCRIPTION	""
	::= { mibvoipProfileEntry 59 }

END
