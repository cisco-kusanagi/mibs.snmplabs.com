-- extracted from draft-ietf-entmib-state-05.txt
-- at Wed Sep 22 06:24:02 2004

   ENTITY-STATE-TC DEFINITIONS ::= BEGIN

   IMPORTS
      MODULE-IDENTITY, mib-2       FROM SNMPv2-SMI
      TEXTUAL-CONVENTION           FROM SNMPv2-TC;

    entityStateTc MODULE-IDENTITY
        LAST-UPDATED "200407190000Z"
        ORGANIZATION "IETF Entity MIB Working Group"
        CONTACT-INFO
            "General Discussion: entmib@ietf.org
                  To Subscribe:
                    http://www.ietf.org/mailman/listinfo/entmib

                  http://www.ietf.org/html.charters/entmib-charter.html

                   Sharon Chisholm
                   Nortel Networks
                   PO Box 3511 Station C
                   Ottawa, Ont.  K1Y 4H7
                   Canada
                   schishol@nortelnetworks.com
                            Entity State MIB              September 2004


                   David T. Perkins
                   548 Qualbrook Ct
                   San Jose, CA 95110
                   USA
                   Phone: 408 394-8702
                   dperkins@snmpinfo.com"
         DESCRIPTION
                 "This MIB defines a state textual conventions.

                Copyright (C) The Internet Society 2004.  This version
                of this MIB module is part of RFC yyyy;  see the RFC
                itself for full legal notices."
           -- RFC Ed.: replace yyyy with actual RFC number & remove
           -- this note
         REVISION    "200407190000Z"
         DESCRIPTION
             "Initial version, published as RFC yyyy."
             -- RFC-Editor assigns yyyy
        ::= { mib-2 XX } -- to be assigned by IANA

     EntityAdminState  ::=  TEXTUAL-CONVENTION
       STATUS         current
       DESCRIPTION
            " Represents the various possible administrative states.

              A value of 'locked' means the resource is administratively
              prohibited from use. A value of 'shuttingDown' means that
              usage is administratively limited to current instances of
              use. A value of 'unlocked' means the resource is not
              administratively prohibited from use. A value of
               'unknown' means that this resource is unable to
               report administrative state."
       SYNTAX         INTEGER
                 {
                 unknown(1),
                 locked(2),
                 shuttingDown(3),
                 unlocked(4)
                 }

     EntityOperState  ::=  TEXTUAL-CONVENTION
       STATUS         current
       DESCRIPTION
            " Represents the possible values of operational states.

              A value of 'disabled' means the resource is totally
              inoperable. A value of 'enabled' means the resource
              is partially or fully operable. A value of 'testing'
              means the resource is currently being tested
              and cannot there fore report whether it is operational
              or not. A value of 'unknown' means that this
              resource is unable to report operational state. "
                            Entity State MIB              September 2004


       SYNTAX         INTEGER
                 {
                 unknown (1),
                 disabled(2),
                 enabled(3),
                 testing (4)
                 }

     EntityUsageState  ::=  TEXTUAL-CONVENTION
       STATUS         current
       DESCRIPTION
            " Represents the possible values of usage states.
              A value of 'idle' means the resource is servicing no
              users. A value of 'active' means the resource is
              currently in use and it has sufficient spare capacity
              to provide for additional users. A value of 'busy'
              means the resource is currently in use, but it
              currently has no spare capacity to provide for
              additional users. A value of 'unknown' means
              that this resource is unable to report usage state."
       SYNTAX         INTEGER
                 {
                 unknown (1),
                 idle(2),
                 active(3),
                 busy(4)
                 }


    EntityAlarmStatus  ::=  TEXTUAL-CONVENTION
       STATUS         current
       DESCRIPTION
            "Represents the possible values of alarm status.
            An Alarm [ALARM-MIB] is a persistent indication
            of an error or warning condition.

            When no bits of this attribute are set, then none
            of the value of under repair is set, the resource is
            currently being repaired, which depending on the
            implementation, may make the other values in this bit
            string unreliable.

            When the value of 'critical' is set, one or more critical
            alarms are active against the resource. When the value
            of 'major' is set, one or more major alarms are active
            against the resource. When the value of 'minor' is set,
            one or more minor alarms are active against the resource.
            When the value of 'warning' is set, one or more warning
            alarms are active against the resource. When the value
            of 'indeterminate' is set, one or more alarms whose of
            perceived severity cannot be determined are active
            against this resource.
                            Entity State MIB              September 2004



            A value of 'unknown' means that this resource is
            unable to report alarm state."
             SYNTAX         BITS
                {
                unknown (0),
                underRepair(1),
                critical(2),
                major(3),
                minor(4),
                -- The following are not defined in X.733
                warning (5),
                indeterminate (6)
                              }


     EntityStandbyStatus  ::=  TEXTUAL-CONVENTION
       STATUS         current
       DESCRIPTION
            " Represents the possible values of standby status.

              A value of 'hotStandby' means the resource is not
              providing service, but it will be immediately able to
              take over the role of the resource to be backed-up,
              without the need for initialization activity, and will
              contain the same information as the resource to be
              backed up. A value of 'coldStandy' means that the
              resource is to back-up another resource, but will not
              be immediately able to take over the role of a resource
              to be backed up, and will require some initialization
              activity. A value of 'providingService' means the
              resource is providing service. A value of
               'unknown' means that this resource is unable to
               report standby state."
             SYNTAX         INTEGER
               {
               unknown (1),
               hotStandby(2),
               coldStandby(3),
               providingService(4)
               }

   END

-- 
--    Copyright (C) The Internet Society (2004).  This document is subject
--    to the rights, licenses and restrictions contained in BCP 78, and
--    except as set forth therein, the authors retain all their rights."
--    "This document and the information contained herein are provided on
--    an "AS IS" basis and THE CONTRIBUTOR, THE ORGANIZATION HE/SHE
--    REPRESENTS OR IS SPONSORED BY (IF ANY), THE INTERNET SOCIETY AND THE
--    INTERNET ENGINEERING TASK FORCE DISCLAIM ALL WARRANTIES, EXPRESS OR
--    IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE."
