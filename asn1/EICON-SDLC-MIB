-- #############################################################################
--              SDLC
-- #############################################################################

-- Documents: 285-519-1.

EICON-SDLC-MIB DEFINITIONS ::= BEGIN

IMPORTS
	Counter,
	TimeTicks,
	enterprises
		FROM RFC1155-SMI
	OBJECT-TYPE
		FROM RFC-1212;

eicon           OBJECT IDENTIFIER  ::= { enterprises 434 }
management      OBJECT IDENTIFIER  ::= { eicon 2 }
mibv2           OBJECT IDENTIFIER  ::= { management 2 }
module          OBJECT IDENTIFIER  ::= { mibv2 4 }

--      Local definitions
OperState ::= INTEGER {
	other (1),              -- none of the following
	disabled (2),           -- not in ready state
	ready (3),              -- in ready state
	active (4),             -- ready and operating
	busy (5)                        -- operating but cannot accept more traffic
	}

AdminState ::= INTEGER {
	start (1),
	stop (2),
	dump (3),
	test (4),
	invalid (5)
	}

PortRef ::= INTEGER (1..48)     -- Port reference on the server.

LinkRef ::= INTEGER (1..32)             -- Link reference of the multi-drop SDLC line.

StationAddr ::= INTEGER (0..255)        -- Link Station address on the multi-drop SDLC line.


--      Title

sdlc    OBJECT IDENTIFIER ::= { module 2 }

--      The SDLC MIB is composed of  the following tables:
--              sdlcCfgTable            configuration parameters for each port,
--              sdlcInfoTable           status information for each port,
--              sdlcLinkInfoTable       status information for each link station,
--              sdlcCountTable          statistics counters for each port,
--              sdlcLinkCountTable      statistics counters for each link station.


-- ****************************************************************************
--              SDLC cfg table
-- ****************************************************************************

sdlcCfgTable            OBJECT-TYPE
	SYNTAX  SEQUENCE OF SdlcCfgEntry 
	ACCESS  not-accessible
	STATUS  mandatory
	DESCRIPTION     
		"The SDLC configuration attributes table, one row per port.
		This information comes from the configuration file (db)."
	::= { sdlc 1 }

sdlcCfgEntry            OBJECT-TYPE
	SYNTAX  SdlcCfgEntry
	ACCESS  not-accessible
	STATUS  mandatory
	DESCRIPTION     
		"The set of SDLC configuration attributes for one port."
	INDEX           { sdlcCfgPortRef }
	::= { sdlcCfgTable 1 }

SdlcCfgEntry ::= SEQUENCE {
	sdlcCfgPortRef
		PortRef,
	sdlcCfgMaxLinkStation
		LinkRef,
	sdlcCfgT1
		INTEGER,
	sdlcCfgT2
		INTEGER,
	sdlcCfgT3       
		INTEGER,
	sdlcCfgT4       
		INTEGER,
	sdlcCfgMaxFrameSz
		INTEGER,
	sdlcCfgMaxRetryCount
		INTEGER,
	sdlcCfgMaxWindowSz
		INTEGER
	}

sdlcCfgPortRef          OBJECT-TYPE
	SYNTAX  PortRef
	ACCESS  read-only 
	STATUS  mandatory
	DESCRIPTION     
		"The Id of the port, equal to portIndex from the port group. It identifies the port to 
		which the configuration parameters apply. "
	::= { sdlcCfgEntry 1 }

sdlcCfgMaxLinkStation   OBJECT-TYPE
	SYNTAX  LinkRef
	ACCESS  read-only 
	STATUS  mandatory
	DESCRIPTION     
		"Maximum number of stations for this port (1..32), default is 9."
	DEFVAL  { 9 }
	::= { sdlcCfgEntry 2 }

sdlcCfgT1               OBJECT-TYPE
	SYNTAX  INTEGER (0..9999)
	ACCESS  read-only 
	STATUS  mandatory
	DESCRIPTION     
		"Check point timer, default is 2900."
	DEFVAL  { 2900 }
	::= { sdlcCfgEntry 3 }

sdlcCfgT2               OBJECT-TYPE
	SYNTAX  INTEGER (0..9999)
	ACCESS  read-only 
	STATUS  mandatory
	DESCRIPTION     
		"Poll delay timer, default is 200."
	DEFVAL  { 200 }
	::= { sdlcCfgEntry 4 }

sdlcCfgT3               OBJECT-TYPE
	SYNTAX  INTEGER (0..99999)
	ACCESS  read-only 
	STATUS  mandatory
	DESCRIPTION     
		"Slow poll timer, default is 15000."
	DEFVAL  { 15000 }
	::= { sdlcCfgEntry 5 }

sdlcCfgT4               OBJECT-TYPE
	SYNTAX  INTEGER (0..99999)
	ACCESS  read-only 
	STATUS  mandatory
	DESCRIPTION     
		"Idle timer, default is 60000."
	DEFVAL  { 60000 }
	::= { sdlcCfgEntry 6 }

sdlcCfgMaxFrameSz       OBJECT-TYPE
	SYNTAX  INTEGER (267..8203)
	ACCESS  read-only 
	STATUS  mandatory
	DESCRIPTION     
		"Number of octets per frame (N1), default is 267."
	DEFVAL  { 267 }
	::= { sdlcCfgEntry 7 }

sdlcCfgMaxRetryCount    OBJECT-TYPE
	SYNTAX  INTEGER (0..99)
	ACCESS  read-only 
	STATUS  mandatory
	DESCRIPTION     
		"Maximum retry count (N2), default is 10."
	DEFVAL  { 10 }
	::= { sdlcCfgEntry 8 }

sdlcCfgMaxWindowSz      OBJECT-TYPE
	SYNTAX  INTEGER (1..127)
	ACCESS  read-only 
	STATUS  mandatory
	DESCRIPTION     
		"Maximum window size (K), default is 7."
	DEFVAL  { 7 }
	::= { sdlcCfgEntry 9 }


-- ****************************************************************************
--              SDLC info table
-- ****************************************************************************

sdlcInfoTable           OBJECT-TYPE
	SYNTAX  SEQUENCE OF SdlcInfoEntry 
	ACCESS  not-accessible
	STATUS  mandatory
	DESCRIPTION     
		"The dynamic (status) attributes table, one row per port (line)."
	::= { sdlc 2 }

sdlcInfoEntry           OBJECT-TYPE
	SYNTAX  SdlcInfoEntry
	ACCESS  not-accessible
	STATUS  mandatory
	DESCRIPTION     
		"The set of status attributes for one port (line)."
	INDEX           { sdlcInfoPortRef }
	::= { sdlcInfoTable 1 }

SdlcInfoEntry ::= SEQUENCE {
	sdlcInfoPortRef
		PortRef,
	sdlcInfoAdminStatusCtr  
		AdminState,                                     
	sdlcInfoOperStatus
		OperState,
	sdlcInfoDial
		INTEGER,
	sdlcInfoDuplex
		INTEGER,
	sdlcInfoMaxFrameSz
		INTEGER,
	sdlcInfoMaxRetryCount   
		INTEGER,
	sdlcInfoMaxWindowSz
		INTEGER,
	sdlcInfoMaxLinkStation  
		INTEGER,
	sdlcInfoNbStationInUse
		INTEGER,
	sdlcInfoStartTime       
		TimeTicks,
	sdlcInfoModemTime
		TimeTicks
	}


sdlcInfoPortRef         OBJECT-TYPE
	SYNTAX  PortRef
	ACCESS  read-only 
	STATUS  mandatory
	DESCRIPTION     
		"The Id of the port, equal to portIndex from the port group. It identifies the port to 
		which the information parameters apply. "
	::= { sdlcInfoEntry 1 }

sdlcInfoAdminStatusCtr  OBJECT-TYPE
	SYNTAX  AdminState
	ACCESS  read-write 
	STATUS  mandatory
	DESCRIPTION     
		"The control parameter, used to stop or start the SDLC port."
	::= { sdlcInfoEntry 2 }

sdlcInfoOperStatus      OBJECT-TYPE
	SYNTAX  OperState
	ACCESS  read-only 
	STATUS  mandatory
	DESCRIPTION     
		"The status of the SDLC line."
	::= { sdlcInfoEntry 3 }

sdlcInfoDial            OBJECT-TYPE
	SYNTAX  INTEGER {
		leased (1),
		dial-up (2)
		}
	ACCESS  read-only 
	STATUS  mandatory
	DESCRIPTION     
		"The value indicates whether the port is connected to a leased line or to a dial-up line."
	::= { sdlcInfoEntry 4 }

sdlcInfoDuplex          OBJECT-TYPE
	SYNTAX  INTEGER {
		full-duplex (1),
		half-duplex (2)
		}
	ACCESS  read-only 
	STATUS  mandatory
	DESCRIPTION     
		"The value indicates the type of the device to which the port is connected. The mode of
		transmission/reception can be full or half duplex."
	::= { sdlcInfoEntry 5 }

sdlcInfoMaxFrameSz      OBJECT-TYPE
	SYNTAX  INTEGER
	ACCESS  read-only 
	STATUS  mandatory
	DESCRIPTION     
		"The maximum frame size "
	::= { sdlcInfoEntry 6 }

sdlcInfoMaxRetryCount   OBJECT-TYPE
	SYNTAX  INTEGER
	ACCESS  read-only 
	STATUS  mandatory
	DESCRIPTION     
		"The number of retries for negative acknowledgement of a frame."
	::= { sdlcInfoEntry 7 }

sdlcInfoMaxWindowSz     OBJECT-TYPE
	SYNTAX  INTEGER
	ACCESS  read-only 
	STATUS  mandatory
	DESCRIPTION     
		"Maximum window size."
	::= { sdlcInfoEntry 8 }

sdlcInfoMaxLinkStation  OBJECT-TYPE
	SYNTAX  INTEGER
	ACCESS  read-only 
	STATUS  mandatory
	DESCRIPTION     
		"The number of multi-drop stations defined for that line."
	::= { sdlcInfoEntry 9 }

sdlcInfoNbStationInUse  OBJECT-TYPE
	SYNTAX  INTEGER
	ACCESS  read-only 
	STATUS  mandatory
	DESCRIPTION     
		"The number of stations currently in use."
	::= { sdlcInfoEntry 10 }

sdlcInfoStartTime       OBJECT-TYPE
	SYNTAX  TimeTicks
	ACCESS  read-only 
	STATUS  mandatory
	DESCRIPTION     
		"The time at which the line was started. Equals to sysUpTime."
	::= { sdlcInfoEntry 11 }

sdlcInfoModemTime       OBJECT-TYPE
	SYNTAX  TimeTicks
	ACCESS  read-only 
	STATUS  mandatory
	DESCRIPTION     
		"The time at which the modem state changed. Equals to sysUpTime."
	::= { sdlcInfoEntry 12 }


-- ****************************************************************************
--              SDLC link info table
-- ****************************************************************************

sdlcLinkInfoTable       OBJECT-TYPE
	SYNTAX  SEQUENCE OF SdlcLinkInfoEntry 
	ACCESS  not-accessible
	STATUS  mandatory
	DESCRIPTION     
		"Dynamic attributes table, one row per link station"
	::= { sdlc 3 }

sdlcLinkInfoEntry       OBJECT-TYPE
	SYNTAX  SdlcLinkInfoEntry
	ACCESS  not-accessible
	STATUS  mandatory
	DESCRIPTION     
		"The set of dynamic attributes for one link station."
	INDEX           { sdlcLinkInfoPortRef, sdlcLinkInfoStationAddr } 
	::= { sdlcLinkInfoTable 1 }

SdlcLinkInfoEntry ::= SEQUENCE {
	sdlcLinkInfoPortRef     
		PortRef,
	sdlcLinkInfoStationAddr 
		StationAddr,
	sdlcLinkInfoAdminStatusCtr
		AdminState,
	sdlcLinkInfoProtocolState
		INTEGER,
	sdlcLinkInfoUserState
		INTEGER,
	sdlcLinkInfoStationType 
		INTEGER,
	sdlcLinkInfoStartTime   
		TimeTicks,
	sdlcLinkInfoChangeTime  
		TimeTicks,
	sdlcLinkInfoDataTime    
		TimeTicks,
	sdlcLinkInfoMaxOut      
		INTEGER,
	sdlcLinkInfoMaxIn       
		INTEGER,
	sdlcLinkInfoMaxData     
		INTEGER,
	sdlcLinkInfoLocalBusy
		INTEGER,
	sdlcLinkInfoRemoteBusy  
		INTEGER,
	sdlcLinkInfoNS          
		INTEGER,
	sdlcLinkInfoNR          
		INTEGER,
	sdlcLinkInfoLNR 
		INTEGER
	}

sdlcLinkInfoPortRef     OBJECT-TYPE
	SYNTAX  PortRef
	ACCESS  read-only 
	STATUS  mandatory
	DESCRIPTION     
		"The Id of the port, equal to portIndex from the port group. 
		 It identifies the port to which the information parameters apply. "
	::= { sdlcLinkInfoEntry 1 }

sdlcLinkInfoStationAddr OBJECT-TYPE
	SYNTAX  StationAddr
	ACCESS  read-only 
	STATUS  mandatory
	DESCRIPTION     
		"The address of the station attached to the line. This number represents a logical
		connection number and is assigned by protocol software."
	::= { sdlcLinkInfoEntry 2 }

sdlcLinkInfoAdminStatusCtr      OBJECT-TYPE
	SYNTAX  AdminState
	ACCESS  read-write
	STATUS  mandatory
	DESCRIPTION     
		"The control parameter used to close the connection."
	::= { sdlcLinkInfoEntry 3 }

sdlcLinkInfoProtocolState       OBJECT-TYPE
	SYNTAX  INTEGER {
		closed(1),
		closing(2),
		opening(3),
		opened(4),
		resetting(5),
		wait-reset(6),
		wait-open(7),
		xid-send(8),
		xid-recv(9)
		}
	ACCESS  read-only 
	STATUS  mandatory
	DESCRIPTION     
		"The protocol state of the SDLC link."
	::= { sdlcLinkInfoEntry 4 }

sdlcLinkInfoUserState   OBJECT-TYPE
	SYNTAX  INTEGER {
		closed(1),
		closing(2),
		opening(3),
		opened(4),
		other(5)
		}
	ACCESS  read-only 
	STATUS  mandatory
	DESCRIPTION     
		"The user state of the connection."
	::= { sdlcLinkInfoEntry 5 }

sdlcLinkInfoStationType OBJECT-TYPE
	SYNTAX  INTEGER {
		secondary(1),
		primary(2),
		negotiable(3)
		}
	ACCESS  read-only 
	STATUS  mandatory
	DESCRIPTION     
		"The type of link station."
	::= { sdlcLinkInfoEntry 6 }

sdlcLinkInfoStartTime   OBJECT-TYPE
	SYNTAX  TimeTicks
	ACCESS  read-only 
	STATUS  mandatory
	DESCRIPTION     
		"The time at which this link was started. Equals to sysUpTime."
	::= { sdlcLinkInfoEntry 7 }

sdlcLinkInfoChangeTime  OBJECT-TYPE
	SYNTAX  TimeTicks
	ACCESS  read-only 
	STATUS  mandatory
	DESCRIPTION     
		"The time at which the link state changed. Equals to sysUpTime."
	::= { sdlcLinkInfoEntry 8 }

sdlcLinkInfoDataTime    OBJECT-TYPE
	SYNTAX  TimeTicks
	ACCESS  read-only 
	STATUS  mandatory
	DESCRIPTION     
		"The time of non-poll data. Equals to sysUpTime."
	::= { sdlcLinkInfoEntry 9 }

sdlcLinkInfoMaxOut      OBJECT-TYPE
	SYNTAX  INTEGER
	ACCESS  read-only 
	STATUS  mandatory
	DESCRIPTION     
		"Maximum number of output frames per window."
	::= { sdlcLinkInfoEntry 10 }

sdlcLinkInfoMaxIn       OBJECT-TYPE
	SYNTAX  INTEGER
	ACCESS  read-only 
	STATUS  mandatory
	DESCRIPTION     
		"Maximum number of input frames per window."
	::= { sdlcLinkInfoEntry 11 }

sdlcLinkInfoMaxData     OBJECT-TYPE
	SYNTAX  INTEGER
	ACCESS  read-only 
	STATUS  mandatory
	DESCRIPTION     
		" Maximum number of octets per frame."
	::= { sdlcLinkInfoEntry 12 }

sdlcLinkInfoLocalBusy   OBJECT-TYPE
	SYNTAX  INTEGER
	ACCESS  read-only 
	STATUS  mandatory
	DESCRIPTION     
		"Busy state flag."
	::= { sdlcLinkInfoEntry 13 }

sdlcLinkInfoRemoteBusy  OBJECT-TYPE
	SYNTAX  INTEGER
	ACCESS  read-only 
	STATUS  mandatory
	DESCRIPTION     
		"Busy state flag."
	::= { sdlcLinkInfoEntry 14 }

sdlcLinkInfoNS          OBJECT-TYPE
	SYNTAX  INTEGER
	ACCESS  read-only 
	STATUS  mandatory
	DESCRIPTION     
		"The NS counter."
	::= { sdlcLinkInfoEntry 15 }

sdlcLinkInfoNR          OBJECT-TYPE
	SYNTAX  INTEGER
	ACCESS  read-only 
	STATUS  mandatory
	DESCRIPTION     
		"The NR counter."
	::= { sdlcLinkInfoEntry 16 }

sdlcLinkInfoLNR         OBJECT-TYPE
	SYNTAX  INTEGER
	ACCESS  read-only 
	STATUS  mandatory
	DESCRIPTION     
		"Last received sequence number."
	::= { sdlcLinkInfoEntry 17 }


-- ****************************************************************************
--              SDLC port flow table
-- ****************************************************************************

sdlcCountTable  OBJECT-TYPE
	SYNTAX  SEQUENCE OF SdlcCountEntry 
	ACCESS  not-accessible
	STATUS  mandatory
	DESCRIPTION     
		"The runtime counters table, one row per port"
	::= { sdlc 4 }
 
sdlcCountEntry  OBJECT-TYPE
	SYNTAX  SdlcCountEntry
	ACCESS  not-accessible
	STATUS  mandatory
	DESCRIPTION     
		"The set of counters values for one port."
	INDEX           { sdlcCountPortRef }
	::= { sdlcCountTable 1 }

SdlcCountEntry ::= SEQUENCE {
	sdlcCountPortRef
		PortRef,
	sdlcCountT1expires      
		Counter,
	sdlcCountRetransmis     
		Counter,
	sdlcCountSNRMTxs        
		Counter,
	sdlcCountSNRMRxs        
		Counter,
	sdlcCountDISCTxs        
		Counter,
	sdlcCountDISCRxs        
		Counter,
	sdlcCountUAsTxs 
		Counter,
	sdlcCountUAsRxs 
		Counter,
	sdlcCountDMsTxs 
		Counter,
	sdlcCountDMsRxs 
		Counter,
	sdlcCountFRMRsTxs       
		Counter,
	sdlcCountFRMRsRxs       
		Counter,
	sdlcCountXIDsTxs        
		Counter,
	sdlcCountXIDsRxs        
		Counter,
	sdlcCountINFOsTxs       
		Counter,
	sdlcCountINFOsRxs       
		Counter,
	sdlcCountRRsTxs 
		Counter,
	sdlcCountRRsRxs 
		Counter,
	sdlcCountRNRsTxs        
		Counter,
	sdlcCountRNRsRxs        
		Counter,
	sdlcCountREJsTxs        
		Counter,
	sdlcCountREJsRxs        
		Counter,
	sdlcCountTestTxs        
		Counter,
	sdlcCountTestRxs        
		Counter,
	sdlcCountBadFcsTxs      
		Counter,
	sdlcCountBadFcsRxs      
		Counter,
	sdlcCountAbortTxs       
		Counter,
	sdlcCountAbortRxs       
		Counter,
	sdlcCountTxUnderRs      
		Counter,
	sdlcCountRxOverRs       
		Counter,
	sdlcCountUnknowTxs      
		Counter,
	sdlcCountUnknowRxs      
		Counter
	}

sdlcCountPortRef                OBJECT-TYPE
	SYNTAX  PortRef
	ACCESS  read-only 
	STATUS  mandatory
	DESCRIPTION     
		"The Id of the port, equal to portIndex from the port group. It identifies the port to 
		which the information parameters apply. "
	::= { sdlcCountEntry 1 }

sdlcCountT1expires      OBJECT-TYPE
	SYNTAX  Counter
	ACCESS  read-only 
	STATUS  mandatory
	DESCRIPTION     
		" The number of times the Checkpoint Timer (T1) protocol
	timer has been exceeded."
	::= { sdlcCountEntry 2 }

sdlcCountRetransmis     OBJECT-TYPE
	SYNTAX  Counter
	ACCESS  read-only 
	STATUS  mandatory
	DESCRIPTION     
		"The number of retransmitted frames. "
	::= { sdlcCountEntry 3 }

sdlcCountSNRMTxs        OBJECT-TYPE
	SYNTAX  Counter
	ACCESS  read-only 
	STATUS  mandatory
	DESCRIPTION     
		"The number of set normal response mode U-frames
	transmitted. "
	::= { sdlcCountEntry 4 }

sdlcCountSNRMRxs        OBJECT-TYPE
	SYNTAX  Counter
	ACCESS  read-only 
	STATUS  mandatory
	DESCRIPTION     
		"The number of set normal response mode U-frames
	received. "
	::= { sdlcCountEntry 5 }

sdlcCountDISCTxs        OBJECT-TYPE
	SYNTAX  Counter
	ACCESS  read-only 
	STATUS  mandatory
	DESCRIPTION     
		"The number of disconnect U-frames sent. "
	::= { sdlcCountEntry 6 }

sdlcCountDISCRxs        OBJECT-TYPE
	SYNTAX  Counter
	ACCESS  read-only 
	STATUS  mandatory
	DESCRIPTION     
		"The number of disconnect U-frames received. "
	::= { sdlcCountEntry 7 }

sdlcCountUAsTxs OBJECT-TYPE
	SYNTAX  Counter
	ACCESS  read-only 
	STATUS  mandatory
	DESCRIPTION     
		"The number of unnumbered acknowledgement U-frames sent. "
	::= { sdlcCountEntry 8 }

sdlcCountUAsRxs OBJECT-TYPE
	SYNTAX  Counter
	ACCESS  read-only 
	STATUS  mandatory
	DESCRIPTION     
		"The number of unnumbered acknowledgement U-frames received. "
	::= { sdlcCountEntry 9 }

sdlcCountDMsTxs OBJECT-TYPE
	SYNTAX  Counter
	ACCESS  read-only 
	STATUS  mandatory
	DESCRIPTION     
		"The number of disconnected mode U-frames sent. "
	::= { sdlcCountEntry 10 }

sdlcCountDMsRxs OBJECT-TYPE
	SYNTAX  Counter
	ACCESS  read-only 
	STATUS  mandatory
	DESCRIPTION     
		"The number of disconnected mode U-frames received. "
	::= { sdlcCountEntry 11 }

sdlcCountFRMRsTxs       OBJECT-TYPE
	SYNTAX  Counter
	ACCESS  read-only 
	STATUS  mandatory
	DESCRIPTION     
		"The number of frame reject U-frames sent. "
	::= { sdlcCountEntry 12 }

sdlcCountFRMRsRxs       OBJECT-TYPE
	SYNTAX  Counter
	ACCESS  read-only 
	STATUS  mandatory
	DESCRIPTION     
		"The number of frame reject U-frames received. "
	::= { sdlcCountEntry 13 }

sdlcCountXIDsTxs        OBJECT-TYPE
	SYNTAX  Counter
	ACCESS  read-only 
	STATUS  mandatory
	DESCRIPTION     
		"The number of XID U-frames sent. "
	::= { sdlcCountEntry 14 }

sdlcCountXIDsRxs        OBJECT-TYPE
	SYNTAX  Counter
	ACCESS  read-only 
	STATUS  mandatory
	DESCRIPTION     
		"The number of XID U-frames received. "
	::= { sdlcCountEntry 15 }

sdlcCountINFOsTxs       OBJECT-TYPE
	SYNTAX  Counter
	ACCESS  read-only 
	STATUS  mandatory
	DESCRIPTION     
		"The number of information U-frames sent. "
	::= { sdlcCountEntry 16 }

sdlcCountINFOsRxs       OBJECT-TYPE
	SYNTAX  Counter
	ACCESS  read-only 
	STATUS  mandatory
	DESCRIPTION     
		"The number of information frames received. "
	::= { sdlcCountEntry 17 }

sdlcCountRRsTxs OBJECT-TYPE
	SYNTAX  Counter
	ACCESS  read-only 
	STATUS  mandatory
	DESCRIPTION     
		"The number of receiver ready I-frames sent. "
	::= { sdlcCountEntry 18 }

sdlcCountRRsRxs OBJECT-TYPE
	SYNTAX  Counter
	ACCESS  read-only 
	STATUS  mandatory
	DESCRIPTION     
		"The number of receiver ready I-frames received. "
	::= { sdlcCountEntry 19 }

sdlcCountRNRsTxs        OBJECT-TYPE
	SYNTAX  Counter
	ACCESS  read-only 
	STATUS  mandatory
	DESCRIPTION     
		"The number of receiver not ready I-frames sent. "
	::= { sdlcCountEntry 20 }

sdlcCountRNRsRxs        OBJECT-TYPE
	SYNTAX  Counter
	ACCESS  read-only 
	STATUS  mandatory
	DESCRIPTION     
		"The number of receiver not ready I-frames received. "
	::= { sdlcCountEntry 21 }

sdlcCountREJsTxs        OBJECT-TYPE
	SYNTAX  Counter
	ACCESS  read-only 
	STATUS  mandatory
	DESCRIPTION     
		"The number of reject I-frames sent. "
	::= { sdlcCountEntry 22 }

sdlcCountREJsRxs        OBJECT-TYPE
	SYNTAX  Counter
	ACCESS  read-only 
	STATUS  mandatory
	DESCRIPTION     
		"The number of reject I-frames received. "
	::= { sdlcCountEntry 23 }

sdlcCountTestTxs        OBJECT-TYPE
	SYNTAX  Counter
	ACCESS  read-only 
	STATUS  mandatory
	DESCRIPTION     
		"The number of TEST U-frames sent. "
	::= { sdlcCountEntry 24 }

sdlcCountTestRxs        OBJECT-TYPE
	SYNTAX  Counter
	ACCESS  read-only 
	STATUS  mandatory
	DESCRIPTION     
		"The number of TEST U-frames received. "
	::= { sdlcCountEntry 25 }

sdlcCountBadFcsTxs      OBJECT-TYPE
	SYNTAX  Counter
	ACCESS  read-only 
	STATUS  mandatory
	DESCRIPTION     
		"The number of bad U-frames sent. "
	::= { sdlcCountEntry 26 }

sdlcCountBadFcsRxs      OBJECT-TYPE
	SYNTAX  Counter
	ACCESS  read-only 
	STATUS  mandatory
	DESCRIPTION     
		"The number of bad U-frames received. "
	::= { sdlcCountEntry 27 }

sdlcCountAbortTxs       OBJECT-TYPE
	SYNTAX  Counter
	ACCESS  read-only 
	STATUS  mandatory
	DESCRIPTION     
		"The number of Abort U-frames sent. "
	::= { sdlcCountEntry 28 }

sdlcCountAbortRxs       OBJECT-TYPE
	SYNTAX  Counter
	ACCESS  read-only 
	STATUS  mandatory
	DESCRIPTION     
		"The number of Abort U-frames received. "
	::= { sdlcCountEntry 29 }

sdlcCountTxUnderRs      OBJECT-TYPE
	SYNTAX  Counter
	ACCESS  read-only 
	STATUS  mandatory
	DESCRIPTION     
		"The number of times an underrun occured."
	::= { sdlcCountEntry 30 }

sdlcCountRxOverRs       OBJECT-TYPE
	SYNTAX  Counter
	ACCESS  read-only 
	STATUS  mandatory
	DESCRIPTION     
		"The number of times an overrun occured."
	::= { sdlcCountEntry 31 }

sdlcCountUnknowTxs      OBJECT-TYPE
	SYNTAX  Counter
	ACCESS  read-only 
	STATUS  mandatory
	DESCRIPTION     
		"The number of unknown frames transmitted."
	::= { sdlcCountEntry 32 }

sdlcCountUnknowRxs      OBJECT-TYPE
	SYNTAX  Counter
	ACCESS  read-only 
	STATUS  mandatory
	DESCRIPTION     
		"The number of unknown frames recieved."
	::= { sdlcCountEntry 33 }


-- ****************************************************************************
--              SDLC link station flow table
-- ****************************************************************************

sdlcLinkCountTable      OBJECT-TYPE
	SYNTAX  SEQUENCE OF SdlcLinkCountEntry 
	ACCESS  not-accessible
	STATUS  mandatory
	DESCRIPTION     
		"The runtime counters table, one row per link station."
	::= { sdlc 5 }
 
sdlcLinkCountEntry      OBJECT-TYPE
	SYNTAX  SdlcLinkCountEntry
	ACCESS  not-accessible
	STATUS  mandatory
	DESCRIPTION     
		"The set of counters values for one specific link station."
	INDEX           { sdlcLinkCountPortRef, sdlcLinkCountStationRef }
	::= { sdlcLinkCountTable 1 }

SdlcLinkCountEntry ::= SEQUENCE {
	sdlcLinkCountPortRef
		PortRef,
	sdlcLinkCountStationRef
		StationAddr,    
	sdlcLinkCountT1expires  
		Counter,
	sdlcLinkCountRetransmis 
		Counter,
	sdlcLinkCountSNRMTxs    
		Counter,
	sdlcLinkCountSNRMRxs    
		Counter,
	sdlcLinkCountDISCTxs    
		Counter,
	sdlcLinkCountDISCRxs    
		Counter,
	sdlcLinkCountUAsTxs     
		Counter,
	sdlcLinkCountUAsRxs     
		Counter,
	sdlcLinkCountDMsTxs     
		Counter,
	sdlcLinkCountDMsRxs     
		Counter,
	sdlcLinkCountFRMRsTxs   
		Counter,
	sdlcLinkCountFRMRsRxs   
		Counter,
	sdlcLinkCountXIDsTxs    
		Counter,
	sdlcLinkCountXIDsRxs    
		Counter,
	sdlcLinkCountINFOsTxs   
		Counter,
	sdlcLinkCountINFOsRxs   
		Counter,
	sdlcLinkCountRRsTxs     
		Counter,
	sdlcLinkCountRRsRxs     
		Counter,
	sdlcLinkCountRNRsTxs    
		Counter,
	sdlcLinkCountRNRsRxs    
		Counter,
	sdlcLinkCountREJsTxs    
		Counter,
	sdlcLinkCountREJsRxs    
		Counter,
	sdlcLinkCountTestTxs    
		Counter,
	sdlcLinkCountTestRxs    
		Counter
	}

sdlcLinkCountPortRef    OBJECT-TYPE
	SYNTAX  PortRef
	ACCESS  read-only 
	STATUS  mandatory
	DESCRIPTION     
		"The Id of the port, equal to portIndex from the port group. 
		It identifies the port to which the information parameters apply. "
	::= { sdlcLinkCountEntry 1 }

sdlcLinkCountStationRef OBJECT-TYPE
	SYNTAX  StationAddr
	ACCESS  read-only 
	STATUS  mandatory
	DESCRIPTION     
		"The address of the station attached to the line. This number represents a logical
		connection number and is assigned by protocol software. Equals to sdlcLinkInfoAddr."
	::= { sdlcLinkCountEntry 2 }

sdlcLinkCountT1expires  OBJECT-TYPE
	SYNTAX  Counter
	ACCESS  read-only 
	STATUS  mandatory
	DESCRIPTION     
		" The number of times the Checkpoint timer (T1) protocol
	timer has been exceeded."
	::= { sdlcLinkCountEntry 3 }

sdlcLinkCountRetransmis OBJECT-TYPE
	SYNTAX  Counter
	ACCESS  read-only 
	STATUS  mandatory
	DESCRIPTION     
		"The number of retransmitted frames. "
	::= { sdlcLinkCountEntry 4 }

sdlcLinkCountSNRMTxs    OBJECT-TYPE
	SYNTAX  Counter
	ACCESS  read-only 
	STATUS  mandatory
	DESCRIPTION     
		"The number of set normal response mode U-frames
	transmitted. "
	::= { sdlcLinkCountEntry 5 }

sdlcLinkCountSNRMRxs    OBJECT-TYPE
	SYNTAX  Counter
	ACCESS  read-only 
	STATUS  mandatory
	DESCRIPTION     
		"The number of set normal response mode U-frames
	received. "
	::= { sdlcLinkCountEntry 6 }

sdlcLinkCountDISCTxs    OBJECT-TYPE
	SYNTAX  Counter
	ACCESS  read-only 
	STATUS  mandatory
	DESCRIPTION     
		"The number of disconnect U-frames sent. "
	::= { sdlcLinkCountEntry 7 }

sdlcLinkCountDISCRxs    OBJECT-TYPE
	SYNTAX  Counter
	ACCESS  read-only 
	STATUS  mandatory
	DESCRIPTION     
		"The number of disconnect U-frames received. "
	::= { sdlcLinkCountEntry 8 }

sdlcLinkCountUAsTxs     OBJECT-TYPE
	SYNTAX  Counter
	ACCESS  read-only 
	STATUS  mandatory
	DESCRIPTION     
		"The number of unnumbered acknowledgement U-frames sent. "
	::= { sdlcLinkCountEntry 9 }

sdlcLinkCountUAsRxs     OBJECT-TYPE
	SYNTAX  Counter
	ACCESS  read-only 
	STATUS  mandatory
	DESCRIPTION     
		"The number of unnumbered acknowledgement U-frames recvd."
	::= { sdlcLinkCountEntry 10 }

sdlcLinkCountDMsTxs     OBJECT-TYPE
	SYNTAX  Counter
	ACCESS  read-only 
	STATUS  mandatory
	DESCRIPTION     
		"The number of disconnected mode U-frames sent. "
	::= { sdlcLinkCountEntry 11 }

sdlcLinkCountDMsRxs     OBJECT-TYPE
	SYNTAX  Counter
	ACCESS  read-only 
	STATUS  mandatory
	DESCRIPTION     
		"The number of disconnected mode U-frames received. "
	::= { sdlcLinkCountEntry 12 }

sdlcLinkCountFRMRsTxs   OBJECT-TYPE
	SYNTAX  Counter
	ACCESS  read-only 
	STATUS  mandatory
	DESCRIPTION     
		"The number of frame reject U-frames sent. "
	::= { sdlcLinkCountEntry 13 }

sdlcLinkCountFRMRsRxs   OBJECT-TYPE
	SYNTAX  Counter
	ACCESS  read-only 
	STATUS  mandatory
	DESCRIPTION     
		"The number of frame reject U-frames received. "
	::= { sdlcLinkCountEntry 14 }

sdlcLinkCountXIDsTxs    OBJECT-TYPE
	SYNTAX  Counter
	ACCESS  read-only 
	STATUS  mandatory
	DESCRIPTION     
		"The number of XID U-frames sent. "
	::= { sdlcLinkCountEntry 15 }

sdlcLinkCountXIDsRxs    OBJECT-TYPE
	SYNTAX  Counter
	ACCESS  read-only 
	STATUS  mandatory
	DESCRIPTION     
		"The number of XID U-frames received. "
	::= { sdlcLinkCountEntry 16 }

sdlcLinkCountINFOsTxs   OBJECT-TYPE
	SYNTAX  Counter
	ACCESS  read-only 
	STATUS  mandatory
	DESCRIPTION     
		"The number of information U-frames sent. "
	::= { sdlcLinkCountEntry 17 }

sdlcLinkCountINFOsRxs   OBJECT-TYPE
	SYNTAX  Counter
	ACCESS  read-only 
	STATUS  mandatory
	DESCRIPTION     
		"The number of information U-frames received. "
	::= { sdlcLinkCountEntry 18 }

sdlcLinkCountRRsTxs     OBJECT-TYPE
	SYNTAX  Counter
	ACCESS  read-only 
	STATUS  mandatory
	DESCRIPTION     
		"The number of receiver ready I-frames sent."
	::= { sdlcLinkCountEntry 19 }

sdlcLinkCountRRsRxs     OBJECT-TYPE
	SYNTAX  Counter
	ACCESS  read-only 
	STATUS  mandatory
	DESCRIPTION     
		"The number of receiver ready I-frames received."
	::= { sdlcLinkCountEntry 21 }

sdlcLinkCountRNRsTxs    OBJECT-TYPE
	SYNTAX  Counter
	ACCESS  read-only 
	STATUS  mandatory
	DESCRIPTION     
		"The number of receiver not ready I-frames sent."
	::= { sdlcLinkCountEntry 22 }

sdlcLinkCountRNRsRxs    OBJECT-TYPE
	SYNTAX  Counter
	ACCESS  read-only 
	STATUS  mandatory
	DESCRIPTION     
		"The number of receiver not ready I-frames received."
	::= { sdlcLinkCountEntry 23 }

sdlcLinkCountREJsTxs    OBJECT-TYPE
	SYNTAX  Counter
	ACCESS  read-only 
	STATUS  mandatory
	DESCRIPTION
		"The number of reject I-frames sent."
	::= { sdlcLinkCountEntry 24 }

sdlcLinkCountREJsRxs    OBJECT-TYPE
	SYNTAX  Counter
	ACCESS  read-only 
	STATUS  mandatory
	DESCRIPTION     
		"The number of reject I-frames received."
	::= { sdlcLinkCountEntry 25 }

sdlcLinkCountTestTxs    OBJECT-TYPE
	SYNTAX  Counter
	ACCESS  read-only 
	STATUS  mandatory
	DESCRIPTION     
		"The number of TEST U-frames sent."
	::= { sdlcLinkCountEntry 26 }

sdlcLinkCountTestRxs    OBJECT-TYPE
	SYNTAX  Counter
	ACCESS  read-only 
	STATUS  mandatory
	DESCRIPTION     
		"The number of TEST U-frames received."
	::= { sdlcLinkCountEntry 27 }

END
