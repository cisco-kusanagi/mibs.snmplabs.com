VERILINK-ENTERPRISE-NCMIMUX-MIB


--              FORCE-INCLUDE <stdio.h>
--              FORCE-INCLUDE <prepc.h>
--              FORCE-INCLUDE <snmp/asn1.h>
--              FORCE-INCLUDE <snmp/mib.h>
--              FORCE-INCLUDE <snmp/snmp.h>
--              FORCE-INCLUDE <snmp/snmpstat.h>
--              FORCE-INCLUDE <snmp/buildpkt.h>
--              FORCE-INCLUDE "vl.h"
--              FORCE-INCLUDE "vkmib.h"
--              FORCE-INCLUDE "vktrap.h"
--              FORCE-INCLUDE "mib2.h"
--

	-- Created:  Muralidhar.S in 1995.
	-- set up MIB-wide defaults
	-- all functions can use %n for object name and
	-- %t for object type, %p for parent name,
	-- %d for name of default-bearing node and %% for %

	  DEFINITIONS ::= BEGIN

     IMPORTS
	     DisplayString
		     FROM RFC1213-MIB
	     OBJECT-TYPE
		     FROM RFC-1212
         ncm-imux
             FROM VERILINK-ENTERPRISE-NCMALARM-MIB;

 
     --  This MIB module uses the extended OBJECT-TYPE macro as
     --  defined in RFC 1212.
     --  This MIB module uses the TRAP-TYPE macro as
     --  defined in RFC 1215.
     --  enterprises{iso(1).org(3).dod(6).intrnet(1).pvt(4).entrprs(1).
     --                                                    vlnk(321).as2000(1).x }

     --  Please update verilink.mib whenever a new entry is added
     --  or deleted

	 --    verilink         OBJECT IDENTIFIER ::= { enterprises 321 }
	 --    as2000           OBJECT IDENTIFIER ::= { verilink 1 }
	 --    ncm-imux         OBJECT IDENTIFIER ::= { as2000 3030 }
     

     -- The consists of following tables:
     --    Configuration
     --    Status       
     --    Control
     --    DTE Status 

     -- the ncm Imux Configuration Table

	 ncmimuxConfigTable OBJECT-TYPE
	     SYNTAX  SEQUENCE OF NcmimuxConfigEntry
	     ACCESS  not-accessible
	     STATUS  mandatory
	     DESCRIPTION
		"The IMUX Configuration table."
             --DEFAULT test-function   imx-test
             --DEFAULT next-function   imx-next
	    ::= { ncm-imux 7000 }


	 ncmimuxConfigEntry OBJECT-TYPE
	     SYNTAX  NcmimuxConfigEntry
	     ACCESS  not-accessible
	     STATUS  mandatory
	     DESCRIPTION
		"An entry in the ncm IMUX Configuration table."
	    -- INDEX   { ncmimuxLineIndex }
	    INDEX   { ncmimuxNIDConfigIndex, ncmimuxLineIndex }
	    ::= { ncmimuxConfigTable 1 }

     NcmimuxConfigEntry ::=
	 SEQUENCE {
	     ncmimuxNIDConfigIndex
		 INTEGER,	 
	     ncmimuxLineIndex
		 INTEGER,
	     ncmimuxEndId
		 INTEGER,       
	     ncmimuxIfIndex
		 INTEGER,
	     ncmimuxBkplaneBusSelect
		 INTEGER,
	     ncmimuxCarrierLineRate
		 INTEGER,
	     ncmimuxCarrierLinesEqp
		 DisplayString,
	     ncmimuxChanneling
		 INTEGER,
	     ncmimuxDTEClkTransmit
		 INTEGER,
	     ncmimuxDTEClkRecv
		 INTEGER,
	     ncmimuxDTEClkRefern
		 INTEGER,
	     ncmimuxDTEMode
		 INTEGER,
	     ncmimuxDSR
		 INTEGER,
	     ncmimuxTM
		 INTEGER,
	     ncmimuxCTS
		 INTEGER,
	     ncmimuxDCD
		INTEGER,
	     ncmimuxRI
		INTEGER,
	     ncmimuxSnapType
		INTEGER, 
	     ncmimuxQuadSlot 
		INTEGER 
	     
	 }

	ncmimuxNIDConfigIndex OBJECT-TYPE
	     SYNTAX  INTEGER (1..'7fffffff'h)
	     ACCESS  read-only
	     STATUS  mandatory
	     DESCRIPTION
		"This variable indicates the node id
		 value of the node."  
	       ::= { ncmimuxConfigEntry 1 }

	 ncmimuxLineIndex OBJECT-TYPE
	     SYNTAX  INTEGER (1..'7fffffff'h)
	     ACCESS  read-only
	     STATUS  mandatory
	     DESCRIPTION
		"This object is the identifier of a  Inter-
		face on a managed device.  If there is an ifEn-
		try that is directly associated with  this it 
		should have the same value as ifIndex. Otherwise,  
		the  value exceeds  ifNumber,  and  is a unique 
		identifier following this rule: inside  interfaces  (e.g.,
		equipment  side)  with even numbers and outside
		interfaces  (e.g.,  network   side)   with   odd
		numbers."
	    ::= { ncmimuxConfigEntry 2 }

	 ncmimuxEndId  OBJECT-TYPE
	     SYNTAX  INTEGER {
			near-End(1),
			far-End(2)
		     }   
	     ACCESS  read-only
	     STATUS  mandatory
	     DESCRIPTION
		"This value for this object indicates which
		 end of the equipment it is accessing."
	    ::= { ncmimuxConfigEntry 3 }

	 ncmimuxIfIndex OBJECT-TYPE
	     SYNTAX  INTEGER (1..'7fffffff'h)
	     ACCESS  read-only
	     STATUS  mandatory
	     DESCRIPTION
		"This value for this object  is  equal  to  the
		value  of  ifIndex from the Interfaces table of
		MIB II (RFC 1213)."
	    ::= { ncmimuxConfigEntry 4 }

         ncmimuxBkplaneBusSelect OBJECT-TYPE
             SYNTAX  INTEGER {
                        bus-AAAAAAAA(1),
                     	bus-AABBAABB(2),
                        bus-AACCAACC(3),
			bus-AADDAADD(4),
                        bus-BBAABBAA(5),
                        bus-BBBBBBBB(6),
                        bus-BBCCBBCC(7),
                        bus-BBDDBBDD(8),
                        bus-CCAACCAA(9),
                        bus-CCBBCCBB(10),
			bus-CCCCCCCC(11),
			bus-CCDDCCDD(12),
			bus-DDAADDAA(13),
			bus-DDBBDDBB(14),
			bus-DDCCDDCC(15),
			bus-DDDDDDDD(16),
			bus-XXEEXXEE(17),
			bus-EEXXEEXX(18)
                     }
             ACCESS  read-write
             STATUS  mandatory
             DESCRIPTION
                "This object only has signifiance for IMUX 2164. 
		 This variable specifies which IMUX line(s) is used,
		 and which backplane bus is assigned to which line(s).
		 The pattern of the the word is compsed as :-

		       line#     8 7 6 5 4 3 2 1 
		       bus # bus-B B D D B B D D(8)

		 means lines 1,2,5,6 use bus - B
		       lines 3,4,7,8 use bus - D	

		 The 'X' means no bus selection has been made."
            ::= { ncmimuxConfigEntry 5 }

	ncmimuxCarrierLineRate OBJECT-TYPE
	     SYNTAX  INTEGER {
			t1-rate(1),
			e1-rate(2)
		     }
	     ACCESS  read-write
	     STATUS  mandatory
	     DESCRIPTION
		"This variable specifies whether the carrier line rate is T1 or
		 carrier line is E1."
	    ::= { ncmimuxConfigEntry 6 }

	 ncmimuxCarrierLinesEqp OBJECT-TYPE
	     SYNTAX  DisplayString (SIZE(0..255))
	     ACCESS  read-write
	     STATUS  mandatory
	     DESCRIPTION
		"This variable indicates the inverse multiplexer 
		carrier lines equipped. One bit per line. Here each 
		bit in this byte represents one of the eight carrier 
		lines that may be used by the Imux. Bit zero represents 
		carrierline number one, and bit seven represents 
		carrier line number eight. For each bit that is set 
		to one, the corresponding carrier line will be configured 
		for use by the ncmimux. For each bit that is set to zero, 
		the corresponding carrier line will be excluded from the 
		ncmimux configuration i.e., 1 = 0000 0001(bin). The range 
		for this variable is from (in decimals 0 to 256)."
	    ::= { ncmimuxConfigEntry 7 }

	 ncmimuxChanneling OBJECT-TYPE
	     SYNTAX  INTEGER {
			mode-64k(1),
			mode-56k(2)
			     }                          
	     ACCESS  read-write
	     STATUS  mandatory
	     DESCRIPTION
		"This variable indicates the inverse multiplexer mode
		for T1 which by default is set to 64 Kbps and when the
		field is set to (1) the 56 kbps mode is selected."
	    ::= { ncmimuxConfigEntry 8 }

	 ncmimuxDTEClkTransmit OBJECT-TYPE
	     SYNTAX  INTEGER {
			normal(1),
			inverted(2)
		     }  
	     ACCESS  read-write
	     STATUS  mandatory
	     DESCRIPTION
		"This field request to determine the DTE data port clock 
		 phase is normal or inverted. 'Normal' refers to inverse 
		 multiplexer DTE clock phase is normal. 'Inverted' refers 
		 to inverse multiplexer DTE clock phase is inverted."
	    ::= { ncmimuxConfigEntry 9 }

	 ncmimuxDTEClkRecv OBJECT-TYPE
	     SYNTAX  INTEGER {
			normal(1),
			inverted(2)
		     }  
	     ACCESS  read-write
	     STATUS  mandatory
	     DESCRIPTION
		"This field request to determine the DTE data port clock 
		 phase is normal or inverted. 'Normal' refers to inverse 
		 multiplexer DTE clock phase is normal. 'Inverted' refers 
		 to inverse multiplexer DTE clock phase is inverted."
	    ::= { ncmimuxConfigEntry 10 }

	 ncmimuxDTEClkRefern OBJECT-TYPE
	     SYNTAX  INTEGER {
			normal(1),
			inverted(2)
		     }  
	     ACCESS  read-write
	     STATUS  mandatory
	     DESCRIPTION
		"This field request to determine the DTE data port clock 
		 phase is normal or inverted. 'Normal' refers to inverse 
		 multiplexer DTE clock phase is normal. 'Inverted' refers 
		 to inverse multiplexer DTE clock phase is inverted."
	    ::= { ncmimuxConfigEntry 11 }

	ncmimuxDTEMode OBJECT-TYPE
	     SYNTAX  INTEGER {
			automatic(1),
			manual(2)
		     }  
	     ACCESS  read-write
	     STATUS  mandatory
	     DESCRIPTION
		"This variable represents the DTE mode of the ncmimux"
	    ::= { ncmimuxConfigEntry 12 }


	ncmimuxDSR OBJECT-TYPE
	     SYNTAX  INTEGER {
			off(1),
			on(2)
		     }  
	     ACCESS  read-write
	     STATUS  mandatory
	     DESCRIPTION
		"This variable represents Data Set Ready for the ncmimux which
		could be set for all interfaces."
	    ::= { ncmimuxConfigEntry 13 }

	ncmimuxTM OBJECT-TYPE
	     SYNTAX  INTEGER {
			off(1),
			on(2)
		     }  
	     ACCESS  read-write
	     STATUS  mandatory
	     DESCRIPTION
		"This variable represents Test Mode for the ncmimux which
		could be set for all interfaces."
	    ::= { ncmimuxConfigEntry 14 }

	ncmimuxCTS OBJECT-TYPE
	     SYNTAX  INTEGER {
			off(1),
			on(2)
		     }  
	     ACCESS  read-write
	     STATUS  mandatory
	     DESCRIPTION
		"This variable represents Clear To Send for the ncmimux which
		could be set for only V.35, EI530 and RS449 interfaces."
	    ::= { ncmimuxConfigEntry 15 }


	ncmimuxDCD OBJECT-TYPE
	     SYNTAX  INTEGER {
			off(1),
			on(2)
		     }  
	     ACCESS  read-write
	     STATUS  mandatory
	     DESCRIPTION
		"This variable represents Data Carrier Detect for the ncmimux which
		could be set for only V.35, EI530 and RS449 interfaces."
	    ::= { ncmimuxConfigEntry 16 }


	ncmimuxRI OBJECT-TYPE
	     SYNTAX  INTEGER {
			off(1),
			on(2)
		     }  
	     ACCESS  read-write
	     STATUS  mandatory
	     DESCRIPTION
		"This variable represents Ring Indicator for the ncmimux which
		could be set for only V.35 interfaces."
	    ::= { ncmimuxConfigEntry 17 }



	ncmimuxSnapType OBJECT-TYPE
	     SYNTAX  INTEGER {
			unknown(1),
			hssi(2),
			v35(3),
			eia530a(4),
			eia530(5),
			rs449(6)
		     } 
	     ACCESS  read-only
	     STATUS  mandatory
	     DESCRIPTION
		"This variable represents the snap type for the ncmimux"
	    ::= { ncmimuxConfigEntry 18 }
 
 	ncmimuxQuadSlot OBJECT-TYPE
	     SYNTAX  INTEGER 
	     ACCESS  read-write
	     STATUS  mandatory
	     DESCRIPTION
		"This variable represents the DTE control mode of the ncmimux"
	    ::= { ncmimuxConfigEntry 19 }




     -- the ncm Imux Status Table
     -- This table gives the status of one carrierline at a time...

	 ncmimuxStatusTable OBJECT-TYPE
	     SYNTAX  SEQUENCE OF NcmimuxStatusEntry
	     ACCESS  not-accessible
	     STATUS  mandatory
	     DESCRIPTION
		"The IMUX Status table."
             --DEFAULT test-function   imx-test
             --DEFAULT next-function   imx-next
	    ::= { ncm-imux 7001 }


	 ncmimuxStatusEntry OBJECT-TYPE
	     SYNTAX  NcmimuxStatusEntry
	     ACCESS  not-accessible
	     STATUS  mandatory
	     DESCRIPTION
		"An entry in the IMUX Status table."
	    -- INDEX   { ncmimuxStatusIndex }
	    INDEX   { ncmimuxNIDStatusIndex, ncmimuxStatusIndex }
	    ::= { ncmimuxStatusTable 1 }

     NcmimuxStatusEntry ::=
	 SEQUENCE {
	     ncmimuxNIDStatusIndex
		 INTEGER,	 
	     ncmimuxStatusIndex
		 INTEGER,
	     ncmimuxStatEndId
		 INTEGER,       
	     ncmimuxLinesEqp
		 DisplayString,
	     ncmimuxLinesStat
		 DisplayString,
	     ncmimuxFrameStatus
		 DisplayString,
	     ncmimuxCTSStatus
		 DisplayString,
	     ncmimuxCRCStatus
		 DisplayString,
	     ncmimuxFarEndCRCStatus
		 DisplayString,
	     ncmimuxDataValidStatus
		 INTEGER,
	     ncmimuxNetworkAlarm
		 INTEGER,
	     ncmimuxAlarmLED
		 INTEGER,
	     ncmimuxEventMessages
		 INTEGER
	  }
	  
	ncmimuxNIDStatusIndex OBJECT-TYPE
	     SYNTAX  INTEGER (1..'7fffffff'h)
	     ACCESS  read-only
	     STATUS  mandatory
	     DESCRIPTION
		"This variable indicates the node id
		 value of the node."  
	       ::= { ncmimuxStatusEntry 1}

	 ncmimuxStatusIndex OBJECT-TYPE
	     SYNTAX  INTEGER (1..'7fffffff'h)
	     ACCESS  read-only
	     STATUS  mandatory
	     DESCRIPTION
		"This object is the identifier of a  Inter-
		face on a managed device.  If there is an ifEn-
		try that is directly associated with  this it 
		should have the same value as ifIndex. Otherwise,  
		the  value exceeds  ifNumber,  and  is a unique 
		identifier following this rule: inside  interfaces  (e.g.,
		equipment  side)  with even numbers and outside
		interfaces  (e.g.,  network   side)   with   odd
		numbers."
	    ::= { ncmimuxStatusEntry 2 }

	 ncmimuxStatEndId  OBJECT-TYPE
	     SYNTAX  INTEGER {
			near-End(1),
			far-End(2)
		     }   
	     ACCESS  read-only
	     STATUS  mandatory
	     DESCRIPTION
		"This value for this object indicates which
		 end of the equipment it is accessing."
	    ::= { ncmimuxStatusEntry 3 }

	 ncmimuxLinesEqp OBJECT-TYPE
	     SYNTAX  DisplayString (SIZE(0..255))
	     ACCESS  read-only
	     STATUS  mandatory
	     DESCRIPTION
		"This variable indicates the inverse multiplexer 
		carrier lines equipped. One bit per line. Here each 
		bit in this byte represents one of the eight carrier 
		lines that may be used by the Imux. Bit zero represents 
		carrierline number one, and bit seven represents 
		carrier line number eight. For each bit that is set 
		to one, the corresponding carrier line will be configured 
		for use by the ncmimux. For each bit that is set to zero, 
		the corresponding carrier line will be excluded from the 
		ncmimux configuration i.e., 1 = 0000 0001(bin). The range 
		for this variable is from (in decimals 0 to 256)."
	    ::= { ncmimuxStatusEntry 4 }

	 ncmimuxLinesStat OBJECT-TYPE
	     SYNTAX  DisplayString (SIZE(0..255))
	     ACCESS  read-only
	     STATUS  mandatory
	     DESCRIPTION
		" This represents the lines active equivalent in tabs message, 
		  indicating  when a carrier line has been allocated for use 
		  by the ncmimux. (Loop integrity must be established before the
		  line can be put into active service).Options supported 
		  active, inactive or none."
	    ::= { ncmimuxStatusEntry 5 }

	 ncmimuxFrameStatus OBJECT-TYPE
	     SYNTAX  DisplayString (SIZE(0..255))
	     ACCESS  read-only
	     STATUS  mandatory
	     DESCRIPTION
		" This variable indicates the ncmimux frame structure is transmitted over
		each carrier line that has been allocated for use by the ncmimux. This
		field indicates that this frame structure has been recongnized and 
		validated in the signal received on the carrier line or invalidated."
	    ::= { ncmimuxStatusEntry 6 }

	 ncmimuxCTSStatus OBJECT-TYPE
	     SYNTAX  DisplayString (SIZE(0..255))
	     ACCESS  read-only
	     STATUS  mandatory
	     DESCRIPTION
		" This variable indicates Clear To Send status that is encoded into
		 the ncmimux frame structure on each carrier line to indicate that the
		 integrity of the incoming signal has been validated. 'validCTS' 
		 refers to Clear To Send indication has been detected in the 
		 receive signal on the corresponding carrier line. 'invalidCTS' 
		 refers to Clear To send has not been detected. 'none' represents 
		 to not supported"
	    ::= { ncmimuxStatusEntry 7 }


	 ncmimuxCRCStatus OBJECT-TYPE
	     SYNTAX  DisplayString (SIZE(0..255))
	     ACCESS  read-only
	     STATUS  mandatory
	     DESCRIPTION
		" This variable represents the crc error of the incoming frame
		  structure corresponding to a Carrier Line." 
	    ::= { ncmimuxStatusEntry 8 }

	 ncmimuxFarEndCRCStatus OBJECT-TYPE
	     SYNTAX  DisplayString (SIZE(0..255))
	     ACCESS  read-only
	     STATUS  mandatory
	     DESCRIPTION
		" This variable represents the crc error of the incoming frame 
		  structure received at the far end of the corresponding 
		  Carrier Lines." 
	    ::= { ncmimuxStatusEntry 9 }
 
	 ncmimuxDataValidStatus OBJECT-TYPE
	  --   SYNTAX  DisplayString (SIZE(0..255))
	     SYNTAX  INTEGER 
	     ACCESS  read-only
	     STATUS  mandatory
	     DESCRIPTION
		" This variable represents the data valid of the  
		  Carrier Lines." 
	    ::= { ncmimuxStatusEntry 10 }
 
	 ncmimuxNetworkAlarm OBJECT-TYPE
	     SYNTAX  INTEGER {
			off(1),
			red(2),
			green(3),
			yellow(4),
			flashing-Red(5),
			flashing-Green(6),
			flashing-Yellow(7),
			flashing-Red-Green(8),
			flashing-Green-Yellow(9),
			flashing-Yellow-Red(10)
		     }   
	     ACCESS  read-only
	     STATUS  mandatory
	     DESCRIPTION
		"The value for this object indicates the front 
		 panel LED alarm status for the network interface."
	    ::= { ncmimuxStatusEntry 11 }

	 ncmimuxAlarmLED OBJECT-TYPE
	     SYNTAX  INTEGER {
                        off(1),
                        red(2),
                        green(3),
                        yellow(4),
                        flashing-Red(5),
                        flashing-Green(6),
                        flashing-Yellow(7),
                        flashing-Red-Green(8),
                        flashing-Green-Yellow(9),
                        flashing-Yellow-Red(10)
		     }   
	     ACCESS  read-only
	     STATUS  mandatory
	     DESCRIPTION
		"The value for this object indicates the front 
		 panel LED alarm status for the IMux."
	    ::= { ncmimuxStatusEntry 12 }

	 ncmimuxEventMessages OBJECT-TYPE
	     SYNTAX  INTEGER (1..'7fffffff'h)
	     ACCESS  read-only
	     STATUS  mandatory
	     DESCRIPTION
		"The value for this object indicates the number 
		 of event messages in the event queue.  The event queue
		 is a list of state changes which are time-stamped and 
		 recorded. "
	    ::= { ncmimuxStatusEntry 13 }

     -- the  ncm Imux Control Table

	 ncmimuxControlTable OBJECT-TYPE
	     SYNTAX  SEQUENCE OF NcmimuxControlEntry
	     ACCESS  not-accessible
	     STATUS  mandatory
	     DESCRIPTION
		"The IMUX Control table."
             --DEFAULT test-function   imx-test
             --DEFAULT next-function   imx-next
	    ::= { ncm-imux 7002 }


	 ncmimuxControlEntry OBJECT-TYPE
	     SYNTAX  NcmimuxControlEntry
	     ACCESS  not-accessible
	     STATUS  mandatory
	     DESCRIPTION
		"An entry in the IMUX Control table."
	    -- INDEX   { ncmimuxControlIndex }
	    INDEX   { ncmimuxNIDControlIndex, ncmimuxControlIndex }
	    ::= { ncmimuxControlTable 1 }

     NcmimuxControlEntry ::=
	 SEQUENCE {
	     ncmimuxNIDControlIndex
		 INTEGER,	 
	     ncmimuxControlIndex
		 INTEGER,
	     ncmimuxCntEndId
		 INTEGER,
	     ncmimuxLoopback 
		 INTEGER,
	     ncmimuxAISPattern 
		 INTEGER,
	     ncmimuxTestPattern
		 INTEGER
	 }

	ncmimuxNIDControlIndex OBJECT-TYPE
	     SYNTAX  INTEGER (1..'7fffffff'h)
	     ACCESS  read-only
	     STATUS  mandatory
	     DESCRIPTION
		"This variable indicates the node id
		 value of the node."  
	       ::= { ncmimuxControlEntry 1 }

	 ncmimuxControlIndex OBJECT-TYPE
	     SYNTAX  INTEGER (1..'7fffffff'h)
	     ACCESS  read-only
	     STATUS  mandatory
	     DESCRIPTION
		"This object is the identifier of a  Inter-
		face on a managed device.  If there is an ifEn-
		try that is directly associated with  this it 
		should have the same value as ifIndex. Otherwise,  
		the  value exceeds  ifNumber,  and  is a unique 
		identifier following this rule: inside  interfaces  (e.g.,
		equipment  side)  with even numbers and outside
		interfaces  (e.g.,  network   side)   with   odd
		numbers."
	    ::= { ncmimuxControlEntry 2 }


	 ncmimuxCntEndId  OBJECT-TYPE
	     SYNTAX  INTEGER {
			near-End(1),
			far-End(2)
		     }   
	     ACCESS  read-only
	     STATUS  mandatory
	     DESCRIPTION
		"This value for this object indicates which
		 end of the equipment it is accessing."
	    ::= { ncmimuxControlEntry 3 }

	 ncmimuxLoopback OBJECT-TYPE
	     SYNTAX  INTEGER {
			no-ELB-AND-PLB(1),
			actv-ELB(2),
			actv-PLB(3),
			actv-ELB-AND-PLB(4),
			deactv-ELB(5),
			deactv-PLB(6)
		}
	     ACCESS  read-write
	     STATUS  mandatory
	     DESCRIPTION
		" This variable represents the Loopback status of Imux,
		  ELB or PLB i.e., Equipment Loop back or Payload loop
		  back."
	    ::= { ncmimuxControlEntry 4 }

	 ncmimuxAISPattern OBJECT-TYPE
	     SYNTAX  INTEGER {
			disable(1),
			all-Ones(2),
			all-Zeros(3)
		     }
	     ACCESS  read-write
	     STATUS  mandatory
	     DESCRIPTION
		" This refers to the AIS test pattern initiated"
	    ::= { ncmimuxControlEntry 5 }

	ncmimuxTestPattern OBJECT-TYPE
	     SYNTAX  INTEGER {
			disable(1),
			pat-127(2),
			inv-Pat-127(3)
		 }
	     ACCESS  read-only
	     STATUS  mandatory
	     DESCRIPTION
		" This refers to the test pattern initiated"
	    ::= { ncmimuxControlEntry 6 }


     -- the ncm DTE Status Table
     -- This table gives the DTE status 

	 ncmimuxDTEStatTable OBJECT-TYPE
	     SYNTAX  SEQUENCE OF NcmimuxDTEStatEntry
	     ACCESS  not-accessible
	     STATUS  mandatory
	     DESCRIPTION
		"The IMUX DTE Status table."
             --DEFAULT test-function   imx-test
             --DEFAULT next-function   imx-next
	    ::= { ncm-imux 7003 }


	 ncmimuxDTEStatEntry OBJECT-TYPE
	     SYNTAX  NcmimuxDTEStatEntry
	     ACCESS  not-accessible
	     STATUS  mandatory
	     DESCRIPTION
		"An entry in the IMUX DTEStatus table."
	    -- INDEX   { ncmimuxDTEStatIndex }
	    INDEX   { ncmimuxNIDDTEStatIndex, ncmimuxDTEStatIndex }
	    ::= { ncmimuxDTEStatTable 1 }

     NcmimuxDTEStatEntry ::=
	 SEQUENCE {
	     ncmimuxNIDDTEStatIndex
		 INTEGER,	 
	     ncmimuxDTEStatIndex
		 INTEGER,
	     ncmimuxDTEStatReg
		 INTEGER,       
	     ncmimuxDTEStatLPBK
		 INTEGER,       
	     ncmimuxDTEStatAlarm
		 INTEGER       
	  }
	  
	ncmimuxNIDDTEStatIndex OBJECT-TYPE
	     SYNTAX  INTEGER (1..'7fffffff'h)
	     ACCESS  read-only
	     STATUS  mandatory
	     DESCRIPTION
		"This variable indicates the node id
		 value of the node."  
	       ::= { ncmimuxDTEStatEntry 1}

	 ncmimuxDTEStatIndex OBJECT-TYPE
	     SYNTAX  INTEGER (1..'7fffffff'h)
	     ACCESS  read-only
	     STATUS  mandatory
	     DESCRIPTION
		"This object is the identifier of a  Inter-
		face on a managed device.  If there is an ifEn-
		try that is directly associated with  this it 
		should have the same value as ifIndex. Otherwise,  
		the  value exceeds  ifNumber,  and  is a unique 
		identifier following this rule: inside  interfaces  (e.g.,
		equipment  side)  with even numbers and outside
		interfaces  (e.g.,  network   side)   with   odd
		numbers."
	    ::= { ncmimuxDTEStatEntry 2 }

	 ncmimuxDTEStatReg OBJECT-TYPE
	     SYNTAX  INTEGER {
			hSSI-DTR(1),
			hSSI-Loopback-A(2),
			hSSI-Loopback-B(3),
			v35-RTS(4),
			v54-RL(5),
			v54-LL(6)
		     }   
	     ACCESS  read-only
	     STATUS  mandatory
	     DESCRIPTION
	       "This object reports the contents of the DTE 
		Status Register as read from the IMUX hardware."
	    ::= { ncmimuxDTEStatEntry 3 }
 
	 ncmimuxDTEStatLPBK OBJECT-TYPE
	     SYNTAX  INTEGER {
			v54-LoopUp(1),
			v54-Ptrn-Loop-Errors(2),
			v54-LoopDown(3),
			v35-LoopDown-Errors(4),
			pRBS(5)
		     }   
	     ACCESS  read-only
	     STATUS  mandatory
	     DESCRIPTION
		"This object reports the DTE Pattern and Loopback 
		 Code Register Status.  (0) indicates that a Loop Up
		 Code was detected.  (1) indicates that Data Pattern 
		 or Loop Up Code errors were detected.  (2) indicates
		 a Loop Down Code was detected. (3) indicates Loop Down
		 Code Errors were detected.  (4) indicates PRBS 2 x 10^25 
		 Aggregate Data Bandwidth. "
	    ::= { ncmimuxDTEStatEntry 4 }

	 ncmimuxDTEStatAlarm OBJECT-TYPE
	     SYNTAX  INTEGER {
			off(1),
			red(2),
			green(3),
			yellow(4),
			flashing-Red(5),
			flashing-Green(6),
			flashing-Yellow(7),
			flashing-Red-Green(8),
			flashing-Green-Yellow(9),
			flashing-Yellow-Red(10)
		     }   
	     ACCESS  read-only
	     STATUS  mandatory
	     DESCRIPTION
	       "This object reports the front panel alarm LED status for 
		the DTE interface.  "
	    ::= { ncmimuxDTEStatEntry 5 }



	END
