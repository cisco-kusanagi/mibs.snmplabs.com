ONEFS-SNAPSHOT-MIB DEFINITIONS ::= BEGIN

IMPORTS
	MODULE-IDENTITY, OBJECT-TYPE,
	Integer32, Unsigned32, Counter32, Counter64, TimeTicks
		FROM SNMPv2-SMI
	TEXTUAL-CONVENTION, PhysAddress, MacAddress, DisplayString
		FROM SNMPv2-TC
	IpAddress
		FROM RFC1155-SMI
	MODULE-COMPLIANCE, OBJECT-GROUP, NOTIFICATION-GROUP
		FROM SNMPv2-CONF
	onefs, TimeTicks64
		FROM ONEFS-MIB;

oneFSss	MODULE-IDENTITY
	LAST-UPDATED "0201172301Z"
	ORGANIZATION "COMPANY_NAME"
	CONTACT-INFO
		"COMPANY_NAME
		 Support phone: SUPPORT_PHONE
		 Support email: SUPPORT_EMAIL
		"
	DESCRIPTION
	       "This is the OneFS statistics MIB"
	::= { onefs 3 }

-- oneFSss (oneFS Statistics Snapshot)

ssVersion		OBJECT-TYPE
	SYNTAX		DisplayString
	MAX-ACCESS	read-only
	STATUS		current
	DESCRIPTION
		"The version number of this onefs snapshot"
	DEFVAL		{ 0}
	::= { oneFSss 1 }

ssLocalNodeId		OBJECT-TYPE
	SYNTAX		Integer32 (0..65535)
	MAX-ACCESS	read-only
	STATUS		current
	DESCRIPTION
	       "The array identification number of this device
	       equivalent to the logical node number
	    	"
	DEFVAL		{ 0}
	::= { oneFSss 2 }

ssTimeStart		OBJECT-TYPE
	SYNTAX		TimeTicks64
	MAX-ACCESS	read-only
	STATUS		current
	DESCRIPTION
	       "Start time of this interval"
	DEFVAL		{ 0}
	::= { oneFSss 3 }

ssTimeEnd		OBJECT-TYPE
	SYNTAX		TimeTicks64
	MAX-ACCESS	read-only
	STATUS		current
	DESCRIPTION
	       "End time of this interval"
	DEFVAL		{ 0}
	::= { oneFSss 4 }

ssGlobal		OBJECT IDENTIFIER ::= { oneFSss 5 }

ssNodeInfo		OBJECT IDENTIFIER ::= { oneFSss 6 }

------------------------------------------------------------------------
--ssGlobal
ssDisk			OBJECT IDENTIFIER ::= { ssGlobal 1 }
ssNet			OBJECT IDENTIFIER ::= { ssGlobal 2 }
ssSystem		OBJECT IDENTIFIER ::= { ssGlobal 3 }

-- (2)ssDisk 
ssFreeBlocks		OBJECT-TYPE
	SYNTAX		Counter64
	MAX-ACCESS	read-only
	STATUS		current
	DESCRIPTION
		"Free Blocks on this cluster"
	DEFVAL		{ 0}
	::= { ssDisk 1 }

ssTotalBlocks		OBJECT-TYPE
	SYNTAX		Counter64
	MAX-ACCESS	read-only
	STATUS		current
	DESCRIPTION
		"Total number of blocks in the cluster"
	DEFVAL		{ 0}
	::= { ssDisk 2 }

ssAvailableBlocks	OBJECT-TYPE
	SYNTAX		Counter64
	MAX-ACCESS	read-only
	STATUS		current
	DESCRIPTION
		"Number of available blocks in the cluster"
	DEFVAL		{ 0}
	::= { ssDisk 3 }

ssBlockSize		OBJECT-TYPE
	SYNTAX		Integer32
	MAX-ACCESS	read-only
	STATUS		current
	DESCRIPTION
		"Size of the oneFS blocks"
	DEFVAL		{ 0}
	::= { ssDisk 4 }

-- (2)ssNet
ssNetBytesIn		OBJECT-TYPE
	SYNTAX		Counter64
	MAX-ACCESS	read-only
	STATUS		current
	DESCRIPTION
		"Total Number of bytes into the cluster"
	DEFVAL		{ 0}
	::= { ssNet 3 }

ssNetBytesOut		OBJECT-TYPE
	SYNTAX		Counter64
	MAX-ACCESS	read-only
	STATUS		current
	DESCRIPTION
		"Total number of bytes out of the cluster"
	DEFVAL		{ 0}
	::= { ssNet 4 }

ssFilesystemBytesIn	OBJECT-TYPE
	SYNTAX		Counter64
	MAX-ACCESS	read-only
	STATUS		current
	DESCRIPTION
		"Number of bytes into the filesystem"
	DEFVAL		{ 0}
	::= { ssNet 5 }

ssFilesystemBytesOut	OBJECT-TYPE
	SYNTAX		Counter64
	MAX-ACCESS	read-only
	STATUS		current
	DESCRIPTION
		"Number of bytes out of the filesystem"
	DEFVAL		{ 0}
	::= { ssNet 6 }

ssNetBitsPerSecIn	OBJECT-TYPE
	SYNTAX		Counter64
	MAX-ACCESS	read-only
	STATUS		current
	DESCRIPTION
		"Total bits/sec into the cluster"
	DEFVAL		{ 0}
	::= { ssNet 9 }

ssNetBitsPerSecOut	OBJECT-TYPE
	SYNTAX		Counter64
	MAX-ACCESS	read-only
	STATUS		current
	DESCRIPTION
		"Total bits/sec out of the cluster"
	DEFVAL		{ 0}
	::= { ssNet 10 }

ssFilesystemBitsPerSecIn	OBJECT-TYPE
	SYNTAX		Counter64
	MAX-ACCESS	read-only
	STATUS		current
	DESCRIPTION
		"Bits/sec into the filesystem"
	DEFVAL		{ 0}
	::= { ssNet 11 }

ssFilesystemBitsPerSecOut	OBJECT-TYPE
	SYNTAX		Counter64
	MAX-ACCESS	read-only
	STATUS		current
	DESCRIPTION
		"Bits/sec out of the filesystem"
	DEFVAL		{ 0}
	::= { ssNet 12 }


-- (2)ssSystem
ssClusterName		OBJECT-TYPE
	SYNTAX		DisplayString
	MAX-ACCESS	read-only
	STATUS		current
	DESCRIPTION
		"The cluster name"
	DEFVAL		{ 0}
	::= { ssSystem 1 }

ssClusterHealth		OBJECT-TYPE
	SYNTAX		DisplayString
	MAX-ACCESS	read-only
	STATUS		current
	DESCRIPTION
		"Health Status of Cluster"
	DEFVAL		{ 0}
	::= { ssSystem 4 }

ssConfiguredNodes	OBJECT-TYPE
	SYNTAX		Integer32 (0..65535)
	MAX-ACCESS	read-only
	STATUS		current
	DESCRIPTION
		"The number of devices currently configured to be in the cluster
		"
	DEFVAL		{ 0}
	::= { ssSystem 5 }

ssOnlineNodes		OBJECT-TYPE
	SYNTAX		Integer32 (0..65535)
	MAX-ACCESS	read-only
	STATUS		current
	DESCRIPTION
		"The number of devices in the cluster currently online"
	DEFVAL		{ 0}
	::= { ssSystem 6 }

-- NodeInfoTables

ssNodeTable		OBJECT-TYPE
	SYNTAX		SEQUENCE OF SsNodeEntry
	MAX-ACCESS	not-accessible
	STATUS		current
	DESCRIPTION
	       "Table of oneFS machines"
	::= { ssNodeInfo 1 }

ssNodeEntry		OBJECT-TYPE
	SYNTAX		SsNodeEntry
	MAX-ACCESS	not-accessible
	STATUS		current
	DESCRIPTION
	       "Table of oneFS machines"
	INDEX	{ ssNodeIndex }
	::= { ssNodeTable 1 } 
SsNodeEntry		::= SEQUENCE {
	ssNodeIndex			Integer32,
	ssNodeFreeBlocks		Counter64,
	ssNodeTotalBlocks		Counter64,
	ssNodeAvailBlocks		Counter64,
	ssNodeNetBytesIn		Counter64,
	ssNodeNetBytesOut		Counter64,
	ssNodeMACaddress		PhysAddress,
	ssNodeIPaddress			IpAddress,
	ssNodeVersion			DisplayString,
	ssNodeBoottime			TimeTicks64,
	ssNodeHealth			DisplayString,
	ssNodeCPUload			Integer32,
	ssNodeFilesystemBytesIn		Counter64,
	ssNodeFilesystemBytesOut	Counter64,
	ssNodeNumberOfDisks		Integer32,
	ssNodeNumberOfSensors		Integer32,
	ssNodeNetBitsIn			Counter64,
	ssNodeNetBitsOut		Counter64,
	ssNodeFilesystemBitsIn		Counter64,
	ssNodeFilesystemBitsOut		Counter64,
	ssNodeNetBitsPerSecIn		Counter64,
	ssNodeNetBitsPerSecOut		Counter64,
	ssNodeFilesystemBitsPerSecIn	Counter64,
	ssNodeFilesystemBitsPerSecOut	Counter64,
	ssNodeCPUuser			Integer32,
	ssNodeCPUnice			Integer32,
	ssNodeCPUsystem			Integer32,
	ssNodeCPUinterrupt		Integer32,
	ssNodeCPUidle			Integer32
}

ssNodeIndex		OBJECT-TYPE
	SYNTAX		Integer32
	MAX-ACCESS	read-only
	STATUS		current
	DESCRIPTION
	       "The logical node number of this device
		   "
	DEFVAL		{ 0 } 
	::= { ssNodeEntry 1 }

ssNodeFreeBlocks	OBJECT-TYPE
	SYNTAX		Counter64
	MAX-ACCESS	read-only
	STATUS		current
	DESCRIPTION
	       "The number of oneFS free blocks equivalent to sysctl
		efs.lbm.free_blocks on this machine
	       "
	DEFVAL		{ 0 } 
	::= { ssNodeEntry 2 }

ssNodeTotalBlocks	OBJECT-TYPE
	SYNTAX		Counter64
	MAX-ACCESS	read-only
	STATUS		current
	DESCRIPTION
	       "The number of oneFS total blocks.
                Equivalent to sysctl efs.lbm.total_blocks on this machine"
	DEFVAL		{ 0 } 
	::= { ssNodeEntry 3 }

ssNodeAvailBlocks	OBJECT-TYPE
	SYNTAX		Counter64
	MAX-ACCESS	read-only
	STATUS		current
	DESCRIPTION
	       "The number of oneFS available blocks. 
                Equivalent to sysctl efs.lbm.free_blocks on this machine"
	DEFVAL		{ 0 } 
	::= { ssNodeEntry 4 }

ssNodeLnn		OBJECT-TYPE
	SYNTAX		Integer32
	MAX-ACCESS	read-only
	STATUS		current
	DESCRIPTION
	       "The logical node number of this device."
	DEFVAL		{ 0 } 
	::= { ssNodeEntry 5 }

ssNodeDiskless		OBJECT-TYPE
	SYNTAX		Integer32
	MAX-ACCESS	read-only
	STATUS		current
	DESCRIPTION
	       "The diskless state of this device."
	DEFVAL		{ 0 } 
	::= { ssNodeEntry 6 }

ssNodeNetBytesIn	OBJECT-TYPE
	SYNTAX		Counter64
	MAX-ACCESS	read-only
	STATUS		current
	DESCRIPTION
		"Total Network traffic into the device not including local
		 overhead.
		"
	DEFVAL		{ 0}
	::= { ssNodeEntry 7 }

ssNodeNetBytesOut	OBJECT-TYPE
	SYNTAX		Counter64
	MAX-ACCESS	read-only
	STATUS		current
	DESCRIPTION
		"Total Network traffic into the device not including local
		 overhead.
		"
	DEFVAL		{ 0}
	::= { ssNodeEntry 8 }

ssNodeMACaddress	OBJECT-TYPE
	SYNTAX		PhysAddress
	MAX-ACCESS	read-only
	STATUS		current
	DESCRIPTION
		"MacAddress of the device"
	DEFVAL		{ 0}
	::= { ssNodeEntry 9 }

ssNodeIPaddress		OBJECT-TYPE
	SYNTAX		IpAddress
	MAX-ACCESS	read-only
	STATUS		current
	DESCRIPTION
		"Internal IP address of the device"
	DEFVAL		{ 0}
	::= { ssNodeEntry 10 }

ssNodeVersion		OBJECT-TYPE
	SYNTAX		DisplayString
	MAX-ACCESS	read-only
	STATUS		current
	DESCRIPTION
		"Isilon IQ version"
	DEFVAL		{ 0}
	::= { ssNodeEntry 11 }

ssNodeBoottime		OBJECT-TYPE
	SYNTAX		TimeTicks64
	MAX-ACCESS	read-only
	STATUS		current
	DESCRIPTION
		""
	DEFVAL		{ 0}
	::= { ssNodeEntry 12 }

ssNodeHealth		OBJECT-TYPE
	SYNTAX		DisplayString
	MAX-ACCESS	read-only
	STATUS		current
	DESCRIPTION
		""
	DEFVAL		{ 0}
	::= { ssNodeEntry 13 }

ssNodeCPUload		OBJECT-TYPE
	SYNTAX		Integer32
	MAX-ACCESS	read-only
	STATUS		current
	DESCRIPTION
		"Local CPU load based on the kern.cp_time sysctl"
	DEFVAL		{ 0}
	::= { ssNodeEntry 14 }

ssNodeFilesystemBytesIn	OBJECT-TYPE
	SYNTAX		Counter64
	MAX-ACCESS	read-only
	STATUS		current
	DESCRIPTION
		"Number of bytes into the filesystem"
	DEFVAL		{ 0}
	::= { ssNodeEntry 15 }

ssNodeFilesystemBytesOut	OBJECT-TYPE
	SYNTAX		Counter64
	MAX-ACCESS	read-only
	STATUS		current
	DESCRIPTION
		"Number of bytes out of the filesystem"
	DEFVAL		{ 0}
	::= { ssNodeEntry 16 }

ssNodeNumberOfDisks	OBJECT-TYPE
	SYNTAX		Integer32
	MAX-ACCESS	read-only
	STATUS		current
	DESCRIPTION
		"Number of disks on the appliance"
	DEFVAL		{ 0}
	::= { ssNodeEntry 17 }

ssNodeNumberOfSensors	OBJECT-TYPE
	SYNTAX		Integer32
	MAX-ACCESS	read-only
	STATUS		current
	DESCRIPTION
		"Number of hardware sensors on the appliance"
	DEFVAL		{ 0}
	::= { ssNodeEntry 18 }

ssNodeNetBitsPerSecIn		OBJECT-TYPE
	SYNTAX			Counter64
	MAX-ACCESS		read-only
	STATUS			current
	DESCRIPTION
		""
	DEFVAL		{ 0 }
	::= { ssNodeEntry 20 }

ssNodeNetBitsPerSecOut		OBJECT-TYPE
	SYNTAX			Counter64
	MAX-ACCESS		read-only
	STATUS			current
	DESCRIPTION
		""
	DEFVAL		{ 0 }
	::= { ssNodeEntry 21 }

ssNodeFilesystemBitsPerSecIn	OBJECT-TYPE
	SYNTAX			Counter64
	MAX-ACCESS		read-only
	STATUS			current
	DESCRIPTION
		""
	DEFVAL		{ 0 }
	::= { ssNodeEntry 22 }

ssNodeFilesystemBitsPerSecOut	OBJECT-TYPE
	SYNTAX			Counter64
	MAX-ACCESS		read-only
	STATUS			current
	DESCRIPTION
		""
	DEFVAL		{ 0 }
	::= { ssNodeEntry 23 }

ssNodeCPUuser		OBJECT-TYPE
	SYNTAX		Integer32
	MAX-ACCESS	read-only
	STATUS		current
	DESCRIPTION
	       "Local CPU % used by user "
	DEFVAL		{ 0}
	::= { ssNodeEntry 24 }

ssNodeCPUnice		OBJECT-TYPE
	SYNTAX		Integer32
	MAX-ACCESS	read-only
	STATUS		current
	DESCRIPTION
	       "Local CPU % used by nice'd proccesses"
	DEFVAL		{ 0}
	::= { ssNodeEntry 25 }

ssNodeCPUsystem		OBJECT-TYPE
	SYNTAX		Integer32
	MAX-ACCESS	read-only
	STATUS		current
	DESCRIPTION
	       "Local CPU % used by system "
	DEFVAL		{ 0}
	::= { ssNodeEntry 26 }

ssNodeCPUinterrupt	OBJECT-TYPE
	SYNTAX		Integer32
	MAX-ACCESS	read-only
	STATUS		current
	DESCRIPTION
	       "Local CPU % used by interrupts "
	DEFVAL		{ 0}
	::= { ssNodeEntry 27 }

ssNodeCPUidle		OBJECT-TYPE
	SYNTAX		Integer32
	MAX-ACCESS	read-only
	STATUS		current
	DESCRIPTION
	       "Local CPU % idle"
	DEFVAL		{ 0}
	::= { ssNodeEntry 28 }

ssNodeDevId		OBJECT-TYPE
	SYNTAX		Integer32
	MAX-ACCESS	read-only
	STATUS		current
	DESCRIPTION
		  "The array identification number of this device
		   equivalent to sysctl efs.rbm.array_id on this machine
		  "
	DEFVAL		{ 0 } 
	::= { ssNodeEntry 29 }

ssDiskInfoTable		OBJECT-TYPE
	SYNTAX		SEQUENCE OF SsDiskInfoEntry
	MAX-ACCESS	not-accessible
	STATUS		current
	DESCRIPTION
	       "Table of oneFS machines"
	::= { ssNodeInfo 2 }

ssDiskInfoEntry		OBJECT-TYPE
	SYNTAX		SsDiskInfoEntry
	MAX-ACCESS	not-accessible
	STATUS		current
	DESCRIPTION
	       "Table of oneFS machines"
	INDEX	{ ssNodeIndex, ssDiskIndex }
	::= { ssDiskInfoTable 1 } 
	
SsDiskInfoEntry		::= SEQUENCE {
	ssDiskIndex		Integer32,
	ssDiskName		DisplayString,
	ssDiskHealth		INTEGER,
	ssDiskBytesRead		Counter64,
	ssDiskBytesWritten	Counter64,
	ssDiskNumXfers		Counter64,
	ssDiskBitsPerSecRead	Counter64,
	ssDiskBitsPerSecWritten	Counter64,
	ssDiskXfersPerSec	Counter64
}

-- (3)ssDiskInfoTable
ssDiskIndex		OBJECT-TYPE
	SYNTAX		Integer32
	MAX-ACCESS	read-only
	STATUS		current
	DESCRIPTION
		"Index of the ssDiskInfoTable, also the disk number"
	DEFVAL		{ 0}
	::= { ssDiskInfoEntry 1 }

ssDiskName		OBJECT-TYPE
	SYNTAX		DisplayString
	MAX-ACCESS	read-only
	STATUS		current
	DESCRIPTION
		"Name of the disk i.e. ad0"
	DEFVAL		{ 0}
	::= { ssDiskInfoEntry 2 }

ssDiskHealth		OBJECT-TYPE
	SYNTAX		INTEGER {
			    red(0),
			    green(1)
			}
	MAX-ACCESS	read-only
	STATUS		current
	DESCRIPTION
		"Current status of a disk"
	DEFVAL		{ 0}
	::= { ssDiskInfoEntry 3 }

ssDiskBytesRead	OBJECT-TYPE
	SYNTAX		Counter64
	MAX-ACCESS	read-only
	STATUS		current
	DESCRIPTION
		"Bytes read on this disk"
	DEFVAL		{ 0}
	::= { ssDiskInfoEntry 4 }

ssDiskBytesWritten	OBJECT-TYPE
	SYNTAX		Counter64
	MAX-ACCESS	read-only
	STATUS		current
	DESCRIPTION
		"Bytes written on this disk"
	DEFVAL		{ 0}
	::= { ssDiskInfoEntry 5 }

ssDiskNumXfers		OBJECT-TYPE
	SYNTAX		Counter64
	MAX-ACCESS	read-only
	STATUS		current
	DESCRIPTION
		"Number of transfers to and from this disk"
	DEFVAL		{ 0}
	::= { ssDiskInfoEntry 6 }

ssDiskBitsPerSecRead	OBJECT-TYPE
	SYNTAX		Counter64
	MAX-ACCESS	read-only
	STATUS		current
	DESCRIPTION
		"Bits per sec read from this disk"
	DEFVAL		{ 0}
	::= { ssDiskInfoEntry 7 }

ssDiskBitsPerSecWritten	OBJECT-TYPE
	SYNTAX		Counter64
	MAX-ACCESS	read-only
	STATUS		current
	DESCRIPTION
		"Bits per sec written on this disk"
	DEFVAL		{ 0}
	::= { ssDiskInfoEntry 8 }

ssDiskXfersPerSec	OBJECT-TYPE
	SYNTAX		Counter64
	MAX-ACCESS	read-only
	STATUS		current
	DESCRIPTION
		"Number of thousandths of transfers per second to and from this 
		 disk
		"
	DEFVAL		{ 0}
	::= { ssDiskInfoEntry 9 }

ssSensorInfoTable	OBJECT-TYPE
	SYNTAX		SEQUENCE OF SsSensorInfoEntry
	MAX-ACCESS	not-accessible
	STATUS		current
	DESCRIPTION
	       "Table of oneFS machines"
	::= { ssNodeInfo 3 }

ssSensorInfoEntry		OBJECT-TYPE
	SYNTAX		SsSensorInfoEntry
	MAX-ACCESS	not-accessible
	STATUS		current
	DESCRIPTION
	       "Table of oneFS machines"
	INDEX	{ ssNodeIndex, ssDiskIndex }
	::= { ssSensorInfoTable 1 } 
	
SsSensorInfoEntry		::= SEQUENCE {
	ssSensorDescriptionName	DisplayString,
	ssSensorType		Integer32,
	ssSensorValue		DisplayString
}

-- (3)ssSensorInfoTable
ssSensorDescriptionName		OBJECT-TYPE
	SYNTAX		DisplayString
	MAX-ACCESS	read-only
	STATUS		current
	DESCRIPTION
		"Description of the hardware sensor; e.g. Temp Front Panel"
	DEFVAL		{ 0}
	::= { ssSensorInfoEntry 1 }

ssSensorType		OBJECT-TYPE
	SYNTAX		Integer32
	MAX-ACCESS	read-only
	STATUS		current
	DESCRIPTION
		"Type of hardware sensor: fan, voltage, or temperature."
	DEFVAL		{ 0}
	::= { ssSensorInfoEntry 2 }

ssSensorValue OBJECT-TYPE
	SYNTAX		DisplayString
	MAX-ACCESS	read-only
	STATUS		current
	DESCRIPTION
		"Current value of sensor."
	DEFVAL		{ 0}
	::= { ssSensorInfoEntry 3 }

END
