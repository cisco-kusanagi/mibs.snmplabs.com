Event-MIB DEFINITIONS ::= BEGIN
	IMPORTS
             OBJECT-TYPE, MODULE-IDENTITY, Counter32, IpAddress
                  FROM SNMPv2-SMI
             TruthValue, DisplayString
                  FROM SNMPv2-TC
             common, UsrConfigStatus
                  FROM USR-DEFINITIONS-MIB;
usrEventHandler MODULE-IDENTITY
         LAST-UPDATED "200203181400Z"
         ORGANIZATION "CommWorks Corporation, a 3Com Company"
         CONTACT-INFO "Customer Support"
         DESCRIPTION
                 "The commWorks enterprise defined MIB objects
                   for the Event Handling Process."
--      REVISION "200203181400Z"
--      DESCRIPTION "Converted to SNMPv2"
::= { common 9 }
   -- textual conventions
   -- Begin managed object definitions here...
usrEhVersion OBJECT-TYPE
	SYNTAX		DisplayString
	MAX-ACCESS	read-only
	STATUS		current
	DESCRIPTION
		"The current software version of the Event Handler process.."
::= { usrEventHandler 1 }
usrEhConfigFileName OBJECT-TYPE
	SYNTAX		DisplayString
	MAX-ACCESS	read-only
	STATUS		current
	DESCRIPTION		
		  "The name of a ConfigFile to read/write permanent database 
                   records. If the value of this object is an empty string, 
                   then the Event process uses the default name 
                   `@file://EventProcess.cfg'."
::= { usrEventHandler 2 }
usrEhCFMStatusFlag OBJECT-TYPE
	SYNTAX		UsrConfigStatus
	MAX-ACCESS	read-write
	STATUS		current
	DESCRIPTION
		"This variable controls saving and loading of configuration
           information for the Event Handler process. The value can 
           be set to either save or load by a management station. The other
           values indicate if any configuration operation and what type
           is in progress."
::= { usrEventHandler 3 }
usrEhSyslogTable OBJECT-TYPE
	SYNTAX SEQUENCE OF UsrEhSyslogEntry
	MAX-ACCESS not-accessible
	STATUS current
	DESCRIPTION
		"The (conceptual) table of SYSLOG sink nodes."
::= { usrEventHandler 4 }
usrEhSyslogEntry OBJECT-TYPE
	SYNTAX UsrEhSyslogEntry
	MAX-ACCESS not-accessible
	STATUS current
	DESCRIPTION
		"A (conceptual) entry for one SYSLOG sink node."
	INDEX { usrEhSyslogSink }
::= { usrEhSyslogTable 1 }
UsrEhSyslogEntry ::= SEQUENCE {
	usrEhSyslogSink			        IpAddress,
	usrEhSyslogLevel			INTEGER,
	usrEhSyslogMsgCount			Counter32,
	usrEhSyslogStatus			INTEGER,
	usrEhSyslogFacility			INTEGER,
	usrEhSyslogAllowAllAuthLevels		TruthValue
--	usrEhSyslogBufferConfDepth		INTEGER
	}
usrEhSyslogSink OBJECT-TYPE
	SYNTAX		IpAddress
	MAX-ACCESS	not-accessible
	STATUS		current
	DESCRIPTION
		"The IP Address of the SYSLOG sink system. Event messages for 
                 the EVF_SYSLOG event sink will be sent to this address's UDP
                 port number 514."
::= { usrEhSyslogEntry 1 }
usrEhSyslogLevel OBJECT-TYPE
	SYNTAX	INTEGER { critical(0), unusual(1), common(2), verbose(3),
						debug(4) }
	MAX-ACCESS	read-write
	STATUS		current
	DESCRIPTION
		"The log level associated with this SYSLOG sink node."
	--CONFIGURABLE
::= { usrEhSyslogEntry 2 }
usrEhSyslogMsgCount OBJECT-TYPE
	SYNTAX		Counter32
	MAX-ACCESS	read-only
	STATUS		current
	DESCRIPTION
		"The number of event messages sent to this syslog sink."
::= { usrEhSyslogEntry 3 }
usrEhSyslogStatus OBJECT-TYPE
	SYNTAX		INTEGER { normal(1), delete(2) }
	MAX-ACCESS	read-write
	STATUS		current
	DESCRIPTION
		"Status flag for the SYSLOG sink. The value returned by the
		 Event process will always be normal. Setting the value to
		 delete will cause the entry to removed from the table."
::= { usrEhSyslogEntry 4 }
usrEhSyslogFacility OBJECT-TYPE
	SYNTAX		INTEGER { auth(1), local0(2), local1(3),
				local2(4), local3(5), local4(6),
				local5(7), local6(8), local7(9) }
	MAX-ACCESS	read-write
	STATUS		current
	DESCRIPTION
		"The SYSLOG sink node facility to which the SYSLOG message is
		 is sent."
	--CONFIGURABLE
::= { usrEhSyslogEntry 5 }
usrEhSyslogAllowAllAuthLevels OBJECT-TYPE
	SYNTAX		TruthValue
	MAX-ACCESS	read-write
	STATUS		current
	DESCRIPTION
		"Whether Pilgrim Auth facility messages get sent irrespective
                 of  their loglevels.  Default is Yes(2).  No is (1)."
	--CONFIGURABLE
::= { usrEhSyslogEntry 6 }
-- usrEhSyslogBufferConfDepth OBJECT-TYPE
--	SYNTAX		INTEGER (1..256)
--	MAX-ACCESS	read-write
--	STATUS		current
--	DESCRIPTION
--		"Maximum number of syslogs that are buffered for a particular 
--               server"
--	CONFIGURABLE
-- ::= { usrEhSyslogEntry 7 }
-- usrEhSyslogBufferReset OBJECT-TYPE
--	SYNTAX		INTEGER (1..2)
--	MAX-ACCESS	write-only
--	STATUS		current
--	DESCRIPTION
--		"Maximum number of syslogs that are buffered for a particular server"
--	CONFIGURABLE
-- ::= { usrEhSyslogEntry 8 }
-- usrEhSyslogBufferState OBJECT-TYPE
--	SYNTAX		INTEGER {
--                       enabled(1),
--                      disabled(2)
--                     }
--	MAX-ACCESS	read-write
--	STATUS		current
--	DESCRIPTION
--		"This flag states whether syslog buffering is enabled."
-- ::= { usrEventHandler 5 }
END         -- End of Event-MIB DEFINITIONS
-- ************************************************************************
--
--     usr_cip.mib 
--
--	Description:	This module contains MIB definitions for the 
--      		Call-Initiation Process. 
--
--	Author:	Hasmik Sarkezians
--
