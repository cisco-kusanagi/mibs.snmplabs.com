--*********************************************************************
-- Copyright: Ericsson Telecom AB 1997
-- Doc no: 92/190 55-CAA 134 74 Uen
--
-- NAME ANS-COMMON-MIB.mib
--
-- DESCRIPTION
--
-- This MIB module defines objects common for whole the ANx.
--
-- REVISION HISTORY
--
-- Old revision history is found in clearcase.
-- Use the 'ct lshistory' command to view it, or
-- use the program '/vobs/tools/bin/cc_mp' program to print
-- the file with the revision information.
--
-- Rev    Date     Name     Reason
-- PA2    970528   etxtsun  restartAndAudit, initiateColdStart and 
--                          initiateWarmStart deleted
-- PA3    970622   etxtsun  errorMessageCode is just an integer, not enum.
-- PA4    011015   teigaba  Changed branch.
-- 

ANS-COMMON-MIB DEFINITIONS ::= BEGIN

IMPORTS
        OBJECT-TYPE, enterprises
                FROM SNMPv2-SMI
	Gauge
		FROM RFC1155-SMI
	DisplayString
		FROM RFC1213-MIB;

-- This MIB module uses the extended OBJECT-TYPE macro as
-- defined in RFC-1212 and the TRAP-TYPE macro as defined in
-- RFC-1215


ericsson		OBJECT IDENTIFIER ::= {enterprises 193}
mlpmp			OBJECT IDENTIFIER ::= {ericsson 96}
mlpmpR115		OBJECT IDENTIFIER ::= {mlpmp 115}   -- Release 1.15
common			OBJECT IDENTIFIER ::= {mlpmpR115 1}

-- restartAndAudit		OBJECT IDENTIFIER ::= {common 1}  rev PA2

errorMessage		OBJECT IDENTIFIER ::= {common 2}

TruthValue ::=
	INTEGER {
		true(1),
		false(2)
		}
-- Represents a boolean value.

-- Textual conventions

-- IfIndex ::= INTEGER (1..65535)
-- A reference to an entry in the Interface table (i.e. the value
-- of ifIndex for an ifEntry in the ifTable).

PhysAddress ::=
	OCTET STRING
-- This data type is used to model media addresses.  For many
-- types of media, this will be in a binary representation.
-- For example, an ethernet address would be represented as
-- a string of 6 octets.

RowPointer ::= OBJECT IDENTIFIER
-- Represents a pointer to a conceptual row.  The value is the
-- name of the instance of the first accessible columnar object
-- in the conceptual row.
-- For example, ifIndex.3 would point to the 3rd row in the
-- ifTable (note that if ifIndex were not-accessible, then
-- ifDescr.3 would be used instead).

RowStatus ::=
	INTEGER {
		active (1),		-- read/write
		notInService (2),	-- read/write
		notReady (3),		-- read only
		createAndGo (4),	-- write only
		createAndWait (5),	-- write only
		destroy (6)		-- write only
		}
-- The meaning and usage of the different row status values are described
-- in RFC 1903.

DateAndTime ::=
	OCTET STRING (SIZE (8 | 11))
-- A date-time specification.
--
-- field  octets  contents                  range
-- =====  ======  ========                  =====
--   1      1-2   year                      0..65536
--   2       3    month                     1..12
--   3       4    day                       1..31
--   4       5    hour                      0..23
--   5       6    minutes                   0..59
--   6       7    seconds                   0..60
--                (use 60 for leap-second)
--   7       8    deci-seconds              0..9
--   8       9    direction from UTC        '+' / '-'
--   9      10    hours from UTC            0..11
--  10      11    minutes from UTC          0..59
--
-- Note that if only local time is known, then
-- timezone information (fields 8-10) is not
-- present.



-- The Restart and Audit Group    DELETED IN REV PA2

-- initiateColdStart  OBJECT-TYPE
--	SYNTAX	INTEGER {
--			oldCopy (1),
--			olderCopy (2),
--			oldestCopy (3),
--			loadedCopy (4),
--			default (5)
--			}
--	ACCESS	read-write
--	STATUS 	mandatory
--	DESCRIPTION
--		"Initiates a restart of the managed system, in which a 
--		backup copy of the configuration data or default values 
--		are used. The backup copy may either be one of three kept
--		in the manged system (old, older and oldest), or a backup
--		copy loaded from some other system (e.g. the management
--		system)."
--	::= { restartAndAudit 1 }
--
-- initiateWarmStart  OBJECT-TYPE
--	SYNTAX 	INTEGER {
--			currentData (1)
--			}
--	ACCESS 	read-write
--	STATUS 	mandatory
--	DESCRIPTION
--		"Initiates a restart of the managed system, in which the
--		current configuration data is used."
--	::= { restartAndAudit 2 }
--
--

-- The Error Message Group

-- This group provides support for providing a user with additional error
-- information, on top of what is provided through the standard SNMP error
-- messages supplied in SNMP PDUs (as defined by the error-status attribute).

errorMessageTable  OBJECT-TYPE
	SYNTAX  SEQUENCE OF ErrorMessageEntry
        ACCESS  not-accessible
        STATUS  mandatory
        DESCRIPTION
		"Table containing additional error information
		associated with particular SNMP request IDs."
	::= { errorMessage 1 }

errorMessageEntry  OBJECT-TYPE
        SYNTAX  ErrorMessageEntry
        ACCESS  not-accessible
        STATUS  mandatory
        DESCRIPTION
      		"Error message associated with a particular request ID."
        INDEX { errorMessageRequestId }
        ::= { errorMessageTable 1 }

ErrorMessageEntry ::=
       	SEQUENCE {
  		errorMessageRequestId	INTEGER,
  		errorMessageCode	INTEGER
        	}

errorMessageRequestId  OBJECT-TYPE
        SYNTAX  INTEGER
        ACCESS  read-only
        STATUS  mandatory
        DESCRIPTION
      		"The value of the request-id (according to RFC 1157)
		of the SNMP request response that was received with
		an error status not equal to 'noError'."
        ::= { errorMessageEntry 1 }

errorMessageCode  OBJECT-TYPE
        SYNTAX  INTEGER
        ACCESS  read-only
        STATUS  mandatory
        DESCRIPTION
      		"An error code representing an application specific 
		error message."
        ::= { errorMessageEntry 2 }


END
