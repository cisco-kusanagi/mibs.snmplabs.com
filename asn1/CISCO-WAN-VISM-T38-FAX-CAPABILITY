-- *****************************************************************
-- CISCO-WAN-VISM-T38-FAX-CAP.my   MIB
--
-- AGENT-CAPABILITIES MIB for CISCO-WAN-T38-FAXRELAY-MIB in the VISM product
--
-- Copyright(c) 2000, 2001 by Cisco Systems,Inc.
--
-- Author: Siana Smith
--
-- 2001/08/05 Results from MIB externalinterfaces review. 
--
-- 2002/04/22 Corrections from Telogy document.
--
-- *****************************************************************

CISCO-WAN-VISM-T38-FAX-CAPABILITY DEFINITIONS ::= BEGIN

IMPORTS
        MODULE-IDENTITY,
        Integer32
                FROM SNMPv2-SMI
        AGENT-CAPABILITIES
                FROM SNMPv2-CONF
        ciscoWanAgentCapability
                FROM CISCOWAN-SMI;

cwVismT38FaxCapability MODULE-IDENTITY
        LAST-UPDATED    "200206010000Z"
        ORGANIZATION    "Cisco Systems, Inc."
        CONTACT-INFO
                "       Cisco Systems
                        Customer Service

                Postal: 170 W Tasman Drive
                        San Jose, CA  95134
                        USA

                        Tel: +1 800 553-NETS

                E-mail: cs-vism@cisco.com"
        DESCRIPTION
                "The Agent Capabilities for CISCO-WAN-T38-FAXRELAY-MIB."

        REVISION        "200108050000Z"
        DESCRIPTION
                "Initial version of this MIB module"

        REVISION        "200206010000Z"
        DESCRIPTION
                "
                t38FaxInfoFieldSize variation was modified.
                t38HsDataPacketSize variation was added.
                t38LsDataRedundancy variation was modified.
                t38HsDataRedundancy variation was modified.
                t38ErrCorrection variation was added.
                t38NSFCountryCode variation was modified.
                t38NSFVendorCode variation was added.
                t38Redundancy variation was added.
                "

        ::= { ciscoWanAgentCapability 335 }

cwVismT38FaxCapabilityV2R00 AGENT-CAPABILITIES
    PRODUCT-RELEASE      "VISM Release3.1"
    STATUS               current
    DESCRIPTION          "CISCO-WAN-T38-FAXRELAY-MIB Capabilities"

    SUPPORTS CISCO-WAN-T38-FAXRELAY-MIB
    INCLUDES { t38FaxRelayGroup }

        VARIATION   t38vismDs1Number
        SYNTAX      Integer32 (1..8)
        DESCRIPTION "Valid range is 1 - 8."

        VARIATION   t38FaxInfoFieldSize
        ACCESS      not-implemented
        DESCRIPTION "Not supported."

        VARIATION   t38HsDataPacketSize
        SYNTAX      INTEGER { tenms(10), twentyms(20), thirtyms(30) }
        DEFVAL      { thirtyms }
        DESCRIPTION "Does not support value fortyms(40)."

        VARIATION   t38LsDataRedundancy
        SYNTAX      Integer32 (0..5)
        DESCRIPTION "This object determines the extent of the internet fax protocol
                     (IFP) packet transmission redundancy for the low-speed control
                     information exchanged during the first phase of a T.38
                     fax relay connection. The valid range is 0 - 5. "

        VARIATION   t38HsDataRedundancy
        SYNTAX      Integer32 (0..2)
        DESCRIPTION "This object determines the extent of the IFP packet
                     transmission redundancy for the high-speed control
                     and image information exchanged following the initial
                     low-speed phase of a T.38 fax relay connection."

        VARIATION   t38ErrCorrection
        ACCESS      not-implemented
        DESCRIPTION "Not supported - forward error correction
                     is always disabled."

        VARIATION   t38NSFCountryCode
        SYNTAX      Integer32 (0..255)
        DEFVAL      {173}
        DESCRIPTION "Supports range 0-255 only and default value is 173."

        VARIATION   t38NSFVendorCode
        DEFVAL      {81}
        DESCRIPTION "Default value is 81."

        VARIATION   t38Redundancy
        ACCESS      not-implemented
        DESCRIPTION "Not supported - redundancy is always enabled."

    ::= { cwVismT38FaxCapability 1 }




END
