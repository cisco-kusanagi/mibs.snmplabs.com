BAS-IP-FORWARD-MIB DEFINITIONS ::= BEGIN

IMPORTS
    MODULE-IDENTITY, OBJECT-TYPE, IpAddress, Integer32, Gauge32
        FROM SNMPv2-SMI
    RowStatus
        FROM SNMPv2-TC
    basAliasCidr, BasChassisId,
    BasSlotId, BasInterfaceId,
    BasLogicalPortId			FROM BAS-MIB;


basIpForward MODULE-IDENTITY
	LAST-UPDATED "9810071415Z"
	ORGANIZATION "Broadband Access Systems"
	CONTACT-INFO
		" Tech Support
		  Broadband Access Systems
		  201 Forest Street
		  Marlboro, MA  01752
		  U.S.A.

		  508-485-8200
		  support@basystems.com"
	DESCRIPTION
		"This module defines the MIB objects
		 for a Broadband Access System IP Forwarding component."
	::= { basAliasCidr 1 }

basCidrObjects		OBJECT IDENTIFIER ::= { basAliasCidr 2 }

basCidrTable OBJECT-TYPE
	SYNTAX		SEQUENCE OF BasCidrEntry
	MAX-ACCESS	not-accessible
	STATUS		current
	DESCRIPTION
		"A list of Route Server forwarding table 
		distribution mechanism statistics."
	::= { basCidrObjects 1 }

basCidrEntry OBJECT-TYPE
	SYNTAX		BasCidrEntry
	MAX-ACCESS	not-accessible
	STATUS		current
	DESCRIPTION
		"Objects for the CIDR mib."
	INDEX   { basCidrChassis, basCidrSlot, basCidrIf, basCidrLPort }
	::= { basCidrTable 1 }

BasCidrEntry ::=
	SEQUENCE {
		basIpCidrRouteNumber						Gauge32,
		basCidrChassis							BasChassisId,
		basCidrSlot							BasSlotId,
		basCidrIf							BasInterfaceId,
		basCidrLPort							BasLogicalPortId
	}



basIpCidrRouteNumber OBJECT-TYPE
    SYNTAX   Gauge32
    MAX-ACCESS read-only
    STATUS   current
    DESCRIPTION
       "The number of current ipCidrRouteTable entries
       that are not invalid."
    ::= { basCidrEntry 3 }

basCidrChassis OBJECT-TYPE
	SYNTAX		BasChassisId
	MAX-ACCESS	not-accessible
	STATUS		current
	DESCRIPTION
		"The BAS Chassis ID of the Route Server."
	::= { basCidrEntry 4 }

basCidrSlot OBJECT-TYPE
	SYNTAX		BasSlotId
	MAX-ACCESS	not-accessible
	STATUS		current
	DESCRIPTION
		"The BAS Slot ID of the Route Server."
	::= { basCidrEntry 5}

basCidrIf OBJECT-TYPE
	SYNTAX		BasInterfaceId
	MAX-ACCESS	not-accessible
	STATUS		current
	DESCRIPTION
		"The BAS interface ID of the Route Server."
	::= { basCidrEntry 6 }

basCidrLPort OBJECT-TYPE
	SYNTAX		BasLogicalPortId
	MAX-ACCESS	not-accessible
	STATUS		current
	DESCRIPTION
		"The BAS logical port ID of the Route Server."
	::= { basCidrEntry 7 }

--  IP CIDR Route Table

--  The IP CIDR Route Table obsoletes and replaces the ipRoute
--  Table current in MIB-I and MIB-II and the IP Forwarding Table.
--  It adds knowledge of the autonomous system of the next hop,
--  multiple next hops, and policy routing, and Classless


--  Inter-Domain Routing.

basIpCidrRouteTable OBJECT-TYPE
    SYNTAX   SEQUENCE OF BasIpCidrRouteEntry
    MAX-ACCESS not-accessible
    STATUS   current
    DESCRIPTION
       "This entity's IP Routing table."
    REFERENCE
       "RFC 1213 Section 6.6, The IP Group"
    ::= { basCidrObjects 4 }

basIpCidrRouteEntry OBJECT-TYPE
    SYNTAX   BasIpCidrRouteEntry
    MAX-ACCESS not-accessible
    STATUS   current
    DESCRIPTION
       "A particular route to  a  particular  destina-
       tion, under a particular policy."
    INDEX  { 
	basIpCidrRouteChassis,
	basIpCidrRouteSlot,
	basIpCidrRouteIf,
	basIpCidrRouteLPort,
	basIpCidrRouteDest,
        basIpCidrRouteMask,
        basIpCidrRouteTos,
        basIpCidrRouteNextHop
        }
    ::= { basIpCidrRouteTable 1 }

BasIpCidrRouteEntry ::=
    SEQUENCE {
        basIpCidrRouteDest
            IpAddress,
        basIpCidrRouteMask
            IpAddress,
        basIpCidrRouteTos
             Integer32,
        basIpCidrRouteNextHop
            IpAddress,
        basIpCidrRouteIfIndex
            Integer32,
        basIpCidrRouteType
            INTEGER,
        basIpCidrRouteProto
            INTEGER,
        basIpCidrRouteAge
            Integer32,
        basIpCidrRouteInfo
            OBJECT IDENTIFIER,
        basIpCidrRouteNextHopAS


            Integer32,
        basIpCidrRouteMetric1
            Integer32,
        basIpCidrRouteMetric2
            Integer32,
        basIpCidrRouteMetric3
            Integer32,
        basIpCidrRouteMetric4
            Integer32,
        basIpCidrRouteMetric5
            Integer32,
        basIpCidrRouteStatus
            RowStatus,
	basIpCidrRouteChassis	BasChassisId,
	basIpCidrRouteSlot	BasSlotId,
	basIpCidrRouteIf	BasInterfaceId,
	basIpCidrRouteLPort	BasLogicalPortId
    }

basIpCidrRouteDest OBJECT-TYPE
    SYNTAX   IpAddress
    MAX-ACCESS read-only
    STATUS   current
    DESCRIPTION
       "The destination IP address of this route.

       This object may not take a Multicast (Class  D)
       address value.

       Any assignment (implicit or  otherwise)  of  an
       instance  of  this  object to a value x must be
       rejected if the bitwise logical-AND of  x  with
       the  value of the corresponding instance of the
       ipCidrRouteMask object is not equal to x."
    ::= { basIpCidrRouteEntry 1 }

basIpCidrRouteMask OBJECT-TYPE
    SYNTAX   IpAddress
    MAX-ACCESS read-only
    STATUS   current
    DESCRIPTION
       "Indicate the mask to be logical-ANDed with the
       destination  address  before  being compared to
       the value  in  the  ipCidrRouteDest  field.   For
       those  systems  that  do  not support arbitrary
       subnet masks, an agent constructs the value  of
       the  ipCidrRouteMask  by  reference to the IP Ad-
       dress Class.

       Any assignment (implicit or  otherwise)  of  an
       instance  of  this  object to a value x must be
       rejected if the bitwise logical-AND of  x  with


       the  value of the corresponding instance of the
       ipCidrRouteDest object is not equal to ipCidrRoute-
       Dest."
    ::= { basIpCidrRouteEntry 2 }

-- The following convention is included for specification
-- of TOS Field contents.  At this time, the Host Requirements
-- and the Router Requirements documents disagree on the width
-- of the TOS field.  This mapping describes the Router
-- Requirements mapping, and leaves room to widen the TOS field
-- without impact to fielded systems.

basIpCidrRouteTos OBJECT-TYPE
    SYNTAX   Integer32
    MAX-ACCESS read-only
    STATUS   current
    DESCRIPTION
       "The policy specifier is the IP TOS Field.  The encoding
       of IP TOS is as specified  by  the  following convention.
       Zero indicates the default path if no more  specific
       policy applies.

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy
           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30"
    ::= { basIpCidrRouteEntry 3 }

basIpCidrRouteNextHop OBJECT-TYPE
    SYNTAX   IpAddress
    MAX-ACCESS read-only
    STATUS   current
    DESCRIPTION
       "On remote routes, the address of the next sys-
       tem en route; Otherwise, 0.0.0.0."


    ::= { basIpCidrRouteEntry 4 }

basIpCidrRouteIfIndex OBJECT-TYPE
    SYNTAX   Integer32
    MAX-ACCESS read-create
    STATUS   current
    DESCRIPTION
       "The ifIndex value which identifies  the  local
       interface  through  which  the next hop of this
       route should be reached."
    DEFVAL { 0 }
    ::= { basIpCidrRouteEntry 5 }

basIpCidrRouteType OBJECT-TYPE
    SYNTAX   INTEGER {
                other    (1), -- not specified by this MIB
                reject   (2), -- route which discards traffic
                local    (3), -- local interface
                remote   (4)  -- remote destination
             }
    MAX-ACCESS read-create
    STATUS   current
    DESCRIPTION
       "The type of route.  Note that local(3)  refers
       to  a route for which the next hop is the final
       destination; remote(4) refers to  a  route  for
       which  the  next  hop is not the final destina-
       tion.

       Routes which do not result in traffic forwarding or
       rejection should not be displayed even if the
       implementation keeps them stored internally.

       reject (2) refers to a route which, if matched, discards
       the message as unreachable. This is used in some
       protocols as a means of correctly aggregating routes."
    ::= { basIpCidrRouteEntry 6 }

basIpCidrRouteProto OBJECT-TYPE
    SYNTAX   INTEGER {
                other     (1),  -- not specified
                local     (2),  -- local interface
                netmgmt   (3),  -- static route
                icmp      (4),  -- result of ICMP Redirect

                        -- the following are all dynamic
                        -- routing protocols


                egp        (5),  -- Exterior Gateway Protocol
                ggp        (6),  -- Gateway-Gateway Protocol
                hello      (7),  -- FuzzBall HelloSpeak
                rip        (8),  -- Berkeley RIP or RIP-II
                isIs       (9),  -- Dual IS-IS
                esIs       (10), -- ISO 9542
                ciscoIgrp  (11), -- Cisco IGRP
                bbnSpfIgp  (12), -- BBN SPF IGP
                ospf       (13), -- Open Shortest Path First
                bgp        (14), -- Border Gateway Protocol
                idpr       (15), -- InterDomain Policy Routing
                ciscoEigrp (16)  -- Cisco EIGRP
             }
    MAX-ACCESS read-only
    STATUS   current
    DESCRIPTION
       "The routing mechanism via which this route was
       learned.  Inclusion of values for gateway rout-
       ing protocols is not  intended  to  imply  that
       hosts should support those protocols."
    ::= { basIpCidrRouteEntry 7 }

basIpCidrRouteAge OBJECT-TYPE
    SYNTAX   Integer32
    MAX-ACCESS read-only
    STATUS   current
    DESCRIPTION
       "The number of seconds  since  this  route  was
       last  updated  or  otherwise  determined  to be
       correct.  Note that no semantics of  `too  old'
       can  be implied except through knowledge of the
       routing  protocol  by  which  the   route   was
       learned."
    DEFVAL  { 0 }
    ::= { basIpCidrRouteEntry 8 }

basIpCidrRouteInfo OBJECT-TYPE
    SYNTAX   OBJECT IDENTIFIER
    MAX-ACCESS read-create
    STATUS   current
    DESCRIPTION
       "A reference to MIB definitions specific to the
       particular  routing protocol which is responsi-
       ble for this route, as determined by the  value
       specified  in the route's ipCidrRouteProto value.
       If this information is not present,  its  value
       should be set to the OBJECT IDENTIFIER { 0 0 },
       which is a syntactically valid object  identif-


       ier, and any implementation conforming to ASN.1
       and the Basic Encoding Rules must  be  able  to
       generate and recognize this value."
    ::= { basIpCidrRouteEntry 9 }

basIpCidrRouteNextHopAS OBJECT-TYPE
    SYNTAX   Integer32
    MAX-ACCESS read-create
    STATUS   current
    DESCRIPTION
       "The Autonomous System Number of the Next  Hop.
       The  semantics of this object are determined by
       the routing-protocol specified in  the  route's
       ipCidrRouteProto  value. When  this object is
       unknown or not relevant its value should be set
       to zero."
    DEFVAL { 0 }
    ::= { basIpCidrRouteEntry 10 }

basIpCidrRouteMetric1 OBJECT-TYPE
    SYNTAX   Integer32
    MAX-ACCESS read-create
    STATUS   current
    DESCRIPTION
       "The primary routing  metric  for  this  route.
       The  semantics of this metric are determined by
       the routing-protocol specified in  the  route's
       ipCidrRouteProto  value.   If  this metric is not
       used, its value should be set to -1."
    DEFVAL { -1 }
    ::= { basIpCidrRouteEntry 11 }

basIpCidrRouteMetric2 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { basIpCidrRouteEntry 12 }

basIpCidrRouteMetric3 OBJECT-TYPE
    SYNTAX   Integer32
    MAX-ACCESS read-create


    STATUS   current
    DESCRIPTION
       "An alternate routing metric  for  this  route.
       The  semantics of this metric are determined by
       the routing-protocol specified in  the  route's
       ipCidrRouteProto  value.   If  this metric is not
       used, its value should be set to -1."
    DEFVAL { -1 }
    ::= { basIpCidrRouteEntry 13 }

basIpCidrRouteMetric4 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { basIpCidrRouteEntry 14 }

basIpCidrRouteMetric5 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { basIpCidrRouteEntry 15 }

basIpCidrRouteStatus OBJECT-TYPE
    SYNTAX   RowStatus
    MAX-ACCESS read-create
    STATUS   current
    DESCRIPTION
       "The row status variable, used according to
       row installation and removal conventions."
    ::= { basIpCidrRouteEntry 16 }


basIpCidrRouteChassis OBJECT-TYPE
	SYNTAX		BasChassisId
	MAX-ACCESS	not-accessible
	STATUS		current
	DESCRIPTION
		"The BAS Chassis ID of the Route Server."
	::= { basIpCidrRouteEntry 17 }

basIpCidrRouteSlot OBJECT-TYPE
	SYNTAX		BasSlotId
	MAX-ACCESS	not-accessible
	STATUS		current
	DESCRIPTION
		"The BAS Slot ID of the Route Server."
	::= { basIpCidrRouteEntry 18}

basIpCidrRouteIf OBJECT-TYPE
	SYNTAX		BasInterfaceId
	MAX-ACCESS	not-accessible
	STATUS		current
	DESCRIPTION
		"The BAS interface ID of the Route Server."
	::= { basIpCidrRouteEntry 19 }

basIpCidrRouteLPort OBJECT-TYPE
	SYNTAX		BasLogicalPortId
	MAX-ACCESS	not-accessible
	STATUS		current
	DESCRIPTION
		"The BAS logical port ID of the Route Server."
	::= { basIpCidrRouteEntry 20 }

END
