-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
AGENTSTATS-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
--hardware        OBJECT IDENTIFIER ::= { modules 1 }
--
--


objects	OBJECT IDENTIFIER ::= { agentStats 1 }
commands	OBJECT IDENTIFIER ::= { agentStats 2 }
transactions	OBJECT IDENTIFIER ::= { agentStats 3 }
procstats	OBJECT IDENTIFIER ::= { agentStats 4 }
totalstats	OBJECT IDENTIFIER ::= { agentStats 5 }
total1	OBJECT IDENTIFIER ::= { commands 1 }
rate1	OBJECT IDENTIFIER ::= { commands 2 }
total2	OBJECT IDENTIFIER ::= { transactions 1 }
rate2	OBJECT IDENTIFIER ::= { transactions 2 }
agentStats	OBJECT IDENTIFIER ::= { modules 30 }
count	OBJECT IDENTIFIER ::= { totalstats 1 }
size1	OBJECT IDENTIFIER ::= { totalstats 2 }
rss1	OBJECT IDENTIFIER ::= { totalstats 3 }
toeCount	OBJECT IDENTIFIER ::= { objects 1 }
bobCount	OBJECT IDENTIFIER ::= { objects 2 }
pid	OBJECT IDENTIFIER ::= { procstats 1 }
id	OBJECT IDENTIFIER ::= { procstats 2 }
name	OBJECT IDENTIFIER ::= { procstats 3 }
info	OBJECT IDENTIFIER ::= { procstats 4 }
state	OBJECT IDENTIFIER ::= { procstats 5 }
uid	OBJECT IDENTIFIER ::= { procstats 6 }
size2	OBJECT IDENTIFIER ::= { procstats 7 }
rss2	OBJECT IDENTIFIER ::= { procstats 8 }
starttime	OBJECT IDENTIFIER ::= { procstats 9 }
startdatestring	OBJECT IDENTIFIER ::= { procstats 10 }
starttimestring	OBJECT IDENTIFIER ::= { procstats 11 }
cputime	OBJECT IDENTIFIER ::= { procstats 12 }
pctcputime	OBJECT IDENTIFIER ::= { procstats 13 }
context	OBJECT IDENTIFIER ::= { procstats 14 }
syscalls	OBJECT IDENTIFIER ::= { procstats 15 }
command	OBJECT IDENTIFIER ::= { procstats 16 }

END
