-- *****************************************************************
-- REDSTONE-DS3-MIB
--
-- Redstone Communications Inc. Enterprise MIB
-- DS3 MIB
--
-- Copyright 1998 Redstone Communications, Incorporated.
-- All Rights Reserved.
-- *****************************************************************

REDSTONE-DS3-MIB DEFINITIONS ::= BEGIN

IMPORTS
	MODULE-IDENTITY,
	OBJECT-TYPE,
	Integer32
		FROM SNMPv2-SMI
	OBJECT-GROUP, MODULE-COMPLIANCE FROM SNMPv2-CONF

    ifIndex
        FROM IF-MIB

	rsMgmt
		FROM REDSTONE-SMI;


rsDs3MIB  MODULE-IDENTITY
	LAST-UPDATED "9907270000Z"
	ORGANIZATION "Redstone Communications, Inc."
	CONTACT-INFO
        "
        Redstone Communications, Inc.
		5 Carlisle Road
        Westford MA 01886
        USA
        Tel:    +1-978-692-1999
		Email:  mib@redstonecom.com
        "
	DESCRIPTION
		"The DS3 MIB for the 
		Redstone Communications Inc. enterprise."
	REVISION      "9907270000Z"
	DESCRIPTION
		"Revised version of this MIB module."
	::= { rsMgmt 4 }

-- ++++++++++++++++++++++++++++++++++++++++++++++++++++++++++++++++++++++
-- Textual conventions
-- ++++++++++++++++++++++++++++++++++++++++++++++++++++++++++++++++++++++

-- No textual conventions are defined in this MIB



-- ++++++++++++++++++++++++++++++++++++++++++++++++++++++++++++++++++++++
-- Managed objects
-- ++++++++++++++++++++++++++++++++++++++++++++++++++++++++++++++++++++++

rsDs3Objects     OBJECT IDENTIFIER ::= { rsDs3MIB 1 }

-- 
-- This MIB contains managed objects for DS3/E3 interfaces.
-- Management objects are provided to supplement those
-- found in RFC1407 DS3/E3 MIB.
--



-- //////////////////////////////////////////////////////////////////////
--
-- DS3 Interfaces
--
-- //////////////////////////////////////////////////////////////////////

--
-- The DS3 Configuration Table
--

rsDsx3ConfigTable OBJECT-TYPE
    SYNTAX      SEQUENCE OF RsDsx3ConfigEntry
    MAX-ACCESS  not-accessible
    STATUS      current
    DESCRIPTION
        "This table contains entries for DS3/E3 interfaces present in the system."
    ::= { rsDs3Objects 1 }

rsDsx3ConfigEntry OBJECT-TYPE
    SYNTAX      RsDsx3ConfigEntry
    MAX-ACCESS  not-accessible
    STATUS      current
    DESCRIPTION
        "Each entry describes the characteristics of an DS3/E3 interface."
    INDEX   { ifIndex }
    ::= { rsDsx3ConfigTable 1 }

RsDsx3ConfigEntry ::= SEQUENCE {
    rsDsx3LineLength
        Integer32,
    rsDsx3LineType
        INTEGER,
    rsDsx3CellScramblerConfig
        INTEGER
    }

rsDsx3LineLength OBJECT-TYPE
    SYNTAX  Integer32 (0..64000)
    UNITS  "meters"
    MAX-ACCESS  read-write
    STATUS  current
    DESCRIPTION
        "The length of the DS3/E3 line in meters. This
        objects provides information for line build out
        circuitry.  This object is only useful if the
        interface has configurable line build out
        circuitry."
    ::= { rsDsx3ConfigEntry 1 }

rsDsx3LineType OBJECT-TYPE
    SYNTAX  INTEGER {
                rsDsx3other(1),
                rsDsx3M23(2),
                rsDsx3SYNTRAN(3),
                rsDsx3CbitParity(4),
                rsDsx3ClearChannel(5),
                rsE3G832(6),
                rsE3Framed(7),
                rsE3Plcp(8),
                rsDsx3M23Plcp(18),
                rsDsx3CbitParityPlcp(20)
            }
    MAX-ACCESS  read-write
    STATUS  current
    DESCRIPTION
         "This variable indicates the variety of DS3 C-bit
         or E3 application implementing this interface.  The type
         of interface affects the interpretation of the
         usage and error statistics.  The rate of DS3 is 44.736
         Mbps and E3 is 34.368 Mbps.  The dsx3ClearChannel value
         means that the C-bits are not used except for
         sending/receiving AIS.  Note that this object represents
         the actual line type when the corresponding value of
         dsx3LineType is dsx3other(1).

             The values, in sequence, describe:

             TITLE:              SPECIFICATION:
             dsx3M23             ANSI T1.107-1988
             dsx3SYNTRAN         ANSI T1.107-1988
             dsx3CbitParity      ANSI T1.107a-1989
             dsx3ClearChannel    ANSI T1.102-1987
             e3G832              ITU-T G.832
             e3Framed            ITU-T G.751
             e3Plcp              ETSI T/NA(91)18.
             dsx3M23Plcp         ATM Forum af-phy-0054.000
             dsx3CbitParityPlcp  ATM Forum af-phy-0054.000"
    ::= { rsDsx3ConfigEntry 2 }

rsDsx3CellScramblerConfig OBJECT-TYPE
    SYNTAX  INTEGER {
                scramblerOn(1),
                scramblerOff(2),
                notSupported(3)
            }
    MAX-ACCESS  read-write
    STATUS  current
    DESCRIPTION
         "This variable indicates the state of the ATM cell
         scrambler for interfaces which support ATM over DS3 or
         E3.  For interfaces which do not support ATM, this
         object returns the value notSupported(3)."
    ::= { rsDsx3ConfigEntry 3 }



-- ++++++++++++++++++++++++++++++++++++++++++++++++++++++++++++++++++++++
-- Notification control objects
-- ++++++++++++++++++++++++++++++++++++++++++++++++++++++++++++++++++++++

-- No notifications are defined in this MIB. Placeholder follows.

-- rsDs3TrapControl      OBJECT IDENTIFIER ::= { rsDs3MIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- rsDs3Traps            OBJECT IDENTIFIER ::= { rsDs3MIB 3 }
-- rsDs3TrapPrefix       OBJECT IDENTIFIER ::= { rsDs3Traps 0 }



-- ++++++++++++++++++++++++++++++++++++++++++++++++++++++++++++++++++++++
-- Conformance information
-- ++++++++++++++++++++++++++++++++++++++++++++++++++++++++++++++++++++++

rsDs3Conformance OBJECT IDENTIFIER ::= { rsDs3MIB 4 }
rsDs3Compliances OBJECT IDENTIFIER ::= { rsDs3Conformance 1 }
rsDs3Groups      OBJECT IDENTIFIER ::= { rsDs3Conformance 2 }

-- compliance statements

rsDs3Compliance MODULE-COMPLIANCE
        STATUS  current
        DESCRIPTION
                "The compliance statement for entities which implement
                the Redstone DS3/E3 MIB."
        MODULE  -- this module
                MANDATORY-GROUPS { rsDs3Group }
        ::= { rsDs3Compliances 1 }

-- units of conformance

rsDs3Group OBJECT-GROUP
        OBJECTS {
        rsDsx3LineLength,
        rsDsx3LineType,
        rsDsx3CellScramblerConfig
	}
	STATUS  current
	DESCRIPTION
		"A collection of objects providing management of DS3/E3 interfaces
		in a Redstone product."
    ::= { rsDs3Groups 1 }

END
