--  ***************************************************************** 
--  Cache Engine MIB
--
--  September 1998, Pradeep Verma and Lori Logan
--
--  Copyright (c) 1998-1999 by Cisco Systems, Inc.
--  All rights reserved.
--
--  Caution.  This MIB is temporary and experimental.  In the future it
--  will be removed from products, perhaps with short notice, in favor
--  of more standard or generic MIBs.  Application developers should not
--  depend on long-term access to this MIB.
--
--  Cisco is interested in receiving feedback on this experimental MIB.
--  Please comment on the usefulness of the defined objects.
-- *****************************************************************

CISCO-CACHE-ENGINE-MIB DEFINITIONS ::= BEGIN

IMPORTS
    MODULE-IDENTITY, 
    OBJECT-TYPE, 
    NOTIFICATION-TYPE,
    Counter32,
    IpAddress,
    Integer32,
    Gauge32,
    Counter64                           FROM SNMPv2-SMI
    MODULE-COMPLIANCE, OBJECT-GROUP     FROM SNMPv2-CONF
    DisplayString, TruthValue           FROM SNMPv2-TC
    ciscoExperiment                     FROM CISCO-SMI;

ciscoCacheEngineMIB MODULE-IDENTITY
    LAST-UPDATED "9811041200Z"
    ORGANIZATION "Cisco Systems, Inc."
    CONTACT-INFO
        "Cisco Systems Customer Service
         Postal: 170 West Tasman Drive
             San Jose, CA 95134-1706
             USA
             Tel: +1 408 526 4000
             E-mail: cs-webcache@cisco.com"
    DESCRIPTION
        "The MIB module for the Cisco Cache Engine from Cisco Systems, Inc."
 ::= {ciscoExperiment 39}

ciscoCacheEngineMIBObjects 
    OBJECT IDENTIFIER ::= {ciscoCacheEngineMIB 1}

ciscoCacheEngineConf
    OBJECT IDENTIFIER ::= {ciscoCacheEngineMIBObjects 1} 


cceConfigGroup    OBJECT IDENTIFIER  ::= {ciscoCacheEngineConf 1}
cceTuningGroup    OBJECT IDENTIFIER  ::= {ciscoCacheEngineConf 2}
cceAccessGroup    OBJECT IDENTIFIER  ::= {ciscoCacheEngineConf 3}
cceReportGroup    OBJECT IDENTIFIER  ::= {ciscoCacheEngineConf 4}
cceStatsGroup     OBJECT IDENTIFIER  ::= {ciscoCacheEngineConf 5}
cceHardwareGroup  OBJECT IDENTIFIER  ::= {ciscoCacheEngineConf 6}


-- Major categories in config group
cceFarm           OBJECT IDENTIFIER  ::= {cceConfigGroup 1}
cceBasic          OBJECT IDENTIFIER  ::= {cceConfigGroup 2}
cceDns            OBJECT IDENTIFIER  ::= {cceConfigGroup 3}
cceIcpClient      OBJECT IDENTIFIER  ::= {cceConfigGroup 4}
cceIcpServer      OBJECT IDENTIFIER  ::= {cceConfigGroup 5}
cceProxy          OBJECT IDENTIFIER  ::= {cceConfigGroup 6}
cceTime           OBJECT IDENTIFIER  ::= {cceConfigGroup 7}

-- Major categories for tuning group
cceCacheFarm      OBJECT IDENTIFIER  ::= {cceTuningGroup 1}
cceFreshness      OBJECT IDENTIFIER  ::= {cceTuningGroup 2}
cceTcp            OBJECT IDENTIFIER  ::= {cceTuningGroup 3}

-- Major categories for access group
cceUrlFilter      OBJECT IDENTIFIER  ::= {cceAccessGroup 1}

-- Major categories for reporting group
cceEvents         OBJECT IDENTIFIER  ::= {cceReportGroup 1}
cceLogging        OBJECT IDENTIFIER  ::= {cceReportGroup 2}

-- Major categories for statistics group
cceDiagDump       OBJECT IDENTIFIER  ::= {cceStatsGroup 1}
cceIms            OBJECT IDENTIFIER  ::= {cceStatsGroup 2}
ccePerformance    OBJECT IDENTIFIER  ::= {cceStatsGroup 3}
cceRequests       OBJECT IDENTIFIER  ::= {cceStatsGroup 4}
cceSavings        OBJECT IDENTIFIER  ::= {cceStatsGroup 5}
cceUsage          OBJECT IDENTIFIER  ::= {cceStatsGroup 6}

-- Major categories for Hardware group
cceInterfaces     OBJECT IDENTIFIER  ::= {cceHardwareGroup 1}



-- The following section describes the objects that are present
-- in the cache farm

cceFarmTable        OBJECT-TYPE
    SYNTAX         SEQUENCE OF CceFarmEntry
    MAX-ACCESS     not-accessible
    STATUS         current
    DESCRIPTION
        "Cache farm table.  A cache farm consists of all the
         cache engines attached to a single router."
    ::= {cceFarm 1}

cceFarmEntry       OBJECT-TYPE
    SYNTAX         CceFarmEntry
    MAX-ACCESS     not-accessible
    STATUS         current
    DESCRIPTION
        "Information on a single cache engine in the cache farm."
    INDEX          {cceFarmEntryIndex}
    ::= {cceFarmTable 1}

CceFarmEntry   ::= SEQUENCE {
    cceFarmEntryIndex     Integer32,
    cceFarmEntryIpAddress IpAddress
}

cceFarmEntryIndex    OBJECT-TYPE
    SYNTAX          Integer32 (1..32)
    MAX-ACCESS      not-accessible
    STATUS          current
    DESCRIPTION
        "Arbitrary index into the cache farm table."
    ::= {cceFarmEntry 1}

cceFarmEntryIpAddress      OBJECT-TYPE
    SYNTAX          IpAddress
    MAX-ACCESS      read-only
    STATUS          current
    DESCRIPTION
        "Cache engine IP address."
    ::= {cceFarmEntry 2}

-- The following section describes the objects that are present
-- in the basic category of the config group

cceBasicIPAddress   OBJECT-TYPE
    SYNTAX          IpAddress
    MAX-ACCESS      read-only
    STATUS          current
    DESCRIPTION
        "IP address of the cache engine."
    ::= {cceBasic 1}

cceBasicNetMask     OBJECT-TYPE
    SYNTAX          IpAddress
    MAX-ACCESS      read-only
    STATUS          current
    DESCRIPTION
        "Network mask of the cache engine."
    ::= {cceBasic  2}

cceBasicGatewayIpAddress     OBJECT-TYPE
    SYNTAX          IpAddress
    MAX-ACCESS      read-only
    STATUS          current
    DESCRIPTION
        "IP address of the default gateway of the cache engine.
         This is the IP address of the router that allows connections
         to the engine from web browsers, and that allows the cache
         engine to be connected to the network.
         If '0.0.0.0', the default gateway address is not configured."
    ::= {cceBasic 3}

cceBasicCacheName       OBJECT-TYPE
    SYNTAX          DisplayString
    MAX-ACCESS      read-only
    STATUS          current
    DESCRIPTION
        "Human-readable name for the cache engine."
    ::= {cceBasic 4}

cceBasicFarmName        OBJECT-TYPE
    SYNTAX          DisplayString
    MAX-ACCESS      read-only
    STATUS          current
    DESCRIPTION
        "Administratively assigned human-readable name associated
         with the router that the cache engine is attached to.
         All cache engines attached to a single router form a cache farm."
    ::= {cceBasic 5}

-- The following section describes the objects that are present
-- in the DNS category of the config group

cceDnsDomain        OBJECT-TYPE
    SYNTAX          DisplayString
    MAX-ACCESS      read-only
    STATUS          current
    DESCRIPTION
        "Domain Name System (DNS) domain of the cache engine."
    ::= {cceDns 1}
    
cceDnsTable        OBJECT-TYPE
    SYNTAX         SEQUENCE OF CceDnsEntry
    MAX-ACCESS     not-accessible
    STATUS         current
    DESCRIPTION
        "DNS server table."
    ::= {cceDns 2}

cceDnsEntry       OBJECT-TYPE
    SYNTAX         CceDnsEntry
    MAX-ACCESS     not-accessible
    STATUS         current
    DESCRIPTION
        "Information on a DNS server that the cache engine has been
         configured to use.  When resolving DNS names, each DNS server
         is tried in table entry order until the name is resolved.
         The table entry order is determined by user configuration."
    INDEX          {cceDnsEntryIndex}
    ::= {cceDnsTable 1}

CceDnsEntry   ::= SEQUENCE {
    cceDnsEntryIndex     Integer32,
    cceDnsEntryIpAddress IpAddress
}

cceDnsEntryIndex    OBJECT-TYPE
    SYNTAX          Integer32 (1..8)
    MAX-ACCESS      not-accessible
    STATUS          current
    DESCRIPTION
        "Arbitrary index into the DNS server table."
    ::= {cceDnsEntry 1}

cceDnsEntryIpAddress      OBJECT-TYPE
    SYNTAX          IpAddress
    MAX-ACCESS      read-only
    STATUS          current
    DESCRIPTION
        "DNS server IP address."
    ::= {cceDnsEntry 2}

-- The following section describes the objects that are present
-- in the ICP client category of the config group

cceIcpClientEnabled     OBJECT-TYPE
    SYNTAX          TruthValue
    MAX-ACCESS      read-only
    STATUS          current
    DESCRIPTION
        "If true(1), the ICP Client is enabled.
         If false(2), the ICP Client is disabled.
         ICP is the Internet Cache Protocol as defined by RFC 2186
         and RFC 2187." 
    ::= {cceIcpClient 1}

cceIcpClientWait       OBJECT-TYPE
    SYNTAX          Integer32 (1..30)
    UNITS           "seconds"
    MAX-ACCESS      read-only
    STATUS          current
    DESCRIPTION
        "The timeout period for ICP responses.  If object retrieval
         has not commenced when the timeout occurs, a new source
         is selected."
    ::= {cceIcpClient 2}

cceIcpClientRetry      OBJECT-TYPE
    SYNTAX          Integer32 (10..100)
    MAX-ACCESS      read-only
    STATUS          current
    DESCRIPTION
        "The number of retries to be attempted before it is assumed that an
         ICP server is down."
    ::= {cceIcpClient 3}

cceIcpClientLocalDomains   OBJECT-TYPE
    SYNTAX         DisplayString
    MAX-ACCESS     read-only
    STATUS         current
    DESCRIPTION
        "Local domains for which ICP requests shall not be made.  These
         are the domains for which the cache engine is closer to the
         actual server than the other caches and would not benefit
         from the ICP interaction."
    ::= {cceIcpClient 4}

cceIcpClientRemServTable  OBJECT-TYPE
    SYNTAX          SEQUENCE OF CceIcpClientRemServEntry
    MAX-ACCESS      not-accessible
    STATUS          current
    DESCRIPTION
        "The remote server table contains information on remote servers
         (cache engines) to which ICP requests should be sent."
    ::= {cceIcpClient 5}

cceIcpClientRemServEntry  OBJECT-TYPE
    SYNTAX          CceIcpClientRemServEntry
    MAX-ACCESS      not-accessible
    STATUS          current
    DESCRIPTION
        "Information on an ICP remote server."
    INDEX          {cceIcpClientRemServIndex}
    ::= {cceIcpClientRemServTable 1}

CceIcpClientRemServEntry  ::= SEQUENCE {
    cceIcpClientRemServIndex       Integer32,
    cceIcpClientRemServIpAddress   IpAddress,
    cceIcpClientRemServState       INTEGER,
    cceIcpClientRemServType        INTEGER,
    cceIcpClientRemServIcpPort     Integer32,
    cceIcpClientRemServHttpPort    Integer32,
    cceIcpClientRemServSelDomains  DisplayString
}

cceIcpClientRemServIndex   OBJECT-TYPE
    SYNTAX          Integer32 (1..32)
    MAX-ACCESS      not-accessible
    STATUS          current
    DESCRIPTION
        "Arbitrary index into the remote server table.  The ICP requests are
         sent simultaneously to all the remote servers that are present."
    ::= {cceIcpClientRemServEntry 1}

cceIcpClientRemServIpAddress    OBJECT-TYPE
    SYNTAX          IpAddress
    MAX-ACCESS      read-only
    STATUS          current
    DESCRIPTION
        "IP address of the ICP remote server where all ICP requests shall
         be sent."
    ::= {cceIcpClientRemServEntry 2}

cceIcpClientRemServState    OBJECT-TYPE
    SYNTAX          INTEGER {
        normal   (1),
        warning  (2),
        critical (3)
    }
    MAX-ACCESS      read-only
    STATUS          current
    DESCRIPTION
        "ICP state of the remote server. 
         If normal(1), this remote server is operating normally.
         If warning(2), this remote server has stopped responding to
         ICP requests.
         If critical(3), this remote server is sending an ICP deny response."
    ::= {cceIcpClientRemServEntry 3}

cceIcpClientRemServType    OBJECT-TYPE
    SYNTAX          INTEGER {
        parent   (1),
        sibling  (2)
    }
    MAX-ACCESS      read-only
    STATUS          current
    DESCRIPTION
        "Configured ICP server type of the cache engine.
         If parent(1), the cache engine is allowed to retrieve objects
         when an ICP miss has occurred.
         If sibling(2), the cache engine is not allowed to retrieve
         objects when an ICP miss has occurred."
    ::= {cceIcpClientRemServEntry 4}

cceIcpClientRemServIcpPort OBJECT-TYPE
    SYNTAX          Integer32 (0..65535)
    MAX-ACCESS      read-only
    STATUS          current
    DESCRIPTION
        "Port on a remote ICP server to which
         ICP requests will be sent."
    ::= {cceIcpClientRemServEntry 5}

cceIcpClientRemServHttpPort    OBJECT-TYPE
    SYNTAX          Integer32 (0..65535)
    MAX-ACCESS      read-only
    STATUS          current
    DESCRIPTION
        "HTTP port to which proxy-style HTTP requests will be
         forwarded."
    ::= {cceIcpClientRemServEntry 6}

cceIcpClientRemServSelDomains        OBJECT-TYPE
    SYNTAX          DisplayString
    MAX-ACCESS      read-only
    STATUS          current
    DESCRIPTION
        "Set of domains for which ICP requests will be forwarded to 
         this ICP remote server.  List of domains is represented as
         a space-delimited string."
::= {cceIcpClientRemServEntry 7}

-- The following section describes the objects that are present
-- in the ICP server category of the config group

cceIcpServerEnabled OBJECT-TYPE
    SYNTAX          TruthValue
    MAX-ACCESS      read-only
    STATUS          current
    DESCRIPTION
        "If true(1), the ICP server protocol functionality is enabled.
         If false(2), the ICP server protocol functionality is disabled."
    ::= {cceIcpServer 1}

cceIcpServerPort    OBJECT-TYPE
    SYNTAX          Integer32 (0..65535)
    MAX-ACCESS      read-only
    STATUS          current
    DESCRIPTION
        "ICP port that the server is listening on.  The port to which
         other ICP clients can send ICP requests."
    ::= {cceIcpServer 2}

cceIcpServerRemClntTable  OBJECT-TYPE
    SYNTAX          SEQUENCE OF CceIcpServerRemClntEntry
    MAX-ACCESS      not-accessible
    STATUS          current
    DESCRIPTION
        "List of remote clients which are allowed to send ICP requests
         to this cache engine."
    ::= {cceIcpServer 3}

cceIcpServerRemClntEntry  OBJECT-TYPE
    SYNTAX          CceIcpServerRemClntEntry
    MAX-ACCESS      not-accessible
    STATUS          current
    DESCRIPTION
        "Information on a remote ICP server."
    INDEX   {cceIcpServerRemClntIndex}
    ::= {cceIcpServerRemClntTable 1}

CceIcpServerRemClntEntry  ::= SEQUENCE {
    cceIcpServerRemClntIndex       Integer32,
    cceIcpServerRemClntIPAddress   IpAddress,
    cceIcpServerRemClntFetch       TruthValue
}

cceIcpServerRemClntIndex    OBJECT-TYPE
    SYNTAX          Integer32 (1..32)
    MAX-ACCESS      not-accessible
    STATUS          current
    DESCRIPTION
        "Arbitrary index into the remote client table."
    ::= {cceIcpServerRemClntEntry 1}

cceIcpServerRemClntIPAddress   OBJECT-TYPE
    SYNTAX          IpAddress
    MAX-ACCESS      read-only
    STATUS          current
    DESCRIPTION
        "IP address of a remote client that is allowed to send ICP
         requests to this cache engine."
    ::= {cceIcpServerRemClntEntry 2}

cceIcpServerRemClntFetch   OBJECT-TYPE
    SYNTAX          TruthValue
    MAX-ACCESS      read-only
    STATUS          current
    DESCRIPTION
        "If true(1), the remote ICP client is allowed to request the
         HTTP object from the cache engine.
         If false(2), the remote ICP client is not allowed to request
         the HTTP object from the cache engine."
    ::= {cceIcpServerRemClntEntry 3}

-- The following section describes the objects that are present
-- in the proxy category of the config group

cceProxyIncomingPort        OBJECT-TYPE
    SYNTAX          Integer32 (0..65535)
    MAX-ACCESS      read-only
    STATUS          current
    DESCRIPTION
        "If non-zero, the cache engine is enabled to accept incoming
         proxy server requests on this port number.  Incoming proxy
         server requests originate from web browsers that are configured
         to use the cache engine as a proxy server.
         If zero, the cache engine is not enabled to act as a proxy server."
    ::= {cceProxy 1}

cceProxyOutgoingAddress     OBJECT-TYPE
    SYNTAX          DisplayString
    MAX-ACCESS      read-only
    STATUS          current
    DESCRIPTION
        "IP address or name of an upstream proxy server.  Outgoing client
         HTTP requests (for misses) from the proxy server are redirected
         to the upstream proxy server identified by this IP address or name.
         'Upstream' means a server closer to the actual source where the
         object resides."
    ::= {cceProxy 2}

cceProxyOutgoingPort        OBJECT-TYPE
    SYNTAX          Integer32 (0..65535)
    MAX-ACCESS      read-only
    STATUS          current
    DESCRIPTION
        "If non-zero, the cache engine is enabled for outgoing proxy mode
         and this value is the port number used to communicate with the
         upstream proxy server.
         If 0, outgoing proxy mode is disabled."
    ::= {cceProxy 3}

-- The following section describes the objects that are present
-- in the time category of the config group

cceTimeGmtTime      OBJECT-TYPE
    SYNTAX          DisplayString
    MAX-ACCESS      read-only
    STATUS          current
    DESCRIPTION
        "Current GMT (Greenwich Mean Time) military format (HH:MM:SS)."
    ::= {cceTime 1}

cceTimeGmtDate      OBJECT-TYPE
    SYNTAX          DisplayString
    MAX-ACCESS      read-only
    STATUS          current
    DESCRIPTION
        "The GMT date in (MM/DD/YYYY) format."
    ::= {cceTime 2}

cceTimeTable       OBJECT-TYPE
    SYNTAX         SEQUENCE OF CceTimeEntry
    MAX-ACCESS     not-accessible
    STATUS         current
    DESCRIPTION
        "The Network Time Protocol (NTP) server table."
    ::= {cceTime 3}

cceTimeEntry       OBJECT-TYPE
    SYNTAX         CceTimeEntry
    MAX-ACCESS     not-accessible
    STATUS         current
    DESCRIPTION
        "Information on an NTP server."
    INDEX          {cceTimeEntryIndex}
    ::= {cceTimeTable 1}

CceTimeEntry ::= SEQUENCE {
    cceTimeEntryIndex     Integer32,
    cceTimeEntryIpAddress IpAddress
}

cceTimeEntryIndex   OBJECT-TYPE
    SYNTAX          Integer32 (1..4)
    MAX-ACCESS      not-accessible
    STATUS          current
    DESCRIPTION
        "Arbitrary index into the NTP server table.
         NTP requests are sent to each server in table order,
         until a request is satisfied."
    ::= {cceTimeEntry 1}

cceTimeEntryIpAddress    OBJECT-TYPE
    SYNTAX          IpAddress
    MAX-ACCESS      read-only
    STATUS          current
    DESCRIPTION
        "IP address of the NTP server."
    ::= {cceTimeEntry 2}
            
-- The following section describes the objects that are present
-- in the cache farm category of the tuning group

cceCacheFarmHealingModeWait    OBJECT-TYPE
    SYNTAX          Integer32 (10..200)
    UNITS           "milliseconds"
    MAX-ACCESS      read-only
    STATUS          current
    DESCRIPTION
        "Maximum time the cache engine shall wait for objects to be
         retrieved from the other caches in the farm during cache
         engine initialization."
    ::= {cceCacheFarm 1}

cceCacheFarmHealingModeRetry   OBJECT-TYPE
    SYNTAX          Integer32 (0..2147483647)
    MAX-ACCESS      read-only
    STATUS          current
    DESCRIPTION
        "Number of times the cache engine will ask its neighbor caches
         in the farm for misses before it determines that the caches
         'knows nothing', and stops asking.  Initial default value is 200."
     ::= {cceCacheFarm 2}

cceCacheFarmVersion    OBJECT-TYPE
    SYNTAX          DisplayString
    MAX-ACCESS      read-only
    STATUS          current
    DESCRIPTION
        "Version description of the currently executing cache engine
         object code image."
    ::= {cceCacheFarm 3}

-- The following section describes the objects that are present
-- in the freshness category of the tuning group

cceFreshnessTextAgeMultiplier  OBJECT-TYPE
    SYNTAX          Integer32 (0..999)
    UNITS           "percentage"
    MAX-ACCESS      read-only
    STATUS          current
    DESCRIPTION
        "Percentage multiplier used to calculate the expiration date of
         a text object if the expiration date is not explicitly specified.
         This percentage is multiplied by the age of the object to calculate
         the freshness time of the object.  The expiration date is
         the sum of the freshness time and the date the object was last
         retrieved from the server or verified was up-to-date.  The object
         will be considered stale after its expiration date and a subsequent
         If-Modified-Since (IMS) request will be revalidated with the
         server by the cache engine.
         If zero, the calculated expiration time will indicate that the
         the object expires immediately."
    ::= {cceFreshness 1}

cceFreshnessBinaryAgeMultiplier OBJECT-TYPE
    SYNTAX          Integer32 (0..999)
    UNITS           "percentage"
    MAX-ACCESS      read-only
    STATUS          current
    DESCRIPTION
        "Percentage multiplier used to calculate the expiration date of
         a binary object if the expiration date is not explicitly specified.
         This percentage is multiplied by the age of the object to calculate
         the freshness time of the object.  The expiration date is
         the sum of the freshness time and the date the object was last
         retrieved from the server or verified was up-to-date.  The object
         will be considered stale after its expiration date and a subsequent
         If-Modified-Since (IMS) request will be revalidated with the
         server by the cache engine.
         If zero, the calculated expiration time will indicate that the
         the object expires immediately."
    ::= {cceFreshness 2}

cceFreshnessTextMaximumTTL    OBJECT-TYPE
    SYNTAX          Integer32 (0..999)
    MAX-ACCESS      read-only
    STATUS          current
    DESCRIPTION
        "Maximum Time-to-Live for any text object for which the cache
         engine has to calculate an expiration date.  Used to impose
         an upper limit on the calculated expiration date.
         If zero, the text object will never be cached.
         Units are specified in cceFreshnessUnitsMaximumTTL."
    ::= {cceFreshness 3}

cceFreshnessBinaryMaximumTTL    OBJECT-TYPE
    SYNTAX          Integer32 (1..999)
    MAX-ACCESS      read-only
    STATUS          current
    DESCRIPTION
        "Maximum Time-to-Live for any binary object for which the cache
         engine has to calculate an expiration date.  Used to impose
         an upper limit on the calculated expiration date.
         If zero, the binary object will never be cached.
         Units are specified in cceFreshnessUnitsMaximumTTL."
    ::= {cceFreshness 4}

cceFreshnessUnitsMaximumTTL    OBJECT-TYPE
    SYNTAX    INTEGER {
        seconds (1),
        minutes (2),
        hours   (3),
        days    (4)
    }
    MAX-ACCESS      read-only
    STATUS          current
    DESCRIPTION
        "Units in which Maximum TTL for text and binary objects should be
         interpreted."
    ::= {cceFreshness 5}

cceFreshnessCacheCookies   OBJECT-TYPE
    SYNTAX          TruthValue
    MAX-ACCESS      read-only
    STATUS          current
    DESCRIPTION
        "If true(1), text objects associated with cookies are cached.
         If false(2), text objects associated with cookies are not cached.
         Cacheable, binary objects associated with cookies are always cached."
    ::= {cceFreshness 6}

cceFreshnessTextMaxAge    OBJECT-TYPE
    SYNTAX          Integer32 (0..999)
    UNITS           "percentage"
    MAX-ACCESS      read-only
    STATUS          current
    DESCRIPTION
        "Percentage of the maximum Time-To-Live of text objects used to
         calculate the minimum age that a text object must be before
         an up-to-date check is performed with the server as a result
         of an IMS request.  If the age of a text object is less than
         this percentage of the maximum Time-To-Live for text objects,
         then an IMS request is served out of the cache.
         If zero, an IMS request is always sent to the server."
    ::= {cceFreshness 7}

cceFreshnessBinaryMaxAge    OBJECT-TYPE
    SYNTAX          Integer32 (0..999)
    UNITS           "percentage"
    MAX-ACCESS      read-only
    STATUS          current
    DESCRIPTION
        "Percentage of the maximum Time-To-Live of binary objects used to
         calculate the minimum age that a binary object must be before
         an up-to-date check is performed with the server as a result
         of an IMS request.  If the age of a binary object is less than
         this percentage of the maximum Time-To-Live for binary objects,
         then an IMS request is served out of the cache.
         If zero, an IMS request is always sent to the server."
    ::= {cceFreshness 8}

cceFreshnessForceMiss    OBJECT-TYPE
    SYNTAX          INTEGER {
        revalidate (1),
        retrieve   (2)
    }
    MAX-ACCESS      read-only
    STATUS          current
    DESCRIPTION
        "If revalidate(1), then on a forced cache miss from the client
         browser the cache engine shall send an If-Modified-Since (IMS)
         HTTP request to revalidate the object.
         If retrieve(2), then on a forced cache miss from the client
         browser the cache engine shall send a Pragma:No-Cache HTTP
         request to retrieve a fresh copy."
    ::= {cceFreshness 9}

-- The following section describes the objects that are present
-- in the TCP category of the tuning group

cceTcpServerSendBuffer    OBJECT-TYPE
    SYNTAX          Integer32 (2..256)
    UNITS           "kilobytes"
    MAX-ACCESS      read-only
    STATUS          current
    DESCRIPTION
        "The size of the TCP send buffer socket for the server."
    ::= {cceTcp 1}

cceTcpClientSendBuffer    OBJECT-TYPE
    SYNTAX          Integer32 (2..256)
    UNITS           "kilobytes"
    MAX-ACCESS      read-only
    STATUS          current
    DESCRIPTION
        "The size of the TCP send buffer socket for the client."
    ::= {cceTcp 2}

cceTcpServerRecvBuffer    OBJECT-TYPE
    SYNTAX          Integer32 (2..256)
    UNITS           "kilobytes"
    MAX-ACCESS      read-only
    STATUS          current
    DESCRIPTION
        "The size of the TCP receive buffer socket for the server."
    ::= {cceTcp 3}

cceTcpClientRecvBuffer    OBJECT-TYPE
    SYNTAX          Integer32 (2..256)
    UNITS           "kilobytes"
    MAX-ACCESS      read-only
    STATUS          current
    DESCRIPTION
        "The size of the TCP receive buffer socket for the client."
    ::= {cceTcp 4}

cceTcpServerReadWriteTimeout    OBJECT-TYPE
    SYNTAX          Integer32 (10..300)
    UNITS           "seconds"
    MAX-ACCESS      read-only
    STATUS          current
    DESCRIPTION
        "Read/write timeout for the server."
    ::= {cceTcp 5}

cceTcpClientReadWriteTimeout    OBJECT-TYPE
    SYNTAX          Integer32 (10..300)
    UNITS           "seconds"
    MAX-ACCESS      read-only
    STATUS          current
    DESCRIPTION
        "Read/write timeout for the client."
    ::= {cceTcp 6}

cceTcpConnectionIdleTimeout    OBJECT-TYPE
    SYNTAX          Integer32 (60..7200)
    UNITS           "seconds"
    MAX-ACCESS      read-only
    STATUS          current
    DESCRIPTION
        "Idle timeout for connection."
    ::= {cceTcp 7}

cceTcpConnectionWaitTimeout    OBJECT-TYPE
    SYNTAX          Integer32 (30..7200)
    UNITS           "seconds"
    MAX-ACCESS      read-only
    STATUS          current
    DESCRIPTION
        "Wait timeout for connection."
    ::= {cceTcp 8}

cceTcpConnectionRetry    OBJECT-TYPE
    SYNTAX          Integer32 (1..20)
    MAX-ACCESS      read-only
    STATUS          current
    DESCRIPTION
        "Number of times to retry the TCP connection."
    ::= {cceTcp 9}

-- The following section describes the objects that are present
-- in the URL filtering category of the access group

cceUrlFilterState   OBJECT-TYPE
    SYNTAX          INTEGER {
        off       (1),
        blockBad  (2),
        allowGood (3)
    }
    MAX-ACCESS      read-only
    STATUS          current
    DESCRIPTION
        "If off(1), the cache engine can serve any URL.
         If blockBad(2), the cache engine can not serve those URLs that are
         present in the bad URL list which resides in a file on the cache
         engine.
         If allowGood(3), the cache engine can serve only those URLs that
         are present in the good URL list which resides in the file on the
         cache engine."
    ::= {cceUrlFilter 1}

-- The following section describes the objects that are present
-- in the events category of the reporting group

cceEventsTotal      OBJECT-TYPE
    SYNTAX          Integer32 (0..999)
    MAX-ACCESS      read-only
    STATUS          current
    DESCRIPTION
        "Maximum number of event entries that can be viewed at this time."
    ::= {cceEvents 1}

cceEventsCritical   OBJECT-TYPE
    SYNTAX          TruthValue
    MAX-ACCESS      read-only
    STATUS          current
    DESCRIPTION
        "If true(1), include event entries with the event entry type
         of critical in the event table if any exist.
         If false(2), do not include event entries with the event entry type
         of critical in the event table."
    ::= {cceEvents 2}

cceEventsWarning    OBJECT-TYPE
    SYNTAX          TruthValue
    MAX-ACCESS      read-only
    STATUS          current
    DESCRIPTION
        "If true(1), include event entries with the event entry type
         of warning in the event table if any exist.
         If false(2), do not include event entries with the event entry type
         of warning in the event table."
    ::= {cceEvents 3}

cceEventsNotice     OBJECT-TYPE
    SYNTAX          TruthValue
    MAX-ACCESS      read-only
    STATUS          current
    DESCRIPTION
        "If true(1), include event entries with the event entry type
         of notice in the event table if any exist.
         If false(2), do not include event entries with the event entry type
         of notice in the event table."
    ::= {cceEvents 4}

cceEventsTable      OBJECT-TYPE
    SYNTAX          SEQUENCE OF CceEventsEntry
    MAX-ACCESS      not-accessible
    STATUS          current
    DESCRIPTION
        "Events logged."
    ::= {cceEvents 5}

cceEventsEntry    OBJECT-TYPE
    SYNTAX          CceEventsEntry
    MAX-ACCESS      not-accessible
    STATUS          current
    DESCRIPTION
        "Each entry contains information on a single event."
    INDEX          {cceEventsEntryIndex}
    ::= {cceEventsTable 1}

CceEventsEntry ::= SEQUENCE {
    cceEventsEntryIndex       Integer32,
    cceEventsEntryType        INTEGER,
    cceEventsEntryMessage     DisplayString,
    cceEventsEntryTime        DisplayString
}

cceEventsEntryIndex OBJECT-TYPE
    SYNTAX          Integer32 (0 | 1..999)
    MAX-ACCESS      not-accessible
    STATUS          current
    DESCRIPTION
        "Arbitrary index into the event table.
         Entries are in reverse chronological order.
         Index range is 1 to cceEventsTotal.
         If 0, there are no events."
    ::= {cceEventsEntry 1}

cceEventsEntryType    OBJECT-TYPE
    SYNTAX          INTEGER {
        notice   (1),
        warning  (2),
        critical (3)
    }
    MAX-ACCESS      read-only
    STATUS          current
    DESCRIPTION
        "Events message type.
         If notice(1), the message is an informational message.
         If warning(2), the message is a warning message.
         If critical(3),the message is critical message."
    ::= {cceEventsEntry 2}

cceEventsEntryMessage    OBJECT-TYPE
    SYNTAX          DisplayString
    MAX-ACCESS      read-only
    STATUS          current
    DESCRIPTION
        "Event message."
    ::= {cceEventsEntry 3}

cceEventsEntryTime       OBJECT-TYPE
    SYNTAX          DisplayString
    MAX-ACCESS      read-only
    STATUS          current
    DESCRIPTION
        "Time when the message was logged.
         Format is 'WWW, DD MMM YYYY HH:MM:SS GMT'."
    ::= {cceEventsEntry 4}

-- The following section describes the objects that are present
-- in the logging category of the reporting group

cceLoggingEnabled OBJECT-TYPE
    SYNTAX          TruthValue
    MAX-ACCESS      read-only
    STATUS          current
    DESCRIPTION
        "If true(1), transaction logging is on.
         If false(2), transaction logging is off.
         Transactions are logged in squid log format."
    ::= {cceLogging 1}

cceLoggingInterval    OBJECT-TYPE
    SYNTAX          Integer32 (1..99999999)
    UNITS           "seconds"
    MAX-ACCESS      read-only
    STATUS          current
    DESCRIPTION
        "Amount of time that must elapse before the working log
         will be cleared by moving the data into the archive log
         which overwrites the previous archive log."
    ::= {cceLogging 2}

cceLoggingWorkingLogPresent OBJECT-TYPE
    SYNTAX          TruthValue
    MAX-ACCESS      read-only
    STATUS          current
    DESCRIPTION
        "If true(1), the working log is present.
         If false(2), the working log is not present.
         The working log is a file that logs information on cache
         engine transactions."
    ::= {cceLogging 3}

cceLoggingSize     OBJECT-TYPE
    SYNTAX          Integer32 (0..2147483647)
    UNITS           "Bytes"
    MAX-ACCESS      read-only
    STATUS          current
    DESCRIPTION
        "Current size of the working log if present."
    ::= {cceLogging 4}

cceLoggingAge    OBJECT-TYPE
    SYNTAX          Integer32 (1..99999999)
    UNITS           "seconds"
    MAX-ACCESS      read-only
    STATUS          current
    DESCRIPTION
        "Age of the working log."
    ::= {cceLogging 5}

cceLoggingArchiveLogPresent OBJECT-TYPE
    SYNTAX          TruthValue
    MAX-ACCESS      read-only
    STATUS          current
    DESCRIPTION
        "If true(1), archive log is present.
         If false(2), archive log is not present.
         The archive log is overwritten with a copy of the working log
         at the interval of time specified in cceLoggingInterval."
    ::= {cceLogging 6}

cceLoggingArchiveLogSize    OBJECT-TYPE
    SYNTAX          Integer32 (0..2147483647)
    UNITS           "Bytes"
    MAX-ACCESS      read-only
    STATUS          current
    DESCRIPTION
        "The current archive log size if present."
    ::= {cceLogging 7}

cceLoggingWriteFailReason    OBJECT-TYPE
    SYNTAX          DisplayString
    MAX-ACCESS      read-only
    STATUS          current
    DESCRIPTION
        "The reason for the failure of the last translog
         write operation.If the last operation was
         successful, then this object will be
         displayed as NotApplicable."
    ::= {cceLogging 8}


-- The following section describes the objects that are present
-- in the diagdump category of the statistics group

cceDiagDumpDiskCreates    OBJECT-TYPE
    SYNTAX          Counter32
    MAX-ACCESS      read-only
    STATUS          current
    DESCRIPTION
        "Number of new files created."
    ::= {cceDiagDump 1}

cceDiagDumpDiskOpens    OBJECT-TYPE
    SYNTAX          Counter32
    MAX-ACCESS      read-only
    STATUS          current
    DESCRIPTION
        "Number of existing files opened."
    ::= {cceDiagDump 2}

cceDiagDumpDiskCloses    OBJECT-TYPE
    SYNTAX          Counter32
    MAX-ACCESS      read-only
    STATUS          current
    DESCRIPTION
        "Number of completed file operations."
    ::= {cceDiagDump 3}

cceDiagDumpDiskDeletes    OBJECT-TYPE
    SYNTAX          Counter32
    MAX-ACCESS      read-only
    STATUS          current
    DESCRIPTION
        "Number of files deleted."
    ::= {cceDiagDump 4}

cceDiagDumpDiskReads    OBJECT-TYPE
    SYNTAX          Counter32
    MAX-ACCESS      read-only
    STATUS          current
    DESCRIPTION
        "Number of file system reads."
    ::= {cceDiagDump 5}

cceDiagDumpDiskWrites    OBJECT-TYPE
    SYNTAX          Counter32
    MAX-ACCESS      read-only
    STATUS          current
    DESCRIPTION
        "Number of file system writes."
    ::= {cceDiagDump 6}

cceDiagDumpDiskStats    OBJECT-TYPE
    SYNTAX          Counter32
    MAX-ACCESS      read-only
    STATUS          current
    DESCRIPTION
        "Number of times we got system info about a file."
    ::= {cceDiagDump 7}

cceDiagDumpDiskFree    OBJECT-TYPE
    SYNTAX          Counter32
    MAX-ACCESS      read-only
    STATUS          current
    DESCRIPTION
        "Total free disk space."
    ::= {cceDiagDump 8}

cceDiagDumpDiskWraps    OBJECT-TYPE
    SYNTAX          Counter32
    MAX-ACCESS      read-only
    STATUS          current
    DESCRIPTION
        "Number of times a disk partition has been wrapped in the 
         cache engine file system."
    ::= {cceDiagDump 9}

cceDiagDumpDiskOverWrites    OBJECT-TYPE
    SYNTAX          Counter32
    MAX-ACCESS      read-only
    STATUS          current
    DESCRIPTION
        "Number of files greater than 48 kilo bytes in size which 
         arrived in a HTTP response without the content length
         being sent explicitly."
    ::= {cceDiagDump 10}

cceDiagDumpDiskTruncReads    OBJECT-TYPE
    SYNTAX          Counter32
    MAX-ACCESS      read-only
    STATUS          current
    DESCRIPTION
        "Number of files which were deemed truncated when end of file 
         was reached prematurely on a read."
    ::= {cceDiagDump 11}

cceDiagDumpDiskInodeErrors    OBJECT-TYPE
    SYNTAX          Counter32
    MAX-ACCESS      read-only
    STATUS          current
    DESCRIPTION
        "Number of times a file has not been found at the expected
         location."
    ::= {cceDiagDump 12}

cceDiagDumpDiskCrcErrors    OBJECT-TYPE
    SYNTAX          Counter32
    MAX-ACCESS      read-only
    STATUS          current
    DESCRIPTION
        "Number of times the Cyclic Redundancy Check (CRC) of the
         file did not match."
    ::= {cceDiagDump 13}

cceDiagDumpDiskDirCollisions    OBJECT-TYPE
    SYNTAX          Counter32
    MAX-ACCESS      read-only
    STATUS          current
    DESCRIPTION
        "Number of directory lookup failures because of collision."
    ::= {cceDiagDump 14}

cceDiagDumpBufferReads    OBJECT-TYPE
    SYNTAX          Counter32
    MAX-ACCESS      read-only
    STATUS          current
    DESCRIPTION
        "Number of physical disk reads occurred."
    ::= {cceDiagDump 15}

cceDiagDumpBufferReadErrors    OBJECT-TYPE
    SYNTAX          Counter32
    MAX-ACCESS      read-only
    STATUS          current
    DESCRIPTION
        "Number of times a failure to read from disk occurred."
    ::= {cceDiagDump 16}

cceDiagDumpBufferWrites        OBJECT-TYPE
    SYNTAX          Counter32
    MAX-ACCESS      read-only
    STATUS          current
    DESCRIPTION
        "Number of physical disk writes."
    ::= {cceDiagDump 17}

cceDiagDumpBufferWriteErrors    OBJECT-TYPE
    SYNTAX          Counter32
    MAX-ACCESS      read-only
    STATUS          current
    DESCRIPTION
        "Number of times a failure to write to disk occurred."
    ::= {cceDiagDump 18}

cceDiagDumpBufferHits        OBJECT-TYPE
    SYNTAX          Counter32
    MAX-ACCESS      read-only
    STATUS          current
    DESCRIPTION
        "Number of objects retrieved from buffer."
    ::= {cceDiagDump 19}

cceDiagDumpBufferMisses    OBJECT-TYPE
    SYNTAX          Counter32
    MAX-ACCESS      read-only
    STATUS          current
    DESCRIPTION
        "Number of objects retrieved from physical drive."
    ::= {cceDiagDump 20}

cceDiagDumpBufferSeekErrors    OBJECT-TYPE
    SYNTAX          Counter32
    MAX-ACCESS      read-only
    STATUS          current
    DESCRIPTION
        "The number of times a failure occurred in positioning the 
         disk head."
    ::= {cceDiagDump 21}

-- The following section describes the objects that are present
-- in the IMS category of the statistics group

cceImsClientRequestTotal                OBJECT-TYPE
    SYNTAX          Counter64
    MAX-ACCESS      read-only
    STATUS          current
    DESCRIPTION
        "The total number of requests from the client to 
         the cache engine."
    ::= {cceIms 1}

cceImsReceived                OBJECT-TYPE
    SYNTAX          Counter64
    MAX-ACCESS      read-only
    STATUS          current
    DESCRIPTION
        "The total number of requests received from the client
         that were IMS requests."
    ::= {cceIms 2}

cceImsClientTotalFromCache                OBJECT-TYPE
    SYNTAX          Counter64
    MAX-ACCESS      read-only
    STATUS          current
    DESCRIPTION
        "The total number of IMS requests from the client served directly 
         from the cache engine's cache without revalidation."
    ::= {cceIms 3}

cceImsClientFreshFromCache                OBJECT-TYPE
    SYNTAX          Counter64
    MAX-ACCESS      read-only
    STATUS          current
    DESCRIPTION
        "The number of times the client's requested IMS object was 
         found to be fresh (304-Not Modified)."
    ::= {cceIms 4}

cceImsClientStaleFromCache                OBJECT-TYPE
    SYNTAX          Counter64
    MAX-ACCESS      read-only
    STATUS          current
    DESCRIPTION
        "The number of times the client's requested IMS object was 
         found to be stale.  If stale, an updated object was returned 
         to the client."
    ::= {cceIms 5}

cceImsClientTotalCacheMiss                OBJECT-TYPE
    SYNTAX          Counter64
    MAX-ACCESS      read-only
    STATUS          current
    DESCRIPTION
        "The total number of IMS requests which had to be forwarded
        to the actual server."
    ::= {cceIms 6}

cceImsClientFreshCacheMiss                OBJECT-TYPE
    SYNTAX          Counter64
    MAX-ACCESS      read-only
    STATUS          current
    DESCRIPTION
        "The number of IMS requests which had to be forwarded  to the 
         actual server but were found to be fresh."
    ::= {cceIms 7}

cceImsClientStaleCacheMiss                OBJECT-TYPE
    SYNTAX          Counter64
    MAX-ACCESS      read-only
    STATUS          current
    DESCRIPTION
        "The number of IMS requests which had to be forwarded  to the 
         actual server but were found to be stale."
    ::= {cceIms 8}

cceImsClientTotalReval                OBJECT-TYPE
    SYNTAX          Counter64
    MAX-ACCESS      read-only
    STATUS          current
    DESCRIPTION
        "The number of IMS requests from the client found in the 
         cache, and revalidated with an IMS to the server."
    ::= {cceIms 9}

cceImsClientFreshReval                OBJECT-TYPE
    SYNTAX          Counter64
    MAX-ACCESS      read-only
    STATUS          current
    DESCRIPTION
        "The number of IMS requests from the client found in the 
        cache, and revalidated with an IMS to the server and found 
        fresh."
    ::= {cceIms 10}

cceImsClientStaleReval                OBJECT-TYPE
    SYNTAX          Counter64
    MAX-ACCESS      read-only
    STATUS          current
    DESCRIPTION
        "The number of IMS requests from the client found in the 
         cache, and revalidated with an IMS to the server and found 
         stale."
    ::= {cceIms 11}

cceImsClientRequestToServer                OBJECT-TYPE
    SYNTAX          Counter64
    MAX-ACCESS      read-only
    STATUS          current
    DESCRIPTION
        "The total number of requests from the cache engine to 
        remote servers." 
    ::= {cceIms 12}

cceImsServerTotalIssued                OBJECT-TYPE
    SYNTAX          Counter64
    MAX-ACCESS      read-only
    STATUS          current
    DESCRIPTION
        "The total number of requests sent from the cache to
         servers that were IMS requests."
    ::= {cceIms 13}

cceImsServerTotalDueClient                OBJECT-TYPE
    SYNTAX          Counter64
    MAX-ACCESS      read-only
    STATUS          current
    DESCRIPTION
        "The number of IMS requests sent to servers because of an 
        IMS request from the client."
    ::= {cceIms 14}

cceImsServerFreshDueClient                OBJECT-TYPE
    SYNTAX          Counter64
    MAX-ACCESS      read-only
    STATUS          current
    DESCRIPTION
        "The number of times the cache's requested IMS object
         was found to be fresh (304-Not Modified)."
    ::= {cceIms 15}

cceImsServerStaleDueClient                OBJECT-TYPE
    SYNTAX          Counter64
    MAX-ACCESS      read-only
    STATUS          current
    DESCRIPTION
        "The number of times the cache's requested IMS object
         was found to be stale.  If stale, a new object was retrieved
        from the server."
    ::= {cceIms 16}

cceImsServerTotalDueExpiration                OBJECT-TYPE
    SYNTAX          Counter64
    MAX-ACCESS      read-only
    STATUS          current
    DESCRIPTION
        "The number of IMS requests sent to servers because the 
        requested object was determined to be stale according to 
        the cache engine's freshness settings."
    ::= {cceIms 17}

cceImsClientFreshDueExpiration                OBJECT-TYPE
    SYNTAX          Counter64
    MAX-ACCESS      read-only
    STATUS          current
    DESCRIPTION
        "The number of times the cache's requested IMS object
         was found to be fresh (304-Not Modified) even when the object's
         age had expired."
    ::= {cceIms 18}

cceImsServerStaleDueExpiration                OBJECT-TYPE
    SYNTAX          Counter64
    MAX-ACCESS      read-only
    STATUS          current
    DESCRIPTION
        "The number of times the cache's requested IMS object
         was found to be stale when the object's age had expired. 
         If stale, a new object was retrieved from the server."
    ::= {cceIms 19}

-- The following section describes the objects that are present
-- in the performance category of the statistics group

ccePerformanceReqPerSecMax    OBJECT-TYPE
    SYNTAX          Gauge32
    MAX-ACCESS      read-only
    STATUS          current
    DESCRIPTION
        "Maximum number of requests per second the cache engine
        has been servicing."
    ::= {ccePerformance 1}

ccePerformanceReqPerSecLast    OBJECT-TYPE
    SYNTAX          Integer32 (0..2147483647)
    MAX-ACCESS      read-only
    STATUS          current
    DESCRIPTION
        "Number of requests per second the cache engine
        has been servicing in the last sampling time."
    ::= {ccePerformance 2}

ccePerformanceBytesPerSecMax    OBJECT-TYPE
    SYNTAX          Gauge32
    UNITS           "Bytes-per-second"
    MAX-ACCESS      read-only
    STATUS          current
    DESCRIPTION
        "Maximum bytes per second served."
    ::= {ccePerformance 3}

ccePerformanceBytesPerSecLast    OBJECT-TYPE
    SYNTAX          Integer32 (0..2147483647)
    UNITS           "Bytes-per-second"
    MAX-ACCESS      read-only
    STATUS          current
    DESCRIPTION
        "Bytes per second served in the last sampling time."
    ::= {ccePerformance 4}

ccePerformanceSecPerReqAvg    OBJECT-TYPE
    SYNTAX          Integer32 (0..2147483647)
    UNITS           "milliseconds-per-req"
    MAX-ACCESS      read-only
    STATUS          current
    DESCRIPTION
        "Average duration of each connection serviced by the cache 
         engine."
    ::= {ccePerformance 5}

ccePerformanceSecPerReqMin    OBJECT-TYPE
    SYNTAX          Integer32 (0..2147483647)
    UNITS           "milliseconds-per-req"
    MAX-ACCESS      read-only
    STATUS          current
    DESCRIPTION
        "Shortest duration of each connection serviced by the cache 
         engine."
    ::= {ccePerformance 6}

ccePerformanceSecPerReqMax    OBJECT-TYPE
    SYNTAX          Gauge32
    UNITS           "milliseconds-per-req"
    MAX-ACCESS      read-only
    STATUS          current
    DESCRIPTION
        "Longest duration of each connection serviced by the cache 
         engine."
    ::= {ccePerformance 7}

ccePerformanceSecPerReqLast    OBJECT-TYPE
    SYNTAX          Integer32 (0..2147483647)
    UNITS           "milliseconds-per-req"
    MAX-ACCESS      read-only
    STATUS          current
    DESCRIPTION
        "Average duration of each connection serviced by the cache 
         engine in the last sampling time."
    ::= {ccePerformance 8}

ccePerformanceHitsSecPerReqAvg     OBJECT-TYPE
    SYNTAX          Integer32 (0..2147483647)
    UNITS           "milliseconds-per-req"
    MAX-ACCESS      read-only
    STATUS          current
    DESCRIPTION
        "Average duration required for the cache engine to send a hit 
         response.  A hit response is a response when the object
         can be serviced from the cache engine."
    ::= {ccePerformance 9}

ccePerformanceHitsSecPerReqMin    OBJECT-TYPE
    SYNTAX          Integer32 (0..2147483647)
    UNITS           "milliseconds-per-req"
    MAX-ACCESS      read-only
    STATUS          current
    DESCRIPTION
        "Shortest duration required for the cache engine to send a hit
         response."
    ::= {ccePerformance 10}

ccePerformanceHitsSecPerReqMax    OBJECT-TYPE
    SYNTAX          Gauge32
    UNITS           "milliseconds-per-req"
    MAX-ACCESS      read-only
    STATUS          current
    DESCRIPTION
        "Longest duration required for the cache engine to send a hit
         response."
    ::= {ccePerformance 11}

ccePerformanceHitsSecPerReqLast    OBJECT-TYPE
    SYNTAX          Integer32 (0..2147483647)
    UNITS           "milliseconds-per-req"
    MAX-ACCESS      read-only
    STATUS          current
    DESCRIPTION
        "Average duration required for the cache engine to send a hit
         response in the last sampling time."
    ::= {ccePerformance 12}

ccePerformanceMissSecPerReqAvg    OBJECT-TYPE
    SYNTAX          Integer32 (0..2147483647)
    UNITS           "milliseconds-per-req"
    MAX-ACCESS      read-only
    STATUS          current
    DESCRIPTION
        "Average duration required for the cache engine to send a miss
         response.  A miss response is a response when the object
         cannot be serviced from the cache engine."
    ::= {ccePerformance 13}

ccePerformanceMissSecPerReqMin    OBJECT-TYPE
    SYNTAX          Integer32 (0..2147483647)
    UNITS           "milliseconds-per-req"
    MAX-ACCESS      read-only
    STATUS          current
    DESCRIPTION
        "Shortest duration required for the cache engine to send a miss
         response."
    ::= {ccePerformance 14}

ccePerformanceMissSecPerReqMax    OBJECT-TYPE
    SYNTAX          Gauge32
    UNITS           "milliseconds-per-req"
    MAX-ACCESS      read-only
    STATUS          current
    DESCRIPTION
        "Longest duration required for the cache engine to send a miss
         response."
    ::= {ccePerformance 15}

ccePerformanceMissSecPerReqLast    OBJECT-TYPE
    SYNTAX          Integer32 (0..2147483647)
    UNITS           "milliseconds-per-req"
    MAX-ACCESS      read-only
    STATUS          current
    DESCRIPTION
        "Average duration required for the cache engine to send a miss
         response in the last sampling time."
    ::= {ccePerformance 16}

ccePerformanceObjectSizeAvg    OBJECT-TYPE
    SYNTAX          Integer32 (0..2147483647)
    UNITS           "byte/10"
    MAX-ACCESS      read-only
    STATUS          current
    DESCRIPTION
        "Average size of the object served from the cache engine."
    ::= {ccePerformance 17}

ccePerformanceObjectSizeMin     OBJECT-TYPE
    SYNTAX          Integer32 (0..2147483647)
    UNITS           "Bytes"
    MAX-ACCESS      read-only
    STATUS          current
    DESCRIPTION
        "Minimum size of the object served from the cache engine."
    ::= {ccePerformance 18}

ccePerformanceObjectSizeMax    OBJECT-TYPE
    SYNTAX          Gauge32
    UNITS           "Bytes"
    MAX-ACCESS      read-only
    STATUS          current
    DESCRIPTION
        "Maximum size of the object served from the cache engine."
    ::= {ccePerformance 19}

ccePerformanceObjectSizeLast    OBJECT-TYPE
    SYNTAX          Integer32 (0..2147483647)
    UNITS           "bytes/10"
    MAX-ACCESS      read-only
    STATUS          current
    DESCRIPTION
        "Average size of the object served from the cache engine
         in the last sampling time."
    ::= {ccePerformance 20}

-- The following section describes the objects that are present
-- in the requests category of the statistics group

cceRequestsForcedReloadTotal    OBJECT-TYPE
    SYNTAX          Counter64
    MAX-ACCESS      read-only
    STATUS          current
    DESCRIPTION
        "Total number of times a client browser has requested a
         fresh copy of an object regardless of its freshness."
    ::= {cceRequests 1}

cceRequestsForcedReloadPercent    OBJECT-TYPE
    SYNTAX          Integer32 (0..1000)
    UNITS           "percentage/10"
    MAX-ACCESS      read-only
    STATUS          current
    DESCRIPTION
        "Total number of times a client browser has requested a
         fresh copy of an object regardless of its freshness."
    ::= {cceRequests 2}

cceRequestsNearHitsTotal   OBJECT-TYPE
    SYNTAX          Counter64
    MAX-ACCESS      read-only
    STATUS          current
    DESCRIPTION
        "Total number of times a cache engine does not find the 
         requested object(s) in its cache, but is able to retrieve 
         the object from a neighboring cache engine in the farm."
    ::= {cceRequests 3}

cceRequestsNearHitsPercent OBJECT-TYPE
    SYNTAX          Integer32 (0..1000)
    UNITS           "percentage/10"
    MAX-ACCESS      read-only
    STATUS          current
    DESCRIPTION
        "Total number of times a cache engine does not find the 
         requested object(s) in its cache, but is able to retrieve 
         the object from a neighboring cache engine in the farm."
::= {cceRequests 4}

cceRequestsServerErrorTotal   OBJECT-TYPE
    SYNTAX          Counter64
    MAX-ACCESS      read-only
    STATUS          current
    DESCRIPTION
        "Total number of times the cache engine has failed to fulfill 
         a request due to a web host problem or network problem and 
         has generated and logged an error."
    ::= {cceRequests 5}

cceRequestsServerErrorPercent OBJECT-TYPE
    SYNTAX          Integer32 (0..1000)
    UNITS           "percentage/10"
    MAX-ACCESS      read-only
    STATUS          current
    DESCRIPTION
        "Total number of times the cache engine has failed to fulfill 
         a request due to a web host problem or network problem and 
         has generated and logged an error."
    ::= {cceRequests 6}

cceRequestsUrlBlockedTotal   OBJECT-TYPE
    SYNTAX          Counter64
    MAX-ACCESS      read-only
    STATUS          current
    DESCRIPTION
        "Total number of times a client browser has attempted to
         access an administratively blocked URL via the cache engine."
    ::= {cceRequests 7}

cceRequestsUrlBlockedPercent OBJECT-TYPE
    SYNTAX          Integer32 (0..1000)
    UNITS           "percentage/10"
    MAX-ACCESS      read-only
    STATUS          current
    DESCRIPTION
        "Total number of times a client browser has attempted to
         access an administratively blocked URL via the cache engine."
    ::= {cceRequests 8}

cceRequestsIcpClientHits   OBJECT-TYPE
    SYNTAX          Counter64
    MAX-ACCESS      read-only
    STATUS          current
    DESCRIPTION
        "The number of times the cache engine was able to satisfy
         a client request by getting an ICP hit from some other
         cache."
    ::= {cceRequests 9}

cceRequestsIcpClientPercentage OBJECT-TYPE
    SYNTAX          Integer32 (0..1000)
    UNITS           "percentage/10"
    MAX-ACCESS      read-only
    STATUS          current
    DESCRIPTION
        "The percentage of total number of ICP client requests that were
         ICP hits."
    ::= {cceRequests 10}

cceRequestsIcpServerHits   OBJECT-TYPE
    SYNTAX          Counter64
    MAX-ACCESS      read-only
    STATUS          current
    DESCRIPTION
        "The number of times the cache engine was able to satisfy
         another cache's ICP requests by issuing ICP hits."
    ::= {cceRequests 11}

cceRequestsIcpServerPercentage OBJECT-TYPE
    SYNTAX          Integer32 (0..1000)
    UNITS           "percentage/10"
    MAX-ACCESS      read-only
    STATUS          current
    DESCRIPTION
        "The percentage of total number of ICP server requests that were
         ICP hits."
    ::= {cceRequests 12}

-- The following section describes the objects that are present
-- in the savings category of the statistics group

cceSavingsRequestsTotal    OBJECT-TYPE
    SYNTAX          Counter64
    MAX-ACCESS      read-only
    STATUS          current
    DESCRIPTION
        "Total number of end-user requests the cache engine has
         serviced."
    ::= {cceSavings 1}

cceSavingsRequestsHits    OBJECT-TYPE
    SYNTAX          Counter64
    MAX-ACCESS      read-only
    STATUS          current
    DESCRIPTION
        "Total number of end-user requests the cache engine has
         serviced as hits."
    ::= {cceSavings 2}

cceSavingsRequestsMiss    OBJECT-TYPE
    SYNTAX          Counter64
    MAX-ACCESS      read-only
    STATUS          current
    DESCRIPTION
        "The number of requests the cache engine retrieved from 
         the internet."
    ::= {cceSavings 3}

cceSavingsRequestsSavings    OBJECT-TYPE
    SYNTAX          Integer32 (0..1000)
    UNITS           "percentage/10"
    MAX-ACCESS      read-only
    STATUS          current
    DESCRIPTION
         "Percentage of hits out of the total."
    ::= {cceSavings 4}

cceSavingsBytesServedTotal    OBJECT-TYPE
    SYNTAX          Counter64
    MAX-ACCESS      read-only
    STATUS          current
    DESCRIPTION
        "Total number of bytes served."
    ::= {cceSavings 5}

cceSavingsBytesServedHits    OBJECT-TYPE
    SYNTAX          Counter64
    MAX-ACCESS      read-only
    STATUS          current
    DESCRIPTION
        "Total number of bytes the cache engine was able to 
         satisfy directly from its populated cache."
    ::= {cceSavings 6}

cceSavingsBytesServedMiss    OBJECT-TYPE
    SYNTAX          Counter64
    MAX-ACCESS      read-only
    STATUS          current
    DESCRIPTION
        "The number of bytes the cache engine retrieved 
         from the internet."
    ::= {cceSavings 7}

cceSavingsBytesServedSavings    OBJECT-TYPE
    SYNTAX          Integer32 (0..1000)
    UNITS           "percentage/10"
    MAX-ACCESS      read-only
    STATUS          current
    DESCRIPTION
         "Percentage of bytes served from the cache out of the total."
    ::= {cceSavings 8}

-- The following section describes the objects that are present
-- in the usage category of the statistics group

cceUsageCPUCurrent OBJECT-TYPE
    SYNTAX          Integer32 (0..100)
    UNITS           "percentage"
    MAX-ACCESS      read-only
    STATUS          current
    DESCRIPTION
        "Current CPU usage."
    ::= {cceUsage 1}

cceUsageCPUPeak      OBJECT-TYPE
    SYNTAX          Gauge32
    UNITS           "percentage"
    MAX-ACCESS      read-only
    STATUS          current
    DESCRIPTION
        "Peak CPU usage.  Calculated based on the amount of time the
         CPU is busy in the last 10 seconds."
    ::= {cceUsage 2}

cceUsageDiskCurrent OBJECT-TYPE
    SYNTAX          Integer32 (0..100)
    UNITS           "percentage"
    MAX-ACCESS      read-only
    STATUS          obsolete
    DESCRIPTION
        "This object is obsolete and will always return zero.
         It has been replaced by cceUsageDiskVolumeCurrent in 
         the CFS per-volume entry cceUsageDiskVolumeEntry in
         the table cceUsageDiskVolumeTable."
    ::= {cceUsage 3}

cceUsageDiskPeak    OBJECT-TYPE
    SYNTAX          Gauge32
    UNITS           "percentage"
    MAX-ACCESS      read-only
    STATUS          obsolete
    DESCRIPTION
        "This object is obsolete and will always return zero.
         It has been replaced by cceUsageDiskVolumePeak in 
         the CFS per-volume entry cceUsageDiskVolumeEntry in
         the table cceUsageDiskVolumeTable."
    ::= {cceUsage 4}

cceUsageNetCurrent OBJECT-TYPE
    SYNTAX          Integer32 (0..100)
    UNITS           "percentage"
    MAX-ACCESS      read-only
    STATUS          current
    DESCRIPTION
        "Current network interface card usage."
    ::= {cceUsage 5}

cceUsageNetPeak    OBJECT-TYPE
    SYNTAX          Gauge32
    UNITS           "percentage"
    MAX-ACCESS      read-only
    STATUS          current
    DESCRIPTION
        "Peak network interface card usage."
    ::= {cceUsage 6}

cceUsageConnsCurrent OBJECT-TYPE
    SYNTAX          Integer32
    MAX-ACCESS      read-only
    STATUS          current
    DESCRIPTION
        "Current connections usage."
    ::= {cceUsage 7}

cceUsageConnsPeak    OBJECT-TYPE
    SYNTAX          Gauge32
    MAX-ACCESS      read-only
    STATUS          current
    DESCRIPTION
        "Peak connections usage."
    ::= {cceUsage 8}

cceUsageDiskVolumeTable    OBJECT-TYPE
    SYNTAX         SEQUENCE OF CceUsageDiskVolumeEntry
    MAX-ACCESS     not-accessible
    STATUS         current
    DESCRIPTION
        "Disk volume usage table which contains information 
         for the Cache File System (CFS) volumes."
    ::= {cceUsage 9}

cceUsageDiskVolumeEntry    OBJECT-TYPE
    SYNTAX         CceUsageDiskVolumeEntry
    MAX-ACCESS     not-accessible
    STATUS         current
    DESCRIPTION
        "Utilization information for a CFS volume."
    INDEX          {cceUsageDiskVolumeEntryIndex}
    ::= {cceUsageDiskVolumeTable 1}

CceUsageDiskVolumeEntry ::= SEQUENCE {
    cceUsageDiskVolumeEntryIndex    Integer32,
    cceUsageDiskVolumeName      DisplayString,  
    cceUsageDiskVolumeEverMounted   TruthValue,
    cceUsageDiskVolumeCurrentlyMounted   TruthValue,
    cceUsageDiskVolumeUnmountReason   INTEGER,
    cceUsageDiskVolumeCurrent Integer32,
    cceUsageDiskVolumePeak Gauge32
}

cceUsageDiskVolumeEntryIndex   OBJECT-TYPE
    SYNTAX          Integer32 (1..16)
    MAX-ACCESS      not-accessible
    STATUS          current
    DESCRIPTION
        "Arbitrary index into the disk usage table."
    ::= {cceUsageDiskVolumeEntry 1}

cceUsageDiskVolumeName   OBJECT-TYPE
    SYNTAX          DisplayString
    MAX-ACCESS      read-only
    STATUS          current
    DESCRIPTION
        "Disk volume name."
    ::= {cceUsageDiskVolumeEntry 2}

cceUsageDiskVolumeEverMounted   OBJECT-TYPE
    SYNTAX          TruthValue
    MAX-ACCESS      read-only
    STATUS          current
    DESCRIPTION
        "If true (1), the CFS volume has been mounted at least once
         since system load.
         If false (2), the CFS volume has not been mounted since
         system load."
    ::= {cceUsageDiskVolumeEntry 3}

cceUsageDiskVolumeCurrentlyMounted   OBJECT-TYPE
    SYNTAX          TruthValue
    MAX-ACCESS      read-only
    STATUS          current
    DESCRIPTION
        "If true (1), the CFS volume is currently mounted.
         If false (2), The CFS volume is currently unmounted."
    ::= {cceUsageDiskVolumeEntry 4}

cceUsageDiskVolumeUnmountReason   OBJECT-TYPE
    SYNTAX         INTEGER  {
        notApplicable (0),
        normal        (1),
        error         (2)
    }         
    MAX-ACCESS      read-only
    STATUS          current
    DESCRIPTION
        "If cceUsageDiskVolumeEverMounted is false(2) or
         cceUsageDiskVolumeCurrentlyMounted is true(1),
         then this object is notApplicable(0).
         If cceUsageDiskVolumeEverMounted is true(1) and
         cceUsageDiskVolumeCurrentlyMounted is false(2),
         then this object the reason the CVS volume is not
         mounted.  If the reason is normal(1), then the volume
         was unmounted by the administrator issuing the
         cfs umount command.  If the reason is error(2), then 
         volume was unmounted by the Cache File System
         due to an error."
    ::= {cceUsageDiskVolumeEntry 5}

cceUsageDiskVolumeCurrent    OBJECT-TYPE
    SYNTAX          Integer32 (0..100)
    UNITS           "percentage"
    MAX-ACCESS      read-only
    STATUS          current
    DESCRIPTION
        "Current utilization of the cache engine's disk controller
         for this CFS volume."
    ::= {cceUsageDiskVolumeEntry 6}

cceUsageDiskVolumePeak    OBJECT-TYPE
    SYNTAX          Gauge32
    UNITS           "percentage"
    MAX-ACCESS      read-only
    STATUS          current
    DESCRIPTION
        "Peak utilization of the cache engine's disk controller
         for this CFS volume."
    ::= {cceUsageDiskVolumeEntry 7}

cceUsageDosfsVolumeTable    OBJECT-TYPE
    SYNTAX         SEQUENCE OF CceUsageDosfsVolumeEntry
    MAX-ACCESS     not-accessible
    STATUS         current
    DESCRIPTION
        "DOSFS volume usage table which contains information
         for the DOS File System (DOSFS) volumes."
    ::= {cceUsage 10}

cceUsageDosfsVolumeEntry    OBJECT-TYPE
    SYNTAX         CceUsageDosfsVolumeEntry
    MAX-ACCESS     not-accessible
    STATUS         current
    DESCRIPTION
        "Utilization information for a DOSFS volume."
    INDEX          {cceUsageDosfsVolumeEntryIndex}
    ::= {cceUsageDosfsVolumeTable 1}

CceUsageDosfsVolumeEntry ::= SEQUENCE {
    cceUsageDosfsVolumeEntryIndex    Integer32,
    cceUsageDosfsVolumeName          DisplayString,
    cceUsageDosfsVolumeState         Integer32,
    cceUsageDosfsVolumeFreeSpace     Gauge32,
    cceUsageDosfsVolumeTotalSpace    Gauge32
}

cceUsageDosfsVolumeEntryIndex   OBJECT-TYPE
    SYNTAX          Integer32 (1..16)
    MAX-ACCESS      not-accessible
    STATUS          current
    DESCRIPTION
        "Arbitrary index into the DOSFS volume table."
    ::= {cceUsageDosfsVolumeEntry 1}

cceUsageDosfsVolumeName   OBJECT-TYPE
    SYNTAX          DisplayString
    MAX-ACCESS      read-only
    STATUS          current
    DESCRIPTION
        "DOSFS volume name."
    ::= {cceUsageDosfsVolumeEntry 2}

cceUsageDosfsVolumeState   OBJECT-TYPE
    SYNTAX          Integer32 (0..7)
    MAX-ACCESS      read-only
    STATUS          current
    DESCRIPTION
        "State of the DOSFS volume .
         0 - DOSFS volume not accessed since ready change, 
         1 - DOSFS volume reset but not mounted,
         2 - DOSFS volume mounted,
         3 - DOSFS volume reset failed,
         4 - DOSFS volume mount failed,
         5 - DOSFS volume is being unmounted,
         6 - DOSFS volume has been unmounted,
         7 - Unmounts on DOSFS volume disabled." 
    ::= {cceUsageDosfsVolumeEntry 3}

cceUsageDosfsVolumeFreeSpace   OBJECT-TYPE 
    SYNTAX          Gauge32 
    UNITS           "Bytes"
    MAX-ACCESS      read-only
    STATUS          current
    DESCRIPTION
        "Amount of free space available on the DOSFS volume."
    ::= {cceUsageDosfsVolumeEntry 4}

cceUsageDosfsVolumeTotalSpace   OBJECT-TYPE
    SYNTAX          Gauge32
    UNITS           "Bytes" 
    MAX-ACCESS      read-only
    STATUS          current
    DESCRIPTION
        "The total space available on the DOSFS volume."
    ::= {cceUsageDosfsVolumeEntry 5}

-- The following section describes the objects that are present
-- in the Interfaces category of the Hardware group

cceIfFullDuplex         OBJECT-TYPE
    SYNTAX          TruthValue
    MAX-ACCESS      read-only
    STATUS          current
    DESCRIPTION
        "If true (1), Full Duplex.
         If false (2), Half Duplex."
    ::= {cceInterfaces 1}


    

-- Define traps here
ciscoCacheEngineMIBTrapPrefix
    OBJECT IDENTIFIER ::= {ciscoCacheEngineMIB 2}

ciscoCacheEngineMIBTraps 
    OBJECT IDENTIFIER ::= {ciscoCacheEngineMIBTrapPrefix 0}

cacheTrapReadDiskError    NOTIFICATION-TYPE
    STATUS    current
    DESCRIPTION
        "First read error occurred on the disk that is being accessed."
    ::= {ciscoCacheEngineMIBTraps 1} 

cacheTrapWriteDiskError    NOTIFICATION-TYPE
    STATUS    current
    DESCRIPTION
        "First write error occurred on the disk that is being accessed."
    ::= {ciscoCacheEngineMIBTraps 2} 

cacheTrapWriteTransFailed    NOTIFICATION-TYPE
    STATUS    current
    DESCRIPTION
        "Failed writing to working transaction log.  Possible causes
         are system errors or the log having been removed."
    ::= {ciscoCacheEngineMIBTraps 3} 

cacheTrapTooManyThreadsDead    NOTIFICATION-TYPE
    STATUS    current
    DESCRIPTION
        "Too many threads are dead.  This causes a reboot to happen."
    ::= {ciscoCacheEngineMIBTraps 4} 

cacheTrapWccpDisabled    NOTIFICATION-TYPE
    STATUS    current
    DESCRIPTION
        "WCCP (Web Cache Control Protocol) is enabled and then disabled
         due to blocked cache."
    ::= {ciscoCacheEngineMIBTraps 5} 

cacheTrapDiskVolUnmounted    NOTIFICATION-TYPE
    OBJECTS   { cceUsageDiskVolumeName }
    STATUS    current
    DESCRIPTION
        "A CFS disk volume has been unmounted due to an error condition.
         Any DOSFS volume on this disk has also been unmounted."
    ::= {ciscoCacheEngineMIBTraps 6} 

cacheTrapDosfsVolFull    NOTIFICATION-TYPE
    OBJECTS   { cceUsageDosfsVolumeName }
    STATUS    current
    DESCRIPTION
         "DOSFS Volume is full."
    ::= {ciscoCacheEngineMIBTraps 7}


-- conformance information
ciscoCacheEngineMIBConformance 
    OBJECT IDENTIFIER ::= {ciscoCacheEngineMIB 3}

ciscoCacheEngineMIBCompliances 
    OBJECT IDENTIFIER ::= {ciscoCacheEngineMIBConformance 1}

ciscoCacheEngineMIBGroups
    OBJECT IDENTIFIER ::= {ciscoCacheEngineMIBConformance 2}

-- compliance statements
ciscoCacheEngineMIBCompliance    MODULE-COMPLIANCE
    STATUS  current
    DESCRIPTION
        "The compliance statement for Cisco Systems entities which
         implement the cache engine model."
    MODULE  -- this module
    MANDATORY-GROUPS {
            cceFarmGroup,
            cceBasicGroup,
            cceDnsGroup,
            cceIcpClientGroup,
            cceIcpServerGroup,
            cceProxyGroup,
            cceTimeGroup,
            cceCacheFarmGroup,
            cceFreshGroup,
            cceTCPGroup,
            cceUrlGroup,
            cceEventsGroup,
            cceLogGroup,
            cceDiagDumpGroup,
            cceImsGroup,
            ccePerfGroup,
            cceReqGroup,
            cceSaveGroup,
            cceUsageGroup,
            cceInterfacesGroup
    }
    ::= {ciscoCacheEngineMIBCompliances 1}

-- units of conformance
cceFarmGroup     OBJECT-GROUP
    OBJECTS {
        cceFarmEntryIpAddress
    }
    STATUS current
    DESCRIPTION
        "Cache engine farm group."
    ::= {ciscoCacheEngineMIBGroups 1}

cceBasicGroup    OBJECT-GROUP
    OBJECTS {
        cceBasicIPAddress,
        cceBasicNetMask,
        cceBasicGatewayIpAddress,
        cceBasicCacheName,
        cceBasicFarmName        
    }
    STATUS current
    DESCRIPTION
        "Cache engine basic group."
    ::= {ciscoCacheEngineMIBGroups 2}

cceDnsGroup  OBJECT-GROUP
    OBJECTS {
        cceDnsDomain,
        cceDnsEntryIpAddress
    }
    STATUS current
    DESCRIPTION
        "Cache engine DNS group."
    ::= {ciscoCacheEngineMIBGroups 3}

cceIcpClientGroup  OBJECT-GROUP
    OBJECTS {
        cceIcpClientEnabled,
        cceIcpClientWait,
        cceIcpClientRetry,
        cceIcpClientLocalDomains,
        cceIcpClientRemServIpAddress,
        cceIcpClientRemServState,
        cceIcpClientRemServType,
        cceIcpClientRemServIcpPort,
        cceIcpClientRemServHttpPort,
        cceIcpClientRemServSelDomains
    }
    STATUS current
    DESCRIPTION
        "Cache engine ICP client group."
    ::= {ciscoCacheEngineMIBGroups 4}

cceIcpServerGroup  OBJECT-GROUP
    OBJECTS {
        cceIcpServerEnabled,
        cceIcpServerPort,
        cceIcpServerRemClntIPAddress,
        cceIcpServerRemClntFetch
    } 
    STATUS current
    DESCRIPTION
        "Cache engine ICP server group."
    ::= {ciscoCacheEngineMIBGroups 5}

cceProxyGroup  OBJECT-GROUP
    OBJECTS {
        cceProxyIncomingPort,
        cceProxyOutgoingAddress,
        cceProxyOutgoingPort
    }
    STATUS current
    DESCRIPTION
        "Cache engine proxy group."
    ::= {ciscoCacheEngineMIBGroups 6}

cceTimeGroup  OBJECT-GROUP
    OBJECTS {
        cceTimeGmtTime,
        cceTimeGmtDate,
        cceTimeEntryIpAddress
    }
    STATUS current
    DESCRIPTION
        "Cache engine Time group."
    ::= {ciscoCacheEngineMIBGroups 7}

cceCacheFarmGroup  OBJECT-GROUP
    OBJECTS {
        cceCacheFarmHealingModeWait,
        cceCacheFarmHealingModeRetry,
        cceCacheFarmVersion
    }
    STATUS current
    DESCRIPTION
        "Cache engine farm group."
    ::= {ciscoCacheEngineMIBGroups 8}

cceFreshGroup  OBJECT-GROUP
    OBJECTS {
        cceFreshnessTextAgeMultiplier,
        cceFreshnessBinaryAgeMultiplier,
        cceFreshnessTextMaximumTTL,
        cceFreshnessBinaryMaximumTTL,
        cceFreshnessUnitsMaximumTTL,
        cceFreshnessCacheCookies,
        cceFreshnessTextMaxAge,
        cceFreshnessBinaryMaxAge,
        cceFreshnessForceMiss
    }
    STATUS current
    DESCRIPTION
        "Cache engine fresh group."
    ::= {ciscoCacheEngineMIBGroups 9}

cceTCPGroup  OBJECT-GROUP
    OBJECTS {
        cceTcpServerSendBuffer,
        cceTcpClientSendBuffer,
        cceTcpServerRecvBuffer,
        cceTcpClientRecvBuffer,
        cceTcpServerReadWriteTimeout,
        cceTcpClientReadWriteTimeout,
        cceTcpConnectionIdleTimeout,
        cceTcpConnectionWaitTimeout,
        cceTcpConnectionRetry    
    }
    STATUS current
    DESCRIPTION
        "Cache engine TCP group."
    ::= {ciscoCacheEngineMIBGroups 10}

cceUrlGroup  OBJECT-GROUP
    OBJECTS {
        cceUrlFilterState
    }
    STATUS current
    DESCRIPTION
        "Cache engine URL group."
    ::= {ciscoCacheEngineMIBGroups 11}

cceEventsGroup  OBJECT-GROUP
    OBJECTS {
        cceEventsTotal,
        cceEventsCritical,
        cceEventsWarning,
        cceEventsNotice,
        cceEventsEntryType,
        cceEventsEntryMessage,
        cceEventsEntryTime        
    }
    STATUS current
    DESCRIPTION
        "Cache engine events group."
    ::= {ciscoCacheEngineMIBGroups 12}

cceLogGroup    OBJECT-GROUP
    OBJECTS {
        cceLoggingEnabled,
        cceLoggingInterval,
        cceLoggingWorkingLogPresent,
        cceLoggingSize,
        cceLoggingAge,
        cceLoggingArchiveLogPresent,
        cceLoggingArchiveLogSize,
        cceLoggingWriteFailReason 
    }
    STATUS current
    DESCRIPTION
        "Cache engine transaction log group."
    ::= {ciscoCacheEngineMIBGroups 13}

cceDiagDumpGroup  OBJECT-GROUP
    OBJECTS {
        cceDiagDumpDiskCreates,
        cceDiagDumpDiskOpens,
        cceDiagDumpDiskCloses,
        cceDiagDumpDiskDeletes,
        cceDiagDumpDiskReads,
        cceDiagDumpDiskWrites,
        cceDiagDumpDiskStats,
        cceDiagDumpDiskFree,
        cceDiagDumpDiskWraps,
        cceDiagDumpDiskOverWrites,
        cceDiagDumpDiskTruncReads,
        cceDiagDumpDiskInodeErrors,
        cceDiagDumpDiskCrcErrors,
        cceDiagDumpDiskDirCollisions,
        cceDiagDumpBufferReads,
        cceDiagDumpBufferReadErrors,
        cceDiagDumpBufferWrites,
        cceDiagDumpBufferWriteErrors,
        cceDiagDumpBufferHits,
        cceDiagDumpBufferMisses,
        cceDiagDumpBufferSeekErrors
    }
    STATUS current
    DESCRIPTION
        "Cache engine diagdump group."
    ::= {ciscoCacheEngineMIBGroups 14}
 
cceImsGroup  OBJECT-GROUP
    OBJECTS {
        cceImsClientRequestTotal,
        cceImsReceived,
        cceImsClientTotalFromCache,
        cceImsClientFreshFromCache,
        cceImsClientStaleFromCache,
        cceImsClientTotalCacheMiss,
        cceImsClientFreshCacheMiss,
        cceImsClientStaleCacheMiss,
        cceImsClientTotalReval,
        cceImsClientFreshReval,
        cceImsClientStaleReval,
        cceImsClientRequestToServer,
        cceImsServerTotalIssued,
        cceImsServerTotalDueClient,
        cceImsServerFreshDueClient,
        cceImsServerStaleDueClient,
        cceImsServerTotalDueExpiration,
        cceImsClientFreshDueExpiration,
        cceImsServerStaleDueExpiration
    }
    STATUS current
    DESCRIPTION
        "Cache engine IMS group."
    ::= {ciscoCacheEngineMIBGroups 15}

ccePerfGroup  OBJECT-GROUP
    OBJECTS {
        ccePerformanceReqPerSecMax,
        ccePerformanceReqPerSecLast,
        ccePerformanceBytesPerSecMax,
        ccePerformanceBytesPerSecLast,
        ccePerformanceSecPerReqAvg,
        ccePerformanceSecPerReqMin,
        ccePerformanceSecPerReqMax,
        ccePerformanceSecPerReqLast,
        ccePerformanceHitsSecPerReqAvg,
        ccePerformanceHitsSecPerReqMin,
        ccePerformanceHitsSecPerReqMax,
        ccePerformanceHitsSecPerReqLast,
        ccePerformanceMissSecPerReqAvg,
        ccePerformanceMissSecPerReqMin,
        ccePerformanceMissSecPerReqMax,
        ccePerformanceMissSecPerReqLast,
        ccePerformanceObjectSizeAvg,
        ccePerformanceObjectSizeMin,
        ccePerformanceObjectSizeMax,
        ccePerformanceObjectSizeLast
    }
    STATUS current
    DESCRIPTION
        "Cache engine performance group."
    ::= {ciscoCacheEngineMIBGroups 16}

cceReqGroup  OBJECT-GROUP
    OBJECTS {
        cceRequestsForcedReloadTotal,
        cceRequestsForcedReloadPercent,
        cceRequestsNearHitsTotal,
        cceRequestsNearHitsPercent,
        cceRequestsServerErrorTotal,
        cceRequestsServerErrorPercent,
        cceRequestsUrlBlockedTotal,
        cceRequestsUrlBlockedPercent,
        cceRequestsIcpClientHits,
        cceRequestsIcpClientPercentage,
        cceRequestsIcpServerHits,
        cceRequestsIcpServerPercentage
    }
    STATUS current
    DESCRIPTION
        "Cache engine request group."
    ::= {ciscoCacheEngineMIBGroups 17}

cceSaveGroup  OBJECT-GROUP
    OBJECTS {
        cceSavingsRequestsTotal,
        cceSavingsRequestsHits,
        cceSavingsRequestsMiss,
        cceSavingsRequestsSavings,
        cceSavingsBytesServedTotal,
        cceSavingsBytesServedHits,
        cceSavingsBytesServedMiss,
        cceSavingsBytesServedSavings
    }
    STATUS current
    DESCRIPTION
        "Cache engine savings group."
    ::= {ciscoCacheEngineMIBGroups 18}

cceUsageGroup  OBJECT-GROUP
    OBJECTS {
        cceUsageCPUCurrent,
        cceUsageCPUPeak,
        cceUsageDiskCurrent,
        cceUsageDiskPeak,
        cceUsageNetCurrent,
        cceUsageNetPeak,
        cceUsageConnsCurrent,
        cceUsageConnsPeak,
        cceUsageDiskVolumeName,
        cceUsageDiskVolumeEverMounted,
        cceUsageDiskVolumeCurrentlyMounted,
        cceUsageDiskVolumeUnmountReason,        
        cceUsageDiskVolumeCurrent,
        cceUsageDiskVolumePeak, 
        cceUsageDosfsVolumeName,
        cceUsageDosfsVolumeState,
        cceUsageDosfsVolumeFreeSpace,
        cceUsageDosfsVolumeTotalSpace 
  
    }
    STATUS current
    DESCRIPTION
        "Cache engine usage group."
    ::= {ciscoCacheEngineMIBGroups 19}

cceInterfacesGroup OBJECT-GROUP
    OBJECTS {
        cceIfFullDuplex
    }
    STATUS current
    DESCRIPTION
       "Cache engine Interfaces group."
    ::= {ciscoCacheEngineMIBGroups 20}

END
