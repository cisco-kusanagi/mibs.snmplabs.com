PERLE-IOLAN-SDS-MIB DEFINITIONS ::= BEGIN

  -- The private MIB module for the Perle IOLAN SDS, SCS and STS
  -- version 7.07.24 (year.month.day)
  

  IMPORTS
        OBJECT-GROUP
                FROM SNMPv2-CONF
        MODULE-IDENTITY, OBJECT-TYPE, enterprises,
        IpAddress, Counter32, Gauge32
                FROM SNMPv2-SMI
        TEXTUAL-CONVENTION, DisplayString, DateAndTime, RowStatus, MacAddress
                FROM SNMPv2-TC
        Ipv6Address, Ipv6IfIndexOrZero       
                FROM IPV6-TC;
                
  sds         MODULE-IDENTITY
    LAST-UPDATED "200707240000Z"
    ORGANIZATION "Perle Systems Limited"
    CONTACT-INFO 
            "Postal: Perle Systems Limited 
                     60 Renfrew Drive 
                     Markham, Ontario 
                     Canada 
                     L3R 0E1 
 
             http://www.perle.com/"
    DESCRIPTION
            "The private MIB module for the Perle IOLAN SDS, SCS and STS"
    REVISION    "200707240000Z"
        DESCRIPTION
             "Updated for 3.2G firmware release"
    REVISION    "200610240000Z"
        DESCRIPTION
             "Updated for 3.0G firmware release"
    REVISION    "200606210000Z"
        DESCRIPTION
             "Updated for 2.4G firmware release"
    REVISION    "200604230000Z"
        DESCRIPTION
             "Updated for 2.3G firmware release"
    REVISION    "200603170000Z"
        DESCRIPTION
             "Updated for 2.1G firmware release"
    REVISION    "200601090000Z"
        DESCRIPTION
             "Updated descriptions"
    REVISION    "200511100000Z"
        DESCRIPTION
             "Added support for: multiple Ethernet interfaces,
              1000 Mbps Ethernet, software serial port termination,
              and dedicated serial console port"
    REVISION    "200511090000Z"
        DESCRIPTION
             "Added support for single character interrupt feature.  Fixed
              syntactical errors and updated descriptions."             
    REVISION    "200506100000Z"
        DESCRIPTION
             "Added support for DCE serial interface and 2-port model"
    REVISION    "200506010000Z"
        DESCRIPTION
             "Added support for 28800 baud"
    REVISION    "200505040000Z"
        DESCRIPTION
             "Added SSL Configuration support"
    REVISION    "200501140000Z"
        DESCRIPTION
             "Initial Release"
    ::= { enterprises 1966 10 }
 
  perle          OBJECT IDENTIFIER  ::= { enterprises 1966 }
    
  adminInfo            OBJECT IDENTIFIER  ::= { sds 1 }

  serverInfo           OBJECT IDENTIFIER  ::= { sds 2 }

  hostsInfo            OBJECT IDENTIFIER  ::= { sds 3 }

  userInfo             OBJECT IDENTIFIER  ::= { sds 4 }

  portInfo             OBJECT IDENTIFIER  ::= { sds 5 }

  modemInfo            OBJECT IDENTIFIER  ::= { sds 6 }

  servicesInfo         OBJECT IDENTIFIER  ::= { sds 7 }

  trueportInfo         OBJECT IDENTIFIER  ::= { sds 8 }

  radiusInfo           OBJECT IDENTIFIER  ::= { sds 9 }

  kerberosInfo         OBJECT IDENTIFIER  ::= { sds 10 }

  ldapInfo             OBJECT IDENTIFIER  ::= { sds 11 }

  tacacsInfo           OBJECT IDENTIFIER  ::= { sds 12 }

  securidInfo          OBJECT IDENTIFIER  ::= { sds 13 }

  nisInfo              OBJECT IDENTIFIER  ::= { sds 14 }

  sshServerInfo        OBJECT IDENTIFIER  ::= { sds 15 }

  defUserInfo          OBJECT IDENTIFIER  ::= { sds 16 }

  snmpInfo             OBJECT IDENTIFIER  ::= { sds 17 }

  dnsInfo              OBJECT IDENTIFIER  ::= { sds 18 }

  winsInfo             OBJECT IDENTIFIER  ::= { sds 19 }

  gatewayInfo          OBJECT IDENTIFIER  ::= { sds 20 }

  syslogInfo           OBJECT IDENTIFIER  ::= { sds 21 }

  emailInfo            OBJECT IDENTIFIER  ::= { sds 22 }

  ripInfo              OBJECT IDENTIFIER  ::= { sds 23 }

  timeInfo             OBJECT IDENTIFIER  ::= { sds 24 }

  fileInfo             OBJECT IDENTIFIER  ::= { sds 25 }

  sntpStatsInfo        OBJECT IDENTIFIER  ::= { sds 27 }

  ripTableInfo         OBJECT IDENTIFIER  ::= { sds 28 }

  tcpConnStatsInfo     OBJECT IDENTIFIER  ::= { sds 29 }

  udpConnStatsInfo     OBJECT IDENTIFIER  ::= { sds 30 }

  ipv6StatsInfo        OBJECT IDENTIFIER  ::= { sds 31 }

  icmpv6StatsInfo      OBJECT IDENTIFIER  ::= { sds 32 }

  udpv6StatsInfo       OBJECT IDENTIFIER  ::= { sds 33 }

  tcpConnv6StatsInfo   OBJECT IDENTIFIER  ::= { sds 34 }

  udpConnv6StatsInfo   OBJECT IDENTIFIER  ::= { sds 35 }

  routev6Info          OBJECT IDENTIFIER  ::= { sds 36 }

  ripv6TableInfo       OBJECT IDENTIFIER  ::= { sds 37 }

  interfacev6Info      OBJECT IDENTIFIER  ::= { sds 38 }

  sslInfo              OBJECT IDENTIFIER  ::= { sds 39 }

  consoleInfo          OBJECT IDENTIFIER  ::= { sds 40 }
  
  ethStatsInfo         OBJECT IDENTIFIER  ::= { sds 41 }
  
  modbusgatewayInfo    OBJECT IDENTIFIER  ::= { sds 42 }
  
  modbusStatsInfo      OBJECT IDENTIFIER  ::= { sds 43 }
  
  customAppServerInfo  OBJECT IDENTIFIER  ::= { sds 44 }

  ioInfo               OBJECT IDENTIFIER ::=  { sds 45 }

clusteringInfo              OBJECT IDENTIFIER  ::= { sds 46 }
  
  dynamicDNSInfo              OBJECT IDENTIFIER  ::= { sds 47 }
  

pciInfo   OBJECT IDENTIFIER  ::= { sds 48 }

vmodemPhoneInfo OBJECT IDENTIFIER  ::= { sds 49 }

  YesNoValue ::= TEXTUAL-CONVENTION
      STATUS        current
      DESCRIPTION
              "Represents a YES or NO value."
      SYNTAX        INTEGER { no(1), yes(2) }

  OnOffValue ::= TEXTUAL-CONVENTION
      STATUS        current
      DESCRIPTION
              "Represents an ON or OFF value."
      SYNTAX        INTEGER { off(1), on(2) }

  Hex16 ::= TEXTUAL-CONVENTION
      DISPLAY-HINT  "2x"
      STATUS        current
      DESCRIPTION
              "Represents a two octet hex value."
      SYNTAX        OCTET STRING (SIZE(2))

  RadiusSessionId ::= TEXTUAL-CONVENTION
      DISPLAY-HINT  "1x:3x"
      STATUS        current
      DESCRIPTION
              "Represents a RADIUS session ID."
      SYNTAX        OCTET STRING (SIZE(4))

  Hex8 ::= TEXTUAL-CONVENTION
      DISPLAY-HINT  "1x"
      STATUS        current
      DESCRIPTION
              "Represents a one byte octet hex value."
      SYNTAX        OCTET STRING (SIZE(1))

  Hex32 ::= TEXTUAL-CONVENTION
      DISPLAY-HINT  "4x"
      STATUS        current
      DESCRIPTION
              "Represents a four octet hex value."
      SYNTAX        OCTET STRING (SIZE(4))

  TrueportBaud ::= TEXTUAL-CONVENTION
      STATUS        current
      DESCRIPTION
              "Represents TruePort baudrate mapping."
      SYNTAX      INTEGER {
          b50(1),
          b75(2),
          b110(3),
          b134(4),
          b150(5),
          b200(6),
          b300(7),
          b600(8),
          b1200(9),
          b1800(10),
          b2400(11),
          b4800(12),
          b9600(13),
          b19200(14),
          b38400(15),
          b57600(16),
          b115200(17),
          b230400(18),
          b28800(23),
          bCustom(24)
          }

  Date ::= TEXTUAL-CONVENTION
      STATUS       current
      DESCRIPTION
            "A date specification.In the format dd/mm/yyyy

            field   contents                  range
            -----   --------                  -----
              1       day                       1..31
              2       month                     1..12
              3       year*                     0..65536
            "
      SYNTAX       OCTET STRING (SIZE (8..10))

  Time ::= TEXTUAL-CONVENTION
      STATUS       current
      DESCRIPTION
            "A time specification. In the format hh:mm:ss

            field  contents                  range
            -----  --------                  -----
              1    hour                      0..23
              2    minutes                   0..59
              3    seconds                   0..59
            "
      SYNTAX       OCTET STRING (SIZE (5..8))

  Ipv4v6Address ::= TEXTUAL-CONVENTION
      DISPLAY-HINT "255a"
      STATUS       current
      DESCRIPTION
          "An IPV4 or IPV6 address"
      SYNTAX  OCTET STRING (SIZE (0..255))

  Ipv6InterfaceId ::= TEXTUAL-CONVENTION
      DISPLAY-HINT "255a"
      STATUS       current
      DESCRIPTION
          "An IPV6 Interface Identifier. The first 64 bits must be 0"
      SYNTAX OCTET STRING (SIZE (0..255))

  
  --  adminInfo group.

  adminFunction OBJECT-TYPE
      SYNTAX INTEGER {
        writeToFlash(1),
        resetToFactoryDefaults(2),
        reboot(3),
        resetSecurIDNodeSecret(4)
      }
      MAX-ACCESS read-write
      STATUS current
      DESCRIPTION
            "Perform a specific function on the Device Server
             If you want to save all the changes that have been
             submitted to the Device Server, you need to expand
             the adminInfo container folder and SET the adminFunction
             to 1 to write to FLASH. To make the configuration
             changes take effect, SET the adminFunction to 3 to
             reboot the Device Server."
      ::= {adminInfo 1 }

  adminLastFunction OBJECT-TYPE
      SYNTAX INTEGER {
        writeToFlash(1),
        resetToFactoryDefaults(2),
        reboot(3),
        resetSecurIDNodeSecret(4)
      }
      MAX-ACCESS read-only
      STATUS current
      DESCRIPTION
            "The last function requested"
      ::= {adminInfo 2 }

   adminStatus OBJECT-TYPE
      SYNTAX INTEGER {
        successful(1),
        error(2),
        inProgress(3)
      }
      MAX-ACCESS read-only
      STATUS current
      DESCRIPTION
            "The status of the last fuction performed."
      ::= {adminInfo 3 }

  adminSystemDate OBJECT-TYPE
      SYNTAX      Date
      MAX-ACCESS  read-write
      STATUS      current
      DESCRIPTION
              "The system date.
               Format dd/mm/yyyy"
      ::= { adminInfo 4 }

  adminSystemTime OBJECT-TYPE
      SYNTAX      Time
      MAX-ACCESS  read-write
      STATUS      current
      DESCRIPTION
              "The system time (local time).
               Format hh:mm:ss"
      ::= { adminInfo 5 }

  adminKillLine OBJECT-TYPE
      SYNTAX      INTEGER
      MAX-ACCESS  read-write
      STATUS      current
      DESCRIPTION
            "Enter the line number you want to reset"
      ::= { adminInfo 6 }
      
   adminGetPortNames OBJECT-TYPE
      SYNTAX      IpAddress
      MAX-ACCESS  read-write
      STATUS      current
      DESCRIPTION
              "The remote slave server's IP address from which you want to get
               its all ports' names."
      ::= { adminInfo 7}            

   adminPowerOn OBJECT-TYPE
      SYNTAX      DisplayString(SIZE(1..5))
      MAX-ACCESS  read-write
      STATUS      current
      DESCRIPTION
              "Turn on the power of the whole line(if the line is not a power
               management line) or a plug (the line is a power management line),
               and the input format is line#:plug#(1 based)."
      ::= { adminInfo 8}            

   adminPowerOff OBJECT-TYPE
      SYNTAX      DisplayString(SIZE(1..5))
      MAX-ACCESS  read-write
      STATUS      current
      DESCRIPTION
              "Turn off the power of the whole line(if the line is not a power
               management line) or a plug (the line is a power management line),
               and the input format is line#:plug#(1 based)."
      ::= { adminInfo 9}            
      
   adminPowerBoot OBJECT-TYPE
      SYNTAX      DisplayString(SIZE(1..5))
      MAX-ACCESS  read-write
      STATUS      current
      DESCRIPTION
              "Boot the whole line(if the line is not a power management line) or
               a plug (the line is a power management line), and the input format 
               is line#:plug#(1 based)."
      ::= { adminInfo 10}            
      
   adminPowerReset OBJECT-TYPE
      SYNTAX      INTEGER
      MAX-ACCESS  read-write
      STATUS      current
      DESCRIPTION
              "Reset whole line(only if the line is a power management line),
               and the input is the line number(1 based)."
      ::= { adminInfo 11}            
      
   adminPowerStatus OBJECT-TYPE
      SYNTAX      DisplayString(SIZE(1..5))
      MAX-ACCESS  read-write
      STATUS      current
      DESCRIPTION
              "Return the status of a plug (the line is a power management line),
               and the input format is line#:plug#(1 based)."
      ::= { adminInfo 12}            
      
  --  serverInfo group.

  serverStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { serverInfo 1 }

  serverName OBJECT-TYPE
      SYNTAX      DisplayString(SIZE(1..14))
      MAX-ACCESS  read-write
      STATUS      current
      DESCRIPTION
              "The name of the Device Server."
      ::= { serverInfo 2 }

  domainName OBJECT-TYPE
      SYNTAX      DisplayString(SIZE(0..32))
      MAX-ACCESS  read-write
      STATUS      current
      DESCRIPTION
              "The domain name of the Device Server."
      ::= { serverInfo 3 }

  serverIPaddress OBJECT-TYPE
      SYNTAX      IpAddress
      MAX-ACCESS  read-write
      STATUS      current
      DESCRIPTION
              "The Device Server's unique IPv4 network IP address.
               If you are using the Device Server in an IPv6 network,
               this field can be left blank."
      ::= { serverInfo 4 }

  serverSubnetBits OBJECT-TYPE
      SYNTAX      INTEGER(1..32)
      MAX-ACCESS  read-write
      STATUS      current
      DESCRIPTION
              "The number of bits in the subnet mask. For example,
               a subnet mask of 255.255.0.0 has 16 subnet/prefix bits.
               Valid values are 0-31. The default is 0. When the value
               is 0, the correct value is determined based on the class
               of the IP Address."
      ::= { serverInfo 5 }

  portBuffering OBJECT-TYPE
      SYNTAX      INTEGER {
               disabled(1),
               local(2),
               remote(3),
               both(4)
      }
      MAX-ACCESS  read-write
      STATUS      current
      DESCRIPTION
              "Specifies where the port buffer log is kept, either Off,
               Local, Remote, or Both. If Remote or Both is selected,
               you must specify an NFS server location for the port buffer log."
      ::= { serverInfo 6 }

  viewPortBufferString OBJECT-TYPE
      SYNTAX      DisplayString(SIZE(0..8))
      MAX-ACCESS  read-write
      STATUS      current
      DESCRIPTION
              "The string (up to 8 characters) used by a a session
               connected to a serial port to display the port buffer for
               that particular serial port. You can specify control
               (unprintable) codes by putting the decimal value in angle
               brackets < > (for example, Escape b is <027>b).
               The default is ~view."
      ::= { serverInfo 7 }

  timeStamping OBJECT-TYPE
      SYNTAX      OnOffValue
      MAX-ACCESS  read-write
      STATUS      current
      DESCRIPTION
              "Enable/disable time stamping of the port buffer data."
      ::= { serverInfo 8 }

  sessionEscapeString OBJECT-TYPE
      SYNTAX      DisplayString(SIZE(0..8))
      MAX-ACCESS  read-write
      STATUS      current
      DESCRIPTION
              "The key sequence to escape the current session and
              display the session options."
      ::= { serverInfo 9 }

  nfsHostName OBJECT-TYPE
      SYNTAX      DisplayString(SIZE(0..14))
      MAX-ACCESS  read-write
      STATUS      current
      DESCRIPTION
              "The NFS host that the Device Server will use for
               its Remote Port Buffering feature. The Device Server
               will open a file on the NFS host for each reverse SSH
               or reverse Telnet line, and send any port data to be
               written to those files. The default is None. This field
               is required when Mode is set to Remote or Both.
               The host name must be defined in the hosts table."
      ::= { serverInfo 10}

  nfsDirectory OBJECT-TYPE
      SYNTAX      DisplayString(SIZE(0..40))
      MAX-ACCESS  read-write
      STATUS      current
      DESCRIPTION
              "The directory and/or subdirectories where the Remote Port
               Buffering files will be created. This field is used when
               Port Buffering Mode is set to Remote or Both. For multiple
               Device Servers using the same NFS host, it is recommended
               that each Device Server have its own unique directory to
               house the remote port log files.
               The default is /device_server/portlogs."
      ::= { serverInfo 11 }

  nfsEncryption  OBJECT-TYPE
      SYNTAX      OnOffValue
      MAX-ACCESS  read-write
      STATUS      current
      DESCRIPTION
              "Determines if the data sent to the NFS host is sent encrypted
               or in the clear across the LAN. The default is set of Off.
               NOTE: When NFS encryption is enabled, the Decoder utility
               software is required to be installed on the NFS host for
               decrypting the data to a readable format."
      ::= { serverInfo 12 }


  portMenuString OBJECT-TYPE
      SYNTAX      DisplayString(SIZE(0..8))
      MAX-ACCESS  read-write
      STATUS      current
      DESCRIPTION
              "The string (up to 8 characters) used by a a session connected
               to a serial port to display the port buffer for that particular
               serial port. You can specify control (unprintable) codes by
               putting the decimal value in angle brackets < > (for example,
               Escape b is <027>b). The default is ~view."
      ::= { serverInfo 13 }


  

  breakEnabled OBJECT-TYPE
      SYNTAX      OnOffValue
      MAX-ACCESS  read-write
      STATUS      current
      DESCRIPTION
              "Enable or disable the ability to generate a break signal on a
               serial port."
      ::= { serverInfo 15 }


  banner OBJECT-TYPE
      SYNTAX      OnOffValue
      MAX-ACCESS  read-write
      STATUS      current
      DESCRIPTION
              "If enabled, displays a product identification banner before
               login prompts. Default is off."
      ::= { serverInfo 16 }

  security OBJECT-TYPE
      SYNTAX      OnOffValue
      MAX-ACCESS  read-write
      STATUS      current
      DESCRIPTION
              "If enabled, the server will only respond to, and allow access
               to and from, the IP addresses of hosts configured in the hosts
               table."
      ::= { serverInfo 17 }

  promptWithName OBJECT-TYPE
      SYNTAX      OnOffValue
      MAX-ACCESS  read-write
      STATUS      current
      DESCRIPTION
              "If enabled, the Device Server name will be included in login prompts,
               command line prompts, etc."
      ::= { serverInfo 18 }

  passwordLimit OBJECT-TYPE
      SYNTAX      INTEGER(0..10)
      MAX-ACCESS  read-write
      STATUS      current
      DESCRIPTION
              "The number of attempts a user is allowed to enter a password
               for a port. If this limit is exceeded, the port is disabled
               for 5 minutes. A user with Admin level rights can restart the
               port, bypassing the timeout, by issuing a kill on the disabled
               port. The default value is 3."
      ::= { serverInfo 19 }

  oemLogin OBJECT-TYPE
      SYNTAX      OnOffValue
      MAX-ACCESS  read-write
      STATUS      current
      DESCRIPTION
              "When set, and a custom language file is in use,
               the login prompt will use the string defined in the
               language file as the login prompt instead of the default prompt, login:."
      ::= { serverInfo 20 }

  bypassPassword OBJECT-TYPE
      SYNTAX      OnOffValue
      MAX-ACCESS  read-write
      STATUS      current
      DESCRIPTION
              "When set, authorised users who do not have a password set,
               with the exception of the Admin user, WILL NOT be prompted
               for a password at login with Local Authentication."
      ::= { serverInfo 21}

  singleTelnet OBJECT-TYPE
      SYNTAX      OnOffValue
      MAX-ACCESS  read-write
      STATUS      current
      DESCRIPTION
              "Sets all reverse connections to a one connection at a time mode.
               Server-side applications will get a (socket) connection refused until:
               All data from previous connections on that serial port has drained,
               There are no other connections,
               Up to a 1 second interconnection poll timer has expired
               This also enables a per-connection keepalive TCP keepalive feature.
               After approximately 3 minutes of network connection idle time, the
               connection will send a gratuitous ACK to the network peer, thus
               either ensuring the connection stays active OR causing a dropped
               connection condition to be recognised by the reverse service
               (all connections)."
      ::= { serverInfo 22 }

  flushOnClose OBJECT-TYPE
      SYNTAX      OnOffValue
      MAX-ACCESS  read-write
      STATUS      current
      DESCRIPTION
              "When enabled, deletes any pending data when a port is closed;
               as opposed to maintaining the port to send pending data.
               Default is Off."
      ::= { serverInfo 23 }

  primaryAuthMethod OBJECT-TYPE
      SYNTAX      INTEGER {
                    local(1),
                    radius(2),
                    kerberos(3),
                    ldap(4),
                tacacs(5),
            securid(6),
            nis(7)
      }
      MAX-ACCESS  read-write
      STATUS      current
      DESCRIPTION
              "The first authentication method that the Device Server attempts.
               Some type of authentication must be done by the Device Server."
      ::= { serverInfo 24 }

  secondaryAuthMethod OBJECT-TYPE
      SYNTAX      INTEGER {
              none(1),
                  local(2),
                  radius(3),
                  kerberos(4),
                  ldap(5),
              tacacs(6),
          securid(7),
          nis(8)
      }
      MAX-ACCESS  read-write
      STATUS      current
      DESCRIPTION
              "If the Primary Authentication Method fails, the next
               authentication method that the Device Server attempts. You
               can choose to use authentication methods in combination.
               For example, you can specify the Primary Authentication
               Method as Local and the Secondary Authentication Method as
               RADIUS. Therefore, some users can be defined in the Device
               Server (Local) others in RADIUS."
      ::= { serverInfo 25 }

  ethernetSpeedDuplex OBJECT-TYPE
      SYNTAX      INTEGER {
             speedAuto(1),
             speed10Half(2),
             speed10Full(3),
             speed100Half(4),
             speed100Full(5),
             speed1000Half(6),
             speed1000Full(7)
        }
      MAX-ACCESS  read-write
      STATUS      current
      DESCRIPTION
              "Define the ethernet connection speed at one of the following:
               auto-automatically detects the ethernet interface speed and duplex
               10 Mbps Half Duplex
               10 Mbps Full Duplex
               100 Mbps Half Duplex
               100 Mbps Full Duplex
               1000 Mbps Half Duplex
               1000 Mbps Full Duplex"
      ::= { serverInfo 26 }

  tftpRetry OBJECT-TYPE
      SYNTAX      INTEGER(0..5)
      MAX-ACCESS  read-write
      STATUS      current
      DESCRIPTION
              "The number of times the Device Server will attempt to
               transfer (using TFTP) a file to/from a host. Default is 5.
               A value of 0 (zero) means that the Device Server will not
               attempt a retry should TFTP fail."
      ::= { serverInfo 27 }

  tftpTimeOut OBJECT-TYPE
      SYNTAX      INTEGER (3..10)
      MAX-ACCESS  read-write
      STATUS      current
      DESCRIPTION
              "The time, in seconds, that the Device Server will wait for
               a successful transmit or receipt of TFTP packets before retrying
               a TFTP transfer. Default is 3 seconds."
      ::= { serverInfo 28 }

  enableGuestLogin OBJECT-TYPE
      SYNTAX      OnOffValue
      MAX-ACCESS  read-write
      STATUS      current
      DESCRIPTION
              "Allow users who are not defined in the User database to log 
               into the Device Server with any user ID and the specified password.
               Guest users inherit their settings from the Default User's 
               configuration."
      ::= { serverInfo 29 }
      
  serverSecondaryIPaddress OBJECT-TYPE
      SYNTAX      IpAddress
      MAX-ACCESS  read-write
      STATUS      current
      DESCRIPTION
              "The Device Server's eth2 IPv4 network IP address.
               If you are using the Device Server in an IPv6 network,
               this field can be left blank."
      ::= { serverInfo 30 }

  serverSecondarySubnetBits OBJECT-TYPE
      SYNTAX      INTEGER(1..32)
      MAX-ACCESS  read-write
      STATUS      current
      DESCRIPTION
              "The number of bits in the eth2 subnet mask. For example,
               a subnet mask of 255.255.0.0 has 16 subnet/prefix bits.
               Valid values are 0-31. The default is 0. When the value
               is 0, the correct value is determined based on the class
               of the IP Address."
      ::= { serverInfo 31 }
   ethernetSecondarySpeedDuplex OBJECT-TYPE
      SYNTAX      INTEGER {
             speedAuto(1),
             speed10Half(2),
             speed10Full(3),
             speed100Half(4),
             speed100Full(5),
             speed1000Half(6),
             speed1000Full(7)
        }    
      MAX-ACCESS  read-write
      STATUS      current
      DESCRIPTION
              "Define the ethernet connection speed at one of the following:
               auto-automatically detects the ethernet interface speed and duplex
               10 Mbps Half Duplex
               10 Mbps Full Duplex
               100 Mbps Half Duplex
               100 Mbps Full Duplex
               1000 Mbps Half Duplex
               1000 Mbps Full Duplex
               
               Note: 1000 Mbps is not supported on certain models"
      ::= { serverInfo 32 }      

  dhcpUpdateDNSPrimary OBJECT-TYPE
      SYNTAX      OnOffValue
      MAX-ACCESS  read-write
      STATUS      current
      DESCRIPTION
              "If enabled, the DNS server will be updated after the device server gets the
               ip address via DHCP."
      ::= { serverInfo 33 }

  powerManagementMenuString OBJECT-TYPE
      SYNTAX      DisplayString(SIZE(0..8))
      MAX-ACCESS  read-write
      STATUS      current
      DESCRIPTION
              "Menu String for power management ."
      ::= { serverInfo 34 }
      
  activeStandbyEnabled OBJECT-TYPE
      SYNTAX      OnOffValue
      MAX-ACCESS  read-write
      STATUS      current
      DESCRIPTION
              "Enable/disable active standby."
      ::= { serverInfo 35}
      
  activeStandbyMiimon OBJECT-TYPE
      SYNTAX      INTEGER (0..9999)
      MAX-ACCESS  read-write
      STATUS      current
      DESCRIPTION
              "Time in msec for frequency in MII link monitoring."
      ::= { serverInfo 36}

  activeStandbyUpdelay OBJECT-TYPE
      SYNTAX      INTEGER (0..9999)
      MAX-ACCESS  read-write
      STATUS      current
      DESCRIPTION
              "Delay in enabling a link after the 'link up' status has been detected"
      ::= { serverInfo 37}
      
  dropSessionDetectionTime OBJECT-TYPE
      SYNTAX      INTEGER (1..32767)
      MAX-ACCESS  read-write
      STATUS      current
      DESCRIPTION
              "Dropped session detection time"
      ::= { serverInfo 38}    
      
  autoObtainDNS OBJECT-TYPE
      SYNTAX      OnOffValue
      MAX-ACCESS  read-write
      STATUS      current
      DESCRIPTION
              "If enabled, the DNS server ip address will be get automatically via DHCP."
      ::= { serverInfo 39 }
      
  autoObtainWINS OBJECT-TYPE
      SYNTAX      OnOffValue
      MAX-ACCESS  read-write
      STATUS      current
      DESCRIPTION
              "If enabled, the WINS server ip address will be get automatically via DHCP."
      ::= { serverInfo 40 }     

  autoObtainGW OBJECT-TYPE
      SYNTAX      OnOffValue
      MAX-ACCESS  read-write
      STATUS      current
      DESCRIPTION
              "If enabled, the default gateway ip address will be get automatically via DHCP."
      ::= { serverInfo 41 }
      
  alwaysAttemptSecond OBJECT-TYPE
      SYNTAX      OnOffValue
      MAX-ACCESS  read-write
      STATUS      current
      DESCRIPTION
              "If enabled, the secondary authentication method will always be used."
      ::= { serverInfo 42 }     
      
  dhcpUpdateDNSSecondary OBJECT-TYPE
      SYNTAX      OnOffValue
      MAX-ACCESS  read-write
      STATUS      current
      DESCRIPTION
              "If enabled, the DNS server will be updated for the secondary ethernet interface 
               after the device server gets the ip address via DHCP."
      ::= { serverInfo 43 }
      
 domainPrefixPrimary OBJECT-TYPE
      SYNTAX      DisplayString(SIZE(0..7))
      MAX-ACCESS  read-write
      STATUS      current
      DESCRIPTION
              "The domain prefix for primary ethernet interface of the Device Server."
      ::= { serverInfo 44 } 
      
 domainPrefixSecondary OBJECT-TYPE
      SYNTAX      DisplayString(SIZE(0..7))
      MAX-ACCESS  read-write
      STATUS      current
      DESCRIPTION
              "The domain prefix for secondary ethernet interface of the Device Server."
      ::= { serverInfo 45 }      
      
      
  --  hostsInfo group. A table of entries, each entry per IP host.

  hostsInfoTable OBJECT-TYPE
      SYNTAX      SEQUENCE OF HostsInfoEntry
      MAX-ACCESS  not-accessible
      STATUS      current
      DESCRIPTION
              "The hosts info table."
      ::= { hostsInfo 1 }

  hostsInfoEntry OBJECT-TYPE
      SYNTAX      HostsInfoEntry
      MAX-ACCESS  not-accessible
      STATUS      current
      DESCRIPTION
              "An entry in the hostsInfoTable, each relating to a host."
      INDEX   { hostIndex }
      ::= { hostsInfoTable 1 }

  HostsInfoEntry ::=
      SEQUENCE {
        hostIndex
              INTEGER,
        hostStatus
            RowStatus,
        hostName
              DisplayString,
        hostIpAddr
              Ipv4v6Address,
        fqdn
              DisplayString
      }

  hostIndex OBJECT-TYPE
      SYNTAX      INTEGER
      MAX-ACCESS  not-accessible
      STATUS      current
      DESCRIPTION
              "The table entry number for this host."
      ::= { hostsInfoEntry 1 }

   hostStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { hostsInfoEntry 2 }

  hostName OBJECT-TYPE
      SYNTAX      DisplayString(SIZE(0..14))
      MAX-ACCESS  read-write
      STATUS      current
      DESCRIPTION
              "The host name used for this host entry.
           To delete an entry, blank out this field.
               If blank, this entry is currently unused."
      ::= { hostsInfoEntry 3 }

  hostIpAddr OBJECT-TYPE
      SYNTAX      Ipv4v6Address
      MAX-ACCESS  read-write
      STATUS      current
      DESCRIPTION
              "The host IP address used for this entry."
      ::= { hostsInfoEntry 4 }

   fqdn OBJECT-TYPE
      SYNTAX      DisplayString(SIZE(0..255))
      MAX-ACCESS  read-write
      STATUS      current
      DESCRIPTION
              "The host full qualified domain name for the host entry.
               If blank, this entry is currently unused."
      ::= { hostsInfoEntry 5 }

--  userInfo group. A table of entries, each entry per user.

  userTable OBJECT-TYPE
      SYNTAX      SEQUENCE OF UserEntry
      MAX-ACCESS  not-accessible
      STATUS      current
      DESCRIPTION
              "The user table."
      ::= { userInfo 1 }

  userEntry OBJECT-TYPE
      SYNTAX      UserEntry
      MAX-ACCESS  not-accessible
      STATUS      current
      DESCRIPTION
              "An entry in the userEntry, each relating to a user."
      INDEX   { userIndex }
      ::= { userTable 1 }

  UserEntry ::=
      SEQUENCE {
        userIndex
              INTEGER,
        userStatus
            RowStatus,
        userName
              DisplayString,
        userService
              INTEGER,
        userLanguage
            INTEGER,
        userLevel
            INTEGER,
        userHotKeyPrefix
            Hex8,
        userPhoneNumber
            DisplayString,
        userCallBack
            OnOffValue,
        userIdleTimer
            INTEGER,
        userSessionTimer
            INTEGER,
        userIpHost
            Ipv4v6Address,
        userTelnetPort
            INTEGER,
        userSSHPort
            INTEGER,
        userTcpPort
            INTEGER,
        userFramedIp
            IpAddress,
        userSubnetBits
            INTEGER,
        userIpv6InterfaceIdentifier
            Ipv6InterfaceId,
        userFramedMtu
            INTEGER,
        userFramedCompression
            OnOffValue,
        userRouting
            INTEGER,
        userPortConnected
            INTEGER,
        userSessionTime
            INTEGER,
        userIdleTime
            INTEGER
            }

  userIndex OBJECT-TYPE
      SYNTAX      INTEGER
      MAX-ACCESS  not-accessible
      STATUS      current
      DESCRIPTION
              "The table entry number for this user."
      ::= { userEntry 1 }

   userStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { userEntry 2}

  userName OBJECT-TYPE
      SYNTAX      DisplayString(SIZE(0..16))
      MAX-ACCESS  read-write
      STATUS      current
      DESCRIPTION
              "The user name.
               To delete a user, set this field to blank.
               If blank, this entry is currently unused."
      ::= { userEntry 3 }

  userService OBJECT-TYPE
      SYNTAX      INTEGER {
        dsprompt(1),
        telnet(2),
        ssh(3),
        rlogin(4),
        slip(5),
        ppp(6),
        tcpclear(7),
        sslraw(8)
      }
      MAX-ACCESS  read-write
      STATUS      current
      DESCRIPTION
              "The type of service that the user will use:
               dsprompt, telnet, ssh, rlogin, slip, ppp, tcpclear
               or sslraw."
      ::= { userEntry 4 }

   userLanguage OBJECT-TYPE
      SYNTAX      INTEGER {
        english(1),
        custom(2)
      }
      MAX-ACCESS  read-write
      STATUS      current
      DESCRIPTION
              "Sets the language the user will view all Menu, CLI,
               and WebManager strings."
      ::= { userEntry 5 }

   userLevel OBJECT-TYPE
      SYNTAX      INTEGER {
        admin(1),
        normal(2),
        restricted(3),
        menu(4)
      }
      MAX-ACCESS  read-write
      STATUS      current
      DESCRIPTION
              "Admin-Total access to the Device Server. More than one admin user
               account can exist, but we recommend that you only have one.
               Normal-Limited access to the Device Server. Limited CLI commands
               and Menu access, can configure the user's own configuration settings.
               Restricted-Can only access predefined sessions or access the
               Easy Port Access menu. Can only view or monitor the Device Server
               using CLI commands to display information about the Device Server.
               Menu-Only access predefined sessions or access the Easy Port Access
               menu. The Easy Port Access allows the user to connect to the
               accessible line without disconnecting their initial connection to the
               Device Server. Does not have any access to CLI commands."
      ::= { userEntry 6}

   userHotKeyPrefix OBJECT-TYPE
      SYNTAX      Hex8
      MAX-ACCESS  read-write
      STATUS      current
      DESCRIPTION
              "The prefix that a user types to control the current session. The
               default value is hex 01, which corresponds to Ctrl-a (^a):
               ^a number-Switches from one session to another, press ^a and then
               the required session number. For example, ^a 2 would switch you to
               session 2. Pressing ^a 0 will return you to the Device Server Menu.
               ^a n-Display the next session. The current session will remain active.
               ^a p-Display the previous session. The current session will remain active.
               ^a m-To exit a session and return to the Device Server. You will be
               returned to where you left off. The session will be left running.
               ^a l-(Lowercase L) Locks the line until the user unlocks it. The user
               is prompted for a password and locks the line. Next, the user must
               retype the password to unlock the line.
               ^r-Redraws the screen."
      ::= { userEntry 7}

   userPhoneNumber OBJECT-TYPE
      SYNTAX      DisplayString(SIZE(0..32))
      MAX-ACCESS  read-write
      STATUS      current
      DESCRIPTION
              "The phone number the Device Server will dial to callback the user
               (you must have set Callback to On). Enter the number without spaces."
      ::= { userEntry 8}

   userCallBack OBJECT-TYPE
      SYNTAX      OnOffValue
      MAX-ACCESS  read-write
      STATUS      current
      DESCRIPTION
              "When On, enter a phone number for the Device Server to call the user
               back (the Callback parameter is unrelated to the Line Dial parameter).
               Note: the Device Server will allow callback only when a user is
               authenticated. If the protocol over the link does not provide
               authentication, there will be no callback. Therefore, when the Line
               Service is set to PPP, you must use either PAP or CHAP, because these
               protocols provide authentication. The default is Off. The Device Server
               supports another type of callback, Roaming Callback, which is
               configurable when the Line Service is set to PPP."
      ::= { userEntry 9}

   userIdleTimer OBJECT-TYPE
      SYNTAX      INTEGER (0..4294967)
      MAX-ACCESS  read-write
      STATUS      current
      DESCRIPTION
              "The amount of time, in seconds, that the Idle Timer will run. Use
               this timer to close a connection because of inactivity. When the
               Idle Timer expires, because there has been no exchange of data within
               the specified time, the Device Server will close the connection. The
               default is 0 (zero), meaning that the Idle Timer will not expire
               (the connection is open permanently)."
      ::= { userEntry 10}

   userSessionTimer OBJECT-TYPE
      SYNTAX      INTEGER (0..4294967)
      MAX-ACCESS  read-write
      STATUS      current
      DESCRIPTION
              "The amount of time, in seconds, that the Session Timer will run. Use
               this timer to forcibly close a user's session (connection). When the
               Session Timer expires, the Device Server will end the connection. The
               default is 0 (zero), meaning that the session timer will not expire
               (the session is open permanently, or until the user logs out)."
      ::= { userEntry 11}

   userIpHost OBJECT-TYPE
      SYNTAX      Ipv4v6Address
      MAX-ACCESS  read-write
      STATUS      current
      DESCRIPTION
              "When the User Service is set to Telnet, TCP_clear or SSL_RAW, the target
               host IP address. If 255.255.255.255 is specified in the configuration,
               the user will be prompted for an IP address or hostname. If no IP
               address is specified, the Host IP value in the Default User configuration
               will be used. The default is 0.0.0.0."
      ::= { userEntry 12}

   userTelnetPort OBJECT-TYPE
      SYNTAX      INTEGER (0..65535)
      MAX-ACCESS  read-write
      STATUS      current
      DESCRIPTION
              "The port number for the Telnet session."
      ::= { userEntry 13}

   userSSHPort OBJECT-TYPE
      SYNTAX      INTEGER(0..65535)
      MAX-ACCESS  read-write
      STATUS      current
      DESCRIPTION
              "The port number for the SSH session."
      ::= { userEntry 14}

   userTcpPort OBJECT-TYPE
      SYNTAX      INTEGER(0..65535)
      MAX-ACCESS  read-write
      STATUS      current
      DESCRIPTION
              "The port number for the TCP-Clear or SSL-Raw session."
      ::= { userEntry 15}

   userFramedIp OBJECT-TYPE
      SYNTAX      IpAddress
      MAX-ACCESS  read-write
      STATUS      current
      DESCRIPTION
              "Used for User Service PPP or SLIP, sets the IP address of the
               remote user. Enter the address in dot decimal notation as follows:
               255.255.255.254 (default)-The Device Server will use the Remote
                  IP Address set in the PPP settings for the line.
               255.255.255.255-When the User Service is PPP, the Device Server will
                  allow the remote machine to specify its IP address (overriding
                  the IP address negotiation value configured in the PPP settings).
               255.255.255.255-When the User Service is SLIP, the Device Server will
                  use the Remote IP Address set for the line (no negotiation).
               n.n.n.n-(where n is a number) Enter the IP address of your choice.
                  This IP address will then be used in preference to the Remote IP
                  Address set for a line."
      ::= { userEntry 16}

   userSubnetBits OBJECT-TYPE
      SYNTAX      INTEGER (0..32)
      MAX-ACCESS  read-write
      STATUS      current
      DESCRIPTION
              "(IPV4 only) If the remote user is on a subnet, enter the number of
               bits in the subnet mask. For example, a subnet mask of 255.255.0.0
               has 16 subnet/prefix bits."
      ::= { userEntry 17}

   userIpv6InterfaceIdentifier OBJECT-TYPE
      SYNTAX      Ipv6InterfaceId
      MAX-ACCESS  read-write
      STATUS      current
      DESCRIPTION
              "Used for User Service PPP, sets the IP address of the remote user.
               Enter the address in IPv6 format. The first 64 bits of the Interface
               Identifier must be zero, therefore, ::abcd:abcd:abcd:abcd is the
               expected format."
      ::= { userEntry 18}

   userFramedMtu OBJECT-TYPE
      SYNTAX      INTEGER (64..1500)
      MAX-ACCESS  read-write
      STATUS      current
      DESCRIPTION
              "Used for User Service PPP or SLIP, specifies the maximum size of
               packets, in bytes, being transferred across the link. On noisy
               links it might be preferable to fragment large packets being
               transferred over the link, since there will be quicker recovery
               from errors. Depending on whether you have selected a User Service
               of SLIP or PPP, details are as follows:
               PPP-Framed MTU will be the maximum size of packets that the Device
                  Server port will accept. This value is negotiated between the
                  two ends of the link. The valid range is 64-1500. The default
                  is 1500 bytes.
               SLIP-Framed MTU will be the maximum size of packets being sent by
                  the Device Server. The Device Server will send SLIP packets in
                  the range 256-1006 bytes. The default value is 256 bytes.
               The Framed MTU value will be used in preference to the MTU/MRU values
               set for a Line."
      ::= { userEntry 19}

   userFramedCompression OBJECT-TYPE
      SYNTAX      OnOffValue
      MAX-ACCESS  read-write
      STATUS      current
      DESCRIPTION
              "Used for User Service PPP or SLIP, determines whether Van Jacobsen
               Compression is used on the link. VJ compression is a means of reducing
               the standard TCP/IP header from 40 octets to approximately 5 octets.
               This gives a significant performance improvement, particularly when
               interactive applications are being used. For example, when the user is
               typing, a single character can be passed over the link with a 40 octet
               header attached. VJ Compression has little effect on other types of links,
               such as ftp, where the packets are much larger. The Framed Compression
               value will be used in preference to the VJ Compression value set for a
               Line. The default is Off."
      ::= { userEntry 20}

   userRouting OBJECT-TYPE
      SYNTAX      INTEGER {
        none(1),
        send(2),
        listen(3),
        sendAndListen(4)
      }
      MAX-ACCESS  read-write
      STATUS      current
      DESCRIPTION
              "Determines the routing mode used for RIP packets on the PPP and SLIP
               interfaces. Values are:
               None-RIP packets are neither received nor sent by the Device Server.
               Send-RIP packets can only be sent by the Device Server.
               Listen-RIP packets can only be received by the Device Server.
               Send and Listen-RIP packets are sent and received by the Device Server."
      ::= { userEntry 21}

    
    
    userPortConnected OBJECT-TYPE
      SYNTAX INTEGER
      MAX-ACCESS  read-only
      STATUS      current
      DESCRIPTION
              "Port user is currently connected to. -1 if user not connected"
      ::= { userEntry 22}

    userSessionTime OBJECT-TYPE
      SYNTAX INTEGER
      MAX-ACCESS  read-only
      STATUS      current
      DESCRIPTION
              "Current User session time."
      ::= { userEntry 23}

    userIdleTime OBJECT-TYPE
      SYNTAX INTEGER
      MAX-ACCESS  read-only
      STATUS      current
      DESCRIPTION
              "Current Idle time"
      ::= { userEntry 24}



-- Port Access Table

  portAccessTable OBJECT-TYPE
      SYNTAX      SEQUENCE OF PortAccessEntry
      MAX-ACCESS  not-accessible
      STATUS      current
      DESCRIPTION
              "The port access info table for user."
      ::= { userEntry 25 }

  portAccessEntry OBJECT-TYPE
      SYNTAX      PortAccessEntry
      MAX-ACCESS  not-accessible
      STATUS      current
      DESCRIPTION
              "An entry in the portAccessTable, each relating to a user's
               access privileges for a serial port."
      INDEX   { portAccessUserIndex, portAccessPortIndex }
      ::= { portAccessTable 1 }

  PortAccessEntry ::=
      SEQUENCE {
        portAccessUserIndex
              INTEGER,
        portAccessPortIndex
              INTEGER,
        portAccessStatus
              RowStatus,
        portRWAccessAllowed
              YesNoValue,
        portRIAccessAllowed
              YesNoValue,
        portROAccessAllowed
              YesNoValue
      }

  portAccessUserIndex OBJECT-TYPE
      SYNTAX      INTEGER
      MAX-ACCESS  not-accessible
      STATUS      current
      DESCRIPTION
              "The index for the user entry that port access applies to."
      ::= { portAccessEntry 1 }

  portAccessPortIndex OBJECT-TYPE
      SYNTAX      INTEGER
      MAX-ACCESS  not-accessible
      STATUS      current
      DESCRIPTION
              "The port number that user access applies to."
      ::= { portAccessEntry 2 }

   portAccessStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portAccessEntry 3 }

  portRWAccessAllowed OBJECT-TYPE
      SYNTAX      YesNoValue
      MAX-ACCESS  read-write
      STATUS      current
      DESCRIPTION
              "Enable or disable the user's read write access to the port."
      ::= { portAccessEntry 4 }

  portRIAccessAllowed OBJECT-TYPE
      SYNTAX      YesNoValue
      MAX-ACCESS  read-write
      STATUS      current
      DESCRIPTION
              "Enable or disable the user's read input access to the port."
      ::= { portAccessEntry 5 }

  portROAccessAllowed OBJECT-TYPE
      SYNTAX      YesNoValue
      MAX-ACCESS  read-write
      STATUS      current
      DESCRIPTION
              "Enable or disable the user's read output access to the port."
      ::= { portAccessEntry 6 }


-- User Session Table


  userSessionTable OBJECT-TYPE
      SYNTAX      SEQUENCE OF UserSessionEntry
      MAX-ACCESS  not-accessible
      STATUS      current
      DESCRIPTION
              "user."
      ::= { userEntry 26 }

  userSessionEntry OBJECT-TYPE
      SYNTAX      UserSessionEntry
      MAX-ACCESS  not-accessible
      STATUS      current
      DESCRIPTION
              "An entry in the userEntry, each relating to a user."
      INDEX   { userSessionUserIndex, userSessionNumber  }
      ::= { userSessionTable 1 }

  UserSessionEntry ::=
      SEQUENCE {
        userSessionUserIndex
            INTEGER,
        userSessionNumber
            INTEGER,
        userSessionStatus
            RowStatus,
        userSessionType
            INTEGER,
        userSessionAuto
            OnOffValue,
        userSessionTelnetPort
            INTEGER,
        userSessionTelnetHost
            DisplayString,
        userSessionTelnetTermType
            DisplayString,
        userSessionTelnetEcho
            OnOffValue,
        userSessionTelnetMapnl
            OnOffValue,
        userSessionTelnetMode
            OnOffValue,
        userSessionTelnetInterrupt
            Hex8,
        userSessionTelnetQuit
            Hex8,
        userSessionTelnetEOF
            Hex8,
        userSessionTelnetErase
            Hex8,
        userSessionTelnetEchoCC
            Hex8,
        userSessionTelnetBreak
            Hex8,
        userSessionSSHPort
            INTEGER,
        userSessionSSHHost
            DisplayString,
        userSessionSSHTermType
            DisplayString,
        userSessionSSHVerbose
            OnOffValue,
        userSessionSSHCompression
            OnOffValue,
        userSessionSSHAutoLogin
            OnOffValue,
        userSessionSSHName
            DisplayString,
        userSessionSSHProtocol
            INTEGER,
        userSessionSSHRSA
            OnOffValue,
        userSessionSSHDSA
            OnOffValue,
        userSessionSSHKeyboard
            OnOffValue,
        userSessionSSHCipherSSH1
            INTEGER,
        userSessionSSHFirstSSH2Cipher
            INTEGER,
        userSessionSSHSecondSSH2Cipher
            INTEGER,
        userSessionSSHThirdSSH2Cipher
            INTEGER,
        userSessionSSHFourthSSH2Cipher
            INTEGER,
        userSessionSSHFifthSSH2Cipher
            INTEGER,
        userSessionRloginHost
            DisplayString,
        userSessionRloginTermType
            DisplayString
      }

  userSessionUserIndex OBJECT-TYPE
      SYNTAX      INTEGER
      MAX-ACCESS  not-accessible
      STATUS      current
      DESCRIPTION
              "The user number."
      ::= { userSessionEntry 1 }

  userSessionNumber OBJECT-TYPE
      SYNTAX      INTEGER (1..4)
      MAX-ACCESS  not-accessible
      STATUS      current
      DESCRIPTION
              "The session number."
      ::= { userSessionEntry 2 }

   userSessionStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { userSessionEntry 3}

  userSessionType OBJECT-TYPE
      SYNTAX      INTEGER {
        none(1),
        telnet(2),
        rlogin(3),
        ssh(4)
      }
      MAX-ACCESS  read-write
      STATUS      current
      DESCRIPTION
              "The type of session for this session number for this user."
      ::= { userSessionEntry 4 }

  userSessionAuto OBJECT-TYPE
      SYNTAX      OnOffValue
      MAX-ACCESS  read-write
      STATUS      current
      DESCRIPTION
              "Specify whether or not the session(s) will start automatically
               when the user logs into the Device Server. "
      ::= { userSessionEntry 5 }

  userSessionTelnetPort OBJECT-TYPE
      SYNTAX      INTEGER (0..65535)
      MAX-ACCESS  read-write
      STATUS      current
      DESCRIPTION
              "For Telnet sessions, the port number the target host is
               listening on for incoming connections."
      ::= { userSessionEntry 6 }

  userSessionTelnetHost OBJECT-TYPE
      SYNTAX      DisplayString(SIZE(0..14))
      MAX-ACCESS  read-write
      STATUS      current
      DESCRIPTION
              "The name of the target host."
      ::= { userSessionEntry 7 }

  userSessionTelnetTermType OBJECT-TYPE
      SYNTAX      DisplayString(SIZE(0..14))
      MAX-ACCESS  read-write
      STATUS      current
      DESCRIPTION
              "Type of terminal attached to this line; for example, ANSI or WYSE60."
      ::= { userSessionEntry 8 }

  userSessionTelnetEcho OBJECT-TYPE
      SYNTAX      OnOffValue
      MAX-ACCESS  read-write
      STATUS      current
      DESCRIPTION
              "Toggles between local echo of entered characters and suppressing local
               echo. Local echo is used for normal processing, while suppressing the
               echo is convenient for entering text that should not be displayed on
               the screen, such as passwords. This parameter can only be used when
               Line Mode is On. Default is Off."
      ::= { userSessionEntry 9}

  userSessionTelnetMapnl OBJECT-TYPE
      SYNTAX      OnOffValue
      MAX-ACCESS  read-write
      STATUS      current
      DESCRIPTION
              "Maps carriage returns (CR) to carriage return line feed (CRLF). Default is Off."
      ::= { userSessionEntry 10}

  userSessionTelnetMode OBJECT-TYPE
      SYNTAX      OnOffValue
      MAX-ACCESS  read-write
      STATUS      current
      DESCRIPTION
              "When On, keyboard input is not sent to the remote host until Enter is
               pressed, otherwise input is sent every time a key is pressed. Default is Off."
      ::= { userSessionEntry 11}

  userSessionTelnetInterrupt OBJECT-TYPE
      SYNTAX      Hex8
      MAX-ACCESS  read-write
      STATUS      current
      DESCRIPTION
              "Defines the interrupt character. Typing the interrupt character interrupts
               the current process. This value is in hexadecimal with a default value
               of 3 (ASCII value ^C)."
      ::= { userSessionEntry 12 }

  userSessionTelnetQuit OBJECT-TYPE
      SYNTAX      Hex8
      MAX-ACCESS  read-write
      STATUS      current
      DESCRIPTION
              "Defines the quit character. Typing the quit character closes and exits the
               current telnet session. This value is in hexadecimal with a default value
               of 1c (ASCII value FS)."
      ::= { userSessionEntry 13}

  userSessionTelnetEOF OBJECT-TYPE
      SYNTAX      Hex8
      MAX-ACCESS  read-write
      STATUS      current
      DESCRIPTION
              "Defines the end-of-file character. When Line Mode is On, entering the eof
               character as the first character on a line sends the character to the remote
               host. This value is in hexadecimal with a default value of 4 (ASCII value ^D)."
      ::= { userSessionEntry 14 }

  userSessionTelnetErase OBJECT-TYPE
      SYNTAX      Hex8
      MAX-ACCESS  read-write
      STATUS      current
      DESCRIPTION
              "Defines the erase character. When Line Mode is Off, typing the erase character
               erases one character. This value is in hexadecimal with a default value of 8
               (ASCII value ^H)."
      ::= { userSessionEntry 15 }

  userSessionTelnetEchoCC OBJECT-TYPE
      SYNTAX      Hex8
      MAX-ACCESS  read-write
      STATUS      current
      DESCRIPTION
              "Defines the echo character. When Line Mode is On, typing the echo character
               echoes the text locally and sends only completed lines to the host. This
               value is in hexadecimal with a default value of 5 (ASCII value ^E)."
      ::= { userSessionEntry 16 }

  userSessionTelnetBreak OBJECT-TYPE
      SYNTAX      Hex8
      MAX-ACCESS  read-write
      STATUS      current
      DESCRIPTION
              "Defines the escape character. Returns you to the command line mode.
               This value is in hexadecimal with a default value of 1d (ASCII value GS)."
      ::= { userSessionEntry 17}

  userSessionSSHPort OBJECT-TYPE
      SYNTAX      INTEGER (0..65535)
      MAX-ACCESS  read-write
      STATUS      current
      DESCRIPTION
              "The target host port number."
      ::= { userSessionEntry 18}

  userSessionSSHHost OBJECT-TYPE
      SYNTAX      DisplayString(SIZE(0..14))
      MAX-ACCESS  read-write
      STATUS      current
      DESCRIPTION
              "The host that the user will automatically connecto to via SSH
               after a successful login."
      ::= { userSessionEntry 19}

  userSessionSSHTermType OBJECT-TYPE
      SYNTAX      DisplayString(SIZE(0..14))
      MAX-ACCESS  read-write
      STATUS      current
      DESCRIPTION
              "The type of terminal that will connecting via SSH."
      ::= { userSessionEntry 20}

  userSessionSSHVerbose OBJECT-TYPE
      SYNTAX      OnOffValue
      MAX-ACCESS  read-write
      STATUS      current
      DESCRIPTION
              "Displays debug messages on the terminal."
      ::= { userSessionEntry 21}

  userSessionSSHCompression OBJECT-TYPE
      SYNTAX      OnOffValue
      MAX-ACCESS  read-write
      STATUS      current
      DESCRIPTION
              "Requests compression of all data. Compression is desirable
               on modem lines and other slow connections, but will only
               slow down things on fast networks."
      ::= { userSessionEntry 22}

  userSessionSSHAutoLogin OBJECT-TYPE
      SYNTAX      OnOffValue
      MAX-ACCESS  read-write
      STATUS      current
      DESCRIPTION
              "Creates an automatic SSH login, using the Name and Password values."
      ::= { userSessionEntry 23}

  userSessionSSHName OBJECT-TYPE
      SYNTAX      DisplayString(SIZE(0..20))
      MAX-ACCESS  read-write
      STATUS      current
      DESCRIPTION
              "The name of the user logging into the SSH session."
      ::= { userSessionEntry 24}

  userSessionSSHProtocol OBJECT-TYPE
      SYNTAX      INTEGER {
        ssh1(1),
        ssh2(2),
        sshBoth(3)
      }
      MAX-ACCESS  read-write
      STATUS      current
      DESCRIPTION
              "Specify the SSH client version that will be used
               for the SSH session."
      ::= { userSessionEntry 25}

  userSessionSSHRSA OBJECT-TYPE
      SYNTAX      OnOffValue
      MAX-ACCESS  read-write
      STATUS      current
      DESCRIPTION
              "An authentication method used by SSH version 1 and 2.
               Use RSA authentication for the SSH session."
      ::= { userSessionEntry 26}

  userSessionSSHDSA OBJECT-TYPE
      SYNTAX      OnOffValue
      MAX-ACCESS  read-write
      STATUS      current
      DESCRIPTION
              "An authentication method used by SSH version 2.
               Use DSA authentication for the SSH session."
      ::= { userSessionEntry 27}

  userSessionSSHKeyboard OBJECT-TYPE
      SYNTAX      OnOffValue
      MAX-ACCESS  read-write
      STATUS      current
      DESCRIPTION
              "The user types in a password for authentication."
      ::= { userSessionEntry 28}

  userSessionSSHCipherSSH1 OBJECT-TYPE
      SYNTAX      INTEGER {
        tripledes(1),
        blowfish(2)
      }
      MAX-ACCESS  read-write
      STATUS      current
      DESCRIPTION
              "Select the encryption method (cipher) that you
               want to use for your SSH version 1 connection:
               3DES or Blowfish"
      ::= { userSessionEntry 29}

  userSessionSSHFirstSSH2Cipher OBJECT-TYPE
      SYNTAX      INTEGER {
        tripledes(1),
        blowfish(2),
        aes(3),
        cast(4),
        arcfour(5)
      }
      MAX-ACCESS  read-write
      STATUS      current
      DESCRIPTION
              "Select the first priority negotiation for the encryption
               method (ciphers) that the Device Server will use for
               the SSH version 2 connection:
               3DES, Blowfish, AES, CAST, or Arcfour"
      ::= { userSessionEntry 30}

  userSessionSSHSecondSSH2Cipher OBJECT-TYPE
      SYNTAX      INTEGER {
        none(1),
        tripledes(2),
        blowfish(3),
        aes(4),
        cast(5),
        arcfour(6)
      }
      MAX-ACCESS  read-write
      STATUS      current
      DESCRIPTION
              "Select the second priority negotiation for the encryption
               method (ciphers) that the Device Server will use for
               the SSH version 2 connection:
               None, 3DES, Blowfish, AES, CAST, or Arcfour"
      ::= { userSessionEntry 31}

  userSessionSSHThirdSSH2Cipher OBJECT-TYPE
      SYNTAX      INTEGER {
        none(1),
        tripledes(2),
        blowfish(3),
        aes(4),
        cast(5),
        arcfour(6)
      }
      MAX-ACCESS  read-write
      STATUS      current
      DESCRIPTION
              "Select the third priority negotiation for the encryption
               method (ciphers) that the Device Server will use for
               the SSH version 2 connection:
               None, 3DES, Blowfish, AES, CAST, or Arcfour"
      ::= { userSessionEntry 32}

  userSessionSSHFourthSSH2Cipher OBJECT-TYPE
      SYNTAX      INTEGER {
        none(1),
        tripledes(2),
        blowfish(3),
        aes(4),
        cast(5),
        arcfour(6)
      }
      MAX-ACCESS  read-write
      STATUS      current
      DESCRIPTION
              "Select the fourth priority negotiation for the encryption
               method (ciphers) that the Device Server will use for
               the SSH version 2 connection:
               None, 3DES, Blowfish, AES, CAST, or Arcfour"
      ::= { userSessionEntry 33}

  userSessionSSHFifthSSH2Cipher OBJECT-TYPE
      SYNTAX      INTEGER {
        none(1),
        tripledes(2),
        blowfish(3),
        aes(4),
        cast(5),
        arcfour(6)
      }
      MAX-ACCESS  read-write
      STATUS      current
      DESCRIPTION
              "Select the fifth priority negotiation for the encryption
               method (ciphers) that the Device Server will use for
               the SSH version 2 connection:
               None, 3DES, Blowfish, AES, CAST, or Arcfour"
      ::= { userSessionEntry 34}

  userSessionRloginHost OBJECT-TYPE
      SYNTAX      DisplayString(SIZE(0..14))
      MAX-ACCESS  read-write
      STATUS      current
      DESCRIPTION
              "The name of the target host."
      ::= { userSessionEntry 35}

  userSessionRloginTermType OBJECT-TYPE
      SYNTAX      DisplayString(SIZE(0..14))
      MAX-ACCESS  read-write
      STATUS      current
      DESCRIPTION
              "Type of terminal attached to this line; for example, ansi or wyse60."
      ::= { userSessionEntry 36}

    userAllowAccessClusterPorts OBJECT-TYPE
      SYNTAX      OnOffValue
      MAX-ACCESS  read-write
      STATUS      current
      DESCRIPTION
              "Allow/disallow the user to access to clustering ports."
      ::= { userEntry 27 }
      
    userHost OBJECT-TYPE
      SYNTAX      DisplayString (SIZE(0..14))
      MAX-ACCESS  read-write
      STATUS      current
      DESCRIPTION
              "The name of the host."
      ::= { userEntry 28}  
      
--  portInfo group. A table of entries, each entry per port.

  portTable OBJECT-TYPE
      SYNTAX      SEQUENCE OF PortEntry
      MAX-ACCESS  not-accessible
      STATUS      current
      DESCRIPTION
              "The port configuration table."
      ::= { portInfo 1 }

  portEntry OBJECT-TYPE
      SYNTAX      PortEntry
      MAX-ACCESS  not-accessible
      STATUS      current
      DESCRIPTION
              "An entry in the port configuration table, each relating to a serial port."
      INDEX   { portIndex }
      ::= { portTable 1 }

  PortEntry ::=
      SEQUENCE {
          portIndex
              INTEGER,
          portStatus
              RowStatus,
          portName
              DisplayString,
          portService
              INTEGER,
          portDial
              INTEGER,
          portModem
              DisplayString,
          portPhone
              DisplayString,
          portTermType
              INTEGER,
          portPages
              INTEGER,
          portPreDefinedUser
              DisplayString,
          portDSPort
              INTEGER,
          portIdleTimer
              INTEGER,
          portSessionTimer
              INTEGER,
          portSecurity
              OnOffValue,
          portBreak
              INTEGER,
          portInboundFlowControl
              OnOffValue,
          portOutboundFlowControl
              OnOffValue,
          portInitialMode
              INTEGER,
          portReset
              OnOffValue,
          portKeepalive
              OnOffValue,
          portMapCR
              OnOffValue,
          portMOTD
              OnOffValue,
          portHotKeyPrefix
              Hex8,
          portLock
              OnOffValue,
          portEnable
            OnOffValue,
          portMultiSession
            INTEGER,
          portDialRetries
            INTEGER,
          portDialTimeout
            INTEGER,
          portInternetAddress
            Ipv4v6Address,
          portRawOption
            INTEGER,
          portDirectTrigger
            Hex8
        }

  portIndex OBJECT-TYPE
      SYNTAX      INTEGER
      MAX-ACCESS  not-accessible
      STATUS      current
      DESCRIPTION
              "Port Index"
      ::= { portEntry 1}

  portStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portEntry 2}

  portName OBJECT-TYPE
      SYNTAX      DisplayString(SIZE(0..19))
      MAX-ACCESS  read-write
      STATUS      current
      DESCRIPTION
              "Provide a name for the line."
      ::= { portEntry 3}

  portService OBJECT-TYPE
      SYNTAX      INTEGER {
        dslogin(1),
        directraw(2),
        silentraw(3),
        reverseraw(4),
        bidirectionalmodem(5),
        directtelnet(6),
        silenttelnet(7),
        reversetelnet(8),
        directssh(9),
        silentssh(10),
        reversessh(11),
        directrlogin(12),
        silentrlogin(13),
        slip(14),
        ppp(15),
        printer(16),
        udp(17),
        vmodem(18),
        clienttunnel(19),
        servertunnel(20),
        modbusslave(21),
        modbusmaster(22),
        customapp(23), 
        signalIo(24),
        trueport(25),
        powermanagement(26)
     }
      MAX-ACCESS  read-write
      STATUS      current
      DESCRIPTION
              "Defines the Line Service, which determines how the
               line will be used."
      ::= { portEntry 4}

  portDial OBJECT-TYPE
      SYNTAX      INTEGER{
        none(1),
        in(2),
        out(3),
        both(4)
      }
      MAX-ACCESS  read-write
      STATUS      current
      DESCRIPTION
              "Determines how a modem will work on the line. If your user
               is remote and will be dialing in via modem or ISDN TA, set
               this parameter to In; if the Device Server is being used as
               a router, set this parameter to either In, Out, or Both,
               depending on which end of the link your Device Server is
               situated and how you want to initiate the communication."
      ::= { portEntry 5}

  portModem OBJECT-TYPE
      SYNTAX      DisplayString(SIZE(0..20))
      MAX-ACCESS  read-write
      STATUS      current
      DESCRIPTION
              "The name of the predefined modem that is used on this line."
      ::= { portEntry 6}
      
  portPhone OBJECT-TYPE
      SYNTAX      DisplayString(SIZE(0..32))
      MAX-ACCESS  read-write
      STATUS      current
      DESCRIPTION
              "The phone number to use when Dial is set to Out."
      ::= { portEntry 7}

  portTermType OBJECT-TYPE
      SYNTAX      INTEGER {
        wyse60(1),
        vt100(2),
        ansi(3),
        dumb(4),
        tvi925(5),
        ibm3151(6),
        vt320(7),
        hp700(8),
        extra1(9),
        extra2(10),
        extra3(11)
      }
      MAX-ACCESS  read-write
      STATUS      current
      DESCRIPTION
        "Specifies the type of terminal connected to the line:
        Dumb, WYSE60, VT100, ANSI, TVI925, IBM3151TE,
        VT320 (specifically supporting VT320-7),
        HP700 (specifically supporting HP700/44),
        Term1, Term2, Term3 (user defined terminals)"
      ::= { portEntry 8}

  portPages OBJECT-TYPE
      SYNTAX      INTEGER (1..7)
      MAX-ACCESS  read-write
      STATUS      current
      DESCRIPTION
              "For DSLogin line service, this is the number of video
               pages the terminal supports. Valid values are 1-7.
               The default is 5 pages."
      ::= { portEntry 9}

  portPreDefinedUser OBJECT-TYPE
      SYNTAX      DisplayString(SIZE(0..16))
      MAX-ACCESS  read-write
      STATUS      current
      DESCRIPTION
              "For DSLogin line service, makes this a line that is dedicated
               to the specified user. Only this user will be able to log in
               on this line and they won't need to enter their login
               name - just their password."
      ::= { portEntry 10}

  portDSPort OBJECT-TYPE
      SYNTAX      INTEGER(0..65535)
      MAX-ACCESS  read-write
      STATUS      current
      DESCRIPTION
              "The Device Server port number."
      ::= { portEntry 11}

  portIdleTimer OBJECT-TYPE
      SYNTAX      INTEGER (0..4294967)
      MAX-ACCESS  read-write
      STATUS      current
      DESCRIPTION
              "Enter a time period, in seconds, for which the Idle Timer will run.
               Use this timer to close a connection because of inactivity. When the
               Idle Timer expires, the Device Server will end the connection. The
               maximum value is 4294967 seconds (about 49 days). The default value
               of 0 (zero) means the Idle Timer will not expire, so the connection is
               permanently open."
      ::= { portEntry 12}

  portSessionTimer OBJECT-TYPE
      SYNTAX      INTEGER (0..4294967)
      MAX-ACCESS  read-write
      STATUS      current
      DESCRIPTION
              "Enter a time, in seconds, for which the Session Timer will run. Use this
               timer to forcibly close the session (connection). When the Session Timer
               expires, the Device Server will end the connection. The default value is
               0 seconds so the port will never timeout. The maximum value is 4294967
               seconds (about 49 days)."
      ::= { portEntry 13}

  portSecurity OBJECT-TYPE
      SYNTAX      OnOffValue
      MAX-ACCESS  read-write
      STATUS      current
      DESCRIPTION
              "Enables/disables login/password authentication, locally or externally,
               on reverse Telnet connections. The default is Off."
      ::= { portEntry 14}

  portBreak OBJECT-TYPE
      SYNTAX      INTEGER {
        off(1),
        local(2),
        remote(3),
        brkintr(4)
      }
      MAX-ACCESS  read-write
      STATUS      current
      DESCRIPTION
              "Specifies how a break is interpreted:
               None-The Device Server ignores the break key completely and
                  it is not passed through to the host. This is the default setting.
               Local-The Device Server deals with the break locally. If the user is
                  in a session, the break key has the same effect as a hot key.
               Remote-When the break key is pressed, the Device Server translates this
                  into a telnet break signal which it sends to the host machine.
               Brkintr-On some systems such as SunOS, XENIX, and AIX, a break received
                  from the peripheral is not passed to the client properly. If the
                  client wishes to make the break act like an interrupt key (for example,
                  when the stty options -ignbrk and brkintr are set)"
      ::= { portEntry 15}

  portInboundFlowControl OBJECT-TYPE
      SYNTAX      OnOffValue
      MAX-ACCESS  read-write
      STATUS      current
      DESCRIPTION
              "Determines if input flow control is to be used.
               Default is On. This is active only when Line Flow Control
               is set to Soft, Hard, or Both."
      ::= { portEntry 16}

  portOutboundFlowControl OBJECT-TYPE
      SYNTAX      OnOffValue
      MAX-ACCESS  read-write
      STATUS      current
      DESCRIPTION
              "Determines if output flow control is to be used.
               Default is On. This is active only when Line Flow Control
               is set to Soft, Hard, or Both."
      ::= { portEntry 17}

  portInitialMode OBJECT-TYPE
      SYNTAX      INTEGER {
        cli(1),
        menu(2)
      }
      MAX-ACCESS  read-write
      STATUS      current
      DESCRIPTION
              "Specifies the initial interface a user navigates when logging
               into the line; either the Menu or a prompt for the CLI.
               The default is CLI."
      ::= { portEntry 18}

  portReset OBJECT-TYPE
      SYNTAX      OnOffValue
      MAX-ACCESS  read-write
      STATUS      current
      DESCRIPTION
              "Resets the terminal type connected to the line when a user logs out."
      ::= { portEntry 19}

  portKeepalive OBJECT-TYPE
      SYNTAX      OnOffValue
      MAX-ACCESS  read-write
      STATUS      current
      DESCRIPTION
              "Enables a per-connection TCP keepalive feature; after approximately
               3 minutes of network connection idle time, the connection will send
               a gratuitous ACK to the network peer, either ensuring the connection
               stays active OR causing a dropped connection condition to be recognised
               by the reverse raw service.
               Applications using this feature need to be aware that there might be
               some considerable delay between a network disconnection and the port
               being available for the next connection attempt; this is to allow any
               data sent on prior connections to be transmitted out of the serial
               port buffer. Application network retry logic needs to accommodate this feature."
      ::= { portEntry 20}

  portMapCR OBJECT-TYPE
      SYNTAX      OnOffValue
      MAX-ACCESS  read-write
      STATUS      current
      DESCRIPTION
              "Maps carriage returns (CR) to carriage return line feed (CRLF).
               The default value is Off."
      ::= { portEntry 21}

  portMOTD OBJECT-TYPE
      SYNTAX      OnOffValue
      MAX-ACCESS  read-write
      STATUS      current
      DESCRIPTION
              "Enables/disables the message of the day on the line."
      ::= { portEntry 22}

  portHotKeyPrefix OBJECT-TYPE
      SYNTAX      Hex8
      MAX-ACCESS  read-write
      STATUS      current
      DESCRIPTION
              "The prefix that a user types to lock a line or redraw the Menu. The
               default value is hex 01, which corresponds to Ctrl-a (^a) (hex value
               02 would be Ctrl-b (^b), etc.):
               ^a l-(Lowercase L) Locks the line until the user unlocks it. The user
                  is prompted for a password (any password, excluding spaces) and locks
                  the line. Next, the user must retype the password to unlock the line.
               ^r-When you switch from a session back to the Menu, the screen may not
                  be redrawn correctly. If this happens, use this command to redraw it properly.
               You can use the Hotkey Prefix key to lock a line only when the Line
               Lock parameter is On."
      ::= { portEntry 23}

  portLock OBJECT-TYPE
      SYNTAX      OnOffValue
      MAX-ACCESS  read-write
      STATUS      current
      DESCRIPTION
              "When enabled, the user can lock his terminal with a password using the
               Hotkey Prefix (default Ctrl-a) ^a l (lowercase L). The Device Server
               prompts the user for a password and a confirmation."
      ::= { portEntry 24}

   portEnable OBJECT-TYPE
      SYNTAX      OnOffValue
      MAX-ACCESS  read-write
      STATUS      current
      DESCRIPTION
              "Is the Port Enabled. This field is not available on 1-port units."
      ::= { portEntry 25}
   portMultiSession OBJECT-TYPE
      SYNTAX      INTEGER (0..255)
      MAX-ACCESS  read-write
      STATUS      current
      DESCRIPTION
              "The number of Multisessions allowed on this port"
      ::= { portEntry 26}

   portDialRetries OBJECT-TYPE
      SYNTAX      INTEGER (0..99)
      MAX-ACCESS  read-write
      STATUS      current
      DESCRIPTION
              "The number of Dial Retries"
      ::= { portEntry 27}

   portDialTimeout OBJECT-TYPE
      SYNTAX      INTEGER (1..99)
      MAX-ACCESS  read-write
      STATUS      current
      DESCRIPTION
              "The timeout value when dialing in seconds"
      ::= { portEntry 28}

   portInternetAddress OBJECT-TYPE
      SYNTAX      Ipv4v6Address
      MAX-ACCESS  read-write
      STATUS      current
      DESCRIPTION
              "The internet address of this port"
      ::= { portEntry 29}
      
	portRawOption OBJECT-TYPE
      SYNTAX      INTEGER {
        noneMultihost(1),
        multihost(2),
        directAny(3)
     }
      MAX-ACCESS  read-write
      STATUS      current
      DESCRIPTION
              "Defines the multihost Service and direct connection initiate mode"
      ::= { portEntry 30}

	portDirectTrigger OBJECT-TYPE
	 SYNTAX	 Hex8
      MAX-ACCESS  read-write
      STATUS      current
      DESCRIPTION
              "Defines the direct connection initiate char"
      ::= { portEntry 31}

      
-- port Hdw Table

  portHdwTable OBJECT-TYPE
      SYNTAX      SEQUENCE OF PortHdwEntry
      MAX-ACCESS  not-accessible
      STATUS      current
      DESCRIPTION
              "Port."
      ::= { portInfo 2 }

  portHdwEntry OBJECT-TYPE
      SYNTAX      PortHdwEntry
      MAX-ACCESS  not-accessible
      STATUS      current
      DESCRIPTION
              "An entry in the portHdwEntry, each relating to a port."
      INDEX   { portHdwIndex }
      ::= { portHdwTable 1 }

  PortHdwEntry ::=
      SEQUENCE {
        portHdwIndex
              INTEGER,
        portHdwStatus
           RowStatus,
        portHdwInterface
            INTEGER,
        portHdwSpeed
            INTEGER,
        portHdwDataBits
            INTEGER,
        portHdwParity
            INTEGER,
        portHdwStopBits
            INTEGER,
        portHdwFlowControl
            INTEGER,
        portHdwMonitorDSR
            OnOffValue,
        portHdwMonitorDCD
            OnOffValue,
        portHdwDuplex
            INTEGER,
        portHdwTXDriverControl
            INTEGER,
        portHdwEchoSuppression
            OnOffValue,
        portHdwUART
            INTEGER,
        portHdwIRQ
            INTEGER,
        portHdwTxBytes
            Counter32,
        portHdwRxBytes
            Counter32,
        portHdwFrameErr
            Counter32,
        portHdwParityErr
            Counter32,
        portHdwBreaks
            Counter32,
        portHdwOverruns
            Counter32,
        portHdwRTS
            OnOffValue,
        portHdwCTS
            OnOffValue,
        portHdwDTR
            OnOffValue,
        portHdwDSR
            OnOffValue,
        portHdwCD
           OnOffValue,
        portHdwRI
           OnOffValue,
        portSoftTermination
           OnOffValue,
        portHdwCustomSpeed
            INTEGER
        }

  portHdwIndex OBJECT-TYPE
      SYNTAX      INTEGER
      MAX-ACCESS  read-only
      STATUS      current
      DESCRIPTION
              "portHdwIndex"
      ::= { portHdwEntry 1 }

  portHdwStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portHdwEntry 2}

  portHdwInterface OBJECT-TYPE
      SYNTAX      INTEGER {
        eia232(1),
        eia422(2),
        eia485(3)
      }
      MAX-ACCESS  read-write
      STATUS      current
      DESCRIPTION
              "Specifies the type of line that is being used with the
               Device Server. Select either EIA-232, EIA-422, or EIA-485."
      ::= { portHdwEntry 3}

  portHdwSpeed OBJECT-TYPE
      SYNTAX      INTEGER {
        b50(1),
        b75(2),
        b110(3),
        b134(4),
        b150(5),
        b200(6),
        b300(7),
        b600(8),
        b1200(9),
        b1800(10),
        b2400(11),
        b4800(12),
        b9600(13),
        b19200(14),
        b38400(15),
        b57600(16),
        b115200(17),
        b230400(18),
        b28800(23),
        bCustom(24)
      }
      MAX-ACCESS  read-write
      STATUS      current
      DESCRIPTION
              "Specifies the baud rate of the line; keep in mind that
               speed is affected by the length of the cable.  When bCustom
               is set, then the baud rate is specified by portHwdCustomSpeed.
               Internal modems only support the following baud rates:
               300, 1200, 2400, 4800, 9600, 19200, 38400, 57600, 
               115200, and 28800."
      ::= { portHdwEntry 4}

  portHdwDataBits OBJECT-TYPE
      SYNTAX      INTEGER {
        d5(1),
        d6(2),
        d7(3),
        d8(4)
      }
      MAX-ACCESS  read-write
      STATUS      current
      DESCRIPTION
              "Specifies the number of bits in a byte. The default is 8.
               Internal modems only support 7 and 8 data bits."
      ::= { portHdwEntry 5}

  portHdwParity OBJECT-TYPE
      SYNTAX      INTEGER {
        none(1),
        odd(2),
        even(3),
        mark(4),
        space(5)
      }
      MAX-ACCESS  read-write
      STATUS      current
      DESCRIPTION
              "Specifies if you are using Even, Odd, or No parity on the line.
               If you want to force a parity type, you can specify Mark for 1
               or Space for 0. "
      ::= { portHdwEntry 6}

  portHdwStopBits OBJECT-TYPE
      SYNTAX      INTEGER {
        s1(1),
        s2(2),
        s1d5(3)
      }
      MAX-ACCESS  read-write
      STATUS      current
      DESCRIPTION
              "Specifies the number of stop bits that follow a byte. 
               Certain models do not support 1.5 stop bits. Internal 
               modems only support 1 stop bit."
      ::= { portHdwEntry 7}

  portHdwFlowControl OBJECT-TYPE
      SYNTAX      INTEGER {
        none(1),
        soft(2),
        hard(3),
        both(4)
      }
      MAX-ACCESS  read-write
      STATUS      current
      DESCRIPTION
              "Defines whether the data flow is handled by the
               software (Soft), hardware (Hard), Both, or None."
      ::= { portHdwEntry 8}

  portHdwMonitorDSR OBJECT-TYPE
      SYNTAX      OnOffValue
      MAX-ACCESS  read-write
      STATUS      current
      DESCRIPTION
              "Specifies whether the RS-232 signal DSR (Data Set Ready) should
               be monitored, for Device Servers with a DTE serial interface.
               On a Device Server with a DCE serial interface, this object 
               specifies whether the DTR (Data Terminal Ready) signal should
               be monitored.
               
               For DTE interfaces, this is used with modems or any device that sends
               a DSR signal. When it is monitored and the Device Server detects
               a DSR signal, the line service is started. Default is Off. If
               both Monitor DCD and Monitor DSR are enabled, both signals must
               be detected before the line service is started.
               
               For DCE interfaces, this is used with terminals or other devices
               that output a DTR signal.
               
               This value cannot be changed for internal modems."
      ::= { portHdwEntry 9}

  portHdwMonitorDCD OBJECT-TYPE
      SYNTAX      OnOffValue
      MAX-ACCESS  read-write
      STATUS      current
      DESCRIPTION
              "Specifies whether the RS-232 signal DCD (Data Carrier Detect) should
               be monitored.  This object does not apply to DCE serial interfaces.
               
               This is used with modems or any other device that sends
               a DCD signal. When it is monitored and the Device Server detects a
               DCD signal, the line service is started. Default is Off. If both
               Monitor DCD and Monitor DSR are enabled, both signals must be detected
               before the line service is started."
      ::= { portHdwEntry 10}

  portHdwDuplex OBJECT-TYPE
      SYNTAX      INTEGER {
        half(1),
        full(2)
      }
      MAX-ACCESS  read-write
      STATUS      current
      DESCRIPTION
              "Specify whether the line is Full Duplex (communication both ways
               at the same time) or Half Duplex (communication in one direction
               at a time)."
      ::= { portHdwEntry 11}

  portHdwTXDriverControl OBJECT-TYPE
      SYNTAX      INTEGER {
        auto(1),
        rts(2)
      }
      MAX-ACCESS  read-write
      STATUS      current
      DESCRIPTION
              "Used with a EIA-485 serial interface, if your application supports
               RTS (Request To Send), select this option. Otherwise, select Auto.
               Default is Auto"
      ::= { portHdwEntry 12}

  portHdwEchoSuppression OBJECT-TYPE
      SYNTAX      OnOffValue
      MAX-ACCESS  read-write
      STATUS      current
      DESCRIPTION
              "This parameter applies only to EIA-485 Half Duplex mode. All characters
               will be echoed to the user and transmitted across the serial ports.
               Some EIA-485 applications require local echo to be enabled in order to
               monitor the loopback data to determine that line contention has occurred.
               If your application cannot handle loopback data, echo suppression should
               be On. The default is echo suppression Off."
      ::= { portHdwEntry 13}

  portHdwUART OBJECT-TYPE
      SYNTAX      INTEGER {
        scc(1),
        smc(2),
        exar(3)
      }
      MAX-ACCESS  read-only
      STATUS      current
      DESCRIPTION
              "portHdwUART"
      ::= { portHdwEntry 14}

  portHdwIRQ OBJECT-TYPE
      SYNTAX      INTEGER
      MAX-ACCESS  read-only
      STATUS      current
      DESCRIPTION
              "portHdwIRQ"
      ::= { portHdwEntry 15}

  portHdwTxBytes OBJECT-TYPE
      SYNTAX      Counter32
      MAX-ACCESS  read-only
      STATUS      current
      DESCRIPTION
              "portHdwTxBytes"
      ::= { portHdwEntry 16}

  portHdwRxBytes OBJECT-TYPE
      SYNTAX      Counter32
      MAX-ACCESS  read-only
      STATUS      current
      DESCRIPTION
              "portHdwRxBytes"
      ::= { portHdwEntry 17}

  portHdwFrameErr OBJECT-TYPE
      SYNTAX      Counter32
      MAX-ACCESS  read-only
      STATUS      current
      DESCRIPTION
              "portHdwFrameErr"
      ::= { portHdwEntry 18}

  portHdwParityErr OBJECT-TYPE
      SYNTAX      Counter32
      MAX-ACCESS  read-only
      STATUS      current
      DESCRIPTION
              "portHdwParityErr"
      ::= { portHdwEntry 19}

  portHdwBreaks OBJECT-TYPE
      SYNTAX      Counter32
      MAX-ACCESS  read-only
      STATUS      current
      DESCRIPTION
              "portHdwBreaks"
      ::= { portHdwEntry 20}

  portHdwOverruns OBJECT-TYPE
      SYNTAX      Counter32
      MAX-ACCESS  read-only
      STATUS      current
      DESCRIPTION
              "portHdwOverruns"
      ::= { portHdwEntry 21}

  portHdwRTS OBJECT-TYPE
      SYNTAX      OnOffValue
      MAX-ACCESS  read-only
      STATUS      current
      DESCRIPTION
              "portHdwRTS"
      ::= { portHdwEntry 22}

  portHdwCTS OBJECT-TYPE
      SYNTAX      OnOffValue
      MAX-ACCESS  read-only
      STATUS      current
      DESCRIPTION
              "portHdwCTS"
      ::= { portHdwEntry 23}

  portHdwDTR OBJECT-TYPE
      SYNTAX      OnOffValue
      MAX-ACCESS  read-only
      STATUS      current
      DESCRIPTION
              "portHdwDTR"
      ::= { portHdwEntry 24}

  portHdwDSR OBJECT-TYPE
      SYNTAX      OnOffValue
      MAX-ACCESS  read-only
      STATUS      current
      DESCRIPTION
              "portHdwDSR"
      ::= { portHdwEntry 25}

  portHdwCD OBJECT-TYPE
      SYNTAX      OnOffValue
      MAX-ACCESS  read-only
      STATUS      current
      DESCRIPTION
              "portHdwCD"
      ::= { portHdwEntry 26}

  portHdwRI OBJECT-TYPE
      SYNTAX      OnOffValue
      MAX-ACCESS  read-only
      STATUS      current
      DESCRIPTION
              "portHdwRI"
      ::= { portHdwEntry 27}

      
 portSoftTermination OBJECT-TYPE
      SYNTAX      OnOffValue
      MAX-ACCESS  read-write
      STATUS      current
      DESCRIPTION
              "Enables or disables software line termination."
      ::= { portHdwEntry 29}
      
   portHdwCustomSpeed OBJECT-TYPE
      SYNTAX      INTEGER (50..1843200)
      MAX-ACCESS  read-write
      STATUS      current
      DESCRIPTION
              "The custom baud rate for this port."
      ::= { portHdwEntry 30 }
      
--- Port Telnet Table

  portTelnetTable OBJECT-TYPE
      SYNTAX      SEQUENCE OF PortTelnetEntry
      MAX-ACCESS  not-accessible
      STATUS      current
      DESCRIPTION
              "Port Telnet Table."
      ::= { portInfo 3 }

  portTelnetEntry OBJECT-TYPE
      SYNTAX      PortTelnetEntry
      MAX-ACCESS  not-accessible
      STATUS      current
      DESCRIPTION
              "An entry in the portTelnetEntry, each relating to a port."
      INDEX   { portTelnetIndex }
      ::= { portTelnetTable 1 }

  PortTelnetEntry ::=
      SEQUENCE {
          portTelnetIndex
            INTEGER,
          portTelnetStatus
            RowStatus,
          portTelnetPort
            INTEGER,
          portTelnetHost
            DisplayString,
          portTelnetTermType
            DisplayString,
          portTelnetEcho
            OnOffValue,
          portTelnetMapnl
            OnOffValue,
          portTelnetMode
            OnOffValue,
          portTelnetInterrupt
            Hex8,
          portTelnetQuit
            Hex8,
          portTelnetEOF
            Hex8,
          portTelnetErase
            Hex8,
          portTelnetEchoCC
            Hex8,
          portTelnetBreak
            Hex8
      }

  portTelnetIndex OBJECT-TYPE
      SYNTAX      INTEGER
      MAX-ACCESS  read-only
      STATUS      current
      DESCRIPTION
              "portTelnetIndex"
      ::= { portTelnetEntry 1 }

  portTelnetStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portTelnetEntry 2}

  portTelnetPort OBJECT-TYPE
      SYNTAX      INTEGER (0..65535)
      MAX-ACCESS  read-write
      STATUS      current
      DESCRIPTION
              "The port number the target host is listening on for
               incoming connections. Default is 23."
      ::= { portTelnetEntry 3 }

  portTelnetHost OBJECT-TYPE
      SYNTAX      DisplayString(SIZE(0..14))
      MAX-ACCESS  read-write
      STATUS      current
      DESCRIPTION
              "The name of the target host."
      ::= { portTelnetEntry 4 }

  portTelnetTermType OBJECT-TYPE
      SYNTAX      DisplayString(SIZE(0..14))
      MAX-ACCESS  read-write
      STATUS      current
      DESCRIPTION
              "Type of terminal attached to this line; for example, ANSI or WYSE60."
      ::= { portTelnetEntry 5 }

  portTelnetEcho OBJECT-TYPE
      SYNTAX      OnOffValue
      MAX-ACCESS  read-write
      STATUS      current
      DESCRIPTION
              "Toggles between local echo of entered characters and suppressing
               local echo. Local echo is used for normal processing, while suppressing
               the echo is convenient for entering text that should not be displayed
               on the screen, such as passwords. This parameter can only be used when
               Line Mode is On. Default is Off."
      ::= { portTelnetEntry 6}

  portTelnetMapnl OBJECT-TYPE
      SYNTAX      OnOffValue
      MAX-ACCESS  read-write
      STATUS      current
      DESCRIPTION
              "Maps carriage returns (CR) to carriage return line feed (CRLF).
               The default value is Off."
      ::= { portTelnetEntry 7 }

  portTelnetMode OBJECT-TYPE
      SYNTAX      OnOffValue
      MAX-ACCESS  read-write
      STATUS      current
      DESCRIPTION
              "When On, keyboard input is not sent to the remote host until
               Enter is pressed, otherwise input is sent every time a key
               is pressed. Default is Off."
      ::= { portTelnetEntry 8}

  portTelnetInterrupt OBJECT-TYPE
      SYNTAX      Hex8
      MAX-ACCESS  read-write
      STATUS      current
      DESCRIPTION
              "Defines the interrupt character. Typing the interrupt
               character interrupts the current process. This value is in
               hexadecimal with a default value of 3 (ASCII value ^C)."
      ::= { portTelnetEntry 9 }

  portTelnetQuit OBJECT-TYPE
      SYNTAX      Hex8
      MAX-ACCESS  read-write
      STATUS      current
      DESCRIPTION
              "Defines the quit character. Typing the quit character closes
               and exits the current telnet session. This value is in
               hexadecimal with a default value of 1c (ASCII value FS)."
      ::= { portTelnetEntry 10}

  portTelnetEOF OBJECT-TYPE
      SYNTAX      Hex8
      MAX-ACCESS  read-write
      STATUS      current
      DESCRIPTION
              "Defines the end-of-file character. When Line Mode is On,
               entering the eof character as the first character on a line
               sends the character to the remote host. This value is in hexadecimal
               with a default value of 4 (ASCII value ^D)."
      ::= { portTelnetEntry 11 }

  portTelnetErase OBJECT-TYPE
      SYNTAX      Hex8
      MAX-ACCESS  read-write
      STATUS      current
      DESCRIPTION
              "Defines the erase character. When Line Mode is Off, typing the erase
               character erases one character. This value is in hexadecimal with a
               default value of 8 (ASCII value ^H)."
      ::= { portTelnetEntry 12 }

  portTelnetEchoCC OBJECT-TYPE
      SYNTAX      Hex8
      MAX-ACCESS  read-write
      STATUS      current
      DESCRIPTION
              "Defines the echo character. When Line Mode is On, typing the echo
               character echoes the text locally and sends only completed lines to
               the host. This value is in hexadecimal with a default value of 5
               (ASCII value ^E)."
      ::= { portTelnetEntry 13 }

  portTelnetBreak OBJECT-TYPE
      SYNTAX      Hex8
      MAX-ACCESS  read-write
      STATUS      current
      DESCRIPTION
              "Defines the escape character. Returns you to the command line mode.
               This value is in hexadecimal with a default value of 1d (ASCII value GS)."
      ::= { portTelnetEntry 14}

-- Port SSH Table

  portSSHTable OBJECT-TYPE
      SYNTAX      SEQUENCE OF PortSSHEntry
      MAX-ACCESS  not-accessible
      STATUS      current
      DESCRIPTION
              "Port SSH Table."
      ::= { portInfo 4 }

  portSSHEntry OBJECT-TYPE
      SYNTAX      PortSSHEntry
      MAX-ACCESS  not-accessible
      STATUS      current
      DESCRIPTION
              "An entry in the portSSHEntry, each relating to a port."
      INDEX   { portSSHIndex }
      ::= { portSSHTable 1 }

  PortSSHEntry ::=
      SEQUENCE {
        portSSHIndex
            INTEGER,
        portSSHStatus
            RowStatus,
        portSSHPort
            INTEGER,
        portSSHHost
            DisplayString,
        portSSHTermType
            DisplayString,
        portSSHVerbose
            OnOffValue,
        portSSHCompression
            OnOffValue,
        portSSHAutoLogin
            OnOffValue,
        portSSHName
            DisplayString,
        portSSHProtocol
            INTEGER,
        portSSHRSA
            OnOffValue,
        portSSHDSA
            OnOffValue,
        portSSHKeyboard
            OnOffValue,
        portSSHCipherSSH1
            INTEGER,
        portSSHFirstSSH2Cipher
            INTEGER,
        portSSHSecondSSH2Cipher
            INTEGER,
        portSSHThirdSSH2Cipher
            INTEGER,
        portSSHFourthSSH2Cipher
            INTEGER,
        portSSHFifthSSH2Cipher
            INTEGER
  }

  portSSHIndex OBJECT-TYPE
      SYNTAX      INTEGER
      MAX-ACCESS  read-only
      STATUS      current
      DESCRIPTION
              "portSSHIndex"
      ::= { portSSHEntry 1}

  portSSHStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portSSHEntry 2}

  portSSHPort OBJECT-TYPE
      SYNTAX      INTEGER (0..65535)
      MAX-ACCESS  read-write
      STATUS      current
      DESCRIPTION
              "The port number the target host is listening on
               for incoming connections. The default is port 22."
      ::= { portSSHEntry 3}

  portSSHHost OBJECT-TYPE
      SYNTAX      DisplayString(SIZE(0..14))
      MAX-ACCESS  read-write
      STATUS      current
      DESCRIPTION
              "The name of the target host."
      ::= { portSSHEntry 4}

  portSSHTermType OBJECT-TYPE
      SYNTAX      DisplayString(SIZE(0..14))
      MAX-ACCESS  read-write
      STATUS      current
      DESCRIPTION
              "The type of terminal that will connecting via SSH."
      ::= { portSSHEntry 5}

  portSSHVerbose OBJECT-TYPE
      SYNTAX      OnOffValue
      MAX-ACCESS  read-write
      STATUS      current
      DESCRIPTION
              "Displays debug messages on the terminal."
      ::= { portSSHEntry 6}

  portSSHCompression OBJECT-TYPE
      SYNTAX      OnOffValue
      MAX-ACCESS  read-write
      STATUS      current
      DESCRIPTION
              "Requests compression of all data. Compression is desirable
               on modem lines and other slow connections, but will only
               slow down things on fast networks"
      ::= { portSSHEntry 7}

  portSSHAutoLogin OBJECT-TYPE
      SYNTAX      OnOffValue
      MAX-ACCESS  read-write
      STATUS      current
      DESCRIPTION
              "Creates an automatic SSH login, using the Name and Password values."
      ::= { portSSHEntry 8}

  portSSHName OBJECT-TYPE
      SYNTAX      DisplayString(SIZE(0..20))
      MAX-ACCESS  read-write
      STATUS      current
      DESCRIPTION
              "The name of the user logging into the SSH session."
      ::= { portSSHEntry 9}

  portSSHProtocol OBJECT-TYPE
      SYNTAX      INTEGER {
        ssh1(1),
        ssh2(2),
        sshBoth(3)
      }
      MAX-ACCESS  read-write
      STATUS      current
      DESCRIPTION
              "Specify the SSH client version that will be used
               for the SSH session."
      ::= { portSSHEntry 10}

  portSSHRSA OBJECT-TYPE
      SYNTAX      OnOffValue
      MAX-ACCESS  read-write
      STATUS      current
      DESCRIPTION
              "An authentication method used by SSH version 1 and 2.
               Use RSA authentication for the SSH session."
      ::= { portSSHEntry 11}

  portSSHDSA OBJECT-TYPE
      SYNTAX      OnOffValue
      MAX-ACCESS  read-write
      STATUS      current
      DESCRIPTION
              "An authentication method used by SSH version 2.
               Use DSA authentication for the SSH session."
      ::= { portSSHEntry 12}

  portSSHKeyboard OBJECT-TYPE
      SYNTAX      OnOffValue
      MAX-ACCESS  read-write
      STATUS      current
      DESCRIPTION
              "The user types in a password for authentication."
      ::= { portSSHEntry 13}

  portSSHCipherSSH1 OBJECT-TYPE
      SYNTAX      INTEGER {
              tripledes(1),
          blowfish(2)
        }
      MAX-ACCESS  read-write
      STATUS      current
      DESCRIPTION
              "Select the encryption method (cipher) that you
               want to use for your SSH version 1 connection:
               3DES or Blowfish"
      ::= { portSSHEntry 14}

  portSSHFirstSSH2Cipher OBJECT-TYPE
      SYNTAX      INTEGER {
        tripledes(1),
        blowfish(2),
        aes(3),
        cast(4),
        arcfour(5)
      }
      MAX-ACCESS  read-write
      STATUS      current
      DESCRIPTION
              "Select the first priority negotiation for the encryption
               method (ciphers) that the Device Server will use for
               the SSH version 2 connection:
               3DES, Blowfish, AES, CAST, or Arcfour"
      ::= { portSSHEntry 15}

  portSSHSecondSSH2Cipher OBJECT-TYPE
      SYNTAX      INTEGER {
        none(1),
        tripledes(2),
        blowfish(3),
        aes(4),
        cast(5),
        arcfour(6)
      }
      MAX-ACCESS  read-write
      STATUS      current
      DESCRIPTION
              "Select the second priority negotiation for the encryption
               method (ciphers) that the Device Server will use for
               the SSH version 2 connection:
               None, 3DES, Blowfish, AES, CAST, or Arcfour"
      ::= { portSSHEntry 16}

  portSSHThirdSSH2Cipher OBJECT-TYPE
      SYNTAX      INTEGER {
        none(1),
        tripledes(2),
        blowfish(3),
        aes(4),
        cast(5),
        arcfour(6)
      }
      MAX-ACCESS  read-write
      STATUS      current
      DESCRIPTION
              "Select the third priority negotiation for the encryption
               method (ciphers) that the Device Server will use for
               the SSH version 2 connection:
               None, 3DES, Blowfish, AES, CAST, or Arcfour"
      ::= { portSSHEntry 17}

  portSSHFourthSSH2Cipher OBJECT-TYPE
      SYNTAX      INTEGER {
        none(1),
        tripledes(2),
        blowfish(3),
        aes(4),
        cast(5),
        arcfour(6)
      }
      MAX-ACCESS  read-write
      STATUS      current
      DESCRIPTION
              "Select the fourth priority negotiation for the encryption
               method (ciphers) that the Device Server will use for
               the SSH version 2 connection:
               None, 3DES, Blowfish, AES, CAST, or Arcfour"
      ::= { portSSHEntry 18}

  portSSHFifthSSH2Cipher OBJECT-TYPE
      SYNTAX      INTEGER {
        none(1),
        tripledes(2),
        blowfish(3),
        aes(4),
        cast(5),
        arcfour(6)
      }
      MAX-ACCESS  read-write
      STATUS      current
      DESCRIPTION
              "Select the fifth priority negotiation for the encryption
               method (ciphers) that the Device Server will use for
               the SSH version 2 connection:
               None, 3DES, Blowfish, AES, CAST, or Arcfour"
      ::= { portSSHEntry 19}

-- Port PPP Table

  portPPPTable OBJECT-TYPE
      SYNTAX      SEQUENCE OF PortPPPEntry
      MAX-ACCESS  not-accessible
      STATUS      current
      DESCRIPTION
              "Port PPP Table."
      ::= { portInfo 5 }

  portPPPEntry OBJECT-TYPE
      SYNTAX      PortPPPEntry
      MAX-ACCESS  not-accessible
      STATUS      current
      DESCRIPTION
              "An entry in the portPPPEntry, each relating to a port."
      INDEX   { portPPPIndex }
      ::= { portPPPTable 1 }

  PortPPPEntry ::=
      SEQUENCE {
        portPPPIndex
            INTEGER,
        portPPPStatus
            RowStatus,
        portPPPLocalIpAddr
            IpAddress,
        portPPPRemoteIpAddr
            IpAddress,
        portPPPSubnetBits
            INTEGER,
        portPPPIpV6LocalIpAddr
            Ipv6InterfaceId,
        portPPPIpV6RemoteIpAddr
            Ipv6InterfaceId,
        portPPPAccm
            Hex32,
        portPPPMru
            INTEGER,
        portPPPSecurity
            INTEGER,
        portPPPUser
            DisplayString,
        portPPPRemoteUser
            DisplayString,
        portPPPACComp
            OnOffValue,
        portPPPProtoComp
            OnOffValue,
        portPPPVJComp
            OnOffValue,
        portPPPMagicNegotiation
            OnOffValue,
        portPPPIPAddrNegotiation
            OnOffValue,
        portPPPCRTimeout
            INTEGER,
        portPPPTRTimeout
            INTEGER,
        portPPPCRRetry
            INTEGER,
        portPPPTRRetry
            INTEGER,
        portPPPNakRetry
            INTEGER,
        portPPPAuthTimeout
            INTEGER,
        portPPPRoamingCallback
            OnOffValue,
        portPPPChallengInterval
            INTEGER,
        portPPPRouting
            INTEGER,
        portPPPDynamicDNSEnabled 
            OnOffValue,
        portPPPDynamicDNSHostname 
            DisplayString,
        portPPPDynamicDNSUserName
            DisplayString,
        portPPPDynamicDNSPassword
            DisplayString,
	portPPPDynamicDNSStatusString
            DisplayString,
       portPPPMSDirectConnection
       	INTEGER
      }

  portPPPIndex OBJECT-TYPE
      SYNTAX      INTEGER
      MAX-ACCESS  read-only
      STATUS      current
      DESCRIPTION
              "portPPPIndex"
      ::= { portPPPEntry 1}

  portPPPStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portPPPEntry 2}

  portPPPLocalIpAddr OBJECT-TYPE
      SYNTAX      IpAddress
      MAX-ACCESS  read-write
      STATUS      current
      DESCRIPTION
              "The IPV4 IP address of the Device Server end of the PPP
               link. For routing to work, you must enter a local IP
               address. Choose an address that is part of the same network
               or subnetwork as the remote end; for example, if the remote
               end is address 192.101.34.146, your local IP address can be
               192.101.34.145. Do not use the Device Server's (main) IP
               address in this field; if you do so, routing will not take
               place correctly."
      ::= { portPPPEntry 3}

  portPPPRemoteIpAddr OBJECT-TYPE
      SYNTAX      IpAddress
      MAX-ACCESS  read-write
      STATUS      current
      DESCRIPTION
              "The IPV4 IP address of the remote end of the PPP link. Choose an
               address that is part of the same network or subnetwork as the
               Device Server. If you set the PPP parameter IP Address Negotiation
               to On, the Device Server will ignore the remote IP address value
               you enter here and will allow the remote end to specify its IP
               address. If your user is authenticated by RADIUS and the RADIUS
               parameter Framed-Address is set in the RADIUS file, the Device
               Server will use the value in the RADIUS file in preference to the
               value configured here. The exception to this rule is a Framed-Address
               value in the RADIUS file of 255.255.255.254; this value allows the
               Device Server to use the remote IP address value configured here."
      ::= { portPPPEntry 4}

  portPPPSubnetBits OBJECT-TYPE
      SYNTAX      INTEGER (0..32)
      MAX-ACCESS  read-write
      STATUS      current
      DESCRIPTION
              "The number of bits in the subnet mask. For example, a subnet mask
               of 255.255.0.0 has 16 subnet/prefix bits. If your user is
               authenticated by RADIUS and the RADIUS parameter Framed-Netmask is
               set in the RADIUS file, the Device Server will use the value in the
               RADIUS file in preference to the value configured here."
      ::= { portPPPEntry 5}

  portPPPIpV6LocalIpAddr OBJECT-TYPE
      SYNTAX      Ipv6InterfaceId
      MAX-ACCESS  read-write
      STATUS      current
      DESCRIPTION
              "The local IPv6 interface identifier of the Device Server end of the
               PPP link. For routing to work, you must enter a local IP address.
               Choose an address that is part of the same network or subnetwork as
               the remote end. Do not use the Device Server's (main) IP address in
               this field; if you do so, routing will not take place correctly. The
               first 64 bits of the Interface Identifier must be zero, therefore,
               ::abcd:abcd:abcd:abcd is the expected format."
      ::= { portPPPEntry 6}

  portPPPIpV6RemoteIpAddr OBJECT-TYPE
      SYNTAX      Ipv6InterfaceId
      MAX-ACCESS  read-write
      STATUS      current
      DESCRIPTION
              "The remote IPv6 interface identifier of the remote end of the PPP link.
               Choose an address that is part of the same network or subnetwork as the
               Device Server. If you set the PPP parameter IP Address Negotiation to On,
               the Device Server will ignore the remote IP address value you enter here
               and will allow the remote end to specify its IP address. If your user is
               authenticated by RADIUS and the RADIUS parameter Framed-Interface-ID is
               set in the RADIUS file, the Device Server will use the value in the RADIUS
               file in preference to the value configured here. The first 64 bits of the
               Interface Identifier must be zero, therefore, ::abcd:abcd:abcd:abcd is the
               expected format."
      ::= { portPPPEntry 7}

  portPPPAccm OBJECT-TYPE
      SYNTAX      Hex32
      MAX-ACCESS  read-write
      STATUS      current
      DESCRIPTION
              "Specifies the ACCM (Asynchronous Control Character Map) characters that
               should be escaped from the data stream. This is entered as a 32-bit
               hexadecimal number with each bit specifying whether or not the corresponding
               character should be escaped. The bits are specified as the most significant
               bit first and are numbered 31-0. Thus if bit 17 is set, the 17th character
               should be escaped, that is, 0x11 (XON). So entering the value 000a0000 will
               cause the control characters 0x11 (XON) and 0x13 (XOFF) to be escaped on the
               link, thus allowing the use of XON/XOFF (software) flow control. If you have
               selected Soft Flow Control on the Line, you must enter a value of 000a0000
               for the ACCM. The default value is 00000000, which means no characters will
               be escaped."
      ::= { portPPPEntry 8}

  portPPPMru OBJECT-TYPE
      SYNTAX      INTEGER (64..1500)
      MAX-ACCESS  read-write
      STATUS      current
      DESCRIPTION
              "The Maximum Receive Unit (MRU) parameter specifies the maximum size of PPP
               packets that the Device Server's port will accept. Enter a value between
               64 and 1500 bytes; for example, 512. The default value is 1500. If your
               user is authenticated by the Device Server, the MRU value will be overridden
               if you have set a Framed MTU value for the user. If your user is authenticated
               by RADIUS and the RADIUS parameter Framed-MTU is set in the RADIUS file, the
               Device Server will use the value in the RADIUS file in preference to the
               value configured here."
      ::= { portPPPEntry 9}

  portPPPSecurity OBJECT-TYPE
      SYNTAX      INTEGER {
        none(1),
        pap(2),
        chap(3)
      }
      MAX-ACCESS  read-write
      STATUS      current
      DESCRIPTION
              "The type of authentication that will be done on the link: None, PAP, or CHAP.
               The default is CHAP. You can use PAP or CHAP to authenticate a port or user
               on the Device Server, from a remote location, or authenticate a remote
               client/device, from the Device Server. PAP is a one time challenge of a
               client/device requiring that it respond with a valid username and password.
               A timer operates during which successful authentication must take place. If
               the timer expires before the remote end has been authenticated successfully,
               the link will be terminated. CHAP challenges a client/device at regular
               intervals to validate itself with a username and a response, based on a hash
               of the secret (password). A timer operates during which successful
               authentication must take place. If the timer expires before the remote end
               has been authenticated successfully, the link will be terminated. When
               setting either PAP and CHAP, make sure the Device Server and the remote
               client/device have the same setting. For example, if the Device Server is set
               to PAP, but the remote end is set to CHAP, the connection will be refused. "
      ::= { portPPPEntry 10}

  portPPPUser OBJECT-TYPE
      SYNTAX      DisplayString(SIZE(0..8))
      MAX-ACCESS  read-write
      STATUS      current
      DESCRIPTION
              "Complete this field only if you have specified PAP or CHAP (security
               protocols) in the Security field, and you wish to dedicate this line
               to a single remote user, who will be authenticated by the Device Server,
               or you are using the Device Server as a router (back-to-back with
               another Device Server). When Dial is set to Out or Both, the User is the
               name the remote device will use to authenticate a port on this Device Server.
               The remote device will only authenticate your Device Server's port when PAP
               or CHAP are operating. You can enter a maximum of sixteen alphanumeric
               characters; for example, tracy201. When connecting together two networks,
               enter a dummy user name; for example, DS_HQ.
               Note If you want a reasonable level of security, the user name and password
               should not be similar to a user name or password used regularly to login to
               the Device Server. External authentication can not be used for this user."
      ::= { portPPPEntry 11}

  portPPPRemoteUser OBJECT-TYPE
      SYNTAX      DisplayString(SIZE(0..8))
      MAX-ACCESS  read-write
      STATUS      current
      DESCRIPTION
              "Complete this field only if you have specified PAP or CHAP (security protocols)
               in the Security field, and you wish to dedicate this line to a single remote
               user, who will be authenticated by the Device Server, or you are using the
               Device Server as a router (back-to-back with another Device Server) When Dial
               is set to In or Both, the Remote User is the name the Device Server will use
               to authenticate the port on the remote device. Your Device Server will only
               authenticate the port on the remote device when PAP or CHAP are operating.
               You can enter a maximum of sixteen alphanumeric characters. When connecting
               together two networks, enter a dummy user name; for example, DS_SALES.
               Note If you want a reasonable level of security, the user name and password
               should not be similar to a user name or password used regularly to login to
               the Device Server. This option does not work with external authentication."
      ::= { portPPPEntry 12}

  portPPPACComp OBJECT-TYPE
      SYNTAX      OnOffValue
      MAX-ACCESS  read-write
      STATUS      current
      DESCRIPTION
              "This determines whether compression of the PPP Address and Control fields
               take place on the link. The default is On. For most applications this should
               be enabled."
      ::= { portPPPEntry 13}

  portPPPProtoComp OBJECT-TYPE
      SYNTAX      OnOffValue
      MAX-ACCESS  read-write
      STATUS      current
      DESCRIPTION
              "This determines whether compression of the PPP Protocol field takes
               place on this link. The default is On."
      ::= { portPPPEntry 14}

  portPPPVJComp OBJECT-TYPE
      SYNTAX      OnOffValue
      MAX-ACCESS  read-write
      STATUS      current
      DESCRIPTION
              "This determines whether Van Jacobson Compression is used on this link.
               The default is On. If your user is authenticated by the Device Server,
               this VJ compression value will be overridden if you have set the User
               Framed Compression On. If your user is authenticated by RADIUS and the
               RADIUS parameter Framed-Compression is set in the RADIUS file, the
               Device Server will use the value in the RADIUS file in preference to
               the value configured here."
      ::= { portPPPEntry 15}

  portPPPMagicNegotiation OBJECT-TYPE
      SYNTAX      OnOffValue
      MAX-ACCESS  read-write
      STATUS      current
      DESCRIPTION
              "Determines if a line is looping back. If enabled (On), random
               numbers are sent on the link. The random numbers should be
               different, unless the link loops back. The default is Off. "
      ::= { portPPPEntry 16}

  portPPPIPAddrNegotiation OBJECT-TYPE
      SYNTAX      OnOffValue
      MAX-ACCESS  read-write
      STATUS      current
      DESCRIPTION
              "Specifies whether or not IP address negotiation will take place.
               IP address negotiation is where the Device Server allows the
               remote end to specify its IP address. The default value is Off.
               When On, the IP address specified by the remote end will be used
               in preference to the Remote IP Address set for a Line. When Off,
               the Remote IP Address set for the Line will be used. "
      ::= { portPPPEntry 17}

  portPPPCRTimeout OBJECT-TYPE
      SYNTAX      INTEGER (1..255)
      MAX-ACCESS  read-write
      STATUS      current
      DESCRIPTION
              "The maximum time, in seconds, that LCP (Link Control Protocol)
               will wait before it considers a configure request packet to have
               been lost."
      ::= { portPPPEntry 18}

  portPPPTRTimeout OBJECT-TYPE
      SYNTAX      INTEGER (1..255)
      MAX-ACCESS  read-write
      STATUS      current
      DESCRIPTION
              "The maximum time, in seconds, that LCP (Link Control Protocol)
               will wait before it considers a terminate request packet to have
               been lost."
      ::= { portPPPEntry 19}

  portPPPCRRetry OBJECT-TYPE
      SYNTAX      INTEGER (0..255)
      MAX-ACCESS  read-write
      STATUS      current
      DESCRIPTION
              "The maximum number of times a configure request packet will
               be sent before the link is terminated."
      ::= { portPPPEntry 20}

  portPPPTRRetry OBJECT-TYPE
      SYNTAX      INTEGER (0..255)
      MAX-ACCESS  read-write
      STATUS      current
      DESCRIPTION
              "The maximum number of times a terminate request packet will
               be sent before the link is terminated."
      ::= { portPPPEntry 21}

  portPPPNakRetry OBJECT-TYPE
      SYNTAX      INTEGER (0..255)
      MAX-ACCESS  read-write
      STATUS      current
      DESCRIPTION
              "The maximum number of times a configure NAK packet will
               be sent before the link is terminated."
      ::= { portPPPEntry 22}

  portPPPAuthTimeout OBJECT-TYPE
      SYNTAX      INTEGER (1..255)
      MAX-ACCESS  read-write
      STATUS      current
      DESCRIPTION
              "The timeout, in minutes, during which successful PAP or
               CHAP authentication must take place (when PAP or CHAP is
               turned On). If the timer expires before the remote end has
               been authenticated successfully, the link will be terminated."
      ::= { portPPPEntry 23}

  portPPPRoamingCallback OBJECT-TYPE
      SYNTAX      OnOffValue
      MAX-ACCESS  read-write
      STATUS      current
      DESCRIPTION
              "A user can enter a telephone number that the Device Server
               will use to callback him/her. This feature is particularly
               useful for a mobile user. Roaming callback can only work when
               the User Callback parameter is set to On. Roaming callback
               therefore overrides (fixed) User Callback.To use Roaming
               Callback, the remote end must be a Microsoft Windows OS that
               supports Microsoft's Callback Control Protocol (CBCP). The user
               is allowed 30 seconds to enter a telephone number after which
               the Device Server ends the call. The default is Off."
      ::= { portPPPEntry 24}

  portPPPChallengInterval OBJECT-TYPE
      SYNTAX      INTEGER (0..255)
      MAX-ACCESS  read-write
      STATUS      current
      DESCRIPTION
              "The interval, in minutes, for which the Device Server will
               issue a CHAP re-challenge to the remote end. During CHAP
               authentication, an initial CHAP challenge takes place, and
               is unrelated to CHAP re-challenges. The initial challenge takes
               place even if re-challenges are disabled. Some PPP client software
               does not work with CHAP re-challenges, so you might want to leave
               the parameter disabled in the Device Server. The default value
               is 0 (zero), meaning CHAP re-challenge is disabled. "
      ::= { portPPPEntry 25}

   portPPPRouting OBJECT-TYPE
      SYNTAX      INTEGER {
        none(1),
        send(2),
        listen(3),
        sendAndListen(4)
      }
      MAX-ACCESS  read-write
      STATUS      current
      DESCRIPTION
              "Determines the routing mode (RIP, Routing Information Protocol)
               used on the PPP interface as one of the following options:
               None-Disables RIP over the PPP/SLIP interface.
               Send-Sends RIP over the PPP/SLIP interface.
               Listen-Listens for RIP over the PPP/SLIP interface.
               Send and Listen-Sends RIP and listens for RIP over the PPP/SLIP interface.
               This is the same function as the Framed-Routing attribute for
               RADIUS authenticated users. Default is None."
      ::= { portPPPEntry 26}

  portPPPDynamicDNSEnabled OBJECT-TYPE
      SYNTAX      OnOffValue
      MAX-ACCESS  read-write
      STATUS      current
      DESCRIPTION
              "Enable/disable dynamic DNS."
      ::= { portPPPEntry 27}

  portPPPDynamicDNSHostname OBJECT-TYPE
      SYNTAX      DisplayString(SIZE(1..14))
      MAX-ACCESS  read-write
      STATUS      current
      DESCRIPTION
              "Host name."
      ::= { portPPPEntry 28}
      
  portPPPDynamicDNSUserName OBJECT-TYPE
      SYNTAX      DisplayString(SIZE(1..16))
      MAX-ACCESS  read-write
      STATUS      current
      DESCRIPTION
              "user name."
      ::= { portPPPEntry 29}
      
  portPPPDynamicDNSPassword OBJECT-TYPE
      SYNTAX      DisplayString(SIZE(1..16))
      MAX-ACCESS  read-write
      STATUS      current
      DESCRIPTION
              "Password."
      ::= { portPPPEntry 30}
      
   portPPPDynamicDNSStatusString OBJECT-TYPE
      SYNTAX      DisplayString(SIZE(1..1024))
      MAX-ACCESS  read-write
      STATUS      current
      DESCRIPTION
              "Dynamic Dns Status"
      ::= { portPPPEntry 31}
      
    portPPPMSDirectConnection OBJECT-TYPE
      SYNTAX      INTEGER {
       disable(1),
       server(2),
       client(3)
      }
      MAX-ACCESS  read-write
      STATUS      current
      DESCRIPTION
              "Set for Microsoft ppp connection working mode"
      ::= { portPPPEntry 32}  
-- Port Slip Table

  portSLIPTable OBJECT-TYPE
      SYNTAX      SEQUENCE OF PortSLIPEntry
      MAX-ACCESS  not-accessible
      STATUS      current
      DESCRIPTION
              "Port SLIP Table."
      ::= { portInfo 6 }

  portSLIPEntry OBJECT-TYPE
      SYNTAX      PortSLIPEntry
      MAX-ACCESS  not-accessible
      STATUS      current
      DESCRIPTION
              "An entry in the portSLIPEntry, each relating to a port."
      INDEX   { portSLIPIndex }
      ::= { portSLIPTable 1 }

  PortSLIPEntry ::=
      SEQUENCE {
        portSLIPIndex
            INTEGER,
        portSlipStatus
            RowStatus,
        portSLIPLocalIpAddress
            IpAddress,
        portSLIPRemoteIpAddress
            IpAddress,
        portSLIPSubnetBits
            INTEGER,
        portSLIPMtu
            INTEGER,
        portSLIPVJComp
            OnOffValue,
        portSLIPRouting
            INTEGER
      }

  portSLIPIndex OBJECT-TYPE
      SYNTAX      INTEGER
      MAX-ACCESS  read-write
      STATUS      current
      DESCRIPTION
              "portSLIPIndex"
      ::= { portSLIPEntry 1}

  portSlipStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portSLIPEntry 2}

  portSLIPLocalIpAddress OBJECT-TYPE
      SYNTAX      IpAddress
      MAX-ACCESS  read-write
      STATUS      current
      DESCRIPTION
              "The IPv4 address of the Device Server end of the SLIP
               link. For routing to work you must enter an IP address
               in this field. Choose an address that is part of the same
               network or subnetwork as the remote end; for example, if
               the remote end is address 192.101.34.146, your local IP
               address can be 192.101.34.145. Do not use the Device Server's
               (main) IP address in this field; if you do so, routing will not
               take place correctly."
      ::= { portSLIPEntry 3}

  portSLIPRemoteIpAddress OBJECT-TYPE
      SYNTAX      IpAddress
      MAX-ACCESS  read-write
      STATUS      current
      DESCRIPTION
              "The IPv4 address of the remote end of the SLIP link. Choose
               an address that is part of the same network or subnetwork as
               the Device Server. If your user is authenticated by the Device
               Server, this remote IP address will be overridden if you have
               set a Framed IP Address for the user. If your user is authenticated
               by RADIUS and the RADIUS parameter Framed-Address is set in the
               RADIUS file, the Device Server will use the value in the RADIUS
               file in preference to the value configured here."
      ::= { portSLIPEntry 4}

  portSLIPSubnetBits OBJECT-TYPE
      SYNTAX      INTEGER (0..32)
      MAX-ACCESS  read-write
      STATUS      current
      DESCRIPTION
              "The number of bits in the subnet mask. For example,
               a subnet mask of 255.255.0.0 has 16 subnet/prefix bits.
               If your user is authenticated by RADIUS and the RADIUS
               parameter Framed-Netmask is set in the RADIUS file, the
               Device Server will use the value in the RADIUS file in
               preference to the value configured here."
      ::= { portSLIPEntry 5}

  portSLIPMtu OBJECT-TYPE
      SYNTAX      INTEGER (256..1006)
      MAX-ACCESS  read-write
      STATUS      current
      DESCRIPTION
              "The Maximum Transmission Unit (MTU) parameter restricts
               the size of individual SLIP packets being sent by the
               Device Server. Enter a value between 256 and 1006 bytes;
               for example, 512. The default value is 256. If your user
               is authenticated by the Device Server, this MTU value will
               be overridden when you have set a Framed MTU value for the
               user. If your user is authenticated by RADIUS and the
               RADIUS parameter Framed-MTU is set in the RADIUS file, the
               Device Server will use the value in the RADIUS file in
               preference to the value configured here."
      ::= { portSLIPEntry 6}

  portSLIPVJComp OBJECT-TYPE
      SYNTAX      OnOffValue
      MAX-ACCESS  read-write
      STATUS      current
      DESCRIPTION
              "This determines whether Van Jacobson compression is used
               on this link; that is, whether you are using SLIP or
               C-SLIP (compressed SLIP). The choices are On (C-SLIP) or
               Off (SLIP). The default is On. C-SLIP greatly improves
               the performance of interactive traffic, such as Telnet
               or Rlogin. If your user is authenticated by the Device
               Server, this VJ compression value will be overridden if
               you have set a Framed Compression value for a user. If
               your user is authenticated by RADIUS and the RADIUS
               parameter Framed-Compression is set in the RADIUS file,
               the Device Server will use the value in the RADIUS file
               in preference to the value configured here."
      ::= { portSLIPEntry 7}

   portSLIPRouting OBJECT-TYPE
      SYNTAX      INTEGER {
        none(1),
        send(2),
        listen(3),
        sendAndListen(4)
      }
      MAX-ACCESS  read-write
      STATUS      current
      DESCRIPTION
              "Determines the routing mode (RIP, Routing Information Protocol)
               used on the SLIP interface as one of the following options:
               None-Disables RIP over the PPP/SLIP interface.
               Send-Sends RIP over the PPP/SLIP interface.
               Listen-Listens for RIP over the PPP/SLIP interface.
               Send and Listen-Sends RIP and listens for RIP over the PPP/SLIP interface.
               This is the same function as the Framed-Routing attribute for
               RADIUS authenticated users. Default is None."
      ::= { portSLIPEntry 8}

-- Port UDP Table

  portUDPTable OBJECT-TYPE
      SYNTAX      SEQUENCE OF PortUDPEntry
      MAX-ACCESS  not-accessible
      STATUS      current
      DESCRIPTION
              "Port UDP Table."
      ::= { portInfo 7 }

  portUDPEntry OBJECT-TYPE
      SYNTAX      PortUDPEntry
      MAX-ACCESS  not-accessible
      STATUS      current
      DESCRIPTION
              "An entry in the portUDPEntry, each relating to a port."
      INDEX   { portUDPIndex, portUDPEntryNumber }
      ::= { portUDPTable 1 }

  PortUDPEntry ::=
      SEQUENCE {
        portUDPIndex
            INTEGER,
        portUDPEntryNumber
            INTEGER,
        portUDPStatus
            RowStatus,
        portUDPStartAddress
            Ipv4v6Address,
        portUDPEndAddress
            Ipv4v6Address,
        portUDPPort
            INTEGER,
        portUDPDirection
            INTEGER,
        portUDPOption
            INTEGER
        }

  portUDPIndex OBJECT-TYPE
      SYNTAX      INTEGER
      MAX-ACCESS  read-only
      STATUS      current
      DESCRIPTION
              "portUDPIndex"
      ::= { portUDPEntry 1}

  portUDPEntryNumber OBJECT-TYPE
      SYNTAX      INTEGER
      MAX-ACCESS  read-only
      STATUS      current
      DESCRIPTION
              "portUDPNumber"
      ::= { portUDPEntry 2}

  portUDPStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portUDPEntry 3}

  portUDPStartAddress OBJECT-TYPE
      SYNTAX      Ipv4v6Address
      MAX-ACCESS  read-write
      STATUS      current
      DESCRIPTION
              "The first host IP address in the range of IP addresses
               (for IPV4 or IPV6) that the Device Server will listen for
               messages from and/or send messages to"
      ::= { portUDPEntry 4}

  portUDPEndAddress OBJECT-TYPE
      SYNTAX      Ipv4v6Address
      MAX-ACCESS  read-write
      STATUS      current
      DESCRIPTION
              "The last host IP address in the range of IP addresses (for
               IPV4, not required for IPV6) that the Device Server will listen
               for messages from and/or send messages to."
      ::= { portUDPEntry 5}

  portUDPPort OBJECT-TYPE
      SYNTAX      INTEGER(0..65535)
      MAX-ACCESS  read-write
      STATUS      current
      DESCRIPTION
              "The port that the Device Server will use to receive messages
               from or relay messages to servers/hosts."
      ::= { portUDPEntry 6}

  portUDPDirection OBJECT-TYPE
      SYNTAX      INTEGER {
        none(1),
        in(2),
        out(3),
        both(4)
      }
      MAX-ACCESS  read-write
      STATUS      current
      DESCRIPTION
              "The direction in which information is received or relayed:
               None-UDP service not enabled.
               In-LAN to serial.
               Out-Serial to LAN.
               Both-Messages are relayed both directions."
      ::= { portUDPEntry 7}

    portUDPOption OBJECT-TYPE
      SYNTAX      INTEGER {
        specificOrAutoLearn(1),
        anyPort(2)
      }
      MAX-ACCESS  read-write
      STATUS      current
      DESCRIPTION
              "when want udp port be any port which only valid for lan to serial direction set this to 2, 
               others for auto lean udp port and specific port set this to 1"
      ::= { portUDPEntry 8}
-- Port Vmodem Table

  portVmodemTable OBJECT-TYPE
      SYNTAX      SEQUENCE OF PortVmodemEntry
      MAX-ACCESS  not-accessible
      STATUS      current
      DESCRIPTION
              "Port Vmodem Table."
      ::= { portInfo 8 }

  portVmodemEntry OBJECT-TYPE
      SYNTAX      PortVmodemEntry
      MAX-ACCESS  not-accessible
      STATUS      current
      DESCRIPTION
              "An entry in the portVmodemEntry, each relating to a port."
      INDEX   { portVmodemIndex }
      ::= { portVmodemTable 1 }

  PortVmodemEntry ::=
      SEQUENCE {
        portVmodemIndex
            INTEGER,
        portVmodemStatus
            RowStatus,
        portVmodemHost
            DisplayString,
        portVmodemPort
            INTEGER,
        portVmodemSuccessString
            DisplayString,
        portVmodemFailureString
            DisplayString,
        portVmodemSuppress
            OnOffValue,
        portVmodemStyle
            INTEGER,
        portVmodemResponseDelay
            INTEGER,
        portVmodemEcho
            OnOffValue,
        portVmodemMode
            INTEGER,
        portVmodemDCD
            INTEGER,
        portVmodemRTS
            INTEGER,
        portVmodemDTR
            INTEGER,
        portVmodemInitString
            DisplayString
        }

  portVmodemIndex OBJECT-TYPE
      SYNTAX      INTEGER
      MAX-ACCESS  read-only
      STATUS      current
      DESCRIPTION
              "portVmodemIndex"
      ::= { portVmodemEntry 1}

  portVmodemStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portVmodemEntry 2}

  portVmodemHost OBJECT-TYPE
      SYNTAX      DisplayString(SIZE(0..14))
      MAX-ACCESS  read-write
      STATUS      current
      DESCRIPTION
              "The target host name."
      ::= { portVmodemEntry 3}

  portVmodemPort OBJECT-TYPE
      SYNTAX      INTEGER (0..65535)
      MAX-ACCESS  read-write
      STATUS      current
      DESCRIPTION
              "The port number the target host is listening on for messages."
      ::= { portVmodemEntry 4}

  portVmodemSuccessString OBJECT-TYPE
      SYNTAX      DisplayString(SIZE(0..40))
      MAX-ACCESS  read-write
      STATUS      current
      DESCRIPTION
              "String that is sent to the serial device when a connection
               succeeds. If no string is entered, then the string CONNECT
               will be sent with the connecting speed, for example CONNECT 9600."
      ::= { portVmodemEntry 5}

  portVmodemFailureString OBJECT-TYPE
      SYNTAX      DisplayString(SIZE(0..30))
      MAX-ACCESS  read-write
      STATUS      current
      DESCRIPTION
              "String that is sent to the serial device when a connection fails.
               If no string is entered, then the string NO CARRIER will be sent."
      ::= { portVmodemEntry 6}

  portVmodemSuppress OBJECT-TYPE
      SYNTAX      OnOffValue
      MAX-ACCESS  read-write
      STATUS      current
      DESCRIPTION
              "If set to No, connection success/failure indication strings are
               sent to the connected device, otherwise these indications
               are suppressed."
      ::= { portVmodemEntry 7}

  portVmodemStyle OBJECT-TYPE
      SYNTAX      INTEGER {
        numeric(1),
        verbose(2)
      }
      MAX-ACCESS  read-write
      STATUS      current
      DESCRIPTION
              "One of the following:
               Verbose-Return codes (strings) are sent to the connected device.
               Numeric-The following characters can be sent to the connected device:
                 1  Successfully Connected
                 2  Failed to Connect
                 4  Error"
      ::= { portVmodemEntry 8}

  portVmodemResponseDelay OBJECT-TYPE
      SYNTAX      INTEGER (0..999)
      MAX-ACCESS  read-write
      STATUS      current
      DESCRIPTION
              "The Vmodem delay to response, in milliseconds, default is 250."
      ::= { portVmodemEntry 9}

  portVmodemEcho OBJECT-TYPE
      SYNTAX      OnOffValue
      MAX-ACCESS  read-write
      STATUS      current
      DESCRIPTION
              "If set to on, vmodem will echo input."
      ::= { portVmodemEntry 10}
  portVmodemMode OBJECT-TYPE
      SYNTAX      INTEGER {
        auto(1),
        manual(2)
      }
      MAX-ACCESS  read-write
      STATUS      current
      DESCRIPTION
              "In auto mode vmodem will automaticall use the host and port make connection,
              otherwise will wait for use input"
      ::= { portVmodemEntry 11}     

  portVmodemDCD OBJECT-TYPE
      SYNTAX      INTEGER {
        alwaysHigh(1),
        followConnection(2)
      }
      MAX-ACCESS  read-write
      STATUS      current
      DESCRIPTION
              "Define the behavior of DCD"
      ::= { portVmodemEntry 12}     

  portVmodemRTS OBJECT-TYPE
      SYNTAX      INTEGER {
        alwaysHigh(1),
        representDCD(4),
        representRI(5)
      }
      MAX-ACCESS  read-write
      STATUS      current
      DESCRIPTION
              "Define the behavior of signal RTS"
      ::= { portVmodemEntry 13}    

  portVmodemDTR OBJECT-TYPE
      SYNTAX      INTEGER {
        alwaysHigh(1),
        representDCD(3),
        representRI(4)
      }
      MAX-ACCESS  read-write
      STATUS      current
      DESCRIPTION
              "Define the behavior of signal DTR"
      ::= { portVmodemEntry 14}   

   portVmodemInitString OBJECT-TYPE
      SYNTAX      DisplayString(SIZE(0..255))
      MAX-ACCESS  read-write
      STATUS      current
      DESCRIPTION
              "String that used as initial AT commands."
      ::= { portVmodemEntry 15}


  portRawTable OBJECT-TYPE
      SYNTAX      SEQUENCE OF PortRawEntry
      MAX-ACCESS  not-accessible
      STATUS      current
      DESCRIPTION
              "Port Raw Table."
      ::= { portInfo 9 }

  portRawEntry OBJECT-TYPE
      SYNTAX      PortRawEntry
      MAX-ACCESS  not-accessible
      STATUS      current
      DESCRIPTION
              "An entry in the portRawEntry, each relating to a port."
      INDEX   { portRawIndex }
      ::= { portRawTable 1 }

  PortRawEntry ::=
      SEQUENCE {
        portRawIndex
            INTEGER,
        portRawStatus
            RowStatus,
        portRawPort
            INTEGER,
        portRawHost
            DisplayString
        }

  portRawIndex OBJECT-TYPE
      SYNTAX      INTEGER
      MAX-ACCESS  read-only
      STATUS      current
      DESCRIPTION
              "Index of the corresponding serial port."
      ::= { portRawEntry 1}

  portRawStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portRawEntry 2}

  portRawPort OBJECT-TYPE
      SYNTAX      INTEGER (0..65535)
      MAX-ACCESS  read-write
      STATUS      current
      DESCRIPTION
              "The port number the target host is listening on for incoming connections."
      ::= { portRawEntry 3}

  portRawHost OBJECT-TYPE
      SYNTAX      DisplayString (SIZE(0..14))
      MAX-ACCESS  read-write
      STATUS      current
      DESCRIPTION
              "The name of the target host."
      ::= { portRawEntry 4}

-- Port Bidir Table

  portBidirTable OBJECT-TYPE
      SYNTAX      SEQUENCE OF PortBidirEntry
      MAX-ACCESS  not-accessible
      STATUS      current
      DESCRIPTION
              "Port Bidir Table."
      ::= { portInfo 10 }

  portBidirEntry OBJECT-TYPE
      SYNTAX      PortBidirEntry
      MAX-ACCESS  not-accessible
      STATUS      current
      DESCRIPTION
              "An entry in the portBidirEntry, each relating to a port."
      INDEX   { portBidirIndex }
      ::= { portBidirTable 1 }

  PortBidirEntry ::=
      SEQUENCE {
        portBidirIndex
            INTEGER,
        portBidirStatus
            RowStatus,
        portBidirPort
            INTEGER,
        portBidirHost
            DisplayString
        }

  portBidirIndex OBJECT-TYPE
      SYNTAX      INTEGER
      MAX-ACCESS  read-only
      STATUS      current
      DESCRIPTION
              "portBidirIndex"
      ::= { portBidirEntry 1}

  portBidirStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portBidirEntry 2}

  portBidirPort OBJECT-TYPE
      SYNTAX      INTEGER (0..65535)
      MAX-ACCESS  read-write
      STATUS      current
      DESCRIPTION
              "The port number the target host is listening on for incoming connections."
      ::= { portBidirEntry 3}

  portBidirHost OBJECT-TYPE
      SYNTAX      DisplayString(SIZE(0..14))
      MAX-ACCESS  read-write
      STATUS      current
      DESCRIPTION
              "The name of the target host."
      ::= { portBidirEntry 4}

-- Port Rlogin Table

  portRloginTable OBJECT-TYPE
      SYNTAX      SEQUENCE OF PortRloginEntry
      MAX-ACCESS  not-accessible
      STATUS      current
      DESCRIPTION
              "Port Rlogin Table."
      ::= { portInfo 11 }

  portRloginEntry OBJECT-TYPE
      SYNTAX      PortRloginEntry
      MAX-ACCESS  not-accessible
      STATUS      current
      DESCRIPTION
              "An entry in the portRloginEntry, each relating to a port."
      INDEX   { portRloginIndex }
      ::= { portRloginTable 1 }

  PortRloginEntry ::=
      SEQUENCE {
        portRloginIndex
            INTEGER,
        portRloginStatus
            RowStatus,
        portRloginHost
            DisplayString,
        portRloginTermType
            DisplayString
        }

  portRloginIndex OBJECT-TYPE
      SYNTAX      INTEGER
      MAX-ACCESS  read-only
      STATUS      current
      DESCRIPTION
              "Index of the corresponding serial port."
      ::= { portRloginEntry 1}

  portRloginStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portRloginEntry 2}

  portRloginHost OBJECT-TYPE
      SYNTAX      DisplayString(SIZE(0..14))
      MAX-ACCESS  read-write
      STATUS      current
      DESCRIPTION
              "The name of the target host."
      ::= { portRloginEntry 3}

  portRloginTermType OBJECT-TYPE
      SYNTAX      DisplayString(SIZE(0..14))
      MAX-ACCESS  read-write
      STATUS      current
      DESCRIPTION
              "Type of terminal attached to this line; for
               example, ANSI or WYSE60."
      ::= { portRloginEntry 4}

-- Port Email Table

  portEmailTable OBJECT-TYPE
      SYNTAX      SEQUENCE OF PortEmailEntry
      MAX-ACCESS  not-accessible
      STATUS      current
      DESCRIPTION
              "Port Email Table."
      ::= { portInfo 12 }

  portEmailEntry OBJECT-TYPE
      SYNTAX      PortEmailEntry
      MAX-ACCESS  not-accessible
      STATUS      current
      DESCRIPTION
              "An entry in the portEmailEntry, each relating to a port."
      INDEX   { portEmailIndex }
      ::= { portEmailTable 1 }

  PortEmailEntry ::=
      SEQUENCE {
        portEmailIndex
            INTEGER,
         portEmailStatus
            RowStatus,
        portEmailActive
            OnOffValue,
         portEmailUseDefault
            OnOffValue,
         portEmailLevel
            INTEGER,
         portEmailTo
            DisplayString,
         portEmailFrom
            DisplayString,
         portEmailSMTPHost
            DisplayString,
         portEmailReply
            DisplayString,
         portEmailSubject
            DisplayString
        }

  portEmailIndex OBJECT-TYPE
      SYNTAX      INTEGER
      MAX-ACCESS  read-only
      STATUS      current
      DESCRIPTION
              "Index of the corresponding serial port."
      ::= { portEmailEntry 1}

  portEmailStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portEmailEntry 2}

   portEmailActive OBJECT-TYPE
      SYNTAX      OnOffValue
      MAX-ACCESS  read-write
      STATUS      current
      DESCRIPTION
              "Determines whether or not email notification
               is turned on. Default is Off."
      ::= { portEmailEntry 3}

   portEmailUseDefault OBJECT-TYPE
      SYNTAX      OnOffValue
      MAX-ACCESS  read-write
      STATUS      current
      DESCRIPTION
              "Determines whether you want the Line to inherit
               the Email Alert settings from the Server Email
               Alert. If this is enabled, Server and Line
               notification events will have the same Email Alert setting."
      ::= { portEmailEntry 4}

   portEmailLevel OBJECT-TYPE
      SYNTAX      INTEGER {
        emergency(1),
        alert(2),
        crticial(3),
        error(4),
        warning(5),
        notice(6),
        informational(7),
        debug(8)
      }
      MAX-ACCESS  read-write
      STATUS      current
      DESCRIPTION
              "Choose the event level that triggers an email notification:
               Emergency, Alert, Critical, Error, Warning, Notice, Info, or
               Debug. You are selecting the lowest notification level;
               therefore, when you select Debug, you will get an email
               notification for all events that trigger a message."
      ::= { portEmailEntry 5}

   portEmailTo OBJECT-TYPE
      SYNTAX      DisplayString(SIZE(0..64))
      MAX-ACCESS  read-write
      STATUS      current
      DESCRIPTION
              "An email address or list of email addresses that will
               receive the email notification."
      ::= { portEmailEntry 6}

   portEmailFrom OBJECT-TYPE
      SYNTAX      DisplayString(SIZE(0..32))
      MAX-ACCESS  read-write
      STATUS      current
      DESCRIPTION
              "This field can contain an email address that might
               identify the Device Server name or some other value."
      ::= { portEmailEntry 7}

   portEmailSMTPHost OBJECT-TYPE
      SYNTAX      DisplayString(SIZE(0..24))
      MAX-ACCESS  read-write
      STATUS      current
      DESCRIPTION
              "The SMTP host (email server) that will process the
               email notification request. This can be either a host
               name defined in the Device Server host table or the
               SMTP host IP address."
      ::= { portEmailEntry 8}

   portEmailReply OBJECT-TYPE
      SYNTAX      DisplayString(SIZE(0..32))
      MAX-ACCESS  read-write
      STATUS      current
      DESCRIPTION
              "The email address to whom all replies to the email
               notification should go."
      ::= { portEmailEntry 9}

   portEmailSubject OBJECT-TYPE
      SYNTAX      DisplayString(SIZE(0..48))
      MAX-ACCESS  read-write
      STATUS      current
      DESCRIPTION
              "A text string, which can contain spaces, that will
               display in the Subject field of the email notification."
      ::= { portEmailEntry 10}

-- Port SSL Info

  portSSLTable OBJECT-TYPE
      SYNTAX      SEQUENCE OF PortSSLEntry
      MAX-ACCESS  not-accessible
      STATUS      current
      DESCRIPTION
              "Port SSL Table."
      ::= { portInfo 13 }

  portSSLEntry OBJECT-TYPE
      SYNTAX      PortSSLEntry
      MAX-ACCESS  not-accessible
      STATUS      current
      DESCRIPTION
              "An entry in the portSSLEntry, each relating to a port."
      INDEX   { portSSLIndex }
      ::= { portSSLTable 1 }
  PortSSLEntry ::=
      SEQUENCE {
  portSSLIndex
        INTEGER,
  portSSLStatus
       RowStatus,
  portSSLEnabled
        OnOffValue,
  portSSLuseServer
        OnOffValue,
  portSSLVersion
        INTEGER,
  portSSLType
        INTEGER,
  portSSLVerifyPeerCertificate
        OnOffValue,
  portSSLCountry
        DisplayString,
  portSSLStateProv
        DisplayString,
  portSSLLocality
        DisplayString,
  portSSLOrganisation
        DisplayString,
  portSSLOrganisationUnit
        DisplayString,
  portSSLCommonName
        DisplayString,
  portSSLEmail
        DisplayString
      
      }

  portSSLIndex OBJECT-TYPE
      SYNTAX      INTEGER
      MAX-ACCESS  read-only
      STATUS      current
      DESCRIPTION
              "port SSL Index"
      ::= { portSSLEntry 1}

  portSSLStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {portSSLEntry 2}

  portSSLEnabled  OBJECT-TYPE
      SYNTAX   OnOffValue
      MAX-ACCESS    read-write
      STATUS        current
      DESCRIPTION
                "Enables/disables SSL."
      ::= {portSSLEntry 3}

  portSSLuseServer  OBJECT-TYPE
      SYNTAX   OnOffValue
      MAX-ACCESS    read-write
      STATUS        current
      DESCRIPTION
                "Uses the SSL/TLS server configuration for the line."
      ::= {portSSLEntry 4}

  portSSLVersion  OBJECT-TYPE
      SYNTAX      INTEGER {
        any(1),
        tlsv1(2),
        sslv3(3)
      }
      MAX-ACCESS    read-write
      STATUS        current
      DESCRIPTION
                "Specify whether you want to use:
                 Any-The Device Server will try a TLSv1 connection first.
                     If that fails, it will try an SSLv3 connection. 
                     If that fails, it will try an SSLv2 connection.
                 TLSv1-The connection will use only TLSv1.
                 SSLv3-The connection will use only SSLv3.
                 The default is Any."
      ::= {portSSLEntry 5}

  portSSLType    OBJECT-TYPE
      SYNTAX      INTEGER {
        client(1),
        server(2)
      }
      MAX-ACCESS    read-write
      STATUS        current
      DESCRIPTION
                "Specify whether the Device Server will act as an 
                 SSL/TLS client or server. The default is Client."
      ::= {portSSLEntry 6}

  portSSLVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {portSSLEntry 7}

  portSSLCountry    OBJECT-TYPE
      SYNTAX      DisplayString(SIZE(0..2))
      MAX-ACCESS    read-write
      STATUS        current
      DESCRIPTION
                "A two character country code; for example, US."
      ::= {portSSLEntry 8}

  portSSLStateProv    OBJECT-TYPE
      SYNTAX      DisplayString(SIZE(0..128))
      MAX-ACCESS    read-write
      STATUS        current
      DESCRIPTION
                "Up to a 128 character entry for the state/province;
                 for example, IL."
      ::= {portSSLEntry 9}

  portSSLLocality    OBJECT-TYPE
      SYNTAX      DisplayString(SIZE(0..128))
      MAX-ACCESS    read-write
      STATUS        current
      DESCRIPTION
                "Up to a 128 character entry for the location; 
                 for example, a city."
      ::= {portSSLEntry 10}

  portSSLOrganisation    OBJECT-TYPE
      SYNTAX      DisplayString(SIZE(0..64))
      MAX-ACCESS    read-write
      STATUS        current
      DESCRIPTION
                "Up to a 64 character entry for the organisation; 
                 for example, Accounting."
      ::= {portSSLEntry 11}

  portSSLOrganisationUnit    OBJECT-TYPE
      SYNTAX      DisplayString(SIZE(0..64))
      MAX-ACCESS    read-write
      STATUS        current
      DESCRIPTION
                "Up to a 64 character entry for the unit in the 
                 organisation; for example, Payroll."
      ::= {portSSLEntry 12}

  portSSLCommonName    OBJECT-TYPE
      SYNTAX      DisplayString(SIZE(0..64))
      MAX-ACCESS    read-write
      STATUS        current
      DESCRIPTION
                "Up to a 64 character entry for common name; for example,
                 the host name or fully qualified domain name."
      ::= {portSSLEntry 13}

  portSSLEmail    OBJECT-TYPE
      SYNTAX      DisplayString(SIZE(0..128))
      MAX-ACCESS    read-write
      STATUS        current
      DESCRIPTION
                "Up to a 64 character entry for an email address; 
                 for example, acct@anycompany.com."
      ::= {portSSLEntry 14}

-- Port SSL Server Cipher Table

  portSSLCipherTable OBJECT-TYPE
      SYNTAX      SEQUENCE OF PortSSLCipherEntry
      MAX-ACCESS  not-accessible
      STATUS      current
      DESCRIPTION
              "SSL CIpher."
      ::= {portSSLEntry 15}

  portSSLCipherEntry OBJECT-TYPE
      SYNTAX      PortSSLCipherEntry
      MAX-ACCESS  not-accessible
      STATUS      current
      DESCRIPTION
              "An entry in the sslCipherTable, each relating to a cipher entry."
      INDEX   { portSSLCipherPort, portSSLCipherPriority }
      ::= { portSSLCipherTable 1 }

  PortSSLCipherEntry ::=
      SEQUENCE {
  portSSLCipherPort
        INTEGER,
  portSSLCipherPriority
       INTEGER,
  portSSLCipherStatus
        RowStatus,
  portSSLCipherEncryption
        INTEGER,
  portSSLCipherKeySizeMin
        INTEGER,
  portSSLCipherKeySizeMax
        INTEGER,
  portSSLCipherKeyExchange
        INTEGER,
  portSSLCipherHMAC
        INTEGER
      }

  portSSLCipherPort OBJECT-TYPE
      SYNTAX      INTEGER
      MAX-ACCESS  not-accessible
      STATUS      current
      DESCRIPTION
              "The port number"
      ::= { portSSLCipherEntry 1 }

  portSSLCipherPriority OBJECT-TYPE
      SYNTAX      INTEGER
      MAX-ACCESS  not-accessible
      STATUS      current
      DESCRIPTION
              "The cipher priority. 1- highest 5 - lowest."
      ::= { portSSLCipherEntry 2 }

  portSSLCipherStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portSSLCipherEntry 3 }

  portSSLCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { portSSLCipherEntry 4 }

  portSSLCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { portSSLCipherEntry 5 }

  portSSLCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { portSSLCipherEntry 6 }

  portSSLCipherKeyExchange OBJECT-TYPE
      SYNTAX      INTEGER {
        any(1),
        rsa(2),
        edhrsa(3),
        edhdss(4),
        adh(5)
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { portSSLCipherEntry 7 }

  portSSLCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { portSSLCipherEntry 8 }
      
-- Packet Forwarding Table
  portPacketForwardingTable OBJECT-TYPE
      SYNTAX      SEQUENCE OF PortPacketForwardingEntry
      MAX-ACCESS  not-accessible
      STATUS      current
      DESCRIPTION
              "The port packet forwarding configuration table."
      ::= { portInfo 14 }

  portPacketForwardingEntry OBJECT-TYPE
      SYNTAX      PortPacketForwardingEntry
      MAX-ACCESS  not-accessible
      STATUS      current
      DESCRIPTION
              "An entry in the port packet forwarding configuration table, each relating to a serial port."
      INDEX   { portPacketForwardingIndex }
      ::= { portPacketForwardingTable 1 }

  PortPacketForwardingEntry ::=
      SEQUENCE {
          portPacketForwardingIndex
              INTEGER,
          portPacketForwardingStatus
               RowStatus,
          portPacketForwardingPacketSize
              INTEGER,
          portPacketForwardingIdleTime
              INTEGER,
          portPacketForwardingForceTransmitTime
              INTEGER,
          portPacketForwardingEnableStartFrameFirst
              OnOffValue,
          portPacketForwardingStartFrameFirst
              Hex8,
          portPacketForwardingEnableStartFrameSecond
              OnOffValue,
          portPacketForwardingStartFrameSecond
              Hex8,
          portPacketForwardingStartFrameTransmit
              OnOffValue,
          portPacketForwardingEnableEndFrameFirst
              OnOffValue,
          portPacketForwardingEndFrameFirst
              Hex8,
          portPacketForwardingEnableEndFrameSecond
              OnOffValue,
          portPacketForwardingEndFrameSecond
              Hex8,
          portPacketForwardingEnableEndTriggerFirst
              OnOffValue,
          portPacketForwardingEndTriggerFirst
              Hex8,
          portPacketForwardingEnableEndTriggerSecond
              OnOffValue,
          portPacketForwardingEndTriggerSecond
              Hex8,
          portPacketForwardingForwardingRule
              INTEGER,
          portPacketForwardingPacketIdleTime
              INTEGER,
          portPacketForwardingFowardMode
              INTEGER
        }

  portPacketForwardingIndex OBJECT-TYPE
      SYNTAX      INTEGER
      MAX-ACCESS  not-accessible
      STATUS      current
      DESCRIPTION
              "Port Index"
      ::= { portPacketForwardingEntry 1}

  portPacketForwardingStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portPacketForwardingEntry 2}

  portPacketForwardingPacketSize OBJECT-TYPE
      SYNTAX      INTEGER(0..1024)
      MAX-ACCESS  read-write
      STATUS      current
      DESCRIPTION
              "When the size of the packet equals this value the packet is 
               transmitted. 0 - Ignore option"
      ::= { portPacketForwardingEntry 3}

  portPacketForwardingIdleTime OBJECT-TYPE
      SYNTAX      INTEGER(0..65535)
      MAX-ACCESS  read-write
      STATUS      current
      DESCRIPTION
              "When the elapsed time between one character to another character
               equals this value the packet is transmitted. 0 - Ignore option"
      ::= { portPacketForwardingEntry 4}

  portPacketForwardingForceTransmitTime OBJECT-TYPE
      SYNTAX      INTEGER(0..65535)
      MAX-ACCESS  read-write
      STATUS      current
      DESCRIPTION
              "When the elapsed time from the 1st character received equals this
               value the packet is transmitted. 0 - Ignore option."
      ::= { portPacketForwardingEntry 5}

  portPacketForwardingEnableStartFrameFirst OBJECT-TYPE
      SYNTAX     OnOffValue
      MAX-ACCESS  read-write
      STATUS      current
      DESCRIPTION
              "Enable/disable the start of frame 1."
      ::= { portPacketForwardingEntry 6}

  portPacketForwardingStartFrameFirst OBJECT-TYPE
      SYNTAX      Hex8
      MAX-ACCESS  read-write
      STATUS      current
      DESCRIPTION
              "Any characters received before the start of frame is received will
               be ignored."
      ::= { portPacketForwardingEntry 7}

  portPacketForwardingEnableStartFrameSecond OBJECT-TYPE
      SYNTAX     OnOffValue
      MAX-ACCESS  read-write
      STATUS      current
      DESCRIPTION
              "Enable/disable the start of frame 2. When this is enabled SOF1 must
               enabled"
      ::= { portPacketForwardingEntry 8}

  portPacketForwardingStartFrameSecond OBJECT-TYPE
      SYNTAX      Hex8
      MAX-ACCESS  read-write
      STATUS      current
      DESCRIPTION
              "Any characters received before the start of frame is received will
               be ignored."
      ::= { portPacketForwardingEntry 9}
      
  portPacketForwardingStartFrameTransmit OBJECT-TYPE
      SYNTAX     OnOffValue
      MAX-ACCESS  read-write
      STATUS      current
      DESCRIPTION
              "A flag to determine if we will transmit the start of frame character(s)."
      ::= { portPacketForwardingEntry 10}
      
  portPacketForwardingEnableEndFrameFirst OBJECT-TYPE
      SYNTAX     OnOffValue
      MAX-ACCESS  read-write
      STATUS      current
      DESCRIPTION
              "Enable/disable the end of frame 1."
      ::= { portPacketForwardingEntry 11}

  portPacketForwardingEndFrameFirst OBJECT-TYPE
      SYNTAX      Hex8
      MAX-ACCESS  read-write
      STATUS      current
      DESCRIPTION
              "The frame will be transmitted after this character is received based on the
               forwarding rule."
      ::= { portPacketForwardingEntry 12}

  portPacketForwardingEnableEndFrameSecond OBJECT-TYPE
      SYNTAX     OnOffValue
      MAX-ACCESS  read-write
      STATUS      current
      DESCRIPTION
              "Enable/disable the end of frame 2. When this is enabled EOF1 must
               enabled"
      ::= { portPacketForwardingEntry 13}

  portPacketForwardingEndFrameSecond OBJECT-TYPE
      SYNTAX      Hex8
      MAX-ACCESS  read-write
      STATUS      current
      DESCRIPTION
              "The frame will be transmitted after this character is received based on the
               forwarding rule."
      ::= { portPacketForwardingEntry 14}
      
  portPacketForwardingEnableEndTriggerFirst OBJECT-TYPE
      SYNTAX     OnOffValue
      MAX-ACCESS  read-write
      STATUS      current
      DESCRIPTION
              "Enable/disable the end of trigger 1."
      ::= { portPacketForwardingEntry 15}

  portPacketForwardingEndTriggerFirst OBJECT-TYPE
      SYNTAX      Hex8
      MAX-ACCESS  read-write
      STATUS      current
      DESCRIPTION
              "When the end trigger is received the packet will transmitted based on the
               forwarding rules."
      ::= { portPacketForwardingEntry 16}

  portPacketForwardingEnableEndTriggerSecond OBJECT-TYPE
      SYNTAX     OnOffValue
      MAX-ACCESS  read-write
      STATUS      current
      DESCRIPTION
              "Enable/disable the end of trigger 2. When this is enabled EOF1 must
               enabled"
      ::= { portPacketForwardingEntry 17}

  portPacketForwardingEndTriggerSecond OBJECT-TYPE
      SYNTAX      Hex8
      MAX-ACCESS  read-write
      STATUS      current
      DESCRIPTION
              "When the end trigger is received the packet will transmitted based on the
               forwarding rules."
      ::= { portPacketForwardingEntry 18}
      
  portPacketForwardingForwardingRule OBJECT-TYPE
  SYNTAX      INTEGER {
      trigger (0),
      triggerplus1 (1),
      triggerplus2 (2),
      stripTrigger (3)
  }
      MAX-ACCESS  read-write
      STATUS      current
      DESCRIPTION
              "Forwarding rules."
      ::= { portPacketForwardingEntry 19}
      
   portPacketForwardingPacketIdleTime OBJECT-TYPE
      SYNTAX      INTEGER(0..65535)
      MAX-ACCESS  read-write
      STATUS      current
      DESCRIPTION
              "When in Packet Accumulation mode it used for packet idle time"
      ::= { portPacketForwardingEntry 20}    
      
   portPacketForwardingForwardMode OBJECT-TYPE
	SYNTAX      INTEGER {
      forwardModeInvalid (0),
      OptimizeEthernetTrafic (1),
      minimizeLatency (2),
      messageAccumulation (3),
      custom (4)
      }
      MAX-ACCESS  read-write
      STATUS      current
      DESCRIPTION
              "Forwarding Mode."
      ::= { portPacketForwardingEntry 21}
            
 -- Port Tunnel Table

  portTunnelTable OBJECT-TYPE
      SYNTAX      SEQUENCE OF PortTunnelEntry
      MAX-ACCESS  not-accessible
      STATUS      current
      DESCRIPTION
              "Port Tunnel Table."
      ::= { portInfo 15 }

  portTunnelEntry OBJECT-TYPE
      SYNTAX      PortTunnelEntry
      MAX-ACCESS  not-accessible
      STATUS      current
      DESCRIPTION
              "An entry in the portTunnelEntry, each relating to a port."
      INDEX   { portTunnelIndex }
      ::= { portTunnelTable 1 }

  PortTunnelEntry ::=
      SEQUENCE {
        portTunnelIndex
            INTEGER,
        portTunnelStatus
            RowStatus,
        portTunnelPort
            INTEGER,
        portTunnelHost
            DisplayString
        }

  portTunnelIndex OBJECT-TYPE
      SYNTAX      INTEGER
      MAX-ACCESS  read-only
      STATUS      current
      DESCRIPTION
              "portTunnelIndex"
      ::= { portTunnelEntry 1}

  portTunnelStatus OBJECT-TYPE
      SYNTAX      RowStatus
      MAX-ACCESS  read-write
      STATUS      current
      DESCRIPTION
              "When you perform a GET on this variable, one of 
               the following values will be returned:
               1-Indicates that the container folder is active with no changes.
               2-Indicates that the container folder is active with change(s).
               Once you have completed setting the variables in a folder, you
               will want to submit your changes to the Device Server. To do 
               this, set the Status variable to 4. If you want to discard the
               changes, set the Status variable to 6.
               4-Indicates that the changes in the container folder are to be
                 submitted to the Device Server.
               6-Indicates that the changes in the container folder are to be
                 discarded."
      ::= { portTunnelEntry 2}

  portTunnelPort OBJECT-TYPE
      SYNTAX      INTEGER (0..65535)
      MAX-ACCESS  read-write
      STATUS      current
      DESCRIPTION
              "The port number the target host is listening on for incoming connections."
      ::= { portTunnelEntry 3}

  portTunnelHost OBJECT-TYPE
      SYNTAX      DisplayString (SIZE(0..14))
      MAX-ACCESS  read-write
      STATUS      current
      DESCRIPTION
              "The name of the target host."
      ::= { portTunnelEntry 4}
      
-- Port Modbus Slave Table

  portMODBUSSlaveTable OBJECT-TYPE
      SYNTAX      SEQUENCE OF PortMODBUSSlaveEntry
      MAX-ACCESS  not-accessible
      STATUS      current
      DESCRIPTION
              "Port MODBUS Slave Table."
      ::= { portInfo 16 }

  portMODBUSSlaveEntry OBJECT-TYPE
      SYNTAX      PortMODBUSSlaveEntry
      MAX-ACCESS  not-accessible
      STATUS      current
      DESCRIPTION
              "An entry in the portMODBUSSlaveEntry, each relating to a port."
      INDEX   { portMODBUSSlaveIndex }
      ::= { portMODBUSSlaveTable 1 }

  PortMODBUSSlaveEntry ::=
      SEQUENCE {
        portMODBUSSlaveIndex
            INTEGER,
        portMODBUSSlaveStatus
            RowStatus,
        portMODBUSSlaveMode
            INTEGER,
        portMODBUSSlaveCRLF
            OnOffValue,
        portMODBUSSlaveUIDRange
            DisplayString
      }

  portMODBUSSlaveIndex OBJECT-TYPE
      SYNTAX      INTEGER
      MAX-ACCESS  read-write
      STATUS      current
      DESCRIPTION
              "portMODBUSSlaveIndex"
      ::= { portMODBUSSlaveEntry 1}

  portMODBUSSlaveStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMODBUSSlaveEntry 2}

  portMODBUSSlaveMode OBJECT-TYPE
  SYNTAX      INTEGER {
	  rtu(0),
	  ascii(1)
  }
      MAX-ACCESS  read-write
      STATUS      current
      DESCRIPTION
              "MODBUS serial device's mode: 0: RTU; 1: ASCII."
      ::= { portMODBUSSlaveEntry 3}

  portMODBUSSlaveCRLF OBJECT-TYPE
      SYNTAX      OnOffValue
      MAX-ACCESS  read-write
      STATUS      current
      DESCRIPTION
              "Enable/disable appending CR/LF"
      ::= { portMODBUSSlaveEntry 4}

  portMODBUSSlaveUIDRange OBJECT-TYPE
      SYNTAX      DisplayString(SIZE(0..40))
      MAX-ACCESS  read-write
      STATUS      current
      DESCRIPTION
              "The UID range for this entry."
      ::= { portMODBUSSlaveEntry 5 }
	        
-- Port Modbus Master Table

  portMODBUSMasterTable OBJECT-TYPE
      SYNTAX      SEQUENCE OF PortMODBUSMasterEntry
      MAX-ACCESS  not-accessible
      STATUS      current
      DESCRIPTION
              "Port MODBUS Master Table."
      ::= { portInfo 17 }

  portMODBUSMasterEntry OBJECT-TYPE
      SYNTAX      PortMODBUSMasterEntry
      MAX-ACCESS  not-accessible
      STATUS      current
      DESCRIPTION
              "An entry in the portMODBUSMasterEntry, each relating to a port."
      INDEX   { portMODBUSMasterIndex }
      ::= { portMODBUSMasterTable 1 }

  PortMODBUSMasterEntry ::=
      SEQUENCE {
        portMODBUSMasterIndex
            INTEGER,
        portMODBUSMasterStatus
            RowStatus,
        portMODBUSMasterMode
            INTEGER,
        portMODBUSMasterCRLF
            OnOffValue
      }
      
      
  portMODBUSMasterIndex OBJECT-TYPE
      SYNTAX      INTEGER
      MAX-ACCESS  read-write
      STATUS      current
      DESCRIPTION
              "portMODBUSMasterIndex"
      ::= { portMODBUSMasterEntry 1}

  portMODBUSMasterStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMODBUSMasterEntry 2}

  portMODBUSMasterMode OBJECT-TYPE
  SYNTAX      INTEGER {
      rtu(0),
      ascii(1)
  }
      MAX-ACCESS  read-write
      STATUS      current
      DESCRIPTION
              "MODBUS serial device's mode: 0: RTU; 1: ASCII."
      ::= { portMODBUSMasterEntry 3}

  portMODBUSMasterCRLF OBJECT-TYPE
      SYNTAX      OnOffValue
      MAX-ACCESS  read-write
      STATUS      current
      DESCRIPTION
              "Enable/disable appending CR/LF"
      ::= { portMODBUSMasterEntry 4}
      
-- Port Modbus Master Slave Mapping Table

  portMODBUSMasterMappingTable OBJECT-TYPE
      SYNTAX      SEQUENCE OF PortMODBUSMasterMappingEntry
      MAX-ACCESS  not-accessible
      STATUS      current
      DESCRIPTION
              "Modbus Master Slave Mapping."
      ::= {portMODBUSMasterEntry 5}
      
  portMODBUSMasterMappingEntry OBJECT-TYPE
      SYNTAX      PortMODBUSMasterMappingEntry
      MAX-ACCESS  not-accessible
      STATUS      current
      DESCRIPTION
              "An entry in the portMODBUSMasterMappingTable, each relating to a slave mapping."
      INDEX   {portMODBUSMasterPortIndex, portMODBUSMasterMappingIndex }
      ::= { portMODBUSMasterMappingTable 1 }

  PortMODBUSMasterMappingEntry ::=
      SEQUENCE {
  portMODBUSMasterPortIndex
        INTEGER,
  portMODBUSMasterMappingIndex
        INTEGER,
  portMODBUSMasterMappingStatus
        RowStatus,
    portMODBUSMasterMappingRemoteIP
        Ipv4v6Address,
    portMODBUSMasterMappingTransportType
        INTEGER,
    portMODBUSMasterMappingPortNumber
        INTEGER,
    portMODBUSMasterMappingUIDStart
        INTEGER,
    portMODBUSMasterMappingUIDEnd
        INTEGER,
    portMODBUSMasterMappingUIDRangeMode
        INTEGER
      }

  portMODBUSMasterPortIndex OBJECT-TYPE
      SYNTAX      INTEGER
      MAX-ACCESS  not-accessible
      STATUS      current
      DESCRIPTION
              "The port number"
      ::= { portMODBUSMasterMappingEntry 1 }
      
  portMODBUSMasterMappingIndex OBJECT-TYPE
      SYNTAX      INTEGER
      MAX-ACCESS  not-accessible
      STATUS      current
      DESCRIPTION
              "The mapping table index"
      ::= { portMODBUSMasterMappingEntry 2 }

  portMODBUSMasterMappingStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMODBUSMasterMappingEntry 3 }

  portMODBUSMasterMappingRemoteIP OBJECT-TYPE
      SYNTAX      Ipv4v6Address
      MAX-ACCESS  read-write
      STATUS      current
      DESCRIPTION
              "The remote slave's IP address."
      ::= { portMODBUSMasterMappingEntry 4 }

  portMODBUSMasterMappingTransportType OBJECT-TYPE
      SYNTAX      INTEGER {
        tcp(0),
        udp(1)
      }
      MAX-ACCESS  read-write
      STATUS      current
      DESCRIPTION
              "The remote slave's transport protocol type (TCP/UDP)."
      ::= { portMODBUSMasterMappingEntry 5 }

  portMODBUSMasterMappingPortNumber OBJECT-TYPE
      SYNTAX      INTEGER
      MAX-ACCESS  read-write
      STATUS      current
      DESCRIPTION
              "the transport protocol layer port number (tcp/udp)."
      ::= { portMODBUSMasterMappingEntry 6 }

  portMODBUSMasterMappingUIDStart OBJECT-TYPE
      SYNTAX      INTEGER
      MAX-ACCESS  read-write
      STATUS      current
      DESCRIPTION
              "The start UID of the UID range for this entry."
      ::= { portMODBUSMasterMappingEntry 7 }

  portMODBUSMasterMappingUIDEnd OBJECT-TYPE
      SYNTAX      INTEGER
      MAX-ACCESS  read-write
      STATUS      current
      DESCRIPTION
              "The end UID of the UID range for this entry."
      ::= { portMODBUSMasterMappingEntry 8 }
	  
  portMODBUSMasterMappingUIDRangeMode OBJECT-TYPE
  SYNTAX      INTEGER {
      host(0),
      gateway(1)
  }
      MAX-ACCESS  read-write
      STATUS      current
      DESCRIPTION
              "The UID-IP mapping mode."
      ::= { portMODBUSMasterMappingEntry 9 }
            

-- Port CustomApp Table

  portCustomAppTable OBJECT-TYPE
      SYNTAX      SEQUENCE OF PortCustomAppEntry
      MAX-ACCESS  not-accessible
      STATUS      current
      DESCRIPTION
              "Port CustomApp Table."
      ::= { portInfo 18 }

  portCustomAppEntry OBJECT-TYPE
      SYNTAX      PortCustomAppEntry
      MAX-ACCESS  not-accessible
      STATUS      current
      DESCRIPTION
              "An entry in the PortCustomAppEntry, each relating to a port."
      INDEX   { portCustomAppIndex }
      ::= { portCustomAppTable 1 }

  PortCustomAppEntry ::=
      SEQUENCE {
        portCustomAppIndex
            INTEGER,
        portCustomAppStatus
            RowStatus,
        portCustomAppCommand
            DisplayString
        }

  portCustomAppIndex OBJECT-TYPE
      SYNTAX      INTEGER
      MAX-ACCESS  read-only
      STATUS      current
      DESCRIPTION
              "portCustomAppIndex"
      ::= { portCustomAppEntry 1}

  portCustomAppStatus OBJECT-TYPE
      SYNTAX      RowStatus
      MAX-ACCESS  read-write
      STATUS      current
      DESCRIPTION
              "When you perform a GET on this variable, one of 
               the following values will be returned:
               1-Indicates that the container folder is active with no changes.
               2-Indicates that the container folder is active with change(s).
               Once you have completed setting the variables in a folder, you
               will want to submit your changes to the Device Server. To do 
               this, set the Status variable to 4. If you want to discard the
               changes, set the Status variable to 6.
               4-Indicates that the changes in the container folder are to be
                 submitted to the Device Server.
               6-Indicates that the changes in the container folder are to be
                 discarded."
      ::= { portCustomAppEntry 2}

  portCustomAppCommand OBJECT-TYPE
      SYNTAX      DisplayString(SIZE(0..80))
      MAX-ACCESS  read-write
      STATUS      current
      DESCRIPTION
              "The command line of the custom application."
      ::= { portCustomAppEntry 3}

  portTrueportServiceTable OBJECT-TYPE
      SYNTAX      SEQUENCE OF PortTrueportServiceEntry
      MAX-ACCESS  not-accessible
      STATUS      current
      DESCRIPTION
              "Port TrueportService Table."
      ::= { portInfo 19 }

  portTrueportServiceEntry OBJECT-TYPE
      SYNTAX      PortTrueportServiceEntry
      MAX-ACCESS  not-accessible
      STATUS      current
      DESCRIPTION
              "An entry in the portTrueportServiceEntry, each relating to a port."
      INDEX   { portTrueportServiceIndex }
      ::= { portTrueportServiceTable 1 }

  PortTrueportServiceEntry ::=
      SEQUENCE {
        portTrueportServiceIndex
            INTEGER,
        portTrueportServiceStatus
            RowStatus,
        portTrueportServicePort
            INTEGER,
        portTrueportServiceHost
            DisplayString,
        portTrueportServiceClientInitiated
            OnOffValue,
       portTrueportServiceActiveSignal
            OnOffValue
        }

  portTrueportServiceIndex OBJECT-TYPE
      SYNTAX      INTEGER
      MAX-ACCESS  read-only
      STATUS      current
      DESCRIPTION
              "portTrueportServiceIndex"
      ::= { portTrueportServiceEntry 1}

  portTrueportServiceStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portTrueportServiceEntry 2}

  portTrueportServicePort OBJECT-TYPE
      SYNTAX      INTEGER (0..65535)
      MAX-ACCESS  read-write
      STATUS      current
      DESCRIPTION
              "The port number the target host is listening on for incoming connections."
      ::= { portTrueportServiceEntry 3}

  portTrueportServiceHost OBJECT-TYPE
      SYNTAX      DisplayString (SIZE(0..14))
      MAX-ACCESS  read-write
      STATUS      current
      DESCRIPTION
              "The name of the target host."
      ::= { portTrueportServiceEntry 4}

  portTrueportServiceClientInitiated OBJECT-TYPE
      SYNTAX      OnOffValue
      MAX-ACCESS  read-write
      STATUS      current
      DESCRIPTION
              "Specifies whether or not the network connection is initiated 
               by the client"
      ::= {  portTrueportServiceEntry 5}

  portTrueportServiceActiveSignal OBJECT-TYPE
      SYNTAX      OnOffValue
      MAX-ACCESS  read-write
      STATUS      current
      DESCRIPTION
              "When turn on the state of the signals on the serial port should be when they are
              not controlled by the service client. In lite mode, this will be the state of the signals 
              at all times. In full mode, this will be the state before service issues specific commands 
              to change the state of the signals."
      ::= {  portTrueportServiceEntry 6}

-- Port Power Management Table

  portPowerManagementTable OBJECT-TYPE
      SYNTAX      SEQUENCE OF PortPowerManagementEntry
      MAX-ACCESS  not-accessible
      STATUS      current
      DESCRIPTION
              "Port Power Management Table."
      ::= { portInfo 20 }

  portPowerManagementEntry OBJECT-TYPE
      SYNTAX      PortPowerManagementEntry
      MAX-ACCESS  not-accessible
      STATUS      current
      DESCRIPTION
              "An entry in the portPowerManagementEntry, each relating to a port."
      INDEX   { portPowerManagementIndex }
      ::= { portPowerManagementTable 1 }

  portPowerManagementIndex OBJECT-TYPE
      SYNTAX      INTEGER
      MAX-ACCESS  read-write
      STATUS      current
      DESCRIPTION
              "portPowerManagementIndex"
      ::= { portPowerManagementEntry 1}

  portPowerManagementStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portPowerManagementEntry 2}

  portPowerManagementName OBJECT-TYPE
      SYNTAX      DisplayString(SIZE(0..15))
      MAX-ACCESS  read-write
      STATUS      current
      DESCRIPTION
              "Power bar's name."
      ::= { portPowerManagementEntry 3}

  portPowerManagementModel OBJECT-TYPE
  SYNTAX      INTEGER {
      RPS820(1),
      RPS830(2),
      RPS1620(3),
      RPS1630(4)
  }
      MAX-ACCESS  read-write
      STATUS      current
      DESCRIPTION
              "Power bar's model"
      ::= { portPowerManagementEntry 4}
      
-- Port Power Management Plug Table

  portPowerManagementPlugTable OBJECT-TYPE
      SYNTAX      SEQUENCE OF PortPowerManagementPlugEntry
      MAX-ACCESS  not-accessible
      STATUS      current
      DESCRIPTION
              "Power Management Plug Table."
      ::= {portPowerManagementEntry 5}
      
  portPowerManagementPlugEntry OBJECT-TYPE
      SYNTAX      PortPowerManagementPlugEntry
      MAX-ACCESS  not-accessible
      STATUS      current
      DESCRIPTION
              "An entry in the portPowerManagementPlugTable, each relating to a plug."
      INDEX   {portPowerManagementPortIndex, portPowerManagementPlugIndex }
      ::= { portPowerManagementPlugTable 1 }

  PortPowerManagementPlugEntry ::=
      SEQUENCE {
  portPowerManagementPortIndex
        INTEGER,
  portPowerManagementPlugIndex
        INTEGER,
  portPowerManagementPlugStatus
        RowStatus,
    portPowerManagementPlugName
        DisplayString,
    portPowerManagementPlugPowerUpInterval
        INTEGER,
    portPowerManagementPlugDefaultState
        OnOffValue,
    portPowerManagementDSLine
        INTEGER
      }

  portPowerManagementPortIndex OBJECT-TYPE
      SYNTAX      INTEGER
      MAX-ACCESS  not-accessible
      STATUS      current
      DESCRIPTION
              "The port number"
      ::= { portPowerManagementPlugEntry 1 }
      
  portPowerManagementPlugIndex OBJECT-TYPE
      SYNTAX      INTEGER
      MAX-ACCESS  not-accessible
      STATUS      current
      DESCRIPTION
              "The plug number"
      ::= { portPowerManagementPlugEntry 2 }

  portPowerManagementPlugStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portPowerManagementPlugEntry 3 }
    portPowerManagementPlugDefaultState
        OnOffValue,
    portPowerManagementDSLine
        INTEGER

  portPowerManagementPlugName OBJECT-TYPE
      SYNTAX      DisplayString(SIZE(0..19))
      MAX-ACCESS  read-write
      STATUS      current
      DESCRIPTION
              "The plug's name."
      ::= { portPowerManagementPlugEntry 4 }

  portPowerManagementPlugPowerUpInterval OBJECT-TYPE
      SYNTAX      INTEGER {
        PU_INTERVAL_HALF(1),
        PU_INTERVAL_1(2),
        PU_INTERVAL_2(3),
        PU_INTERVAL_5(4),
        PU_INTERVAL_15(5),
        PU_INTERVAL_30(6),
        PU_INTERVAL_60(7),
        PU_INTERVAL_120(8),
        PU_INTERVAL_180(9),
        PU_INTERVAL_300(10)
      }
      MAX-ACCESS  read-write
      STATUS      current
      DESCRIPTION
              "The plug's power up delay."
      ::= { portPowerManagementPlugEntry 5 }

  portPowerManagementPlugDefaultState OBJECT-TYPE
      SYNTAX      OnOffValue
      MAX-ACCESS  read-write
      STATUS      current
      DESCRIPTION
              "the plug's default state."
      ::= { portPowerManagementPlugEntry 6 }

  portPowerManagementDSLine OBJECT-TYPE
      SYNTAX      INTEGER
      MAX-ACCESS  read-write
      STATUS      current
      DESCRIPTION
              "the DS line number which the device on this plug is connected to(0:none, >0:corresponding to the 
               line number."
      ::= { portPowerManagementPlugEntry 7 }

-- Port Multihost Table

  portMultihostTable OBJECT-TYPE
      SYNTAX      SEQUENCE OF PortMultihostEntry
      MAX-ACCESS  not-accessible
      STATUS      current
      DESCRIPTION
              "Port Multihost Table."
      ::= { portInfo 21 }

  portMultihostEntry OBJECT-TYPE
      SYNTAX      PortMultihostEntry
      MAX-ACCESS  not-accessible
      STATUS      current
      DESCRIPTION
              "An entry in the portMultihostEntry, each relating to a port."
      INDEX   { portMultihostIndex }
      ::= { portMultihostTable 1 }

  PortMultihostEntry ::=
      SEQUENCE {
        portMultihostIndex
            INTEGER,
        portMultihostStatus
            RowStatus,
        portMultihostSingleMaster
            INTEGER,
        portMultihostMode
            INTEGER
        
        }

  portMultihostIndex OBJECT-TYPE
      SYNTAX      INTEGER
      MAX-ACCESS  read-only
      STATUS      current
      DESCRIPTION
              "portMultihostIndex"
      ::= { portMultihostEntry 1}

  portMultihostStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMultihostEntry 2}

  portMultihostSingleMaster OBJECT-TYPE
      SYNTAX      INTEGER
      MAX-ACCESS  read-write
      STATUS      current
      DESCRIPTION
              "The Multihost configure option."
      ::= { portMultihostEntry 3}

  portMultihostMode OBJECT-TYPE
        SYNTAX      INTEGER {
        all(1),
        backup(2)
      }
      MAX-ACCESS  read-write
      STATUS      current
      DESCRIPTION
              "Set multihost operation mode.all:for muliple host list mode. backup: for primary-backup mode"
      ::= { portMultihostEntry 4}

-- Port multihost outbound Table

  portMultihostOutboundTable OBJECT-TYPE
      SYNTAX      SEQUENCE OF portMultihostOutboundEntry
      MAX-ACCESS  not-accessible
      STATUS      current
      DESCRIPTION
              "Multihost outbound table."
      ::= {portMultihostEntry 5}
      
  portMultihostOutboundEntry OBJECT-TYPE
      SYNTAX      PortMultihostOutboundEntry
      MAX-ACCESS  not-accessible
      STATUS      current
      DESCRIPTION
              "An entry in the portMultihostOutboundTable."
      INDEX   {portMultihostPortIndex, portMultihostOutboundIndex }
      ::= { portMultihostOutboundTable 1 }

  PortMultihostOutboundEntry ::=
      SEQUENCE {
  portMultihostPortIndex
        INTEGER,
  portMultihostOutboundIndex
        INTEGER,
  portMultihostOutboundStatus
        RowStatus,
  portMultihostOutboundHostID
        INTEGER,
  portMultihostOutboundTcpPort
        INTEGER
      }

   portMultihostPortIndex OBJECT-TYPE
      SYNTAX      INTEGER
      MAX-ACCESS  not-accessible
      STATUS      current
      DESCRIPTION
              "The port number"
      ::= { portMultihostOutboundEntry 1 }
      
  portMultihostOutboundIndex OBJECT-TYPE
      SYNTAX      INTEGER
      MAX-ACCESS  not-accessible
      STATUS      current
      DESCRIPTION
              "The outbound entry number"
      ::= { portMultihostOutboundEntry 2 }

  portMultihostOutboundStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMultihostOutboundEntry 3 }


  portMultihostOutboundHostID OBJECT-TYPE
      SYNTAX      DisplayString (SIZE(0..14))
      MAX-ACCESS  read-write
      STATUS      current
      DESCRIPTION
              "The host name."
      ::= { portMultihostOutboundEntry 4 }

  portMultihostOutboundTcpPort OBJECT-TYPE
      SYNTAX      INTEGER (0..65535)
      MAX-ACCESS  read-write
      STATUS      current
      DESCRIPTION
              "The host TCP port."
      ::= { portMultihostOutboundEntry 5 }

      
-- Modem Table

  modemInfoTable OBJECT-TYPE
      SYNTAX      SEQUENCE OF ModemInfoEntry
      MAX-ACCESS  not-accessible
      STATUS      current
      DESCRIPTION
              "The modem info table."
      ::= { modemInfo 1 }

  modemInfoEntry OBJECT-TYPE
      SYNTAX      ModemInfoEntry
      MAX-ACCESS  not-accessible
      STATUS      current
      DESCRIPTION
              "An entry in the modemInfoTable, each relating to a host."
      INDEX   { modemIndex }
      ::= { modemInfoTable 1 }

  ModemInfoEntry ::=
      SEQUENCE {
        modemIndex
              INTEGER,
        modemStatus
              RowStatus,
        modemName
              DisplayString,
        modemInitialisation
              DisplayString
      }

  modemIndex OBJECT-TYPE
      SYNTAX      INTEGER
      MAX-ACCESS  not-accessible
      STATUS      current
      DESCRIPTION
              "The table entry number for this modem"
      ::= { modemInfoEntry 1 }

  modemStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { modemInfoEntry 2 }

  modemName OBJECT-TYPE
      SYNTAX      DisplayString(SIZE(0..20))
      MAX-ACCESS  read-write
      STATUS      current
      DESCRIPTION
              "The modem name used for this modem entry. If blank, this entry
               is currently unused."
      ::= { modemInfoEntry 3 }

  modemInitialisation OBJECT-TYPE
      SYNTAX      DisplayString(SIZE(0..30))
      MAX-ACCESS  read-write
      STATUS      current
      DESCRIPTION
              "The modem Initialisation string"
      ::= { modemInfoEntry 4 }


-- Services Info

  serviceStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {servicesInfo 1}

  serviceDHCP OBJECT-TYPE
      SYNTAX      OnOffValue
      MAX-ACCESS  read-write
      STATUS      current
      DESCRIPTION
               "Turn on/off the DHCP Service"
      ::= {servicesInfo 2}

  serviceRouteD OBJECT-TYPE
      SYNTAX      OnOffValue
      MAX-ACCESS  read-write
      STATUS      current
      DESCRIPTION
               "RouteD Service"
      ::= {servicesInfo 3}

  serviceTelnetD OBJECT-TYPE
      SYNTAX      OnOffValue
      MAX-ACCESS  read-write
      STATUS      current
      DESCRIPTION
               "Turn on/off the TelnetD Service"
      ::= {servicesInfo 4}

  serviceSSHD OBJECT-TYPE
      SYNTAX      OnOffValue
      MAX-ACCESS  read-write
      STATUS      current
      DESCRIPTION
               "Turn on/off the SSHD Service"
      ::= {servicesInfo 5}

  serviceHTTPD OBJECT-TYPE
      SYNTAX      OnOffValue
      MAX-ACCESS  read-write
      STATUS      current
      DESCRIPTION
               "Turn on/off the HTTPD Service"
      ::= {servicesInfo 6}

  serviceSnmpD OBJECT-TYPE
      SYNTAX      OnOffValue
      MAX-ACCESS  read-write
      STATUS      current
      DESCRIPTION
               "Turn on/off the SnmpD Service"
      ::= {servicesInfo 7}

  serviceSPCD OBJECT-TYPE
      SYNTAX      OnOffValue
      MAX-ACCESS  read-write
      STATUS      current
      DESCRIPTION
               "Turn on/off the SPCD Service (TruePort)"
      ::= {servicesInfo 8}

  serviceSNTP OBJECT-TYPE
      SYNTAX      OnOffValue
      MAX-ACCESS  read-write
      STATUS      current
      DESCRIPTION
               "Turn on/off the SNTP Service"
      ::= {servicesInfo 9}

  serviceHTTPSD OBJECT-TYPE
      SYNTAX      OnOffValue
      MAX-ACCESS  read-write
      STATUS      current
      DESCRIPTION
               "Turn on/off the HTTPSD Service"
      ::= {servicesInfo 10}

  serviceSyslog OBJECT-TYPE
      SYNTAX      OnOffValue
      MAX-ACCESS  read-write
      STATUS      current
      DESCRIPTION
               "Turn on/off the Syslog Service"
      ::= {servicesInfo 11}

  serviceDeviceManagerD OBJECT-TYPE
      SYNTAX      OnOffValue
      MAX-ACCESS  read-write
      STATUS      current
      DESCRIPTION
               "Turn on/off the DeviceManagerD Service"
      ::= {servicesInfo 12}
	  
  serviceMODBUSD OBJECT-TYPE
      SYNTAX      OnOffValue
      MAX-ACCESS  read-write
      STATUS      current
      DESCRIPTION
               "Turn on/off the Modbus Gateway Service"
      ::= {servicesInfo 13}

  serviceSecondaryDHCP OBJECT-TYPE
      SYNTAX      OnOffValue
      MAX-ACCESS  read-write
      STATUS      current
      DESCRIPTION
               "Turn on/off the DHCP Service on The eth2 interface"
      ::= {servicesInfo 14}	  
      
-- Trueport Info

  trueportStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {trueportInfo 1}

  trueport50 OBJECT-TYPE
      SYNTAX TrueportBaud
      MAX-ACCESS  read-write
      STATUS      current
      DESCRIPTION
               "Mapping for trueport baud rate 50"
      ::= {trueportInfo 2}

  trueport75 OBJECT-TYPE
      SYNTAX TrueportBaud
      MAX-ACCESS  read-write
      STATUS      current
      DESCRIPTION
               "Mapping for trueport baud rate 75"
      ::= {trueportInfo 3}

  trueport110 OBJECT-TYPE
      SYNTAX TrueportBaud
      MAX-ACCESS  read-write
      STATUS      current
      DESCRIPTION
               "Mapping for trueport baud rate 110"
      ::= {trueportInfo 4}

  trueport134 OBJECT-TYPE
      SYNTAX TrueportBaud
      MAX-ACCESS  read-write
      STATUS      current
      DESCRIPTION
               "Mapping for trueport baud rate 134"
      ::= {trueportInfo 5}

  trueport150 OBJECT-TYPE
      SYNTAX TrueportBaud
      MAX-ACCESS  read-write
      STATUS      current
      DESCRIPTION
               "Mapping for trueport baud rate 150"
      ::= {trueportInfo 6}

  trueport200 OBJECT-TYPE
      SYNTAX TrueportBaud
      MAX-ACCESS  read-write
      STATUS      current
      DESCRIPTION
               "Mapping for trueport baud rate 200"
      ::= {trueportInfo 7}

  trueport300 OBJECT-TYPE
      SYNTAX TrueportBaud
      MAX-ACCESS  read-write
      STATUS      current
      DESCRIPTION
               "Mapping for trueport baud rate 300"
      ::= {trueportInfo 8}

  trueport600 OBJECT-TYPE
      SYNTAX TrueportBaud
      MAX-ACCESS  read-write
      STATUS      current
      DESCRIPTION
               "Mapping for trueport baud rate 600"
      ::= {trueportInfo 9}

  trueport1200 OBJECT-TYPE
      SYNTAX TrueportBaud
      MAX-ACCESS  read-write
      STATUS      current
      DESCRIPTION
               "Mapping for trueport baud rate 1200"
      ::= {trueportInfo 10}

  trueport1800 OBJECT-TYPE
      SYNTAX TrueportBaud
      MAX-ACCESS  read-write
      STATUS      current
      DESCRIPTION
               "Mapping for trueport baud rate 1800"
      ::= {trueportInfo 11}

  trueport2400 OBJECT-TYPE
      SYNTAX TrueportBaud
      MAX-ACCESS  read-write
      STATUS      current
      DESCRIPTION
               "Mapping for trueport baud rate 2400"
      ::= {trueportInfo 12}

  trueport4800 OBJECT-TYPE
      SYNTAX TrueportBaud
      MAX-ACCESS  read-write
      STATUS      current
      DESCRIPTION
               "Mapping for trueport baud rate 4800"
      ::= {trueportInfo 13}

  trueport9600 OBJECT-TYPE
      SYNTAX TrueportBaud
      MAX-ACCESS  read-write
      STATUS      current
      DESCRIPTION
               "Mapping for trueport baud rate 9600"
      ::= {trueportInfo 14}

  trueport19200 OBJECT-TYPE
      SYNTAX TrueportBaud
      MAX-ACCESS  read-write
      STATUS      current
      DESCRIPTION
               "Mapping for trueport baud rate 19200"
      ::= {trueportInfo 15}

  trueport38400 OBJECT-TYPE
      SYNTAX TrueportBaud
      MAX-ACCESS  read-write
      STATUS      current
      DESCRIPTION
               "Mapping for trueport baud rate 38400"
      ::= {trueportInfo 16}

  trueportCustom50 OBJECT-TYPE
      SYNTAX      INTEGER (50..230400)
      MAX-ACCESS  read-write
      STATUS      current
      DESCRIPTION
               "Mapping for trueport baud rate 50"
      ::= {trueportInfo 17}

  trueportCustom75 OBJECT-TYPE
      SYNTAX      INTEGER (50..230400)
      MAX-ACCESS  read-write
      STATUS      current
      DESCRIPTION
               "custom mapping for trueport baud rate 75"
      ::= {trueportInfo 18}

  trueportCustom110 OBJECT-TYPE
      SYNTAX      INTEGER (50..230400)
      MAX-ACCESS  read-write
      STATUS      current
      DESCRIPTION
               "custom mapping for trueport baud rate 110"
      ::= {trueportInfo 19}

  trueportCustom134 OBJECT-TYPE
      SYNTAX      INTEGER (50..230400)
      MAX-ACCESS  read-write
      STATUS      current
      DESCRIPTION
               "custom mapping for trueport baud rate 134"
      ::= {trueportInfo 20}

  trueportCustom150 OBJECT-TYPE
      SYNTAX      INTEGER (50..230400)
      MAX-ACCESS  read-write
      STATUS      current
      DESCRIPTION
               "custom mapping for trueport baud rate 150"
      ::= {trueportInfo 21}

  trueportCustom200 OBJECT-TYPE
      SYNTAX      INTEGER (50..230400)
      MAX-ACCESS  read-write
      STATUS      current
      DESCRIPTION
               "custom mapping for trueport baud rate 200"
      ::= {trueportInfo 22}

  trueportCustom300 OBJECT-TYPE
      SYNTAX      INTEGER (50..230400)
      MAX-ACCESS  read-write
      STATUS      current
      DESCRIPTION
               "custom mapping for trueport baud rate 300"
      ::= {trueportInfo 23}

  trueportCustom600 OBJECT-TYPE
      SYNTAX      INTEGER (50..230400)
      MAX-ACCESS  read-write
      STATUS      current
      DESCRIPTION
               "custom mapping for trueport baud rate 600"
      ::= {trueportInfo 24}

  trueportCustom1200 OBJECT-TYPE
      SYNTAX      INTEGER (50..230400)
      MAX-ACCESS  read-write
      STATUS      current
      DESCRIPTION
               "custom mapping for trueport baud rate 1200"
      ::= {trueportInfo 25}

  trueportCustom1800 OBJECT-TYPE
      SYNTAX      INTEGER (50..230400)
      MAX-ACCESS  read-write
      STATUS      current
      DESCRIPTION
               "custom mapping for trueport baud rate 1800"
      ::= {trueportInfo 26}

  trueportCustom2400 OBJECT-TYPE
      SYNTAX      INTEGER (50..230400)
      MAX-ACCESS  read-write
      STATUS      current
      DESCRIPTION
               "custom mapping for trueport baud rate 2400"
      ::= {trueportInfo 27}

  trueportCustom4800 OBJECT-TYPE
      SYNTAX      INTEGER (50..230400)
      MAX-ACCESS  read-write
      STATUS      current
      DESCRIPTION
               "custom mapping for trueport baud rate 4800"
      ::= {trueportInfo 28}

  trueportCustom9600 OBJECT-TYPE
      SYNTAX      INTEGER (50..230400)
      MAX-ACCESS  read-write
      STATUS      current
      DESCRIPTION
               "custom mapping for trueport baud rate 9600"
      ::= {trueportInfo 29}

  trueportCustom19200 OBJECT-TYPE
      SYNTAX      INTEGER (50..230400)
      MAX-ACCESS  read-write
      STATUS      current
      DESCRIPTION
               "custom mapping for trueport baud rate 19200"
      ::= {trueportInfo 30}

  trueportCustom38400 OBJECT-TYPE
      SYNTAX      INTEGER (50..230400)
      MAX-ACCESS  read-write
      STATUS      current
      DESCRIPTION
               "custom mapping for trueport baud rate 38400"
      ::= {trueportInfo 31}
-- Radius Info

  radiusStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {radiusInfo 1}

  radiusPrimaryAuthHost OBJECT-TYPE
      SYNTAX   DisplayString(SIZE(0..14))
      MAX-ACCESS    read-write
      STATUS        current
      DESCRIPTION
                "Primary Radius Authentication Host"
      ::= {radiusInfo 2}

  radiusSecondaryAuthHost OBJECT-TYPE
      SYNTAX   DisplayString(SIZE(0..14))
      MAX-ACCESS    read-write
      STATUS        current
      DESCRIPTION
                "Secondary Radius Authentication Host"
      ::= {radiusInfo 3}

  radiusAuthenticationPort OBJECT-TYPE
      SYNTAX   INTEGER(0..65535)
      MAX-ACCESS    read-write
      STATUS        current
      DESCRIPTION
                "The port that the RADIUS host listens to for 
                 authentication requests. The default port is 1812."
      ::= {radiusInfo 4}

  radiusAccountingEnabled OBJECT-TYPE
      SYNTAX   OnOffValue
      MAX-ACCESS    read-write
      STATUS        current
      DESCRIPTION
                "Radius Accounting enabled"
      ::= {radiusInfo 5}

  radiusPrimaryAcctHost OBJECT-TYPE
      SYNTAX   DisplayString(SIZE(0..14))
      MAX-ACCESS    read-write
      STATUS        current
      DESCRIPTION
                "Name of the primary RADIUS authentication host."
      ::= {radiusInfo 6}

  radiusSecondaryAcctHost OBJECT-TYPE
      SYNTAX   DisplayString(SIZE(0..14))
      MAX-ACCESS    read-write
      STATUS        current
      DESCRIPTION
                "Name of the secondary RADIUS authentication host."
      ::= {radiusInfo 7}

  radiusAccountingPort OBJECT-TYPE
      SYNTAX   INTEGER(0..65535)
      MAX-ACCESS    read-write
      STATUS        current
      DESCRIPTION
                "The port that the RADIUS host listens to for 
                 accounting requests. The default port is 1813."
      ::= {radiusInfo 8}

  radiusAcctAuth OBJECT-TYPE
      SYNTAX   OnOffValue
      MAX-ACCESS    read-write
      STATUS        current
      DESCRIPTION
                "Radius Accounting Authenticator enabled"
      ::= {radiusInfo 9}

  radiusRetryLimit OBJECT-TYPE
      SYNTAX   INTEGER (0..255)
      MAX-ACCESS    read-write
      STATUS        current
      DESCRIPTION
                "The number of times the Device Server tries
                     to connect to the RADIUS server before erroring
                     out. Valid values are 0-255. The default is 5."
      ::= {radiusInfo 10}

  radiusTimeout OBJECT-TYPE
      SYNTAX   INTEGER (1..255)
      MAX-ACCESS    read-write
      STATUS        current
      DESCRIPTION
                "The time, in seconds, that the Device Server waits
                     to receive a reply after sending out a request to
                     a RADIUS accounting or authentication host. If no
                     reply is received before the timeout period expires,
                     the Device Server will retry the same host up to and
                     including the number of retry attempts. Valid values
                     are 1-255. The default is 3 seconds."
      ::= {radiusInfo 11}

-- Kerberos Info

  kerberosStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {kerberosInfo 1}

  kerberosRealm OBJECT-TYPE
      SYNTAX   DisplayString(SIZE(0..32))
      MAX-ACCESS    read-write
      STATUS        current
      DESCRIPTION
                "The Kerberos realm is the Kerberos host domain name,
                     in upper-case letters."
      ::= {kerberosInfo 2}

  kerberosDomain OBJECT-TYPE
      SYNTAX   DisplayString(SIZE(0..32))
      MAX-ACCESS    read-write
      STATUS        current
      DESCRIPTION
                "The name of a host running the KDC (Key Distribution
                     Center) for the specified realm. The host name that
                     you specifiy must either be defined in the Device
                     Server's Host Table before the last reboot or be
                     resolved by DNS."
      ::= {kerberosInfo 3}

  kerberosPort OBJECT-TYPE
      SYNTAX   INTEGER(0..65535)
      MAX-ACCESS    read-write
      STATUS        current
      DESCRIPTION
                "The port that the Kerberos server listens to for
                     authentication requests. If no port is specified,
                     the default port 88 is used."
      ::= {kerberosInfo 4}


-- ldap Info

  ldapStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {ldapInfo 1}

  ldapHost OBJECT-TYPE
      SYNTAX   DisplayString(SIZE(0..64))
      MAX-ACCESS    read-write
      STATUS        current
      DESCRIPTION
                "The name or IP address of the LDAP host. If you use
                     a host name, that host must either have been defined
                     in the Device Server's Host Table before the last
                     reboot or be resolved by DNS. If you are using TLS,
                     you must enter the same string you used to create
                     the LDAP certificate. "
      ::= {ldapInfo 2}

  ldapPort OBJECT-TYPE
      SYNTAX   INTEGER(0..65535)
      MAX-ACCESS    read-write
      STATUS        current
      DESCRIPTION
                "The port that the LDAP host listens to for
                     authentication requests. The default port is 389."
      ::= {ldapInfo 3}

  ldapBase OBJECT-TYPE
      SYNTAX   DisplayString(SIZE(0..64))
      MAX-ACCESS    read-write
      STATUS        current
      DESCRIPTION
                "The domain component (dc) that is the starting
                     point for the search for user authentication."
      ::= {ldapInfo 4}

  ldapEnableTLS OBJECT-TYPE
      SYNTAX   OnOffValue
      MAX-ACCESS    read-write
      STATUS        current
      DESCRIPTION
                "Enables/disables the Transport Layer Security
                     (TLS) with the LDAP host."
      ::= {ldapInfo 5}

  ldapTLSPort OBJECT-TYPE
      SYNTAX   INTEGER(0..65535)
      MAX-ACCESS    read-write
      STATUS        current
      DESCRIPTION
                "Specify the port number that LDAP will use
                     for TLS. The default is port 636."
      ::= {ldapInfo 6}


-- TACACS Info

  tacacsStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {tacacsInfo 1}

  tacacsPrimaryHost OBJECT-TYPE
      SYNTAX   DisplayString(SIZE(0..14))
      MAX-ACCESS    read-write
      STATUS        current
      DESCRIPTION
                "The primary TACACS+ host that is used
                     for authentication."
      ::= {tacacsInfo 2}

  tacacsSecondaryHost OBJECT-TYPE
      SYNTAX   DisplayString(SIZE(0..14))
      MAX-ACCESS    read-write
      STATUS        current
      DESCRIPTION
                "The secondary TACACS+ host that is used
                     for authentication, should the primary
                     TACACS+ host fail to respond."
      ::= {tacacsInfo 3}

  tacacsPort OBJECT-TYPE
      SYNTAX   INTEGER(0..65535)
      MAX-ACCESS    read-write
      STATUS        current
      DESCRIPTION
                "The port number that TACACS+ listens to
                     for authentication requests. The default
                     port number is 49."
      ::= {tacacsInfo 4}
      
  tacacsAccounting OBJECT-TYPE
      SYNTAX   OnOffValue
      MAX-ACCESS    read-write
      STATUS        current
      DESCRIPTION
                "Enable/Disable TACACS+ accounting"
      ::= {tacacsInfo 5}
      
  tacacsAccountingPrimaryHost OBJECT-TYPE
      SYNTAX   DisplayString(SIZE(0..14))
      MAX-ACCESS    read-write
      STATUS        current
      DESCRIPTION
                "The primary TACACS+ accounting host that is used
                     for."
      ::= {tacacsInfo 6}

  tacacsAccountingSecondaryHost OBJECT-TYPE
      SYNTAX   DisplayString(SIZE(0..14))
      MAX-ACCESS    read-write
      STATUS        current
      DESCRIPTION
                "The secondary TACACS+ accounting host that is used
                     for , should the primary TACACS+ host fail 
                     to respond."
      ::= {tacacsInfo 7}

  tacacsAccountingPort OBJECT-TYPE
      SYNTAX   INTEGER(0..65535)
      MAX-ACCESS    read-write
      STATUS        current
      DESCRIPTION
                "The port number that TACACS+ listens to
                     for accouting requests. The default
                     port number is 49."
      ::= {tacacsInfo 8}

  tacacsAuthorization OBJECT-TYPE
      SYNTAX   OnOffValue
      MAX-ACCESS    read-write
      STATUS        current
      DESCRIPTION
                "Enable/Disable TACACS+ authorisation"
      ::= {tacacsInfo 9}
 
-- Securid Info

  securidStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {securidInfo 1}

  securidMasterHost OBJECT-TYPE
      SYNTAX   DisplayString(SIZE(0..14))
      MAX-ACCESS    read-write
      STATUS        current
      DESCRIPTION
                "The first SecurID server that is tried for
                     user authentication."
      ::= {securidInfo 2}

  securidSlaveHost OBJECT-TYPE
      SYNTAX   DisplayString(SIZE(0..14))
      MAX-ACCESS    read-write
      STATUS        current
      DESCRIPTION
                "If the first SecurID server does not respond
                     to an authentication request, this is the next
                     SecurID server that is tried for user authentication."
      ::= {securidInfo 3}

  securidPort OBJECT-TYPE
      SYNTAX   INTEGER (0..65535)
      MAX-ACCESS    read-write
      STATUS        current
      DESCRIPTION
                "The port number that SecurID listens to for
                     authentication requests. The default port number is 5500."
      ::= {securidInfo 4}

  securidType OBJECT-TYPE
      SYNTAX   INTEGER {
            des(1),
        sdi(2)
        }
      MAX-ACCESS    read-write
      STATUS        current
      DESCRIPTION
                "You can specify either SDI or DES encryption for SecurID
                     server communication. The default is SDI encryption."
      ::= {securidInfo 5}

  securidLegacy OBJECT-TYPE
      SYNTAX   YesNoValue
      MAX-ACCESS    read-write
      STATUS        current
      DESCRIPTION
                "If you are running SecurID 3.x or 4.x, you need to run
                     in Legacy Mode. If you are running SecurID 5.x or above,
                     do not select Legacy Mode."
      ::= {securidInfo 6}

-- NIS Info
  nisStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {nisInfo 1}

  nisDomain OBJECT-TYPE
      SYNTAX   DisplayString(SIZE(0..32))
      MAX-ACCESS    read-write
      STATUS        current
      DESCRIPTION
                "The NIS domain name."
      ::= {nisInfo 2}

  nisPrimaryHost OBJECT-TYPE
      SYNTAX   DisplayString(SIZE(0..14))
      MAX-ACCESS    read-write
      STATUS        current
      DESCRIPTION
                "The primary NIS host that is used for authentication."
      ::= {nisInfo 3}

  nisSecondaryHost OBJECT-TYPE
      SYNTAX   DisplayString(SIZE(0..14))
      MAX-ACCESS    read-write
      STATUS        current
      DESCRIPTION
                "The secondary NIS host that is used for authentication,
                     should the primary NIS host fail to respond."
      ::= {nisInfo 4}

-- SSH Server Info

  sshServerStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {sshServerInfo 1}

 sshServerRSA OBJECT-TYPE
      SYNTAX   OnOffValue
      MAX-ACCESS    read-write
      STATUS        current
      DESCRIPTION
                "When a client SSH session requests RSA authentication,
                     the Device Server's SSH server will authenticate the
                     user via RSA."
      ::= {sshServerInfo 2}

  sshServerDSA OBJECT-TYPE
      SYNTAX   OnOffValue
      MAX-ACCESS    read-write
      STATUS        current
      DESCRIPTION
                "When a client SSH session requests DSA authentication,
                     the Device Server's SSH server will authenticate the
                     user via DSA"
      ::= {sshServerInfo 3}

  sshServerKeyboard OBJECT-TYPE
      SYNTAX   OnOffValue
      MAX-ACCESS    read-write
      STATUS        current
      DESCRIPTION
                "The user types in a password for authentication."
      ::= {sshServerInfo 4}

  sshServer3Des OBJECT-TYPE
      SYNTAX   OnOffValue
      MAX-ACCESS    read-write
      STATUS        current
      DESCRIPTION
                "The Device Server SSH server's 3DES encryption is
                     enabled/disabled."
      ::= {sshServerInfo 5}

  sshServerBlowfish OBJECT-TYPE
      SYNTAX   OnOffValue
      MAX-ACCESS    read-write
      STATUS        current
      DESCRIPTION
                "The Device Server SSH server's Blowfish encryption
                     is enabled/disabled."
      ::= {sshServerInfo 6}

  sshServerAES OBJECT-TYPE
      SYNTAX   OnOffValue
      MAX-ACCESS    read-write
      STATUS        current
      DESCRIPTION
                "The Device Server SSH server's AES encryption
                     is enabled/disabled"
      ::= {sshServerInfo 7}

  sshServerCAST OBJECT-TYPE
      SYNTAX   OnOffValue
      MAX-ACCESS    read-write
      STATUS        current
      DESCRIPTION
                "The Device Server SSH server's CAST encryption
                     is enabled/disabled"
      ::= {sshServerInfo 8}

  sshServerArcfour OBJECT-TYPE
      SYNTAX   OnOffValue
      MAX-ACCESS    read-write
      STATUS        current
      DESCRIPTION
                "The Device Server SSH server's Arcfour encryption
                     is enabled/disabled."
      ::= {sshServerInfo 9}

  sshServerVerbose OBJECT-TYPE
      SYNTAX   OnOffValue
      MAX-ACCESS    read-write
      STATUS        current
      DESCRIPTION
                "Displays debug messages on the terminal."
      ::= {sshServerInfo 10}

  sshServerCompression OBJECT-TYPE
      SYNTAX   OnOffValue
      MAX-ACCESS    read-write
      STATUS        current
      DESCRIPTION
                "Requests compression of all data. Compression is
                     desirable on modem lines and other slow connections,
                     but will only slow down things on fast networks."
      ::= {sshServerInfo 11}

  sshServerBreakString OBJECT-TYPE
      SYNTAX   DisplayString(SIZE(0..8))
      MAX-ACCESS    read-write
      STATUS        current
      DESCRIPTION
                "The break string used for inband SSH break signal
                     processing. A break signal is generated on a specific
                     serial port only when the server's break option is
                     enabled and the user currently connected using reverse
                     SSH has typed the break string exactly. The default is
                     set to ~break, where ~ is tilde; the break string can
                     be up to eight characters."
      ::= {sshServerInfo 12}

 sshServerSSH1 OBJECT-TYPE
      SYNTAX   OnOffValue
      MAX-ACCESS    read-write
      STATUS        current
      DESCRIPTION
                "Enable/Disable SSH-1 on the server."
      ::= {sshServerInfo 13}

  sshServerPassword OBJECT-TYPE
      SYNTAX   OnOffValue
      MAX-ACCESS    read-write
      STATUS        current
      DESCRIPTION
                "The user types in a password for authentication."
      ::= {sshServerInfo 14}

      
-- Default user Info

  defUserStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { defUserInfo 1}

  defUserService OBJECT-TYPE
      SYNTAX      INTEGER {
        dsprompt(1),
        telnet(2),
        ssh(3),
        rlogin(4),
        slip(5),
        ppp(6),
        tcpclear(7),
        sslraw(8)
      }
      MAX-ACCESS  read-write
      STATUS      current
      DESCRIPTION
              "The type of service that the user will use:
               dsprompt, telnet, ssh, rlogin, slip, ppp, tcpclear
               or sslraw."
      ::= { defUserInfo 2 }

   defUserLanguage OBJECT-TYPE
      SYNTAX      INTEGER {
        english(1),
        custom(2)
      }
      MAX-ACCESS  read-write
      STATUS      current
      DESCRIPTION
              "You can specify whether a user will use English or
               Customlang as the language that appears in the Menu,
               CLI, or WebManager. The Device Server supports one custom
               language that must be downloaded to the Device Server;
               otherwise, Customlang defaults to English."
      ::= { defUserInfo 3 }

   defUserLevel OBJECT-TYPE
      SYNTAX      INTEGER {
        admin(1),
        normal(2),
        restricted(3),
        menu(4)
      }
      MAX-ACCESS  read-write
      STATUS      current
      DESCRIPTION
              "The access that a user is allowed:
               Admin-The admin level user has total access to the Device Server.
                     You can create more than one admin user account but we
                     recommend that you only have one. They can monitor and
                     configure the Device Server.
               Normal-The Normal level user has limited access to the Device Server.
                     Limited CLI commands and Menu access are available with the
                     ability to configure the user's own configuration settings.
               Restricted-The Restricted level user can only access predefined
                     sessions or access the Easy Port Access menu. Can only view or
                     monitor the Device Server using CLI commands to display
                     information about the Device Server.
               Menu-The menu level user will only be able to access predefined session
                     or access the Easy Port Access menu. The Easy Port Access allows
                     the user to connect to the accessible line without disconnecting
                     their initial connection to the Device Server. Does not have any
                     access to CLI commands."
      ::= { defUserInfo 4}

   defUserHotKeyPrefix OBJECT-TYPE
      SYNTAX      Hex8
      MAX-ACCESS  read-write
      STATUS      current
      DESCRIPTION
              "The prefix that a user types to control the current session. The default
               value is hex 01, which corresponds to Ctrl-a (^a) (hex value 02 would
               be Ctrl-b (^b), etc.):
               ^a number-To switch from one session to another, press ^a and then the
                     required session number. For example, ^a 2 would switch you to
                     session 2. Pressing ^a 0 will return you to the Device Server Menu.
               ^a n-Display the next session. The current session will remain active. The
                     lowest numbered active session will be displayed.
               ^a p-Display the previous session. The current session will remain active.
                     The highest numbered active session will be displayed.
               ^a m-To exit a session and return to the Device Server. You will be
                     returned to where you left off. The session will be left running.
               ^a l-(Lowercase L) Locks the line until the user unlocks it. The user is
                     prompted for a password (any password, excluding spaces) and locks
                     the line. Next, the user must retype the password to unlock the line.
               ^r-When you switch from a session back to the Menu, the screen may not be
                     redrawn correctly. If this happens, use this command to redraw it properly.
               The User Hotkey Prefix value overrides the Line Hotkey Prefix value. You can
               use the Hotkey Prefix keys to lock a line only when the line Lock parameter is On."
      ::= { defUserInfo 5}

   defUserPhoneNumber OBJECT-TYPE
      SYNTAX      DisplayString(SIZE(0..32))
      MAX-ACCESS  read-write
      STATUS      current
      DESCRIPTION
              "The phone number the Device Server will dial to callback the user
               (you must have set Callback to On). Enter the number without spaces."
      ::= { defUserInfo 6}

   defUserCallBack OBJECT-TYPE
      SYNTAX      OnOffValue
      MAX-ACCESS  read-write
      STATUS      current
      DESCRIPTION
              "When On, enter a phone number for the Device Server to call the user
               back (the Callback parameter is unrelated to the Line Dial parameter).
               Note: the Device Server will allow callback only when a user is
               authenticated. If the protocol over the link does not provide
               authentication, there will be no callback. Therefore, when the Line
               Service is set to PPP, you must use either PAP or CHAP, because these
               protocols provide authentication. The default is Off. The Device Server
               supports another type of callback, Roaming Callback, which is
               configurable when the Line Service is set to PPP."
      ::= { defUserInfo 7}

   defUserIdleTimer OBJECT-TYPE
      SYNTAX      INTEGER (0..4294967)
      MAX-ACCESS  read-write
      STATUS      current
      DESCRIPTION
              "The amount of time, in seconds, that the Idle Timer will run. Use this timer
               to close a connection because of inactivity. When the Idle Timer expires, because
               there has been no exchange of data within the specified time, the Device Server
               will close the connection. The default value is 0 (zero), meaning that the
               Idle Timer will not expire (the connection is open permanently). The maximum value
               is 4294967 seconds. The User Idle Timer will override the Line Idle Timer, with
               the exception of reverse Telnet sessions."
      ::= { defUserInfo 8}

   defUserSessionTimer OBJECT-TYPE
      SYNTAX      INTEGER (0..4294967)
      MAX-ACCESS  read-write
      STATUS      current
      DESCRIPTION
              "Enter a time, in seconds, for which the Session Timer will run. Use this
               timer to forcibly close the session (connection). When the Session Timer
               expires, the Device Server will end the connection. The default value is
               0 seconds so the port will never timeout. The maximum value is 4294967
               seconds (about 49 days)."
      ::= { defUserInfo 9}

   defUserIpHost OBJECT-TYPE
      SYNTAX      Ipv4v6Address
      MAX-ACCESS  read-write
      STATUS      current
      DESCRIPTION
              "When the User Service is set to Telnet, TCP_clear or SSL_RAW, the target
               host IP address. If 255.255.255.255 is specified in the configuration,
               the user will be prompted for an IP address or hostname. If no IP
               address is specified, the Host IP value in the Default User configuration
               will be used. The default is 0.0.0.0."
      ::= { defUserInfo 10}

   defUserTelnetPort OBJECT-TYPE
      SYNTAX      INTEGER(0..65535)
      MAX-ACCESS  read-write
      STATUS      current
      DESCRIPTION
              "The port number the target host is listening on for
               incoming connections. Default is 23."
      ::= { defUserInfo 11}

   defUserSSHPort OBJECT-TYPE
      SYNTAX      INTEGER(0..65535)
      MAX-ACCESS  read-write
      STATUS      current
      DESCRIPTION
              "userSSHPort"
      ::= { defUserInfo 12}

   defUserTcpPort OBJECT-TYPE
      SYNTAX      INTEGER(0..65535)
      MAX-ACCESS  read-write
      STATUS      current
      DESCRIPTION
              "The port number for the TCP-Clear or SSL-Raw session."
      ::= { defUserInfo 13}

   defUserFramedIp OBJECT-TYPE
      SYNTAX      IpAddress
      MAX-ACCESS  read-write
      STATUS      current
      DESCRIPTION
              "Used for User Service PPP or SLIP, sets the IP address of the
               remote user. Enter the address in dot decimal notation as follows:
               255.255.255.254 (default)-The Device Server will use the Remote
                  IP Address set in the PPP settings for the line.
               255.255.255.255-When the User Service is PPP, the Device Server will
                  allow the remote machine to specify its IP address (overriding
                  the IP address negotiation value configured in the PPP settings).
               255.255.255.255-When the User Service is SLIP, the Device Server will
                  use the Remote IP Address set for the line (no negotiation).
               n.n.n.n-(where n is a number) Enter the IP address of your choice.
                  This IP address will then be used in preference to the Remote IP
                  Address set for a line."
      ::= { defUserInfo 14}

   defUserSubnetBits OBJECT-TYPE
      SYNTAX      INTEGER (0..32)
      MAX-ACCESS  read-write
      STATUS      current
      DESCRIPTION
              "(IPV4 only) If the remote user is on a subnet, enter the number of
               bits in the subnet mask. For example, a subnet mask of 255.255.0.0
               has 16 subnet/prefix bits."
      ::= { defUserInfo 15}

   defUserIpv6InterfaceId OBJECT-TYPE
      SYNTAX      Ipv6InterfaceId
      MAX-ACCESS  read-write
      STATUS      current
      DESCRIPTION
              "Used for User Service PPP, sets the IP address of the remote user.
               Enter the address in IPv6 format. The first 64 bits of the Interface
               Identifier must be zero, therefore, ::abcd:abcd:abcd:abcd is the
               expected format."
      ::= { defUserInfo 16}

   defUserFramedMtu OBJECT-TYPE
      SYNTAX      INTEGER (64..1500)
      MAX-ACCESS  read-write
      STATUS      current
      DESCRIPTION
              "Used for User Service PPP or SLIP, specifies the maximum size of
               packets, in bytes, being transferred across the link. On noisy
               links it might be preferable to fragment large packets being
               transferred over the link, since there will be quicker recovery
               from errors. Depending on whether you have selected a User Service
               of SLIP or PPP, details are as follows:
               PPP-Framed MTU will be the maximum size of packets that the Device
                  Server port will accept. This value is negotiated between the
                  two ends of the link. The valid range is 64-1500. The default
                  is 1500 bytes.
               SLIP-Framed MTU will be the maximum size of packets being sent by
                  the Device Server. The Device Server will send SLIP packets in
                  the range 256-1006 bytes. The default value is 256 bytes.
               The Framed MTU value will be used in preference to the MTU/MRU values
               set for a Line."
      ::= { defUserInfo 17}

   defUserFramedCompression OBJECT-TYPE
      SYNTAX      OnOffValue
      MAX-ACCESS  read-write
      STATUS      current
      DESCRIPTION
              "Used for User Service PPP or SLIP, determines whether Van Jacobsen
               Compression is used on the link. VJ compression is a means of reducing
               the standard TCP/IP header from 40 octets to approximately 5 octets.
               This gives a significant performance improvement, particularly when
               interactive applications are being used. For example, when the user is
               typing, a single character can be passed over the link with a 40 octet
               header attached. VJ Compression has little effect on other types of links,
               such as ftp, where the packets are much larger. The Framed Compression
               value will be used in preference to the VJ Compression value set for a
               Line. The default is Off."
      ::= { defUserInfo 18}

   defUserRouting OBJECT-TYPE
      SYNTAX      INTEGER {
        none(1),
        send(2),
        listen(3),
        sendAndListen(4)
      }
      MAX-ACCESS  read-write
      STATUS      current
      DESCRIPTION
              "Determines the routing mode used for RIP packets on the PPP and SLIP
               interfaces. Values are:
               None-RIP packets are neither received nor sent by the Device Server.
               Send-RIP packets can only be sent by the Device Server.
               Listen-RIP packets can only be received by the Device Server.
               Send and Listen-RIP packets are sent and received by the Device Server."
      ::= { defUserInfo 19}
      
    defUserAllowAccessClusterPorts OBJECT-TYPE
      SYNTAX      OnOffValue
      MAX-ACCESS  read-write
      STATUS      current
      DESCRIPTION
              "Allow/disallow the user to access to clustering ports."
      ::= { defUserInfo 20 }

    defUserHost OBJECT-TYPE
      SYNTAX      DisplayString (SIZE(0..14))
      MAX-ACCESS  read-write
      STATUS      current
      DESCRIPTION
              "The name of the  host."
      ::= { defUserInfo 21}

-- Default User Port Access Table

  defUserPortAccessTable OBJECT-TYPE
      SYNTAX      SEQUENCE OF PortAccessEntry
      MAX-ACCESS  not-accessible
      STATUS      current
      DESCRIPTION
              "The port access info table for user."
      ::= { defUserInfo 22 }

  defUserPortAccessEntry OBJECT-TYPE
      SYNTAX      DefUserPortAccessEntry
      MAX-ACCESS  not-accessible
      STATUS      current
      DESCRIPTION
              "An entry in the portAccessTable, each relating to a user's
               access privileges for a serial port."
      INDEX   { defUserPortAccessPortIndex }
      ::= { defUserPortAccessTable 1 }

  DefUserPortAccessEntry ::=
      SEQUENCE {
        defUserPortAccessPortIndex
              INTEGER,
        defUserPortAccessStatus
              RowStatus,
        defUserPortRWAccessAllowed
              YesNoValue,
        defUserPortRIAccessAllowed
              YesNoValue,
        defUserPortROAccessAllowed
              YesNoValue
      }

  defUserPortAccessPortIndex OBJECT-TYPE
      SYNTAX      INTEGER
      MAX-ACCESS  not-accessible
      STATUS      current
      DESCRIPTION
              "The port number that user access applies to."
      ::= { defUserPortAccessEntry 1 }

  defUserPortAccessStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { defUserPortAccessEntry 2 }

  defUserPortRWAccessAllowed OBJECT-TYPE
      SYNTAX      YesNoValue
      MAX-ACCESS  read-write
      STATUS      current
      DESCRIPTION
              "Enable or disable the user's read write access to the port."
      ::= { defUserPortAccessEntry 3 }

  defUserPortRIAccessAllowed OBJECT-TYPE
      SYNTAX      YesNoValue
      MAX-ACCESS  read-write
      STATUS      current
      DESCRIPTION
              "Enable or disable the user's read input access to the port."
      ::= { defUserPortAccessEntry 4 }

  defUserPortROAccessAllowed OBJECT-TYPE
      SYNTAX      YesNoValue
      MAX-ACCESS  read-write
      STATUS      current
      DESCRIPTION
              "Enable or disable the user's read output access to the port."
      ::= { defUserPortAccessEntry 5 }

-- SNMP Info

   snmpStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { snmpInfo 1}

   snmpContact OBJECT-TYPE
      SYNTAX      DisplayString(SIZE(0..14))
      MAX-ACCESS  read-write
      STATUS      current
      DESCRIPTION
              "The name and contract information of the person who manages this SMNP node."
      ::= { snmpInfo 2}

   snmpLocation OBJECT-TYPE
      SYNTAX      DisplayString(SIZE(0..32))
      MAX-ACCESS  read-write
      STATUS      current
      DESCRIPTION
              "The physical location of the SNMP node."
      ::= { snmpInfo 3}

   snmpReadOnlyUser OBJECT-TYPE
      SYNTAX      DisplayString(SIZE(0..16))
      MAX-ACCESS  read-write
      STATUS      current
      DESCRIPTION
              "(SNMP version 3) Specified user can only view SNMP variables."
      ::= { snmpInfo 4}

   snmpReadWriteUser OBJECT-TYPE
      SYNTAX      DisplayString(SIZE(0..16))
      MAX-ACCESS  read-write
      STATUS      current
      DESCRIPTION
              "(SNMP version 3) Specified user can view and edit SNMP variables."
      ::= { snmpInfo 5}

-- SNMP Community Info

   snmpCommunityTable OBJECT-TYPE
      SYNTAX      SEQUENCE OF SnmpCommunityEntry
      MAX-ACCESS  not-accessible
      STATUS      current
      DESCRIPTION
              "snmpCommunityTable"
      ::= { snmpInfo 6}

   snmpCommunityEntry OBJECT-TYPE
      SYNTAX      SnmpCommunityEntry
      MAX-ACCESS  not-accessible
      STATUS      current
      DESCRIPTION
               "snmpCommunityEntry"
      INDEX   { snmpCommunityIndex }
      ::= { snmpCommunityTable 1 }

   SnmpCommunityEntry ::=
      SEQUENCE {
        snmpCommunityIndex
              INTEGER,
        snmpCommunityStatus
              RowStatus,
        snmpCommunityName
              DisplayString,
        snmpCommunityIpAddress
              Ipv4v6Address,
        snmpCommunityPermission
              INTEGER
              }

   snmpCommunityIndex OBJECT-TYPE
      SYNTAX      INTEGER
      MAX-ACCESS  not-accessible
      STATUS      current
      DESCRIPTION
              "snmpCommunityIndex"
      ::= { snmpCommunityEntry 1}

  snmpCommunityStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { snmpCommunityEntry 2}

   snmpCommunityName OBJECT-TYPE
      SYNTAX      DisplayString(SIZE(0..14))
      MAX-ACCESS  read-write
      STATUS      current
      DESCRIPTION
              "A name that will be sent to the Device Server from an SNMP
               manager. This name will define the permissions of the manager."
      ::= { snmpCommunityEntry 3}

   snmpCommunityIpAddress OBJECT-TYPE
      SYNTAX      Ipv4v6Address
      MAX-ACCESS  read-write
      STATUS      current
      DESCRIPTION
              "The IP address of the SNMP manager that will send requests to
               the Device Server. If the address is 0.0.0.0, any SNMP manager
               with the Community Name can access the Device Server."
      ::= { snmpCommunityEntry 4}

   snmpCommunityPermission OBJECT-TYPE
      SYNTAX      INTEGER {
        none(1),
        readonly(2),
        readwrite(3)
      }
      MAX-ACCESS  read-write
      STATUS      current
      DESCRIPTION
              "Permits the Device Server to respond to SNMP requests by:
               None-There is no response to requests from SNMP.
               Readonly-Responds only to Read requests from SNMP.
               Readwrite-Responds to both Read and Write requests from SNMP."
      ::= { snmpCommunityEntry 5}

-- SNMP Trap Table

   snmpTrapTable OBJECT-TYPE
      SYNTAX      SEQUENCE OF SnmpTrapEntry
      MAX-ACCESS  not-accessible
      STATUS      current
      DESCRIPTION
              "snmpTrapTable"
      ::= { snmpInfo 7}

   snmpTrapEntry OBJECT-TYPE
      SYNTAX      SnmpTrapEntry
      MAX-ACCESS  not-accessible
      STATUS      current
      DESCRIPTION
               "snmpTrapEntry"
      INDEX   { snmpTrapIndex }
      ::= { snmpTrapTable 1 }

   SnmpTrapEntry ::=
      SEQUENCE {
        snmpTrapIndex
              INTEGER,
        snmpTrapStatus
              RowStatus,
        snmpTrapName
              DisplayString,
        snmpTrapIpAddress
              Ipv4v6Address
              }

   snmpTrapIndex OBJECT-TYPE
      SYNTAX      INTEGER
      MAX-ACCESS  not-accessible
      STATUS      current
      DESCRIPTION
              "snmpTrapIndex"
      ::= { snmpTrapEntry 1}

  snmpTrapStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { snmpTrapEntry 2}

   snmpTrapName OBJECT-TYPE
      SYNTAX      DisplayString(SIZE(0..14))
      MAX-ACCESS  read-write
      STATUS      current
      DESCRIPTION
              "An arbitrary trap community name."
      ::= { snmpTrapEntry 3}

   snmpTrapIpAddress OBJECT-TYPE
      SYNTAX      Ipv4v6Address
      MAX-ACCESS  read-write
      STATUS      current
      DESCRIPTION
              "Defines the hosts (by IP address) that will receive
               trap messages generated by the Device Server. Up to four
               trap hosts can be defined."
      ::= { snmpTrapEntry 4}

-- DNS Info

   dnsTable OBJECT-TYPE
      SYNTAX      SEQUENCE OF DnsEntry
      MAX-ACCESS  not-accessible
      STATUS      current
      DESCRIPTION
              "dnsTable"
      ::= { dnsInfo 1}

   dnsEntry OBJECT-TYPE
      SYNTAX      DnsEntry
      MAX-ACCESS  not-accessible
      STATUS      current
      DESCRIPTION
               "dnsEntry"
      INDEX   { dnsIndex }
      ::= { dnsTable 1 }

   DnsEntry ::=
      SEQUENCE {
        dnsIndex
            INTEGER,
        dnsStatus
            RowStatus,
        dnsIpAddress
            Ipv4v6Address,
        dnsActive
            OnOffValue
          }

   dnsIndex OBJECT-TYPE
      SYNTAX      INTEGER
      MAX-ACCESS  not-accessible
      STATUS      current
      DESCRIPTION
              "dnsIndex"
      ::= { dnsEntry 1}

   dnsStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { dnsEntry 2 }

   dnsIpAddress OBJECT-TYPE
      SYNTAX      Ipv4v6Address
      MAX-ACCESS  read-write
      STATUS      current
      DESCRIPTION
              "You can specify the IP addresses for up to two DNS
               (Domain Name Servers) hosts in your network. The first
               DNS entry in the list is the primary DNS and the second
               DNS entry is the secondary server."
      ::= { dnsEntry 3}

   dnsActive OBJECT-TYPE
      SYNTAX      OnOffValue
      MAX-ACCESS  read-write
      STATUS      current
      DESCRIPTION
              "Activates/deactivates a DNS entry."
      ::= { dnsEntry 4}


-- WINS Info

   winsTable OBJECT-TYPE
      SYNTAX      SEQUENCE OF WinsEntry
      MAX-ACCESS  not-accessible
      STATUS      current
      DESCRIPTION
              "winsTable"
      ::= { winsInfo 1}

   winsEntry OBJECT-TYPE
      SYNTAX      WinsEntry
      MAX-ACCESS  not-accessible
      STATUS      current
      DESCRIPTION
               "winsEntry"
      INDEX   { winsIndex }
      ::= { winsTable 1 }

   WinsEntry ::=
      SEQUENCE {
        winsIndex
            INTEGER,
        winsStatus
            RowStatus,
        winsIpAddress
            Ipv4v6Address,
        winsActive
            OnOffValue
          }

   winsIndex OBJECT-TYPE
      SYNTAX      INTEGER
      MAX-ACCESS  not-accessible
      STATUS      current
      DESCRIPTION
              "winsIndex"
      ::= { winsEntry 1}

   winsStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { winsEntry 2}

   winsIpAddress OBJECT-TYPE
      SYNTAX      Ipv4v6Address
      MAX-ACCESS  read-write
      STATUS      current
      DESCRIPTION
              "You can specify the IP addresses for up to two WINS
               (Windows Internet Naming Service) hosts in your network.
               The first WINS entry in the list is the primary WINS server
               and the second WINS entry is the secondary server."
      ::= { winsEntry 3}

   winsActive OBJECT-TYPE
      SYNTAX      OnOffValue
      MAX-ACCESS  read-write
      STATUS      current
      DESCRIPTION
              "Activates/deactivates a WINS entry."
      ::= { winsEntry 4}

-- Gateway Info

   gatewayTable OBJECT-TYPE
      SYNTAX      SEQUENCE OF GatewayEntry
      MAX-ACCESS  not-accessible
      STATUS      current
      DESCRIPTION
              "gatewayTable"
      ::= { gatewayInfo 1}

   gatewayEntry OBJECT-TYPE
      SYNTAX      GatewayEntry
      MAX-ACCESS  not-accessible
      STATUS      current
      DESCRIPTION
               "gatewayEntry"
      INDEX   { gatewayIndex }
      ::= { gatewayTable 1 }

   GatewayEntry ::=
      SEQUENCE {
        gatewayIndex
              INTEGER,
        gatewayStatus
            RowStatus,
        gatewayHost
            DisplayString,
        gatewayType
            INTEGER,
        gatewayIpAddress
            Ipv4v6Address,
        gatewaySubnetBits
            INTEGER
          }

   gatewayIndex OBJECT-TYPE
      SYNTAX      INTEGER
      MAX-ACCESS  not-accessible
      STATUS      current
      DESCRIPTION
              "gatewayIndex"
      ::= { gatewayEntry 1}

   gatewayStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { gatewayEntry 2}

   gatewayHost OBJECT-TYPE
      SYNTAX      DisplayString(SIZE(0..14))
      MAX-ACCESS  read-write
      STATUS      current
      DESCRIPTION
              "You can specify up to twenty hosts to act as gateways
               in your network. Each gateway host must be defined in
               the Device Server host table."
      ::= { gatewayEntry 3}

   gatewayType OBJECT-TYPE
      SYNTAX      INTEGER {
        host(1),
        network(2),
        default(3)
      }
      MAX-ACCESS  read-write
      STATUS      current
      DESCRIPTION
              "Specify the type of gateway:
               Default-A gateway which provides general access beyond
                    your local network.
               Host-A gateway reserved for accessing a specific host
                    external to your local network.
               Network-A gateway reserved for accessing a specific
                    network external to your local network."
      ::= { gatewayEntry 4}

   gatewayIpAddress OBJECT-TYPE
      SYNTAX      Ipv4v6Address
      MAX-ACCESS  read-write
      STATUS      current
      DESCRIPTION
              "When the gateway is a Host or Network gateway, you must
               specify the IP address of the target host machine/network."
      ::= { gatewayEntry 5}

   gatewaySubnetBits OBJECT-TYPE
      SYNTAX      INTEGER (0..128)
      MAX-ACCESS  read-write
      STATUS      current
      DESCRIPTION
              "When the gateway is a Network gateway, you must specify the
               subnet/prefix bits for that network. If the IP address is IPv4,
               then the Subnet/Prefix Bits range is 0-32. If the IP address
               is IPv6, then the Subnet/Prefix Bits range is 0-128."
      ::= { gatewayEntry 6}

-- Syslog Info

  syslogStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { syslogInfo 1}

   syslogPrimaryHost OBJECT-TYPE
      SYNTAX      DisplayString(SIZE(0..14))
      MAX-ACCESS  read-write
      STATUS      current
      DESCRIPTION
              "The first preconfigured host that the Device Server will attempt
               to send system log messages to; messages will be displayed on the
               host's monitor."
      ::= { syslogInfo 2}

   syslogSecondaryHost OBJECT-TYPE
      SYNTAX      DisplayString(SIZE(0..14))
      MAX-ACCESS  read-write
      STATUS      current
      DESCRIPTION
              "If the Device Server cannot communicate with the primary host,
               then the Device Server will attempt to send system log messages to
               this preconfigured host; messages will be displayed on the host's monitor."
      ::= { syslogInfo 3}

    syslogLevel OBJECT-TYPE
      SYNTAX      INTEGER {
        emergency(1),
        alert(2),
        crticial(3),
        error(4),
        warning(5),
        notice(6),
        informational(7),
        debug(8)
      }
      MAX-ACCESS  read-write
      STATUS      current
      DESCRIPTION
              "Choose the event level that triggers a syslog entry:
               Emergency, Alert, Critical, Error, Warning, Notice, Info, Debug
               When you select a Level, all the levels that appear above it in the list
               also trigger a syslog entry. For example, if you select Error, all Error,
               Critical, Alert, and Emergency events will be logged."
      ::= { syslogInfo 4}

-- Email Info

   emailStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { emailInfo 1}

   emailActive OBJECT-TYPE
      SYNTAX      OnOffValue
      MAX-ACCESS  read-write
      STATUS      current
      DESCRIPTION
              "Determines whether or not email notification
               is turned on. Default is Off."
      ::= { emailInfo 2}

   emailLevel OBJECT-TYPE
      SYNTAX      INTEGER {
        emergency(1),
        alert(2),
        crticial(3),
        error(4),
        warning(5),
        notice(6),
        informational(7),
        debug(8)
      }
      MAX-ACCESS  read-write
      STATUS      current
      DESCRIPTION
              "Choose the event level that triggers an email notification:
               Emergency, Alert, Critical, Error, Warning, Notice, Info, or
               Debug. You are selecting the lowest notification level;
               therefore, when you select Debug, you will get an email
               notification for all events that trigger a message."
      ::= { emailInfo 3}

   emailTo OBJECT-TYPE
      SYNTAX      DisplayString(SIZE(0..64))
      MAX-ACCESS  read-write
      STATUS      current
      DESCRIPTION
              "An email address or list of email addresses that will
               receive the email notification."
      ::= { emailInfo 4}

   emailFrom OBJECT-TYPE
      SYNTAX      DisplayString(SIZE(0..32))
      MAX-ACCESS  read-write
      STATUS      current
      DESCRIPTION
              "This field can contain an email address that might
               identify the Device Server name or some other value."
      ::= { emailInfo 5}

   emailSMTPHost OBJECT-TYPE
      SYNTAX      DisplayString(SIZE(0..24))
      MAX-ACCESS  read-write
      STATUS      current
      DESCRIPTION
              "The SMTP host (email server) that will process the
               email notification request. This can be either a host
               name defined in the Device Server host table or the
               SMTP host IP address."
      ::= { emailInfo 6}

   emailReply OBJECT-TYPE
      SYNTAX      DisplayString(SIZE(0..32))
      MAX-ACCESS  read-write
      STATUS      current
      DESCRIPTION
              "The email address to whom all replies to the email
               notification should go."
      ::= { emailInfo 7}

   emailSubject OBJECT-TYPE
      SYNTAX      DisplayString(SIZE(0..48))
      MAX-ACCESS  read-write
      STATUS      current
      DESCRIPTION
              "A text string, which can contain spaces, that will
               display in the Subject field of the email notification."
      ::= { emailInfo 8}


-- RIP Info

  ripStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ripInfo 1}

   ripMode OBJECT-TYPE
      SYNTAX      INTEGER {
        none(1),
        send(2),
        listen(3),
        sendandlisten(4)
      }
      MAX-ACCESS  read-write
      STATUS      current
      DESCRIPTION
              "Enable/disable RIP (Routing Information Protocol) mode
               for the ethernet interface with one of the following options:
               None-Disables RIP over the ethernet interface.
               Send-Sends RIP over the ethernet interface.
               Listen-Listens for RIP over the ethernet interface.
               Send and Listen-Sends RIP and listens for RIP over the
               ethernet interface."
      ::= { ripInfo 2}

   ripAuthentication OBJECT-TYPE
      SYNTAX      INTEGER {
        none(1),
        password(2),
        md5(3)
      }
      MAX-ACCESS  read-write
      STATUS      current
      DESCRIPTION
              "Specify the type of RIP authentication:
               None-No authentication for RIP.
               Password-Simple RIP password authentication.
               MD5-Use MD5 RIP authentication."
      ::= { ripInfo 3}


  --  A table of RIP key entries, each entry indexed by chain number
  --  and entry number.

  ripKeysInfoTable OBJECT-TYPE
      SYNTAX      SEQUENCE OF RipKeysInfoEntry
      MAX-ACCESS  not-accessible
      STATUS      current
      DESCRIPTION
              "The RIP authentication keys info table."
      ::= { ripInfo 4 }

  ripKeysInfoEntry OBJECT-TYPE
      SYNTAX      RipKeysInfoEntry
      MAX-ACCESS  not-accessible
      STATUS      current
      DESCRIPTION
              "An entry in the ripKeysInfoTable, each relating to a
               RIP authentication key."
      INDEX   { ripKeysChainIndex, ripKeysKeyIndex }
      ::= { ripKeysInfoTable 1 }

  RipKeysInfoEntry ::=
      SEQUENCE {
        ripKeysChainIndex
              INTEGER,
        ripKeysKeyIndex
              INTEGER,
        ripKeyStatus
            RowStatus,
        ripKeyId
              INTEGER,
        ripKeyStartDate
              Date,
        ripKeyStartTime
              Time,
        ripKeyEndDate
              Date,
        ripKeyEndTime
              Time
      }

  ripKeysChainIndex OBJECT-TYPE
      SYNTAX      INTEGER
      MAX-ACCESS  not-accessible
      STATUS      current
      DESCRIPTION
              "The key chain index for this RIP authentication key."
      ::= { ripKeysInfoEntry 1 }

  ripKeysKeyIndex OBJECT-TYPE
      SYNTAX      INTEGER
      MAX-ACCESS  not-accessible
      STATUS      current
      DESCRIPTION
              "The key index in the chain for this RIP authentication key."
      ::= { ripKeysInfoEntry 2 }

  ripKeyStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ripKeysInfoEntry 3 }

  ripKeyId OBJECT-TYPE
      SYNTAX      INTEGER (0..255)
      MAX-ACCESS  read-write
      STATUS      current
      DESCRIPTION
              "The key Id for this RIP authentication key."
      ::= { ripKeysInfoEntry 4 }

  ripKeyStartDate OBJECT-TYPE
      SYNTAX      Date
      MAX-ACCESS  read-write
      STATUS      current
      DESCRIPTION
              "The starting date for which this
               RIP authentication key becomes effective.
               Format dd/mm/yyyy"
      ::= { ripKeysInfoEntry 5 }

  ripKeyStartTime OBJECT-TYPE
      SYNTAX      Time
      MAX-ACCESS  read-write
      STATUS      current
      DESCRIPTION
              "The starting time (local time) for which this
               RIP authentication key becomes effective.
               Format hh:mm:ss"
      ::= { ripKeysInfoEntry 6 }

  ripKeyEndDate OBJECT-TYPE
      SYNTAX      Date
      MAX-ACCESS  read-write
      STATUS      current
      DESCRIPTION
              "The end date , after which this
               RIP authentication key is no longer in effect."
      ::= { ripKeysInfoEntry 7 }

  ripKeyEndTime OBJECT-TYPE
      SYNTAX      Time
      MAX-ACCESS  read-write
      STATUS      current
      DESCRIPTION
              "The end time (local time), after which this
               RIP authentication key is no longer in effect."
      ::= { ripKeysInfoEntry 8 }

  --  timeInfo group.

  timeStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { timeInfo 1 }

  timeZoneName OBJECT-TYPE
      SYNTAX      DisplayString(SIZE(0..4))
      MAX-ACCESS  read-write
      STATUS      current
      DESCRIPTION
              "The name of the time zone when using standard time."
      ::= { timeInfo 2 }

  timeOffset OBJECT-TYPE
      SYNTAX      INTEGER (-720..840)
      MAX-ACCESS  read-write
      STATUS      current
      DESCRIPTION
              "The offset of summer time from standard time in minutes."
      ::= { timeInfo 3 }

  timeSummerName OBJECT-TYPE
      SYNTAX      DisplayString(SIZE(0..4))
      MAX-ACCESS  read-write
      STATUS      current
      DESCRIPTION
              "The name of the time zone when using summer time."
      ::= { timeInfo 4 }

  timeSummerOffset OBJECT-TYPE
      SYNTAX      INTEGER (0..180)
      MAX-ACCESS  read-write
      STATUS      current
      DESCRIPTION
              "The offset of summer time from standard time in minutes."
      ::= { timeInfo 5 }

  timeSummerMode OBJECT-TYPE
      SYNTAX      INTEGER {
        disabled(1),
        fixed(2),
        recurring(3)
      }
      MAX-ACCESS  read-write
      STATUS      current
      DESCRIPTION
              "You can configure the summer time to take effect:
               None-No summer time change.
               Fixed-The summer time change goes into effect at
                  the specified time every year. For example,
                  April 15 at 1:00 pm.
               Recurring-The summer time changes goes into effect
                  every year at same relative time. For example,
                  on the third week in April on a Tuesday at 1:00 pm."
      ::= { timeInfo 6 }

  timeSummerRecStartMonth OBJECT-TYPE
      SYNTAX      INTEGER {
        january(1),
        february(2),
        march(3),
        april(4),
        may(5),
        june(6),
        july(7),
        august(8),
        september(9),
        october(10),
        november(11),
        december(12)
      }
      MAX-ACCESS  read-write
      STATUS      current
      DESCRIPTION
              "The recurring summer time start month."
      ::= { timeInfo 7 }

  timeSummerRecStartWeek OBJECT-TYPE
      SYNTAX      INTEGER {
        first(1),
        second(2),
        third(3),
        fourth(4),
        last(5)
      }
      MAX-ACCESS  read-write
      STATUS      current
      DESCRIPTION
              "The recurring summer time start week."
      ::= { timeInfo 8}

  timeSummerRecStartDay OBJECT-TYPE
      SYNTAX      INTEGER {
        sunday(1),
        monday(2),
        tuesday(3),
        wednesday(4),
        thursday(5),
        friday(6),
        saturday(7)
      }
      MAX-ACCESS  read-write
      STATUS      current
      DESCRIPTION
              "The recurring summer time start day."
      ::= { timeInfo 9}

  timeSummerRecStartHour OBJECT-TYPE
      SYNTAX      INTEGER (0..23)
      MAX-ACCESS  read-write
      STATUS      current
      DESCRIPTION
              "The recurring summer time start hour."
      ::= { timeInfo 10}

  timeSummerRecStartMin OBJECT-TYPE
      SYNTAX      INTEGER (0..59)
      MAX-ACCESS  read-write
      STATUS      current
      DESCRIPTION
              "The recurring summer time start minute"
      ::= { timeInfo 11}

  timeSummerRecEndMonth OBJECT-TYPE
      SYNTAX      INTEGER {
        january(1),
        february(2),
        march(3),
        april(4),
        may(5),
        june(6),
        july(7),
        august(8),
        september(9),
        october(10),
        november(11),
        december(12)
      }
      MAX-ACCESS  read-write
      STATUS      current
      DESCRIPTION
              "The recurring summer time end month."
      ::= { timeInfo 12 }

  timeSummerRecEndWeek OBJECT-TYPE
      SYNTAX      INTEGER {
        first(1),
        second(2),
        third(3),
        fourth(4),
        last(5)
      }
      MAX-ACCESS  read-write
      STATUS      current
      DESCRIPTION
              "The recurring summer time end week."
      ::= { timeInfo 13 }

  timeSummerRecEndDay OBJECT-TYPE
      SYNTAX      INTEGER {
        sunday(1),
        monday(2),
        tuesday(3),
        wednesday(4),
        thursday(5),
        friday(6),
        saturday(7)
      }
      MAX-ACCESS  read-write
      STATUS      current
      DESCRIPTION
              "The recurring summer time end day."
      ::= { timeInfo 14 }

  timeSummerRecEndHour OBJECT-TYPE
      SYNTAX      INTEGER (0..23)
      MAX-ACCESS  read-write
      STATUS      current
      DESCRIPTION
              "The recurring summer time end hour"
      ::= { timeInfo 15 }

  timeSummerRecEndMin OBJECT-TYPE
      SYNTAX      INTEGER (0..59)
      MAX-ACCESS  read-write
      STATUS      current
      DESCRIPTION
              "The recurring summer time end minute"
      ::= { timeInfo 16 }

  timeSummerFixStartMonth OBJECT-TYPE
      SYNTAX      INTEGER {
        january(1),
        february(2),
        march(3),
        april(4),
        may(5),
        june(6),
        july(7),
        august(8),
        september(9),
        october(10),
        november(11),
        december(12)
      }
      MAX-ACCESS  read-write
      STATUS      current
      DESCRIPTION
              "The fixed summer time start month"
      ::= { timeInfo 17 }

  timeSummerFixStartDay OBJECT-TYPE
      SYNTAX      INTEGER (1..31)
      MAX-ACCESS  read-write
      STATUS      current
      DESCRIPTION
              "The fixed summer time start day"
      ::= { timeInfo 18 }

  timeSummerFixStartHour OBJECT-TYPE
      SYNTAX      INTEGER (0..23)
      MAX-ACCESS  read-write
      STATUS      current
      DESCRIPTION
              "The fixed summer time start hour"
      ::= { timeInfo 19 }

  timeSummerFixStartMinute OBJECT-TYPE
      SYNTAX      INTEGER (0..59)
      MAX-ACCESS  read-write
      STATUS      current
      DESCRIPTION
              "The fixed summer time start minute"
      ::= { timeInfo 20 }

  timeSummerFixEndMonth OBJECT-TYPE
      SYNTAX      INTEGER {
        january(1),
        february(2),
        march(3),
        april(4),
        may(5),
        june(6),
        july(7),
        august(8),
        september(9),
        october(10),
        november(11),
        december(12)
      }
      MAX-ACCESS  read-write
      STATUS      current
      DESCRIPTION
              "The fixed summer time End month"
      ::= { timeInfo 21 }

  timeSummerFixEndDay OBJECT-TYPE
      SYNTAX      INTEGER (1..31)
      MAX-ACCESS  read-write
      STATUS      current
      DESCRIPTION
              "The fixed summer time End day"
      ::= { timeInfo 22 }

  timeSummerFixEndHour OBJECT-TYPE
      SYNTAX      INTEGER (0..23)
      MAX-ACCESS  read-write
      STATUS      current
      DESCRIPTION
              "The fixed summer time End hour"
      ::= { timeInfo 23 }

  timeSummerFixEndMinute OBJECT-TYPE
      SYNTAX      INTEGER (0..59)
      MAX-ACCESS  read-write
      STATUS      current
      DESCRIPTION
              "The fixed summer time End minute"
      ::= { timeInfo 24 }

  timeSntpMode OBJECT-TYPE
      SYNTAX      INTEGER {
        disabled(1),
        unicast(2),
        multicast(3),
        anycast(4)
      }
      MAX-ACCESS  read-write
      STATUS      current
      DESCRIPTION
              "The sntp client mode.  Valid modes are Unicast, Multicast or Anycast"
      ::= { timeInfo 25 }

  timeSntpVersion OBJECT-TYPE
      SYNTAX      INTEGER  {
        version1(1),
        version2(2),
        version3(3),
        version4(4)
      }
      MAX-ACCESS  read-write
      STATUS      current
      DESCRIPTION
              "The sntp client version."
      ::= { timeInfo 26 }

  timeSntpHost1 OBJECT-TYPE
      SYNTAX      DisplayString(SIZE(0..14))
      MAX-ACCESS  read-write
      STATUS      current
      DESCRIPTION
              "The first remote SNTP host name that the device server communicates with."
      ::= { timeInfo 27 }

  timeSntpHost2 OBJECT-TYPE
      SYNTAX      DisplayString(SIZE(0..14))
      MAX-ACCESS  read-write
      STATUS      current
      DESCRIPTION
              "The second remote SNTP host name that the device server communicates with."
      ::= { timeInfo 28 }

  --  fileInfo group.

  fileStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { fileInfo 1}

  fileFirmwareHost OBJECT-TYPE
      SYNTAX      DisplayString(SIZE(0..46))
      MAX-ACCESS  read-write
      STATUS      current
      DESCRIPTION
              "The host name or IP address of the server that contains the firmware file.
               If you use a host name, it must exist in the Device Server's host table
               or be resolved by DNS."
      ::= { fileInfo 2}

  fileFirmwareName OBJECT-TYPE
      SYNTAX      DisplayString(SIZE(0..64))
      MAX-ACCESS  read-write
      STATUS      current
      DESCRIPTION
              "The path and file name (do not use a drive letter), relative to the default
               path of your TFTP server software, of the update software for the Device
               Server that will be loaded when the Device Server is rebooted."
      ::= { fileInfo 3}

  fileConfigurationHost OBJECT-TYPE
      SYNTAX      DisplayString(SIZE(0..46))
      MAX-ACCESS  read-write
      STATUS      current
      DESCRIPTION
              "The host name or IP address of the server that contains the configuration file.
               If you use a host name, it must exist in the Device Server's host table
               or be resolved by DNS."
      ::= { fileInfo 4}

  fileConfigurationName OBJECT-TYPE
      SYNTAX      DisplayString(SIZE(0..64))
      MAX-ACCESS  read-write
      STATUS      current
      DESCRIPTION
              "The path and file name (do not use a drive letter), relative to the default
               path of your TFTP server software, of the new configuration file for the Device
               Server that will be loaded when the Device Server is rebooted."
      ::= { fileInfo 5}

  fileMOTDHost OBJECT-TYPE
      SYNTAX      DisplayString(SIZE(0..46))
      MAX-ACCESS  read-write
      STATUS      current
      DESCRIPTION
              "The host name or IP address of the server that contains the MOTD file.
               If you use a host name, it must exist in the Device Server's host table
               or be resolved by DNS."
      ::= { fileInfo 6}

  fileMOTDName OBJECT-TYPE
      SYNTAX      DisplayString(SIZE(0..64))
      MAX-ACCESS  read-write
      STATUS      current
      DESCRIPTION
              "The path and file name (do not use a drive letter), relative to the default
               path of your TFTP server software, of the file that contains a string that
               is displayed when a user connects to the Device Server."
      ::= { fileInfo 7}

-- Ethernet Stats Info
  ethStatsInfoTable OBJECT-TYPE
      SYNTAX      SEQUENCE OF EthStatsInfoEntry
      MAX-ACCESS  not-accessible
      STATUS      current
      DESCRIPTION
              "The Ethernet statistics table."
      ::= { ethStatsInfo 1 }

  ethStatsInfoEntry OBJECT-TYPE
      SYNTAX      EthStatsInfoEntry
      MAX-ACCESS  not-accessible
      STATUS      current
      DESCRIPTION
              "An entry in the Ethernet statistics table, each relating to an Ethernet interface."
      INDEX   { ethStatsIndex }
      ::= { ethStatsInfoTable 1 }

  EthStatsInfoEntry ::=
      SEQUENCE {
        ethStatsIndex
              INTEGER,
        ethStatsName
              DisplayString,
        ethStatsMacAddress
              MacAddress,
        ethStatsStatus
              INTEGER,
        ethStatsBroadcast
              YesNoValue,
        ethStatsDebug 
            YesNoValue,
        ethStatsLoopback 
              YesNoValue,
        ethStatsPointtoPoint 
              YesNoValue,
        ethStatsNoTrailers 
              YesNoValue,
        ethStatsRunning 
              YesNoValue,
        ethStatsNoArp 
              YesNoValue,
        ethStatsPromiscuous 
              YesNoValue,
        ethStatsRxMulticast 
              YesNoValue,
        ethStatsMasterLoadBalancer
              YesNoValue,
        ethStatsSlaveLoadBalancer
              YesNoValue,
        ethStatsMulticast 
              YesNoValue,
        ethStatsSetMedia
              YesNoValue,
        ethStatsAutoMedia
              YesNoValue,
        ethStatsDynamic
              YesNoValue,
        ethStatsLocalAddress 
              IpAddress,
            ethStatsSubnetMask
              IpAddress,
        ethStatsBroadcastAddress
              IpAddress,
        ethStatsMtu
              Counter32,
        ethStatsTxQLen
              Counter32,
        ethStatsRxBytes
              Counter32,
        ethStatsTxBytes
              Counter32,
        ethStatsRxPackets
              Counter32,
        ethStatsTxPackets
              Counter32,
        ethStatsRxErrors
              Counter32,
        ethStatsTxErrors
              Counter32,
        ethStatsRxDropped
              Counter32,
        ethStatsTxDropped
              Counter32,
        ethStatsRxOverruns
              Counter32,
        ethStatsTxOverruns
              Counter32,
        ethStatsRxFrame
              Counter32,
        ethStatsTxCarrier 
              Counter32,
        ethStatsCollisions
              Counter32
      }
  ethStatsIndex OBJECT-TYPE
      SYNTAX      INTEGER
      MAX-ACCESS  not-accessible
      STATUS      current
      DESCRIPTION
              "The Ethernet interface number."
      ::= { ethStatsInfoEntry 1 }

  ethStatsName OBJECT-TYPE
      SYNTAX      DisplayString
      MAX-ACCESS  read-only
      STATUS      current
      DESCRIPTION
              "Displays ethernet statistics."
      ::= { ethStatsInfoEntry 2}

  ethStatsMacAddress OBJECT-TYPE
      SYNTAX      MacAddress
      MAX-ACCESS  read-only
      STATUS      current
      DESCRIPTION
              "Displays the MAC address."
      ::= { ethStatsInfoEntry 3}

  ethStatsStatus OBJECT-TYPE
      SYNTAX      INTEGER {
        down(1),
        up(2)
      }
      MAX-ACCESS  read-only
      STATUS      current
      DESCRIPTION
              "Displays the ethernet status:
        1 is down and 2 is up."
      ::= { ethStatsInfoEntry 4}

  ethStatsBroadcast OBJECT-TYPE
      SYNTAX      YesNoValue
      MAX-ACCESS  read-only
      STATUS      current
      DESCRIPTION
              "ethStatsBroadcast"
      ::= { ethStatsInfoEntry 5}

  ethStatsDebug OBJECT-TYPE
      SYNTAX      YesNoValue
      MAX-ACCESS  read-only
      STATUS      current
      DESCRIPTION
              "ethStatsDebug"
      ::= { ethStatsInfoEntry 6}

  ethStatsLoopback OBJECT-TYPE
      SYNTAX      YesNoValue
      MAX-ACCESS  read-only
      STATUS      current
      DESCRIPTION
              "ethStatsLoopback"
      ::= { ethStatsInfoEntry 7}

  ethStatsPointtoPoint OBJECT-TYPE
      SYNTAX      YesNoValue
      MAX-ACCESS  read-only
      STATUS      current
      DESCRIPTION
              "ethStatsPointtoPoint"
      ::= { ethStatsInfoEntry 8}

  ethStatsNoTrailers OBJECT-TYPE
      SYNTAX      YesNoValue
      MAX-ACCESS  read-only
      STATUS      current
      DESCRIPTION
              "ethStatsNoTrailers"
      ::= { ethStatsInfoEntry 9}

  ethStatsRunning OBJECT-TYPE
      SYNTAX      YesNoValue
      MAX-ACCESS  read-only
      STATUS      current
      DESCRIPTION
              "ethStatsRunning"
      ::= { ethStatsInfoEntry 10}

  ethStatsNoArp OBJECT-TYPE
      SYNTAX      YesNoValue
      MAX-ACCESS  read-only
      STATUS      current
      DESCRIPTION
              "ethStatsNoArp"
      ::= { ethStatsInfoEntry 11}

  ethStatsPromiscuous OBJECT-TYPE
      SYNTAX      YesNoValue
      MAX-ACCESS  read-only
      STATUS      current
      DESCRIPTION
              "ethStatsPromiscuous"
      ::= { ethStatsInfoEntry 12}

  ethStatsRxMulticast OBJECT-TYPE
      SYNTAX      YesNoValue
      MAX-ACCESS  read-only
      STATUS      current
      DESCRIPTION
              "ethStatsRxMulticast"
      ::= { ethStatsInfoEntry 13}

  ethStatsMasterLoadBalancer OBJECT-TYPE
      SYNTAX      YesNoValue
      MAX-ACCESS  read-only
      STATUS      current
      DESCRIPTION
              "ethStatsMasterLoadBalancer"
      ::= { ethStatsInfoEntry 14}

  ethStatsSlaveLoadBalancer OBJECT-TYPE
      SYNTAX      YesNoValue
      MAX-ACCESS  read-only
      STATUS      current
      DESCRIPTION
              "ethStatsSlaveLoadBalancer"
      ::= { ethStatsInfoEntry 15}

  ethStatsMulticast OBJECT-TYPE
      SYNTAX      YesNoValue
      MAX-ACCESS  read-only
      STATUS      current
      DESCRIPTION
              "ethStatsMulticast"
      ::= { ethStatsInfoEntry 16}

  ethStatsSetMedia OBJECT-TYPE
      SYNTAX      YesNoValue
      MAX-ACCESS  read-only
      STATUS      current
      DESCRIPTION
              "ethStatsSetMedia"
      ::= { ethStatsInfoEntry 17}

  ethStatsAutoMedia OBJECT-TYPE
      SYNTAX      YesNoValue
      MAX-ACCESS  read-only
      STATUS      current
      DESCRIPTION
              "ethStatsAutoMedia"
      ::= { ethStatsInfoEntry 18}

  ethStatsDynamic OBJECT-TYPE
      SYNTAX      YesNoValue
      MAX-ACCESS  read-only
      STATUS      current
      DESCRIPTION
              "ethStatsDynamic"
      ::= { ethStatsInfoEntry 19}

  ethStatsLocalAddress OBJECT-TYPE
      SYNTAX      IpAddress
      MAX-ACCESS  read-only
      STATUS      current
      DESCRIPTION
              "ethStatsLocalAddress"
      ::= { ethStatsInfoEntry 20}

  ethStatsSubnetMask OBJECT-TYPE
      SYNTAX      IpAddress
      MAX-ACCESS  read-only
      STATUS      current
      DESCRIPTION
              "ethStatsSubnetMask"
      ::= { ethStatsInfoEntry 21}

  ethStatsBroadcastAddress OBJECT-TYPE
      SYNTAX      IpAddress
      MAX-ACCESS  read-only
      STATUS      current
      DESCRIPTION
              "ethStatsBroadcastAddress"
      ::= { ethStatsInfoEntry 22}

  ethStatsMtu OBJECT-TYPE
      SYNTAX      Counter32
      MAX-ACCESS  read-only
      STATUS      current
      DESCRIPTION
              "ethStatsMtu"
      ::= { ethStatsInfoEntry 23}

  ethStatsTxQLen OBJECT-TYPE
      SYNTAX      Counter32
      MAX-ACCESS  read-only
      STATUS      current
      DESCRIPTION
              "ethStatsTxQLen"
      ::= { ethStatsInfoEntry 24}

  ethStatsRxBytes OBJECT-TYPE
      SYNTAX      Counter32
      MAX-ACCESS  read-only
      STATUS      current
      DESCRIPTION
              "ethStatsRxBytes"
      ::= { ethStatsInfoEntry 25}

  ethStatsTxBytes OBJECT-TYPE
      SYNTAX      Counter32
      MAX-ACCESS  read-only
      STATUS      current
      DESCRIPTION
              "ethStatsTxBytes"
      ::= { ethStatsInfoEntry 26}

  ethStatsRxPackets OBJECT-TYPE
      SYNTAX      Counter32
      MAX-ACCESS  read-only
      STATUS      current
      DESCRIPTION
              "ethStatsRxPackets"
      ::= { ethStatsInfoEntry 27}

  ethStatsTxPackets OBJECT-TYPE
      SYNTAX      Counter32
      MAX-ACCESS  read-only
      STATUS      current
      DESCRIPTION
              "ethStatsTxPackets"
      ::= { ethStatsInfoEntry 28}

  ethStatsRxErrors OBJECT-TYPE
      SYNTAX      Counter32
      MAX-ACCESS  read-only
      STATUS      current
      DESCRIPTION
              "ethStatsRxErrors"
      ::= { ethStatsInfoEntry 29}

  ethStatsTxErrors OBJECT-TYPE
      SYNTAX      Counter32
      MAX-ACCESS  read-only
      STATUS      current
      DESCRIPTION
              "ethStatsTxErrors"
      ::= { ethStatsInfoEntry 30}

  ethStatsRxDropped OBJECT-TYPE
      SYNTAX      Counter32
      MAX-ACCESS  read-only
      STATUS      current
      DESCRIPTION
              "ethStatsRxDropped"
      ::= { ethStatsInfoEntry 31}

  ethStatsTxDropped OBJECT-TYPE
      SYNTAX      Counter32
      MAX-ACCESS  read-only
      STATUS      current
      DESCRIPTION
              "ethStatsTxDropped"
      ::= { ethStatsInfoEntry 32}

  ethStatsRxOverruns OBJECT-TYPE
      SYNTAX      Counter32
      MAX-ACCESS  read-only
      STATUS      current
      DESCRIPTION
              "ethStatsRxOverruns"
      ::= { ethStatsInfoEntry 33}

  ethStatsTxOverruns OBJECT-TYPE
      SYNTAX      Counter32
      MAX-ACCESS  read-only
      STATUS      current
      DESCRIPTION
              "ethStatsTxOverruns"
      ::= { ethStatsInfoEntry 34}

  ethStatsRxFrame OBJECT-TYPE
      SYNTAX      Counter32
      MAX-ACCESS  read-only
      STATUS      current
      DESCRIPTION
              "ethStatsRxFrame"
      ::= { ethStatsInfoEntry 35}

  ethStatsTxCarrier OBJECT-TYPE
      SYNTAX      Counter32
      MAX-ACCESS  read-only
      STATUS      current
      DESCRIPTION
              "ethStatsTxCarrier"
      ::= { ethStatsInfoEntry 36}

  ethStatsCollisions OBJECT-TYPE
      SYNTAX      Counter32
      MAX-ACCESS  read-only
      STATUS      current
      DESCRIPTION
              "ethStatsCollisions"
      ::= { ethStatsInfoEntry 37}

-- SNTP Stats Info

  sntpStatsAddress OBJECT-TYPE
      SYNTAX      DisplayString
      MAX-ACCESS  read-only
      STATUS      current
      DESCRIPTION
              "sntpStatsAddress"
      ::= { sntpStatsInfo 1}

  sntpStatsLastUpdate OBJECT-TYPE
      SYNTAX      DisplayString
      MAX-ACCESS  read-only
      STATUS      current
      DESCRIPTION
              "sntpStatsLastUpdate"
      ::= { sntpStatsInfo 2}

  sntpStatsLeapIndicator OBJECT-TYPE
      SYNTAX      INTEGER {
         noWarning(1),
         minutes61(2),
         minutes59(3),
         alarm(4)
      }
      MAX-ACCESS  read-only
      STATUS      current
      DESCRIPTION
              "sntpStatsLeapIndicator"
      ::= { sntpStatsInfo 3}

  sntpStatsVersion OBJECT-TYPE
      SYNTAX      INTEGER {
        ipV4(3),
        ipv4ipv6osi(4)
      }
      MAX-ACCESS  read-only
      STATUS      current
      DESCRIPTION
              "sntpStatsVersion"
      ::= { sntpStatsInfo 4}

  sntpStatsMode OBJECT-TYPE
      SYNTAX      INTEGER {
         reserved(1),
         symmetricActive(2),
         symmetricPassive(3),
         client(4),
         server(5),
         broadcast(6),
         reservedNTP(7),
         reserved2(8)
      }
      MAX-ACCESS  read-only
      STATUS      current
      DESCRIPTION
              "sntpStatsMode"
      ::= { sntpStatsInfo 5}

  sntpStatsStratum OBJECT-TYPE
      SYNTAX      INTEGER
      MAX-ACCESS  read-only
      STATUS      current
      DESCRIPTION
              "sntpStatsStratum"
      ::= { sntpStatsInfo 6}

  sntpStatsRefId OBJECT-TYPE
      SYNTAX      Counter32
      MAX-ACCESS  read-only
      STATUS      current
      DESCRIPTION
              "sntpStatsRefId"
      ::= { sntpStatsInfo 7}

  sntpStatsCorrection OBJECT-TYPE
      SYNTAX      Counter32
      MAX-ACCESS  read-only
      STATUS      current
      DESCRIPTION
              "sntpStats"
      ::= { sntpStatsInfo 8}

-- Rip (V4) Info
  ripInfoTable OBJECT-TYPE
      SYNTAX      SEQUENCE OF RipInfoEntry
      MAX-ACCESS  not-accessible
      STATUS      current
      DESCRIPTION
              "The rip info table."
      ::= { ripTableInfo 1 }

  ripInfoEntry OBJECT-TYPE
      SYNTAX      RipInfoEntry
      MAX-ACCESS  not-accessible
      STATUS      current
      DESCRIPTION
              "An entry in the ripInfoTable, each relating to a rip entry."
      INDEX   { ripIndex }
      ::= { ripInfoTable 1 }

  RipInfoEntry ::=
      SEQUENCE {
        ripIndex
              INTEGER,
        ripTableIpAddr
              IpAddress,
        ripTableLastUpdate
            Counter32,
        ripTableVersion
            INTEGER,
        ripTableAuthType
            INTEGER,
        ripTableSequence
            Counter32,
        ripTableBadPackets
            Counter32,
        ripTableBadRoutes
            Counter32
      }

  ripIndex OBJECT-TYPE
      SYNTAX      INTEGER
      MAX-ACCESS  not-accessible
      STATUS      current
      DESCRIPTION
              "The table entry number for this rip."
      ::= { ripInfoEntry 1 }

  ripTableIpAddr OBJECT-TYPE
      SYNTAX      IpAddress
      MAX-ACCESS  read-only
      STATUS      current
      DESCRIPTION
              "ripIpAddr"
      ::= { ripInfoEntry 2 }

  ripTableLastUpdate OBJECT-TYPE
      SYNTAX      Counter32
      MAX-ACCESS  read-only
      STATUS      current
      DESCRIPTION
              "Last Update in Seconds"
      ::= { ripInfoEntry 3 }

  ripTableVersion OBJECT-TYPE
      SYNTAX      INTEGER
      MAX-ACCESS  read-only
      STATUS      current
      DESCRIPTION
              "Version"
      ::= { ripInfoEntry 4 }

  ripTableAuthType OBJECT-TYPE
      SYNTAX      INTEGER {
        noAuth(1),
        authData(2),
        password(3),
        md5(4)
      }
      MAX-ACCESS  read-only
      STATUS      current
      DESCRIPTION
              "Authentication Type"
      ::= { ripInfoEntry 5 }

  ripTableSequence OBJECT-TYPE
      SYNTAX      Counter32
      MAX-ACCESS  read-only
      STATUS      current
      DESCRIPTION
              "Sequence"
      ::= { ripInfoEntry 6 }

  ripTableBadPackets OBJECT-TYPE
      SYNTAX      Counter32
      MAX-ACCESS  read-only
      STATUS      current
      DESCRIPTION
              "ripTableBadPackets"
      ::= { ripInfoEntry 7 }

  ripTableBadRoutes OBJECT-TYPE
      SYNTAX      Counter32
      MAX-ACCESS  read-only
      STATUS      current
      DESCRIPTION
              "ripTableBadRoutes"
      ::= { ripInfoEntry 8 }

-- TCP Conn Stats

  tcpConnTable OBJECT-TYPE
      SYNTAX      SEQUENCE OF TcpConnEntry
      MAX-ACCESS  not-accessible
      STATUS      current
      DESCRIPTION
              "tcpConnTable."
      ::= { tcpConnStatsInfo 1 }

  tcpConnEntry OBJECT-TYPE
      SYNTAX      TcpConnEntry
      MAX-ACCESS  not-accessible
      STATUS      current
      DESCRIPTION
              "An entry in the tcpConnTable"
      INDEX   { tcpConnIndex }
      ::= { tcpConnTable 1 }

  TcpConnEntry ::=
      SEQUENCE {
        tcpConnIndex
              INTEGER,
        tcpConnLocalAddress
            IpAddress,
        tcpConnLocalPort
            INTEGER,
        tcpConnRemoteAddress
            IpAddress,
        tcpConnRemotePort
            INTEGER,
        tcpConnTxQueue
            Counter32,
        tcpConnRxQueue
            Counter32,
        tcpConnState
            INTEGER
        }

  tcpConnIndex OBJECT-TYPE
      SYNTAX      INTEGER
      MAX-ACCESS  not-accessible
      STATUS      current
      DESCRIPTION
              "Index"
      ::= { tcpConnEntry 1 }

  tcpConnLocalAddress OBJECT-TYPE
      SYNTAX      IpAddress
      MAX-ACCESS  read-only
      STATUS      current
      DESCRIPTION
              "LocalAddress"
      ::= { tcpConnEntry 2}

  tcpConnLocalPort OBJECT-TYPE
      SYNTAX      INTEGER
      MAX-ACCESS  read-only
      STATUS      current
      DESCRIPTION
              "LocalPort"
      ::= { tcpConnEntry 3}

  tcpConnRemoteAddress OBJECT-TYPE
      SYNTAX      IpAddress
      MAX-ACCESS  read-only
      STATUS      current
      DESCRIPTION
              "RemoteAddress"
      ::= { tcpConnEntry 4}

  tcpConnRemotePort OBJECT-TYPE
      SYNTAX      INTEGER
      MAX-ACCESS  read-only
      STATUS      current
      DESCRIPTION
              "RemotePort"
      ::= { tcpConnEntry 5}

  tcpConnTxQueue OBJECT-TYPE
      SYNTAX      Counter32
      MAX-ACCESS  read-only
      STATUS      current
      DESCRIPTION
              "TxQueue"
      ::= { tcpConnEntry 6}

  tcpConnRxQueue OBJECT-TYPE
      SYNTAX      Counter32
      MAX-ACCESS  read-only
      STATUS      current
      DESCRIPTION
              "RxQueue"
      ::= { tcpConnEntry 7}

  tcpConnState OBJECT-TYPE
      SYNTAX      INTEGER {
        established(1),
        synSent(2),
        synRecv(3),
        finWait1(4),
        finWait2(5),
        timewait(6),
        close(7),
        closeWait(8),
        lastack(9),
        listen(10),
        closing(11)
      }
      MAX-ACCESS  read-only
      STATUS      current
      DESCRIPTION
              "State"
      ::= { tcpConnEntry 8}

-- UDP Conn V6 Stats

  udpConnTable OBJECT-TYPE
      SYNTAX      SEQUENCE OF UdpConnEntry
      MAX-ACCESS  not-accessible
      STATUS      current
      DESCRIPTION
              "udpConnTable"
      ::= { udpConnStatsInfo 1 }

  udpConnEntry OBJECT-TYPE
      SYNTAX      UdpConnEntry
      MAX-ACCESS  not-accessible
      STATUS      current
      DESCRIPTION
              "An entry in the udpConnTable"
      INDEX   { udpConnIndex }
      ::= { udpConnTable 1 }

  UdpConnEntry ::=
      SEQUENCE {
        udpConnIndex
              INTEGER,
        udpConnLocalAddress
            DisplayString,
        udpConnLocalPort
            INTEGER,
        udpConnRemoteAddress
            DisplayString,
        udpConnRemotePort
            INTEGER,
        udpConnTxQueue
            Counter32,
        udpConnRxQueue
            Counter32,
        udpConnState
            INTEGER
        }

  udpConnIndex OBJECT-TYPE
      SYNTAX      INTEGER
      MAX-ACCESS  not-accessible
      STATUS      current
      DESCRIPTION
              "Index"
      ::= { udpConnEntry 1 }

  udpConnLocalAddress OBJECT-TYPE
      SYNTAX      DisplayString
      MAX-ACCESS  read-only
      STATUS      current
      DESCRIPTION
              "LocalAddress"
      ::= { udpConnEntry 2}

  udpConnLocalPort OBJECT-TYPE
      SYNTAX      INTEGER
      MAX-ACCESS  read-only
      STATUS      current
      DESCRIPTION
              "LocalPort"
      ::= { udpConnEntry 3}

  udpConnRemoteAddress OBJECT-TYPE
      SYNTAX      DisplayString
      MAX-ACCESS  read-only
      STATUS      current
      DESCRIPTION
              "RemoteAddress"
      ::= { udpConnEntry 4}

  udpConnRemotePort OBJECT-TYPE
      SYNTAX      INTEGER
      MAX-ACCESS  read-only
      STATUS      current
      DESCRIPTION
              "RemotePort"
      ::= { udpConnEntry 5}

  udpConnTxQueue OBJECT-TYPE
      SYNTAX      Counter32
      MAX-ACCESS  read-only
      STATUS      current
      DESCRIPTION
              "TxQueue"
      ::= { udpConnEntry 6}

  udpConnRxQueue OBJECT-TYPE
      SYNTAX      Counter32
      MAX-ACCESS  read-only
      STATUS      current
      DESCRIPTION
              "RxQueue"
      ::= { udpConnEntry 7}

  udpConnState OBJECT-TYPE
      SYNTAX      INTEGER {
          established(1)
      }
      MAX-ACCESS  read-only
      STATUS      current
      DESCRIPTION
              "State"
      ::= { udpConnEntry 8}

-- IPV6 Stats
   ipV6StatsRxTotal OBJECT-TYPE
      SYNTAX       Counter32
      MAX-ACCESS   read-only
      STATUS       current
      DESCRIPTION
               "RxTotal"
      ::= {ipv6StatsInfo 1}

   ipV6StatsRxHdrErrors OBJECT-TYPE
      SYNTAX       Counter32
      MAX-ACCESS   read-only
      STATUS       current
      DESCRIPTION
               "RxHdrErrors"
      ::= {ipv6StatsInfo 2}

   ipV6StatsRxTooBigErrors OBJECT-TYPE
      SYNTAX       Counter32
      MAX-ACCESS   read-only
      STATUS       current
      DESCRIPTION
               "RxTooBigErrors"
      ::= {ipv6StatsInfo 3}

   ipV6StatsRxNoRoutes OBJECT-TYPE
      SYNTAX       Counter32
      MAX-ACCESS   read-only
      STATUS       current
      DESCRIPTION
               "RxNoRoutes"
      ::= {ipv6StatsInfo 4}

   ipV6StatsRxAddrErrors OBJECT-TYPE
      SYNTAX       Counter32
      MAX-ACCESS   read-only
      STATUS       current
      DESCRIPTION
               "RxAddrErrors"
      ::= {ipv6StatsInfo 5}

   ipV6StatsRxUnknownProtos OBJECT-TYPE
      SYNTAX       Counter32
      MAX-ACCESS   read-only
      STATUS       current
      DESCRIPTION
               "RxUnknownProtos"
      ::= {ipv6StatsInfo 6}

   ipV6StatsRxTruncatedPkts OBJECT-TYPE
      SYNTAX       Counter32
      MAX-ACCESS   read-only
      STATUS       current
      DESCRIPTION
               "RxTruncatedPkts"
      ::= {ipv6StatsInfo 7}

   ipV6StatsRxDiscards OBJECT-TYPE
      SYNTAX       Counter32
      MAX-ACCESS   read-only
      STATUS       current
      DESCRIPTION
               "RxDiscards"
      ::= {ipv6StatsInfo 8}

   ipV6StatsRxDelivers OBJECT-TYPE
      SYNTAX       Counter32
      MAX-ACCESS   read-only
      STATUS       current
      DESCRIPTION
               "RxDelivers"
      ::= {ipv6StatsInfo 9}

   ipV6StatsRxMcastPkts OBJECT-TYPE
      SYNTAX       Counter32
      MAX-ACCESS   read-only
      STATUS       current
      DESCRIPTION
               "RxMcastPkts"
      ::= {ipv6StatsInfo 10}

   ipV6StatsTxForwDatagrams OBJECT-TYPE
      SYNTAX       Counter32
      MAX-ACCESS   read-only
      STATUS       current
      DESCRIPTION
               "TxForwDatagrams"
      ::= {ipv6StatsInfo 11}

   ipV6StatsTxRequests OBJECT-TYPE
      SYNTAX       Counter32
      MAX-ACCESS   read-only
      STATUS       current
      DESCRIPTION
               "TxRequests"
      ::= {ipv6StatsInfo 12}

   ipV6StatsTxDiscards OBJECT-TYPE
      SYNTAX       Counter32
      MAX-ACCESS   read-only
      STATUS       current
      DESCRIPTION
               "TxDiscards"
      ::= {ipv6StatsInfo 13}

   ipV6StatsTxNoRoutes OBJECT-TYPE
      SYNTAX       Counter32
      MAX-ACCESS   read-only
      STATUS       current
      DESCRIPTION
               "TxNoRoutes"
      ::= {ipv6StatsInfo 14}

   ipV6StatsTxMcastPkts OBJECT-TYPE
      SYNTAX       Counter32
      MAX-ACCESS   read-only
      STATUS       current
      DESCRIPTION
               "TxMcastPkts"
      ::= {ipv6StatsInfo 15}

   ipV6StatsReasmTimeout OBJECT-TYPE
      SYNTAX       Counter32
      MAX-ACCESS   read-only
      STATUS       current
      DESCRIPTION
               "ReasmTimeout"
      ::= {ipv6StatsInfo 16}

   ipV6StatsReasmReqds OBJECT-TYPE
      SYNTAX       Counter32
      MAX-ACCESS   read-only
      STATUS       current
      DESCRIPTION
               "ReasmReqds"
      ::= {ipv6StatsInfo 17}

   ipV6StatsReasmOKs OBJECT-TYPE
      SYNTAX       Counter32
      MAX-ACCESS   read-only
      STATUS       current
      DESCRIPTION
               "ReasmOKs"
      ::= {ipv6StatsInfo 18}

   ipV6StatsReasmFails OBJECT-TYPE
      SYNTAX       Counter32
      MAX-ACCESS   read-only
      STATUS       current
      DESCRIPTION
               "ReasmFails"
      ::= {ipv6StatsInfo 19}


   ipV6StatsFragOKs OBJECT-TYPE
      SYNTAX       Counter32
      MAX-ACCESS   read-only
      STATUS       current
      DESCRIPTION
               "FragOKs"
      ::= {ipv6StatsInfo 20}

   ipV6StatsFragFails OBJECT-TYPE
      SYNTAX       Counter32
      MAX-ACCESS   read-only
      STATUS       current
      DESCRIPTION
               "FragFails"
      ::= {ipv6StatsInfo 21}

   ipV6StatsFragCreates OBJECT-TYPE
      SYNTAX       Counter32
      MAX-ACCESS   read-only
      STATUS       current
      DESCRIPTION
               "FragCreates"
      ::= {ipv6StatsInfo 22}

-- ICMP V6 Stats Info

   icmpV6TxMsgs OBJECT-TYPE
     SYNTAX      Counter32
     MAX-ACCESS  read-only
     STATUS      current
     DESCRIPTION
               "TxMsgs"
     ::= {icmpv6StatsInfo 1}

   icmpV6TxErrors OBJECT-TYPE
     SYNTAX      Counter32
     MAX-ACCESS  read-only
     STATUS      current
     DESCRIPTION
               "TxErrors"
     ::= {icmpv6StatsInfo 2}

   icmpV6TxDestUnreachs OBJECT-TYPE
     SYNTAX      Counter32
     MAX-ACCESS  read-only
     STATUS      current
     DESCRIPTION
               "TxDestUnreachs"
     ::= {icmpv6StatsInfo 3}

   icmpV6TxPktTooBigs OBJECT-TYPE
     SYNTAX      Counter32
     MAX-ACCESS  read-only
     STATUS      current
     DESCRIPTION
               "TxPktTooBigs"
     ::= {icmpv6StatsInfo 4}

   icmpV6TxTimeExcds OBJECT-TYPE
     SYNTAX      Counter32
     MAX-ACCESS  read-only
     STATUS      current
     DESCRIPTION
               "TxTimeExcds"
     ::= {icmpv6StatsInfo 5}

   icmpV6TxParmProblems OBJECT-TYPE
     SYNTAX      Counter32
     MAX-ACCESS  read-only
     STATUS      current
     DESCRIPTION
               "TxParmProblems"
     ::= {icmpv6StatsInfo 6}

   icmpV6TxEchos OBJECT-TYPE
     SYNTAX      Counter32
     MAX-ACCESS  read-only
     STATUS      current
     DESCRIPTION
               "TxEchos"
     ::= {icmpv6StatsInfo 7}

   icmpV6TxEchoReplies OBJECT-TYPE
     SYNTAX      Counter32
     MAX-ACCESS  read-only
     STATUS      current
     DESCRIPTION
               "TxEchoReplies"
     ::= {icmpv6StatsInfo 8}

   icmpV6TxGroupMembQueries OBJECT-TYPE
     SYNTAX      Counter32
     MAX-ACCESS  read-only
     STATUS      current
     DESCRIPTION
               "TxGroupMembQueries"
     ::= {icmpv6StatsInfo 9}

   icmpV6TxGroupMembResponses OBJECT-TYPE
     SYNTAX      Counter32
     MAX-ACCESS  read-only
     STATUS      current
     DESCRIPTION
               "TxGroupMembResponses"
     ::= {icmpv6StatsInfo 10}

   icmpV6TxGroupMembReductions OBJECT-TYPE
     SYNTAX      Counter32
     MAX-ACCESS  read-only
     STATUS      current
     DESCRIPTION
               "TxGroupMembReductions"
     ::= {icmpv6StatsInfo 11}

   icmpV6TxRouterSolicits OBJECT-TYPE
     SYNTAX      Counter32
     MAX-ACCESS  read-only
     STATUS      current
     DESCRIPTION
               "TxRouterSolicits"
     ::= {icmpv6StatsInfo 12}

   icmpV6TxRouterAdvertisements OBJECT-TYPE
     SYNTAX      Counter32
     MAX-ACCESS  read-only
     STATUS      current
     DESCRIPTION
               "TxRouterAdvertisements"
     ::= {icmpv6StatsInfo 13}

   icmpV6TxNeighborSolicits OBJECT-TYPE
     SYNTAX      Counter32
     MAX-ACCESS  read-only
     STATUS      current
     DESCRIPTION
               "TxNeighborSolicits"
     ::= {icmpv6StatsInfo 14}

   icmpV6TxNeighborAdvertisements OBJECT-TYPE
     SYNTAX      Counter32
     MAX-ACCESS  read-only
     STATUS      current
     DESCRIPTION
               "TxNeighborAdvertisements"
     ::= {icmpv6StatsInfo 15}

   icmpV6TxRedirects OBJECT-TYPE
     SYNTAX      Counter32
     MAX-ACCESS  read-only
     STATUS      current
     DESCRIPTION
               "TxRedirects"
     ::= {icmpv6StatsInfo 16}

   icmpV6RxMsgs OBJECT-TYPE
     SYNTAX      Counter32
     MAX-ACCESS  read-only
     STATUS      current
     DESCRIPTION
               "RxMsgs"
     ::= {icmpv6StatsInfo 17}

   icmpV6RxDestUnreachs OBJECT-TYPE
     SYNTAX      Counter32
     MAX-ACCESS  read-only
     STATUS      current
     DESCRIPTION
               "RxDestUnreachs"
     ::= {icmpv6StatsInfo 18}

   icmpV6RxPktTooBigs OBJECT-TYPE
     SYNTAX      Counter32
     MAX-ACCESS  read-only
     STATUS      current
     DESCRIPTION
               "RxPktTooBigs"
     ::= {icmpv6StatsInfo 19}

   icmpV6RxTimeExcds OBJECT-TYPE
     SYNTAX      Counter32
     MAX-ACCESS  read-only
     STATUS      current
     DESCRIPTION
               "RxTimeExcds"
     ::= {icmpv6StatsInfo 20}

   icmpV6RxParmProblems OBJECT-TYPE
     SYNTAX      Counter32
     MAX-ACCESS  read-only
     STATUS      current
     DESCRIPTION
               "RxParmProblems"
     ::= {icmpv6StatsInfo 21}

   icmpV6RxEchoReplies OBJECT-TYPE
     SYNTAX      Counter32
     MAX-ACCESS  read-only
     STATUS      current
     DESCRIPTION
               "RxEchoReplies"
     ::= {icmpv6StatsInfo 22}

   icmpV6RxRouterSolicits OBJECT-TYPE
     SYNTAX      Counter32
     MAX-ACCESS  read-only
     STATUS      current
     DESCRIPTION
               "RxRouterSolicits"
     ::= {icmpv6StatsInfo 23}

   icmpV6RxNeighborSolicits OBJECT-TYPE
     SYNTAX      Counter32
     MAX-ACCESS  read-only
     STATUS      current
     DESCRIPTION
               "RxNeighborSolicits"
     ::= {icmpv6StatsInfo 24}

   icmpV6RxNeighborAdvertisements OBJECT-TYPE
     SYNTAX      Counter32
     MAX-ACCESS  read-only
     STATUS      current
     DESCRIPTION
               "RxNeighborAdvertisements"
     ::= {icmpv6StatsInfo 25}

   icmpV6RxRedirects OBJECT-TYPE
     SYNTAX      Counter32
     MAX-ACCESS  read-only
     STATUS      current
     DESCRIPTION
               "RxRedirects"
     ::= {icmpv6StatsInfo 26}

   icmpV6RxGroupMembResponses OBJECT-TYPE
     SYNTAX      Counter32
     MAX-ACCESS  read-only
     STATUS      current
     DESCRIPTION
               "RxGroupMembResponses"
     ::= {icmpv6StatsInfo 27}

   icmpV6RxGroupMembReductions OBJECT-TYPE
     SYNTAX      Counter32
     MAX-ACCESS  read-only
     STATUS      current
     DESCRIPTION
               "RxGroupMembReductions"
     ::= {icmpv6StatsInfo 28}

-- UDP V6 Stats Info

   udpV6RxDatagrams OBJECT-TYPE
     SYNTAX      Counter32
     MAX-ACCESS  read-only
     STATUS      current
     DESCRIPTION
               "udpV6RxDatagrams"
     ::= {udpv6StatsInfo 1}

   udpV6noPorts OBJECT-TYPE
     SYNTAX      Counter32
     MAX-ACCESS  read-only
     STATUS      current
     DESCRIPTION
               "udpV6noPorts"
     ::= {udpv6StatsInfo 2}

   udpV6RxErrors OBJECT-TYPE
     SYNTAX      Counter32
     MAX-ACCESS  read-only
     STATUS      current
     DESCRIPTION
               "udpV6RxErrors"
     ::= {udpv6StatsInfo 3}

   udpV6TxDatagrams OBJECT-TYPE
     SYNTAX      Counter32
     MAX-ACCESS  read-only
     STATUS      current
     DESCRIPTION
               "udpV6TxDatagrams"
     ::= {udpv6StatsInfo 4}

-- TCP Conn V6 Stats

  tcpConnv6Table OBJECT-TYPE
      SYNTAX      SEQUENCE OF TcpConnv6Entry
      MAX-ACCESS  not-accessible
      STATUS      current
      DESCRIPTION
              "The rip info table."
      ::= { tcpConnv6StatsInfo 1 }

  tcpConnv6Entry OBJECT-TYPE
      SYNTAX      TcpConnv6Entry
      MAX-ACCESS  not-accessible
      STATUS      current
      DESCRIPTION
              "An entry in the tcpConnv6Table"
      INDEX   { tcpConnv6Index }
      ::= { tcpConnv6Table 1 }

  TcpConnv6Entry ::=
      SEQUENCE {
        tcpConnv6Index
              INTEGER,
        tcpConnv6LocalAddress
            DisplayString,
        tcpConnv6LocalPort
            INTEGER,
        tcpConnv6RemoteAddress
            DisplayString,
        tcpConnv6RemotePort
            INTEGER,
        tcpConnv6TxQueue
            Counter32,
        tcpConnv6RxQueue
            Counter32,
        tcpConnv6State
            INTEGER
        }

  tcpConnv6Index OBJECT-TYPE
      SYNTAX      INTEGER
      MAX-ACCESS  not-accessible
      STATUS      current
      DESCRIPTION
              "Index"
      ::= { tcpConnv6Entry 1 }

  tcpConnv6LocalAddress OBJECT-TYPE
      SYNTAX      DisplayString
      MAX-ACCESS  read-only
      STATUS      current
      DESCRIPTION
              "LocalAddress"
      ::= { tcpConnv6Entry 2}

  tcpConnv6LocalPort OBJECT-TYPE
      SYNTAX      INTEGER
      MAX-ACCESS  read-only
      STATUS      current
      DESCRIPTION
              "LocalPort"
      ::= { tcpConnv6Entry 3}

  tcpConnv6RemoteAddress OBJECT-TYPE
      SYNTAX      DisplayString
      MAX-ACCESS  read-only
      STATUS      current
      DESCRIPTION
              "RemoteAddress"
      ::= { tcpConnv6Entry 4}

  tcpConnv6RemotePort OBJECT-TYPE
      SYNTAX      INTEGER
      MAX-ACCESS  read-only
      STATUS      current
      DESCRIPTION
              "RemotePort"
      ::= { tcpConnv6Entry 5}

  tcpConnv6TxQueue OBJECT-TYPE
      SYNTAX      Counter32
      MAX-ACCESS  read-only
      STATUS      current
      DESCRIPTION
              "TxQueue"
      ::= { tcpConnv6Entry 6}

  tcpConnv6RxQueue OBJECT-TYPE
      SYNTAX      Counter32
      MAX-ACCESS  read-only
      STATUS      current
      DESCRIPTION
              "RxQueue"
      ::= { tcpConnv6Entry 7}

  tcpConnv6State OBJECT-TYPE
      SYNTAX      INTEGER {
        established(1),
        synSent(2),
        synRecv(3),
        finWait1(4),
        finWait2(5),
        timeWait(6),
        close(7),
        closeWait(8),
        lastAck(9),
        listen(10),
        closing(11)
      }
      MAX-ACCESS  read-only
      STATUS      current
      DESCRIPTION
              "State"
      ::= { tcpConnv6Entry 8}

-- UDP Conn V6 Stats

  udpConnv6Table OBJECT-TYPE
      SYNTAX      SEQUENCE OF UdpConnv6Entry
      MAX-ACCESS  not-accessible
      STATUS      current
      DESCRIPTION
              "udpConnv6Table"
      ::= { udpConnv6StatsInfo 1 }

  udpConnv6Entry OBJECT-TYPE
      SYNTAX      UdpConnv6Entry
      MAX-ACCESS  not-accessible
      STATUS      current
      DESCRIPTION
              "An entry in the udpConnv6Table"
      INDEX   { udpConnv6Index }
      ::= { udpConnv6Table 1 }

  UdpConnv6Entry ::=
      SEQUENCE {
        udpConnv6Index
              INTEGER,
        udpConnv6LocalAddress
            DisplayString,
        udpConnv6LocalPort
            INTEGER,
        udpConnv6RemoteAddress
            DisplayString,
        udpConnv6RemotePort
            INTEGER,
        udpConnv6TxQueue
            Counter32,
        udpConnv6RxQueue
            Counter32,
        udpConnv6State
            INTEGER
        }

  udpConnv6Index OBJECT-TYPE
      SYNTAX      INTEGER
      MAX-ACCESS  not-accessible
      STATUS      current
      DESCRIPTION
              "Index"
      ::= { udpConnv6Entry 1 }

  udpConnv6LocalAddress OBJECT-TYPE
      SYNTAX      DisplayString
      MAX-ACCESS  read-only
      STATUS      current
      DESCRIPTION
              "LocalAddress"
      ::= { udpConnv6Entry 2}

  udpConnv6LocalPort OBJECT-TYPE
      SYNTAX      INTEGER
      MAX-ACCESS  read-only
      STATUS      current
      DESCRIPTION
              "LocalPort"
      ::= { udpConnv6Entry 3}

  udpConnv6RemoteAddress OBJECT-TYPE
      SYNTAX      DisplayString
      MAX-ACCESS  read-only
      STATUS      current
      DESCRIPTION
              "RemoteAddress"
      ::= { udpConnv6Entry 4}

  udpConnv6RemotePort OBJECT-TYPE
      SYNTAX      INTEGER
      MAX-ACCESS  read-only
      STATUS      current
      DESCRIPTION
              "RemotePort"
      ::= { udpConnv6Entry 5}

  udpConnv6TxQueue OBJECT-TYPE
      SYNTAX      Counter32
      MAX-ACCESS  read-only
      STATUS      current
      DESCRIPTION
              "TxQueue"
      ::= { udpConnv6Entry 6}

  udpConnv6RxQueue OBJECT-TYPE
      SYNTAX      Counter32
      MAX-ACCESS  read-only
      STATUS      current
      DESCRIPTION
              "RxQueue"
      ::= { udpConnv6Entry 7}

  udpConnv6State OBJECT-TYPE
      SYNTAX      INTEGER {
          established(1)
      }
      MAX-ACCESS  read-only
      STATUS      current
      DESCRIPTION
              "State"
      ::= { udpConnv6Entry 8}

-- Route V6 Stats

  routev6Table OBJECT-TYPE
      SYNTAX      SEQUENCE OF Routev6Entry
      MAX-ACCESS  not-accessible
      STATUS      current
      DESCRIPTION
              "The route v6 info table."
      ::= { routev6Info 1 }

  routev6Entry OBJECT-TYPE
      SYNTAX      Routev6Entry
      MAX-ACCESS  not-accessible
      STATUS      current
      DESCRIPTION
              "An entry in the routev6Table"
      INDEX   { routev6Index }
      ::= { routev6Table 1 }

  Routev6Entry ::=
      SEQUENCE {
        routev6Index
              INTEGER,
        routev6Destination
            DisplayString,
        routev6PrefixBits
            INTEGER,
        routev6Gateway
            DisplayString,
        routev6Metric
            INTEGER,
        routev6Flags
            DisplayString,
        routev6Interface
            DisplayString
        }

  routev6Index OBJECT-TYPE
      SYNTAX      INTEGER
      MAX-ACCESS  not-accessible
      STATUS      current
      DESCRIPTION
              "Index"
      ::= { routev6Entry 1 }

  routev6Destination OBJECT-TYPE
      SYNTAX      DisplayString
      MAX-ACCESS  read-only
      STATUS      current
      DESCRIPTION
              "Destination"
      ::= { routev6Entry 2}

  routev6PrefixBits OBJECT-TYPE
      SYNTAX      INTEGER
      MAX-ACCESS  read-only
      STATUS      current
      DESCRIPTION
              "PrefixBits"
      ::= { routev6Entry 3}

  routev6Gateway OBJECT-TYPE
      SYNTAX      DisplayString
      MAX-ACCESS  read-only
      STATUS      current
      DESCRIPTION
              "Gateway"
      ::= { routev6Entry 4}

  routev6Metric OBJECT-TYPE
      SYNTAX      INTEGER
      MAX-ACCESS  read-only
      STATUS      current
      DESCRIPTION
              "Metric"
      ::= { routev6Entry 5}

  routev6Flags OBJECT-TYPE
      SYNTAX      DisplayString
      MAX-ACCESS  read-only
      STATUS      current
      DESCRIPTION
              "Flags"
      ::= { routev6Entry 6}

  routev6Interface OBJECT-TYPE
      SYNTAX      DisplayString
      MAX-ACCESS  read-only
      STATUS      current
      DESCRIPTION
              "Interface"
      ::= { routev6Entry 7}

-- Rip (V6) Info

  ripv6InfoTable OBJECT-TYPE
      SYNTAX      SEQUENCE OF Ripv6InfoEntry
      MAX-ACCESS  not-accessible
      STATUS      current
      DESCRIPTION
              "The ripv6 info table."
      ::= { ripv6TableInfo 1 }

  ripv6InfoEntry OBJECT-TYPE
      SYNTAX      Ripv6InfoEntry
      MAX-ACCESS  not-accessible
      STATUS      current
      DESCRIPTION
              "An entry in the ripv6InfoTable, each relating to a ripv6 entry."
      INDEX   { ripv6Index }
      ::= { ripv6InfoTable 1 }

  Ripv6InfoEntry ::=
      SEQUENCE {
        ripv6Index
              INTEGER,
        ripv6TableIpAddr
              IpAddress,
        ripv6TableLastUpdate
            Counter32,
        ripv6TableBadPackets
            Counter32,
        ripv6TableBadRoutes
            Counter32
      }

  ripv6Index OBJECT-TYPE
      SYNTAX      INTEGER
      MAX-ACCESS  not-accessible
      STATUS      current
      DESCRIPTION
              "The table entry number for this ripv6."
      ::= { ripv6InfoEntry 1 }

  ripv6TableIpAddr OBJECT-TYPE
      SYNTAX      IpAddress
      MAX-ACCESS  read-only
      STATUS      current
      DESCRIPTION
              "ripv6IpAddr"
      ::= { ripv6InfoEntry 2 }

  ripv6TableLastUpdate OBJECT-TYPE
      SYNTAX      Counter32
      MAX-ACCESS  read-only
      STATUS      current
      DESCRIPTION
              "Last Update in Seconds"
      ::= { ripv6InfoEntry 3 }


  ripv6TableBadPackets OBJECT-TYPE
      SYNTAX      Counter32
      MAX-ACCESS  read-only
      STATUS      current
      DESCRIPTION
              "Last Update in Seconds"
      ::= { ripv6InfoEntry 4 }

  ripv6TableBadRoutes OBJECT-TYPE
      SYNTAX      Counter32
      MAX-ACCESS  read-only
      STATUS      current
      DESCRIPTION
              "Last Update in Seconds"
      ::= { ripv6InfoEntry 5 }

-- Interface V6 Stats

  interfacev6InfoTable OBJECT-TYPE
      SYNTAX      SEQUENCE OF Interfacev6InfoEntry
      MAX-ACCESS  not-accessible
      STATUS      current
      DESCRIPTION
              "The interface v6 info table."
      ::= { interfacev6Info 1 }

  interfacev6InfoEntry OBJECT-TYPE
      SYNTAX      Interfacev6InfoEntry
      MAX-ACCESS  not-accessible
      STATUS      current
      DESCRIPTION
              "IPv6 interface index."
      INDEX   { interfacev6Index }
      ::= { interfacev6InfoTable 1 }

  Interfacev6InfoEntry ::=
      SEQUENCE {
        interfacev6Index
              INTEGER,
        interfacev6Name
              DisplayString,
        interfacev6Address
              DisplayString,
        interfacev6PrefixBits
              INTEGER,
        interfacev6Scope
              INTEGER
            }

  interfacev6Index OBJECT-TYPE
      SYNTAX      INTEGER
      MAX-ACCESS  not-accessible
      STATUS      current
      DESCRIPTION
              "Index"
      ::= { interfacev6InfoEntry 1}

  interfacev6Name OBJECT-TYPE
      SYNTAX      DisplayString
      MAX-ACCESS  read-only
      STATUS      current
      DESCRIPTION
              "Name"
      ::= { interfacev6InfoEntry 2}

  interfacev6Address OBJECT-TYPE
      SYNTAX      DisplayString
      MAX-ACCESS  read-only
      STATUS      current
      DESCRIPTION
              "Address"
      ::= { interfacev6InfoEntry 3}

  interfacev6PrefixBits OBJECT-TYPE
      SYNTAX      INTEGER
      MAX-ACCESS  read-only
      STATUS      current
      DESCRIPTION
              "PrefixBits"
      ::= { interfacev6InfoEntry 4}

  interfacev6Scope OBJECT-TYPE
      SYNTAX      INTEGER {
        global(1),
        host(2),
        link(3),
        site(4),
        compatv4(5),
        unknown(6)
      }
      MAX-ACCESS  read-only
      STATUS      current
      DESCRIPTION
              "Scope"
      ::= { interfacev6InfoEntry 5}

-- SSL Server Info

  sslServerStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {sslInfo 1}

  sslVersion  OBJECT-TYPE
      SYNTAX      INTEGER {
        any(1),
        tlsv1(2),
        sslv3(3)
      }
      MAX-ACCESS    read-write
      STATUS        current
      DESCRIPTION
                "Specify whether you want to use:
                 Any-The Device Server will try a TLSv1 connection first.
                     If that fails, it will try an SSLv3 connection. 
                     If that fails, it will try an SSLv2 connection.
                 TLSv1-The connection will use only TLSv1.
                 SSLv3-The connection will use only SSLv3.
                 The default is Any."
      ::= {sslInfo 2}

  sslType    OBJECT-TYPE
      SYNTAX      INTEGER {
        client(1),
        server(2)
      }
      MAX-ACCESS    read-write
      STATUS        current
      DESCRIPTION
                "Specify whether the Device Server will act as an 
                 SSL/TLS client or server. The default is Client."
      ::= {sslInfo 3}

  sslVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {sslInfo 4}

  sslCountry    OBJECT-TYPE
      SYNTAX      DisplayString(SIZE(0..2))
      MAX-ACCESS    read-write
      STATUS        current
      DESCRIPTION
                "A two character country code; for example, US."
      ::= {sslInfo 5}

  sslStateProv    OBJECT-TYPE
      SYNTAX      DisplayString(SIZE(0..128))
      MAX-ACCESS    read-write
      STATUS        current
      DESCRIPTION
                "Up to a 128 character entry for the state/province;
                 for example, IL."
      ::= {sslInfo 6}

  sslLocality    OBJECT-TYPE
      SYNTAX      DisplayString(SIZE(0..128))
      MAX-ACCESS    read-write
      STATUS        current
      DESCRIPTION
                "Up to a 128 character entry for the location; 
                 for example, a city."
      ::= {sslInfo 7}

  sslOrganisation    OBJECT-TYPE
      SYNTAX      DisplayString(SIZE(0..64))
      MAX-ACCESS    read-write
      STATUS        current
      DESCRIPTION
                "Up to a 64 character entry for the organisation; 
                 for example, Accounting."
      ::= {sslInfo 8}

  sslOrganisationUnit    OBJECT-TYPE
      SYNTAX      DisplayString(SIZE(0..64))
      MAX-ACCESS    read-write
      STATUS        current
      DESCRIPTION
                "Up to a 64 character entry for the unit in the 
                 organisation; for example, Payroll."
      ::= {sslInfo 9}

  sslCommonName    OBJECT-TYPE
      SYNTAX      DisplayString(SIZE(0..64))
      MAX-ACCESS    read-write
      STATUS        current
      DESCRIPTION
                "Up to a 64 character entry for common name; for example,
                 the host name or fully qualified domain name."
      ::= {sslInfo 10}

  sslEmail    OBJECT-TYPE
      SYNTAX      DisplayString(SIZE(0..128))
      MAX-ACCESS    read-write
      STATUS        current
      DESCRIPTION
                "Up to a 64 character entry for an email address; 
                 for example, acct@anycompany.com."
      ::= {sslInfo 11}

-- SSL Server Cipher Table

  sslCipherTable OBJECT-TYPE
      SYNTAX      SEQUENCE OF SSLCipherEntry
      MAX-ACCESS  not-accessible
      STATUS      current
      DESCRIPTION
              "SSL CIpher."
      ::= {sslInfo 12}

  sslCipherEntry OBJECT-TYPE
      SYNTAX      SSLCipherEntry
      MAX-ACCESS  not-accessible
      STATUS      current
      DESCRIPTION
              "An entry in the sslCipherTable, each relating to a cipher entry."
      INDEX   { sslCipherPriority }
      ::= { sslCipherTable 1 }

  SSLCipherEntry ::=
      SEQUENCE {
  sslCipherPriority
       INTEGER,
  sslCipherStatus
        RowStatus,
  sslCipherEncryption
        INTEGER,
  sslCipherKeySizeMin
        INTEGER,
  sslCipherKeySizeMax
        INTEGER,
  sslCipherKeyExchange
        INTEGER,
  sslCipherHMAC
        INTEGER
      }

  sslCipherPriority OBJECT-TYPE
      SYNTAX      INTEGER
      MAX-ACCESS  not-accessible
      STATUS      current
      DESCRIPTION
              "The cipher number from highest priority(1) to lowest priority"
      ::= { sslCipherEntry 1 }

  sslCipherStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { sslCipherEntry 2 }

  sslCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { sslCipherEntry 3 }

  sslCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { sslCipherEntry 4 }

  sslCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { sslCipherEntry 5 }

  sslCipherKeyExchange OBJECT-TYPE
      SYNTAX      INTEGER {
        any(1),
        rsa(2),
        edhrsa(3),
        edhdss(4),
        adh(5) 
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { sslCipherEntry 6 }

  sslCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { sslCipherEntry 7 }

    -- Console Info
   consoleStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {consoleInfo 1}
  consoleSpeed OBJECT-TYPE
      SYNTAX      INTEGER {
        b9600(1),
        b19200(2),
        b38400(3),
        b57600(4),
        b115200(5)
      }
      MAX-ACCESS  read-write
      STATUS      current
      DESCRIPTION
              "Specifies the baud rate of the console port; keep in mind that
               speed is affected by the length of the cable."
      ::= { consoleInfo 2}

  consoleFlowControl OBJECT-TYPE
      SYNTAX      INTEGER {
        none(0),
        soft(1),
        hard(2)
      }
      MAX-ACCESS  read-write
      STATUS      current
      DESCRIPTION
              "Defines whether the data flow is handled by the
               software (Soft), hardware (Hard), Both, or None."
      ::= { consoleInfo 3}

-- Modbusgateway Info
   modbusgatewayStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {modbusgatewayInfo 1}
  modbusgatewayConnectionIdleTimeout OBJECT-TYPE
      SYNTAX      INTEGER
      MAX-ACCESS  read-write
      STATUS      current
      DESCRIPTION
              "Connection/Idle timeout: 0: never close; 1->300."
      ::= { modbusgatewayInfo 2}

  modbusgatewayException OBJECT-TYPE
      SYNTAX      OnOffValue
      MAX-ACCESS  read-write
      STATUS      current
      DESCRIPTION
              "Enable/disable modbus exception."
      ::= { modbusgatewayInfo 3}

  modbusgatewayCharacterTimeout OBJECT-TYPE
      SYNTAX      INTEGER
      MAX-ACCESS  read-write
      STATUS      current
      DESCRIPTION
              "Character timeout."
      ::= { modbusgatewayInfo 4}
	  
  modbusgatewayMessageTimeout OBJECT-TYPE
      SYNTAX      INTEGER
      MAX-ACCESS  read-write
      STATUS      current
      DESCRIPTION
              "Message timeout."
      ::= { modbusgatewayInfo 5}
	  
  modbusgatewayPortNumber OBJECT-TYPE
      SYNTAX      INTEGER
      MAX-ACCESS  read-write
      STATUS      current
      DESCRIPTION
              "Remote master transport layer (TCP/UDP) port number"
      ::= { modbusgatewayInfo 6}
	  
  modbusgatewayUIDAddressMode OBJECT-TYPE
  SYNTAX      INTEGER{
	  embedded (0),
	  remapped (1)
  }
      MAX-ACCESS  read-write
      STATUS      current
      DESCRIPTION
              "Slave UID address mode."
      ::= { modbusgatewayInfo 7}
	  
  modbusgatewayRemappedUID OBJECT-TYPE
  SYNTAX      INTEGER
      MAX-ACCESS  read-write
      STATUS      current
      DESCRIPTION
              "Remapped UID under Remapped address mode"
      ::= { modbusgatewayInfo 8}
	  
  modbusgatewayBroadcast OBJECT-TYPE
      SYNTAX      OnOffValue
      MAX-ACCESS  read-write
      STATUS      current
      DESCRIPTION
              "Enable/disable propagate Modbus TCP broadcast requests."
      ::= { modbusgatewayInfo 9}
      
  modbusgatewayNextRequestDelay OBJECT-TYPE
      SYNTAX      INTEGER
      MAX-ACCESS  read-write
      STATUS      current
      DESCRIPTION
              "Delay to allow serial slaves to re-enable receivers before issuing next
			   master request."
      ::= { modbusgatewayInfo 10}

  modbusgatewayQueuing OBJECT-TYPE
      SYNTAX      OnOffValue
      MAX-ACCESS  read-write
      STATUS      current
      DESCRIPTION
              "Enable/disable request queuing."
      ::= { modbusgatewayInfo 11}

  modbusgatewaySSL OBJECT-TYPE
      SYNTAX      OnOffValue
      MAX-ACCESS  read-write
      STATUS      current
      DESCRIPTION
              "Enable/disable modbus slave SSL."
      ::= { modbusgatewayInfo 12}
      
-- Modbus Stats Info

  modbusSlaveTCPStatsTable OBJECT-TYPE
      SYNTAX      SEQUENCE OF ModbusSlaveTCPStatsEntry
      MAX-ACCESS  not-accessible
      STATUS      current
      DESCRIPTION
              "Modbus/TCP Slave Statistics Table."
      ::= { modbusStatsInfo 1 }
      
  modbusSlaveTCPStatsEntry OBJECT-TYPE
      SYNTAX      ModbusSlaveTCPStatsEntry
      MAX-ACCESS  not-accessible
      STATUS      current
      DESCRIPTION
              "An entry in the modbus/TCP Slave statistics table, each relating to a serial port."
      INDEX   { modbusSlaveTCPStatsPortIndex }
      ::= { modbusSlaveTCPStatsTable 1 }

  ModbusSlaveTCPStatsEntry ::=
      SEQUENCE {
    modbusSlaveTCPStatsPortIndex
        INTEGER,
    modbusSlaveTCPStatsSerialMode
        INTEGER,
    modbusSlaveTCPStatsSerialFrameErrors
        INTEGER --,
    --modbusSlaveTCPStatsGatewayTable
        --SEQUENCE OF ModbusSlaveTCPStatsGatewayEntry
      }
      
      
  modbusSlaveTCPStatsPortIndex OBJECT-TYPE
      SYNTAX      INTEGER
      MAX-ACCESS  not-accessible
      STATUS      current
      DESCRIPTION
              "modbusSlaveTCPStatsPortIndex"
      ::= { modbusSlaveTCPStatsEntry 1}

  modbusSlaveTCPStatsSerialMode OBJECT-TYPE
  SYNTAX      INTEGER {
	  rtu(0),
	  ascii(1)
  }
      MAX-ACCESS  read-only
      STATUS      current
      DESCRIPTION
              "MODBUS serial device's mode: 0: RTU; 1: ASCII."
      ::= { modbusSlaveTCPStatsEntry 2}
      
  modbusSlaveTCPStatsSerialFrameErrors OBJECT-TYPE
      SYNTAX      INTEGER 
      MAX-ACCESS  read-only
      STATUS      current
      DESCRIPTION
              "MODBUS serial port frame errors"
      ::= { modbusSlaveTCPStatsEntry 3}
      
-- Modbus Gateway Statistics Table

  modbusSlaveTCPStatsGatewayTable OBJECT-TYPE
      SYNTAX      SEQUENCE OF ModbusSlaveTCPStatsGatewayEntry
      MAX-ACCESS  not-accessible
      STATUS      current
      DESCRIPTION
              "Modbus Gateway Statistics Table."
      ::= {modbusSlaveTCPStatsEntry 4}
      
  modbusSlaveTCPStatsGatewayEntry OBJECT-TYPE
      SYNTAX      ModbusSlaveTCPStatsGatewayEntry
      MAX-ACCESS  not-accessible
      STATUS      current
      DESCRIPTION
              "An entry in the modbusStatsGatewayTable."
      INDEX   {modbusSlaveTCPStatsGatewayPortIndex, modbusSlaveTCPStatsGatewayUIDIndex }
      ::= { modbusSlaveTCPStatsGatewayTable 1 }

  ModbusSlaveTCPStatsGatewayEntry ::=
      SEQUENCE {
  modbusSlaveTCPStatsGatewayPortIndex
        INTEGER,
  modbusSlaveTCPStatsGatewayUIDIndex
        INTEGER,
    modbusSlaveTCPStatsGatewayRemoteIP
        Ipv4v6Address,
    modbusSlaveTCPStatsGatewayUID
        INTEGER,
    modbusSlaveTCPStatsGatewayRemotePortNumber
        INTEGER,
    modbusSlaveTCPStatsGatewayCommands
        INTEGER,
    modbusSlaveTCPStatsGatewayResponses
        INTEGER,
    modbusSlaveTCPStatsGatewayExceptions
        INTEGER,
    modbusSlaveTCPStatsGatewayFrameErrors
        INTEGER
      }

  modbusSlaveTCPStatsGatewayPortIndex OBJECT-TYPE
      SYNTAX      INTEGER
      MAX-ACCESS  not-accessible
      STATUS      current
      DESCRIPTION
              "The port number index"
      ::= { modbusSlaveTCPStatsGatewayEntry 1 }
      
  modbusSlaveTCPStatsGatewayUIDIndex OBJECT-TYPE
      SYNTAX      INTEGER
      MAX-ACCESS  not-accessible
      STATUS      current
      DESCRIPTION
              "The UID index"
      ::= { modbusSlaveTCPStatsGatewayEntry 2 }

  modbusSlaveTCPStatsGatewayRemoteIP OBJECT-TYPE
      SYNTAX      Ipv4v6Address
      MAX-ACCESS  read-only
      STATUS      current
      DESCRIPTION
              "The remote slave/master IP address."
      ::= { modbusSlaveTCPStatsGatewayEntry 3 }

  modbusSlaveTCPStatsGatewayUID OBJECT-TYPE
      SYNTAX      INTEGER
      MAX-ACCESS  read-only
      STATUS      current
      DESCRIPTION
              "The UID."
      ::= { modbusSlaveTCPStatsGatewayEntry 4 }

  modbusSlaveTCPStatsGatewayRemotePortNumber OBJECT-TYPE
      SYNTAX      INTEGER
      MAX-ACCESS  read-only
      STATUS      current
      DESCRIPTION
              "the remote tcp/udp port number."
      ::= { modbusSlaveTCPStatsGatewayEntry 5 }

  modbusSlaveTCPStatsGatewayCommands OBJECT-TYPE
      SYNTAX      INTEGER
      MAX-ACCESS  read-only
      STATUS      current
      DESCRIPTION
              "the commands count."
      ::= { modbusSlaveTCPStatsGatewayEntry 6 }
	  
  modbusSlaveTCPStatsGatewayResponses OBJECT-TYPE
      SYNTAX      INTEGER
      MAX-ACCESS  read-only
      STATUS      current
      DESCRIPTION
              "the response count."
      ::= { modbusSlaveTCPStatsGatewayEntry 7 }
      
  modbusSlaveTCPStatsGatewayExceptions OBJECT-TYPE
      SYNTAX      INTEGER
      MAX-ACCESS  read-only
      STATUS      current
      DESCRIPTION
              "the exceptions count."
      ::= { modbusSlaveTCPStatsGatewayEntry 8 }
      
  modbusSlaveTCPStatsGatewayFrameErrors OBJECT-TYPE
      SYNTAX      INTEGER
      MAX-ACCESS  read-only
      STATUS      current
      DESCRIPTION
              "the frame errors count."
      ::= { modbusSlaveTCPStatsGatewayEntry 9 }
      
  modbusMasterTCPStatsTable OBJECT-TYPE
      SYNTAX      SEQUENCE OF ModbusMasterTCPStatsEntry
      MAX-ACCESS  not-accessible
      STATUS      current
      DESCRIPTION
              "Modbus/TCP Master Statistics Table."
      ::= { modbusStatsInfo 2 }
      
  modbusMasterTCPStatsEntry OBJECT-TYPE
      SYNTAX      ModbusMasterTCPStatsEntry
      MAX-ACCESS  not-accessible
      STATUS      current
      DESCRIPTION
              "An entry in the modbus/TCP Master statistics table, each relating to a serial port."
      INDEX   { modbusMasterTCPStatsPortIndex }
      ::= { modbusMasterTCPStatsTable 1 }

  ModbusMasterTCPStatsEntry ::=
      SEQUENCE
      {
        modbusMasterTCPStatsPortIndex
            INTEGER,
        modbusMasterTCPStatsSerialMode
            INTEGER,
        modbusMasterTCPStatsSerialFrameErrors
            INTEGER --,
        --modbusMasterTCPStatsGatewayTable
            --SEQUENCE OF ModbusMasterTCPStatsGatewayEntry
      }
      
  modbusMasterTCPStatsPortIndex OBJECT-TYPE
      SYNTAX      INTEGER
      MAX-ACCESS  not-accessible
      STATUS      current
      DESCRIPTION
              "modbusMasterTCPStatsPortIndex"
      ::= { modbusMasterTCPStatsEntry 1}

  modbusMasterTCPStatsSerialMode OBJECT-TYPE
  SYNTAX      INTEGER {
	  rtu(0),
	  ascii(1)
  }
      MAX-ACCESS  read-only
      STATUS      current
      DESCRIPTION
              "MODBUS serial device's mode: 0: RTU; 1: ASCII."
      ::= { modbusMasterTCPStatsEntry 2}
      
  modbusMasterTCPStatsSerialFrameErrors OBJECT-TYPE
      SYNTAX      INTEGER 
      MAX-ACCESS  read-only
      STATUS      current
      DESCRIPTION
              "MODBUS serial port frame errors"
      ::= { modbusMasterTCPStatsEntry 3}
      
-- Modbus Gateway Statistics Table

  modbusMasterTCPStatsGatewayTable OBJECT-TYPE
      SYNTAX      SEQUENCE OF ModbusMasterTCPStatsGatewayEntry
      MAX-ACCESS  not-accessible
      STATUS      current
      DESCRIPTION
              "Modbus Gateway Statistics Table."
      ::= {modbusMasterTCPStatsEntry 4}
      
  modbusMasterTCPStatsGatewayEntry OBJECT-TYPE
      SYNTAX      ModbusMasterTCPStatsGatewayEntry
      MAX-ACCESS  not-accessible
      STATUS      current
      DESCRIPTION
              "An entry in the modbusStatsGatewayTable."
      INDEX   {modbusMasterTCPStatsGatewayPortIndex, modbusMasterTCPStatsGatewayUIDIndex }
      ::= { modbusMasterTCPStatsGatewayTable 1 }

  ModbusMasterTCPStatsGatewayEntry ::=
      SEQUENCE {
  modbusMasterTCPStatsGatewayPortIndex
        INTEGER,
  modbusMasterTCPStatsGatewayUIDIndex
        INTEGER,
    modbusMasterTCPStatsGatewayRemoteIP
        Ipv4v6Address,
    modbusMasterTCPStatsGatewayUID
        INTEGER,
    modbusMasterTCPStatsGatewayRemotePortNumber
        INTEGER,
    modbusMasterTCPStatsGatewayCommands
        INTEGER,
    modbusMasterTCPStatsGatewayResponses
        INTEGER,
    modbusMasterTCPStatsGatewayExceptions
        INTEGER,
    modbusMasterTCPStatsGatewayFrameErrors
        INTEGER
      }

  modbusMasterTCPStatsGatewayPortIndex OBJECT-TYPE
      SYNTAX      INTEGER
      MAX-ACCESS  not-accessible
      STATUS      current
      DESCRIPTION
              "The port number index"
      ::= { modbusMasterTCPStatsGatewayEntry 1 }
      
  modbusMasterTCPStatsGatewayUIDIndex OBJECT-TYPE
      SYNTAX      INTEGER
      MAX-ACCESS  not-accessible
      STATUS      current
      DESCRIPTION
              "The UID index"
      ::= { modbusMasterTCPStatsGatewayEntry 2 }

  modbusMasterTCPStatsGatewayRemoteIP OBJECT-TYPE
      SYNTAX      Ipv4v6Address
      MAX-ACCESS  read-only
      STATUS      current
      DESCRIPTION
              "The remote slave/master IP address."
      ::= { modbusMasterTCPStatsGatewayEntry 3 }

  modbusMasterTCPStatsGatewayUID OBJECT-TYPE
      SYNTAX      INTEGER
      MAX-ACCESS  read-only
      STATUS      current
      DESCRIPTION
              "The UID."
      ::= { modbusMasterTCPStatsGatewayEntry 4 }

  modbusMasterTCPStatsGatewayRemotePortNumber OBJECT-TYPE
      SYNTAX      INTEGER
      MAX-ACCESS  read-only
      STATUS      current
      DESCRIPTION
              "the remote tcp/udp port number."
      ::= { modbusMasterTCPStatsGatewayEntry 5 }

  modbusMasterTCPStatsGatewayCommands OBJECT-TYPE
      SYNTAX      INTEGER
      MAX-ACCESS  read-only
      STATUS      current
      DESCRIPTION
              "the commands count."
      ::= { modbusMasterTCPStatsGatewayEntry 6 }
	  
  modbusMasterTCPStatsGatewayResponses OBJECT-TYPE
      SYNTAX      INTEGER
      MAX-ACCESS  read-only
      STATUS      current
      DESCRIPTION
              "the response count."
      ::= { modbusMasterTCPStatsGatewayEntry 7 }
      
  modbusMasterTCPStatsGatewayExceptions OBJECT-TYPE
      SYNTAX      INTEGER
      MAX-ACCESS  read-only
      STATUS      current
      DESCRIPTION
              "the exceptions count."
      ::= { modbusMasterTCPStatsGatewayEntry 8 }
      
  modbusMasterTCPStatsGatewayFrameErrors OBJECT-TYPE
      SYNTAX      INTEGER
      MAX-ACCESS  read-only
      STATUS      current
      DESCRIPTION
              "the frame errors count."
      ::= { modbusMasterTCPStatsGatewayEntry 9 }
      
  modbusSlaveUDPStatsTable OBJECT-TYPE
      SYNTAX      SEQUENCE OF ModbusSlaveUDPStatsEntry
      MAX-ACCESS  not-accessible
      STATUS      current
      DESCRIPTION
              "Modbus/UDP Slave Statistics Table."
      ::= { modbusStatsInfo 3 }
      
  modbusSlaveUDPStatsEntry OBJECT-TYPE
      SYNTAX      ModbusSlaveUDPStatsEntry
      MAX-ACCESS  not-accessible
      STATUS      current
      DESCRIPTION
              "An entry in the modbus/UDP Slave statistics table, each relating to a serial port."
      INDEX   { modbusSlaveUDPStatsPortIndex }
      ::= { modbusSlaveUDPStatsTable 1 }

  ModbusSlaveUDPStatsEntry ::=
      SEQUENCE
      {
        modbusSlaveUDPStatsPortIndex
            INTEGER,
        modbusSlaveUDPStatsSerialMode
            INTEGER,
        modbusSlaveUDPStatsSerialFrameErrors
            INTEGER --,
        --modbusSlaveUDPStatsGatewayTable
            --SEQUENCE OF ModbusSlaveUDPStatsGatewayEntry
      }
      
  modbusSlaveUDPStatsPortIndex OBJECT-TYPE
      SYNTAX      INTEGER
      MAX-ACCESS  not-accessible
      STATUS      current
      DESCRIPTION
              "modbusSlaveUDPStatsPortIndex"
      ::= { modbusSlaveUDPStatsEntry 1}

  modbusSlaveUDPStatsSerialMode OBJECT-TYPE
  SYNTAX      INTEGER {
	  rtu(0),
	  ascii(1)
  }
      MAX-ACCESS  read-only
      STATUS      current
      DESCRIPTION
              "MODBUS serial device's mode: 0: RTU; 1: ASCII."
      ::= { modbusSlaveUDPStatsEntry 2}
      
  modbusSlaveUDPStatsSerialFrameErrors OBJECT-TYPE
      SYNTAX      INTEGER 
      MAX-ACCESS  read-only
      STATUS      current
      DESCRIPTION
              "MODBUS serial port frame errors"
      ::= { modbusSlaveUDPStatsEntry 3}
      
-- Modbus Gateway Statistics Table

  modbusSlaveUDPStatsGatewayTable OBJECT-TYPE
      SYNTAX      SEQUENCE OF ModbusSlaveUDPStatsGatewayEntry
      MAX-ACCESS  not-accessible
      STATUS      current
      DESCRIPTION
              "Modbus Gateway Statistics Table."
      ::= {modbusSlaveUDPStatsEntry 4}
      
  modbusSlaveUDPStatsGatewayEntry OBJECT-TYPE
      SYNTAX      ModbusSlaveUDPStatsGatewayEntry
      MAX-ACCESS  not-accessible
      STATUS      current
      DESCRIPTION
              "An entry in the modbusStatsGatewayTable."
      INDEX   {modbusSlaveUDPStatsGatewayPortIndex, modbusSlaveUDPStatsGatewayUIDIndex }
      ::= { modbusSlaveUDPStatsGatewayTable 1 }

  ModbusSlaveUDPStatsGatewayEntry ::=
      SEQUENCE {
  modbusSlaveUDPStatsGatewayPortIndex
        INTEGER,
  modbusSlaveUDPStatsGatewayUIDIndex
        INTEGER,
    modbusSlaveUDPStatsGatewayRemoteIP
        Ipv4v6Address,
    modbusSlaveUDPStatsGatewayUID
        INTEGER,
    modbusSlaveUDPStatsGatewayRemotePortNumber
        INTEGER,
    modbusSlaveUDPStatsGatewayCommands
        INTEGER,
    modbusSlaveUDPStatsGatewayResponses
        INTEGER,
    modbusSlaveUDPStatsGatewayExceptions
        INTEGER,
    modbusSlaveUDPStatsGatewayFrameErrors
        INTEGER
      }

  modbusSlaveUDPStatsGatewayPortIndex OBJECT-TYPE
      SYNTAX      INTEGER
      MAX-ACCESS  not-accessible
      STATUS      current
      DESCRIPTION
              "The port number index"
      ::= { modbusSlaveUDPStatsGatewayEntry 1 }
      
  modbusSlaveUDPStatsGatewayUIDIndex OBJECT-TYPE
      SYNTAX      INTEGER
      MAX-ACCESS  not-accessible
      STATUS      current
      DESCRIPTION
              "The UID index"
      ::= { modbusSlaveUDPStatsGatewayEntry 2 }

  modbusSlaveUDPStatsGatewayRemoteIP OBJECT-TYPE
      SYNTAX      Ipv4v6Address
      MAX-ACCESS  read-only
      STATUS      current
      DESCRIPTION
              "The remote slave/master IP address."
      ::= { modbusSlaveUDPStatsGatewayEntry 3 }

  modbusSlaveUDPStatsGatewayUID OBJECT-TYPE
      SYNTAX      INTEGER
      MAX-ACCESS  read-only
      STATUS      current
      DESCRIPTION
              "The UID."
      ::= { modbusSlaveUDPStatsGatewayEntry 4 }

  modbusSlaveUDPStatsGatewayRemotePortNumber OBJECT-TYPE
      SYNTAX      INTEGER
      MAX-ACCESS  read-only
      STATUS      current
      DESCRIPTION
              "the remote tcp/udp port number."
      ::= { modbusSlaveUDPStatsGatewayEntry 5 }

  modbusSlaveUDPStatsGatewayCommands OBJECT-TYPE
      SYNTAX      INTEGER
      MAX-ACCESS  read-only
      STATUS      current
      DESCRIPTION
              "the commands count."
      ::= { modbusSlaveUDPStatsGatewayEntry 6 }
	  
  modbusSlaveUDPStatsGatewayResponses OBJECT-TYPE
      SYNTAX      INTEGER
      MAX-ACCESS  read-only
      STATUS      current
      DESCRIPTION
              "the response count."
      ::= { modbusSlaveUDPStatsGatewayEntry 7 }
      
  modbusSlaveUDPStatsGatewayExceptions OBJECT-TYPE
      SYNTAX      INTEGER
      MAX-ACCESS  read-only
      STATUS      current
      DESCRIPTION
              "the exceptions count."
      ::= { modbusSlaveUDPStatsGatewayEntry 8 }
      
  modbusSlaveUDPStatsGatewayFrameErrors OBJECT-TYPE
      SYNTAX      INTEGER
      MAX-ACCESS  read-only
      STATUS      current
      DESCRIPTION
              "the frame errors count."
      ::= { modbusSlaveUDPStatsGatewayEntry 9 }

  modbusMasterUDPStatsTable OBJECT-TYPE
      SYNTAX      SEQUENCE OF ModbusMasterUDPStatsEntry
      MAX-ACCESS  not-accessible
      STATUS      current
      DESCRIPTION
              "Modbus/UDP Master Statistics Table."
      ::= { modbusStatsInfo 4 }
      
  modbusMasterUDPStatsEntry OBJECT-TYPE
      SYNTAX      ModbusMasterUDPStatsEntry
      MAX-ACCESS  not-accessible
      STATUS      current
      DESCRIPTION
              "An entry in the modbus/UDP Master statistics table, each relating to a serial port."
      INDEX   { modbusMasterUDPStatsPortIndex }
      ::= { modbusMasterUDPStatsTable 1 }

  ModbusMasterUDPStatsEntry ::=
      SEQUENCE
      {
        modbusMasterUDPStatsPortIndex
            INTEGER,
        modbusMasterUDPStatsSerialMode
            INTEGER,
        modbusMasterUDPStatsSerialFrameErrors
            INTEGER --,
        --modbusMasterUDPStatsGatewayTable
            --SEQUENCE OF ModbusMasterUDPStatsGatewayEntry
      }
      
  modbusMasterUDPStatsPortIndex OBJECT-TYPE
      SYNTAX      INTEGER
      MAX-ACCESS  not-accessible
      STATUS      current
      DESCRIPTION
              "modbusMasterUDPStatsPortIndex"
      ::= { modbusMasterUDPStatsEntry 1}

  modbusMasterUDPStatsSerialMode OBJECT-TYPE
  SYNTAX      INTEGER {
	  rtu(0),
	  ascii(1)
  }
      MAX-ACCESS  read-only
      STATUS      current
      DESCRIPTION
              "MODBUS serial device's mode: 0: RTU; 1: ASCII."
      ::= { modbusMasterUDPStatsEntry 2}
      
  modbusMasterUDPStatsSerialFrameErrors OBJECT-TYPE
      SYNTAX      INTEGER 
      MAX-ACCESS  read-only
      STATUS      current
      DESCRIPTION
              "MODBUS serial port frame errors"
      ::= { modbusMasterUDPStatsEntry 3}
      
-- Modbus Gateway Statistics Table

  modbusMasterUDPStatsGatewayTable OBJECT-TYPE
      SYNTAX      SEQUENCE OF ModbusMasterUDPStatsGatewayEntry
      MAX-ACCESS  not-accessible
      STATUS      current
      DESCRIPTION
              "Modbus Gateway Statistics Table."
      ::= {modbusMasterUDPStatsEntry 4}
      
  modbusMasterUDPStatsGatewayEntry OBJECT-TYPE
      SYNTAX      ModbusMasterUDPStatsGatewayEntry
      MAX-ACCESS  not-accessible
      STATUS      current
      DESCRIPTION
              "An entry in the modbusStatsGatewayTable."
      INDEX   {modbusMasterUDPStatsGatewayPortIndex, modbusMasterUDPStatsGatewayUIDIndex }
      ::= { modbusMasterUDPStatsGatewayTable 1 }

  ModbusMasterUDPStatsGatewayEntry ::=
      SEQUENCE {
  modbusMasterUDPStatsGatewayPortIndex
        INTEGER,
  modbusMasterUDPStatsGatewayUIDIndex
        INTEGER,
    modbusMasterUDPStatsGatewayRemoteIP
        Ipv4v6Address,
    modbusMasterUDPStatsGatewayUID
        INTEGER,
    modbusMasterUDPStatsGatewayRemotePortNumber
        INTEGER,
    modbusMasterUDPStatsGatewayCommands
        INTEGER,
    modbusMasterUDPStatsGatewayResponses
        INTEGER,
    modbusMasterUDPStatsGatewayExceptions
        INTEGER,
    modbusMasterUDPStatsGatewayFrameErrors
        INTEGER
      }

  modbusMasterUDPStatsGatewayPortIndex OBJECT-TYPE
      SYNTAX      INTEGER
      MAX-ACCESS  not-accessible
      STATUS      current
      DESCRIPTION
              "The port number index"
      ::= { modbusMasterUDPStatsGatewayEntry 1 }
      
  modbusMasterUDPStatsGatewayUIDIndex OBJECT-TYPE
      SYNTAX      INTEGER
      MAX-ACCESS  not-accessible
      STATUS      current
      DESCRIPTION
              "The UID index"
      ::= { modbusMasterUDPStatsGatewayEntry 2 }

  modbusMasterUDPStatsGatewayRemoteIP OBJECT-TYPE
      SYNTAX      Ipv4v6Address
      MAX-ACCESS  read-only
      STATUS      current
      DESCRIPTION
              "The remote slave/master IP address."
      ::= { modbusMasterUDPStatsGatewayEntry 3 }

  modbusMasterUDPStatsGatewayUID OBJECT-TYPE
      SYNTAX      INTEGER
      MAX-ACCESS  read-only
      STATUS      current
      DESCRIPTION
              "The UID."
      ::= { modbusMasterUDPStatsGatewayEntry 4 }

  modbusMasterUDPStatsGatewayRemotePortNumber OBJECT-TYPE
      SYNTAX      INTEGER
      MAX-ACCESS  read-only
      STATUS      current
      DESCRIPTION
              "the remote tcp/udp port number."
      ::= { modbusMasterUDPStatsGatewayEntry 5 }

  modbusMasterUDPStatsGatewayCommands OBJECT-TYPE
      SYNTAX      INTEGER
      MAX-ACCESS  read-only
      STATUS      current
      DESCRIPTION
              "the commands count."
      ::= { modbusMasterUDPStatsGatewayEntry 6 }
	  
  modbusMasterUDPStatsGatewayResponses OBJECT-TYPE
      SYNTAX      INTEGER
      MAX-ACCESS  read-only
      STATUS      current
      DESCRIPTION
              "the response count."
      ::= { modbusMasterUDPStatsGatewayEntry 7 }
      
  modbusMasterUDPStatsGatewayExceptions OBJECT-TYPE
      SYNTAX      INTEGER
      MAX-ACCESS  read-only
      STATUS      current
      DESCRIPTION
              "the exceptions count."
      ::= { modbusMasterUDPStatsGatewayEntry 8 }
      
  modbusMasterUDPStatsGatewayFrameErrors OBJECT-TYPE
      SYNTAX      INTEGER
      MAX-ACCESS  read-only
      STATUS      current
      DESCRIPTION
              "the frame errors count."
      ::= { modbusMasterUDPStatsGatewayEntry 9 }

  ioModbusSlaveStats OBJECT IDENTIFIER ::= { modbusStatsInfo 5 }          
  ioModbusSlaveStatsServiceMode OBJECT-TYPE
      SYNTAX      OnOffValue
      MAX-ACCESS  read-only
      STATUS      current
      DESCRIPTION
              "Indicates whether I/O Modbus service is active"
      ::= { ioModbusSlaveStats 1 }

  ioModbusSlaveStatsUid OBJECT-TYPE
      SYNTAX      INTEGER(0..255)
      MAX-ACCESS  read-only
      STATUS      current
      DESCRIPTION
              "I/O Modbus Slave UID"
      ::= { ioModbusSlaveStats 2 }
      
  ioModbusSlaveStatsCommands OBJECT-TYPE
      SYNTAX      Counter32
      MAX-ACCESS  read-only
      STATUS      current
      DESCRIPTION
              "I/O Modbus Slave Commands"
      ::= { ioModbusSlaveStats 3 }
      
  ioModbusSlaveStatsResponses OBJECT-TYPE
      SYNTAX      Counter32
      MAX-ACCESS  read-only
      STATUS      current
      DESCRIPTION
              "I/O Modbus Slave Responses"
      ::= { ioModbusSlaveStats 4 }
      
  ioModbusSlaveStatsExceptions OBJECT-TYPE
      SYNTAX      Counter32
      MAX-ACCESS  read-only
      STATUS      current
      DESCRIPTION
              "I/O Modbus Slave Exceptions"
      ::= { ioModbusSlaveStats 5 }
      

  --  customAppServerInfo group.

  customAppServerStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { customAppServerInfo 1 }

  customAppServerCommand OBJECT-TYPE
      SYNTAX      DisplayString(SIZE(1..80))
      MAX-ACCESS  read-write
      STATUS      current
      DESCRIPTION
              "The command line for custom application."
      ::= { customAppServerInfo 2 }


-- I/O info BEGINS  

ioGlobalCfg          OBJECT IDENTIFIER ::= { ioInfo 1 }
ioChannelInfo        OBJECT IDENTIFIER ::= { ioInfo 2 }

ioChannelCfg         OBJECT IDENTIFIER ::= { ioChannelInfo 1 }
ioChannelStatus      OBJECT IDENTIFIER ::= { ioChannelInfo 2 }


  -- I/O global config BEGINS
  ioGlobalCfgStatus OBJECT-TYPE
      SYNTAX      INTEGER
      {
        configUnchanged(1),
        configChanged(2),
        submitChanges(4),
        discardChanges(6)
      }
      MAX-ACCESS  read-write
      STATUS      current
      DESCRIPTION
              "When read, this object indicates the state of all the configuration 
               objects in the ioGlobalCfg group (including all sub-groups and
               tables).  
               
               Read values:
               'configUnchanged'
                 Indicates that none of the configuration objects have been 
                 changed since the last submit operation.
               'configChanged' value is read,
                 Indicates that 1 or more of the configuration objects has 
                 changed, and a 'submit_changes' operation is required to commit
                 the values from temporary storage to running config.
                 
               Write values:
               'submitChanges'
                 Causes all configuration objects in the ioGlobalCfg group
                 to be committed from temporary storage to running config.
               'discardChanges'
                 Causes all changes to configuration objects to be discarded
                 from temporary storage (and replaced with values from 
                 running config)."
      ::= { ioGlobalCfg 1 }
      
  ioTemperatureScale OBJECT-TYPE
      SYNTAX      INTEGER {
               celsius(1),
               fahrenheit(2)
      }
      MAX-ACCESS  read-write
      STATUS      current
      DESCRIPTION
              "The temperature scale to be used when displaying 
               thermocouple or RTD values"
      ::= { ioGlobalCfg 2 }
      
  ioFailsafeCfg OBJECT IDENTIFIER ::= { ioGlobalCfg 3 }
  ioFailsafeEnable OBJECT-TYPE
      SYNTAX      OnOffValue
      MAX-ACCESS  read-write
      STATUS      current
      DESCRIPTION
              "Enable/disable I/O failsafe timer"
      ::= { ioFailsafeCfg 1 }
  ioFailsafeTimeout    OBJECT-TYPE
      SYNTAX      INTEGER(1..9999)
      MAX-ACCESS  read-write
      STATUS      current
      DESCRIPTION
              "I/O failsafe timeout, in seconds"
      ::= { ioFailsafeCfg 2 }
      
  ioModbusCfg OBJECT IDENTIFIER ::= { ioGlobalCfg 4 }          
  ioModbusEnable OBJECT-TYPE
      SYNTAX      OnOffValue
      MAX-ACCESS  read-write
      STATUS      current
      DESCRIPTION
              "Enable/disable I/O Modbus service"
      ::= { ioModbusCfg 1 }
  ioModbusUid    OBJECT-TYPE
      SYNTAX      INTEGER(0..255)
      MAX-ACCESS  read-write
      STATUS      current
      DESCRIPTION
              "I/O Modbus UID"
      ::= { ioModbusCfg 2 }
      
      
  ioUdpCfg OBJECT IDENTIFIER ::= { ioGlobalCfg 5 }
  ioUdpEnable OBJECT-TYPE
      SYNTAX      OnOffValue
      MAX-ACCESS  read-write
      STATUS      current
      DESCRIPTION
              "Enable/disable I/O UDP service"
      ::= { ioUdpCfg 1 }
  
  ioUdpBroadcastInterval    OBJECT-TYPE
      SYNTAX      INTEGER(1..9999)
      MAX-ACCESS  read-write
      STATUS      current
      DESCRIPTION
              "I/O UDP broadcast interval, in seconds"
      ::= { ioUdpCfg 2 }
      
-- I/O UDP Table

  ioUdpTable OBJECT-TYPE
      SYNTAX      SEQUENCE OF IoUdpEntry
      MAX-ACCESS  not-accessible
      STATUS      current
      DESCRIPTION
              "Port UDP Table."
      ::= { ioUdpCfg 3 }

  ioUdpEntry OBJECT-TYPE
      SYNTAX      IoUdpEntry
      MAX-ACCESS  not-accessible
      STATUS      current
      DESCRIPTION
              "An entry in the ioUdpEntry, each relating to a port."
      INDEX   { ioUdpEntryIndex }
      ::= { ioUdpTable 1 }

  IoUdpEntry ::=
      SEQUENCE {
        ioUdpEntryIndex
            INTEGER,
        ioUdpEntryEnable
            OnOffValue,
        ioUdpEntryStartAddress
            Ipv4v6Address,
        ioUdpEntryEndAddress
            Ipv4v6Address,
        ioUdpEntryPort
            INTEGER
        }

  ioUdpEntryIndex OBJECT-TYPE
      SYNTAX      INTEGER
      MAX-ACCESS  read-only
      STATUS      current
      DESCRIPTION
              "ioUdpNumber"
      ::= { ioUdpEntry 1 }


  ioUdpEntryEnable  OBJECT-TYPE
      SYNTAX      OnOffValue
      MAX-ACCESS  read-write
      STATUS      current
      DESCRIPTION 
                "Enable/disable this UDP entry"
      ::= { ioUdpEntry 2 }
      
  ioUdpEntryStartAddress OBJECT-TYPE
      SYNTAX      Ipv4v6Address
      MAX-ACCESS  read-write
      STATUS      current
      DESCRIPTION
              "The first host IP address in the range of IP addresses
               (for IPV4 or IPV6) that the Device Server 
               send messages to"
      ::= { ioUdpEntry 3 }

  ioUdpEntryEndAddress OBJECT-TYPE
      SYNTAX      Ipv4v6Address
      MAX-ACCESS  read-write
      STATUS      current
      DESCRIPTION
              "The last host IP address in the range of IP addresses (for
               IPV4, not required for IPV6) that the Device Server will
               send messages to."
      ::= { ioUdpEntry 4 }

  ioUdpEntryPort OBJECT-TYPE
      SYNTAX      INTEGER(0..65535)
      MAX-ACCESS  read-write
      STATUS      current
      DESCRIPTION
              "The port that the Device Server will use to 
               relay messages to servers/hosts."
      ::= { ioUdpEntry 5 }


  ioTrueportCfg OBJECT IDENTIFIER ::= { ioGlobalCfg 6 }          
  ioTrueportEnable OBJECT-TYPE
      SYNTAX      OnOffValue
      MAX-ACCESS  read-write
      STATUS      current
      DESCRIPTION
          "Enable/disable I/O TruePort service"
      ::= { ioTrueportCfg 1 }
  ioTrueportTcpListenPort    OBJECT-TYPE
      SYNTAX      INTEGER(1..65535)
      MAX-ACCESS  read-write
      STATUS      current
      DESCRIPTION
          "I/O TruePort TCP Listening Port"
      ::= { ioTrueportCfg 2 }
      
  ioTrueportSslEnable    OBJECT-TYPE
      SYNTAX      OnOffValue
      MAX-ACCESS  read-write
      STATUS      current
      DESCRIPTION
          "Enable/disable I/O TruePort SSL"
      ::= { ioTrueportCfg 3 }

      
  -- I/O global config ENDS
  
 ioAnalogCfg       OBJECT IDENTIFIER ::= { ioChannelCfg 1 }
 ioDigitalCfg      OBJECT IDENTIFIER ::= { ioChannelCfg 2 }
 ioRelayCfg        OBJECT IDENTIFIER ::= { ioChannelCfg 3 }
 ioLineSignalCfg   OBJECT IDENTIFIER ::= { ioChannelCfg 4 }

-- I/O Analog config BEGINS
  ioAnalogCfgTable OBJECT-TYPE
      SYNTAX      SEQUENCE OF IoAnalogCfgEntry
      MAX-ACCESS  not-accessible
      STATUS      current
      DESCRIPTION
              "ioAnalogCfgTable."
      ::= { ioAnalogCfg 1 }

  ioAnalogCfgEntry OBJECT-TYPE
      SYNTAX      IoAnalogCfgEntry
      MAX-ACCESS  not-accessible
      STATUS      current
      DESCRIPTION
              "An entry in the ioAnalogCfgTable"
      INDEX   { ioAnalogCfgChannelIndex }
      ::= { ioAnalogCfgTable 1 }

  IoAnalogCfgEntry ::= 
      SEQUENCE 
      {
        ioAnalogCfgChannelIndex
          INTEGER,
        ioAnalogCfgStatus
          RowStatus,
        ioAnalogCfgEnable
          OnOffValue,
        ioAnalogCfgDescription
          DisplayString,
        ioAnalogCfgType
          INTEGER,
        ioAnalogCfgRtdRange
          INTEGER,
        ioAnalogCfgThermRange
          INTEGER,
        ioAnalogCfgCurrentRange
          INTEGER,
        ioAnalogCfgVoltageRange
          INTEGER,
        ioAnalogCfgAlarmTrigger
          INTEGER,
        ioAnalogCfgAlarmClearMode
          INTEGER
      }

  ioAnalogCfgChannelIndex OBJECT-TYPE
      SYNTAX      INTEGER
      MAX-ACCESS  read-only
      STATUS      current
      DESCRIPTION
              "Index"
      ::= { ioAnalogCfgEntry 1 }

  ioAnalogCfgStatus OBJECT-TYPE
      SYNTAX      RowStatus
      MAX-ACCESS  read-write
      STATUS      current
      DESCRIPTION
              "NOTE: This object also applies to the corresponding rows
               in ioAnalogAlarmCfgTable.  e.g. If changes are submitted
               to row 1 of this table (i.e. channel 1), then changes will
               also be submitted for all rows in ioAnalogAlarmCfgTable where
               ioAnalogAlarmCfgChannelIndex is equal to 1.
               
               When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioAnalogCfgEntry 2 }

  ioAnalogCfgEnable OBJECT-TYPE
      SYNTAX      OnOffValue
      MAX-ACCESS  read-write
      STATUS      current
      DESCRIPTION
              "Enable/disable this analog I/O resource"
      ::= { ioAnalogCfgEntry 3 }

  ioAnalogCfgDescription OBJECT-TYPE
      SYNTAX      DisplayString(SIZE(0..20))
      MAX-ACCESS  read-write
      STATUS      current
      DESCRIPTION
              "Description for the I/O resource"
      ::= { ioAnalogCfgEntry 4 }

  ioAnalogCfgType OBJECT-TYPE
      SYNTAX      INTEGER
      {
          none(1),
          rtd(2),
          thermocouple(3),
          current(4),
          voltage(5)
      }
      MAX-ACCESS  read-write
      STATUS      current
      DESCRIPTION
              "Analog I/O resource type.  For current and voltage types, please 
               note that the corresponding hardware jumpers must be set 
               accordingly."
      ::= { ioAnalogCfgEntry 5 }
      
  ioAnalogCfgRtdRange OBJECT-TYPE
      SYNTAX      INTEGER
      {
          pt100A385RangeMinus50to150(1),
          pt100A385Range0to100(2),
          pt100A385Range0to200(3),
          pt100A385Range0to400(4),
          pt100A385RangeMinus200to200(5),
          pt100A392RangeMinus50to150(6),
          pt100A392Range0to100(7),
          pt100A392Range0to200(8),
          pt100A392Range0to400(9),
          pt100A392RangeMinus200to200(10),
          pt1000A385RangeMinus40to160(11),
          nickelRangeMinus80to100(12),
          nickelRange0to100(13)
          
      }
      MAX-ACCESS  read-write
      STATUS      current
      DESCRIPTION
              "Range for RTD analog I/O"
      ::= { ioAnalogCfgEntry 6 }

  ioAnalogCfgThermRange OBJECT-TYPE
      SYNTAX      INTEGER
      {
          j(1),
          k(2),
          t(3),
          e(4),
          r(5),
          s(6),
          b(7)
      }
      MAX-ACCESS  read-write
      STATUS      current
      DESCRIPTION
              "Range for thermocouple analog I/O"
      ::= { ioAnalogCfgEntry 7 }

  ioAnalogCfgCurrentRange OBJECT-TYPE
      SYNTAX      INTEGER
      {
          ampsRange0to20(1),
          ampsRange4to20(2)
      }
      MAX-ACCESS  read-write
      STATUS      current
      DESCRIPTION
              "Range for current-measuring analog I/O"
      ::= { ioAnalogCfgEntry 8 }
      
  ioAnalogCfgVoltageRange OBJECT-TYPE
      SYNTAX      INTEGER
      {
          voltsRangeMinus10To10(1),
          voltsRangeMinus5To5(2),
          voltsRangeMinus1To1(3),
          millivoltsRangeMinus500to500(4),
          millivoltsRangeMinus150to150(5)
      }
      MAX-ACCESS  read-write
      STATUS      current
      DESCRIPTION
              "Range for voltage-measuring analog I/O"
      ::= { ioAnalogCfgEntry 9 }

  ioAnalogCfgAlarmTrigger OBJECT-TYPE
      SYNTAX      INTEGER
      {
          disabled(1),
          low(2),
          high(3)
      }
      MAX-ACCESS  read-write
      STATUS      current
      DESCRIPTION
              "Analog I/O alarm trigger type"
      ::= { ioAnalogCfgEntry 10 }

  ioAnalogCfgAlarmClearMode OBJECT-TYPE
      SYNTAX      INTEGER 
      {
          auto(1),
          manual(2)
      }
      MAX-ACCESS  read-write
      STATUS      current
      DESCRIPTION
              "Analog I/O alarm clear mode"
      ::= { ioAnalogCfgEntry 11 }

  ioAnalogAlarmCfgTable OBJECT-TYPE
      SYNTAX      SEQUENCE OF IoAnalogAlarmCfgEntry
      MAX-ACCESS  not-accessible
      STATUS      current
      DESCRIPTION
              "ioAnalogAlarmCfgTable."
      ::= { ioAnalogCfg 2 }

  ioAnalogAlarmCfgEntry OBJECT-TYPE
      SYNTAX      IoAnalogAlarmCfgEntry
      MAX-ACCESS  not-accessible
      STATUS      current
      DESCRIPTION
              "An entry in the ioAnalogAlarmCfgTable"
      INDEX   { ioAnalogAlarmCfgChannelIndex, 
                ioAnalogAlarmCfgEntryIndex }
      ::= { ioAnalogAlarmCfgTable 1 }

  IoAnalogAlarmCfgEntry ::= 
      SEQUENCE 
      {
        ioAnalogAlarmCfgChannelIndex
          INTEGER,
        ioAnalogAlarmCfgEntryIndex
          INTEGER,
        ioAnalogCfgAlarmEnable
          OnOffValue,
        ioAnalogCfgAlarmTriggerLevel
          DisplayString,
        ioAnalogCfgAlarmClearLevel
          DisplayString,
        ioAnalogCfgAlarmEmail
          OnOffValue,
        ioAnalogCfgAlarmSyslog
          OnOffValue,
        ioAnalogCfgAlarmSNMP
          OnOffValue
      }

  ioAnalogAlarmCfgChannelIndex OBJECT-TYPE
      SYNTAX      INTEGER
      MAX-ACCESS  read-only
      STATUS      current
      DESCRIPTION
              "Channel Index"
      ::= { ioAnalogAlarmCfgEntry 1 }

  ioAnalogAlarmCfgEntryIndex OBJECT-TYPE
      SYNTAX      INTEGER
      MAX-ACCESS  read-only
      STATUS      current
      DESCRIPTION
              "Entry Index"
      ::= { ioAnalogAlarmCfgEntry 2 }

  ioAnalogCfgAlarmEnable OBJECT-TYPE
      SYNTAX      OnOffValue
      MAX-ACCESS  read-write
      STATUS      current
      DESCRIPTION
              "Enable/disable I/O analog alarm entry"
      ::= { ioAnalogAlarmCfgEntry 3 }
      
  ioAnalogCfgAlarmTriggerLevel OBJECT-TYPE
      SYNTAX      DisplayString
      MAX-ACCESS  read-write
      STATUS      current
      DESCRIPTION
              "Trigger level for I/O analog alarm (floating point value)"
      ::= { ioAnalogAlarmCfgEntry 4 }
      
  ioAnalogCfgAlarmClearLevel OBJECT-TYPE
      SYNTAX      DisplayString
      MAX-ACCESS  read-write
      STATUS      current
      DESCRIPTION
              "Clear level for non-latching I/O analog alarm (floating point 
               value)"
      ::= { ioAnalogAlarmCfgEntry 5 }
      
  ioAnalogCfgAlarmEmail OBJECT-TYPE
      SYNTAX      OnOffValue
      MAX-ACCESS  read-write
      STATUS      current
      DESCRIPTION
              "Enable/disable email notification on triggered analog alarm"
      ::= { ioAnalogAlarmCfgEntry 6 }
      
  ioAnalogCfgAlarmSyslog OBJECT-TYPE
      SYNTAX      OnOffValue
      MAX-ACCESS  read-write
      STATUS      current
      DESCRIPTION
              "Enable/disable syslog notification on triggered analog alarm"
      ::= { ioAnalogAlarmCfgEntry 7 }
      
  ioAnalogCfgAlarmSNMP OBJECT-TYPE
      SYNTAX      OnOffValue
      MAX-ACCESS  read-write
      STATUS      current
      DESCRIPTION
              "Enable/disable SNMP trap notification on triggered analog alarm"
      ::= { ioAnalogAlarmCfgEntry 8 }
      
  -- I/O Analog config ENDS

  -- I/O Digital config BEGINS
  ioDigitalCfgTable OBJECT-TYPE
      SYNTAX      SEQUENCE OF IoDigitalCfgEntry
      MAX-ACCESS  not-accessible
      STATUS      current
      DESCRIPTION
              "ioDigitalCfgTable."
      ::= { ioDigitalCfg 1 }

  ioDigitalCfgEntry OBJECT-TYPE
      SYNTAX      IoDigitalCfgEntry
      MAX-ACCESS  not-accessible
      STATUS      current
      DESCRIPTION
              "An entry in the ioDigitalCfgTable"
      INDEX   { ioDigitalCfgChannelIndex }
      ::= { ioDigitalCfgTable 1 }

  IoDigitalCfgEntry ::= 
      SEQUENCE 
      {
        ioDigitalCfgChannelIndex
          INTEGER,
        ioDigitalCfgStatus
          RowStatus,
        ioDigitalCfgResourceType
          INTEGER,
        ioDigitalCfgEnable
          OnOffValue,
        ioDigitalCfgDescription
          DisplayString,
        ioDigitalInputCfgLatch
          INTEGER,
        ioDigitalInputCfgInvertSignal
          OnOffValue,
        ioDigitalInputCfgAlarmTrigger
          INTEGER,
        ioDigitalInputCfgAlarmClear
          INTEGER,
        ioDigitalInputCfgAlarmEmail
          OnOffValue,
        ioDigitalInputCfgAlarmSyslog
          OnOffValue,
        ioDigitalInputCfgAlarmSNMP
          OnOffValue,
        ioDigitalOutputCfgType
          INTEGER,
        ioDigitalOutputCfgMode
          INTEGER,
        ioDigitalOutputCfgPulseMode
          INTEGER,
        ioDigitalOutputCfgPulseCount
          INTEGER,
        ioDigitalOutputCfgInactiveSignalWidth
          INTEGER,
        ioDigitalOutputCfgActiveSignalWidth
          INTEGER,
        ioDigitalOutputCfgDelay
          INTEGER,
        ioDigitalOutputCfgFailsafe
          INTEGER
      }

  ioDigitalCfgChannelIndex OBJECT-TYPE
      SYNTAX      INTEGER
      MAX-ACCESS  read-only
      STATUS      current
      DESCRIPTION
              "I/O resource index"
      ::= { ioDigitalCfgEntry 1 }

  ioDigitalCfgStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioDigitalCfgEntry 2 }

  ioDigitalCfgResourceType OBJECT-TYPE
      SYNTAX      INTEGER
      {
         input(2),   
         output(3)
      }
      MAX-ACCESS  read-write
      STATUS      current
      DESCRIPTION
              "Set your digital I/O resource type to Input or Output
               using this object.  Please note that the corresponding 
               hardware jumpers must be set accordingly."
      ::= { ioDigitalCfgEntry 3 }
      
  ioDigitalCfgEnable OBJECT-TYPE
      SYNTAX      OnOffValue
      MAX-ACCESS  read-write
      STATUS      current
      DESCRIPTION
              "Enable/disable this digital I/O channel"
      ::= { ioDigitalCfgEntry 4 }

  ioDigitalCfgDescription OBJECT-TYPE
      SYNTAX      DisplayString(SIZE(0..20))
      MAX-ACCESS  read-write
      STATUS      current
      DESCRIPTION
              "Description for this digital I/O "
      ::= { ioDigitalCfgEntry 5 }

  ioDigitalInputCfgLatch OBJECT-TYPE
      SYNTAX      INTEGER
      {
         disabled(1),
         inactiveToActive(2),
         activeToInactive(3)
      }
      MAX-ACCESS  read-write
      STATUS      current
      DESCRIPTION
              "Digital Input: Latch type"
      ::= { ioDigitalCfgEntry 6 }

  ioDigitalInputCfgInvertSignal OBJECT-TYPE
      SYNTAX      OnOffValue
      MAX-ACCESS  read-write
      STATUS      current
      DESCRIPTION
              "Digital Input: Enable/disable signal inversion"
      ::= { ioDigitalCfgEntry 7 }

  ioDigitalInputCfgAlarmTrigger OBJECT-TYPE
      SYNTAX      INTEGER
      {
        disabled(1),
        low(2),
        high(3)
      }
      MAX-ACCESS  read-write
      STATUS      current
      DESCRIPTION
              "Digital Input: Alarm trigger type"
      ::= { ioDigitalCfgEntry 8 }
      
  ioDigitalInputCfgAlarmClear OBJECT-TYPE
      SYNTAX      INTEGER
      {
        auto(1),
        manual(2)
      }
      MAX-ACCESS  read-write
      STATUS      current
      DESCRIPTION
              "Digital Input: Clear alarm - manual/automatic"
      ::= { ioDigitalCfgEntry 9 }
      
  ioDigitalInputCfgAlarmEmail OBJECT-TYPE
      SYNTAX      OnOffValue
      MAX-ACCESS  read-write
      STATUS      current
      DESCRIPTION
              "Digital Input: Enable/disable email alert on triggered alarm"
      ::= { ioDigitalCfgEntry 10 }
      
  ioDigitalInputCfgAlarmSyslog OBJECT-TYPE
      SYNTAX      OnOffValue
      MAX-ACCESS  read-write
      STATUS      current
      DESCRIPTION
              "Digital Input: Enable/disable syslog alert on triggered alarm"
      ::= { ioDigitalCfgEntry 11 }
      
  ioDigitalInputCfgAlarmSNMP OBJECT-TYPE
      SYNTAX      OnOffValue
      MAX-ACCESS  read-write
      STATUS      current
      DESCRIPTION
              "Digital Input: Enable/disable SNMP trap on triggered alarm"
      ::= { ioDigitalCfgEntry 12 }
      
      
  ioDigitalOutputCfgType OBJECT-TYPE
      SYNTAX      INTEGER
      {
         sink(1),
         source(2),
         sinkAndSource(3)
      }
      MAX-ACCESS  read-write
      STATUS      current
      DESCRIPTION
              "Digital Output: Output type"
      ::= { ioDigitalCfgEntry 13 }
      
  ioDigitalOutputCfgMode OBJECT-TYPE
      SYNTAX      INTEGER
      {
         manual(1),
         pulse(2),
         inactiveToActiveDelay(3),
         activeToInactiveDelay(4)
      }
      MAX-ACCESS  read-write
      STATUS      current
      DESCRIPTION
              "Digital Output: Output mode"
      ::= { ioDigitalCfgEntry 14 }

  ioDigitalOutputCfgPulseMode OBJECT-TYPE
      SYNTAX      INTEGER
      {
         continuous(1),
         counted(2)
      }
      MAX-ACCESS  read-write
      STATUS      current
      DESCRIPTION
              "Digital Output: Pulse mode (counted or continuous)"
      ::= { ioDigitalCfgEntry 15 }
      

  ioDigitalOutputCfgPulseCount OBJECT-TYPE
      SYNTAX      INTEGER(1..9999)
      MAX-ACCESS  read-write
      STATUS      current
      DESCRIPTION
              "Digital Output: Pulse count (only applies to counted pulse mode)"
      ::= { ioDigitalCfgEntry 16 }
      
  ioDigitalOutputCfgInactiveSignalWidth OBJECT-TYPE
      SYNTAX      INTEGER(1..9999)
      MAX-ACCESS  read-write
      STATUS      current
      DESCRIPTION
              "Digital Output: Inactive signal width, in 100 ms units (only applies 
               to pulse mode)"
      ::= { ioDigitalCfgEntry 17 }
      
  ioDigitalOutputCfgActiveSignalWidth OBJECT-TYPE
      SYNTAX      INTEGER(1..9999)
      MAX-ACCESS  read-write
      STATUS      current
      DESCRIPTION
              "Digital Output: Active signal width, in 100 ms units (only applies 
               to pulse mode)"
      ::= { ioDigitalCfgEntry 18 }
      
  ioDigitalOutputCfgDelay OBJECT-TYPE
      SYNTAX      INTEGER(1..9999)
      MAX-ACCESS  read-write
      STATUS      current
      DESCRIPTION
              "Digital Output: Delay time, in 100 ms units (only applies to 
               delay mode)"
      ::= { ioDigitalCfgEntry 19 }
      
  ioDigitalOutputCfgFailsafe OBJECT-TYPE
      SYNTAX      INTEGER
      {
          none(1),
          activateOutput(2),
          deactivateOutput(3)
      }
      MAX-ACCESS  read-write
      STATUS      current
      DESCRIPTION
              "Digital Output: Failsafe action - choose the action that 
               will take place when the failsafe timer expires"
      ::= { ioDigitalCfgEntry 20 }
      
-- I/O Digital Cfg ENDS

  -- I/O Relay config BEGINS
  ioRelayCfgTable OBJECT-TYPE
      SYNTAX      SEQUENCE OF IoRelayCfgEntry
      MAX-ACCESS  not-accessible
      STATUS      current
      DESCRIPTION
              "ioRelayCfgTable."
      ::= { ioRelayCfg 1 }

  ioRelayCfgEntry OBJECT-TYPE
      SYNTAX      IoRelayCfgEntry
      MAX-ACCESS  not-accessible
      STATUS      current
      DESCRIPTION
              "An entry in the ioRelayCfgTable"
      INDEX   { ioRelayCfgChannelIndex }
      ::= { ioRelayCfgTable 1 }

  IoRelayCfgEntry ::= 
      SEQUENCE 
      {
        ioRelayCfgChannelIndex
          INTEGER,
        ioRelayCfgStatus
          RowStatus,
        ioRelayCfgEnable
          OnOffValue,
        ioRelayCfgDescription
          DisplayString,
        ioRelayCfgMode
          INTEGER,
        ioRelayCfgPulseMode
          INTEGER,
        ioRelayCfgPulseCount
          INTEGER,
        ioRelayCfgInactiveSignalWidth
          INTEGER,
        ioRelayCfgActiveSignalWidth
          INTEGER,
        ioRelayCfgDelay
          INTEGER,
        ioRelayCfgFailsafe
          INTEGER
      }

  ioRelayCfgChannelIndex OBJECT-TYPE
      SYNTAX      INTEGER
      MAX-ACCESS  read-only
      STATUS      current
      DESCRIPTION
              "Index"
      ::= { ioRelayCfgEntry 1 }

  ioRelayCfgStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioRelayCfgEntry 2 }

  ioRelayCfgEnable OBJECT-TYPE
      SYNTAX      OnOffValue
      MAX-ACCESS  read-write
      STATUS      current
      DESCRIPTION
              "Enable/disable this Relay I/O channel"
      ::= { ioRelayCfgEntry 3 }

  ioRelayCfgDescription OBJECT-TYPE
      SYNTAX      DisplayString(SIZE(0..20))
      MAX-ACCESS  read-write
      STATUS      current
      DESCRIPTION
              "Description for this relay"
      ::= { ioRelayCfgEntry 4 }

  ioRelayCfgMode OBJECT-TYPE
      SYNTAX      INTEGER
      {
         manual(1),
         pulse(2),
         inactiveToActiveDelay(3),
         activeToInactiveDelay(4)
      }
      MAX-ACCESS  read-write
      STATUS      current
      DESCRIPTION
              "Relay output mode"
      ::= { ioRelayCfgEntry 5 }

  ioRelayCfgPulseMode OBJECT-TYPE
      SYNTAX      INTEGER
      {
         continuous(1),
         counted(2)
      }
      MAX-ACCESS  read-write
      STATUS      current
      DESCRIPTION
              "Relay pulse mode (only applies when output mode is set to 'pulse'"
      ::= { ioRelayCfgEntry 6 }
      

  ioRelayCfgPulseCount OBJECT-TYPE
      SYNTAX      INTEGER(1..9999)
      MAX-ACCESS  read-write
      STATUS      current
      DESCRIPTION
              "Relay pulse count; only applies for counted pulse mode"
      ::= { ioRelayCfgEntry 7 }
      
  ioRelayCfgInactiveSignalWidth OBJECT-TYPE
      SYNTAX      INTEGER(1..9999)
      MAX-ACCESS  read-write
      STATUS      current
      DESCRIPTION
              "Relay inactive signal width in 100 ms units; only applies to pulse mode"
      ::= { ioRelayCfgEntry 8 }
      
  ioRelayCfgActiveSignalWidth OBJECT-TYPE
      SYNTAX      INTEGER(1..9999)
      MAX-ACCESS  read-write
      STATUS      current
      DESCRIPTION
              "Relay active signal width in 100 ms units; only applies to pulse mode"
      ::= { ioRelayCfgEntry 9 }
      
  ioRelayCfgDelay OBJECT-TYPE
      SYNTAX      INTEGER(1..9999)
      MAX-ACCESS  read-write
      STATUS      current
      DESCRIPTION
              "Relay pulse delay, in 100 ms units; only applies to delay mode"
      ::= { ioRelayCfgEntry 10 }
      
  ioRelayCfgFailsafe OBJECT-TYPE
      SYNTAX      INTEGER
      {
          none(1),
          activateOutput(2),
          deactivateOutput(3)
      }
      MAX-ACCESS  read-write
      STATUS      current
      DESCRIPTION
              "Action to take when the failsafe timer expires"
      ::= { ioRelayCfgEntry 11 }
      
-- I/O Relay Cfg ENDS      

  -- I/O LineSignal config BEGINS
  ioLineSignalCfgTable OBJECT-TYPE
      SYNTAX      SEQUENCE OF IoLineSignalCfgEntry
      MAX-ACCESS  not-accessible
      STATUS      current
      DESCRIPTION
              "ioLineSignalCfgTable."
      ::= { ioLineSignalCfg 1 }

  ioLineSignalCfgEntry OBJECT-TYPE
      SYNTAX      IoLineSignalCfgEntry
      MAX-ACCESS  not-accessible
      STATUS      current
      DESCRIPTION
              "An entry in the ioLineSignalCfgTable"
      INDEX   { ioLineSignalCfgPortIndex,
                ioLineSignalCfgSignalIndex}
      ::= { ioLineSignalCfgTable 1 }

  IoLineSignalCfgEntry ::= 
      SEQUENCE 
      {
        ioLineSignalCfgPortIndex
          INTEGER,
        ioLineSignalCfgSignalIndex
          INTEGER,
        ioLineSignalCfgStatus
          RowStatus,
        ioLineSignalCfgResourceType
          INTEGER,
        ioLineSignalCfgEnable
          OnOffValue,
        ioLineSignalCfgDescription
          DisplayString,
        ioLineSignalInputCfgLatch
          INTEGER,
        ioLineSignalInputCfgInvertSignal
          OnOffValue,
        ioLineSignalInputCfgAlarmTrigger
          INTEGER,
        ioLineSignalInputCfgAlarmClear
          INTEGER,
        ioLineSignalInputCfgAlarmEmail
          OnOffValue,
        ioLineSignalInputCfgAlarmSyslog
          OnOffValue,
        ioLineSignalInputCfgAlarmSNMP
          OnOffValue,
        ioLineSignalOutputCfgFailsafe
          INTEGER
      }

  ioLineSignalCfgPortIndex OBJECT-TYPE
      SYNTAX      INTEGER
      MAX-ACCESS  read-only
      STATUS      current
      DESCRIPTION
              "Index of the associated serial port"
      ::= { ioLineSignalCfgEntry 1 }

  ioLineSignalCfgSignalIndex OBJECT-TYPE
      SYNTAX      INTEGER {
          dsr(1),
          dcd(2),
          cts(3),
          dtr(4),
          rts(5)
      }
          
      MAX-ACCESS  read-only
      STATUS      current
      DESCRIPTION
              "Index of the associate line signal"
      ::= { ioLineSignalCfgEntry 2 }
      
  ioLineSignalCfgStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioLineSignalCfgEntry 3 }

  ioLineSignalCfgResourceType OBJECT-TYPE
      SYNTAX      INTEGER
      {
         input(2),   
         output(3)
      }
      MAX-ACCESS  read-only
      STATUS      current
      DESCRIPTION
              "Signifies whether this resource is input or output"
      ::= { ioLineSignalCfgEntry 4 }
      
  ioLineSignalCfgEnable OBJECT-TYPE
      SYNTAX      OnOffValue
      MAX-ACCESS  read-write
      STATUS      current
      DESCRIPTION
              "Enable/disable this resource"
      ::= { ioLineSignalCfgEntry 5 }

  ioLineSignalCfgDescription OBJECT-TYPE
      SYNTAX      DisplayString(SIZE(0..20))
      MAX-ACCESS  read-write
      STATUS      current
      DESCRIPTION
              "Description for this resource"
      ::= { ioLineSignalCfgEntry 6 }

  ioLineSignalInputCfgLatch OBJECT-TYPE
      SYNTAX      INTEGER
      {
         disabled(1),
         inactiveToActive(2),
         activeToInactive(3)
      }
      MAX-ACCESS  read-write
      STATUS      current
      DESCRIPTION
              "Line Signal (input): Latch mode"
      ::= { ioLineSignalCfgEntry 7 }

  ioLineSignalInputCfgInvertSignal OBJECT-TYPE
      SYNTAX      OnOffValue
      MAX-ACCESS  read-write
      STATUS      current
      DESCRIPTION
              "Line Signal (input): Enable/disable signal inversion"
      ::= { ioLineSignalCfgEntry 8 }

  ioLineSignalInputCfgAlarmTrigger OBJECT-TYPE
      SYNTAX      INTEGER
      {
        disabled(1),
        low(2),
        high(3)
      }
      MAX-ACCESS  read-write
      STATUS      current
      DESCRIPTION
              "Line Signal (input): Alarm trigger type"
      ::= { ioLineSignalCfgEntry 9 }
      
  ioLineSignalInputCfgAlarmClear OBJECT-TYPE
      SYNTAX      INTEGER
      {
        auto(1),
        manual(2)
      }
      MAX-ACCESS  read-write
      STATUS      current
      DESCRIPTION
              "Line Signal (input): Alarm clear type"
      ::= { ioLineSignalCfgEntry 10 }
      
  ioLineSignalInputCfgAlarmEmail OBJECT-TYPE
      SYNTAX      OnOffValue
      MAX-ACCESS  read-write
      STATUS      current
      DESCRIPTION
              "Line Signal (input): Enable/disable email alert on alarm trigger"
      ::= { ioLineSignalCfgEntry 11 }
      
  ioLineSignalInputCfgAlarmSyslog OBJECT-TYPE
      SYNTAX      OnOffValue
      MAX-ACCESS  read-write
      STATUS      current
      DESCRIPTION
              "Line Signal (input): Enable/disable syslog alert on alarm trigger"
      ::= { ioLineSignalCfgEntry 12 }
      
  ioLineSignalInputCfgAlarmSNMP OBJECT-TYPE
      SYNTAX      OnOffValue
      MAX-ACCESS  read-write
      STATUS      current
      DESCRIPTION
              "Line Signal (input): Enable/disable SNMP alert on alarm trigger"
      ::= { ioLineSignalCfgEntry 13 }
      

  ioLineSignalOutputCfgFailsafe OBJECT-TYPE
      SYNTAX      INTEGER
      {
          none(1),
          activateOutput(2),
          deactivateOutput(3)
      }
      MAX-ACCESS  read-write
      STATUS      current
      DESCRIPTION
              "Line Signal (output): Action to take when failsafe timer expires"
      ::= { ioLineSignalCfgEntry 14 }
      
-- I/O LineSignal Cfg ENDS

  ioChannelFunction OBJECT-TYPE
      SYNTAX      INTEGER {
        none(1),
        killall(2)
      }
      MAX-ACCESS  read-write
      STATUS      current
      DESCRIPTION
              "killall - Apply configuration changes to all channels"
      ::= { ioChannelStatus 1 } 


 ioAnalogStatus       OBJECT IDENTIFIER ::= { ioChannelStatus 2 }
 ioDigitalStatus      OBJECT IDENTIFIER ::= { ioChannelStatus 3 }
 ioRelayStatus        OBJECT IDENTIFIER ::= { ioChannelStatus 4 }
 ioLineSignalStatus   OBJECT IDENTIFIER ::= { ioChannelStatus 5 }
      
      -- I/O Analog status BEGINS
  ioAnalogStatusTable OBJECT-TYPE
      SYNTAX      SEQUENCE OF IoAnalogStatusEntry
      MAX-ACCESS  not-accessible
      STATUS      current
      DESCRIPTION
              "ioAnalogStatusTable."
      ::= { ioAnalogStatus 1 }

  ioAnalogStatusEntry OBJECT-TYPE
      SYNTAX      IoAnalogStatusEntry
      MAX-ACCESS  not-accessible
      STATUS      current
      DESCRIPTION
              "An entry in the ioAnalogStatusTable"
      INDEX   { ioAnalogStatusChannelIndex }
      ::= { ioAnalogStatusTable 1 }

  IoAnalogStatusEntry ::= 
      SEQUENCE 
      {
        ioAnalogStatusChannelIndex
          INTEGER,
        ioAnalogStatusEnabled
          OnOffValue,
        ioAnalogStatusDescription
          DisplayString,
        ioAnalogFunction
          INTEGER,
        ioAnalogStatusInputState
          INTEGER,
        ioAnalogStatusValue
          DisplayString,
        ioAnalogStatusMinimum
          DisplayString,
        ioAnalogStatusMaximum
          DisplayString,
        ioAnalogStatusAlarmLevel
          INTEGER
      }

  ioAnalogStatusChannelIndex OBJECT-TYPE
      SYNTAX      INTEGER
      MAX-ACCESS  read-only
      STATUS      current
      DESCRIPTION
              "Index"
      ::= { ioAnalogStatusEntry 1 }

  ioAnalogStatusEnabled OBJECT-TYPE
      SYNTAX      OnOffValue
      MAX-ACCESS  read-only
      STATUS      current
      DESCRIPTION
              "Enabled"
      ::= { ioAnalogStatusEntry 2 }
      
  ioAnalogStatusDescription OBJECT-TYPE
      SYNTAX      DisplayString(SIZE(0..20))
      MAX-ACCESS  read-only
      STATUS      current
      DESCRIPTION
              "Description"
      ::= { ioAnalogStatusEntry 3 }
      
  ioAnalogFunction OBJECT-TYPE
      SYNTAX      INTEGER {
        none(1),
        kill(2),
        clearAlarm(6),
        clearMin(7),
        clearMax(8)
      }
      MAX-ACCESS  read-write
      STATUS      current
      DESCRIPTION
              "kill - Apply configuration changes to this entry"
      ::= { ioAnalogStatusEntry 4 }

  ioAnalogStatusInputState OBJECT-TYPE
    SYNTAX      INTEGER {
        normal(1),
        open(2),
        short(3)
      }
      MAX-ACCESS  read-only
      STATUS      current
      DESCRIPTION
              "Input state."
      ::= { ioAnalogStatusEntry 5 }     
      
  ioAnalogStatusValue OBJECT-TYPE
      SYNTAX      DisplayString
      MAX-ACCESS  read-only
      STATUS      current
      DESCRIPTION
              "Current analog input value."
      ::= { ioAnalogStatusEntry 6 }

  ioAnalogStatusMinimum OBJECT-TYPE
      SYNTAX      DisplayString
      MAX-ACCESS  read-only
      STATUS      current
      DESCRIPTION
              "Minimum analog input value."
      ::= { ioAnalogStatusEntry 7 }
      
  ioAnalogStatusMaximum OBJECT-TYPE
      SYNTAX      DisplayString
      MAX-ACCESS  read-only
      STATUS      current
      DESCRIPTION
              "Maximum analog input value."
      ::= { ioAnalogStatusEntry 8 }

  ioAnalogStatusAlarmLevel OBJECT-TYPE
      SYNTAX      INTEGER(0..5)
      MAX-ACCESS  read-only
      STATUS      current
      DESCRIPTION
              "Alarm level."
      ::= { ioAnalogStatusEntry 9 }
      
  -- I/O Analog status ENDS 
  
  -- I/O Digital status BEGINS
  ioDigitalStatusTable OBJECT-TYPE
      SYNTAX      SEQUENCE OF IoDigitalStatusEntry
      MAX-ACCESS  not-accessible
      STATUS      current
      DESCRIPTION
              "ioDigitalStatusTable."
      ::= { ioDigitalStatus 1 }

  ioDigitalStatusEntry OBJECT-TYPE
      SYNTAX      IoDigitalStatusEntry
      MAX-ACCESS  not-accessible
      STATUS      current
      DESCRIPTION
              "An entry in the ioDigitalStatusTable"
      INDEX   { ioDigitalStatusChannelIndex }
      ::= { ioDigitalStatusTable 1 }

  IoDigitalStatusEntry ::= 
      SEQUENCE 
      {
        ioDigitalStatusChannelIndex
          INTEGER,
        ioDigitalStatusEnabled
          OnOffValue,
        ioDigitalStatusDescription
          DisplayString,
        ioDigitalStatusType
          INTEGER,
        ioDigitalFunction
          INTEGER,
        ioDigitalStatusState
          INTEGER,
        ioDigitalStatusLatchedInputState
          INTEGER,
        ioDigitalStatusInputAlarm
          INTEGER
      }

  ioDigitalStatusChannelIndex OBJECT-TYPE
      SYNTAX      INTEGER
      MAX-ACCESS  read-only
      STATUS      current
      DESCRIPTION
              "Index"
      ::= { ioDigitalStatusEntry 1 }

  ioDigitalStatusEnabled OBJECT-TYPE
      SYNTAX      OnOffValue
      MAX-ACCESS  read-only
      STATUS      current
      DESCRIPTION
              "Enabled"
      ::= { ioDigitalStatusEntry 2 }
      
  ioDigitalStatusDescription OBJECT-TYPE
      SYNTAX      DisplayString(SIZE(0..20))
      MAX-ACCESS  read-only
      STATUS      current
      DESCRIPTION
              "Description"
      ::= { ioDigitalStatusEntry 3 }
      
      

  ioDigitalStatusType OBJECT-TYPE
      SYNTAX      INTEGER {
        unknown(1),
        input(2),
        output(3)
      }
      MAX-ACCESS  read-only
      STATUS      current
      DESCRIPTION
              "Resource type"
      ::= { ioDigitalStatusEntry 4 }
      
  ioDigitalFunction OBJECT-TYPE
      SYNTAX      INTEGER {
        none(1),
        kill(2),
        activateOutput(3),
        deactivateOutput(4),
        clearInputLatch(5),
        clearAlarmLatch(6)        
      }
      MAX-ACCESS  read-write
      STATUS      current
      DESCRIPTION
              "kill - Apply configuration changes to this entry"
      ::= { ioDigitalStatusEntry 5 }
  ioDigitalStatusState OBJECT-TYPE
      SYNTAX      INTEGER {
        inactive(1),
        active(2)
      }
      MAX-ACCESS  read-write
      STATUS      current
      DESCRIPTION
              "Digital State.  ."
      ::= { ioDigitalStatusEntry 6 }
  ioDigitalStatusLatchedInputState OBJECT-TYPE
      SYNTAX      INTEGER {
        none(1),
        inactiveToActive(2),
        activeToInactive(3)
      }
      MAX-ACCESS  read-only
      STATUS      current
      DESCRIPTION
              "For digital inputs only."
      ::= { ioDigitalStatusEntry 7 }

  ioDigitalStatusInputAlarm OBJECT-TYPE
      SYNTAX      INTEGER {
        notTriggered(1),
        triggered(2)
      }
      MAX-ACCESS  read-only
      STATUS      current
      DESCRIPTION
              "LineSignal State.  ."
      ::= { ioDigitalStatusEntry 8 }      
      
   -- I/O Digital status ENDS 
      
  -- I/O Relay status BEGINS
  ioRelayStatusTable OBJECT-TYPE
      SYNTAX      SEQUENCE OF IoRelayStatusEntry
      MAX-ACCESS  not-accessible
      STATUS      current
      DESCRIPTION
              "ioRelayStatusTable."
      ::= { ioRelayStatus 1 }

  ioRelayStatusEntry OBJECT-TYPE
      SYNTAX      IoRelayStatusEntry
      MAX-ACCESS  not-accessible
      STATUS      current
      DESCRIPTION
              "An entry in the ioRelayStatusTable"
      INDEX   { ioRelayStatusChannelIndex }
      ::= { ioRelayStatusTable 1 }

  IoRelayStatusEntry ::= 
      SEQUENCE 
      {
        ioRelayStatusChannelIndex
          INTEGER,
        ioRelayStatusEnabled
          OnOffValue,
        ioRelayStatusDescription
          DisplayString,
        ioRelayFunction
          INTEGER,
        ioRelayStatusState
          INTEGER
      }

  ioRelayStatusChannelIndex OBJECT-TYPE
      SYNTAX      INTEGER
      MAX-ACCESS  read-only
      STATUS      current
      DESCRIPTION
              "Index"
      ::= { ioRelayStatusEntry 1 }

  ioRelayStatusEnabled OBJECT-TYPE
      SYNTAX      OnOffValue
      MAX-ACCESS  read-only
      STATUS      current
      DESCRIPTION
              "Enabled"
      ::= { ioRelayStatusEntry 2 }
      
  ioRelayStatusDescription OBJECT-TYPE
      SYNTAX      DisplayString(SIZE(0..20))
      MAX-ACCESS  read-only
      STATUS      current
      DESCRIPTION
              "Description"
      ::= { ioRelayStatusEntry 3 }
      
  ioRelayFunction OBJECT-TYPE
      SYNTAX      INTEGER {
        none(1),
        kill(2),
        activateOutput(3),
        deactivateOutput(4)
      }
      MAX-ACCESS  read-write
      STATUS      current
      DESCRIPTION
              "kill - Apply configuration changes to this entry"
      ::= { ioRelayStatusEntry 4 }

  ioRelayStatusState OBJECT-TYPE
      SYNTAX      INTEGER {
        inactive(1),
        active(2)
      }
      MAX-ACCESS  read-write
      STATUS      current
      DESCRIPTION
              "Relay State.  ."
      ::= { ioRelayStatusEntry 5 }
   -- I/O Relay status ENDS 

   
  -- I/O LineSignal status BEGINS
  ioLineSignalStatusTable OBJECT-TYPE
      SYNTAX      SEQUENCE OF IoLineSignalStatusEntry
      MAX-ACCESS  not-accessible
      STATUS      current
      DESCRIPTION
              "ioLineSignalStatusTable."
      ::= { ioLineSignalStatus 1 }

  ioLineSignalStatusEntry OBJECT-TYPE
      SYNTAX      IoLineSignalStatusEntry
      MAX-ACCESS  not-accessible
      STATUS      current
      DESCRIPTION
              "An entry in the ioLineSignalStatusTable"
      INDEX   { ioLineSignalStatusPortIndex, ioLineSignalStatusSignalIndex  }
      ::= { ioLineSignalStatusTable 1 }

  IoLineSignalStatusEntry ::= 
      SEQUENCE 
      {
        ioLineSignalStatusPortIndex
          INTEGER,
        ioLineSignalStatusSignalIndex
          INTEGER,
        ioLineSignalStatusEnabled
          OnOffValue,
        ioLineSignalStatusDescription
          DisplayString,
        ioLineSignalStatusType
          INTEGER,
        ioLineSignalFunction
          INTEGER,
        ioLineSignalStatusState
          INTEGER,
        ioLineSignalStatusLatchedInputState
          INTEGER,
        ioLineSignalStatusInputAlarm
          INTEGER

      }

  ioLineSignalStatusPortIndex OBJECT-TYPE
      SYNTAX      INTEGER
      MAX-ACCESS  read-only
      STATUS      current
      DESCRIPTION
              "Index"
      ::= { ioLineSignalStatusEntry 1 }


  ioLineSignalStatusSignalIndex OBJECT-TYPE
      SYNTAX      INTEGER {
          dsr(1),
          dcd(2),
          cts(3),
          dtr(4),
          rts(5)
      }
          
      MAX-ACCESS  read-only
      STATUS      current
      DESCRIPTION
              "Index"
      ::= { ioLineSignalStatusEntry 2 }
      
  ioLineSignalStatusEnabled OBJECT-TYPE
      SYNTAX      OnOffValue
      MAX-ACCESS  read-only
      STATUS      current
      DESCRIPTION
              "Enabled"
      ::= { ioLineSignalStatusEntry 3 }
      
  ioLineSignalStatusDescription OBJECT-TYPE
      SYNTAX      DisplayString(SIZE(0..20))
      MAX-ACCESS  read-only
      STATUS      current
      DESCRIPTION
              "Description"
      ::= { ioLineSignalStatusEntry 4 }
      
  ioLineSignalStatusType OBJECT-TYPE
      SYNTAX      INTEGER {
        unknown(1),
        input(2),
        output(3)
      }
      MAX-ACCESS  read-only
      STATUS      current
      DESCRIPTION
              "resource type"
      ::= { ioLineSignalStatusEntry 5 }
      
  ioLineSignalFunction OBJECT-TYPE
      SYNTAX      INTEGER {
        none(1),
        kill(2),
        activateOutput(3),
        deactivateOutput(4),
        clearInputLatch(5),
        clearAlarmLatch(6)
      }
      MAX-ACCESS  read-write
      STATUS      current
      DESCRIPTION
              "kill - Apply configuration changes to this entry"
      ::= { ioLineSignalStatusEntry 6 }
  ioLineSignalStatusState OBJECT-TYPE
      SYNTAX      INTEGER {
        inactive(1),
        active(2)
      }
      MAX-ACCESS  read-write
      STATUS      current
      DESCRIPTION
              "LineSignal State.  ."
      ::= { ioLineSignalStatusEntry 7 }
  ioLineSignalStatusLatchedInputState OBJECT-TYPE
      SYNTAX      INTEGER {
        none(1),
        inactiveToActive(2),
        activeToInactive(3)
      }
      MAX-ACCESS  read-only
      STATUS      current
      DESCRIPTION
              "LineSignal State.  ."
      ::= { ioLineSignalStatusEntry 8 }      
  ioLineSignalStatusInputAlarm OBJECT-TYPE
      SYNTAX      INTEGER {
        notTriggered(1),
        triggered(2)
      }
      MAX-ACCESS  read-only
      STATUS      current
      DESCRIPTION
              "LineSignal State.  ."
      ::= { ioLineSignalStatusEntry 9 }      
   -- I/O Line Signal status ENDS 
   
-- I/O Group ENDS


--  ClusteringInfo group. A table of entries, each entry per port.

  clusteringTable OBJECT-TYPE
      SYNTAX      SEQUENCE OF ClusteringEntry
      MAX-ACCESS  not-accessible
      STATUS      current
      DESCRIPTION
              "The Clustering table."
      ::= { clusteringInfo 1 }

  clusteringEntry OBJECT-TYPE
      SYNTAX      ClusteringEntry
      MAX-ACCESS  not-accessible
      STATUS      current
      DESCRIPTION
              "An entry in the clusteringEntry, each relating to a port."
      INDEX   { clusteringIndex }
      ::= { clusteringTable 1 }

  ClusteringEntry ::=
      SEQUENCE {
        clusteringIndex
              INTEGER,
        clusteringServerName
          DisplayString,
        clusteringSlaveIP
            Ipv4v6Address,
        clusteringPort
            INTEGER,
        clusteringPortName
          DisplayString,
        clusteringSlavePort
            INTEGER,
        clusteringMasterPort
            INTEGER,
        clusteringProtocol
            INTEGER,
        clusteringStatus
            RowStatus
            }

  clusteringIndex OBJECT-TYPE
      SYNTAX      INTEGER
      MAX-ACCESS  not-accessible
      STATUS      current
      DESCRIPTION
              "The table entry number."
      ::= { clusteringEntry 1 }

   clusteringStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { clusteringEntry 2}

   clusteringServerName OBJECT-TYPE
      SYNTAX      DisplayString(SIZE(1..15))
      MAX-ACCESS  read-write
      STATUS      current
      DESCRIPTION
              "The slave server's name."
      ::= { clusteringEntry 3 }
      
   clusteringSlaveIP OBJECT-TYPE
      SYNTAX      IpAddress
      MAX-ACCESS  read-write
      STATUS      current
      DESCRIPTION
              "The remote slave server's IP address."
      ::= { clusteringEntry 4}
            
   clusteringPort OBJECT-TYPE
      SYNTAX      INTEGER (1..48)
      MAX-ACCESS  read-write
      STATUS      current
      DESCRIPTION
              "The port number on the clustered slave server."
      ::= { clusteringEntry 5}

  clusteringPortName OBJECT-TYPE
      SYNTAX      DisplayString(SIZE(1..54))
      MAX-ACCESS  read-write
      STATUS      current
      DESCRIPTION
              "The slave server's port name."
      ::= { clusteringEntry 6 }
      
   clusteringSlavePort OBJECT-TYPE
      SYNTAX      INTEGER(1..65535)
      MAX-ACCESS  read-write
      STATUS      current
      DESCRIPTION
              "The starting TCP port on the slave server."
      ::= { clusteringEntry 7}

   clusteringMasterPort OBJECT-TYPE
      SYNTAX      INTEGER(1..65535)
      MAX-ACCESS  read-write
      STATUS      current
      DESCRIPTION
              "The starting TCP port on the master server."
      ::= { clusteringEntry 8}

   clusteringProtocol OBJECT-TYPE
      SYNTAX      INTEGER {
        Telnet(1),
        SSH(2),
        Not Used (3)
      }
      MAX-ACCESS  read-write
      STATUS      current
      DESCRIPTION
              "The protocol used to connect between the slave and server."
      ::= { clusteringEntry 9}
      
-- Dynamic DSN Info
   dynamicDNSStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {dynamicDNSInfo 1}
      
  dynamicDNSEnabled OBJECT-TYPE
      SYNTAX      OnOffValue
      MAX-ACCESS  read-write
      STATUS      current
      DESCRIPTION
              "Enable/disable dynamic DNS."
      ::= { dynamicDNSInfo 2}

  dynamicDNSHostname OBJECT-TYPE
      SYNTAX      DisplayString(SIZE(1..14))
      MAX-ACCESS  read-write
      STATUS      current
      DESCRIPTION
              "Host name."
      ::= { dynamicDNSInfo 3}
      
  dynamicDNSUserName OBJECT-TYPE
      SYNTAX      DisplayString(SIZE(1..16))
      MAX-ACCESS  read-write
      STATUS      current
      DESCRIPTION
              "user name."
      ::= { dynamicDNSInfo 4}
      
  dynamicDNSPassword OBJECT-TYPE
      SYNTAX      DisplayString(SIZE(1..16))
      MAX-ACCESS  read-write
      STATUS      current
      DESCRIPTION
              "Password."
      ::= { dynamicDNSInfo 5}
      
  dynamicDNSSystemType OBJECT-TYPE
      SYNTAX      INTEGER {
        dynamic(1),
        static(2),
        custom(3)
      }
      MAX-ACCESS  read-write
      STATUS      current
      DESCRIPTION
              "System type."
      ::= { dynamicDNSInfo 6}
      
  dynamicDNSWildcard OBJECT-TYPE
      SYNTAX      INTEGER {
        enable(1),
        disable(2),
        nochange(3)
      }
      MAX-ACCESS  read-write
      STATUS      current
      DESCRIPTION
              "wildcard."
      ::= { dynamicDNSInfo 7}
      
  dynamicDNSConnectionMethod OBJECT-TYPE
      SYNTAX      INTEGER {
        http(1),
        httpport8245(2),
        https(3)
      }
      MAX-ACCESS  read-write
      STATUS      current
      DESCRIPTION
              "connection method."
      ::= { dynamicDNSInfo 8}
      
  dynamicDNSSSLVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {dynamicDNSInfo 9}

  dynamicDNSSSLCountry    OBJECT-TYPE
      SYNTAX      DisplayString(SIZE(0..2))
      MAX-ACCESS    read-write
      STATUS        current
      DESCRIPTION
                "A two character country code; for example, US."
      ::= {dynamicDNSInfo 10}

  dynamicDNSSSLStateProv    OBJECT-TYPE
      SYNTAX      DisplayString(SIZE(0..128))
      MAX-ACCESS    read-write
      STATUS        current
      DESCRIPTION
                "Up to a 128 character entry for the state/province;
                 for example, IL."
      ::= {dynamicDNSInfo 11}

  dynamicDNSSSLLocality    OBJECT-TYPE
      SYNTAX      DisplayString(SIZE(0..128))
      MAX-ACCESS    read-write
      STATUS        current
      DESCRIPTION
                "Up to a 128 character entry for the location; 
                 for example, a city."
      ::= {dynamicDNSInfo 12}

  dynamicDNSSSLOrganisation    OBJECT-TYPE
      SYNTAX      DisplayString(SIZE(0..64))
      MAX-ACCESS    read-write
      STATUS        current
      DESCRIPTION
                "Up to a 64 character entry for the organisation; 
                 for example, Accounting."
      ::= {dynamicDNSInfo 13}

  dynamicDNSSSLOrganisationUnit    OBJECT-TYPE
      SYNTAX      DisplayString(SIZE(0..64))
      MAX-ACCESS    read-write
      STATUS        current
      DESCRIPTION
                "Up to a 64 character entry for the unit in the 
                 organisation; for example, Payroll."
      ::= {dynamicDNSInfo 14}

  dynamicDNSSSLCommonName    OBJECT-TYPE
      SYNTAX      DisplayString(SIZE(0..64))
      MAX-ACCESS    read-write
      STATUS        current
      DESCRIPTION
                "Up to a 64 character entry for common name; for example,
                 the host name or fully qualified domain name."
      ::= {dynamicDNSInfo 15}

  dynamicDNSSSLEmail    OBJECT-TYPE
      SYNTAX      DisplayString(SIZE(0..128))
      MAX-ACCESS    read-write
      STATUS        current
      DESCRIPTION
                "Up to a 64 character entry for an email address; 
                 for example, acct@anycompany.com."
      ::= {dynamicDNSInfo 16}

      dynamicDNSStatusString OBJECT-TYPE
      SYNTAX      DisplayString(SIZE(0..1024))
      MAX-ACCESS  read-only
      STATUS      current
      DESCRIPTION
              "Dynamic DNS statistics"
      ::= {dynamicDNSInfo 17}
-- Dynamic DND SSL Cipher Table

  dynamicDNSSSLCipherTable OBJECT-TYPE
      SYNTAX      SEQUENCE OF dynamicDNSSSLCipherEntry
      MAX-ACCESS  not-accessible
      STATUS      current
      DESCRIPTION
              "SSL CIpher."
      ::= {dynamicDNSInfo 18}

  dynamicDNSSSLCipherEntry OBJECT-TYPE
      SYNTAX      DynamicDNSSSLCipherEntry
      MAX-ACCESS  not-accessible
      STATUS      current
      DESCRIPTION
              "An entry in the dynamicDNSSSLCipherTable, each relating to a cipher entry."
      INDEX   { dynamicDNSSSLCipherPriority }
      ::= { dynamicDNSSSLCipherTable 1 }

  DynamicDNSSSLCipherEntry ::=
      SEQUENCE {
  dynamicDNSSSLCipherPriority
       INTEGER,
  dynamicDNSSSLCipherStatus
        RowStatus,
  dynamicDNSSSLCipherEncryption
        INTEGER,
  dynamicDNSSSLCipherKeySizeMin
        INTEGER,
  dynamicDNSSSLCipherKeySizeMax
        INTEGER,
  dynamicDNSSSLCipherKeyExchange
        INTEGER,
  dynamicDNSSSLCipherHMAC
        INTEGER
      }

  dynamicDNSSSLCipherPriority OBJECT-TYPE
      SYNTAX      INTEGER
      MAX-ACCESS  not-accessible
      STATUS      current
      DESCRIPTION
              "The cipher number from highest priority(1) to lowest priority"
      ::= { dynamicDNSSSLCipherEntry 1 }

  dynamicDNSSSLCipherStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { dynamicDNSSSLCipherEntry 2 }

  dynamicDNSSSLCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { dynamicDNSSSLCipherEntry 3 }

  dynamicDNSSSLCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { dynamicDNSSSLCipherEntry 4 }

  dynamicDNSSSLCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { dynamicDNSSSLCipherEntry 5 }

  dynamicDNSSSLCipherKeyExchange OBJECT-TYPE
      SYNTAX      INTEGER {
        any(1),
        rsa(2),
        edhrsa(3),
        edhdss(4),
        adh(5) 
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { dynamicDNSSSLCipherEntry 6 }

  dynamicDNSSSLCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { dynamicDNSSSLCipherEntry 7 }

        
-- Dynamic DNS Stats Info


-- PCI Info

 pciCardInfo       OBJECT IDENTIFIER ::= { pciInfo 1 }
 pciWwanInfo       OBJECT IDENTIFIER ::= { pciInfo 2 }
 
 pciCardStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {pciCardInfo 1}
      
 pciCardType OBJECT-TYPE
      SYNTAX INTEGER {
         none(1),
         pciModem(2),
         WirelesWan(3)
         }
      MAX-ACCESS  read-only
      STATUS      current
      DESCRIPTION
              "PCI Card Type"
      ::= { pciCardInfo 2}
 
  wwanCardStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {pciWwanInfo 1}
      
      wwanCardType OBJECT-TYPE
      SYNTAX INTEGER {
         Sierra(1),
         SonyEricsson(2),
         Other-UseStandardDriver(3),
         Other-UseCustomDriver(4)
         }
      MAX-ACCESS  read-only
      STATUS      current
      DESCRIPTION
              "Wireless Wan Card Type"
      ::= { pciWwanInfo 2}
      
 wwanAPN OBJECT-TYPE
      SYNTAX      DisplayString(SIZE(0..60))
      MAX-ACCESS  read-only
      STATUS      current
      DESCRIPTION
              "APN"
      ::= { pciWwanInfo 3}
      
 wwanUserName OBJECT-TYPE
      SYNTAX      DisplayString(SIZE(0..16))
      MAX-ACCESS  read-only
      STATUS      current
      DESCRIPTION
              "User Name"
      ::= { pciWwanInfo 4}

 wwanPhoneNumer OBJECT-TYPE
      SYNTAX      DisplayString(SIZE(0..31))
      MAX-ACCESS  read-only
      STATUS      current
      DESCRIPTION
              "Phone Number"
      ::= { pciWwanInfo 5}
      
 wwanInitString OBJECT-TYPE
      SYNTAX      DisplayString(SIZE(0..60))
      MAX-ACCESS  read-only
      STATUS      current
      DESCRIPTION
              "Init String"
      ::= { pciWwanInfo 6}
      
  wwanNetworkRegistration OBJECT-TYPE
      SYNTAX      INTEGER
      MAX-ACCESS  read-only
      STATUS      current
      DESCRIPTION
              "Network Registration.
	      Possible Values
	      0 - Not Registered. Not searching for a network,
	      1 - Registered. Home Network,
	      2 - Not Registered. Searching for a network,
	      3 - Registration Denied
	      4 - Unknown,
	      5 - Registered. Roaming"
      ::= { pciWwanInfo 7}
      
  wwanSignalStrength OBJECT-TYPE
      SYNTAX      INTEGER
      MAX-ACCESS  read-only
      STATUS      current
      DESCRIPTION
              "Signal Strength"
      ::= { pciWwanInfo 8}


 -- VModem phone Table

  vmodemPhoneInfoTable OBJECT-TYPE
      SYNTAX      SEQUENCE OF VmodemPhoneInfoEntry
      MAX-ACCESS  not-accessible
      STATUS      current
      DESCRIPTION
              "The vmodem phone  info table."
      ::= { vmodemPhoneInfo 1 }

  vmodemPhoneInfoEntry OBJECT-TYPE
      SYNTAX      VmodemPhoneInfoEntry
      MAX-ACCESS  not-accessible
      STATUS      current
      DESCRIPTION
              "An entry in the vmodemPhoneInfoTable, each relating to a host."
      INDEX   { vmodemPhoneIndex }
      ::= { vmodemPhoneInfoTable 1 }

  VmodemPhoneInfoEntry ::=
      SEQUENCE {
        vmodemPhoneIndex
              INTEGER,
        vmodemPhoneStatus
              RowStatus,
        vmodemPhone
              DisplayString,
        vmodemPhoneIP
              Ipv4v6Address,
        vmodemPhonePort
              INTEGER
      }

  vmodemPhoneIndex OBJECT-TYPE
      SYNTAX      INTEGER
      MAX-ACCESS  not-accessible
      STATUS      current
      DESCRIPTION
              "The table entry number for this vmodem phone table"
      ::= { vmodemPhoneInfoEntry 1 }

  vmodemPhoneStatus OBJECT-TYPE
      SYNTAX      RowStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { vmodemPhoneInfoEntry 2 }

  vmodemPhone OBJECT-TYPE
      SYNTAX      DisplayString(SIZE(0..31))
      MAX-ACCESS  read-write
      STATUS      current
      DESCRIPTION
              "The modem name used for this modem entry. If blank, this entry
               is currently unused."
      ::= { vmodemPhoneInfoEntry 3 }

  vmodemPhoneIP OBJECT-TYPE
      SYNTAX      Ipv4v6Address
      MAX-ACCESS  read-write
      STATUS      current
      DESCRIPTION
              "The ip address corresponding to a phone number"
      ::= { vmodemPhoneInfoEntry 4 }


  vmodemPhonePort OBJECT-TYPE
      SYNTAX      INTEGER (0..65535)
      MAX-ACCESS  not-accessible
      STATUS      current
      DESCRIPTION
              "TCP port number corresponding to a phone number."
      ::= { vmodemPhoneInfoEntry 5 }
 END
