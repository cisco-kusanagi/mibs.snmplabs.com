-- $Id: rstone-cmts-mib.txt,v 1.2 2000/07/14 08:59:31 hyung Exp $

RIVERSTONE-CMTS-MIB DEFINITIONS ::= BEGIN

IMPORTS
        MODULE-IDENTITY, Counter32, Integer32,
        OBJECT-TYPE
            FROM SNMPv2-SMI
        MODULE-COMPLIANCE, OBJECT-GROUP
            FROM SNMPv2-CONF
        DisplayString, TEXTUAL-CONVENTION, TruthValue
            FROM SNMPv2-TC
        ifIndex
            FROM IF-MIB
        docsIfCmtsModIntervalUsageCode, docsIfCmtsModIndex
            FROM DOCS-IF-MIB
        riverstoneMibs
            FROM RSTONE-SMI-MIB;

rsCmtsMib MODULE-IDENTITY   
        LAST-UPDATED "200007080000Z"
        ORGANIZATION "Riverstone Networks, Inc"
        CONTACT-INFO
            "Riverstone Networks, Inc
             5200 Great America Parkway
             Santa Clara CA USA 95054
             PHONE:+1 408.878.6500
             EMAIL: nms-eng@riverstonenet.com
             WEB: http://www.riverstonenet.com"
        DESCRIPTION
            "This mib module defines the Riverstone Networks enterpise MIB for 
             CMTS modules.
             http://www.riverstonenet.com/products. 

             Copyright (C) Riverstone Networks, Inc 2000"

        REVISION     "200007080000Z"
        DESCRIPTION
            "First Version of the Riverstone CMTS MIB."
	::= { riverstoneMibs 11 }  

-- 
-- Status codes of the generic cmts command variable
-- 
RsCmtsCmdStatus ::= TEXTUAL-CONVENTION
       STATUS       current
       DESCRIPTION
           "A unique value for each status code of the generic cmts 
            command variable."
       SYNTAX   INTEGER {
                undefined(0),
                active(1),
                startup(2),
                process(3),
                success(4),
                failed(5)
       }

-- 
-- The Base table for the CMTSs, indexed by ifIndex
-- 
rsCmtsBaseTable  OBJECT-TYPE
        SYNTAX      SEQUENCE OF RsCmtsBaseEntry
        MAX-ACCESS  not-accessible
        STATUS      current
        DESCRIPTION
            "CMTS Base table settable parameters."
        ::= { rsCmtsMib 1 }

rsCmtsBaseEntry OBJECT-TYPE
        SYNTAX      RsCmtsBaseEntry
        MAX-ACCESS  not-accessible
        STATUS      current
        DESCRIPTION
            "An entry containing objects describing attributes of each
             MAC entry, extending the information in ifEntry.
             An entry in this table exists for each ifEntry with an
             ifType of docsCableMaclayer(127)."
        INDEX { ifIndex }
        ::= { rsCmtsBaseTable 1 }

RsCmtsBaseEntry ::= SEQUENCE {
            rsCmtsBaseBpduFilter            TruthValue,
            rsCmtsBaseBpduFilterHits        Counter32,
            rsCmtsBaseNonIPFilter           TruthValue,
            rsCmtsBaseNonIPFilterHits       Counter32,
            rsCmtsBaseMapLength             Integer32,
            rsCmtsBaseMapLeadTime           Integer32,
            rsCmtsBaseInitMaintLength       Integer32,
            rsCmtsBase3137Config1           Integer32,
            rsCmtsBase3137Config2           Integer32,
            rsCmtsBaseConcatenation         TruthValue,
            rsCmtsBaseBpiHwAssist           TruthValue,
            rsCmtsBaseGenericCmd            DisplayString,
            rsCmtsBaseGenericCmdStatus      RsCmtsCmdStatus,
            rsCmtsBaseUccRetryInterval      Integer32,
            rsCmtsBaseUccRetries            Integer32
        }

rsCmtsBaseBpduFilter  OBJECT-TYPE
        SYNTAX      TruthValue
        MAX-ACCESS  read-write
        STATUS      current
        DESCRIPTION
            "Indicates whether we do BPDU filtering on the headend."
        DEFVAL { false }
        ::= { rsCmtsBaseEntry 2 }

rsCmtsBaseBpduFilterHits  OBJECT-TYPE
        SYNTAX      Counter32
        MAX-ACCESS  read-only
        STATUS      current
        DESCRIPTION
            "Counts number of BPDU filter hits on the headend."
        ::= { rsCmtsBaseEntry 3 }

rsCmtsBaseNonIPFilter  OBJECT-TYPE
        SYNTAX      TruthValue
        MAX-ACCESS  read-write
        STATUS      current
        DESCRIPTION
            "Indicates whether we do non-IP filtering on the headend."
        DEFVAL { false }
        ::= { rsCmtsBaseEntry 4 }

rsCmtsBaseNonIPFilterHits  OBJECT-TYPE
        SYNTAX      Counter32
        MAX-ACCESS  read-only
        STATUS      current
        DESCRIPTION
            "Counts number of non-IP filter hits on the headend."
        ::= { rsCmtsBaseEntry 5 }

rsCmtsBaseMapLength  OBJECT-TYPE
        SYNTAX      Integer32 (0..2000)
        UNITS       "Microseconds"
        MAX-ACCESS  read-write
        STATUS      current
        DESCRIPTION
            "Length of the generated maps in microseconds."
        ::= { rsCmtsBaseEntry 6 }

rsCmtsBaseMapLeadTime  OBJECT-TYPE
        SYNTAX      Integer32 (0..2000)
        UNITS       "Microseconds"
        MAX-ACCESS  read-write
        STATUS      current
        DESCRIPTION
            "The amount of time between when we send a map and
             its effective start time in microseconds."
        ::= { rsCmtsBaseEntry 7 }

rsCmtsBaseInitMaintLength  OBJECT-TYPE
        SYNTAX      Integer32 (0..2000)
        UNITS       "Microseconds"
        MAX-ACCESS  read-write
        STATUS      current
        DESCRIPTION
            "The length of the initial maintenance interval in microseconds."
        ::= { rsCmtsBaseEntry 8 }

rsCmtsBase3137Config1  OBJECT-TYPE
        SYNTAX      Integer32 (0..255)
        MAX-ACCESS  read-write
        STATUS      current
        DESCRIPTION
            "3137 configuration register 1."
        ::= { rsCmtsBaseEntry 9 }
 
rsCmtsBase3137Config2  OBJECT-TYPE
        SYNTAX      Integer32 (0..255)
        MAX-ACCESS  read-write
        STATUS      current
        DESCRIPTION
            "3137 configuration register 2."
        ::= { rsCmtsBaseEntry 10 }

rsCmtsBaseConcatenation  OBJECT-TYPE
        SYNTAX      TruthValue
        MAX-ACCESS  read-write
        STATUS      current
        DESCRIPTION
            "Indicates whether we do Concatenation on the headend."
        DEFVAL { false }
        ::= { rsCmtsBaseEntry 11 }

rsCmtsBaseBpiHwAssist  OBJECT-TYPE
        SYNTAX      TruthValue
        MAX-ACCESS  read-write
        STATUS      current
        DESCRIPTION
            "Indicates whether we do key generation in hardware."
        DEFVAL { false }
        ::= { rsCmtsBaseEntry 12 }

rsCmtsBaseGenericCmd  OBJECT-TYPE
        SYNTAX      DisplayString
        MAX-ACCESS  read-write
        STATUS      current
        DESCRIPTION
            "A generic command to be applied to the active or startup 
             configuration.  The string is not to exceed 255 alpha-numeric 
             characters.  To write or check the status of the command, use
             the variable rsCmtsBaseGenericCmdStatus."
        ::= { rsCmtsBaseEntry 13 }

rsCmtsBaseGenericCmdStatus  OBJECT-TYPE
        SYNTAX      RsCmtsCmdStatus
        MAX-ACCESS  read-write
        STATUS      current
        DESCRIPTION
            "This variable is used to write the command in rsCmtsBaseGenericCmd
             to either the active or startup configuration file.  It is also
             useful to determine if the command is written successfully.  These
             are the codes of the status:
                 undefined(0)    --  default value
                 active(1)       --  write to active configuration
                 startup(2)      --  write to startup configuration
                 process(3)      --  processing request
                 success(4)      --  write succeeded
                 failed(5)       --  write failed"
        ::= { rsCmtsBaseEntry 14 }
 
rsCmtsBaseUccRetryInterval  OBJECT-TYPE
        SYNTAX      Integer32 (0..1000000)
        MAX-ACCESS  read-write
        STATUS      current
        DESCRIPTION
            "Interval in milliseconds between successive UCC requests."
        ::= { rsCmtsBaseEntry 15 }

rsCmtsBaseUccRetries  OBJECT-TYPE
        SYNTAX      Integer32
        MAX-ACCESS  read-only
        STATUS      current
        DESCRIPTION
            "Number of UCC request retries before timing out."
        ::= { rsCmtsBaseEntry 16 }

-- 
-- The Upstream table for the CMTSs, indexed by ifIndex
-- 
rsCmtsUpstreamTable  OBJECT-TYPE
        SYNTAX      SEQUENCE OF RsCmtsUpstreamEntry
        MAX-ACCESS  not-accessible
        STATUS      current
        DESCRIPTION
            "CMTS Upstream table configurable parameters."
        ::= { rsCmtsMib 2 }

rsCmtsUpstreamEntry OBJECT-TYPE
        SYNTAX      RsCmtsUpstreamEntry
        MAX-ACCESS  not-accessible
        STATUS      current
        DESCRIPTION
            "An entry containing objects describing attributes of each
             Upstream entry, extending the information in ifEntry."
        INDEX { ifIndex }
        ::= { rsCmtsUpstreamTable 1 }

RsCmtsUpstreamEntry ::= SEQUENCE {
            rsCmtsUpstreamNominalRxPower       Integer32,
            rsCmtsUpstreamState                TruthValue,
            rsCmtsUpstreamPolicing             TruthValue,
            rsCmtsUpstreamRangeInterval        Integer32,
            rsCmtsUpstreamRangeRetryInterval   Integer32,
            rsCmtsUpstreamPowerThreshold       Integer32,
            rsCmtsUpstreamPowerAdjust          TruthValue,
            rsCmtsUpstreamTimingAdjust         TruthValue,
            rsCmtsUpstreamFreqencyAdjust       TruthValue,
            rsCmtsUpstreamTXCoefficients       TruthValue,
            rsCmtsUpstreamForceContinue        TruthValue,
            rsCmtsUpstreamQosConfirm           TruthValue,
            rsCmtsUpstreamQosMaxBps            Integer32
        }

rsCmtsUpstreamNominalRxPower  OBJECT-TYPE
        SYNTAX      Integer32
        MAX-ACCESS  read-write
        STATUS      current
        DESCRIPTION
            "The value indicates the nominal, receive power (indBmV)
             of each upstream RF port."
        ::= { rsCmtsUpstreamEntry 1 }

rsCmtsUpstreamState  OBJECT-TYPE
        SYNTAX      TruthValue
        MAX-ACCESS  read-write
        STATUS      current
        DESCRIPTION
            "Indicates that the given upstream port is operational."
        DEFVAL { false }
        ::= { rsCmtsUpstreamEntry 2 }

rsCmtsUpstreamPolicing  OBJECT-TYPE
        SYNTAX      TruthValue
        MAX-ACCESS  read-write
        STATUS      current
        DESCRIPTION
            "Indicates if we are doing upstream traffic policing."
        DEFVAL { false }
        ::= { rsCmtsUpstreamEntry 3 }

rsCmtsUpstreamRangeInterval  OBJECT-TYPE
        SYNTAX      Integer32 (0..30000)
        UNITS       "Milliseconds"
        MAX-ACCESS  read-write
        STATUS      current
        DESCRIPTION
            "Indicates the Invited (Periodic) Ranging Intervals as input to
             the Bandwidth Allocator algorithm."
        DEFVAL { 0 }
        ::= { rsCmtsUpstreamEntry 4 }

rsCmtsUpstreamRangeRetryInterval  OBJECT-TYPE
        SYNTAX      Integer32 (0..30000)
        UNITS       "Milliseconds"
        MAX-ACCESS  read-write
        STATUS      current
        DESCRIPTION
            "Indicates the Invited (Periodic) Ranging Retry Intervals as 
             input to the Bandwidth Allocator algorithm."
        DEFVAL { 0 }
        ::= { rsCmtsUpstreamEntry 5 }

rsCmtsUpstreamPowerThreshold  OBJECT-TYPE
        SYNTAX      Integer32 (0..30000)
        UNITS       "Quarter DBmv"
        MAX-ACCESS  read-write
        STATUS      current
        DESCRIPTION
            "Indicates the Power Threshold for the upstream port."
        ::= { rsCmtsUpstreamEntry 6 }

rsCmtsUpstreamPowerAdjust  OBJECT-TYPE
        SYNTAX      TruthValue
        MAX-ACCESS  read-write
        STATUS      current
        DESCRIPTION
            "Indicates whether we override upstream power adjustments performed
             by the CMTS to the CMs.  If set the 'true', all RNG-Resp 
             messages will be transmitted with ZERO power adjustment, 
             regardless of received upstream power levels."
        DEFVAL { false }
        ::= { rsCmtsUpstreamEntry 7 }

rsCmtsUpstreamTimingAdjust  OBJECT-TYPE
        SYNTAX      TruthValue
        MAX-ACCESS  read-write
        STATUS      current
        DESCRIPTION
            "Indicates whether we override upstream timing adjustments performed
             by the CMTS to the CMs.  If set the 'true', all RNG-Resp 
             messages will be transmitted with ZERO timing adjustment, 
             regardless of received upstream timing."
        DEFVAL { false }
        ::= { rsCmtsUpstreamEntry 8 }

rsCmtsUpstreamFreqencyAdjust  OBJECT-TYPE
        SYNTAX      TruthValue
        MAX-ACCESS  read-write
        STATUS      current
        DESCRIPTION
            "Indicates whether we override upstream frequency adjustments 
             performed by the CMTS to the CMs.  If set the 'true', all RNG-Resp 
             messages will be transmitted with ZERO frequency adjustment, 
             regardless of received upstream frequency levels."
        DEFVAL { false }
        ::= { rsCmtsUpstreamEntry 9 }

rsCmtsUpstreamTXCoefficients  OBJECT-TYPE
        SYNTAX      TruthValue
        MAX-ACCESS  read-write
        STATUS      current
        DESCRIPTION
            "Indicates whether we omit the equalization coefficients for
             this upstream channel."
        DEFVAL { false }
        ::= { rsCmtsUpstreamEntry 10 }

rsCmtsUpstreamForceContinue  OBJECT-TYPE
        SYNTAX      TruthValue
        MAX-ACCESS  read-write
        STATUS      current
        DESCRIPTION
            "Indicates whether we force all RNG-Resp messages to issue
             a 'Continue' Ranging Status indefinitely."
        DEFVAL { false }
        ::= { rsCmtsUpstreamEntry 11 }

rsCmtsUpstreamQosConfirm  OBJECT-TYPE
        SYNTAX      TruthValue
        MAX-ACCESS  read-write
        STATUS      current
        DESCRIPTION
            "Indicates whether we would like to confirm the requested QoS
             parameters for this upstream during registration."
        DEFVAL { false }
        ::= { rsCmtsUpstreamEntry 12 }

rsCmtsUpstreamQosMaxBps  OBJECT-TYPE
        SYNTAX      Integer32
        MAX-ACCESS  read-write
        STATUS      current
        DESCRIPTION
            "The maximum number of bits per second of upstream bandwidth
             that we will allot to modems which request a minimum upstream
             rate.  We use this to control the amount of bandwidth
             oversubscription."
        ::= { rsCmtsUpstreamEntry 13 }

-- 
-- The Burst Descriptor table for the CMTSs, indexed by ifIndex
-- 

rsCmtsModulationTable OBJECT-TYPE
        SYNTAX      SEQUENCE OF RsCmtsModulationEntry
        MAX-ACCESS  not-accessible
        STATUS      current
        DESCRIPTION
            "Describes a modulation profile associated with one or more
             upstream channels."
        ::= { rsCmtsMib 3 }
 
rsCmtsModulationEntry OBJECT-TYPE
        SYNTAX      RsCmtsModulationEntry
        MAX-ACCESS  not-accessible
        STATUS      current
        DESCRIPTION
            "Describes a modulation profile for an Interval Usage Code
             for one or more upstream channels."
        INDEX { docsIfCmtsModIndex, docsIfCmtsModIntervalUsageCode }
        ::= { rsCmtsModulationTable 1 }
 
RsCmtsModulationEntry ::= SEQUENCE {
            rsCmtsModulationUWLength            Integer32,
            rsCmtsModulationDetectWindow        Integer32,
            rsCmtsModulationUWMismatch          Integer32,
            rsCmtsModulationEQSymbols           Integer32
        }

rsCmtsModulationUWLength  OBJECT-TYPE
        SYNTAX      Integer32 (1..3)
        MAX-ACCESS  read-only
        STATUS      current
        DESCRIPTION
            "Length of unique word pattern, in bytes."
        DEFVAL { 1 }
        ::= { rsCmtsModulationEntry 1 }

rsCmtsModulationDetectWindow  OBJECT-TYPE
        SYNTAX      Integer32 (0..255)
        MAX-ACCESS  read-write
        STATUS      current
        DESCRIPTION
            "Time window around a nominal detection time in which the unique 
             window detector is enabled."
        ::= { rsCmtsModulationEntry 2 }
 
rsCmtsModulationUWMismatch  OBJECT-TYPE
        SYNTAX      Integer32 (0..3)
        MAX-ACCESS  read-write
        STATUS      current
        DESCRIPTION
            "Specifies precision of match between unique word pattern and 
             incoming burst by specifying the number of bits which are 
             allowed to NOT match."
        ::= { rsCmtsModulationEntry 3 }
 
rsCmtsModulationEQSymbols  OBJECT-TYPE
        SYNTAX      Integer32 (0..512)
        MAX-ACCESS  read-write
        STATUS      current
        DESCRIPTION
            "Equalizer training sequence length, in symbols."
        ::= { rsCmtsModulationEntry 4 }
 
-- 
-- The Downstream table for the CMTSs, indexed by ifIndex
-- 

rsCmtsDownstreamTable  OBJECT-TYPE
        SYNTAX      SEQUENCE OF RsCmtsDownstreamEntry
        MAX-ACCESS  not-accessible
        STATUS      current
        DESCRIPTION
            "CMTS Downstream table settable parameters."
        ::= { rsCmtsMib 4 }

rsCmtsDownstreamEntry OBJECT-TYPE
        SYNTAX      RsCmtsDownstreamEntry
        MAX-ACCESS  not-accessible
        STATUS      current
        DESCRIPTION
            "An entry containing objects describing attributes of each
             Downstream entry, extending the information in ifEntry."
        INDEX { ifIndex }
        ::= { rsCmtsDownstreamTable 1 }

RsCmtsDownstreamEntry ::= SEQUENCE {
            rsCmtsDownstreamState                TruthValue,
            rsCmtsDownstreamModulation           TruthValue
        }

rsCmtsDownstreamState  OBJECT-TYPE
        SYNTAX      TruthValue
        MAX-ACCESS  read-write
        STATUS      current
        DESCRIPTION
            "Indicates whether the downstream port is enabled."
        DEFVAL { true }
        ::= { rsCmtsDownstreamEntry 1 }

rsCmtsDownstreamModulation  OBJECT-TYPE
        SYNTAX      TruthValue
        MAX-ACCESS  read-write
        STATUS      current
        DESCRIPTION
            "Indicates whether downstream modulation is turned on.
             When disabled, the downstream transmitter will output
             a CW, or tonal signal, at the tuned RF frequency."
        DEFVAL { false }
        ::= { rsCmtsDownstreamEntry 2 }

--
--  Compliance Section
--

rsCmtsConformance OBJECT IDENTIFIER ::= { rsCmtsMib 6 }

rsCmtsGroups OBJECT IDENTIFIER ::= { rsCmtsConformance 1 }

rsCmtsCompliances OBJECT IDENTIFIER ::= { rsCmtsConformance 2 }

rsCmtsBaseGroup OBJECT-GROUP
    OBJECTS {
       rsCmtsBaseBpduFilter,
       rsCmtsBaseBpduFilterHits,
       rsCmtsBaseNonIPFilter,
       rsCmtsBaseNonIPFilterHits,
       rsCmtsBaseMapLength,
       rsCmtsBaseMapLeadTime,
       rsCmtsBaseInitMaintLength,
       rsCmtsBase3137Config1,
       rsCmtsBase3137Config2,
       rsCmtsBaseConcatenation,
       rsCmtsBaseBpiHwAssist,
       rsCmtsBaseGenericCmd,
       rsCmtsBaseGenericCmdStatus,
       rsCmtsBaseUccRetryInterval,
       rsCmtsBaseUccRetries,
       rsCmtsUpstreamNominalRxPower,
       rsCmtsUpstreamState,
       rsCmtsUpstreamPolicing,
       rsCmtsUpstreamRangeInterval,
       rsCmtsUpstreamRangeRetryInterval,
       rsCmtsUpstreamPowerThreshold,
       rsCmtsUpstreamPowerAdjust,
       rsCmtsUpstreamTimingAdjust,
       rsCmtsUpstreamFreqencyAdjust,
       rsCmtsUpstreamTXCoefficients,
       rsCmtsUpstreamForceContinue,
       rsCmtsUpstreamQosConfirm,
       rsCmtsUpstreamQosMaxBps,
       rsCmtsModulationUWLength,
       rsCmtsModulationDetectWindow,
       rsCmtsModulationUWMismatch,
       rsCmtsModulationEQSymbols,
       rsCmtsDownstreamState,
       rsCmtsDownstreamModulation
    }
    STATUS      current
    DESCRIPTION
        "A collection of objects providing additional
         configuration and monitoring capabilites of Cable Modem
         Line Card parameters."
    ::= { rsCmtsGroups 1 }

rsCmtsMibCompliance MODULE-COMPLIANCE
    STATUS  current
    DESCRIPTION
        "The compliance statement for devices implementing
         Riverstone extended Cable Modem MIB."

    MODULE
        MANDATORY-GROUPS { rsCmtsBaseGroup }

       ::= { rsCmtsCompliances 1 }

END
