EMAIL-MIB DEFINITIONS ::= BEGIN

IMPORTS
	unix				FROM BSDUNIX-MIB

	DisplayString			FROM RFC1213-MIB

	OBJECT-TYPE, NetworkAddress, 
	Counter, internet		FROM RFC1155-SMI;


unix	      OBJECT IDENTIFIER	::= { enterprises 4 }
email	OBJECT IDENTIFIER ::= { unix 51 }



-- e-mail summary
	
eMailDeliveries OBJECT-TYPE
	SYNTAX	Counter
	ACCESS	read-only
	STATUS	mandatory
	DESCRIPTION
		"The number of deliveries or attempted deliveries." 
	::= { email 1 }

eMailErrors OBJECT-TYPE
	SYNTAX	Counter
	ACCESS	read-only
	STATUS	mandatory
	DESCRIPTION
		"The number delivery attempts with errors." 
	::= { email 2 }



-- e-mail transaction cache, remember last N transactions

eMailCacheSize OBJECT-TYPE
	SYNTAX	INTEGER
	ACCESS	read-only
	STATUS	mandatory
	DESCRIPTION
		"The number of valid entrys in the cache. The coresponding
		 indicies will be 0..N, where N equals the cache size - 1."
	::= { email 3 }

eMailCache OBJECT-TYPE
	SYNTAX	SEQUENCE OF EMailDelivery
	ACCESS	not-accessible
	STATUS	mandatory
	DESCRIPTION
		"A cache, of the 'eMailCacheSize' most recent 
		 e-mail deliveries."
	::= { email 4 }

eMailDelivery OBJECT-TYPE
	SYNTAX	EMailDelivery
	ACCESS	not-accessible
	STATUS	mandatory
	DESCRIPTION
		"An entry in the eMail delivery cache."
	INDEX	{ eMailIndex }
	::= { eMailCache 1 }

EMailDelivery ::= SEQUENCE {
	eMailIndex			INTEGER,
	eMailIdentifier			DisplayString,
	eMailSender			DisplayString,
	eMailReceiver			DisplayString,
	eMailChannel			DisplayString,
	eMailStatus			INTEGER,
	eMailSize			INTEGER,
	eMailPriority			INTEGER
}

eMailIndex OBJECT-TYPE
	SYNTAX  INTEGER
	ACCESS	read-only
	STATUS	mandatory
	DESCRIPTION
		"A unique index for this message."
	::= { eMailDelivery 1 }

eMailIdentifier OBJECT-TYPE
	SYNTAX	DisplayString
	ACCESS	read-only
	STATUS	mandatory
	DESCRIPTION
		"The message identifier of the form AA99999."
	::= { eMailDelivery 2 }

eMailSender OBJECT-TYPE
	SYNTAX	DisplayString
	ACCESS	read-only
	STATUS	mandatory
	DESCRIPTION
		"The message sender as listed in the message header."
	::= { eMailDelivery 3 }

eMailReceiver OBJECT-TYPE
	SYNTAX	DisplayString
	ACCESS	read-only
	STATUS 	mandatory
	DESCRIPTION
		"The message receiver as listed in the message header."
	::= { eMailDelivery 4 }
	
eMailChannel OBJECT-TYPE
	SYNTAX	DisplayString
	ACCESS	read-only
	STATUS	mandatory
	DESCRIPTION
		"The sending entity (not the person sending the message)."
	::= { eMailDelivery 5 }
	

eMailStatus OBJECT-TYPE
	SYNTAX INTEGER {
		unknown(1),
		success(2),
		unreachable(3),
		resourceLimitation(4),
		syntaxError(5),
		internalError(6),
		systemError(7),
		hostnameError(8),
		tempError(9)
	}
	ACCESS	read-only
	STATUS	mandatory
	DESCRIPTION
		"The status of this transaction."
	::= { eMailDelivery 6 }

eMailSize OBJECT-TYPE
	SYNTAX	INTEGER
	ACCESS	read-only
	STATUS	mandatory
	DESCRIPTION
		"The size, in octects, of the message."
	::= { eMailDelivery 7 }

eMailPriority OBJECT-TYPE
	SYNTAX	INTEGER
	ACCESS	read-only
	STATUS	mandatory
	DESCRIPTION
		"The priority of the message."
	::= { eMailDelivery 8 }

END
