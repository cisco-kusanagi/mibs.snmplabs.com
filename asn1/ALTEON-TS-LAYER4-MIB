-- COPYRIGHT NOTICE
-- Copyright (c) Alteon WebSystems, Inc. 2001
-- All rights reserved
-- 
-- HISTORY
-- $Log: tigonLayer4.mib $
-- Revision jb10_jbuswell/2 2002/02/15 17:00:25 jbuswell
-- 	Q00168061: Added slbStatPortMaintVMAdiscards to slbStatPortMaintTable.
-- 	To add support for vma discards stats.
-- 
-- Revision ge_rrekha/32 2001/11/28 18:28:30 rrekha
-- 	Added detailed decription for slbCurCfgAllowHttpHc and 
-- 	slbNewCfgAllowHttpHc.
-- 
-- Revision ge_rrekha/30 2001/11/28 01:30:36 rrekha
-- 	Added new MIB objects slbCurCfgAllowHttpHc/slbNewCfgAllowHttpHc.
-- 
-- Revision ge_rrekha/28 2001/11/20 23:31:18 rrekha
-- 	merged
-- 
-- Revision ge_rrekha/27 2001/11/20 23:27:51 rrekha
-- 	Added SNMP support for L7 deny filter.
-- 
-- Revision work_rmundhra/25 2001/11/20 18:36:03 rmundhra
-- 	Correct the ranges for Cookie offset and Cookie extract in
-- 	the Virtual Server table.
-- 
-- Revision work_rmundhra/23 2001/11/20 17:50:30 rmundhra
-- 	Correctly described syntax for entering in Cookie expiration.
-- 
-- Revision work_rmundhra/21 2001/11/20 02:29:32 rmundhra
-- 	Fixed comment.
-- 
-- Revision work_rmundhra/20 2001/11/20 02:28:01 rmundhra
-- 	Fixed CR Q00169389: Cookie Insert - No expiration params
-- 	in EMS, SNMP and WEBUI.
-- 	
-- 	Added slbCurCfgVirtServerCExpire and slbNewCfgVirtServerCExpire
--      MIB objects.	
-- 
-- Revision ge_rrekha/24 2001/11/07 00:23:47 rrekha
-- 	Since the contract table can vary in size removed the range for
-- 	fltCurCfgBwmContract/fltNewCfgBwmContract and 
-- 	fltCurCfgUrlBwmContract/fltNewCfgBwmContract.
-- 	The max size of the contract table should be used for range checking.
-- 
-- Revision ge_rrekha/22 2001/11/01 02:06:07 rrekha
-- 	Added new subtree rtspUrlRedir under slbUrl to support the RTSP
-- 	URL expression table.
-- 
-- Revision ge_rrekha/20 2001/10/31 23:23:12 rrekha
-- 	Fixed 13588: Added RTSP SLB options hash and patternMatch to the
-- 	MIB.
-- 
-- Revision ge_rrekha/18 2001/10/27 01:21:03 rrekha
-- 	Fixed 13617: Correct description for slbCurCfgGroupHealthCheckUrl
-- 	and slbNewCfgGroupHealthCheckUrl.
-- 
-- Revision ge_rrekha/16 2001/10/23 00:17:49 rrekha
-- 	Changed description of fltCurCfgTcpRateMaxConn/fltNewCfgTcpRateMaxConn
-- 	to reflect changes in CLI.
-- 
-- Revision ge_rrekha/14 2001/10/18 00:06:37 rrekha
-- 	Specify the correct range for fltCurCfgName/fltNewCfgName and
-- 	fltCurCfgBwmContract/fltNewCfgBwmContract.
-- 
-- Revision ge_rrekha/12 2001/10/17 19:59:38 rrekha
-- 	Changed slbNewCfgRealServerTimeOut range to 2-30.
-- 
-- Revision ge_rrekha/10 2001/10/17 18:34:14 rrekha
-- 	Added correct description for MIB object slbOperConfigSync.
-- 
-- Revision test_smiao/29 2001/10/16 19:07:21 smiao
-- 	Fixed 13289. Added sipsport enumeration for filter hash config.ag_filt.c
-- 
-- Revision ge_rrekha/8 2001/10/15 21:21:32 rrekha
-- 	Fixed typo in MIB variable name nasaStatMpHealthResponses.
-- 
-- Revision ge_rrekha/6 2001/09/17 21:26:34 rrekha
-- 	Fixed Q00103252: Added range for slbNewCfgRealServRealPort and
-- 	slbCurCfgRealServRealPort.
-- 	Also added range for filter source and destination ports.
-- 
-- Revision ge_rrekha/4 2001/09/06 21:37:40 rrekha
-- 	Added SNMP support for ARP health checks.
-- 
-- Revision test_smiao/27 2001/07/31 23:19:33 smiao
-- 	Added nasa base filter config.
-- 
-- Revision test_smiao/25 2001/07/17 01:45:48 smiao
-- 	Checked in for Hash Parameters.
-- 
-- Revision ge_rrekha/2 2001/07/16 22:38:50 rrekha
-- 	Added MIB objects for DNS SLB statistics.
-- 
-- Revision test_smiao/23 2001/07/11 22:26:35 smiao
-- 	Implemented NASA statistics in webUI and SNMP.
-- 
-- Revision genie_rekha/51 2001/07/11 01:34:52 rekha
-- 	Added MIB objects to support DNS SLB. Also removed objects 
-- 	related to AOL DPS.
-- 
-- Revision test_smiao/17 2001/07/06 23:48:14 smiao
-- 	Implemented ISD info for webUI and SNMP.
-- 
-- Revision test_smiao/16 2001/07/06 19:10:55 smiao
-- 	merged
-- 
-- Revision genie_rekha/49 2001/07/06 18:45:04 rekha
-- 	Added support for UDP based DNS health check.
-- 
-- Revision genie_rekha/47 2001/07/04 01:36:42 rekha
-- 	Added MIB objects for rate limiting time window and hold down
-- 	duration.
-- 
-- Revision genie_rekha/45 2001/07/04 00:20:01 rekha
-- 	Assigned correct OID for synAttackDetCfg.
-- 
-- Revision test_smiao/14 2001/06/29 18:15:34 smiao
-- 	Added ISD config in webUI and SNMP.
-- 
-- Revision genie_rekha/42 2001/06/25 23:07:10 rekha
-- 	Added MIB objects fltCurCfgDeepPktScan and fltNewCfgDeepPktScan
-- 	for AOL DPS support.
-- 
-- Revision genie_rekha/40 2001/06/25 19:26:21 rekha
-- 	Added MIB objects fltCurCfgIdslbHash and fltNewCfgIdslbHash.
-- 
-- Revision genie_rekha/38 2001/06/23 00:33:05 rekha
-- 	Added SNMP support for health check on VIP.
-- 
-- Revision genie_rekha/36 2001/06/22 02:51:15 rekha
-- 	Added MIB objects for TCP rate limiting config and statistics.
-- 
-- Revision test_smiao/12 2001/06/20 22:20:17 smiao
-- 	Implemented LDAP health check in SNMP and webUI.
-- 
-- Revision test_smiao/11 2001/06/20 22:10:05 smiao
-- 	merged
-- 
-- Revision genie_rekha/34 2001/06/20 19:52:33 rekha
-- 	Moved SYN attack detection under serverloadbalance to be consistent
-- 	with CLI.
-- 
-- Revision test_smiao/9 2001/06/19 01:18:24 smiao
-- 	Added filter name for webUI and SNMP for Tigon.
-- 
-- Revision genie_rekha/32 2001/06/12 17:35:24 rekha
-- 	Added MIB objects fltCurCfgVlan and fltNewCfgVlan for filter/VLAN 
-- 	support.
-- 
-- Revision genie_rekha/30 2001/06/11 19:44:51 rekha
-- 	Added new option 'headerhash' to httpslb for hashing based on 
-- 	header.
-- 
-- Revision work_rmundhra/17 2001/06/08 21:16:57 rmundhra
-- 	Fixed 11723: Changed the oids for slbVirtServicesCookieMode,
-- 	slbVirtServicesDbind for backward compatibility.
-- 
-- Revision work_rmundhra/15 2001/06/07 01:26:13 rmundhra
-- 	Fixed 11723: Renumbering of SLB SNMP object identifiers breaking
-- 	SNMP standards. 
-- 
-- Revision genie_rekha/28 2001/06/05 19:17:43 rekha
-- 	Added MIB object for slb sync oper command.
-- 
-- Revision genie_rekha/26 2001/05/31 23:35:54 rekha
-- 	Added MIB objects to support enable/disable real server oper
-- 	commands.
-- 
-- Revision genie_rekha/24 2001/05/29 22:54:38 rekha
-- 	Removed 'other' from most of the enumerations.
-- 
-- Revision genie_rekha/22 2001/05/18 00:11:08 rekha
-- 	CR11595: Changed references to GPP in the MIB description to iSD.
-- 
-- Revision genie_rekha/20 2001/05/09 20:16:52 rekha
-- 	CR11266: Added range for redirection port and icmp type.
-- 
-- Revision genie_rekha/18 2001/05/04 19:32:40 rekha
-- 	Fixed CR10941 & CR10942: Added WSP and WTLS health check options.
-- 
-- Revision genie_rekha/16 2001/04/27 00:32:24 rekha
-- 	Fixed CR11352: Added MIB object for WTLS port.
-- 
-- Revision genie_rekha/14 2001/04/13 22:46:44 rekha
-- 	Fixed CR11256: Added MIB objects fltNewCfgSrcIpMac, 
-- 	fltNewCfgDstIpMac, fltCurCfgSrcIpMac, fltCurCfgDstIpMac which
-- 	allows choosing between the sip/smac and dip/smac.
-- 
-- Revision work_rmundhra/13 2001/04/11 23:22:03 rmundhra
-- 	Fixed 11164: Need to make fltNewCfgPortFiltBmap read/write.
-- 	Incremented the octet string to be 256 bytes long to support
-- 	2K filters and also made fltNewCfgPortFiltBmap read-write.
-- 
-- Revision work_rmundhra/11 2001/03/30 21:09:33 rmundhra
-- 	Moved link health check option to the end of the 
-- 	enumeration list to avoid many changes which would 
-- 	otherwise be required to EMS.
-- 
-- Revision gs_sbatchu/2 2001/03/30 17:13:26 sbatchu
-- 	Renamed VPN feature to RTS.
-- 
-- Revision work_rmundhra/7 2001/03/19 19:49:39 rmundhra
-- 	Fixed 10943: WebUI link health check is not available as part
-- 	of group health check options. 
-- 
-- Revision work_rmundhra/5 2001/03/16 03:46:37 rmundhra
-- 	Fixed 10971: IDSLB/WebUI cannot configure IDSLB on port
-- 	for group.
-- 	Added entries slbCurCfgPortSlbIdslbState, slbNewCfgPortSlbIdslbState,
-- 	slbCurCfgRealGroupIdslb, slbNewCfgRealGroupIdslb to the mib.
-- 	Also deleted fltCurCfgIdslb and fltNewCfgIdslb entries as they
-- 	are redundant.
-- 
-- Revision genie_rekha/12 2001/02/27 23:32:51 rekha
-- 	Added MIB objects for tpcp and metric update interval.
-- 
-- Revision genie_rekha/10 2001/02/27 21:47:49 rekha
-- 	Added MIB objects to enable/disable real server proxy.
-- 
-- Revision genie_rekha/8 2001/02/27 20:57:23 rekha
-- 	Added SNMP support to enable/disable syncing BWM configuration.
-- 
-- Revision work_rmundhra/3 2001/02/22 18:44:35 rmundhra
-- 	Fixed 10749: 9.0.8: EMS: "pbind cookie rewrite AlteonP 1 16" gets
-- 	configured when configuring "httpslb browser and none".
-- 	Added disabled option to the enumeration for slbCurCfgVirtServiceCookieMode
-- 	& slbNewCfgVirtServiceCookieMode in the mib.
-- 	
-- 
-- Revision genie_rekha/6 2001/02/20 20:03:34 rekha
-- 	Added missing RURL information statistics.
-- 
-- Revision genie_rekha/4 2001/02/17 01:03:52 rekha
-- 	Change URL expression size to 20 for consistency with CLI.
-- 
-- Revision test_smiao/2 2001/02/14 02:52:26 smiao
-- 	Obsoleted slbFailOverInfo Table.
-- 
-- Revision genie_rekha/2 2001/02/08 18:18:02 rekha
-- 	As part of the code cleanup split the Tigon MIB into smaller
-- 	modules. Instead of altswitch.mib these 5 new modules should be
-- 	used.
-- 
-- $EndLog$
-- 
-- Version 10.0.x
--

ALTEON-TS-LAYER4-MIB DEFINITIONS ::= BEGIN

IMPORTS
    IpAddress, Counter, Gauge 
        FROM RFC1155-SMI
    OBJECT-TYPE
        FROM RFC-1212
    PhysAddress, DisplayString
        FROM RFC1213-MIB
    Counter64
        FROM SNMPv2-SMI
    switch 
        FROM ALTEON-ROOT-MIB
    stats, information, operCmds
        FROM ALTEON-TIGON-SWITCH-MIB;

serverloadbalance OBJECT IDENTIFIER ::= { switch 5 }
filtering  	  OBJECT IDENTIFIER ::= { switch 10 }
globalSLB         OBJECT IDENTIFIER ::= { switch 11 }
dynamicSLB        OBJECT IDENTIFIER ::= { switch 12 } -- obsoleted

slbfailover	  OBJECT IDENTIFIER ::= { serverloadbalance 16 } -- obsoleted
slbUrl            OBJECT IDENTIFIER ::= { serverloadbalance 27 }

slbUrlRedir       OBJECT IDENTIFIER ::= { slbUrl 1 }
slbUrlBalance     OBJECT IDENTIFIER ::= { slbUrl 2 }
rtspUrlRedir      OBJECT IDENTIFIER ::= { slbUrl 3 }

slbRurl           OBJECT IDENTIFIER ::= { serverloadbalance 52 }
slbRurlGeneral    OBJECT IDENTIFIER ::= { slbRurl 1 }

slbWaphc          OBJECT IDENTIFIER ::= { serverloadbalance 62 }
slbWap            OBJECT IDENTIFIER ::= { serverloadbalance 63 }
synAttackDetCfg   OBJECT IDENTIFIER ::= { serverloadbalance 82 }


gslbGeneral       OBJECT IDENTIFIER ::= { globalSLB 1 }
gslbDNS           OBJECT IDENTIFIER ::= { globalSLB 2 }
gslbSites         OBJECT IDENTIFIER ::= { globalSLB 3 }
gslbLookup        OBJECT IDENTIFIER ::= { globalSLB 4 }

slbStats  	  OBJECT IDENTIFIER ::= { stats  2 }
filterStats  	  OBJECT IDENTIFIER ::= { stats  6 }
gslbStats  	  OBJECT IDENTIFIER ::= { stats  7 }
gslbMaintStats    OBJECT IDENTIFIER ::= { stats  8 }
urlStats          OBJECT IDENTIFIER ::= { stats  10 }
tcpStats	  OBJECT IDENTIFIER ::= { stats  11 }
ftpStats          OBJECT IDENTIFIER ::= { stats  14 }
rurlStats	  OBJECT IDENTIFIER ::= { stats  18 }
rtspStats	  OBJECT IDENTIFIER ::= { stats  19 }
tcpLimitStats     OBJECT IDENTIFIER ::= { stats  23 }
nasaStats         OBJECT IDENTIFIER ::= { stats  24 }
dnsSlbStats       OBJECT IDENTIFIER ::= { stats  25 }

slb-info	  OBJECT IDENTIFIER ::= { information 2 }

slbOper           OBJECT IDENTIFIER ::= { operCmds 4 }

-- Real Server Table - Current Configuration

slbRealServerMaxSize OBJECT-TYPE
    SYNTAX INTEGER 
    ACCESS read-only 
    STATUS mandatory 
    DESCRIPTION 
        "The maximum number of entries in SLB RealServerTable." 
    ::= { serverloadbalance 1 }

slbCurCfgRealServerTable OBJECT-TYPE
    SYNTAX SEQUENCE OF SlbCurCfgRealServerEntry
    ACCESS not-accessible
    STATUS mandatory
    DESCRIPTION
        "The table of Real Server configuration in the current_config."
    ::= { serverloadbalance 2 }

slbCurCfgRealServerEntry OBJECT-TYPE
    SYNTAX SlbCurCfgRealServerEntry
    ACCESS not-accessible
    STATUS mandatory
    DESCRIPTION
        "Information about a particular Real Server configuration."
    INDEX { slbCurCfgRealServerIndex }
    ::= { slbCurCfgRealServerTable 1 }
 
SlbCurCfgRealServerEntry ::= SEQUENCE {
    slbCurCfgRealServerIndex           INTEGER,
    slbCurCfgRealServerIpAddr          IpAddress,
    slbCurCfgRealServerWeight          INTEGER,
    slbCurCfgRealServerMaxConns        INTEGER,
    slbCurCfgRealServerTimeOut         INTEGER,
    slbCurCfgRealServerBackUp          INTEGER,
    slbCurCfgRealServerPingInterval    INTEGER,
    slbCurCfgRealServerFailRetry       INTEGER,
    slbCurCfgRealServerSuccRetry       INTEGER,
    slbCurCfgRealServerState           INTEGER,
    slbCurCfgRealServerType            INTEGER,
    slbCurCfgRealServerName            DisplayString,
    slbCurCfgRealServerUrlBmap         OCTET STRING,
    slbCurCfgRealServerCookie          INTEGER,
    slbCurCfgRealServerExcludeStr      INTEGER,
    slbCurCfgRealServerSubmac          INTEGER,
    slbCurCfgRealServerProxy           INTEGER
    }

slbCurCfgRealServerIndex OBJECT-TYPE
    SYNTAX  INTEGER
    ACCESS  read-only
    STATUS  mandatory
    DESCRIPTION
        "The real server number" 
    ::= { slbCurCfgRealServerEntry 1 }

slbCurCfgRealServerIpAddr OBJECT-TYPE
    SYNTAX  IpAddress
    ACCESS  read-only
    STATUS  mandatory
    DESCRIPTION
        "IP address of the real server identified by the instance of the 
         slbRealServerIndex." 
    ::= { slbCurCfgRealServerEntry 2 }

slbCurCfgRealServerWeight OBJECT-TYPE
    SYNTAX  INTEGER (1..48)
    ACCESS  read-only
    STATUS  mandatory
    DESCRIPTION
        "The server weight." 
    ::= { slbCurCfgRealServerEntry 3 }

slbCurCfgRealServerMaxConns OBJECT-TYPE
    SYNTAX  INTEGER (0..200000)
    ACCESS  read-only
    STATUS  mandatory
    DESCRIPTION
        "The maximum number of connections that are allowed." 
    ::= { slbCurCfgRealServerEntry 4 }

slbCurCfgRealServerTimeOut OBJECT-TYPE
    SYNTAX  INTEGER (2..30)
    ACCESS  read-only
    STATUS  mandatory
    DESCRIPTION
        "The maximum number of minutes an inactive connection remains open." 
    ::= { slbCurCfgRealServerEntry 5 }

slbCurCfgRealServerBackUp OBJECT-TYPE
    SYNTAX INTEGER
    ACCESS  read-only
    STATUS  mandatory
    DESCRIPTION
        "The backup server number for this server." 
    ::= { slbCurCfgRealServerEntry 6 }

slbCurCfgRealServerPingInterval OBJECT-TYPE
    SYNTAX  INTEGER (0..60)
    ACCESS  read-only
    STATUS  mandatory
    DESCRIPTION
	"The interval between keep-alive (ping) attempts in number of seconds.
         Zero means disabling ping attempt."
    ::= { slbCurCfgRealServerEntry 7 }

slbCurCfgRealServerFailRetry OBJECT-TYPE
    SYNTAX  INTEGER  (1..63)
    ACCESS  read-only
    STATUS  mandatory
    DESCRIPTION
        "The number of failed attempts to declare this server DOWN." 
    ::= { slbCurCfgRealServerEntry 8 }

slbCurCfgRealServerSuccRetry OBJECT-TYPE
    SYNTAX  INTEGER (1..63)
    ACCESS  read-only
    STATUS  mandatory
    DESCRIPTION
        "The number of successful attempts to declare a server UP." 
    ::= { slbCurCfgRealServerEntry 9 }

slbCurCfgRealServerState OBJECT-TYPE
    SYNTAX  INTEGER {
	enabled(2),
	disabled(3)
	}
    ACCESS  read-only
    STATUS  mandatory
    DESCRIPTION
        "Enable or disable this server." 
    ::= { slbCurCfgRealServerEntry 10 }

slbCurCfgRealServerType OBJECT-TYPE
    SYNTAX  INTEGER {
	local-server(1),
	remote-server(2)
	}
    ACCESS  read-only
    STATUS  mandatory
    DESCRIPTION
        "The server type.  It participates in global server
	 load balancing when it is configured as remote-server." 
    ::= { slbCurCfgRealServerEntry 11 }

slbCurCfgRealServerName OBJECT-TYPE 
    SYNTAX  DisplayString (SIZE(0..31))
    ACCESS  read-only 
    STATUS  mandatory 
    DESCRIPTION 
        "The name of the real server."  
    ::= { slbCurCfgRealServerEntry 12 }

slbCurCfgRealServerUrlBmap OBJECT-TYPE
    SYNTAX  OCTET STRING
    ACCESS  read-only
    STATUS  mandatory
    DESCRIPTION
        "The URL Pathes selected for URL load balancing for by the real 
         server.  The selected URL Pathes are presented in a bitmap format.
         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

             where x : 1 - The represented URL Path is selected
                       0 - The represented URL Path is not selected"
    ::= { slbCurCfgRealServerEntry 13 }

slbCurCfgRealServerCookie OBJECT-TYPE
    SYNTAX  INTEGER {
        enabled(1),
        disabled(2)
        }
    ACCESS  read-only
    STATUS  mandatory
    DESCRIPTION
        "The real server that will handle client requests that doesn't 
         contain an URL cookie if Cookie loadbalance is enabled." 
    ::= { slbCurCfgRealServerEntry 14 }

slbCurCfgRealServerExcludeStr OBJECT-TYPE
    SYNTAX  INTEGER {
	enabled(1),
	disabled(2)
	}
    ACCESS  read-only
    STATUS  mandatory
    DESCRIPTION
        "The real server will handle requests that don't match the 
         loadbalance string if it is enabled."
    ::= { slbCurCfgRealServerEntry 15 }

slbCurCfgRealServerSubmac OBJECT-TYPE
    SYNTAX  INTEGER {
	enabled(1),
	disabled(2)
	}
    ACCESS  read-only
    STATUS  mandatory
    DESCRIPTION
        "The real server config to enable/disable MAC SA substitution for 
         L4 traffic. If disabled (the default) we will NOT substitute the 
         MAC SA of client-to-server frames.  If enabled, we will substitute 
         the MAC SA."
    ::= { slbCurCfgRealServerEntry 16 }

slbCurCfgRealServerProxy OBJECT-TYPE
    SYNTAX  INTEGER {
	enabled(1),
	disabled(2)
	}
    ACCESS  read-only
    STATUS  mandatory
    DESCRIPTION
        "The real server config to enable/disable client proxy operation."
    ::= { slbCurCfgRealServerEntry 17 }

-- Real Server Table - New Configuration

slbNewCfgRealServerTable OBJECT-TYPE
    SYNTAX  SEQUENCE OF SlbNewCfgRealServerEntry
    ACCESS  not-accessible
    STATUS  mandatory
    DESCRIPTION
        "The table of Real Server configuration in the new_config."
    ::= { serverloadbalance 3 }

slbNewCfgRealServerEntry OBJECT-TYPE
    SYNTAX  SlbNewCfgRealServerEntry
    ACCESS  not-accessible
    STATUS  mandatory
    DESCRIPTION
        "Information about a particular Real Server configuration."
    INDEX   { slbNewCfgRealServerIndex }
    ::= { slbNewCfgRealServerTable 1 }
 
SlbNewCfgRealServerEntry ::= SEQUENCE {
    slbNewCfgRealServerIndex           INTEGER,
    slbNewCfgRealServerIpAddr          IpAddress,
    slbNewCfgRealServerWeight          INTEGER,
    slbNewCfgRealServerMaxConns        INTEGER,
    slbNewCfgRealServerTimeOut         INTEGER,
    slbNewCfgRealServerBackUp          INTEGER,
    slbNewCfgRealServerPingInterval    INTEGER,
    slbNewCfgRealServerFailRetry       INTEGER,
    slbNewCfgRealServerSuccRetry       INTEGER,
    slbNewCfgRealServerState           INTEGER,
    slbNewCfgRealServerDelete          INTEGER,
    slbNewCfgRealServerType            INTEGER,
    slbNewCfgRealServerName            DisplayString,
    slbNewCfgRealServerUrlBmap         OCTET STRING,
    slbNewCfgRealServerAddUrl          INTEGER,
    slbNewCfgRealServerRemUrl          INTEGER,
    slbNewCfgRealServerCookie          INTEGER,
    slbNewCfgRealServerExcludeStr      INTEGER,
    slbNewCfgRealServerSubmac          INTEGER,
    slbNewCfgRealServerProxy           INTEGER
    }

slbNewCfgRealServerIndex OBJECT-TYPE
    SYNTAX  INTEGER
    ACCESS  read-only
    STATUS  mandatory
    DESCRIPTION
        "The real server number" 
    ::= { slbNewCfgRealServerEntry 1 }

slbNewCfgRealServerIpAddr OBJECT-TYPE
    SYNTAX  IpAddress
    ACCESS  read-write
    STATUS  mandatory
    DESCRIPTION
        "IP address of the real server identified by the instance of 
         slbRealServerIndex." 
    ::= { slbNewCfgRealServerEntry 2 }

slbNewCfgRealServerWeight OBJECT-TYPE
    SYNTAX  INTEGER (1..48)
    ACCESS  read-write
    STATUS  mandatory
    DESCRIPTION
        "The server weight." 
    ::= { slbNewCfgRealServerEntry 3 }

slbNewCfgRealServerMaxConns OBJECT-TYPE
    SYNTAX  INTEGER (0..200000)
    ACCESS  read-write
    STATUS  mandatory
    DESCRIPTION
        "The maximum number of connections that are allowed." 
    ::= { slbNewCfgRealServerEntry 4 }

slbNewCfgRealServerTimeOut OBJECT-TYPE
    SYNTAX  INTEGER (2..30)
    ACCESS  read-write
    STATUS  mandatory
    DESCRIPTION
        "The maximum number of minutes an inactive connection remains open." 
    ::= { slbNewCfgRealServerEntry 5 }

slbNewCfgRealServerBackUp OBJECT-TYPE
    SYNTAX INTEGER
    ACCESS  read-write
    STATUS  mandatory
    DESCRIPTION
        "The backup server number for this server." 
    ::= { slbNewCfgRealServerEntry 6 }

slbNewCfgRealServerPingInterval OBJECT-TYPE
    SYNTAX  INTEGER (0..60)
    ACCESS  read-write
    STATUS  mandatory
    DESCRIPTION
        "The interval between keep-alive (ping) attempts in number of 
         seconds. Zero means disabling ping attempt."
    ::= { slbNewCfgRealServerEntry 7 }

slbNewCfgRealServerFailRetry OBJECT-TYPE
    SYNTAX  INTEGER  (1..63)
    ACCESS  read-write
    STATUS  mandatory
    DESCRIPTION
        "The number of failed attempts to declare this server DOWN." 
    ::= { slbNewCfgRealServerEntry 8 }

slbNewCfgRealServerSuccRetry OBJECT-TYPE
    SYNTAX  INTEGER (1..63)
    ACCESS  read-write
    STATUS  mandatory
    DESCRIPTION
        "The number of successful attempts to declare a server UP." 
    ::= { slbNewCfgRealServerEntry 9 }

slbNewCfgRealServerState OBJECT-TYPE
    SYNTAX  INTEGER {
	enabled(2),
	disabled(3)
	}
    ACCESS  read-write
    STATUS  mandatory
    DESCRIPTION
        "Enable or disable this server." 
    ::= { slbNewCfgRealServerEntry 10 }

slbNewCfgRealServerDelete OBJECT-TYPE
    SYNTAX  INTEGER {
        other(1),
        delete(2)
        }
    ACCESS  read-write
    STATUS  mandatory
    DESCRIPTION
        "By setting the value to delete(2), the entire row is deleted."
    ::= { slbNewCfgRealServerEntry 11 }

slbNewCfgRealServerType OBJECT-TYPE
    SYNTAX  INTEGER {
        local-server(1),
	remote-server(2)
	}
    ACCESS  read-write
    STATUS  mandatory
    DESCRIPTION
        "The server type.  It participates in global server load balancing 
         when it is configured as remote-server." 
    ::= { slbNewCfgRealServerEntry 12 }

slbNewCfgRealServerName OBJECT-TYPE 
    SYNTAX  DisplayString (SIZE(0..31))
    ACCESS  read-write 
    STATUS  mandatory 
    DESCRIPTION 
        "The name of the real server."  
    ::= { slbNewCfgRealServerEntry 13 }

slbNewCfgRealServerUrlBmap OBJECT-TYPE
    SYNTAX  OCTET STRING
    ACCESS  read-only
    STATUS  mandatory
    DESCRIPTION
        "The URL Pathes selected for URL load balancing for by the
	 real server.  The selected URL Pathes are presented in 
	 a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL Path is selected
                   0 - The represented URL Path is not selected"
    ::= { slbNewCfgRealServerEntry 14 }

slbNewCfgRealServerAddUrl OBJECT-TYPE
    SYNTAX  INTEGER
    ACCESS  read-write
    STATUS  mandatory
    DESCRIPTION
        "The URL Path (slbCurCfgUrlLbPathIndex) to be added to the 
         real server. A zero is returned when read."
    ::= { slbNewCfgRealServerEntry 15 }

slbNewCfgRealServerRemUrl OBJECT-TYPE
    SYNTAX  INTEGER
    ACCESS  read-write
    STATUS  mandatory
    DESCRIPTION
        "The URL Path (slbCurCfgUrlLbPathIndex) to be removed from 
         the real server. A zero is returned when read."
    ::= { slbNewCfgRealServerEntry 16 }

slbNewCfgRealServerCookie OBJECT-TYPE
    SYNTAX  INTEGER {
	enabled(1),
	disabled(2)
	}
    ACCESS  read-write
    STATUS  mandatory
    DESCRIPTION
        "Enable or disable real server to handle client requests
         that don't contain a cookie if cookie loadbalance is enabled." 
    ::= { slbNewCfgRealServerEntry 17 }

slbNewCfgRealServerExcludeStr OBJECT-TYPE
    SYNTAX  INTEGER {
	enabled(1),
	disabled(2)
	}
    ACCESS  read-write
    STATUS  mandatory
    DESCRIPTION
        "Enable or disable exclusionary matching string on real server."
    ::= { slbNewCfgRealServerEntry 18 }

slbNewCfgRealServerSubmac OBJECT-TYPE
    SYNTAX  INTEGER {
	enabled(1),
	disabled(2)
	}
    ACCESS  read-write
    STATUS  mandatory
    DESCRIPTION
        "The real server config to enable/disable MAC SA substitution for 
         L4 traffic. If disabled (the default) we will NOT substitute the 
         MAC SA of client-to-server frames.  If enabled, we will substitute 
         the MAC SA."
    ::= { slbNewCfgRealServerEntry 19 }

slbNewCfgRealServerProxy OBJECT-TYPE
    SYNTAX  INTEGER {
	enabled(1),
	disabled(2)
	}
    ACCESS  read-write
    STATUS  mandatory
    DESCRIPTION
        "The real server config to enable/disable client proxy operation."
    ::= { slbNewCfgRealServerEntry 20 }

-- Real Server Multiple Port Table

slbRealServPortTableMaxSize OBJECT-TYPE
    SYNTAX  INTEGER 
    ACCESS  read-only 
    STATUS  mandatory 
    DESCRIPTION 
        "The maximum number of entries in SLB RealServPortTable." 
    ::= { serverloadbalance 53 }

slbCurCfgRealServPortTable OBJECT-TYPE
    SYNTAX  SEQUENCE OF SlbCurCfgRealServPortEntry
    ACCESS  not-accessible
    STATUS  mandatory
    DESCRIPTION
        "The table of real server service ports."
    ::= { serverloadbalance 48 }

slbCurCfgRealServPortEntry OBJECT-TYPE
    SYNTAX  SlbCurCfgRealServPortEntry
    ACCESS  not-accessible
    STATUS  mandatory
    DESCRIPTION
        "A row in the real server service ports table."
    INDEX   { slbCurCfgRealServIndex, slbCurCfgRealServPortIndex }
    ::= { slbCurCfgRealServPortTable 1 }

SlbCurCfgRealServPortEntry ::= SEQUENCE {
    slbCurCfgRealServIndex         INTEGER,
    slbCurCfgRealServPortIndex     INTEGER,
    slbCurCfgRealServRealPort      INTEGER
    }

slbCurCfgRealServIndex OBJECT-TYPE
    SYNTAX  INTEGER
    ACCESS  read-only
    STATUS  mandatory
    DESCRIPTION
        "The number of the real server." 
    ::= { slbCurCfgRealServPortEntry 1 }

slbCurCfgRealServPortIndex OBJECT-TYPE 
    SYNTAX  INTEGER 
    ACCESS  read-only 
    STATUS  mandatory 
    DESCRIPTION 
        "The port index. This has no external meaning" 
    ::= { slbCurCfgRealServPortEntry 2 }

slbCurCfgRealServRealPort OBJECT-TYPE  
    SYNTAX  INTEGER (2..65534)
    ACCESS  read-only  
    STATUS  mandatory  
    DESCRIPTION 
        "The layer4 real service port number."  
    ::= { slbCurCfgRealServPortEntry 3 } 

slbNewCfgRealServPortTable OBJECT-TYPE
    SYNTAX  SEQUENCE OF SlbNewCfgRealServPortEntry
    ACCESS  not-accessible
    STATUS  mandatory
    DESCRIPTION
        "The table of real server service ports."
    ::= { serverloadbalance 49 }

slbNewCfgRealServPortEntry OBJECT-TYPE
    SYNTAX  SlbNewCfgRealServPortEntry
    ACCESS  not-accessible
    STATUS  mandatory
    DESCRIPTION
        "A row in the real server service ports table."
    INDEX   { slbNewCfgRealServIndex, slbNewCfgRealServPortIndex }
    ::= { slbNewCfgRealServPortTable 1 }

SlbNewCfgRealServPortEntry ::= SEQUENCE {
    slbNewCfgRealServIndex         INTEGER,
    slbNewCfgRealServPortIndex     INTEGER,
    slbNewCfgRealServRealPort      INTEGER,
    slbNewCfgRealServPortDelete    INTEGER
    }

slbNewCfgRealServIndex OBJECT-TYPE
    SYNTAX  INTEGER
    ACCESS  read-only
    STATUS  mandatory
    DESCRIPTION
        "The number of the real server." 
    ::= { slbNewCfgRealServPortEntry 1 }

slbNewCfgRealServPortIndex OBJECT-TYPE 
    SYNTAX  INTEGER 
    ACCESS  read-only 
    STATUS  mandatory 
    DESCRIPTION 
        "The port index. This has no external meaning" 
    ::= { slbNewCfgRealServPortEntry 2 }

slbNewCfgRealServRealPort OBJECT-TYPE  
    SYNTAX  INTEGER (2..65534)
    ACCESS  read-write  
    STATUS  mandatory  
    DESCRIPTION 
        "The layer4 real service port number."  
    ::= { slbNewCfgRealServPortEntry 3 } 

slbNewCfgRealServPortDelete OBJECT-TYPE
    SYNTAX  INTEGER {
        other(1),
        delete(2)
        }
    ACCESS  read-write
    STATUS  mandatory
    DESCRIPTION
        "When set to the value of 2 (delete), the entire row is deleted. 
         When read, other(1) is returned. Setting the value to anything 
         other than 2(delete) has no effect on the state of the row."
    ::= { slbNewCfgRealServPortEntry 4 }

-- Server load balancing - Virtual Server Table

slbVirtServerTableMaxSize OBJECT-TYPE
    SYNTAX  INTEGER
    ACCESS  read-only
    STATUS  mandatory
    DESCRIPTION
        "The maximum number of entries in SLB VirtServerTable."
    ::= { serverloadbalance 4 }

slbCurCfgVirtServerTable OBJECT-TYPE
    SYNTAX  SEQUENCE OF SlbCurCfgVirtualServerEntry
    ACCESS  not-accessible
    STATUS  mandatory
    DESCRIPTION
        "The table of virtual Servers."
    ::= { serverloadbalance 5 }
 
slbCurCfgVirtualServerEntry OBJECT-TYPE
    SYNTAX  SlbCurCfgVirtualServerEntry
    ACCESS  not-accessible
    STATUS  mandatory
    DESCRIPTION
        "A row in the virtual server table."
    INDEX   { slbCurCfgVirtServerIndex }
    ::= { slbCurCfgVirtServerTable 1 }
 
SlbCurCfgVirtualServerEntry ::= SEQUENCE {
    slbCurCfgVirtServerIndex     	INTEGER,
    slbCurCfgVirtServerIpAddress 	IpAddress,
    slbCurCfgVirtServerLayer3Only    	INTEGER,
    slbCurCfgVirtServerState     	INTEGER,
    slbCurCfgVirtServerDname     	DisplayString,
    slbCurCfgVirtServerCname            DisplayString,
    slbCurCfgVirtServerCoffset          INTEGER,
    slbCurCfgVirtServerClength          INTEGER,
    slbCurCfgVirtServerUriCookie        INTEGER,
    slbCurCfgVirtServerFtpParsing	INTEGER,  -- obsoleted
    slbCurCfgVirtServerUrlHashLen       INTEGER,
    slbCurCfgVirtServerHttpHdrName      DisplayString,
    slbCurCfgVirtServerBwmContract	INTEGER,
    slbCurCfgVirtServerResponseCount	INTEGER,
    slbCurCfgVirtServerCExpire          DisplayString
    }

slbCurCfgVirtServerIndex OBJECT-TYPE
    SYNTAX  INTEGER
    ACCESS  read-only
    STATUS  mandatory
    DESCRIPTION
        "Virtual Server Number" 
    ::= { slbCurCfgVirtualServerEntry 1 }

slbCurCfgVirtServerIpAddress OBJECT-TYPE
    SYNTAX  IpAddress
    ACCESS  read-only
    STATUS  mandatory
    DESCRIPTION
        "IP address of the virtual server." 
    ::= { slbCurCfgVirtualServerEntry 2 }

slbCurCfgVirtServerLayer3Only OBJECT-TYPE 
    SYNTAX  INTEGER {
	layer3Only(1),
	disabled(2)
	}
    ACCESS  read-only 
    STATUS  mandatory 
    DESCRIPTION 
        "Enable or disable layer3 only balancing."  
    ::= { slbCurCfgVirtualServerEntry 3 }

slbCurCfgVirtServerState OBJECT-TYPE 
    SYNTAX  INTEGER {
	enabled(2),
	disabled(3)
	}
    ACCESS  read-only 
    STATUS  mandatory 
    DESCRIPTION 
        "Enable or disable the virtual server."  
    ::= { slbCurCfgVirtualServerEntry 4 }

slbCurCfgVirtServerDname OBJECT-TYPE 
    SYNTAX  DisplayString (SIZE(0..34))
    ACCESS  read-only 
    STATUS  mandatory 
    DESCRIPTION 
        "The domain name of the virtual server."  
    ::= { slbCurCfgVirtualServerEntry 5 }

slbCurCfgVirtServerCname OBJECT-TYPE 
    SYNTAX  DisplayString (SIZE(0..20))
    ACCESS  read-only 
    STATUS  mandatory 
    DESCRIPTION 
        "The cookie name of the virtual server used for cookie load balance."  
    ::= { slbCurCfgVirtualServerEntry 6 }

slbCurCfgVirtServerCoffset OBJECT-TYPE
    SYNTAX  INTEGER (0..64)
    ACCESS  read-only
    STATUS  mandatory
    DESCRIPTION
        "The starting byte offset of the cookie value." 
    ::= { slbCurCfgVirtualServerEntry 7 }

slbCurCfgVirtServerClength OBJECT-TYPE
    SYNTAX  INTEGER (0..64)
    ACCESS  read-only
    STATUS  mandatory
    DESCRIPTION
        "The number of bytes to extract from the cookie value." 
    ::= { slbCurCfgVirtualServerEntry 8 }

slbCurCfgVirtServerUriCookie OBJECT-TYPE 
    SYNTAX  INTEGER {
	enabled(1),
	disabled(2)
	}
    ACCESS  read-only 
    STATUS  mandatory 
    DESCRIPTION 
        "Enable or disable cookie search in URI"  
    ::= { slbCurCfgVirtualServerEntry 9 }

slbCurCfgVirtServerFtpParsing OBJECT-TYPE
    SYNTAX  INTEGER {
	enabled(1),
	disabled(2)
	}
    ACCESS  read-only
    STATUS  obsolete
    DESCRIPTION
        "Enable or Disable the ftp parsing for the virtual server."
    ::= { slbCurCfgVirtualServerEntry 10 }

slbCurCfgVirtServerUrlHashLen OBJECT-TYPE
    SYNTAX  INTEGER (0..255)
    ACCESS  read-only
    STATUS  mandatory
    DESCRIPTION
        "The number of bytes used to hash onto server. A zero means 
         URL hashing disabled."
    ::= { slbCurCfgVirtualServerEntry 11 }

slbCurCfgVirtServerHttpHdrName OBJECT-TYPE
    SYNTAX  DisplayString (SIZE(0..32))
    ACCESS  read-only
    STATUS  mandatory
    DESCRIPTION
        "The HTTP header name of the virtual server."
    ::= { slbCurCfgVirtualServerEntry 12 }

slbCurCfgVirtServerBwmContract OBJECT-TYPE
    SYNTAX  INTEGER
    ACCESS  read-only
    STATUS  mandatory
    DESCRIPTION
        "The default BW contract of virtual server."
    ::= { slbCurCfgVirtualServerEntry 13 }

slbCurCfgVirtServerResponseCount OBJECT-TYPE 
    SYNTAX  INTEGER (1..16)
    ACCESS  read-only
    STATUS  mandatory 
    DESCRIPTION 
        "The number of cookie search response count."
    ::= { slbCurCfgVirtualServerEntry 14}

slbCurCfgVirtServerCExpire OBJECT-TYPE 
    SYNTAX  DisplayString (SIZE(0..20))
    ACCESS  read-only 
    STATUS  mandatory 
    DESCRIPTION 
        "The cookie expire of the virtual server used for insert cookie load
         balance depending on the mode it has the following format 
         <MM/dd/yy[@hh:mm]> absolute mode or <days[:hours[:minutes]]>
         for relative mode."  
    ::= { slbCurCfgVirtualServerEntry 15 }

-- Server load balancing - Virtual Server Table

slbNewCfgVirtServerTable OBJECT-TYPE
    SYNTAX  SEQUENCE OF SlbNewCfgVirtualServerEntry
    ACCESS  not-accessible
    STATUS  mandatory
    DESCRIPTION
        "The table of virtual Servers."
    ::= { serverloadbalance 6 }

slbNewCfgVirtualServerEntry OBJECT-TYPE
    SYNTAX  SlbNewCfgVirtualServerEntry
    ACCESS  not-accessible
    STATUS  mandatory
    DESCRIPTION
        "A row in the virtual server table."
    INDEX   { slbNewCfgVirtServerIndex }
    ::= { slbNewCfgVirtServerTable 1 }
 
SlbNewCfgVirtualServerEntry ::= SEQUENCE {
    slbNewCfgVirtServerIndex   		INTEGER,
    slbNewCfgVirtServerIpAddress 	IpAddress,
    slbNewCfgVirtServerLayer3Only   	INTEGER,
    slbNewCfgVirtServerState     	INTEGER,
    slbNewCfgVirtServerDelete    	INTEGER,
    slbNewCfgVirtServerDname     	DisplayString,
    slbNewCfgVirtServerCname            DisplayString,
    slbNewCfgVirtServerCoffset          INTEGER,
    slbNewCfgVirtServerClength          INTEGER, 
    slbNewCfgVirtServerUriCookie        INTEGER,
    slbNewCfgVirtServerFtpParsing       INTEGER,   -- obsolete
    slbNewCfgVirtServerUrlHashLen       INTEGER,
    slbNewCfgVirtServerHttpHdrName      DisplayString,
    slbNewCfgVirtServerBwmContract	INTEGER,
    slbNewCfgVirtServerResponseCount	INTEGER,
    slbNewCfgVirtServerCExpire          DisplayString
    }

slbNewCfgVirtServerIndex OBJECT-TYPE
    SYNTAX  INTEGER
    ACCESS  read-only
    STATUS  mandatory
    DESCRIPTION
        "The Virtual Server Number" 
    ::= { slbNewCfgVirtualServerEntry 1 }

slbNewCfgVirtServerIpAddress OBJECT-TYPE
    SYNTAX  IpAddress
    ACCESS  read-write
    STATUS  mandatory
    DESCRIPTION
        "IP address of the virtual server." 
    ::= { slbNewCfgVirtualServerEntry 2 }

slbNewCfgVirtServerLayer3Only OBJECT-TYPE 
    SYNTAX  INTEGER {
        layer3Only(1),
	disabled(2)
	}
    ACCESS  read-write 
    STATUS  mandatory 
    DESCRIPTION 
        "Enable or disable layer3 only balancing."  
    ::= { slbNewCfgVirtualServerEntry 3 }

slbNewCfgVirtServerState OBJECT-TYPE 
    SYNTAX  INTEGER {
	enabled(2),
	disabled(3)
	}
    ACCESS  read-write 
    STATUS  mandatory 
    DESCRIPTION 
        "Enable or disable the virtual server."  
    ::= { slbNewCfgVirtualServerEntry 4 }

slbNewCfgVirtServerDelete OBJECT-TYPE
    SYNTAX  INTEGER {
        other(1),
        delete(2)
        }
    ACCESS  read-write
    STATUS  mandatory
    DESCRIPTION
        "By setting the value to delete(2), the entire row is deleted."
    ::= { slbNewCfgVirtualServerEntry 5 }

slbNewCfgVirtServerDname OBJECT-TYPE 
    SYNTAX  DisplayString (SIZE(0..34))
    ACCESS  read-write 
    STATUS  mandatory 
    DESCRIPTION 
        "The domain name of the virtual server."  
    ::= { slbNewCfgVirtualServerEntry 6 }

slbNewCfgVirtServerCname OBJECT-TYPE 
    SYNTAX  DisplayString (SIZE(0..20))
    ACCESS  read-write 
    STATUS  mandatory 
    DESCRIPTION 
        "The cookie name of the virtual server used for cookie load balance."  
    ::= { slbNewCfgVirtualServerEntry 7 }

slbNewCfgVirtServerCoffset OBJECT-TYPE
    SYNTAX  INTEGER (0..64)
    ACCESS  read-write 
    STATUS  mandatory
    DESCRIPTION
        "The starting byte offset of the cookie value." 
    ::= { slbNewCfgVirtualServerEntry 8 }

slbNewCfgVirtServerClength OBJECT-TYPE
    SYNTAX  INTEGER (0..64)
    ACCESS  read-write
    STATUS  mandatory
    DESCRIPTION
        "The number of bytes to extract from the cookie value." 
    ::= { slbNewCfgVirtualServerEntry 9 }

slbNewCfgVirtServerUriCookie OBJECT-TYPE 
    SYNTAX  INTEGER {
	enabled(1),
	disabled(2)
	}
    ACCESS  read-write 
    STATUS  mandatory 
    DESCRIPTION 
        "Enable or disable cookie search in URI"  
    ::= { slbNewCfgVirtualServerEntry 10}

slbNewCfgVirtServerFtpParsing OBJECT-TYPE
    SYNTAX  INTEGER {
	enabled(1),
	disabled(2)
	}
    ACCESS  read-write
    STATUS  obsolete
    DESCRIPTION
        "Enable or Disable the ftp parsing for the virtual server."
    ::= { slbNewCfgVirtualServerEntry 11 }

slbNewCfgVirtServerUrlHashLen OBJECT-TYPE 
    SYNTAX  INTEGER (0..255)
    ACCESS  read-write 
    STATUS  mandatory 
    DESCRIPTION 
        "The number of bytes used to hash onto server, A zero means
         URL hashing disabled."
    ::= { slbNewCfgVirtualServerEntry 12}

slbNewCfgVirtServerHttpHdrName OBJECT-TYPE 
    SYNTAX  DisplayString  (SIZE(0..32))
    ACCESS  read-write 
    STATUS  mandatory 
    DESCRIPTION 
        "The HTTP header name of the virtual server."
    ::= { slbNewCfgVirtualServerEntry 13}

slbNewCfgVirtServerBwmContract OBJECT-TYPE 
    SYNTAX  INTEGER
    ACCESS  read-write 
    STATUS  mandatory 
    DESCRIPTION 
        "The default BW contract number of the virtual server."
    ::= { slbNewCfgVirtualServerEntry 14}

slbNewCfgVirtServerResponseCount OBJECT-TYPE 
    SYNTAX  INTEGER (1..16)
    ACCESS  read-write 
    STATUS  mandatory 
    DESCRIPTION 
        "The number of cookie search response count."
    ::= { slbNewCfgVirtualServerEntry 15}

slbNewCfgVirtServerCExpire OBJECT-TYPE 
    SYNTAX  DisplayString (SIZE(0..20))
    ACCESS  read-write 
    STATUS  mandatory 
    DESCRIPTION 
        "The cookie expire of the virtual server used for insert cookie load
         balance depending on the mode it has the following format 
         <MM/dd/yy[@hh:mm]> absolute mode or <days[:hours[:minutes]]>
         for relative mode."  
    ::= { slbNewCfgVirtualServerEntry 16 }


-- Server load balancing - Virtual Services Table 
slbVirtServicesTableMaxSize OBJECT-TYPE
    SYNTAX  INTEGER 
    ACCESS  read-only 
    STATUS  mandatory 
    DESCRIPTION 
        "The maximum number of entries in SLB Virtual Services Table." 
    ::= { serverloadbalance 55 }

slbCurCfgVirtServicesTable OBJECT-TYPE
    SYNTAX  SEQUENCE OF SlbCurCfgVirtServicesEntry
    ACCESS  not-accessible
    STATUS  mandatory
    DESCRIPTION
        "The table of virtual services."
    ::= { serverloadbalance 7 }

slbCurCfgVirtServicesEntry OBJECT-TYPE
    SYNTAX  SlbCurCfgVirtServicesEntry
    ACCESS  not-accessible
    STATUS  mandatory
    DESCRIPTION
        "A row in the virtual services table."
    INDEX   { slbCurCfgVirtServIndex, slbCurCfgVirtServiceIndex }
    ::= { slbCurCfgVirtServicesTable 1 }

SlbCurCfgVirtServicesEntry ::= SEQUENCE {
    slbCurCfgVirtServIndex            INTEGER,
    slbCurCfgVirtServiceIndex         INTEGER,
    slbCurCfgVirtServiceVirtPort      INTEGER,
    slbCurCfgVirtServiceRealGroup     INTEGER,
    slbCurCfgVirtServiceRealPort      INTEGER,
    slbCurCfgVirtServiceUDPBalance    INTEGER,
    slbCurCfgVirtServiceCookieMode    INTEGER,
    slbCurCfgVirtServicePBind         INTEGER,
    slbCurCfgVirtServiceHname         DisplayString,
    slbCurCfgVirtServiceHttpSlb       INTEGER,
    slbCurCfgVirtServiceHttpSlbOption INTEGER,
    slbCurCfgVirtServiceHttpSlb2      INTEGER,
    slbCurCfgVirtServiceBwmContract   INTEGER,
    slbCurCfgVirtServiceDirServerRtn  INTEGER,
    slbCurCfgVirtServiceRtspUrlParse  INTEGER,
    slbCurCfgVirtServiceDBind         INTEGER,
    slbCurCfgVirtServiceFtpParsing    INTEGER,
    slbCurCfgVirtServiceRemapUDPFrags INTEGER,
    slbCurCfgVirtServiceDnsSlb        INTEGER
    }

slbCurCfgVirtServIndex OBJECT-TYPE
    SYNTAX  INTEGER
    ACCESS  read-only
    STATUS  mandatory
    DESCRIPTION
        "The number of the virtual server." 
    ::= { slbCurCfgVirtServicesEntry 1 }

slbCurCfgVirtServiceIndex OBJECT-TYPE 
    SYNTAX  INTEGER 
    ACCESS  read-only 
    STATUS  mandatory 
    DESCRIPTION 
        "The service index. This has no external meaning" 
    ::= { slbCurCfgVirtServicesEntry 2 }

slbCurCfgVirtServiceVirtPort OBJECT-TYPE  
    SYNTAX  INTEGER (2..65534)
    ACCESS  read-only  
    STATUS  mandatory  
    DESCRIPTION 
        "The layer4 virtual port number of the service."  
    ::= { slbCurCfgVirtServicesEntry 3 } 

slbCurCfgVirtServiceRealGroup OBJECT-TYPE   
    SYNTAX  INTEGER   
    ACCESS  read-only   
    STATUS  mandatory   
    DESCRIPTION 
        "The real server group number for this service."   
    ::= { slbCurCfgVirtServicesEntry 4 }

slbCurCfgVirtServiceRealPort OBJECT-TYPE   
    SYNTAX  INTEGER (0..65534)
    ACCESS  read-only   
    STATUS  mandatory   
    DESCRIPTION 
        "The layer4 real port number of the service."   
    ::= { slbCurCfgVirtServicesEntry 5 }

slbCurCfgVirtServiceUDPBalance OBJECT-TYPE   
    SYNTAX  INTEGER    {
	enabled(2),
	disabled(3),
	stateless(4)
	}
    ACCESS  read-only   
    STATUS  mandatory   
    DESCRIPTION 
        "Enable, disable or stateless the UDP balancing for the virtual port."
    ::= { slbCurCfgVirtServicesEntry 6 }

slbCurCfgVirtServicePBind OBJECT-TYPE   
    SYNTAX  INTEGER {
	enabled(2),
	disabled(3),
	sessid(4),
        cookie(5)
        }
    ACCESS  read-only   
    STATUS  mandatory   
    DESCRIPTION 
        "Enable or disable persistent bindings for the virtual port."   
    ::= { slbCurCfgVirtServicesEntry 7 }

slbCurCfgVirtServiceHname OBJECT-TYPE 
    SYNTAX  DisplayString (SIZE(0..9))
    ACCESS  read-only 
    STATUS  mandatory 
    DESCRIPTION 
        "The host name of the virtual service."  
    ::= { slbCurCfgVirtServicesEntry 8 }

slbCurCfgVirtServiceHttpSlb OBJECT-TYPE   
    SYNTAX  INTEGER {
	disabled(1),
	urlslb(2),
        urlhash(3),
        cookie(4),
        host(5),
        browser(6),
        others(7),
        headerhash(8) 
	}
    ACCESS  read-only   
    STATUS  mandatory   
    DESCRIPTION 
        "Select HTTP server loadbalancing for the virtual port."   
    ::= { slbCurCfgVirtServicesEntry 9 }

slbCurCfgVirtServiceHttpSlbOption OBJECT-TYPE   
    SYNTAX  INTEGER {
	and(1),
	or(2),
        none(3)
	}
    ACCESS  read-only   
    STATUS  mandatory   
    DESCRIPTION 
        "Select HTTP server loadbalancing option for the virtual port."   
    ::= { slbCurCfgVirtServicesEntry 16 }

slbCurCfgVirtServiceHttpSlb2 OBJECT-TYPE   
    SYNTAX  INTEGER {
	disabled(1),
	urlslb(2),
        urlhash(3),
        cookie(4),
        host(5),
        browser(6),
        others(7),
        headerhash(8) 
	}
    ACCESS  read-only   
    STATUS  mandatory   
    DESCRIPTION 
        "Select HTTP server loadbalancing for the virtual port."   
    ::= { slbCurCfgVirtServicesEntry 17 }

slbCurCfgVirtServiceBwmContract OBJECT-TYPE   
    SYNTAX  INTEGER   
    ACCESS  read-only   
    STATUS  mandatory   
    DESCRIPTION 
        "The BWM contract number for this service."   
    ::= { slbCurCfgVirtServicesEntry 10 }

slbCurCfgVirtServiceDirServerRtn OBJECT-TYPE   
    SYNTAX  INTEGER {
	enabled(1),
	disabled(2)
	}
    ACCESS  read-only   
    STATUS  mandatory   
    DESCRIPTION 
        "Enable or disable direct server return feature. To translate only 
         MAC addresses in performing server load balancing when enabled.
         This allow servers to return directly to client since IP addresses 
         have not been changed."
    ::= { slbCurCfgVirtServicesEntry 11 }

slbCurCfgVirtServiceRtspUrlParse OBJECT-TYPE   
    SYNTAX  INTEGER {
	disabled(2),
        hash(3),
        patternMatch(4)
	}
    ACCESS  read-only   
    STATUS  mandatory   
    DESCRIPTION 
        "Enable or disable RTSP URL hashing."
    ::= { slbCurCfgVirtServicesEntry 12 }

slbCurCfgVirtServiceDBind OBJECT-TYPE   
    SYNTAX  INTEGER {
	enabled(1),
	disabled(2)
	}
    ACCESS  read-only   
    STATUS  mandatory   
    DESCRIPTION 
        "Enable or disable Delayed Binding."
    ::= { slbCurCfgVirtServicesEntry 14 }

slbCurCfgVirtServiceCookieMode OBJECT-TYPE   
    SYNTAX INTEGER {
        rewrite(1),
        passive(2),
	insert(3),
	disabled(4)
        }
    ACCESS read-only 
    STATUS mandatory   
    DESCRIPTION 
        "Select cookie persistance mode."
    ::= { slbCurCfgVirtServicesEntry 13 }

slbCurCfgVirtServiceFtpParsing OBJECT-TYPE
    SYNTAX  INTEGER {
	enabled(1),
	disabled(2)
	}
    ACCESS  read-only
    STATUS  mandatory
    DESCRIPTION
       "Enable or Disable the ftp parsing for the virtual service."
    ::= { slbCurCfgVirtServicesEntry 15 }

slbCurCfgVirtServiceRemapUDPFrags OBJECT-TYPE   
    SYNTAX INTEGER {
        enabled(1),
        disabled(2)
        }
    ACCESS read-only   
    STATUS mandatory   
    DESCRIPTION 
        "Enable or disable remapping UDP server fragments"   
    ::= { slbCurCfgVirtServicesEntry 18 }

slbCurCfgVirtServiceDnsSlb OBJECT-TYPE   
    SYNTAX  INTEGER {
        enabled(1),
	disabled(2)
	}
    ACCESS  read-only   
    STATUS  mandatory   
    DESCRIPTION 
        "Enable or disable DNS query load balancing."
    ::= { slbCurCfgVirtServicesEntry 19 }

-- Server load balancing - Virtual Services Table 

slbNewCfgVirtServicesTable OBJECT-TYPE
    SYNTAX  SEQUENCE OF SlbNewCfgVirtServicesEntry
    ACCESS  not-accessible
    STATUS  mandatory
    DESCRIPTION
        "The table of virtual Services."
    ::= { serverloadbalance 8 }

slbNewCfgVirtServicesEntry OBJECT-TYPE
    SYNTAX  SlbNewCfgVirtServicesEntry
    ACCESS  not-accessible
    STATUS  mandatory
    DESCRIPTION
        "A row in the virtual services table."
    INDEX   { slbNewCfgVirtServIndex, slbNewCfgVirtServiceIndex }
    ::= { slbNewCfgVirtServicesTable 1 }

SlbNewCfgVirtServicesEntry ::= SEQUENCE {
    slbNewCfgVirtServIndex            INTEGER,
    slbNewCfgVirtServiceIndex         INTEGER,
    slbNewCfgVirtServiceVirtPort      INTEGER,
    slbNewCfgVirtServiceRealGroup     INTEGER,
    slbNewCfgVirtServiceRealPort      INTEGER,
    slbNewCfgVirtServiceUDPBalance    INTEGER,
    slbNewCfgVirtServicePBind         INTEGER,
    slbNewCfgVirtServiceCookieMode    INTEGER,
    slbNewCfgVirtServiceHname         DisplayString,
    slbNewCfgVirtServiceHttpSlb       INTEGER,
    slbNewCfgVirtServiceHttpSlbOption INTEGER,
    slbNewCfgVirtServiceHttpSlb2      INTEGER,
    slbNewCfgVirtServiceBwmContract   INTEGER,
    slbNewCfgVirtServiceDirServerRtn  INTEGER,
    slbNewCfgVirtServiceDelete        INTEGER,
    slbNewCfgVirtServiceRtspUrlParse  INTEGER,
    slbNewCfgVirtServiceDBind         INTEGER,
    slbNewCfgVirtServiceFtpParsing    INTEGER,
    slbNewCfgVirtServiceRemapUDPFrags INTEGER,
    slbNewCfgVirtServiceDnsSlb        INTEGER
    }

slbNewCfgVirtServIndex OBJECT-TYPE
    SYNTAX  INTEGER
    ACCESS  read-only
    STATUS  mandatory
    DESCRIPTION
        "The number of the virtual server." 
    ::= { slbNewCfgVirtServicesEntry 1 }

slbNewCfgVirtServiceIndex OBJECT-TYPE 
    SYNTAX  INTEGER 
    ACCESS  read-only 
    STATUS  mandatory 
    DESCRIPTION 
        "The service index. This has no external meaning" 
    ::= { slbNewCfgVirtServicesEntry 2 }

slbNewCfgVirtServiceVirtPort OBJECT-TYPE  
    SYNTAX  INTEGER (2..65534)
    ACCESS  read-write  
    STATUS  mandatory  
    DESCRIPTION 
        "The layer4 virtual port number of the service."  
    ::= { slbNewCfgVirtServicesEntry 3 } 

slbNewCfgVirtServiceRealGroup OBJECT-TYPE   
    SYNTAX  INTEGER   
    ACCESS  read-write   
    STATUS  mandatory   
    DESCRIPTION 
        "The real server group number for this service."   
    ::= { slbNewCfgVirtServicesEntry 4 }

slbNewCfgVirtServiceRealPort OBJECT-TYPE   
    SYNTAX  INTEGER (0..65534)
    ACCESS  read-write   
    STATUS  mandatory   
    DESCRIPTION 
        "The layer4 real port number of the service."   
    ::= { slbNewCfgVirtServicesEntry 5 }

slbNewCfgVirtServiceUDPBalance OBJECT-TYPE   
    SYNTAX  INTEGER    {
	enabled(2),
	disabled(3),
	stateless(4)
	}
    ACCESS  read-write   
    STATUS  mandatory   
    DESCRIPTION 
        "Enable, disable or stateless the UDP balancing for the virtual port."
    ::= { slbNewCfgVirtServicesEntry 6 }

slbNewCfgVirtServicePBind OBJECT-TYPE   
    SYNTAX  INTEGER {
	enabled(2),
	disabled(3),
	sessid(4),
        cookie(5)
	}
    ACCESS  read-write   
    STATUS  mandatory   
    DESCRIPTION 
        "Enable or disable persistent bindings for the virtual port."
    ::= { slbNewCfgVirtServicesEntry 7 }

slbNewCfgVirtServiceHname OBJECT-TYPE 
    SYNTAX  DisplayString (SIZE(0..9))
    ACCESS  read-write 
    STATUS  mandatory 
    DESCRIPTION 
        "The host name of the virtual service."  
    ::= { slbNewCfgVirtServicesEntry 8 }

slbNewCfgVirtServiceHttpSlb OBJECT-TYPE   
    SYNTAX  INTEGER {
	disabled(1),
        urlslb(2),
        urlhash(3),
        cookie(4),
        host(5),
        browser(6),
        others(7),
        headerhash(8) 
	}
    ACCESS  read-write   
    STATUS  mandatory   
    DESCRIPTION 
        "Select HTTP server loadbalancing for the virtual port."   
    ::= { slbNewCfgVirtServicesEntry 9 }

slbNewCfgVirtServiceHttpSlbOption OBJECT-TYPE   
    SYNTAX  INTEGER {
	and(1),
        or(2),
        none(3)
	}
    ACCESS  read-write   
    STATUS  mandatory   
    DESCRIPTION 
        "Select HTTP server loadbalancing for the virtual port."   
    ::= { slbNewCfgVirtServicesEntry 17 }

slbNewCfgVirtServiceHttpSlb2 OBJECT-TYPE   
    SYNTAX  INTEGER {
	disabled(1),
        urlslb(2),
        urlhash(3),
        cookie(4),
        host(5),
        browser(6),
        others(7),
        headerhash(8) 
	}
    ACCESS  read-write   
    STATUS  mandatory   
    DESCRIPTION 
        "Select HTTP server loadbalancing for the virtual port."   
    ::= { slbNewCfgVirtServicesEntry 18 }

slbNewCfgVirtServiceBwmContract OBJECT-TYPE   
    SYNTAX  INTEGER   
    ACCESS  read-write
    STATUS  mandatory   
    DESCRIPTION 
        "The BWM contract number for this service."   
    ::= { slbNewCfgVirtServicesEntry 10 }

slbNewCfgVirtServiceDirServerRtn OBJECT-TYPE
    SYNTAX  INTEGER {
        enabled(1),
        disabled(2)
        }
    ACCESS  read-write
    STATUS  mandatory   
    DESCRIPTION 
        "Enable or disable direct server return feature. To translate only 
         MAC addresses in performing server load balancing when enabled.  
         This allow servers to return directly to client since IP addresses 
         have not been changed."
    ::= { slbNewCfgVirtServicesEntry 11 }

slbNewCfgVirtServiceDelete OBJECT-TYPE
    SYNTAX  INTEGER {
        other(1),
        delete(2)
        }
    ACCESS  read-write
    STATUS  mandatory
    DESCRIPTION
        "When set to the value of 2 (delete), the entire row is deleted. 
         When read, other(1) is returned. Setting the value to anything 
         other than 2(delete) has no effect on the state of the row."
    ::= { slbNewCfgVirtServicesEntry 12 }

slbNewCfgVirtServiceRtspUrlParse OBJECT-TYPE   
    SYNTAX  INTEGER {
	disabled(2),
        hash(3),
        patternMatch(4)
	}
    ACCESS  read-write
    STATUS  mandatory   
    DESCRIPTION 
        "Enable or disable RTSP URL hashing."
    ::= { slbNewCfgVirtServicesEntry 13 }

slbNewCfgVirtServiceDBind OBJECT-TYPE   
    SYNTAX  INTEGER {
	enabled(1),
	disabled(2)
	}
    ACCESS  read-write
    STATUS  mandatory   
    DESCRIPTION 
        "Enable or disable Delayed Binding."
    ::= { slbNewCfgVirtServicesEntry 15 }

slbNewCfgVirtServiceCookieMode OBJECT-TYPE   
    SYNTAX INTEGER {
        rewrite(1),
        passive(2),
	insert(3),
	disabled(4)
        }
    ACCESS read-write 
    STATUS mandatory   
    DESCRIPTION 
        "Select cookie persistance mode."
    ::= { slbNewCfgVirtServicesEntry 14 }

slbNewCfgVirtServiceFtpParsing OBJECT-TYPE
    SYNTAX  INTEGER {
	enabled(1),
	disabled(2)
	}
    ACCESS  read-write
    STATUS  mandatory
    DESCRIPTION
        "Enable or Disable the ftp parsing for the virtual service."
    ::= { slbNewCfgVirtServicesEntry 16 }

slbNewCfgVirtServiceRemapUDPFrags OBJECT-TYPE   
    SYNTAX INTEGER {
        enabled(1),
        disabled(2)
        }
    ACCESS read-write   
    STATUS mandatory   
    DESCRIPTION 
        "Enable or disable remapping UDP server fragments"   
    ::= { slbNewCfgVirtServicesEntry 19 }

slbNewCfgVirtServiceDnsSlb OBJECT-TYPE   
    SYNTAX  INTEGER {
        enabled(1),
	disabled(2)
	}
    ACCESS  read-write   
    STATUS  mandatory   
    DESCRIPTION 
        "Enable or disable DNS query load balancing."
    ::= { slbNewCfgVirtServicesEntry 20 }

-- URL based BWM table for Virtual Services

slbUrlBwmTableMaxSize OBJECT-TYPE
    SYNTAX  INTEGER 
    ACCESS  read-only 
    STATUS  mandatory 
    DESCRIPTION 
        "The maximum number of entries in SLB URL BWM Table." 
    ::= { serverloadbalance 56 }

slbCurCfgUrlBwmTable OBJECT-TYPE
    SYNTAX  SEQUENCE OF SlbCurCfgUrlBwmEntry
    ACCESS  not-accessible
    STATUS  mandatory
    DESCRIPTION
        "The table of URL based BWM for Virtual Services."
    ::= { serverloadbalance 50 }

slbCurCfgUrlBwmEntry OBJECT-TYPE
    SYNTAX  SlbCurCfgUrlBwmEntry
    ACCESS  not-accessible
    STATUS  mandatory
    DESCRIPTION
        "A row in the URL based BWM virtual services table."
    INDEX   { slbCurCfgUrlBwmVirtServIndex, 
              slbCurCfgUrlBwmVirtServiceIndex, 
              slbCurCfgUrlBwmUrlId }
    ::= { slbCurCfgUrlBwmTable 1 }

SlbCurCfgUrlBwmEntry ::= SEQUENCE {
    slbCurCfgUrlBwmVirtServIndex     INTEGER,
    slbCurCfgUrlBwmVirtServiceIndex  INTEGER,
    slbCurCfgUrlBwmUrlId             INTEGER,
    slbCurCfgUrlBwmContract          INTEGER
    }

slbCurCfgUrlBwmVirtServIndex OBJECT-TYPE
    SYNTAX  INTEGER
    ACCESS  read-only
    STATUS  mandatory
    DESCRIPTION
        "The number of the virtual server." 
    ::= { slbCurCfgUrlBwmEntry 1 }

slbCurCfgUrlBwmVirtServiceIndex OBJECT-TYPE 
    SYNTAX  INTEGER 
    ACCESS  read-only 
    STATUS  mandatory 
    DESCRIPTION 
        "The service index. This has no external meaning" 
    ::= { slbCurCfgUrlBwmEntry 2 }

slbCurCfgUrlBwmUrlId OBJECT-TYPE  
    SYNTAX  INTEGER  
    ACCESS  read-only  
    STATUS  mandatory  
    DESCRIPTION 
        "The URL Path Identifier."  
    ::= { slbCurCfgUrlBwmEntry 3 } 

slbCurCfgUrlBwmContract OBJECT-TYPE  
    SYNTAX  INTEGER  
    ACCESS  read-only  
    STATUS  mandatory  
    DESCRIPTION 
        "The BW contract number."  
    ::= { slbCurCfgUrlBwmEntry 4 } 

slbNewCfgUrlBwmTable OBJECT-TYPE
    SYNTAX  SEQUENCE OF SlbNewCfgUrlBwmEntry
    ACCESS  not-accessible
    STATUS  mandatory
    DESCRIPTION
        "The table of URL based BWM for Virtual Services."
    ::= { serverloadbalance 51 }

slbNewCfgUrlBwmEntry OBJECT-TYPE
    SYNTAX  SlbNewCfgUrlBwmEntry
    ACCESS  not-accessible
    STATUS  mandatory
    DESCRIPTION
        "A row in the URL based BWM virtual services table."
    INDEX   { slbNewCfgUrlBwmVirtServIndex, 
              slbNewCfgUrlBwmVirtServiceIndex, 
              slbNewCfgUrlBwmUrlId }
    ::= { slbNewCfgUrlBwmTable 1 }

SlbNewCfgUrlBwmEntry ::= SEQUENCE {
    slbNewCfgUrlBwmVirtServIndex     INTEGER,
    slbNewCfgUrlBwmVirtServiceIndex  INTEGER,
    slbNewCfgUrlBwmUrlId             INTEGER,
    slbNewCfgUrlBwmContract          INTEGER,
    slbNewCfgUrlBwmDelete            INTEGER
    }

slbNewCfgUrlBwmVirtServIndex OBJECT-TYPE
    SYNTAX  INTEGER
    ACCESS  read-only
    STATUS  mandatory
    DESCRIPTION
        "The number of the virtual server." 
    ::= { slbNewCfgUrlBwmEntry 1 }

slbNewCfgUrlBwmVirtServiceIndex OBJECT-TYPE 
    SYNTAX  INTEGER 
    ACCESS  read-only 
    STATUS  mandatory 
    DESCRIPTION 
        "The service index. This has no external meaning" 
    ::= { slbNewCfgUrlBwmEntry 2 }

slbNewCfgUrlBwmUrlId OBJECT-TYPE  
    SYNTAX  INTEGER  
    ACCESS  read-only  
    STATUS  mandatory  
    DESCRIPTION 
        "The URL Path Identifier."  
    ::= { slbNewCfgUrlBwmEntry 3 } 

slbNewCfgUrlBwmContract OBJECT-TYPE  
    SYNTAX  INTEGER  
    ACCESS  read-write  
    STATUS  mandatory  
    DESCRIPTION 
        "The BW contract number."
    ::= { slbNewCfgUrlBwmEntry 4 } 

slbNewCfgUrlBwmDelete OBJECT-TYPE
    SYNTAX  INTEGER {
        other(1),
        delete(2)
       }
    ACCESS  read-write
    STATUS  mandatory
    DESCRIPTION
        "When set to the value of 2 (delete), the entire row is deleted. 
         When read, other(1) is returned. Setting the value to anything 
         other than 2(delete) has no effect on the state of the row."
    ::= { slbNewCfgUrlBwmEntry 5 }

-- Server load balancing - Group Table

slbGroupTableMaxSize OBJECT-TYPE
    SYNTAX  INTEGER
    ACCESS  read-only
    STATUS  mandatory
    DESCRIPTION
        "The maximum number of entries in slbCurCfgGroupTable."
    ::= { serverloadbalance 9 }

slbCurCfgGroupTable OBJECT-TYPE
    SYNTAX  SEQUENCE OF SlbCurCfgGroupEntry
    ACCESS  not-accessible
    STATUS  mandatory
    DESCRIPTION
        "The table of groups"
    ::= { serverloadbalance 10 }

slbCurCfgGroupEntry OBJECT-TYPE
    SYNTAX  SlbCurCfgGroupEntry
    ACCESS  not-accessible
    STATUS  mandatory
    DESCRIPTION
        "A row in the slbCurCfgGroupTable "
    INDEX   { slbCurCfgGroupIndex }
    ::= { slbCurCfgGroupTable 1 }

SlbCurCfgGroupEntry ::= SEQUENCE {
    slbCurCfgGroupIndex            INTEGER,
    slbCurCfgGroupRealServers      OCTET STRING,
    slbCurCfgGroupMetric           INTEGER,
    slbCurCfgGroupBackupServer     INTEGER,
    slbCurCfgGroupHealthCheckUrl   DisplayString,
    slbCurCfgGroupHealthCheckLayer INTEGER,
    slbCurCfgGroupName             DisplayString,
    slbCurCfgGroupRealThreshold    INTEGER,
    slbCurCfgGroupBackupGroup      INTEGER,
    slbCurCfgGroupVipHealthCheck   INTEGER
    }

slbCurCfgGroupIndex OBJECT-TYPE
    SYNTAX  INTEGER
    ACCESS  read-only
    STATUS  mandatory
    DESCRIPTION
        "The group number for which the information pertains."
    ::= { slbCurCfgGroupEntry 1 }

slbCurCfgGroupRealServers    OBJECT-TYPE
    SYNTAX  OCTET STRING (SIZE(0..64))
    ACCESS  read-only
    STATUS  mandatory
    DESCRIPTION
        "The Real servers in the group. The servers are presented in 
         bitmap format.

         in receiving order:

             OCTET 1  OCTET 2  .....
             xxxxxxxx xxxxxxxx ..... 
             |     || |_ server 9
             |     ||  
             |     ||___ server 8
             |     |____ server 7
             |       .    .   .
             |__________ server 1
 
         where x : 1 - The represented server belongs to the group
                   0 - The represented server does not belong to the group"
    ::= { slbCurCfgGroupEntry 2 }

slbCurCfgGroupMetric OBJECT-TYPE
    SYNTAX  INTEGER {
	roundRobin(1),
	leastConnections(2),
	minMisses(3),
	hash(4),
	response(5),
	bandwidth(6)
	}
    ACCESS  read-only
    STATUS  mandatory
    DESCRIPTION
        "The metric used to select next server in group."
    ::= { slbCurCfgGroupEntry 3 }

slbCurCfgGroupBackupServer OBJECT-TYPE
    SYNTAX INTEGER
    ACCESS  read-only
    STATUS  mandatory
    DESCRIPTION
        "The backup real server for this group."
    ::= { slbCurCfgGroupEntry 4 }

slbCurCfgGroupHealthCheckUrl OBJECT-TYPE
    SYNTAX  DisplayString (SIZE(0..31))
    ACCESS  read-only
    STATUS  mandatory
    DESCRIPTION
        "The specific content which is examined during health checks.
         The content depends on the type of health check."
    ::= { slbCurCfgGroupEntry 5 }

slbCurCfgGroupHealthCheckLayer OBJECT-TYPE
    SYNTAX  INTEGER {
	icmp(1),
	tcp(2),
	http(3),
	dns(4),
	smtp(5),
	pop3(6),
	nntp(7),
	ftp(8),
	imap(9),
	radius(10),
	sslh(11),
	script1(12),
	script2(13),
	script3(14),
	script4(15),
	script5(16),
	script6(17),
	script7(18),
	script8(19),
	script9(20),
	script10(21),
	script11(22),
	script12(23),
	script13(24),
	script14(25),
	script15(26),
	script16(27),
	link(28),
	wsp(29),
	wtls(30),
	ldap(31),
	udpdns(32),
	arp(33)
	}
    ACCESS  read-only
    STATUS  mandatory
    DESCRIPTION
        "The OSI layer at which servers are health checked."
    ::= { slbCurCfgGroupEntry 6 }

slbCurCfgGroupName OBJECT-TYPE 
    SYNTAX  DisplayString (SIZE(0..31))
    ACCESS  read-only 
    STATUS  mandatory 
    DESCRIPTION 
        "The name of the real server group."  
    ::= { slbCurCfgGroupEntry 7 }

slbCurCfgGroupRealThreshold OBJECT-TYPE 
    SYNTAX  INTEGER (0..15)
    ACCESS  read-only 
    STATUS  mandatory 
    DESCRIPTION 
        "The server failure syslog threshold of the real server group."  
    ::= { slbCurCfgGroupEntry 8 }

slbCurCfgGroupBackupGroup OBJECT-TYPE
    SYNTAX  INTEGER
    ACCESS  read-only
    STATUS  mandatory
    DESCRIPTION
        "The backup real server group for this group."
    ::= { slbCurCfgGroupEntry 9 }

slbCurCfgGroupVipHealthCheck OBJECT-TYPE
    SYNTAX  INTEGER {
	enabled(1),
	disabled(2)
	}
    ACCESS  read-only
    STATUS  mandatory
    DESCRIPTION
        "Enable or disable VIP health checking in DSR mode." 
    ::= { slbCurCfgGroupEntry 10 }

-- Server load balancing - Group Table - New Configuration
slbNewCfgGroupTable OBJECT-TYPE
    SYNTAX  SEQUENCE OF SlbNewCfgGroupEntry
    ACCESS  not-accessible
    STATUS  mandatory
    DESCRIPTION
        "The table of groups"
    ::= { serverloadbalance 11 }

slbNewCfgGroupEntry OBJECT-TYPE
    SYNTAX  SlbNewCfgGroupEntry
    ACCESS  not-accessible
    STATUS  mandatory
    DESCRIPTION
        "A row in the slbNewCfgGroupTable "
    INDEX   { slbNewCfgGroupIndex }
    ::= { slbNewCfgGroupTable 1 }

SlbNewCfgGroupEntry ::= SEQUENCE {
    slbNewCfgGroupIndex            INTEGER,
    slbNewCfgGroupRealServers      OCTET STRING,
    slbNewCfgGroupAddServer        INTEGER,
    slbNewCfgGroupRemoveServer     INTEGER,
    slbNewCfgGroupMetric           INTEGER,
    slbNewCfgGroupBackupServer     INTEGER,
    slbNewCfgGroupDelete     	   INTEGER,
    slbNewCfgGroupHealthCheckUrl   DisplayString,
    slbNewCfgGroupHealthCheckLayer INTEGER,
    slbNewCfgGroupName             DisplayString,
    slbNewCfgGroupRealThreshold	   INTEGER,
    slbNewCfgGroupBackupGroup	   INTEGER,
    slbNewCfgGroupVipHealthCheck   INTEGER
    }

slbNewCfgGroupIndex OBJECT-TYPE
    SYNTAX  INTEGER
    ACCESS  read-only
    STATUS  mandatory
    DESCRIPTION
        "The group number for which the information pertains."
    ::= { slbNewCfgGroupEntry 1 }

slbNewCfgGroupRealServers    OBJECT-TYPE
    SYNTAX  OCTET STRING (SIZE(0..64))
    ACCESS  read-only
    STATUS  mandatory
    DESCRIPTION
        "The Real servers in the group.  The servers are presented
         in bitmap format.

         in receiving order:

             OCTET 1  OCTET 2  .....
             xxxxxxxx xxxxxxxx ..... 
             |     || |_ server 9
             |     ||  
             |     ||___ server 8
             |     |____ server 7
             |       .    .   .
             |__________ server 1
 
         where x : 1 - The represented server belongs to the group
                   0 - The represented server does not belong to the group"
    ::= { slbNewCfgGroupEntry 2 }

slbNewCfgGroupAddServer OBJECT-TYPE
    SYNTAX  INTEGER
    ACCESS  read-write
    STATUS  mandatory
    DESCRIPTION
        "The real server to be added to the group. When read, 0 is returned."
    ::= { slbNewCfgGroupEntry 3 }

slbNewCfgGroupRemoveServer OBJECT-TYPE 
    SYNTAX  INTEGER 
    ACCESS  read-write 
    STATUS  mandatory
    DESCRIPTION
        "The real server to be removed from the group. When read, 
         0 is returned."
    ::= { slbNewCfgGroupEntry 4 }

slbNewCfgGroupMetric OBJECT-TYPE
    SYNTAX  INTEGER {  
	roundRobin(1),
	leastConnections(2),
	minMisses(3),
	hash(4),
	response(5),
	bandwidth(6)
        }
    ACCESS  read-write
    STATUS  mandatory
    DESCRIPTION
        "The metric used to select next server in group."
    ::= { slbNewCfgGroupEntry 5 }

slbNewCfgGroupBackupServer OBJECT-TYPE
    SYNTAX  INTEGER
    ACCESS  read-write
    STATUS  mandatory
    DESCRIPTION
        "The backup real server for this group."
    ::= { slbNewCfgGroupEntry 6 }

slbNewCfgGroupDelete OBJECT-TYPE
    SYNTAX  INTEGER {
	other(1),
	delete(2)
	}
    ACCESS  read-write
    STATUS  mandatory
    DESCRIPTION
        "By setting the value to delete(2), the entire group is deleted."
    ::= { slbNewCfgGroupEntry 7 }

slbNewCfgGroupHealthCheckUrl OBJECT-TYPE
    SYNTAX  DisplayString (SIZE(0..31))
    ACCESS  read-write
    STATUS  mandatory
    DESCRIPTION
        "The specific content which is examined during health checks.
         The content depends on the type of health check."
    ::= { slbNewCfgGroupEntry 8 }

slbNewCfgGroupHealthCheckLayer OBJECT-TYPE
    SYNTAX  INTEGER {
	icmp(1),
	tcp(2),
	http(3),
	dns(4),
	smtp(5),
	pop3(6),
	nntp(7),
	ftp(8),
	imap(9),
	radius(10),
	sslh(11),
	script1(12),
	script2(13),
	script3(14),
	script4(15),
	script5(16),
	script6(17),
	script7(18),
	script8(19),
	script9(20),
	script10(21),
	script11(22),
	script12(23),
	script13(24),
	script14(25),
	script15(26),
	script16(27),
	link(28),
	wsp(29),
	wtls(30),
	ldap(31),
	udpdns(32),
	arp(33)
	}
    ACCESS  read-write
    STATUS  mandatory
    DESCRIPTION
        "The OSI layer at which servers are health checked."
    ::= { slbNewCfgGroupEntry 9 }

slbNewCfgGroupName OBJECT-TYPE 
    SYNTAX  DisplayString (SIZE(0..31))
    ACCESS  read-write 
    STATUS  mandatory 
    DESCRIPTION 
        "The name of the real server group."  
    ::= { slbNewCfgGroupEntry 10 }

slbNewCfgGroupRealThreshold OBJECT-TYPE 
    SYNTAX  INTEGER (0..15)
    ACCESS  read-write 
    STATUS  mandatory 
    DESCRIPTION 
        "The server failure syslog threshold of the real server group."  
    ::= { slbNewCfgGroupEntry 11 }

slbNewCfgGroupBackupGroup OBJECT-TYPE
    SYNTAX  INTEGER
    ACCESS  read-write
    STATUS  mandatory
    DESCRIPTION
        "The backup real server group for this group."
    ::= { slbNewCfgGroupEntry 12 }

slbNewCfgGroupVipHealthCheck OBJECT-TYPE
    SYNTAX  INTEGER {
	enabled(1),
	disabled(2)
	}
    ACCESS  read-write
    STATUS  mandatory
    DESCRIPTION
        "Enable or disable VIP health checking in DSR mode." 
    ::= { slbNewCfgGroupEntry 13 }

-- Server load balancing - slb port state table

slbPortTableMaxSize OBJECT-TYPE
    SYNTAX  INTEGER 
    ACCESS  read-only 
    STATUS  mandatory 
    DESCRIPTION 
                "The maximum number of entries in SLB Port Table." 
    ::= { serverloadbalance 54 }

slbCurCfgPortTable OBJECT-TYPE
    SYNTAX  SEQUENCE OF SlbCurCfgPortEntry
    ACCESS  not-accessible
    STATUS  mandatory
    DESCRIPTION
                "The table of ports and their SLB states"
    ::= { serverloadbalance 12 }

slbCurCfgPortEntry OBJECT-TYPE
    SYNTAX  SlbCurCfgPortEntry
    ACCESS  not-accessible
    STATUS  mandatory
    DESCRIPTION
        "A row in the slbPortTable "
    INDEX   { slbCurCfgPortIndex }
    ::= { slbCurCfgPortTable 1 }

SlbCurCfgPortEntry ::= SEQUENCE {
    slbCurCfgPortIndex              INTEGER,
    slbCurCfgPortProxyIpAddr        IpAddress,
    slbCurCfgPortSlbState           INTEGER,
    slbCurCfgPortSlbHotStandby      INTEGER,
    slbCurCfgPortSlbInterSwitch     INTEGER,
    slbCurCfgPortSlbPipState        INTEGER,
    slbCurCfgPortSlbRtsState        INTEGER,
    slbCurCfgPortSlbIdslbState      INTEGER,
    slbCurCfgPortSlbNasaState       INTEGER
    }

slbCurCfgPortIndex OBJECT-TYPE
    SYNTAX  INTEGER
    ACCESS  read-only
    STATUS  mandatory
    DESCRIPTION
        "The port number for which the SLB information pertains." 
    ::= { slbCurCfgPortEntry 1 }

slbCurCfgPortProxyIpAddr OBJECT-TYPE
    SYNTAX  IpAddress
    ACCESS  read-only 
    STATUS  mandatory
    DESCRIPTION
        "The proxy IP address of the interface."
    ::= { slbCurCfgPortEntry 2 }

slbCurCfgPortSlbState OBJECT-TYPE
    SYNTAX  INTEGER {
	none(1),
	client(2),
	server(3),
	client-server(4)
	}
    ACCESS  read-only
    STATUS  mandatory
    DESCRIPTION
        "The SLB state of the port.
	 none(1)            - not SLB port
	 client(2)          - SLB client port
	 server(3)          - SLB server port
	 client-server(4)   - SLB client and server port"
    ::= { slbCurCfgPortEntry 3 }

slbCurCfgPortSlbHotStandby OBJECT-TYPE
    SYNTAX  INTEGER {
        enabled(1),
        disabled(2)
        }
    ACCESS  read-only
    STATUS  mandatory
    DESCRIPTION
        "Enable or disable hot standby processing on the switch port."
    ::= { slbCurCfgPortEntry 4 }

slbCurCfgPortSlbInterSwitch OBJECT-TYPE
    SYNTAX  INTEGER {
        enabled(1),
        disabled(2)
        }
    ACCESS  read-only
    STATUS  mandatory
    DESCRIPTION
        "Enable or disable inter-switch processing on the switch port."
    ::= { slbCurCfgPortEntry 5 }

slbCurCfgPortSlbPipState OBJECT-TYPE
    SYNTAX  INTEGER {
        enabled(1),
        disabled(2)
        }
    ACCESS  read-only
    STATUS  mandatory
    DESCRIPTION
        "Enable or disable use of proxy IP address on the switch port."
    ::= { slbCurCfgPortEntry 6 }

slbCurCfgPortSlbRtsState OBJECT-TYPE
    SYNTAX  INTEGER   {
        enabled(1),
        disabled(2)
        }
    ACCESS  read-only
    STATUS  mandatory
    DESCRIPTION
        "Enable or disable RTS processing on the switch port."
    ::= { slbCurCfgPortEntry 7 }

slbCurCfgPortSlbIdslbState OBJECT-TYPE
    SYNTAX  INTEGER {
        enabled(1),
        disabled(2)
        }
    ACCESS  read-only
    STATUS  mandatory
    DESCRIPTION
        "Enable or disable Intrusion Detection server load balancing."
    ::= { slbCurCfgPortEntry 8 }

slbCurCfgPortSlbNasaState OBJECT-TYPE
    SYNTAX  INTEGER {
        enabled(1),
        disabled(2)
        }
    ACCESS  read-only
    STATUS  mandatory
    DESCRIPTION
        "Enable or disable NASA base processing."
    ::= { slbCurCfgPortEntry 9 }

-- Server load balancing - slb port state table

slbNewCfgPortTable OBJECT-TYPE
    SYNTAX  SEQUENCE OF SlbNewCfgPortEntry
    ACCESS  not-accessible
    STATUS  mandatory
    DESCRIPTION
        "The table of ports and their SLB states"
    ::= { serverloadbalance 13 }

slbNewCfgPortEntry OBJECT-TYPE
    SYNTAX  SlbNewCfgPortEntry
    ACCESS  not-accessible
    STATUS  mandatory
    DESCRIPTION
        "A row in the slbPortTable "
    INDEX   { slbNewCfgPortIndex }
    ::= { slbNewCfgPortTable 1 }

SlbNewCfgPortEntry ::= SEQUENCE {
    slbNewCfgPortIndex              INTEGER,
    slbNewCfgPortProxyIpAddr        IpAddress,
    slbNewCfgPortSlbState           INTEGER,
    slbNewCfgPortSlbHotStandby      INTEGER,
    slbNewCfgPortSlbInterSwitch     INTEGER,
    slbNewCfgPortSlbPipState        INTEGER,
    slbNewCfgPortSlbRtsState        INTEGER,
    slbNewCfgPortDelete             INTEGER,
    slbNewCfgPortSlbIdslbState      INTEGER,
    slbNewCfgPortSlbNasaState       INTEGER
    }

slbNewCfgPortIndex OBJECT-TYPE
    SYNTAX  INTEGER
    ACCESS  read-only
    STATUS  mandatory
    DESCRIPTION
        "The port number for which the SLB information pertains." 
    ::= { slbNewCfgPortEntry 1 }

slbNewCfgPortProxyIpAddr OBJECT-TYPE 
    SYNTAX  IpAddress 
    ACCESS  read-write 
    STATUS  mandatory 
    DESCRIPTION 
        "The proxy IP address of the interface." 
    ::= { slbNewCfgPortEntry 2 }

slbNewCfgPortSlbState OBJECT-TYPE
    SYNTAX  INTEGER {
	none(1),
	client(2),
	server(3),
	client-server(4)
	}
    ACCESS  read-write
    STATUS  mandatory
    DESCRIPTION
        "The SLB state of the port.
	 none(1)            - not SLB port
	 client(2)          - SLB client port
	 server(3)          - SLB server port
	 client-server(4)   - SLB client and server port"
    ::= { slbNewCfgPortEntry 3 }

slbNewCfgPortSlbHotStandby OBJECT-TYPE
    SYNTAX  INTEGER   {
        enabled(1),
        disabled(2)
        }
    ACCESS  read-write
    STATUS  mandatory
    DESCRIPTION
        "Enable or disable hot standby processing on the switch port."
    ::= { slbNewCfgPortEntry 4 }

slbNewCfgPortSlbInterSwitch OBJECT-TYPE
    SYNTAX  INTEGER   {
        enabled(1),
        disabled(2)
        }
    ACCESS  read-write
    STATUS  mandatory
    DESCRIPTION
        "Enable or disable inter-switch processing on the switch port."
    ::= { slbNewCfgPortEntry 5 }

slbNewCfgPortSlbPipState OBJECT-TYPE
    SYNTAX  INTEGER   {
        enabled(1),
        disabled(2)
        }
    ACCESS  read-write
    STATUS  mandatory
    DESCRIPTION
        "Enable or disable use of proxy IP address on the switch port."
    ::= { slbNewCfgPortEntry 6 }

slbNewCfgPortSlbRtsState OBJECT-TYPE
    SYNTAX  INTEGER   {
        enabled(1),
        disabled(2)
        }
    ACCESS  read-write
    STATUS  mandatory
    DESCRIPTION
        "Enable or disable RTS processing on the switch port."
    ::= { slbNewCfgPortEntry 7 }

slbNewCfgPortDelete OBJECT-TYPE
    SYNTAX INTEGER {
        other(1),
        delete(2)
        }
    ACCESS read-write
    STATUS mandatory
    DESCRIPTION
        "When set to the value of 2 (delete), the entire row is deleted. 
         When read, other(1) is returned. Setting the value to anything 
         other than 2(delete) has no effect on the state of the row."
    ::= { slbNewCfgPortEntry 8 }

slbNewCfgPortSlbIdslbState OBJECT-TYPE
    SYNTAX  INTEGER {
        enabled(1),
        disabled(2)
        }
    ACCESS  read-write
    STATUS  mandatory
    DESCRIPTION
        "Enable or disable Intrusion Detection server load balancing."
    ::= { slbNewCfgPortEntry 9 }

slbNewCfgPortSlbNasaState OBJECT-TYPE
    SYNTAX  INTEGER {
        enabled(1),
        disabled(2)
        }
    ACCESS  read-write
    STATUS  mandatory
    DESCRIPTION
        "Enable or disable NASA base processing."
    ::= { slbNewCfgPortEntry 10 }

slbCurCfgImask OBJECT-TYPE
    SYNTAX  IpAddress
    ACCESS  read-only
    STATUS  mandatory
    DESCRIPTION
        "The virtual and real IP address mask - corresponding to the
	 imask command of the slb configuration menu." 
    ::= { serverloadbalance 14 }

slbNewCfgImask OBJECT-TYPE
    SYNTAX  IpAddress
    ACCESS  read-write
    STATUS  mandatory
    DESCRIPTION
        "The virtual and real IP address mask - corresponding to the
         imask command of the slb configuration menu."
    ::= { serverloadbalance 15 }

slbCurCfgMnet OBJECT-TYPE
    SYNTAX  IpAddress
    ACCESS  read-only
    STATUS  mandatory
    DESCRIPTION
        "The management network - corresponding to the mnet command of 
         the slb configuration menu." 
    ::= { serverloadbalance 19 }

slbNewCfgMnet OBJECT-TYPE
    SYNTAX  IpAddress
    ACCESS  read-write
    STATUS  mandatory
    DESCRIPTION
        "The management network - corresponding to the mnet command of 
         the slb configuration menu." 
    ::= { serverloadbalance 20 }

slbCurCfgMmask OBJECT-TYPE
    SYNTAX  IpAddress
    ACCESS  read-only
    STATUS  mandatory
    DESCRIPTION
        "The management subnet mask - corresponding to the mmask command 
         of the slb configuration menu." 
    ::= { serverloadbalance 21 }

slbNewCfgMmask OBJECT-TYPE
    SYNTAX  IpAddress
    ACCESS  read-write
    STATUS  mandatory
    DESCRIPTION
        "The management subnet mask - corresponding to the mmask command 
         of the slb configuration menu." 
    ::= { serverloadbalance 22 }

slbCurCfgRadiusAuthenString OBJECT-TYPE
    SYNTAX  DisplayString (SIZE(0..32))
    ACCESS  read-only
    STATUS  mandatory
    DESCRIPTION
        "The RADIUS authentication string.  The string is used for 
	 generating encrypted authentication string for RADIUS health check."
    ::= { serverloadbalance 23 }

slbNewCfgRadiusAuthenString OBJECT-TYPE
    SYNTAX  DisplayString (SIZE(0..32))
    ACCESS  read-write
    STATUS  mandatory
    DESCRIPTION
        "The RADIUS authentication string.  The string is used for 
	 generating encrypted authentication string for RADIUS health check."
    ::= { serverloadbalance 24 }

slbCurCfgDirectMode OBJECT-TYPE
    SYNTAX  INTEGER {
        enabled(1),
        disabled(2)
        }
    ACCESS  read-only
    STATUS  mandatory
    DESCRIPTION
        "Enable or disable direct access mode. It allows direct access to 
         real servers and any combination of virtual and real servers 
         when set to enabled(1)."
    ::= { serverloadbalance 25 }

slbNewCfgDirectMode OBJECT-TYPE
    SYNTAX  INTEGER {
        enabled(1),
        disabled(2)
        }
    ACCESS  read-write
    STATUS  mandatory
    DESCRIPTION
        "Enable or disable direct access mode. It allows direct access to 
         real servers and any combination of virtual and real servers 
         when set to enabled(1)."
    ::= { serverloadbalance 26 }

slbCurCfgPmask OBJECT-TYPE
    SYNTAX  IpAddress
    ACCESS  read-only
    STATUS  mandatory
    DESCRIPTION
        "The persistent mask - corresponding to the pmask command of the 
         slb configuration menu." 
    ::= { serverloadbalance 28 }

slbNewCfgPmask OBJECT-TYPE
    SYNTAX  IpAddress
    ACCESS  read-write
    STATUS  mandatory
    DESCRIPTION
        "The persistent mask - corresponding to the pmask command of the 
         slb configuration menu." 
    ::= { serverloadbalance 29 }

slbCurCfgGrace OBJECT-TYPE
    SYNTAX  INTEGER {
        enabled(1),
        disabled(2)
        }
    ACCESS  read-only
    STATUS  mandatory
    DESCRIPTION
        "Enable or disable graceful server failure. It allows to keep the 
         connection to the failure real servers when set to enabled(1)."
    ::= { serverloadbalance 30 }

slbNewCfgGrace OBJECT-TYPE
    SYNTAX  INTEGER {
        enabled(1),
        disabled(2)
                }
    ACCESS  read-write
    STATUS  mandatory
    DESCRIPTION
        "Enable or disable graceful server failure. It allows to keep the 
         connection to the failure real servers when set to enabled(1)."
    ::= { serverloadbalance 31 }

--
-- WAP Load Balancing Configuration 
--

slbCurCfgWapTpcp OBJECT-TYPE
    SYNTAX INTEGER {
        enabled(1),
        disabled(2)
        }
    ACCESS  read-only
    STATUS  mandatory
    DESCRIPTION
        "Enable or disable WAP load balancing. "
    ::= { slbWap 1 }

slbNewCfgWapTpcp OBJECT-TYPE
    SYNTAX INTEGER {
        enabled(1),
        disabled(2)
        }
    ACCESS  read-write
    STATUS  mandatory
    DESCRIPTION
        "Enable or disable WAP load balancing. "
    ::= { slbWap 2 }

slbCurCfgWapDebug OBJECT-TYPE
    SYNTAX  INTEGER  (0..10)
    ACCESS  read-only
    STATUS  mandatory
    DESCRIPTION
        "WAP Debug level."
    ::= { slbWap 3 }

slbNewCfgWapDebug OBJECT-TYPE
    SYNTAX  INTEGER  (0..10)
    ACCESS  read-write
    STATUS  mandatory
    DESCRIPTION
        "WAP Debug level."
    ::= { slbWap 4 }

-- Synch Peer Switch Configuration

slbPeerTableMaxSize OBJECT-TYPE
    SYNTAX  INTEGER 
    ACCESS  read-only 
    STATUS  mandatory 
    DESCRIPTION 
        "The maximum number of entries in SLB Peer Table." 
    ::= { serverloadbalance 57 }

slbCurCfgPeerTable OBJECT-TYPE
    SYNTAX SEQUENCE OF SlbCurCfgPeerEntry
    ACCESS not-accessible
    STATUS mandatory
    DESCRIPTION
        "The table of Synch Peer Switch configuration in the current_config."
    ::= { serverloadbalance 32 }

slbCurCfgPeerEntry OBJECT-TYPE
    SYNTAX SlbCurCfgPeerEntry
    ACCESS not-accessible
    STATUS mandatory
    DESCRIPTION
        "Information about Synch Peer Switch configuration."
    INDEX { slbCurCfgPeerIndex }
    ::= { slbCurCfgPeerTable 1 }
 
SlbCurCfgPeerEntry ::= SEQUENCE {
    slbCurCfgPeerIndex          INTEGER,
    slbCurCfgPeerIpAddr         IpAddress,
    slbCurCfgPeerState          INTEGER
    }
 
slbCurCfgPeerIndex OBJECT-TYPE
    SYNTAX INTEGER
    ACCESS read-only
    STATUS mandatory
    DESCRIPTION
        "The index for synch peer switchs."
    ::= { slbCurCfgPeerEntry 1 }

slbCurCfgPeerIpAddr OBJECT-TYPE
    SYNTAX IpAddress
    ACCESS read-only
    STATUS mandatory
    DESCRIPTION
        "The IP address of the peer switch."
    ::= { slbCurCfgPeerEntry 2 }
 
slbCurCfgPeerState OBJECT-TYPE
    SYNTAX INTEGER {
        enable(1),
        disable(2)
        }
    ACCESS  read-only
    STATUS  mandatory
    DESCRIPTION
        "Enable or disable the peer switch."
    ::= { slbCurCfgPeerEntry 3 }
 
slbNewCfgPeerTable OBJECT-TYPE
    SYNTAX SEQUENCE OF SlbNewCfgPeerEntry
    ACCESS not-accessible
    STATUS mandatory
    DESCRIPTION
        "The table of Synch Peer Switch configuration in the new_config."
    ::= { serverloadbalance 33 }
 
slbNewCfgPeerEntry OBJECT-TYPE
    SYNTAX SlbNewCfgPeerEntry
    ACCESS not-accessible
    STATUS mandatory
    DESCRIPTION
        "Information about synch peer switch  configuration."
    INDEX { slbNewCfgPeerIndex }
    ::= { slbNewCfgPeerTable 1 }
 
SlbNewCfgPeerEntry ::= SEQUENCE {
    slbNewCfgPeerIndex          INTEGER,
    slbNewCfgPeerIpAddr         IpAddress,
    slbNewCfgPeerState          INTEGER,
    slbNewCfgPeerDelete         INTEGER
    }
 
slbNewCfgPeerIndex OBJECT-TYPE
    SYNTAX INTEGER
    ACCESS read-only
    STATUS mandatory
    DESCRIPTION
        "The index number for synch peer switchs."
    ::= { slbNewCfgPeerEntry 1 }
 
slbNewCfgPeerIpAddr OBJECT-TYPE
    SYNTAX IpAddress
    ACCESS read-write
    STATUS mandatory
    DESCRIPTION
        "The IP address of the peer switch."
    ::= { slbNewCfgPeerEntry 2 }
 
slbNewCfgPeerState OBJECT-TYPE
    SYNTAX INTEGER {
        enable(1),
        disable(2)
        }
    ACCESS  read-write
    STATUS  mandatory
    DESCRIPTION
        "Enable or disable the peer switch."
    ::= { slbNewCfgPeerEntry 3 }
 
slbNewCfgPeerDelete OBJECT-TYPE
    SYNTAX INTEGER {
        other(1),
        delete(2)
        }
    ACCESS  read-write
    STATUS  mandatory
    DESCRIPTION
        "By setting the value to delete(2), the entire row is
         deleted."
    ::= { slbNewCfgPeerEntry 4 }
 
slbCurCfgSyncFilt OBJECT-TYPE
    SYNTAX  INTEGER {
        enabled(1),
        disabled(2)
        }
    ACCESS  read-only
    STATUS  mandatory
    DESCRIPTION
        "Enable or disable synch filter configuration."
    ::= { serverloadbalance 34 }

slbNewCfgSyncFilt OBJECT-TYPE
    SYNTAX  INTEGER {
        enabled(1),
        disabled(2)
        }
    ACCESS  read-write
    STATUS  mandatory
    DESCRIPTION
        "Enable or disable synch filter configuration."
    ::= { serverloadbalance 35 }

slbCurCfgSyncPort OBJECT-TYPE
    SYNTAX  INTEGER {
        enabled(1),
        disabled(2)
        }
    ACCESS  read-only
    STATUS  mandatory
    DESCRIPTION
        "Enable or disable synch port configuration."
    ::= { serverloadbalance 36 }

slbNewCfgSyncPort OBJECT-TYPE
    SYNTAX  INTEGER {
        enabled(1),
        disabled(2)
        }
    ACCESS  read-write
    STATUS  mandatory
    DESCRIPTION
        "Enable or disable synch port configuration."
    ::= { serverloadbalance 37 }

slbCurCfgSyncVrrp OBJECT-TYPE
    SYNTAX  INTEGER {
        enabled(1),
        disabled(2)
        }
    ACCESS  read-only
    STATUS  mandatory
    DESCRIPTION
        "Enable or disable synch VRRP Priorities."
    ::= { serverloadbalance 38 }

slbNewCfgSyncVrrp OBJECT-TYPE
    SYNTAX  INTEGER {
        enabled(1),
        disabled(2)
        }
    ACCESS  read-write
    STATUS  mandatory
    DESCRIPTION
        "Enable or disable synch VRRP Priorities."
    ::= { serverloadbalance 39 }

slbCurCfgSyncPip OBJECT-TYPE
    SYNTAX  INTEGER {
        enabled(1),
        disabled(2)
        }
    ACCESS  read-only
    STATUS  mandatory
    DESCRIPTION
        "Enable or disable synch proxy IP addresses."
    ::= { serverloadbalance 40 }

slbNewCfgSyncPip OBJECT-TYPE
    SYNTAX  INTEGER {
        enabled(1),
        disabled(2)
        }
    ACCESS  read-write
    STATUS  mandatory
    DESCRIPTION
        "Enable or disable synch proxy IP addresses."
    ::= { serverloadbalance 41}

slbCurCfgSyncSfo OBJECT-TYPE
    SYNTAX  INTEGER {
        enabled(1),
        disabled(2)
        }
    ACCESS  read-only
    STATUS  mandatory
    DESCRIPTION
        "Enable or disable synch stateful failover."
    ::= { serverloadbalance 44}

slbNewCfgSyncSfo OBJECT-TYPE
    SYNTAX  INTEGER {
        enabled(1),
        disabled(2)
        }
    ACCESS  read-write
    STATUS  mandatory
    DESCRIPTION
        "Enable or disable synch stateful failover."
    ::= { serverloadbalance 45}

slbCurCfgSyncSfoUpdatePeriod OBJECT-TYPE
    SYNTAX  INTEGER (1..60)
    ACCESS  read-only
    STATUS  mandatory
    DESCRIPTION
        "The stateful failover update period in seconds."
    ::= { serverloadbalance 46}

slbNewCfgSyncSfoUpdatePeriod OBJECT-TYPE
    SYNTAX  INTEGER (1..60)
    ACCESS  read-write
    STATUS  mandatory
    DESCRIPTION
        "The stateful failover update period in seconds."
    ::= { serverloadbalance 47}

slbCurCfgSyncBwm OBJECT-TYPE
    SYNTAX  INTEGER {
        enabled(1),
        disabled(2)
        }
    ACCESS  read-only
    STATUS  mandatory
    DESCRIPTION
        "Enable or disable syncing BWM configuration."
    ::= { serverloadbalance 64 }

slbNewCfgSyncBwm OBJECT-TYPE
    SYNTAX  INTEGER {
        enabled(1),
        disabled(2)
        }
    ACCESS  read-write
    STATUS  mandatory
    DESCRIPTION
        "Enable or disable syncing BWM configuration."
    ::= { serverloadbalance 65 }

slbCurCfgVirtMatrixArch OBJECT-TYPE
    SYNTAX  INTEGER {
        enabled(1),
        disabled(2)
        }
    ACCESS  read-only
    STATUS  mandatory
    DESCRIPTION
        "Enable or disable Virtual Matrix Architecture."
    ::= { serverloadbalance 42 }

slbNewCfgVirtMatrixArch OBJECT-TYPE
    SYNTAX  INTEGER {
        enabled(1),
        disabled(2)
        }
    ACCESS  read-write
    STATUS  mandatory
    DESCRIPTION
        "Enable or disable Virtual Matrix Architecture."
    ::= { serverloadbalance 43}

slbCurCfgFastage OBJECT-TYPE
    SYNTAX  INTEGER (0..7) 
    ACCESS  read-only
    STATUS  mandatory
    DESCRIPTION
        "Session table fast-age (1 sec) period bit shift."
    ::= { serverloadbalance 58 }

slbNewCfgFastage OBJECT-TYPE
    SYNTAX  INTEGER (0..7) 
    ACCESS  read-write
    STATUS  mandatory
    DESCRIPTION
        "Session table fast-age (1 sec) period bit shift."
    ::= { serverloadbalance 59}

slbCurCfgSlowage OBJECT-TYPE
    SYNTAX  INTEGER (0..15) 
    ACCESS  read-only
    STATUS  mandatory
    DESCRIPTION
        "Session table slow-age (2 min) period bit shift."
    ::= { serverloadbalance 60 }

slbNewCfgSlowage OBJECT-TYPE
    SYNTAX  INTEGER (0..15) 
    ACCESS  read-write
    STATUS  mandatory
    DESCRIPTION
        "Session table slow-age (2 min) period bit shift."
    ::= { serverloadbalance 61}

slbCurCfgTpcp OBJECT-TYPE
    SYNTAX  INTEGER {
        enabled(1),
        disabled(2)
        }
    ACCESS  read-only
    STATUS  mandatory
    DESCRIPTION
        "Enable or disable Transparent Proxy Cache Protocol."
    ::= { serverloadbalance 66 }

slbNewCfgTpcp OBJECT-TYPE
    SYNTAX  INTEGER {
        enabled(1),
        disabled(2)
        }
    ACCESS  read-write
    STATUS  mandatory
    DESCRIPTION
        "Enable or disable Transparent Proxy Cache Protocol."
    ::= { serverloadbalance 67 }

slbCurCfgMetricInterval OBJECT-TYPE
    SYNTAX  INTEGER (1..256) 
    ACCESS  read-only
    STATUS  mandatory
    DESCRIPTION
        "The interval of response and bandwidth metric updates."
    ::= { serverloadbalance 68 }

slbNewCfgMetricInterval OBJECT-TYPE
    SYNTAX  INTEGER (1..256) 
    ACCESS  read-write
    STATUS  mandatory
    DESCRIPTION
        "The interval of response and bandwidth metric updates."
    ::= { serverloadbalance 69 }

slbCurCfgRealGroupIdslb OBJECT-TYPE
    SYNTAX  INTEGER (1..256) 
    ACCESS  read-only
    STATUS  mandatory
    DESCRIPTION
        "The real server group number for IDSLB."
    ::= { serverloadbalance 70 }

slbNewCfgRealGroupIdslb OBJECT-TYPE
    SYNTAX  INTEGER (1..256) 
    ACCESS  read-write
    STATUS  mandatory
    DESCRIPTION
        "The real server group number for IDSLB."
    ::= { serverloadbalance 71 }

slbCurCfgLdapVersion OBJECT-TYPE
    SYNTAX  INTEGER {
	version2(1),
	version3(2)
    } 
    ACCESS  read-only
    STATUS  mandatory
    DESCRIPTION
        "The version number for LDAP."
    ::= { serverloadbalance 72 }

slbNewCfgLdapVersion OBJECT-TYPE
    SYNTAX  INTEGER {
	version2(1),
	version3(2)
    } 
    ACCESS  read-write
    STATUS  mandatory
    DESCRIPTION
        "The Version number of LDAP."
    ::= { serverloadbalance 73 }

slbCurCfgIsdInterval OBJECT-TYPE
    SYNTAX  INTEGER (1..60) 
    ACCESS  read-only
    STATUS  mandatory
    DESCRIPTION
        "The interval of ISD health checks."
    ::= { serverloadbalance 74 }

slbNewCfgIsdInterval OBJECT-TYPE
    SYNTAX  INTEGER (1..60) 
    ACCESS  read-write
    STATUS  mandatory
    DESCRIPTION
        "The interval of ISD health checks."
    ::= { serverloadbalance 75 }

slbCurCfgIsdRetry OBJECT-TYPE
    SYNTAX  INTEGER (1..63) 
    ACCESS  read-only
    STATUS  mandatory
    DESCRIPTION
        "The number of failed attemps to declare ISD down."
    ::= { serverloadbalance 76 }

slbNewCfgIsdRetry OBJECT-TYPE
    SYNTAX  INTEGER (1..63) 
    ACCESS  read-write
    STATUS  mandatory
    DESCRIPTION
        "The number of failed attemps to declare ISD down."
    ::= { serverloadbalance 77 }

slbCurCfgIsdRestr OBJECT-TYPE
    SYNTAX  INTEGER (1..63) 
    ACCESS  read-only
    STATUS  mandatory
    DESCRIPTION
        "The number of successful attemps to declare ISD up."
    ::= { serverloadbalance 78 }

slbNewCfgIsdRestr OBJECT-TYPE
    SYNTAX  INTEGER (1..63) 
    ACCESS  read-write
    STATUS  mandatory
    DESCRIPTION
        "The number of successful attemps to declare ISD up."
    ::= { serverloadbalance 79 }

slbCurCfgIsdNumber OBJECT-TYPE
    SYNTAX  INTEGER (0..16) 
    ACCESS  read-only
    STATUS  mandatory
    DESCRIPTION
        "The number of real servers used for ISDs."
    ::= { serverloadbalance 80 }

slbNewCfgIsdNumber OBJECT-TYPE
    SYNTAX  INTEGER (0..16) 
    ACCESS  read-write
    STATUS  mandatory
    DESCRIPTION
        "The number of real servers used for ISDs."
    ::= { serverloadbalance 81 }

slbCurCfgTcpTimeWindow OBJECT-TYPE
    SYNTAX  INTEGER (1..65535) 
    ACCESS  read-only
    STATUS  mandatory
    DESCRIPTION
        "The time window for TCP rate limiting."
    ::= { serverloadbalance 83 }

slbNewCfgTcpTimeWindow OBJECT-TYPE
    SYNTAX  INTEGER (1..65535) 
    ACCESS  read-write
    STATUS  mandatory
    DESCRIPTION
        "The time window for TCP rate limiting."
    ::= { serverloadbalance 84 }

slbCurCfgTcpHoldDuration OBJECT-TYPE
    SYNTAX  INTEGER (1..65535) 
    ACCESS  read-only
    STATUS  mandatory
    DESCRIPTION
        "The hold down duration for TCP rate limiting."
    ::= { serverloadbalance 85 }

slbNewCfgTcpHoldDuration OBJECT-TYPE
    SYNTAX  INTEGER (1..65535) 
    ACCESS  read-write
    STATUS  mandatory
    DESCRIPTION
        "The hold down duration for TCP rate limiting."
    ::= { serverloadbalance 86 }

slbCurCfgAllowHttpHc OBJECT-TYPE
    SYNTAX  INTEGER {
	enabled(1),
	disabled(2)
    } 
    ACCESS  read-only
    STATUS  mandatory
    DESCRIPTION
        "Enable or disable allow HTTP health check on any port.
         If disabled the non-HTTP virtual services will use TCP Health Checks,
         if enabled the HTTP Content Health Check will be sent to any port 
         except HTTPS (443) if properly configured."
    ::= { serverloadbalance 87 }

slbNewCfgAllowHttpHc OBJECT-TYPE
    SYNTAX  INTEGER {
	enabled(1),
	disabled(2)
    } 
    ACCESS  read-write
    STATUS  mandatory
    DESCRIPTION
        "Enable or disable allow HTTP health check on any port.
         If disabled the non-HTTP virtual services will use TCP Health Checks,
         if enabled the HTTP Content Health Check will be sent to any port 
         except HTTPS (443) if properly configured."
    ::= { serverloadbalance 88 }

-- SLB Switch FailOver Group

slbCurCfgFailOverTable OBJECT-TYPE
    SYNTAX  SEQUENCE OF SlbCurCfgFailOverTblEntry
    ACCESS  not-accessible
    STATUS  obsolete
    DESCRIPTION
        "The table of current switch fail-over configuration."
    ::= { slbfailover 1 }

slbCurCfgFailOverTblEntry OBJECT-TYPE
    SYNTAX  SlbCurCfgFailOverTblEntry
    ACCESS  not-accessible
    STATUS  obsolete
    DESCRIPTION
        "A row in the current switch fail-over configuration table."
    INDEX   { slbCurCfgFailOverIndex }
    ::= { slbCurCfgFailOverTable 1 }
 
SlbCurCfgFailOverTblEntry ::= SEQUENCE {
        slbCurCfgFailOverIndex            INTEGER,      
        slbCurCfgFailOverPrimaryIp        IpAddress,
        slbCurCfgFailOverSecondaryIp      IpAddress,
	slbCurCfgFailOverSilenceInterval  INTEGER,
	slbCurCfgFailOverState            INTEGER,
	slbCurCfgFailOverRouteSupply      INTEGER
	}

slbCurCfgFailOverIndex OBJECT-TYPE
    SYNTAX  INTEGER
    ACCESS  read-only
    STATUS  obsolete
    DESCRIPTION
        "The index of current switch fail-over configuration table."
    ::= { slbCurCfgFailOverTblEntry 1 }

slbCurCfgFailOverPrimaryIp OBJECT-TYPE
    SYNTAX  IpAddress
    ACCESS  read-only
    STATUS  obsolete
    DESCRIPTION
        "The IP address of the Primary switch."
    ::= { slbCurCfgFailOverTblEntry 2 }

slbCurCfgFailOverSecondaryIp OBJECT-TYPE
    SYNTAX  IpAddress
    ACCESS  read-only
    STATUS  obsolete
    DESCRIPTION
        "The IP address of the Secondary switch."
    ::= { slbCurCfgFailOverTblEntry 3 }

slbCurCfgFailOverSilenceInterval OBJECT-TYPE
    SYNTAX  INTEGER (2..120)
    ACCESS  read-only
    STATUS  obsolete
    DESCRIPTION
        "Number of seconds before a silent peer is assumed down."
    ::= { slbCurCfgFailOverTblEntry 4 }

slbCurCfgFailOverState OBJECT-TYPE
    SYNTAX  INTEGER {
        enabled(2),
        disabled(3)
        }
    ACCESS  read-only
    STATUS  obsolete
    DESCRIPTION
        "Enable or disable slb switch failover feature."
    ::= { slbCurCfgFailOverTblEntry 5 }

slbCurCfgFailOverRouteSupply OBJECT-TYPE
    SYNTAX  INTEGER {
        enabled(1),
        disabled(2)
        }
    ACCESS  read-only
    STATUS  obsolete
    DESCRIPTION
        "Enable or disable to supply network routes update when switch 
         is a standby switch."
    ::= { slbCurCfgFailOverTblEntry 6 }

slbNewCfgFailOverTable OBJECT-TYPE
    SYNTAX  SEQUENCE OF SlbNewCfgFailOverTblEntry
    ACCESS  not-accessible
    STATUS  obsolete
    DESCRIPTION
        "The table of new switch fail-over configuration."
    ::= { slbfailover 2 }

slbNewCfgFailOverTblEntry OBJECT-TYPE
    SYNTAX  SlbNewCfgFailOverTblEntry
    ACCESS  not-accessible
    STATUS  obsolete
    DESCRIPTION
        "A row in the new switch fail-over configuration table."
    INDEX   { slbNewCfgFailOverIndex }
    ::= { slbNewCfgFailOverTable 1 }
 
SlbNewCfgFailOverTblEntry ::= SEQUENCE {
        slbNewCfgFailOverIndex            INTEGER,
        slbNewCfgFailOverPrimaryIp        IpAddress,
        slbNewCfgFailOverSecondaryIp      IpAddress,
	slbNewCfgFailOverSilenceInterval  INTEGER,
	slbNewCfgFailOverState            INTEGER,
	slbNewCfgFailOverRouteSupply      INTEGER
	}

slbNewCfgFailOverIndex OBJECT-TYPE
    SYNTAX  INTEGER
    ACCESS  read-only
    STATUS  obsolete
    DESCRIPTION
        "The index of new switch fail-over configuration table."
    ::= { slbNewCfgFailOverTblEntry 1 }

slbNewCfgFailOverPrimaryIp OBJECT-TYPE
    SYNTAX  IpAddress
    ACCESS  read-write
    STATUS  obsolete
    DESCRIPTION
        "The IP address of the Primary switch."
    ::= { slbNewCfgFailOverTblEntry 2 }

slbNewCfgFailOverSecondaryIp OBJECT-TYPE
    SYNTAX  IpAddress
    ACCESS  read-write
    STATUS  obsolete
    DESCRIPTION
        "The IP address of the Secondary switch."
    ::= { slbNewCfgFailOverTblEntry 3 }

slbNewCfgFailOverSilenceInterval OBJECT-TYPE
    SYNTAX  INTEGER (2..120)
    ACCESS  read-write
    STATUS  obsolete
    DESCRIPTION
        "Number of seconds before a silent peer is assumed down."
    ::= { slbNewCfgFailOverTblEntry 4 }

slbNewCfgFailOverState OBJECT-TYPE
    SYNTAX  INTEGER {
        enabled(2),
        disabled(3)
        }
    ACCESS  read-write
    STATUS  obsolete
    DESCRIPTION
        "Enable or disable slb switch failover feature."
    ::= { slbNewCfgFailOverTblEntry 5 }

slbNewCfgFailOverRouteSupply OBJECT-TYPE
    SYNTAX  INTEGER {
        enabled(1),
        disabled(2)
        }
    ACCESS  read-only
    STATUS  obsolete
    DESCRIPTION
        "Enable or disable to supply network routes update when switch 
         is a standby switch."
    ::= { slbNewCfgFailOverTblEntry 6 }

-- The SLB global turn on/off controls 

slbCurCfgGlobalControl OBJECT-TYPE
    SYNTAX  INTEGER { 
	enabled(2),
	disabled(3)
	}
    ACCESS  read-only
    STATUS  mandatory
    DESCRIPTION
        "The global state of Server Load Balancing."
    ::= { serverloadbalance 17 }

slbNewCfgGlobalControl OBJECT-TYPE
    SYNTAX  INTEGER { 
        enabled(2),
        disabled(3)
        }
    ACCESS  read-write
    STATUS  mandatory
    DESCRIPTION
        "The global state of Server Load Balancing."
    ::= { serverloadbalance 18 }


-- SLB URL Group

-- SLB URL Redirection Group

slbCurCfgUrlExpTable OBJECT-TYPE
    SYNTAX  SEQUENCE OF SlbCurCfgUrlExpTableEntry
    ACCESS  not-accessible
    STATUS  mandatory
    DESCRIPTION
        "The table of URL expressions in the current_config."
    ::= { slbUrlRedir 1 }

slbCurCfgUrlExpTableEntry OBJECT-TYPE
    SYNTAX  SlbCurCfgUrlExpTableEntry
    ACCESS  not-accessible
    STATUS  mandatory
    DESCRIPTION
        "Information about a expression for URL parsing."
    INDEX   { slbCurCfgUrlExpIndex }
    ::= { slbCurCfgUrlExpTable 1 }

SlbCurCfgUrlExpTableEntry ::= SEQUENCE {
    slbCurCfgUrlExpIndex          INTEGER,
    slbCurCfgUrlExpression        DisplayString
    }

slbCurCfgUrlExpIndex OBJECT-TYPE
    SYNTAX  INTEGER
    ACCESS  read-only
    STATUS  mandatory
    DESCRIPTION
        "The URL expressions table index."
    ::= { slbCurCfgUrlExpTableEntry 1 }

slbCurCfgUrlExpression OBJECT-TYPE
    SYNTAX  DisplayString (SIZE(0..20))
    ACCESS  read-only
    STATUS  mandatory
    DESCRIPTION
        "The expressions for URL parsing."
    ::= { slbCurCfgUrlExpTableEntry 2 }


slbNewCfgUrlExpTable OBJECT-TYPE
    SYNTAX  SEQUENCE OF SlbNewCfgUrlExpTableEntry
    ACCESS  not-accessible
    STATUS  mandatory
    DESCRIPTION
        "The table of URL expressions in the new_config."
    ::= { slbUrlRedir 2 }

slbNewCfgUrlExpTableEntry OBJECT-TYPE
    SYNTAX  SlbNewCfgUrlExpTableEntry
    ACCESS  not-accessible
    STATUS  mandatory
    DESCRIPTION
        "Information about a expression for URL parsing."
    INDEX   { slbNewCfgUrlExpIndex }
    ::= { slbNewCfgUrlExpTable 1 }

SlbNewCfgUrlExpTableEntry ::= SEQUENCE {
    slbNewCfgUrlExpIndex          INTEGER,
    slbNewCfgUrlExpression        DisplayString,
    slbNewCfgUrlExpDelete         INTEGER
    }

slbNewCfgUrlExpIndex OBJECT-TYPE
    SYNTAX  INTEGER
    ACCESS  read-only
    STATUS  mandatory
    DESCRIPTION
        "The URL expressions table index."
    ::= { slbNewCfgUrlExpTableEntry 1 }

slbNewCfgUrlExpression OBJECT-TYPE
    SYNTAX  DisplayString (SIZE(0..20))
    ACCESS  read-write
    STATUS  mandatory
    DESCRIPTION
        "The expressions for URL parsing."
    ::= { slbNewCfgUrlExpTableEntry 2 }

slbNewCfgUrlExpDelete OBJECT-TYPE
    SYNTAX  INTEGER {
        other(1),
        delete(2)
       }
    ACCESS  read-write
    STATUS  mandatory
    DESCRIPTION
        "Action object to delete an URL expression.  When set to the value of 
         2 (delete), the entire row is deleted. When read, other(1) is 
         returned. Setting the value to anything other than delete(2) has 
         no effect on the state of the row."
    ::= { slbNewCfgUrlExpTableEntry 3 }

slbCurCfgUrlRedirNonGetOrigSrv OBJECT-TYPE
    SYNTAX  INTEGER {
        enabled(1),
        disabled(2)
        }
    ACCESS  read-only
    STATUS  mandatory
    DESCRIPTION
	"This is for controlling if the switch should redirect packet 
         to the origin server when HTTP non-GETs are detected.  

         enabled(1) - Allow redirect traffic to the origin server
         disabled(2)- redirect to a group of servers"
    ::= { slbUrlRedir 3 }

slbNewCfgUrlRedirNonGetOrigSrv OBJECT-TYPE
    SYNTAX  INTEGER {
        enabled(1),
        disabled(2)
        }
    ACCESS  read-write
    STATUS  mandatory
    DESCRIPTION
        "This is for controlling if the switch should redirect packet to 
         the origin server when HTTP non-GETs are detected.  

         enabled(1) - Allow redirect traffic to the origin server
         disabled(2)- redirect to a group of servers"
    ::= { slbUrlRedir 4 }

slbCurCfgUrlRedirCookieOrigSrv OBJECT-TYPE
    SYNTAX  INTEGER {
        enabled(1),
        disabled(2)
        }
    ACCESS  read-only
    STATUS  mandatory
    DESCRIPTION
        "This is for controlling if the switch should redirect packet to the 
         origin server when user cookies are detected.  

         enabled(1) - Allow redirect traffic to the origin server
         disabled(2)- redirect to a group of servers"
    ::= { slbUrlRedir 5 }

slbNewCfgUrlRedirCookieOrigSrv OBJECT-TYPE
    SYNTAX  INTEGER {
        enabled(1),
        disabled(2)
        }
    ACCESS  read-write
    STATUS  mandatory
    DESCRIPTION
        "This is for controlling if the switch should redirect packet to the 
         origin server when user cookies are detected.  

         enabled(1) - Allow redirect traffic to the origin server
         disabled(2)- redirect to a group of servers"
    ::= { slbUrlRedir 6 }

slbCurCfgUrlRedirNoCacheOrigSrv OBJECT-TYPE
    SYNTAX  INTEGER {
        enabled(1),
        disabled(2)
        }
    ACCESS  read-only
    STATUS  mandatory
    DESCRIPTION
        "This is for controlling if the switch should redirect packet to the 
         origin server when no-cache header are detected.  

         enabled(1) - Allow redirect traffic to the origin server
         disabled(2)- redirect to a group of servers"
    ::= { slbUrlRedir 7 }

slbNewCfgUrlRedirNoCacheOrigSrv OBJECT-TYPE
    SYNTAX  INTEGER {
        enabled(1),
        disabled(2)
        }
    ACCESS  read-write
    STATUS  mandatory
    DESCRIPTION
        "This is for controlling if the switch should redirect packet to the 
         origin server when no-cache header are detected.  

         enabled(1) - Allow redirect traffic to the origin server
         disabled(2)- redirect to a group of servers"
    ::= { slbUrlRedir 8 }

slbCurCfgUrlRedirUriHashLength OBJECT-TYPE
    SYNTAX  INTEGER (0..255) 
    ACCESS  read-only
    STATUS  mandatory
    DESCRIPTION
        "Specify the number of bytes in the URI will be used to hash 
         onto server"
    ::= { slbUrlRedir 9 }

slbNewCfgUrlRedirUriHashLength OBJECT-TYPE
    SYNTAX  INTEGER (0..255) 
    ACCESS  read-write
    STATUS  mandatory
    DESCRIPTION
        "Specify the number of bytes in the URI will be used to hash 
         onto server"
    ::= { slbUrlRedir 10 }

slbCurCfgUrlRedirHeader OBJECT-TYPE
    SYNTAX  INTEGER {
        enabled(1),
        disabled(2)
        }
    ACCESS  read-only
    STATUS  mandatory
    DESCRIPTION
	"This is for controlling if the switch should redirect packet to the 
         cache server based on HTTP header.

         enabled(1) - Redirect web traffic based on HTTP header
         disabled(2)- Redirect web traffic based on URI"
    ::= { slbUrlRedir 11 }

slbNewCfgUrlRedirHeader OBJECT-TYPE
    SYNTAX  INTEGER {
        enabled(1),
        disabled(2)
        }
    ACCESS  read-write
    STATUS  mandatory
    DESCRIPTION
	"This is for controlling if the switch should redirect packet to the 
         cache server based on HTTP header.

         enabled(1) - Redirect web traffic based on HTTP header
         disabled(2)- Redirect web traffic based on URI"
    ::= { slbUrlRedir 12 }

slbCurCfgUrlRedirHeaderName OBJECT-TYPE
    SYNTAX DisplayString (SIZE(0..32))
    ACCESS read-only
    STATUS mandatory
    DESCRIPTION
        "The HTTP header name"
    ::= { slbUrlRedir 13 }

slbNewCfgUrlRedirHeaderName OBJECT-TYPE
    SYNTAX DisplayString (SIZE(0..32))
    ACCESS read-write 
    STATUS mandatory
    DESCRIPTION
        "The HTTP header name"
    ::= { slbUrlRedir 14 }

slbUrlExpTableMaxSize OBJECT-TYPE
    SYNTAX INTEGER 
    ACCESS read-only 
    STATUS mandatory 
    DESCRIPTION 
        "The maximum number of entries in SLB Url Expression table." 
    ::= {  slbUrlRedir 15 }

-- SLB URL Load Balancing

slbCurCfgUrlLbPathTable OBJECT-TYPE
    SYNTAX  SEQUENCE OF SlbCurCfgUrlLbPathTableEntry
    ACCESS  not-accessible
    STATUS  mandatory
    DESCRIPTION
        "The table of URL path for URL load balancing in the current_config."
    ::= { slbUrlBalance 1 }

slbCurCfgUrlLbPathTableEntry OBJECT-TYPE
    SYNTAX  SlbCurCfgUrlLbPathTableEntry
    ACCESS  not-accessible
    STATUS  mandatory
    DESCRIPTION
        "Information about an URL path for URL load balancing."
    INDEX   { slbCurCfgUrlLbPathIndex }
    ::= { slbCurCfgUrlLbPathTable 1 }

SlbCurCfgUrlLbPathTableEntry ::= SEQUENCE {
    slbCurCfgUrlLbPathIndex      INTEGER,
    slbCurCfgUrlLbPathString     DisplayString,
    slbCurCfgUrlLbBwmContract    INTEGER
    }

slbCurCfgUrlLbPathIndex OBJECT-TYPE
    SYNTAX  INTEGER
    ACCESS  read-only
    STATUS  mandatory
    DESCRIPTION
        "The URL path table index."
    ::= { slbCurCfgUrlLbPathTableEntry 1 }

slbCurCfgUrlLbPathString OBJECT-TYPE
    SYNTAX  DisplayString (SIZE(0..40))
    ACCESS  read-only
    STATUS  mandatory
    DESCRIPTION
        "The URL path for URL load balancing."
    ::= { slbCurCfgUrlLbPathTableEntry 2 }

slbCurCfgUrlLbBwmContract OBJECT-TYPE
    SYNTAX  INTEGER
    ACCESS  read-only
    STATUS  mandatory
    DESCRIPTION
        "The BW contract for the path."
    ::= { slbCurCfgUrlLbPathTableEntry 3 }

slbNewCfgUrlLbPathTable OBJECT-TYPE
    SYNTAX  SEQUENCE OF SlbNewCfgUrlLbPathTableEntry
    ACCESS  not-accessible
    STATUS  mandatory
    DESCRIPTION
        "The table of URL path for URL load balancing in the new_config."
    ::= { slbUrlBalance 2 }

slbNewCfgUrlLbPathTableEntry OBJECT-TYPE
    SYNTAX  SlbNewCfgUrlLbPathTableEntry
    ACCESS  not-accessible
    STATUS  mandatory
    DESCRIPTION
        "Information about an URL path for URL load balancing."
    INDEX   { slbNewCfgUrlLbPathIndex }
    ::= { slbNewCfgUrlLbPathTable 1 }

SlbNewCfgUrlLbPathTableEntry ::= SEQUENCE {
    slbNewCfgUrlLbPathIndex      INTEGER,
    slbNewCfgUrlLbPathString     DisplayString,
    slbNewCfgUrlLbBwmContract    INTEGER,
    slbNewCfgUrlLbPathDelete     INTEGER
    }

slbNewCfgUrlLbPathIndex OBJECT-TYPE
    SYNTAX  INTEGER
    ACCESS  read-only
    STATUS  mandatory
    DESCRIPTION
        "The URL path table index."
    ::= { slbNewCfgUrlLbPathTableEntry 1 }

slbNewCfgUrlLbPathString OBJECT-TYPE
    SYNTAX  DisplayString (SIZE(0..40))
    ACCESS  read-write
    STATUS  mandatory
    DESCRIPTION
        "The URL path for URL load balancing."
    ::= { slbNewCfgUrlLbPathTableEntry 2 }

slbNewCfgUrlLbBwmContract OBJECT-TYPE
    SYNTAX  INTEGER
    ACCESS  read-write
    STATUS  mandatory
    DESCRIPTION
        "The BW contract for the load path."
    ::= { slbNewCfgUrlLbPathTableEntry 4 }

slbNewCfgUrlLbPathDelete OBJECT-TYPE
    SYNTAX  INTEGER {
        other(1),
        delete(2)
        }
    ACCESS  read-write
    STATUS  mandatory
    DESCRIPTION
        "Action object to delete an URL Path.  When set to the value 
         of 2 (delete), the entire row is deleted. When read, other(1) is 
         returned. Setting the value to anything other than delete(2) 
         has no effect on the state of the row."
    ::= { slbNewCfgUrlLbPathTableEntry 3 }

slbCurCfgUrlLbErrorMsg OBJECT-TYPE
    SYNTAX  DisplayString (SIZE(0..64))
    ACCESS  read-only
    STATUS  mandatory
    DESCRIPTION
        "Customize error message to send back to client when switch cannot 
         bind client's request to servers."
    ::= { slbUrlBalance 3 }

slbNewCfgUrlLbErrorMsg OBJECT-TYPE
    SYNTAX  DisplayString (SIZE(0..64))
    ACCESS  read-write
    STATUS  mandatory
    DESCRIPTION
        "Customize error message to send back to client when switch cannot 
         bind client's request to servers."
    ::= { slbUrlBalance 4 }

slbUrlLbPathTableMaxSize OBJECT-TYPE
    SYNTAX INTEGER 
    ACCESS read-only 
    STATUS mandatory 
    DESCRIPTION 
        "The maximum number of entries in SLB URL load balance table." 
    ::= { slbUrlBalance 5 }

-- RTSP WCR Group

rtspUrlExpTableMaxSize OBJECT-TYPE
    SYNTAX INTEGER 
    ACCESS read-only 
    STATUS mandatory 
    DESCRIPTION 
        "The maximum number of entries in RTSP URL expression table." 
    ::= { rtspUrlRedir 1 }

rtspCurCfgUrlExpTable OBJECT-TYPE
    SYNTAX  SEQUENCE OF RtspCurCfgUrlExpTableEntry
    ACCESS  not-accessible
    STATUS  mandatory
    DESCRIPTION
        "The table of RTSP URL expressions."
    ::= { rtspUrlRedir 2 }

rtspCurCfgUrlExpTableEntry OBJECT-TYPE
    SYNTAX  RtspCurCfgUrlExpTableEntry
    ACCESS  not-accessible
    STATUS  mandatory
    DESCRIPTION
        "Information about a expression in the RTSP URL Redirection table."
    INDEX   { rtspCurCfgUrlExpIndex }
    ::= { rtspCurCfgUrlExpTable 1 }

RtspCurCfgUrlExpTableEntry ::= SEQUENCE {
    rtspCurCfgUrlExpIndex          INTEGER,
    rtspCurCfgUrlExpression        DisplayString
    }

rtspCurCfgUrlExpIndex OBJECT-TYPE
    SYNTAX  INTEGER
    ACCESS  read-only
    STATUS  mandatory
    DESCRIPTION
        "The RTSP URL expression table index."
    ::= { rtspCurCfgUrlExpTableEntry 1 }

rtspCurCfgUrlExpression OBJECT-TYPE
    SYNTAX  DisplayString (SIZE(0..20))
    ACCESS  read-only
    STATUS  mandatory
    DESCRIPTION
        "The expressions for RTSP URL redirection."
    ::= { rtspCurCfgUrlExpTableEntry 2 }

rtspNewCfgUrlExpTable OBJECT-TYPE
    SYNTAX  SEQUENCE OF RtspNewCfgUrlExpTableEntry
    ACCESS  not-accessible
    STATUS  mandatory
    DESCRIPTION
        "The table of RTSP URL expressions."
    ::= { rtspUrlRedir 3 }

rtspNewCfgUrlExpTableEntry OBJECT-TYPE
    SYNTAX  RtspNewCfgUrlExpTableEntry
    ACCESS  not-accessible
    STATUS  mandatory
    DESCRIPTION
        "Information about a expression in the RTSP URL Redirection table."
    INDEX   { rtspNewCfgUrlExpIndex }
    ::= { rtspNewCfgUrlExpTable 1 }

RtspNewCfgUrlExpTableEntry ::= SEQUENCE {
    rtspNewCfgUrlExpIndex          INTEGER,
    rtspNewCfgUrlExpression        DisplayString,
    rtspNewCfgUrlExpDelete         INTEGER
    }

rtspNewCfgUrlExpIndex OBJECT-TYPE
    SYNTAX  INTEGER
    ACCESS  read-only
    STATUS  mandatory
    DESCRIPTION
        "The RTSP URL expression table index."
    ::= { rtspNewCfgUrlExpTableEntry 1 }

rtspNewCfgUrlExpression OBJECT-TYPE
    SYNTAX  DisplayString (SIZE(0..20))
    ACCESS  read-write
    STATUS  mandatory
    DESCRIPTION
        "The expression for RTSP URL redirection."
    ::= { rtspNewCfgUrlExpTableEntry 2 }

rtspNewCfgUrlExpDelete OBJECT-TYPE
    SYNTAX  INTEGER {
        other(1),
        delete(2)
       }
    ACCESS  read-write
    STATUS  mandatory
    DESCRIPTION
        "Action object to delete an RTSP URL expression.  When set to the 
         value of 2 (delete), the entire row is deleted. When read, other(1)
         is returned. Setting the value to anything other than delete(2) has 
         no effect on the state of the row."
    ::= { rtspNewCfgUrlExpTableEntry 3 }

-- SLB RURL Group

slbCurCfgRurlGenDeny OBJECT-TYPE
    SYNTAX INTEGER {
            enabled(1),
            disabled(2)
            }
    ACCESS read-only
    STATUS mandatory
    DESCRIPTION
        "This is for controlling if the switch should deny packets from 
         passing through to L2 in the event that the switch runs out of 
         buffer resources."
    ::= { slbRurlGeneral 1 }

slbNewCfgRurlGenDeny OBJECT-TYPE
    SYNTAX INTEGER {
            enabled(1),
            disabled(2)
            }
    ACCESS read-write
    STATUS mandatory
    DESCRIPTION
        "This is for controlling if the switch should deny packets from 
         passing through to L2 in the event that the switch runs out of 
         buffer resources."
    ::= { slbRurlGeneral 2 }

slbRurlDportTableMaxSize OBJECT-TYPE
    SYNTAX INTEGER 
    ACCESS read-only 
    STATUS mandatory 
    DESCRIPTION 
        "The maximum number of entries in RURL destination port table." 
    ::= { slbRurl 2 }

slbCurCfgRurlDportTable OBJECT-TYPE
    SYNTAX  SEQUENCE OF SlbCurCfgRurlDportTableEntry
    ACCESS  not-accessible
    STATUS  mandatory
    DESCRIPTION
        "The table of RURL destination port ranges in current_config."
    ::= { slbRurl 3 }

slbCurCfgRurlDportTableEntry OBJECT-TYPE
    SYNTAX  SlbCurCfgRurlDportTableEntry
    ACCESS  not-accessible
    STATUS  mandatory
    DESCRIPTION
        "Information about a destination port range for RURL parsing."
    INDEX   { slbCurCfgRurlDportIndex }
    ::= { slbCurCfgRurlDportTable 1 }

SlbCurCfgRurlDportTableEntry ::= SEQUENCE {
    slbCurCfgRurlDportIndex          INTEGER,
    slbCurCfgRurlDportLowPort        INTEGER,
    slbCurCfgRurlDportHighPort       INTEGER
    }

slbCurCfgRurlDportIndex OBJECT-TYPE
    SYNTAX  INTEGER
    ACCESS  read-only
    STATUS  mandatory
    DESCRIPTION
        "The RURL destination port table index."
    ::= { slbCurCfgRurlDportTableEntry 1 }

slbCurCfgRurlDportLowPort OBJECT-TYPE
    SYNTAX  INTEGER (0..65534)
    ACCESS  read-only
    STATUS  mandatory
    DESCRIPTION
        "The first destination port in the port range."
    ::= { slbCurCfgRurlDportTableEntry 2 }

slbCurCfgRurlDportHighPort OBJECT-TYPE
    SYNTAX  INTEGER (0..65534)
    ACCESS  read-only
    STATUS  mandatory
    DESCRIPTION
        "The last destination port in the port range."
    ::= { slbCurCfgRurlDportTableEntry 3 }

slbNewCfgRurlDportTable OBJECT-TYPE
    SYNTAX  SEQUENCE OF SlbNewCfgRurlDportTableEntry
    ACCESS  not-accessible
    STATUS  mandatory
    DESCRIPTION
        "The table of RURL destination port ranges in new_config."
    ::= { slbRurl 4 }

slbNewCfgRurlDportTableEntry OBJECT-TYPE
    SYNTAX  SlbNewCfgRurlDportTableEntry
    ACCESS  not-accessible
    STATUS  mandatory
    DESCRIPTION
        "Information about a destination port range for RURL parsing."
    INDEX   { slbNewCfgRurlDportIndex }
    ::= { slbNewCfgRurlDportTable 1 }

SlbNewCfgRurlDportTableEntry ::= SEQUENCE {
    slbNewCfgRurlDportIndex          INTEGER,
    slbNewCfgRurlDportLowPort        INTEGER,
    slbNewCfgRurlDportHighPort       INTEGER, 
    slbNewCfgRurlDportDelete         INTEGER
    }

slbNewCfgRurlDportIndex OBJECT-TYPE
    SYNTAX  INTEGER
    ACCESS  read-write
    STATUS  mandatory
    DESCRIPTION
        "The RURL destination port table index."
    ::= { slbNewCfgRurlDportTableEntry 1 }

slbNewCfgRurlDportLowPort OBJECT-TYPE
    SYNTAX  INTEGER (0..65534)
    ACCESS  read-write
    STATUS  mandatory
    DESCRIPTION
        "The first destination port in the port range."
    ::= { slbNewCfgRurlDportTableEntry 2 }

slbNewCfgRurlDportHighPort OBJECT-TYPE
    SYNTAX  INTEGER (0..65534)
    ACCESS  read-write
    STATUS  mandatory
    DESCRIPTION
        "The last destination port in the port range."
    ::= { slbNewCfgRurlDportTableEntry 3 }

slbNewCfgRurlDportDelete OBJECT-TYPE
    SYNTAX INTEGER {
        other(1),
        delete(2)
        }
    ACCESS read-write
    STATUS mandatory
    DESCRIPTION
        "Action object to delete an destination port/range.  When set to the
         value of 2 (delete), the entire row is deleted. When read,
         other(1) is returned. Setting the value to anything other
         than delete(2) has no effect on the state of the row."
    ::= { slbNewCfgRurlDportTableEntry 4 }

-- WAP Health Check

slbCurCfgWaphcWSPPort OBJECT-TYPE   
    SYNTAX INTEGER (0..65534)
    ACCESS read-only   
    STATUS mandatory   
    DESCRIPTION 
        "The WSP port number to health check."   
    ::= { slbWaphc 1 }

slbNewCfgWaphcWSPPort OBJECT-TYPE   
    SYNTAX INTEGER (0..65534)
    ACCESS read-write
    STATUS mandatory   
    DESCRIPTION 
        "The WSP port number to health check."   
    ::= { slbWaphc 2 }

slbCurCfgWaphcOffset OBJECT-TYPE   
    SYNTAX INTEGER (0..256)
    ACCESS read-only   
    STATUS mandatory   
    DESCRIPTION 
        "The offset in received WSP packet."   
    ::= { slbWaphc 3 }

slbNewCfgWaphcOffset OBJECT-TYPE   
    SYNTAX INTEGER (0..256)
    ACCESS read-write
    STATUS mandatory   
    DESCRIPTION 
        "The offset in received WSP packet."   
    ::= { slbWaphc 4 }

slbCurCfgWaphcSndContent OBJECT-TYPE   
    SYNTAX DisplayString (SIZE(0..256))
    ACCESS read-only   
    STATUS mandatory   
    DESCRIPTION 
        "The content to be sent to the WAP gateway."   
    ::= { slbWaphc 5 }

slbNewCfgWaphcSndContent OBJECT-TYPE   
    SYNTAX DisplayString (SIZE(0..256))
    ACCESS read-write
    STATUS mandatory   
    DESCRIPTION 
        "The content to be sent to the WAP gateway."   
    ::= { slbWaphc 6 }

slbCurCfgWaphcRcvContent OBJECT-TYPE   
    SYNTAX DisplayString (SIZE(0..256))
    ACCESS read-only   
    STATUS mandatory   
    DESCRIPTION 
        "The content to be received from the WAP gateway."   
    ::= { slbWaphc 7 }

slbNewCfgWaphcRcvContent OBJECT-TYPE   
    SYNTAX DisplayString (SIZE(0..256))
    ACCESS read-write
    STATUS mandatory   
    DESCRIPTION 
        "The content to be received from the WAP gateway."   
    ::= { slbWaphc 8 }

slbCurCfgWaphcWTLSPort OBJECT-TYPE   
    SYNTAX INTEGER (0..65534)
    ACCESS read-only   
    STATUS mandatory   
    DESCRIPTION 
        "The WTLS port number to health check."   
    ::= { slbWaphc 9 }

slbNewCfgWaphcWTLSPort OBJECT-TYPE   
    SYNTAX INTEGER (0..65534)
    ACCESS read-write
    STATUS mandatory   
    DESCRIPTION 
        "The WTLS port number to health check."   
    ::= { slbWaphc 10 }

-- SYN Attack Detection 

synAttackCurCfgInterval OBJECT-TYPE
    SYNTAX  INTEGER (2..3600)
    ACCESS  read-only
    STATUS  mandatory
    DESCRIPTION
        "The interval specified in seconds determines how frequently the 
         switch checks for SYN attacks."
    ::= { synAttackDetCfg 1 }

synAttackNewCfgInterval OBJECT-TYPE
    SYNTAX  INTEGER (2..3600)
    ACCESS  read-write
    STATUS  mandatory
    DESCRIPTION
        "The interval specified in seconds determines how frequently the 
         switch checks for SYN attacks."
    ::= { synAttackDetCfg 2 }

synAttackCurCfgThreshhold OBJECT-TYPE
    SYNTAX  INTEGER (1..100000)
    ACCESS  read-only
    STATUS  mandatory
    DESCRIPTION
        "The threshhold indicating the number of new half-open sessions
         per second."
    ::= { synAttackDetCfg 3 }

synAttackNewCfgThreshhold OBJECT-TYPE
    SYNTAX  INTEGER (1..100000)
    ACCESS  read-write
    STATUS  mandatory
    DESCRIPTION
        "The threshhold indicating the number of new half-open sessions
         per second."
    ::= { synAttackDetCfg 4 }

-- Filtering Group
 
fltCfgTableMaxSize OBJECT-TYPE
    SYNTAX  INTEGER
    ACCESS  read-only
    STATUS  mandatory
    DESCRIPTION
        "The maximum number of filtering table entries."
    ::= { filtering 1 }

-- Current Config Filtering Table

fltCurCfgTable OBJECT-TYPE
    SYNTAX  SEQUENCE OF FltCurCfgTableEntry
    ACCESS  not-accessible
    STATUS  mandatory
    DESCRIPTION
        "The filtering table in the current configuration block."
    ::= { filtering 2 }

fltCurCfgTableEntry OBJECT-TYPE
    SYNTAX  FltCurCfgTableEntry
    ACCESS  not-accessible
    STATUS  mandatory
    DESCRIPTION
        "A row in the filtering table."
    INDEX   { fltCurCfgIndx }
    ::= { fltCurCfgTable 1 }

FltCurCfgTableEntry ::= SEQUENCE {
    fltCurCfgIndx             INTEGER,
    fltCurCfgSrcIpMac         INTEGER,
    fltCurCfgSrcIp            IpAddress,
    fltCurCfgSrcIpMask        IpAddress,
    fltCurCfgDstIpMac         INTEGER,
    fltCurCfgDstIp            IpAddress,
    fltCurCfgDstIpMask        IpAddress,
    fltCurCfgProtocol         INTEGER,
    fltCurCfgRangeLowSrcPort  INTEGER,
    fltCurCfgRangeHighSrcPort INTEGER,
    fltCurCfgRangeLowDstPort  INTEGER,
    fltCurCfgRangeHighDstPort INTEGER,
    fltCurCfgAction           INTEGER,
    fltCurCfgRedirPort        INTEGER,
    fltCurCfgRedirGroup       INTEGER,
    fltCurCfgLog              INTEGER,
    fltCurCfgState            INTEGER,
    fltCurCfgNat              INTEGER,
    fltCurCfgCache            INTEGER,
    fltCurCfgInvert           INTEGER,
    fltCurCfgClientProxy      INTEGER,
    fltCurCfgTcpAck           INTEGER,
    fltCurCfgUrlRedir         INTEGER,
    fltCurCfgSrcMac           PhysAddress,
    fltCurCfgDstMac           PhysAddress,
    fltCurCfgFtpNatActive     INTEGER,
    fltCurCfgAclTcpUrg        INTEGER, 
    fltCurCfgAclTcpAck        INTEGER, 
    fltCurCfgAclTcpPsh        INTEGER, 
    fltCurCfgAclTcpRst        INTEGER, 
    fltCurCfgAclTcpSyn        INTEGER, 
    fltCurCfgAclTcpFin        INTEGER,
    fltCurCfgAclIcmp	      INTEGER,
    fltCurCfgAclIpOption      INTEGER,
    fltCurCfgBwmContract      INTEGER,
    fltCurCfgAclIpTos         INTEGER,
    fltCurCfgAclIpTosMask     INTEGER,
    fltCurCfgAclIpTosNew      INTEGER,
    fltCurCfgFwlb	      INTEGER,
    fltCurCfgNatTimeout       INTEGER,
    fltCurCfgRurl             INTEGER,
    fltCurCfgLinklb           INTEGER,
    fltCurCfgWapRadiusSnoop   INTEGER,
    fltCurCfgIdslbHash        INTEGER,
    fltCurCfgVlan             INTEGER,
    fltCurCfgName             DisplayString,
    fltCurCfgTcpRateLimit     INTEGER,
    fltCurCfgTcpRateMaxConn   INTEGER,
    fltCurCfgHash             INTEGER,
    fltCurCfgNasa	      INTEGER,
    fltCurCfgLayer7DenyState  INTEGER,
    fltCurCfgLayer7DenyUrlBmap OCTET STRING
    }

fltCurCfgIndx OBJECT-TYPE
    SYNTAX  INTEGER
    ACCESS  read-only
    STATUS  mandatory
    DESCRIPTION
        "The filteriang table index."
    ::= { fltCurCfgTableEntry 1 }

fltCurCfgSrcIp OBJECT-TYPE
    SYNTAX  IpAddress
    ACCESS  read-only
    STATUS  mandatory
    DESCRIPTION
        "The source IP address to be filtered."
    ::= { fltCurCfgTableEntry 2 }

fltCurCfgSrcIpMask OBJECT-TYPE
    SYNTAX  IpAddress
    ACCESS  read-only
    STATUS  mandatory
    DESCRIPTION
        "The source IP sub-net mask for filtering."
    ::= { fltCurCfgTableEntry 3 }

fltCurCfgDstIp OBJECT-TYPE
    SYNTAX  IpAddress
    ACCESS  read-only
    STATUS  mandatory
    DESCRIPTION
        "The destination IP address to be filtered."
    ::= { fltCurCfgTableEntry 4 }

fltCurCfgDstIpMask OBJECT-TYPE
    SYNTAX  IpAddress
    ACCESS  read-only
    STATUS  mandatory
    DESCRIPTION
        "The destination IP sub-net mask for filtering."
    ::= { fltCurCfgTableEntry 5 }

fltCurCfgProtocol OBJECT-TYPE
    SYNTAX  INTEGER 
    ACCESS  read-only
    STATUS  mandatory
    DESCRIPTION
        "The protocol to be filtered."
    ::= { fltCurCfgTableEntry 6 }

fltCurCfgRangeHighSrcPort OBJECT-TYPE
    SYNTAX  INTEGER (0..65534)
    ACCESS  read-only
    STATUS  mandatory
    DESCRIPTION
        "The higher source TCP/UDP port number to be filtered. It applies 
         only when protocol defined in fltCurCfgProtocol is UDP or TCP.
         '0' means no filtering."
    ::= { fltCurCfgTableEntry 7 }

fltCurCfgRangeLowSrcPort OBJECT-TYPE
    SYNTAX  INTEGER (0..65534)
    ACCESS  read-only
    STATUS  mandatory
    DESCRIPTION
        "The lower source TCP/UDP port number to be filtered. It applies 
         only when protocol defined in fltCurCfgProtocol is UDP or TCP.  
         '0' means no filtering."
    ::= { fltCurCfgTableEntry 8 }

fltCurCfgRangeLowDstPort OBJECT-TYPE
    SYNTAX  INTEGER (0..65534)
    ACCESS  read-only
    STATUS  mandatory
    DESCRIPTION
        "The lower destination TCP/UDP port number to be filtered. It applies 
         only when protocol defined in fltCurCfgProtocol is UDP or TCP.
         '0' means no filtering."
    ::= { fltCurCfgTableEntry 9 }

fltCurCfgRangeHighDstPort OBJECT-TYPE
    SYNTAX  INTEGER (0..65534)
    ACCESS  read-only
    STATUS  mandatory
    DESCRIPTION
        "The higher destination TCP/UDP port number to be filtered. It applies
         only when protocol defined in fltCurCfgProtocol is UDP or TCP.
         '0' means no filtering."
    ::= { fltCurCfgTableEntry 10 }

fltCurCfgAction OBJECT-TYPE
    SYNTAX  INTEGER {
        allow(1),
        deny(2),
        redirect(3),
        nat(4)       -- network address translation
        }
    ACCESS  read-only
    STATUS  mandatory
    DESCRIPTION
        "The action for the filtering rule."
    ::= { fltCurCfgTableEntry 11 }

fltCurCfgRedirPort OBJECT-TYPE
    SYNTAX  INTEGER (0..65534)
    ACCESS  read-only
    STATUS  mandatory
    DESCRIPTION
        "The real server port number used for redirection."
    ::= { fltCurCfgTableEntry 12 }

fltCurCfgRedirGroup OBJECT-TYPE
    SYNTAX  INTEGER
    ACCESS  read-only
    STATUS  mandatory
    DESCRIPTION
        "The real server group to be redirected to."
    ::= { fltCurCfgTableEntry 13 }

fltCurCfgLog OBJECT-TYPE
    SYNTAX  INTEGER {
        enabled(1),
        disabled(2)
        }
    ACCESS  read-only
    STATUS  mandatory
    DESCRIPTION
        "Enable or disable logging."
    ::= { fltCurCfgTableEntry 14 }

fltCurCfgState OBJECT-TYPE
    SYNTAX  INTEGER {
        enabled(1),
        disabled(2)
        }
    ACCESS  read-only
    STATUS  mandatory
    DESCRIPTION
        "The state of this filtering rule."
    ::= { fltCurCfgTableEntry 15 }

fltCurCfgNat OBJECT-TYPE
    SYNTAX  INTEGER {
        destination-address(1),
        source-address(2)
        }
    ACCESS  read-only
    STATUS  mandatory
    DESCRIPTION
        "The selection of destination or source for network address 
         translation."
    ::= { fltCurCfgTableEntry 16 }

fltCurCfgCache OBJECT-TYPE
    SYNTAX  INTEGER {
        enabled(1),
        disabled(2)
        }
    ACCESS  read-only
    STATUS  mandatory
    DESCRIPTION
        "Enable or disable caching sessions that match filter."
    ::= { fltCurCfgTableEntry 17 }

fltCurCfgInvert OBJECT-TYPE
    SYNTAX  INTEGER {
        invert-on(1),
        invert-off(2)
        }
    ACCESS  read-only
    STATUS  mandatory
    DESCRIPTION
        "Turn the invert logic on or off for the filter entry."
    ::= { fltCurCfgTableEntry 18 }

fltCurCfgClientProxy OBJECT-TYPE
    SYNTAX  INTEGER {
        enabled(1),
        disabled(2)
        }
    ACCESS  read-only
    STATUS  mandatory
    DESCRIPTION
        "Enable or disable client proxy."
    ::= { fltCurCfgTableEntry 19 }

fltCurCfgTcpAck OBJECT-TYPE
    SYNTAX  INTEGER {
        enabled(1),
        disabled(2)
        }
    ACCESS  read-only
    STATUS  mandatory
    DESCRIPTION
        "Enable or disable filtering on matching TCP ACK and RST flag."
    ::= { fltCurCfgTableEntry 20 }

fltCurCfgUrlRedir OBJECT-TYPE
    SYNTAX  INTEGER {
        enabled(1),
        disabled(2)
        }
    ACCESS  read-only
    STATUS  mandatory
    DESCRIPTION
        "Enable or disable URL redirection. The URL expressions are 
         defined in slbCurCfgUrlTable."
    ::= { fltCurCfgTableEntry 21 }

fltCurCfgSrcMac OBJECT-TYPE
    SYNTAX  PhysAddress 
    ACCESS  read-only
    STATUS  mandatory
    DESCRIPTION
        "The source MAC address to be filtered."
    ::= { fltCurCfgTableEntry 22 }

fltCurCfgDstMac OBJECT-TYPE
    SYNTAX  PhysAddress 
    ACCESS  read-only
    STATUS  mandatory
    DESCRIPTION
        "The Destination MAC address to be filtered."
    ::= { fltCurCfgTableEntry 23 }

fltCurCfgFtpNatActive OBJECT-TYPE
    SYNTAX  INTEGER{
	enabled(1),
	disabled(2)
	}
    ACCESS  read-only
    STATUS  mandatory	
    DESCRIPTION
        "Enable or disable FTP NAT for active ftp only."
    ::= { fltCurCfgTableEntry 24 }

-- Current Config for TCP ACL filtering Table 

fltCurCfgAclTcpUrg OBJECT-TYPE
    SYNTAX  INTEGER {
	enable(1),
	disable(2)
	}
    ACCESS  read-only
    STATUS  mandatory
    DESCRIPTION
        "Enable or disable TCP URG packet."
    ::= { fltCurCfgTableEntry 25 }	

fltCurCfgAclTcpAck OBJECT-TYPE
    SYNTAX  INTEGER {
	enable(1),
	disable(2)
	}
    ACCESS  read-only
    STATUS  mandatory
    DESCRIPTION
        "Enable or disable TCP ACK packet."
    ::= { fltCurCfgTableEntry 26 }	

fltCurCfgAclTcpPsh OBJECT-TYPE
    SYNTAX  INTEGER {
	enable(1),
	disable(2)
	}
    ACCESS  read-only
    STATUS  mandatory
    DESCRIPTION
        "Enable or disable TCP PSH packet."
    ::= { fltCurCfgTableEntry 27 }	

fltCurCfgAclTcpRst OBJECT-TYPE
    SYNTAX  INTEGER {
	enable(1),
	disable(2)
	}
    ACCESS  read-only
    STATUS  mandatory 
    DESCRIPTION
        "Enable or disable TCP RST packet."
    ::= { fltCurCfgTableEntry 28 }	

fltCurCfgAclTcpSyn OBJECT-TYPE
    SYNTAX  INTEGER {
	enable(1),
	disable(2)
	}
    ACCESS  read-only
    STATUS  mandatory
    DESCRIPTION
        "Enable or disable TCP SYN packet."
    ::= { fltCurCfgTableEntry 29 }	

fltCurCfgAclTcpFin OBJECT-TYPE
    SYNTAX  INTEGER {
	enable(1),
	disable(2)
	}
    ACCESS  read-only
    STATUS  mandatory
    DESCRIPTION
	"Enable or disable TCP FIN packet."
    ::= { fltCurCfgTableEntry 30 }	

-- Current Config for ICMP Type ACL filtering Table 

fltCurCfgAclIcmp OBJECT-TYPE
    SYNTAX  INTEGER (0..255)
    ACCESS  read-only
    STATUS  mandatory
    DESCRIPTION
        "ICMP type to be filtered. A ICMP type of 255 indicates 'any'"
    ::= { fltCurCfgTableEntry 31 }	

-- Current Config IP Option ACL Filtering Table

fltCurCfgAclIpOption OBJECT-TYPE
    SYNTAX  INTEGER {
        enable(1),
	disable(2)
        }
    ACCESS  read-only
    STATUS  mandatory
    DESCRIPTION
        "Enable or disable IP option matching."
    ::= { fltCurCfgTableEntry 32 }

-- Current BW contract Filtering table

fltCurCfgBwmContract OBJECT-TYPE
    SYNTAX  INTEGER
    ACCESS  read-only
    STATUS  mandatory
    DESCRIPTION
	"Filt default BW contract number."
    ::= { fltCurCfgTableEntry 33 }	

fltCurCfgAclIpTos OBJECT-TYPE
    SYNTAX  INTEGER (0..255)
    ACCESS  read-only
    STATUS  mandatory
    DESCRIPTION
        "The IP TOS value to be filtered."
    ::= { fltCurCfgTableEntry 34 }	

fltCurCfgAclIpTosMask OBJECT-TYPE
    SYNTAX  INTEGER (0..255)
    ACCESS  read-only
    STATUS  mandatory
    DESCRIPTION
        "The IP TOS mask for filtering."
    ::= { fltCurCfgTableEntry 35 }	

fltCurCfgAclIpTosNew OBJECT-TYPE
    SYNTAX  INTEGER (0..255)
    ACCESS  read-only
    STATUS  mandatory
    DESCRIPTION
        "The new IP TOS value to over-write when filtering fired."
    ::= { fltCurCfgTableEntry 36 }	

fltCurCfgFwlb OBJECT-TYPE
    SYNTAX  INTEGER {
        enabled(1),
        disabled(2)
        }
    ACCESS  read-only
    STATUS  mandatory
    DESCRIPTION
        "Enable or disable filtering on firewall redirect hash method."
    ::= { fltCurCfgTableEntry 37 }

fltCurCfgNatTimeout OBJECT-TYPE
    SYNTAX  INTEGER (4..30)
    ACCESS  read-only
    STATUS  mandatory
    DESCRIPTION
        "The NAT session timeout. The timeout value should be an even number 
         between (4..30)"
    ::= { fltCurCfgTableEntry 38 }	

fltCurCfgRurl OBJECT-TYPE
    SYNTAX  INTEGER {
        enabled(1),
        disabled(2)
        }
    ACCESS  read-only
    STATUS  mandatory
    DESCRIPTION
        "Enable or disable RURL parsing."
    ::= { fltCurCfgTableEntry 39 }


fltCurCfgLinklb OBJECT-TYPE
    SYNTAX  INTEGER {
        enabled(1),
        disabled(2)
        }
    ACCESS  read-only
    STATUS  mandatory
    DESCRIPTION
        "Enable or disable WAN link load balancing."
    ::= { fltCurCfgTableEntry 40 }

fltCurCfgWapRadiusSnoop OBJECT-TYPE
    SYNTAX  INTEGER {
        enabled(1),
        disabled(2)
        }
    ACCESS  read-only
    STATUS  mandatory
    DESCRIPTION
        "Enable or disable WAP RADIUS snooping."
    ::= { fltCurCfgTableEntry 41 }

fltCurCfgSrcIpMac OBJECT-TYPE
    SYNTAX  INTEGER {
        ip(1),
        mac(2)
        }
    ACCESS  read-only
    STATUS  mandatory
    DESCRIPTION
        "Set a flag indicating whether filtering should be based on the 
         source IP address or the source MAC address field."
    ::= { fltCurCfgTableEntry 42 }

fltCurCfgDstIpMac OBJECT-TYPE
    SYNTAX  INTEGER {
        ip(1),
        mac(2)
        }
    ACCESS  read-only
    STATUS  mandatory
    DESCRIPTION
        "Set a flag indicating whether filtering should be based on the 
         destination IP address or the destination MAC address field."
    ::= { fltCurCfgTableEntry 43 }

fltCurCfgIdslbHash OBJECT-TYPE
    SYNTAX  INTEGER {
        sip(1),
        dip(2),
        both(3)
        }
    ACCESS  read-only
    STATUS  mandatory
    DESCRIPTION
        "Set hash parameter for intrusion detection server load balancing."
    ::= { fltCurCfgTableEntry 44 }

fltCurCfgVlan OBJECT-TYPE
    SYNTAX  INTEGER (0..4094)
    ACCESS  read-only
    STATUS  mandatory
    DESCRIPTION
        "Set the VLAN assoicated with the filter."
    ::= { fltCurCfgTableEntry 45 }

fltCurCfgName OBJECT-TYPE
    SYNTAX DisplayString (SIZE(0..31))
    ACCESS read-only
    STATUS mandatory
    DESCRIPTION
        "The name of the filter."
    ::= { fltCurCfgTableEntry 46 }

fltCurCfgTcpRateLimit OBJECT-TYPE
    SYNTAX  INTEGER {
        enabled(1),
        disabled(2)
        }
    ACCESS  read-only
    STATUS  mandatory
    DESCRIPTION
        "Enable or disable TCP connection rate limiting."
    ::= { fltCurCfgTableEntry 47 }

fltCurCfgTcpRateMaxConn OBJECT-TYPE
    SYNTAX  INTEGER (0..255)
    ACCESS  read-only
    STATUS  mandatory
    DESCRIPTION
        "Set maximum connections (number of connections in units of 10)
         for TCP connection rate limiting."
    ::= { fltCurCfgTableEntry 48 }

fltCurCfgHash OBJECT-TYPE
    SYNTAX  INTEGER {
	auto(1),
        sip(2),
        dip(3),
        both(4),
	sipsport(5)
        }
    ACCESS  read-only
    STATUS  mandatory
    DESCRIPTION
        "Set hash parameter for the filter."
    ::= { fltCurCfgTableEntry 49 }

fltCurCfgNasa OBJECT-TYPE
    SYNTAX  INTEGER {
        enabled(1),
        disabled(2)
        }
    ACCESS  read-only
    STATUS  mandatory
    DESCRIPTION
        "Enable or disable NASA redirect to ISD."
    ::= { fltCurCfgTableEntry 50 }

fltCurCfgLayer7DenyState OBJECT-TYPE
    SYNTAX  INTEGER {
        enabled(1),
        disabled(2)
        }
    ACCESS  read-only
    STATUS  mandatory
    DESCRIPTION
        "Enable or disable layer 7 deny filtering."
    ::= { fltCurCfgTableEntry 51 }

fltCurCfgLayer7DenyUrlBmap OBJECT-TYPE
    SYNTAX  OCTET STRING
    ACCESS  read-only
    STATUS  mandatory
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltCurCfgTableEntry 52 }

-- New Config Filtering Table

fltNewCfgTable OBJECT-TYPE
    SYNTAX  SEQUENCE OF FltNewCfgTableEntry
    ACCESS  not-accessible
    STATUS  mandatory
    DESCRIPTION
        "The filtering table in the new configuration block."
    ::= { filtering 3 }

fltNewCfgTableEntry OBJECT-TYPE
    SYNTAX  FltNewCfgTableEntry
    ACCESS  not-accessible
    STATUS  mandatory
    DESCRIPTION
        "A row in the filtering table."
    INDEX   { fltNewCfgIndx }
    ::= { fltNewCfgTable 1 }

FltNewCfgTableEntry ::= SEQUENCE {
    fltNewCfgIndx             INTEGER,
    fltNewCfgSrcIpMac         INTEGER,
    fltNewCfgSrcIp            IpAddress,
    fltNewCfgSrcIpMask        IpAddress,
    fltNewCfgDstIpMac         INTEGER,
    fltNewCfgDstIp            IpAddress,
    fltNewCfgDstIpMask        IpAddress,
    fltNewCfgProtocol         INTEGER,
    fltNewCfgRangeLowSrcPort  INTEGER,
    fltNewCfgRangeHighSrcPort INTEGER,
    fltNewCfgRangeLowDstPort  INTEGER,
    fltNewCfgRangeHighDstPort INTEGER,
    fltNewCfgAction           INTEGER,
    fltNewCfgRedirPort        INTEGER,
    fltNewCfgRedirGroup       INTEGER,
    fltNewCfgLog              INTEGER,
    fltNewCfgState            INTEGER,
    fltNewCfgDelete           INTEGER,
    fltNewCfgNat              INTEGER,
    fltNewCfgCache            INTEGER,
    fltNewCfgInvert           INTEGER,
    fltNewCfgClientProxy      INTEGER,
    fltNewCfgTcpAck           INTEGER,
    fltNewCfgUrlRedir         INTEGER,
    fltNewCfgSrcMac           PhysAddress,
    fltNewCfgDstMac           PhysAddress,
    fltNewCfgFtpNatActive     INTEGER,
    fltNewCfgAclTcpUrg        INTEGER,
    fltNewCfgAclTcpAck        INTEGER,
    fltNewCfgAclTcpPsh        INTEGER,
    fltNewCfgAclTcpRst        INTEGER,
    fltNewCfgAclTcpSyn        INTEGER,
    fltNewCfgAclTcpFin        INTEGER,
    fltNewCfgAclIcmp          INTEGER,
    fltNewCfgAclIpOption      INTEGER,
    fltNewCfgBwmContract      INTEGER,
    fltNewCfgAclIpTos	      INTEGER,
    fltNewCfgAclIpTosMask     INTEGER,
    fltNewCfgAclIpTosNew      INTEGER,
    fltNewCfgFwlb             INTEGER,
    fltNewCfgNatTimeout	      INTEGER,
    fltNewCfgRurl	      INTEGER,
    fltNewCfgLinklb           INTEGER,
    fltNewCfgWapRadiusSnoop   INTEGER,
    fltNewCfgIdslbHash        INTEGER,
    fltNewCfgVlan             INTEGER,
    fltNewCfgName             DisplayString,
    fltNewCfgTcpRateLimit     INTEGER,
    fltNewCfgTcpRateMaxConn   INTEGER,
    fltNewCfgHash             INTEGER,
    fltNewCfgNasa	      INTEGER,
    fltNewCfgLayer7DenyState   INTEGER,
    fltNewCfgLayer7DenyUrlBmap OCTET STRING,
    fltNewCfgLayer7DenyAddUrl  INTEGER,
    fltNewCfgLayer7DenyRemUrl  INTEGER
    }

fltNewCfgIndx OBJECT-TYPE
    SYNTAX  INTEGER
    ACCESS  read-only
    STATUS  mandatory
    DESCRIPTION
        "The filtering table index."
    ::= { fltNewCfgTableEntry 1 }

fltNewCfgSrcIp OBJECT-TYPE
    SYNTAX  IpAddress
    ACCESS  read-write
    STATUS  mandatory
    DESCRIPTION
        "The source IP address to be filtered."
    ::= { fltNewCfgTableEntry 2 }

fltNewCfgSrcIpMask OBJECT-TYPE
    SYNTAX  IpAddress
    ACCESS  read-write
    STATUS  mandatory
    DESCRIPTION
        "The source IP sub-net mask for filtering."
    ::= { fltNewCfgTableEntry 3 }

fltNewCfgDstIp OBJECT-TYPE
    SYNTAX  IpAddress
    ACCESS  read-write
    STATUS  mandatory
    DESCRIPTION
        "The destination IP address to be filtered."
    ::= { fltNewCfgTableEntry 4 }

fltNewCfgDstIpMask OBJECT-TYPE
    SYNTAX  IpAddress
    ACCESS  read-write
    STATUS  mandatory
    DESCRIPTION
        "The destination IP sub-net mask for filtering."
    ::= { fltNewCfgTableEntry 5 }

fltNewCfgProtocol OBJECT-TYPE
    SYNTAX  INTEGER 
    ACCESS  read-write
    STATUS  mandatory
    DESCRIPTION
        "The protocol to be filtered."
    ::= { fltNewCfgTableEntry 6 }

fltNewCfgRangeHighSrcPort OBJECT-TYPE
    SYNTAX  INTEGER (0..65534)
    ACCESS  read-write
    STATUS  mandatory
    DESCRIPTION
        "The higher source TCP/UDP port number to be filtered. It applies 
         only when protocol defined in fltNewCfgProtocol is UDP or TCP. 
         '0' means no filtering."
    ::= { fltNewCfgTableEntry 7 }

fltNewCfgRangeLowSrcPort OBJECT-TYPE
    SYNTAX  INTEGER (0..65534)
    ACCESS  read-write
    STATUS  mandatory
    DESCRIPTION
        "The lower source TCP/UDP port number to be filtered. It applies 
         only when protocol defined in fltNewCfgProtocol is UDP or TCP. 
         '0' means no filtering."
    ::= { fltNewCfgTableEntry 8 }

fltNewCfgRangeLowDstPort OBJECT-TYPE
    SYNTAX  INTEGER (0..65534)
    ACCESS  read-write
    STATUS  mandatory
    DESCRIPTION
        "The lower destination TCP/UDP port number to be filtered.
         It applies only when protocol defined in fltNewCfgProtocol
	 is UDP or TCP.  '0' means no filtering."
    ::= { fltNewCfgTableEntry 9 }

fltNewCfgRangeHighDstPort OBJECT-TYPE
    SYNTAX  INTEGER (0..65534)
    ACCESS  read-write
    STATUS  mandatory
    DESCRIPTION
        "The higher destination TCP/UDP port number to be filtered.
         It applies only when protocol defined in fltNewCfgProtocol
         is UDP or TCP.  '0' means no filtering."
    ::= { fltNewCfgTableEntry 10 }

fltNewCfgAction OBJECT-TYPE
    SYNTAX  INTEGER {
        allow(1),
        deny(2),
        redirect(3),
        nat(4)       -- network address translation
        }
    ACCESS  read-write
    STATUS  mandatory
    DESCRIPTION
        "The action for the filtering rule."
    ::= { fltNewCfgTableEntry 11 }

fltNewCfgRedirPort OBJECT-TYPE
    SYNTAX  INTEGER (0..65534)
    ACCESS  read-write
    STATUS  mandatory
    DESCRIPTION
        "The real server port number used for redirection."
    ::= { fltNewCfgTableEntry 12 }

fltNewCfgRedirGroup OBJECT-TYPE
    SYNTAX  INTEGER
    ACCESS  read-write
    STATUS  mandatory
    DESCRIPTION
        "The real server group to be redirected to."
    ::= { fltNewCfgTableEntry 13 }

fltNewCfgLog OBJECT-TYPE
    SYNTAX  INTEGER {
        enabled(1),
        disabled(2)
        }
    ACCESS  read-write
    STATUS  mandatory
    DESCRIPTION
        "Enable or disable logging."
    ::= { fltNewCfgTableEntry 14 }

fltNewCfgState OBJECT-TYPE
    SYNTAX  INTEGER {
        enabled(1),
        disabled(2)
        }
    ACCESS  read-write
    STATUS  mandatory
    DESCRIPTION
        "The state of this filtering rule."
    ::= { fltNewCfgTableEntry 15 }

fltNewCfgDelete OBJECT-TYPE
    SYNTAX  INTEGER {
        other(1),
        delete(2)
        }
    ACCESS  read-write
    STATUS  mandatory
    DESCRIPTION
        "When set to the value of 2 (delete), the entire row is deleted. 
         When read, other(1) is returned. Setting the value to anything 
         other than 2(delete) has no effect on the state of the row."
    ::= { fltNewCfgTableEntry 16 }

fltNewCfgNat OBJECT-TYPE
    SYNTAX  INTEGER {
        destination-address(1),
        source-address(2)
        }
    ACCESS  read-write
    STATUS  mandatory
    DESCRIPTION
        "The selection of destination or source for network address 
         translation."
    ::= { fltNewCfgTableEntry 17 }

fltNewCfgCache OBJECT-TYPE
    SYNTAX  INTEGER {
        enabled(1),
        disabled(2)
        }
    ACCESS  read-write
    STATUS  mandatory
    DESCRIPTION
        "Enable or disable caching sessions that match filter."
    ::= { fltNewCfgTableEntry 18 }

fltNewCfgInvert OBJECT-TYPE
    SYNTAX  INTEGER {
        invert-on(1),
        invert-off(2)
        }
    ACCESS  read-write
    STATUS  mandatory
    DESCRIPTION
        "Turn the invert logic on or off for the filter entry."
    ::= { fltNewCfgTableEntry 19 }

fltNewCfgClientProxy OBJECT-TYPE
    SYNTAX  INTEGER {
        enabled(1),
        disabled(2)
        }
    ACCESS  read-write
    STATUS  mandatory
    DESCRIPTION
        "Enable or disable client proxy."
    ::= { fltNewCfgTableEntry 20 }

fltNewCfgTcpAck OBJECT-TYPE
    SYNTAX  INTEGER {
        enabled(1),
        disabled(2)
        }
    ACCESS  read-write
    STATUS  mandatory
    DESCRIPTION
        "Enable or disable filtering on matching TCP ACK and RST flag."
    ::= { fltNewCfgTableEntry 21 }

fltNewCfgUrlRedir OBJECT-TYPE
    SYNTAX  INTEGER {
        enabled(1),
        disabled(2)
        }
    ACCESS  read-write
    STATUS  mandatory
    DESCRIPTION
        "Enable or disable URL redirection.  The URL expressions are
         defined in slbNewCfgUrlTable."
    ::= { fltNewCfgTableEntry 22 }

fltNewCfgSrcMac OBJECT-TYPE
    SYNTAX  PhysAddress 
    ACCESS  read-write
    STATUS  mandatory
    DESCRIPTION
        "The source MAC address to be filtered."
    ::= { fltNewCfgTableEntry 23 }

fltNewCfgDstMac OBJECT-TYPE
    SYNTAX  PhysAddress 
    ACCESS  read-write
    STATUS  mandatory
    DESCRIPTION
        "The Destination MAC address to be filtered."
    ::= { fltNewCfgTableEntry 24 }

fltNewCfgFtpNatActive OBJECT-TYPE
    SYNTAX  INTEGER {
        enabled(1),	
	disabled(2)
	}	
    ACCESS  read-write
    STATUS  mandatory
    DESCRIPTION
        "Enable or disable FTP NAT for active ftp."
    ::= { fltNewCfgTableEntry 25 }	

-- New Config TCP Flag ACL Filtering Table

fltNewCfgAclTcpUrg OBJECT-TYPE
    SYNTAX  INTEGER {
	enable(1),
	disable(2)
	}	
    ACCESS  read-write
    STATUS  mandatory
    DESCRIPTION
	"Enable or disable TCP URG packet."
    ::= { fltNewCfgTableEntry 26 }	

fltNewCfgAclTcpAck OBJECT-TYPE
    SYNTAX  INTEGER {
	enable(1),
	disable(2)
	}	
    ACCESS  read-write
    STATUS  mandatory
    DESCRIPTION
        "Enable or disable TCP ACK packet."
    ::= { fltNewCfgTableEntry 27 }	

fltNewCfgAclTcpPsh OBJECT-TYPE
    SYNTAX  INTEGER {
	enable(1),
	disable(2)
	}	
    ACCESS  read-write
    STATUS  mandatory
    DESCRIPTION
        "Enable or disable TCP PSH packet."
    ::= { fltNewCfgTableEntry 28 }	

fltNewCfgAclTcpRst OBJECT-TYPE
    SYNTAX  INTEGER {
	enable(1),
	disable(2)
	}	
    ACCESS  read-write
    STATUS  mandatory
    DESCRIPTION
        "Enable or disable TCP RST packet."
    ::= { fltNewCfgTableEntry 29 }	

fltNewCfgAclTcpSyn OBJECT-TYPE
    SYNTAX  INTEGER {
	enable(1),
	disable(2)
	}	
    ACCESS  read-write
    STATUS  mandatory
    DESCRIPTION
        "Enable or disable TCP SYN packet."
    ::= { fltNewCfgTableEntry 30 }	

fltNewCfgAclTcpFin OBJECT-TYPE
    SYNTAX  INTEGER {
	enable(1),
	disable(2)
	}	
    ACCESS  read-write
    STATUS  mandatory
    DESCRIPTION
        "Enable or disable TCP FIN packet."
    ::= { fltNewCfgTableEntry 31 }	

-- New Config ICMP Type ACL Filtering Table

fltNewCfgAclIcmp OBJECT-TYPE
    SYNTAX  INTEGER (0..255) 
    ACCESS  read-write
    STATUS  mandatory
    DESCRIPTION
        "ICMP type to be filtered. A ICMP type of 255 indicates 'any'"
    ::= { fltNewCfgTableEntry 32 }	

-- New Config IP Option ACL Filtering Table

fltNewCfgAclIpOption OBJECT-TYPE
    SYNTAX  INTEGER {
        enable(1),
        disable(2)
        }
    ACCESS  read-write
    STATUS  mandatory
    DESCRIPTION
        "Enable or disable IP option matching."
    ::= { fltNewCfgTableEntry 33 }

-- New Config BW Contract Filtering Table

fltNewCfgBwmContract OBJECT-TYPE
    SYNTAX  INTEGER 
    ACCESS  read-write
    STATUS  mandatory
    DESCRIPTION
        "Filt default BW contract number."
    ::= { fltNewCfgTableEntry 34 }	

fltNewCfgAclIpTos OBJECT-TYPE
    SYNTAX  INTEGER (0..255)
    ACCESS  read-write
    STATUS  mandatory
    DESCRIPTION
        "The IP TOS value to be filtered."
    ::= { fltNewCfgTableEntry 35 }	

fltNewCfgAclIpTosMask OBJECT-TYPE
    SYNTAX  INTEGER (0..255)
    ACCESS  read-write
    STATUS  mandatory
    DESCRIPTION
        "The IP TOS mask for filtering."
    ::= { fltNewCfgTableEntry 36 }	

fltNewCfgAclIpTosNew OBJECT-TYPE
    SYNTAX  INTEGER (0..255)
    ACCESS  read-write
    STATUS  mandatory
    DESCRIPTION
        "The new IP TOS value to over-write when filtering fired."
    ::= { fltNewCfgTableEntry 37 }	

fltNewCfgFwlb OBJECT-TYPE
    SYNTAX  INTEGER {
        enabled(1),
        disabled(2)
        }
    ACCESS  read-write
    STATUS  mandatory
    DESCRIPTION
        "Enable or disable filtering on firewall redirect hash method."
    ::= { fltNewCfgTableEntry 38 }

fltNewCfgNatTimeout OBJECT-TYPE
    SYNTAX  INTEGER (4..30)
    ACCESS  read-write
    STATUS  mandatory
    DESCRIPTION
	"The NAT session timeout. The timeout value should be an even
         number between (4..30)"
    ::= { fltNewCfgTableEntry 39 }	

fltNewCfgRurl OBJECT-TYPE
    SYNTAX  INTEGER {
        enabled(1),
        disabled(2)
        }
    ACCESS  read-write
    STATUS  mandatory
    DESCRIPTION
        "Enable or disable RURL parsing."
    ::= { fltNewCfgTableEntry 40 }

fltNewCfgLinklb OBJECT-TYPE
    SYNTAX  INTEGER {
        enabled(1),
        disabled(2)
        }
    ACCESS  read-write
    STATUS  mandatory
    DESCRIPTION
        "Enable or disable WAN link load balancing."
    ::= { fltNewCfgTableEntry 41 }

fltNewCfgWapRadiusSnoop OBJECT-TYPE
    SYNTAX  INTEGER {
        enabled(1),
        disabled(2)
        }
    ACCESS  read-write
    STATUS  mandatory
    DESCRIPTION
        "Enable or disable WAP RADIUS snooping."
    ::= { fltNewCfgTableEntry 42 }

fltNewCfgSrcIpMac OBJECT-TYPE
    SYNTAX  INTEGER {
        ip(1),
        mac(2)
        }
    ACCESS  read-write
    STATUS  mandatory
    DESCRIPTION
        "Set a flag indicating whether filtering should be based on the 
         source IP address or the source MAC address field."
    ::= { fltNewCfgTableEntry 43 }

fltNewCfgDstIpMac OBJECT-TYPE
    SYNTAX  INTEGER {
        ip(1),
        mac(2)
        }
    ACCESS  read-write
    STATUS  mandatory
    DESCRIPTION
        "Set a flag indicating whether filtering should be based on the 
         destination IP address or the destination MAC address field."
    ::= { fltNewCfgTableEntry 44 }

fltNewCfgIdslbHash OBJECT-TYPE
    SYNTAX  INTEGER {
        sip(1),
        dip(2),
        both(3)
        }
    ACCESS  read-write
    STATUS  mandatory
    DESCRIPTION
        "Set hash parameter for intrusion detection server load balancing."
    ::= { fltNewCfgTableEntry 45 }

fltNewCfgVlan OBJECT-TYPE
    SYNTAX  INTEGER (0..4094)
    ACCESS  read-write
    STATUS  mandatory
    DESCRIPTION
        "Set the VLAN assoicated with the filter."
    ::= { fltNewCfgTableEntry 46 }

fltNewCfgName OBJECT-TYPE
    SYNTAX DisplayString (SIZE(0..31))
    ACCESS read-write
    STATUS mandatory
    DESCRIPTION
        "The name of the filter."
    ::= { fltNewCfgTableEntry 47 }

fltNewCfgTcpRateLimit OBJECT-TYPE
    SYNTAX  INTEGER {
        enabled(1),
        disabled(2)
        }
    ACCESS  read-write
    STATUS  mandatory
    DESCRIPTION
        "Enable or disable TCP connection rate limiting."
    ::= { fltNewCfgTableEntry 48 }

fltNewCfgTcpRateMaxConn OBJECT-TYPE
    SYNTAX  INTEGER (0..255)
    ACCESS  read-write
    STATUS  mandatory
    DESCRIPTION
        "Set maximum connections (number of connections in units of 10)
         for TCP connection rate limiting."
    ::= { fltNewCfgTableEntry 49 }

fltNewCfgHash OBJECT-TYPE
    SYNTAX  INTEGER {
	auto(1),
        sip(2),
        dip(3),
        both(4),
	sipsport(5)
        }
    ACCESS  read-write
    STATUS  mandatory
    DESCRIPTION
        "Set hash parameter for the filter."
    ::= { fltNewCfgTableEntry 50 }

fltNewCfgNasa OBJECT-TYPE
    SYNTAX  INTEGER {
        enabled(1),
        disabled(2)
        }
    ACCESS  read-write
    STATUS  mandatory
    DESCRIPTION
        "Enable or disable NASA redirect to ISD."
    ::= { fltNewCfgTableEntry 51 }

fltNewCfgLayer7DenyState OBJECT-TYPE
    SYNTAX  INTEGER {
        enabled(1),
        disabled(2)
        }
    ACCESS  read-write
    STATUS  mandatory
    DESCRIPTION
        "Enable or disable layer 7 deny filtering."
    ::= { fltNewCfgTableEntry 52 }

fltNewCfgLayer7DenyUrlBmap OBJECT-TYPE
    SYNTAX  OCTET STRING
    ACCESS  read-only
    STATUS  mandatory
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltNewCfgTableEntry 53 }

fltNewCfgLayer7DenyAddUrl OBJECT-TYPE
    SYNTAX  INTEGER
    ACCESS  read-write
    STATUS  mandatory
    DESCRIPTION
        "The URL Path (slbCurCfgUrlLbPathIndex) to be added to the 
         Layer 7 deny filter. A zero is returned when read."
    ::= { fltNewCfgTableEntry 54 }

fltNewCfgLayer7DenyRemUrl OBJECT-TYPE
    SYNTAX  INTEGER
    ACCESS  read-write
    STATUS  mandatory
    DESCRIPTION
        "The URL Path (slbCurCfgUrlLbPathIndex) to be removed from 
         the Layer 7 deny filter. A zero is returned when read."
    ::= { fltNewCfgTableEntry 55 }

-- Filtering Port Table

fltCurCfgPortTable OBJECT-TYPE
    SYNTAX  SEQUENCE OF FltCurCfgPortTableEntry
    ACCESS  not-accessible
    STATUS  mandatory
    DESCRIPTION
        "The filtering port table in the current configuration block."
    ::= { filtering 4 }

fltCurCfgPortTableEntry OBJECT-TYPE
    SYNTAX  FltCurCfgPortTableEntry
    ACCESS  not-accessible
    STATUS  mandatory
    DESCRIPTION
        "A row in the filtering port table."
    INDEX   { fltCurCfgPortIndx }
    ::= { fltCurCfgPortTable 1 }

FltCurCfgPortTableEntry ::= SEQUENCE {
    fltCurCfgPortIndx         INTEGER,
    fltCurCfgPortState        INTEGER,
    fltCurCfgPortFiltBmap     OCTET STRING
    }

fltCurCfgPortIndx OBJECT-TYPE
    SYNTAX  INTEGER
    ACCESS  read-only
    STATUS  mandatory
    DESCRIPTION
        "The port index."
    ::= { fltCurCfgPortTableEntry 1 }

fltCurCfgPortState OBJECT-TYPE
    SYNTAX  INTEGER {
        enabled(1),
        disabled(2)
        }
    ACCESS  read-only
    STATUS  mandatory
    DESCRIPTION
        "Enable or disable filtering."
    ::= { fltCurCfgPortTableEntry 2 }

fltCurCfgPortFiltBmap OBJECT-TYPE
    SYNTAX  OCTET STRING (SIZE(0..256))
    ACCESS  read-only
    STATUS  mandatory
    DESCRIPTION
	"The filtering rules applied to the port.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the port
		   0 - The represented filter rule not applied to the port "
    ::= { fltCurCfgPortTableEntry 3 }

fltNewCfgPortTable OBJECT-TYPE
    SYNTAX  SEQUENCE OF FltNewCfgPortTableEntry
    ACCESS  not-accessible
    STATUS  mandatory
    DESCRIPTION
        "The filtering port table in the new configuration block."
    ::= { filtering 5 }

fltNewCfgPortTableEntry OBJECT-TYPE
    SYNTAX  FltNewCfgPortTableEntry
    ACCESS  not-accessible
    STATUS  mandatory
    DESCRIPTION
        "A row in the filtering port table."
    INDEX   { fltNewCfgPortIndx }
    ::= { fltNewCfgPortTable 1 }

FltNewCfgPortTableEntry ::= SEQUENCE {
    fltNewCfgPortIndx         INTEGER,
    fltNewCfgPortState        INTEGER,
    fltNewCfgPortFiltBmap     OCTET STRING,
    fltNewCfgPortAddFiltRule  INTEGER,
    fltNewCfgPortRemFiltRule  INTEGER
    }

fltNewCfgPortIndx OBJECT-TYPE
    SYNTAX  INTEGER
    ACCESS  read-only
    STATUS  mandatory
    DESCRIPTION
        "The port index."
    ::= { fltNewCfgPortTableEntry 1 }

fltNewCfgPortState OBJECT-TYPE
    SYNTAX  INTEGER {
        enabled(1),
        disabled(2)
        }
    ACCESS  read-write
    STATUS  mandatory
    DESCRIPTION
        "Enable or disable filtering."
    ::= { fltNewCfgPortTableEntry 2 }

fltNewCfgPortFiltBmap OBJECT-TYPE
    SYNTAX  OCTET STRING (SIZE(0..256))
    ACCESS  read-write
    STATUS  mandatory
    DESCRIPTION
        "The filtering rules applied to the port.  The filtering rules
         are presented in bitmap format.

         in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltNewCfgTable)

         where x : 1 - The represented filter rule applied to the port
		   0 - The represented filter rule not applied to the port "
    ::= { fltNewCfgPortTableEntry 3 }

fltNewCfgPortAddFiltRule OBJECT-TYPE
    SYNTAX  INTEGER
    ACCESS  read-write
    STATUS  mandatory
    DESCRIPTION
        "This is an action object to add filtering rule to a port. The value 
         specified with this object is the index to the fltNewCfgTable for 
         which filtering rule to be added to the port. The range of the 
         valid index is between 1 and fltCurCfgTableMaxSize. When read, the 
         value '0' is returned always."
    ::= { fltNewCfgPortTableEntry 4 }

fltNewCfgPortRemFiltRule OBJECT-TYPE
    SYNTAX  INTEGER
    ACCESS  read-write
    STATUS  mandatory
    DESCRIPTION
        "This is an action object to remove filtering rule from a port.	The 
         value specified with this object is the index to the fltNewCfgTable 
         for which filtering rule to be removed from the port. The range of 
         the valid index is between 1 and fltCurCfgTableMaxSize.  When read, 
         the value '0' is returned always."
    ::= { fltNewCfgPortTableEntry 5 }

-- URL based BWM filtering table

fltCurCfgUrlBwmTable OBJECT-TYPE
    SYNTAX  SEQUENCE OF FltCurCfgUrlBwmEntry
    ACCESS  not-accessible
    STATUS  mandatory
    DESCRIPTION
        "The table of URL based BWM for filtering."
    ::= { filtering 6 }

fltCurCfgUrlBwmEntry OBJECT-TYPE
    SYNTAX  FltCurCfgUrlBwmEntry
    ACCESS  not-accessible
    STATUS  mandatory
    DESCRIPTION
        "A row in the URL based BWM filtering table."
    INDEX   { fltCurCfgUrlBwmFltIndex, fltCurCfgUrlBwmUrlId }
    ::= { fltCurCfgUrlBwmTable 1 }

FltCurCfgUrlBwmEntry ::= SEQUENCE {
    fltCurCfgUrlBwmFltIndex     INTEGER,
    fltCurCfgUrlBwmUrlId        INTEGER,
    fltCurCfgUrlBwmContract     INTEGER
    }

fltCurCfgUrlBwmFltIndex OBJECT-TYPE
    SYNTAX  INTEGER
    ACCESS  read-only
    STATUS  mandatory
    DESCRIPTION
        "The number of the filter." 
    ::= { fltCurCfgUrlBwmEntry 1 }

fltCurCfgUrlBwmUrlId OBJECT-TYPE  
    SYNTAX  INTEGER  
    ACCESS  read-only  
    STATUS  mandatory  
    DESCRIPTION 
        "The URL Path Identifier."  
    ::= { fltCurCfgUrlBwmEntry 2 } 

fltCurCfgUrlBwmContract OBJECT-TYPE  
    SYNTAX  INTEGER  
    ACCESS  read-only  
    STATUS  mandatory  
    DESCRIPTION 
        "The BW contract."  
    ::= { fltCurCfgUrlBwmEntry 3 } 

fltNewCfgUrlBwmTable OBJECT-TYPE
    SYNTAX  SEQUENCE OF FltNewCfgUrlBwmEntry
    ACCESS  not-accessible
    STATUS  mandatory
    DESCRIPTION
        "The table of URL based BWM for filtering."
    ::= { filtering 7 }

fltNewCfgUrlBwmEntry OBJECT-TYPE
    SYNTAX  FltNewCfgUrlBwmEntry
    ACCESS  not-accessible
    STATUS  mandatory
    DESCRIPTION
        "A row in the URL based BWM filtering table."
    INDEX   { fltNewCfgUrlBwmFltIndex, fltNewCfgUrlBwmUrlId }
    ::= { fltNewCfgUrlBwmTable 1 }

FltNewCfgUrlBwmEntry ::= SEQUENCE {
    fltNewCfgUrlBwmFltIndex     INTEGER,
    fltNewCfgUrlBwmUrlId        INTEGER,
    fltNewCfgUrlBwmContract     INTEGER,
    fltNewCfgUrlBwmDelete       INTEGER
    }

fltNewCfgUrlBwmFltIndex OBJECT-TYPE
    SYNTAX  INTEGER
    ACCESS  read-only
    STATUS  mandatory
    DESCRIPTION
        "The number of the filter." 
    ::= { fltNewCfgUrlBwmEntry 1 }

fltNewCfgUrlBwmUrlId OBJECT-TYPE  
    SYNTAX  INTEGER  
    ACCESS  read-only  
    STATUS  mandatory  
    DESCRIPTION 
        "The URL Path Identifier."  
    ::= { fltNewCfgUrlBwmEntry 2 } 

fltNewCfgUrlBwmContract OBJECT-TYPE  
    SYNTAX  INTEGER  
    ACCESS  read-write  
    STATUS  mandatory  
    DESCRIPTION 
        "The BW traffic contract."  
    ::= { fltNewCfgUrlBwmEntry 3 } 

fltNewCfgUrlBwmDelete OBJECT-TYPE
    SYNTAX  INTEGER {
        other(1),
        delete(2)
        }
    ACCESS  read-write
    STATUS  mandatory
    DESCRIPTION
        "When set to the value of 2 (delete), the entire row is deleted. 
         When read, other(1) is returned. Setting the value to anything 
         other than 2(delete) has no effect on the state of the row."
    ::= { fltNewCfgUrlBwmEntry 4 }

fltUrlBwmTableMaxSize OBJECT-TYPE
    SYNTAX INTEGER
    ACCESS read-only
    STATUS mandatory
    DESCRIPTION
        "The maximum number of URL based BWM entries."
    ::= { filtering 8 }

-- Global Server Load Balancing

-- GSLB General Configuration

gslbCurCfgGenState OBJECT-TYPE
    SYNTAX  INTEGER {
        on(1),
        off(2)
        }
     ACCESS  read-only
     STATUS  mandatory
     DESCRIPTION
         "Turn on or off Distributed Server Load Balance."
    ::= { gslbGeneral 1 }

gslbNewCfgGenState OBJECT-TYPE
    SYNTAX  INTEGER {
        on(1),
        off(2)
        }
    ACCESS  read-write
    STATUS  mandatory
    DESCRIPTION
        "Turn on or off Distributed Server Load Balance."
    ::= { gslbGeneral 2 }

gslbCurCfgGenDnsHandoff OBJECT-TYPE
    SYNTAX  INTEGER {
        enabled(1),
        disabled(2)
        }
    ACCESS  read-only
    STATUS  mandatory
    DESCRIPTION
        "Enable/Disable DNS handoffs in the current_configuration block."
    ::= { gslbGeneral 3 }

gslbNewCfgGenDnsHandoff OBJECT-TYPE
    SYNTAX  INTEGER {
        enabled(1),
        disabled(2)
        }
    ACCESS  read-write
    STATUS  mandatory
    DESCRIPTION
        "Enable/Disable DNS handoffs in the new_configuration block."
    ::= { gslbGeneral 4 }

gslbCurCfgGenDnsTTL OBJECT-TYPE
    SYNTAX  INTEGER (0..65535)
    ACCESS  read-only
    STATUS  mandatory
    DESCRIPTION
        "Time to live value in minute of DNS resource records in 
	 the current_configuration block."
    ::= { gslbGeneral 5 }

gslbNewCfgGenDnsTTL OBJECT-TYPE
    SYNTAX  INTEGER (0..65535)
    ACCESS  read-write
    STATUS  mandatory
    DESCRIPTION
        "Time to live value in minute of DNS resource records in 
	 the new_configuration block."
    ::= { gslbGeneral 6 }

gslbCurCfgGenHttpRedirect OBJECT-TYPE
    SYNTAX  INTEGER {
        enabled(1),
        disabled(2)
        }
    ACCESS  read-only
    STATUS  mandatory
    DESCRIPTION
        "Enable/Disable DNS handoffs in the current_configuration block."
    ::= { gslbGeneral 7 }

gslbNewCfgGenHttpRedirect OBJECT-TYPE
    SYNTAX  INTEGER {
        enabled(1),
        disabled(2)
        }
    ACCESS  read-write
    STATUS  mandatory
    DESCRIPTION
        "Enable/Disable DNS handoffs in the new_configuration block."
    ::= { gslbGeneral 8 }

gslbCurCfgGenRemSiteUpdateInterval OBJECT-TYPE
    SYNTAX  INTEGER (1..120)
    ACCESS  read-only
    STATUS  mandatory
    DESCRIPTION
        "The time interval in minute for updating remote site status
         in the current_configuration block."
    ::= { gslbGeneral 9 }

gslbNewCfgGenRemSiteUpdateInterval OBJECT-TYPE
    SYNTAX  INTEGER (1..120)
    ACCESS  read-write
    STATUS  mandatory
    DESCRIPTION
        "The time interval in minute for updating remote site status
         in the new_configuration block."
    ::= { gslbGeneral 10 }

gslbCurCfgGenDnsLocalPref OBJECT-TYPE
    SYNTAX  INTEGER {
        enabled(1),
        disabled(2)
        }
    ACCESS  read-only
    STATUS  mandatory
    DESCRIPTION
        "Enable/Disable DNS responses with only local addresses."
    ::= { gslbGeneral 11 }

gslbNewCfgGenDnsLocalPref OBJECT-TYPE
    SYNTAX  INTEGER {
        enabled(1),
        disabled(2)
        }
    ACCESS  read-write
    STATUS  mandatory
    DESCRIPTION
        "Enable/Disable DNS responses with only local addresses."
    ::= { gslbGeneral 12 }

gslbCurCfgGenMinco OBJECT-TYPE
    SYNTAX  INTEGER (0..65535)
    ACCESS  read-only
    STATUS  mandatory
    DESCRIPTION
        "Minmum number of site connections in the current_configuration block."
    ::= { gslbGeneral 13 }

gslbNewCfgGenMinco OBJECT-TYPE
    SYNTAX  INTEGER (0..65535)
    ACCESS  read-write
    STATUS  mandatory
    DESCRIPTION
        "Minmum number of site connections in the new_configuration block."
    ::= { gslbGeneral 14 }

gslbCurCfgGenOne OBJECT-TYPE
    SYNTAX  INTEGER {
        enabled(1),
        disabled(2)
        }
    ACCESS  read-only
    STATUS  mandatory
    DESCRIPTION
        "Enable/Disable DNS responses with only one address."
    ::= { gslbGeneral 15 }

gslbNewCfgGenOne OBJECT-TYPE
    SYNTAX  INTEGER {
        enabled(1),
        disabled(2)
        }
    ACCESS  read-write
    STATUS  mandatory
    DESCRIPTION
        "Enable/Disable DNS responses with only one address."
    ::= { gslbGeneral 16 }

gslbCurCfgGenUsern OBJECT-TYPE
    SYNTAX  INTEGER {
        enabled(1),
        disabled(2)
        }
    ACCESS  read-only
    STATUS  mandatory
    DESCRIPTION
        "Enable/Disable HTTP redirect to real server name."
    ::= { gslbGeneral 17 }

gslbNewCfgGenUsern OBJECT-TYPE
    SYNTAX  INTEGER {
        enabled(1),
        disabled(2)
        }
    ACCESS  read-write
    STATUS  mandatory
    DESCRIPTION
        "Enable/Disable HTTP redirect to real server name."
    ::= { gslbGeneral 18 }

gslbCurCfgGenGeo OBJECT-TYPE
    SYNTAX  INTEGER {
        enabled(1),
        disabled(2)
        }
    ACCESS  read-only
    STATUS  mandatory
    DESCRIPTION
        "Enable/Disable geographic awareness."
    ::= { gslbGeneral 19 }

gslbNewCfgGenGeo OBJECT-TYPE
    SYNTAX  INTEGER {
        enabled(1),
        disabled(2)
        }
    ACCESS  read-write
    STATUS  mandatory
    DESCRIPTION
        "Enable/Disable geographic awareness."
    ::= { gslbGeneral 20 }

gslbCurCfgGenAlways OBJECT-TYPE
    SYNTAX INTEGER {
        enabled(1),
        disabled(2)
        }
    ACCESS read-only
    STATUS mandatory
    DESCRIPTION
        "Enable/Disable DNS responses with at least one address."
    ::= { gslbGeneral 21 }

gslbNewCfgGenAlways OBJECT-TYPE
    SYNTAX INTEGER {
        enabled(1),
        disabled(2)
        }
    ACCESS read-write
    STATUS mandatory
    DESCRIPTION
        "Enable/Disable DNS responses with at least one address."
    ::= { gslbGeneral 22 }

gslbCurCfgGenWeight OBJECT-TYPE
    SYNTAX INTEGER (1..48)
    ACCESS read-only
    STATUS mandatory
    DESCRIPTION
        "Sets the local weight. The higher the weight value, the
         more connections that will be directed to the local site."
    ::= { gslbGeneral 23 }

gslbNewCfgGenWeight OBJECT-TYPE
    SYNTAX INTEGER (1..48)
    ACCESS read-write
    STATUS mandatory
    DESCRIPTION
        "Sets the local weight. The higher the weight value, the
         more connections that will be directed to the local site."
    ::= { gslbGeneral 24 }

-- GSLB Lookup

gslbCurCfgGenLookups OBJECT-TYPE
    SYNTAX INTEGER {
        enabled(1),
        disabled(2)
        }
    ACCESS read-only
    STATUS mandatory
    DESCRIPTION
        "Enable or disable network preference lookups."
    ::= { gslbLookup 1 }
 
gslbNewCfgGenLookups OBJECT-TYPE
    SYNTAX INTEGER {
        enabled(1),
        disabled(2)
    }
    ACCESS read-write
    STATUS mandatory
    DESCRIPTION
        "Enable or disable network preference lookups."
    ::= { gslbLookup 2 }

gslbCurCfgGenLookupDname OBJECT-TYPE
    SYNTAX DisplayString (SIZE(0..34))
    ACCESS read-only
    STATUS mandatory
    DESCRIPTION
        "Domain name for internal lookup table"
    ::= { gslbLookup 3 }

gslbNewCfgGenLookupDname OBJECT-TYPE
    SYNTAX DisplayString (SIZE(0..34))
    ACCESS read-write
    STATUS mandatory
    DESCRIPTION
        "Domain name for internal lookup table"
    ::= { gslbLookup 4 }

gslbNetwork    OBJECT IDENTIFIER ::= { gslbLookup 5 }

gslbCurCfgGenExternal OBJECT-TYPE
    SYNTAX INTEGER {
        enabled(1),
        disabled(2)
        }
    ACCESS read-only
    STATUS obsolete
    DESCRIPTION
        "Enable or disable external lookups."
    ::= { gslbLookup 6 }
 
gslbNewCfgGenExternal OBJECT-TYPE
    SYNTAX INTEGER {
        enabled(1),
        disabled(2)
        }
    ACCESS read-write
    STATUS obsolete
    DESCRIPTION
        "Enable or disable external lookups."
    ::= { gslbLookup 7 }

gslbCurCfgGenEip OBJECT-TYPE
    SYNTAX IpAddress
    ACCESS read-only
    STATUS obsolete
    DESCRIPTION
        "External lookup IP address"
    ::= { gslbLookup 8 }
 
gslbNewCfgGenEip OBJECT-TYPE
    SYNTAX IpAddress
    ACCESS read-write
    STATUS obsolete
    DESCRIPTION
        "External lookup IP address"
    ::= { gslbLookup 9 }

gslbCurCfgGenLookupPort OBJECT-TYPE
    SYNTAX INTEGER (8100..9999)
    ACCESS read-only
    STATUS obsolete
    DESCRIPTION
        "External lookup UDP port number"
    ::= { gslbLookup 10 }
 
gslbNewCfgGenLookupPort OBJECT-TYPE
    SYNTAX INTEGER (8100..9999)
    ACCESS read-write
    STATUS obsolete
    DESCRIPTION
        "External lookup UDP port number"
    ::= { gslbLookup 11 }

gslbCurCfgGenLookupTimeout OBJECT-TYPE
    SYNTAX INTEGER (1..5)
    ACCESS read-only
    STATUS obsolete
    DESCRIPTION
        "External lookup Timeout Interval"
    ::= { gslbLookup 12 }
 
gslbNewCfgGenLookupTimeout OBJECT-TYPE
    SYNTAX INTEGER (1..5)
    ACCESS read-write
    STATUS obsolete
    DESCRIPTION
        "External lookup Timeout Interval"
    ::= { gslbLookup 13 }

-- GSLB Internet network preference Configuration

gslbNetworkTableMaxSize OBJECT-TYPE
    SYNTAX INTEGER
    ACCESS read-only
    STATUS mandatory
    DESCRIPTION
        "The maximum number of GSLB Internet network preference entries."
    ::= { gslbNetwork 1 }

gslbCurCfgNetworkTable OBJECT-TYPE
    SYNTAX SEQUENCE OF GslbCurCfgNetworkTableEntry
    ACCESS not-accessible
    STATUS mandatory
    DESCRIPTION
        "The table of Internet network preference in the current_config."
    ::= { gslbNetwork 2 }

gslbCurCfgNetworkTableEntry OBJECT-TYPE
    SYNTAX GslbCurCfgNetworkTableEntry
    ACCESS not-accessible
    STATUS mandatory
    DESCRIPTION
        "The table about a network preference entry configuration."
    INDEX { gslbCurCfgNetworkIndx }
    ::= { gslbCurCfgNetworkTable 1 }

GslbCurCfgNetworkTableEntry ::= SEQUENCE {
    gslbCurCfgNetworkIndx       INTEGER,
    gslbCurCfgNetworkSourceIp   IpAddress,
    gslbCurCfgNetworkNetMask    IpAddress,
    gslbCurCfgNetworkVip1       IpAddress,
    gslbCurCfgNetworkVip2       IpAddress
    } 

gslbCurCfgNetworkIndx  OBJECT-TYPE
    SYNTAX INTEGER 
    ACCESS read-only
    STATUS mandatory
    DESCRIPTION
        "The current Internet network preference table index."
    ::= { gslbCurCfgNetworkTableEntry 1 }

gslbCurCfgNetworkSourceIp OBJECT-TYPE
    SYNTAX IpAddress
    ACCESS read-only
    STATUS mandatory
    DESCRIPTION
        "The Source IP address of the network table."
    ::= { gslbCurCfgNetworkTableEntry 2}

gslbCurCfgNetworkNetMask OBJECT-TYPE
    SYNTAX IpAddress
    ACCESS read-only
    STATUS mandatory
    DESCRIPTION
        "The Net mask of the network table."
    ::= { gslbCurCfgNetworkTableEntry 3}

gslbCurCfgNetworkVip1 OBJECT-TYPE
    SYNTAX IpAddress
    ACCESS read-only
    STATUS mandatory
    DESCRIPTION
        "The Vip1 of the network table."
    ::= { gslbCurCfgNetworkTableEntry 4}

gslbCurCfgNetworkVip2 OBJECT-TYPE
    SYNTAX IpAddress
    ACCESS read-only
    STATUS mandatory
    DESCRIPTION
        "The Vip2 of the network table."
    ::= { gslbCurCfgNetworkTableEntry 5}

gslbNewCfgNetworkTable OBJECT-TYPE
    SYNTAX SEQUENCE OF GslbNewCfgNetworkTableEntry
    ACCESS not-accessible
    STATUS mandatory
    DESCRIPTION
        "The table of Internet network preference in the new_config."
    ::= { gslbNetwork 3 }

gslbNewCfgNetworkTableEntry OBJECT-TYPE
    SYNTAX GslbNewCfgNetworkTableEntry
    ACCESS not-accessible
    STATUS mandatory
    DESCRIPTION
        "The table about a network preference entry configuration."
    INDEX { gslbNewCfgNetworkIndx }
    ::= { gslbNewCfgNetworkTable 1 }

GslbNewCfgNetworkTableEntry ::= SEQUENCE {
    gslbNewCfgNetworkIndx       INTEGER,
    gslbNewCfgNetworkSourceIp   IpAddress,
    gslbNewCfgNetworkNetMask    IpAddress,
    gslbNewCfgNetworkVip1       IpAddress,
    gslbNewCfgNetworkVip2       IpAddress,
    gslbNewCfgNetworkDelete     INTEGER
    } 

gslbNewCfgNetworkIndx  OBJECT-TYPE
    SYNTAX INTEGER 
    ACCESS read-only
    STATUS mandatory
    DESCRIPTION
        "The new Internet network preference table index."
    ::= { gslbNewCfgNetworkTableEntry 1 }

gslbNewCfgNetworkSourceIp OBJECT-TYPE
    SYNTAX IpAddress
    ACCESS read-write
    STATUS mandatory
    DESCRIPTION
        "The Source IP address of the network table."
    ::= { gslbNewCfgNetworkTableEntry 2}

gslbNewCfgNetworkNetMask OBJECT-TYPE
    SYNTAX IpAddress
    ACCESS read-write
    STATUS mandatory
    DESCRIPTION
        "The Net mask of the network table."
    ::= { gslbNewCfgNetworkTableEntry 3}

gslbNewCfgNetworkVip1 OBJECT-TYPE
    SYNTAX IpAddress
    ACCESS read-write
    STATUS mandatory
    DESCRIPTION
        "The Vip1 of the network table."
    ::= { gslbNewCfgNetworkTableEntry 4}

gslbNewCfgNetworkVip2 OBJECT-TYPE
    SYNTAX IpAddress
    ACCESS read-write
    STATUS mandatory
    DESCRIPTION
        "The Vip2 of the network table."
    ::= { gslbNewCfgNetworkTableEntry 5}

gslbNewCfgNetworkDelete OBJECT-TYPE
    SYNTAX INTEGER {
        other(1),
        delete(2)
        }
    ACCESS read-write
    STATUS mandatory
    DESCRIPTION
        "By setting the value to delete(2), the entire row is deleted."
    ::= { gslbNewCfgNetworkTableEntry 12}

-- GSLB Domain Name Server Configuration

dnsCurCfgPrimaryIpAddr OBJECT-TYPE
    SYNTAX  IpAddress
    ACCESS  read-only
    STATUS  mandatory
    DESCRIPTION
        "The DNS primary IP address in the current_configuration block."
    ::= { gslbDNS 1 }

dnsNewCfgPrimaryIpAddr OBJECT-TYPE
    SYNTAX  IpAddress
    ACCESS  read-write
    STATUS  mandatory
    DESCRIPTION
        "The DNS primary IP address in the new_configuration block."
    ::= { gslbDNS 2 }

dnsCurCfgSecondaryIpAddr OBJECT-TYPE
    SYNTAX  IpAddress
    ACCESS  read-only
    STATUS  mandatory
    DESCRIPTION
        "The DNS primary IP address in the current_configuration block."
    ::= { gslbDNS 3 }

dnsNewCfgSecondaryIpAddr OBJECT-TYPE
    SYNTAX  IpAddress
    ACCESS  read-write
    STATUS  mandatory
    DESCRIPTION
        "The DNS primary IP address in the new_configuration block."
    ::= { gslbDNS 4 }

dnsCurCfgDomainName OBJECT-TYPE
    SYNTAX  DisplayString (SIZE(0..191))
    ACCESS  read-only
    STATUS  mandatory
    DESCRIPTION
        "The DNS doamin name in the current_configuration block."
    ::= { gslbDNS 5 }

dnsNewCfgDomainName OBJECT-TYPE
    SYNTAX  DisplayString (SIZE(0..191))
    ACCESS  read-write
    STATUS  mandatory
    DESCRIPTION
        "The DNS doamin name in the new_configuration block."
    ::= { gslbDNS 6 }


-- GSLB Remote Sites Configuration

gslbRemSiteTableMaxSize OBJECT-TYPE
    SYNTAX  INTEGER
    ACCESS  read-only
    STATUS  mandatory
    DESCRIPTION
        "The maximum number of GSLB remote sites."
    ::= { gslbSites 1 }

gslbCurCfgRemSiteTable OBJECT-TYPE
    SYNTAX  SEQUENCE OF GslbCurCfgRemSiteTableEntry
    ACCESS  not-accessible
    STATUS  mandatory
    DESCRIPTION
        "The GSLB remote sites table in the current configuration block."
    ::= { gslbSites 2 }

gslbCurCfgRemSiteTableEntry OBJECT-TYPE
    SYNTAX  GslbCurCfgRemSiteTableEntry
    ACCESS  not-accessible
    STATUS  mandatory
    DESCRIPTION
        "A row in the GSLB remote sites table."
    INDEX   { gslbCurCfgRemSiteIndx }
    ::= { gslbCurCfgRemSiteTable 1 }

GslbCurCfgRemSiteTableEntry ::= SEQUENCE {
    gslbCurCfgRemSiteIndx        INTEGER,
    gslbCurCfgRemSitePrimaryIp   IpAddress,
    gslbCurCfgRemSiteSecondaryIp IpAddress,
    gslbCurCfgRemSiteState       INTEGER,
    gslbCurCfgRemSiteUpdate      INTEGER,
    gslbCurCfgRemSiteName        DisplayString
    }

gslbCurCfgRemSiteIndx OBJECT-TYPE
    SYNTAX  INTEGER
    ACCESS  read-only
    STATUS  mandatory
    DESCRIPTION
        "The GSLB remote sites table index."
    ::= { gslbCurCfgRemSiteTableEntry 1 }

gslbCurCfgRemSitePrimaryIp OBJECT-TYPE
    SYNTAX  IpAddress
    ACCESS  read-only
    STATUS  mandatory
    DESCRIPTION
        "The primary IP address of the remote site in the 
         current_configuration block."
    ::= { gslbCurCfgRemSiteTableEntry 2 }

gslbCurCfgRemSiteSecondaryIp OBJECT-TYPE
    SYNTAX  IpAddress
    ACCESS  read-only
    STATUS  mandatory
    DESCRIPTION
        "The secondary IP address of the remote site in the 
	 current_configuration block."
    ::= { gslbCurCfgRemSiteTableEntry 3 }

gslbCurCfgRemSiteState OBJECT-TYPE
    SYNTAX  INTEGER {
        enabled(1),
        disabled(2)
        }
    ACCESS  read-only
    STATUS  mandatory
    DESCRIPTION
        "Enable/Disable GSLB for the remote site in the 
         current_configuration block."
    ::= { gslbCurCfgRemSiteTableEntry 4 }

gslbCurCfgRemSiteUpdate OBJECT-TYPE
    SYNTAX  INTEGER {
        enabled(1),
        disabled(2)
        }
    ACCESS  read-only
    STATUS  mandatory
    DESCRIPTION
        "Enable/Disable GSLB for the remote site status update in the 
         current_configuration block."
    ::= { gslbCurCfgRemSiteTableEntry 5 }

gslbCurCfgRemSiteName OBJECT-TYPE
    SYNTAX DisplayString (SIZE(0..31))
    ACCESS read-only
    STATUS mandatory
    DESCRIPTION
	"The name of the GSLB remote site."
    ::= { gslbCurCfgRemSiteTableEntry 6 }

gslbNewCfgRemSiteTable OBJECT-TYPE
    SYNTAX  SEQUENCE OF GslbNewCfgRemSiteTableEntry
    ACCESS  not-accessible
    STATUS  mandatory
    DESCRIPTION
        "The GSLB remote sites table in the current configuration block."
    ::= { gslbSites 3 }

gslbNewCfgRemSiteTableEntry OBJECT-TYPE
    SYNTAX  GslbNewCfgRemSiteTableEntry
    ACCESS  not-accessible
    STATUS  mandatory
    DESCRIPTION
        "A row in the GSLB remote sites table."
    INDEX   { gslbNewCfgRemSiteIndx }
    ::= { gslbNewCfgRemSiteTable 1 }

GslbNewCfgRemSiteTableEntry ::= SEQUENCE {
    gslbNewCfgRemSiteIndx        INTEGER,
    gslbNewCfgRemSitePrimaryIp   IpAddress,
    gslbNewCfgRemSiteSecondaryIp IpAddress,
    gslbNewCfgRemSiteState       INTEGER,
    gslbNewCfgRemSiteUpdate      INTEGER,
    gslbNewCfgRemSiteDelete      INTEGER,
    gslbNewCfgRemSiteName        DisplayString
    }

gslbNewCfgRemSiteIndx OBJECT-TYPE
    SYNTAX  INTEGER
    ACCESS  read-only
    STATUS  mandatory
    DESCRIPTION
        "The GSLB remote sites table index."
    ::= { gslbNewCfgRemSiteTableEntry 1 }

gslbNewCfgRemSitePrimaryIp OBJECT-TYPE
    SYNTAX  IpAddress
    ACCESS  read-write
    STATUS  mandatory
    DESCRIPTION
        "The primary IP address of the remote site in the new_configuration 
         block."
    ::= { gslbNewCfgRemSiteTableEntry 2 }

gslbNewCfgRemSiteSecondaryIp OBJECT-TYPE
    SYNTAX  IpAddress
    ACCESS  read-write
    STATUS  mandatory
    DESCRIPTION
        "The secondary IP address of the remote site in the new_configuration 
         block."
    ::= { gslbNewCfgRemSiteTableEntry 3 }

gslbNewCfgRemSiteState OBJECT-TYPE
    SYNTAX  INTEGER {
        enabled(1),
        disabled(2)
        }
    ACCESS  read-write
    STATUS  mandatory
    DESCRIPTION
        "Enable/Disable GSLB for the remote site in the new_configuration 
         block."
    ::= { gslbNewCfgRemSiteTableEntry 4 }

gslbNewCfgRemSiteUpdate OBJECT-TYPE
    SYNTAX  INTEGER {
        enabled(1),
        disabled(2)
        }
    ACCESS  read-write
    STATUS  mandatory
    DESCRIPTION
        "Enable/Disable GSLB for the remote site status update in the 
         new_configuration block."
    ::= { gslbNewCfgRemSiteTableEntry 5 }

gslbNewCfgRemSiteDelete OBJECT-TYPE
    SYNTAX INTEGER {
        other(1),
        delete(2)
        }
    ACCESS read-write
    STATUS mandatory
    DESCRIPTION
        "By setting the value to delete(2), the entire row is deleted."
    ::= { gslbNewCfgRemSiteTableEntry 6 }

gslbNewCfgRemSiteName OBJECT-TYPE
    SYNTAX DisplayString (SIZE(0..31))
    ACCESS read-write
    STATUS mandatory
    DESCRIPTION
	"The name of the GSLB remote site."
    ::= { gslbNewCfgRemSiteTableEntry 7 }

-- To allow configuring real server weight dynamically (For HP only)

dynSLBRealServerTable OBJECT-TYPE
    SYNTAX  SEQUENCE OF DynSLBRealServerEntry
    ACCESS  not-accessible
    STATUS  obsolete
    DESCRIPTION
        "The table of Real Servers."
    ::= { dynamicSLB 1 }

dynSLBRealServerEntry OBJECT-TYPE
    SYNTAX  DynSLBRealServerEntry
    ACCESS  not-accessible
    STATUS  obsolete
    DESCRIPTION
        "A row in the Real Server table."
   INDEX   { dynSLBRealServerIpAddr,
             dynSLBRealServerPortNum  }
    ::= { dynSLBRealServerTable 1 }
 
DynSLBRealServerEntry ::= SEQUENCE {
    dynSLBRealServerIpAddr     IpAddress,
    dynSLBRealServerPortNum    INTEGER,
    dynSLBRealServerWeight     INTEGER
    }
 
dynSLBRealServerIpAddr OBJECT-TYPE
    SYNTAX  IpAddress
    ACCESS  read-only
    STATUS  obsolete
    DESCRIPTION
        "IP address of the Real Server."
    ::= { dynSLBRealServerEntry 1 }
 
dynSLBRealServerPortNum OBJECT-TYPE
    SYNTAX  INTEGER
    ACCESS  read-only
    STATUS  obsolete
    DESCRIPTION
        "The switch port that the Real Server is connected to."
    ::= { dynSLBRealServerEntry 2 }

dynSLBRealServerWeight OBJECT-TYPE
    SYNTAX  INTEGER
    ACCESS  read-write
    STATUS  obsolete
    DESCRIPTION
        "The Real Server weight.  The higher the server weight means the 
         Real Server is allowed to receive more traffic load."
    ::= { dynSLBRealServerEntry 3 }

-- SLB Statistics Group

-- SLB Real Servers Statistics Table

slbStatRServerTable OBJECT-TYPE
    SYNTAX  SEQUENCE OF SlbStatRServerEntry
    ACCESS  not-accessible
    STATUS  mandatory
    DESCRIPTION
        "The real server statistics table."
    ::= { slbStats 5 }

slbStatRServerEntry OBJECT-TYPE
    SYNTAX  SlbStatRServerEntry
    ACCESS  not-accessible
    STATUS  mandatory
    DESCRIPTION
        "The statistics of a particular real server."
    INDEX   { slbStatRServerIndex }
    ::= { slbStatRServerTable 1 }

SlbStatRServerEntry ::= SEQUENCE {
    slbStatRServerIndex               INTEGER,
    slbStatRServerCurrSessions        Gauge,
    slbStatRServerTotalSessions       Counter,
    slbStatRServerFailures            Counter,
    slbStatRServerHighestSessions     Counter,
    slbStatRServerHCOctets            Counter64,   -- obsoleted 
    slbStatRServerHCOctetsLow32       Counter,
    slbStatRServerHCOctetsHigh32      Counter
    }

slbStatRServerIndex OBJECT-TYPE
    SYNTAX  INTEGER
    ACCESS  read-only
    STATUS  mandatory
    DESCRIPTION
        "The real server number that identifies the server." 
    ::= { slbStatRServerEntry 1 }

slbStatRServerCurrSessions OBJECT-TYPE 
    SYNTAX  Gauge
    ACCESS  read-only
    STATUS  mandatory 
    DESCRIPTION 
        "The number of sessions that are currently handled by the real server."
    ::= { slbStatRServerEntry 2 }

slbStatRServerTotalSessions OBJECT-TYPE 
    SYNTAX  Counter 
    ACCESS  read-only
    STATUS  mandatory 
    DESCRIPTION 
        "The total number of sessions that are handled by the real server."
    ::= { slbStatRServerEntry 3 }

slbStatRServerFailures OBJECT-TYPE 
    SYNTAX  Counter 
    ACCESS  read-only
    STATUS  mandatory 
    DESCRIPTION 
        "The total number of times that the real server is claimed down."
    ::= { slbStatRServerEntry 4 }

slbStatRServerHighestSessions OBJECT-TYPE 
    SYNTAX  Counter 
    ACCESS  read-only
    STATUS  mandatory 
    DESCRIPTION 
        "The highest sessions that have been handled by the real server."
    ::= { slbStatRServerEntry 5 }

slbStatRServerHCOctets OBJECT-TYPE 
    SYNTAX  Counter64
    ACCESS  read-only
    STATUS  obsolete
    DESCRIPTION 
        "The total number of octets received and transmitted out of the real 
         server."
    ::= { slbStatRServerEntry 6 }

slbStatRServerHCOctetsLow32 OBJECT-TYPE
    SYNTAX  Counter
    ACCESS  read-only
    STATUS  mandatory
    DESCRIPTION
        "The lower 32 bit value of octets received and transmitted out of the 
         real server."
    ::= { slbStatRServerEntry 7 }

slbStatRServerHCOctetsHigh32 OBJECT-TYPE
    SYNTAX  Counter
    ACCESS  read-only
    STATUS  mandatory
    DESCRIPTION
        "The higher 32 bit value of octets received and transmitted out
         of the real server."
    ::= { slbStatRServerEntry 8 }

-- SLB Real Server Groups Statistics Table

slbStatGroupTable OBJECT-TYPE
    SYNTAX  SEQUENCE OF SlbStatGroupEntry
    ACCESS  not-accessible
    STATUS  mandatory
    DESCRIPTION
        "The real server group statistics table."
    ::= { slbStats 6 }

slbStatGroupEntry OBJECT-TYPE
    SYNTAX  SlbStatGroupEntry
    ACCESS  not-accessible
    STATUS  mandatory
    DESCRIPTION
        "The statistics of a particular real server group."
    INDEX   { slbStatGroupIndex }
    ::= { slbStatGroupTable 1 }

SlbStatGroupEntry ::= SEQUENCE {
    slbStatGroupIndex               INTEGER,
    slbStatGroupCurrSessions        Gauge,
    slbStatGroupTotalSessions       Counter,
    slbStatGroupHighestSessions     Counter,
    slbStatGroupHCOctets            Counter64,   -- obsoleted
    slbStatGroupHCOctetsLow32       Counter,
    slbStatGroupHCOctetsHigh32      Counter
    }

slbStatGroupIndex OBJECT-TYPE
    SYNTAX  INTEGER
    ACCESS  read-only
    STATUS  mandatory
    DESCRIPTION
        "The real server group number that identifies the group." 
    ::= { slbStatGroupEntry 1 }

slbStatGroupCurrSessions OBJECT-TYPE 
    SYNTAX  Gauge
    ACCESS  read-only
    STATUS  mandatory 
    DESCRIPTION 
        "The number of sessions that are currently handled by the real server 
         group."
    ::= { slbStatGroupEntry 2 }

slbStatGroupTotalSessions OBJECT-TYPE 
    SYNTAX  Counter 
    ACCESS  read-only
    STATUS  mandatory 
    DESCRIPTION 
        "The total number of sessions that are handled by the real 
         server group."
    ::= { slbStatGroupEntry 3 }

slbStatGroupHighestSessions OBJECT-TYPE 
    SYNTAX  Counter 
    ACCESS  read-only
    STATUS  mandatory 
    DESCRIPTION 
        "The highest sessions that have been handled by the real server group."
    ::= { slbStatGroupEntry 4 }

slbStatGroupHCOctets OBJECT-TYPE 
    SYNTAX  Counter64
    ACCESS  read-only
    STATUS  obsolete
    DESCRIPTION 
        "The total number of octets received and transmitted out of the real 
         server group."
    ::= { slbStatGroupEntry 5 }

slbStatGroupHCOctetsLow32 OBJECT-TYPE
    SYNTAX  Counter
    ACCESS  read-only
    STATUS  mandatory
    DESCRIPTION
        "The lower 32 bit value of octets received and transmitted out of the 
         real server group."
    ::= { slbStatGroupEntry 6 }

slbStatGroupHCOctetsHigh32 OBJECT-TYPE
    SYNTAX  Counter
    ACCESS  read-only
    STATUS  mandatory
    DESCRIPTION
        "The higher 32 bit value of octets received and transmitted out
         of the real server group."
    ::= { slbStatGroupEntry 7 }

-- SLB Virtual Servers Statistics Table

slbStatVServerTable OBJECT-TYPE
    SYNTAX  SEQUENCE OF SlbStatVServerEntry
    ACCESS  not-accessible
    STATUS  mandatory
    DESCRIPTION
        "The virtual server statistics table."
    ::= { slbStats 7 }

slbStatVServerEntry OBJECT-TYPE
    SYNTAX  SlbStatVServerEntry
    ACCESS  not-accessible
    STATUS  mandatory
    DESCRIPTION
        "The statistics of a particular virtual server group."
    INDEX   { slbStatVServerIndex }
    ::= { slbStatVServerTable 1 }

SlbStatVServerEntry ::= SEQUENCE {
    slbStatVServerIndex                   INTEGER,
    slbStatVServerCurrSessions            Gauge,
    slbStatVServerTotalSessions           Counter,
    slbStatVServerHighestSessions         Counter,
    slbStatVServerHCOctets                Counter64,  -- obsoleted 
    slbStatVServerHCOctetsLow32           Counter,
    slbStatVServerHCOctetsHigh32          Counter,
    slbStatVServerHeaderHits              Counter,
    slbStatVServerHeaderMisses            Counter,
    slbStatVServerHeaderTotalSessions     Counter,
    slbStatVServerCookieRewrites          Counter,
    slbStatVServerCookieInserts           Counter
    }

slbStatVServerIndex OBJECT-TYPE
    SYNTAX  INTEGER
    ACCESS  read-only
    STATUS  mandatory
    DESCRIPTION
        "The virtual server number that identifies the server." 
    ::= { slbStatVServerEntry 1 }

slbStatVServerCurrSessions OBJECT-TYPE 
    SYNTAX  Gauge
    ACCESS  read-only
    STATUS  mandatory 
    DESCRIPTION 
        "The number of sessions that are currently handled by the 
         virtual server."
    ::= { slbStatVServerEntry 2 }

slbStatVServerTotalSessions OBJECT-TYPE 
    SYNTAX  Counter 
    ACCESS  read-only
    STATUS  mandatory 
    DESCRIPTION 
        "The total number of sessions that are handled by the virtual server."
    ::= { slbStatVServerEntry 3 }

slbStatVServerHighestSessions OBJECT-TYPE 
    SYNTAX  Counter 
    ACCESS  read-only
    STATUS  mandatory 
    DESCRIPTION 
        "The highest sessions that have been handled by the virtual server."
    ::= { slbStatVServerEntry 4 }

slbStatVServerHCOctets OBJECT-TYPE 
    SYNTAX  Counter64
    ACCESS  read-only
    STATUS  obsolete
    DESCRIPTION 
        "The total number of octets received and transmitted out of the 
         virtual server."
    ::= { slbStatVServerEntry 5 }

slbStatVServerHCOctetsLow32 OBJECT-TYPE
    SYNTAX  Counter
    ACCESS  read-only
    STATUS  mandatory
    DESCRIPTION
        "The lower 32 bit value of octets received and transmitted out
         of the virtual server."
    ::= { slbStatVServerEntry 6 }

slbStatVServerHCOctetsHigh32 OBJECT-TYPE
    SYNTAX  Counter
    ACCESS  read-only
    STATUS  mandatory
    DESCRIPTION
        "The higher 32 bit value of octets received and transmitted out
         of the virtual server."
    ::= { slbStatVServerEntry 7 }

--  HTTP Header LB stats 
slbStatVServerHeaderHits OBJECT-TYPE 
    SYNTAX  Counter 
    ACCESS  read-only
    STATUS  mandatory 
    DESCRIPTION 
        "The current HTTP header hits." 
    ::= { slbStatVServerEntry 8 }

slbStatVServerHeaderMisses OBJECT-TYPE 
    SYNTAX  Counter 
    ACCESS  read-only
    STATUS  mandatory 
    DESCRIPTION 
        "The current HTTP header misses."  
    ::= { slbStatVServerEntry 9 }

slbStatVServerHeaderTotalSessions OBJECT-TYPE 
    SYNTAX  Counter 
    ACCESS  read-only
    STATUS  mandatory 
    DESCRIPTION 
        "The total HTTP header sessions."
    ::= { slbStatVServerEntry 10 }

-- Cookie Statistics 
slbStatVServerCookieRewrites OBJECT-TYPE 
    SYNTAX  Counter 
    ACCESS  read-only
    STATUS  mandatory 
    DESCRIPTION 
        "The total Cookie Rewrites."
    ::= { slbStatVServerEntry 11 }

slbStatVServerCookieInserts OBJECT-TYPE 
    SYNTAX  Counter 
    ACCESS  read-only
    STATUS  mandatory 
    DESCRIPTION 
        "The total Cookie Inserts."
    ::= { slbStatVServerEntry 12 }

-- SLB Port Maintenance Statistics Table

slbStatPortMaintTable OBJECT-TYPE
    SYNTAX  SEQUENCE OF SlbStatPortMaintEntry
    ACCESS  not-accessible
    STATUS  mandatory
    DESCRIPTION
        "The table of SLB port maintenance statistics." 
    ::= { slbStats 1 }

slbStatPortMaintEntry OBJECT-TYPE
    SYNTAX  SlbStatPortMaintEntry
    ACCESS  not-accessible
    STATUS  mandatory
    DESCRIPTION
        "A row in the SLB port maintenance statistcs table."
    INDEX   { slbStatPortMaintPortIndex }
    ::= { slbStatPortMaintTable 1 }
 
SlbStatPortMaintEntry ::= SEQUENCE {
    slbStatPortMaintPortIndex                 INTEGER,
    slbStatPortMaintCurBindings               Gauge,
    slbStatPortMaintBindingFails              Counter,
    slbStatPortMaintNonTcpFrames              Counter,
    slbStatPortMaintTcpFragments              Counter,
    slbStatPortMaintUdpDatagrams              Counter,
    slbStatPortMaintIncorrectVIPs             Counter,
    slbStatPortMaintIncorrectVports           Counter,
    slbStatPortMaintRealServerNoAvails        Counter,
    slbStatPortMaintFilteredDeniedFrames      Counter,
    slbStatPortMaintCurBindings4Seconds	      Gauge,
    slbStatPortMaintCurBindings64Seconds      Gauge,
    slbStatPortMaintVMAdiscards               Counter
    }

slbStatPortMaintPortIndex OBJECT-TYPE
    SYNTAX  INTEGER
    ACCESS  read-only
    STATUS  mandatory
    DESCRIPTION
        "The port number for which the statistics apply."
    ::= { slbStatPortMaintEntry 1 }

slbStatPortMaintCurBindings OBJECT-TYPE
    SYNTAX  Gauge 
    ACCESS  read-only
    STATUS  mandatory
    DESCRIPTION
        "The current number of bindings on the port."
    ::= { slbStatPortMaintEntry 2 }

slbStatPortMaintBindingFails OBJECT-TYPE
    SYNTAX  Counter
    ACCESS  read-only
    STATUS  mandatory
    DESCRIPTION
        "The total number of Binding failures on the port. A Binding Failure 
         occurs when a port runs out of binding table entries."
    ::= { slbStatPortMaintEntry 3 }

slbStatPortMaintNonTcpFrames OBJECT-TYPE
    SYNTAX  Counter
    ACCESS  read-only
    STATUS  mandatory
    DESCRIPTION
        "The total number of non-TCP/IP frames dropped on the port."
    ::= { slbStatPortMaintEntry 4 }

slbStatPortMaintTcpFragments OBJECT-TYPE
    SYNTAX  Counter
    ACCESS  read-only
    STATUS  mandatory
    DESCRIPTION
        "The total number of TCP fragments dropped on the port."
    ::= { slbStatPortMaintEntry 5 }

slbStatPortMaintUdpDatagrams OBJECT-TYPE
    SYNTAX  Counter
    ACCESS  read-only
    STATUS  mandatory
    DESCRIPTION
        "The total number of UDP datagrams dropped on the port."
    ::= { slbStatPortMaintEntry 6 }

slbStatPortMaintIncorrectVIPs OBJECT-TYPE
    SYNTAX  Counter
    ACCESS  read-only
    STATUS  mandatory
    DESCRIPTION
        "The total number of frames with incorrect VIPs that are dropped on 
         the port."
    ::= { slbStatPortMaintEntry 7 }

slbStatPortMaintIncorrectVports OBJECT-TYPE
    SYNTAX  Counter
    ACCESS  read-only
    STATUS  mandatory
    DESCRIPTION
        "The total number of frames with incorrect Virtual Port
	 that are dropped on the port."
    ::= { slbStatPortMaintEntry 8 }

slbStatPortMaintRealServerNoAvails OBJECT-TYPE
    SYNTAX  Counter
    ACCESS  read-only
    STATUS  mandatory
    DESCRIPTION
        "The total number of frames that are dropped on the port
	 because no real server is available."
    ::= { slbStatPortMaintEntry 9 }

slbStatPortMaintFilteredDeniedFrames OBJECT-TYPE
    SYNTAX  Counter
    ACCESS  read-only
    STATUS  mandatory
    DESCRIPTION
        "The total number of frames that are denied on the port by the filter."
    ::= { slbStatPortMaintEntry 10 }

slbStatPortMaintCurBindings4Seconds OBJECT-TYPE
    SYNTAX  Gauge 
    ACCESS  read-only
    STATUS  mandatory
    DESCRIPTION
        "The 4 second average current number of bindings on the port."
    ::= { slbStatPortMaintEntry 11 }

slbStatPortMaintCurBindings64Seconds OBJECT-TYPE
    SYNTAX  Gauge 
    ACCESS  read-only
    STATUS  mandatory
    DESCRIPTION
        "The 64 second average current number of bindings on the port."
    ::= { slbStatPortMaintEntry 12 }

slbStatPortMaintVMAdiscards OBJECT-TYPE
    SYNTAX  Counter
    ACCESS  read-only
    STATUS  mandatory
    DESCRIPTION
        "The total number of internal VMA frames dropped by the port."
    ::= { slbStatPortMaintEntry 13 }

-- SLB Port to Real Servers Statistics Table

slbStatPortRealServerTable OBJECT-TYPE
    SYNTAX  SEQUENCE OF SlbStatPortRealServerEntry
    ACCESS  not-accessible
    STATUS  mandatory
    DESCRIPTION
        "The port-server statistics table.  This table shows the statistics 
         of real servers that are connectted to switch ports."
    ::= { slbStats 2 }

slbStatPortRealServerEntry OBJECT-TYPE
    SYNTAX  SlbStatPortRealServerEntry
    ACCESS  not-accessible
    STATUS  mandatory
    DESCRIPTION
        "A row in the port-server statistics table."
    INDEX  { slbStatPortRealServerPortIndex, slbStatPortRealServerServerIndex }
    ::= { slbStatPortRealServerTable 1 }

SlbStatPortRealServerEntry ::= SEQUENCE {
    slbStatPortRealServerPortIndex             INTEGER,
    slbStatPortRealServerServerIndex           INTEGER,
    slbStatPortRealServerCurrSessions          Gauge,
    slbStatPortRealServerTotalSessions         Counter,
    slbStatPortRealServerHCOctets              Counter64,  -- obsoleted 
    slbStatPortRealServerHCOctetsLow32         Counter,
    slbStatPortRealServerHCOctetsHigh32        Counter
    }

slbStatPortRealServerPortIndex OBJECT-TYPE
    SYNTAX  INTEGER
    ACCESS  read-only
    STATUS  mandatory
    DESCRIPTION
        "The port number that identifies the switch port."
    ::= { slbStatPortRealServerEntry 1 }

slbStatPortRealServerServerIndex OBJECT-TYPE 
    SYNTAX  INTEGER 
    ACCESS  read-only
    STATUS  mandatory 
    DESCRIPTION 
        "The real server number that identifies the server." 
    ::= { slbStatPortRealServerEntry 2 }

slbStatPortRealServerCurrSessions OBJECT-TYPE 
    SYNTAX  Gauge
    ACCESS  read-only
    STATUS  mandatory 
    DESCRIPTION 
        "The current sessions for the real server."
    ::= { slbStatPortRealServerEntry 3 }

slbStatPortRealServerTotalSessions OBJECT-TYPE 
    SYNTAX  Counter 
    ACCESS  read-only
    STATUS  mandatory 
    DESCRIPTION 
        "The total number of sessions for the real server."
    ::= { slbStatPortRealServerEntry 4 }

slbStatPortRealServerHCOctets OBJECT-TYPE 
    SYNTAX  Counter64
    ACCESS  read-only
    STATUS  obsolete
    DESCRIPTION 
        "The total number of octets received and transmitted out of the real 
         server on a particular port."
    ::= { slbStatPortRealServerEntry 5 }

slbStatPortRealServerHCOctetsLow32 OBJECT-TYPE
    SYNTAX  Counter
    ACCESS  read-only
    STATUS  mandatory
    DESCRIPTION
        "The lower 32 bit value of the total octets received and transmitted 
         out of the real server on a particular port."
    ::= { slbStatPortRealServerEntry 6 }

slbStatPortRealServerHCOctetsHigh32 OBJECT-TYPE
    SYNTAX  Counter
    ACCESS  read-only
    STATUS  mandatory
    DESCRIPTION
        "The higher 32 bit value of the total octets received and transmitted 
         out of the real server on a particular port."
    ::= { slbStatPortRealServerEntry 7 }

-- SLB Maintenance Statistics Table

slbMaintStats    OBJECT IDENTIFIER ::= { slbStats  8 }

slbIncorrectVirtServs OBJECT-TYPE 
    SYNTAX  Counter 
    ACCESS  read-only
    STATUS  mandatory 
    DESCRIPTION 
        "Incorrect Virtual Servers specified for Server Load Balancing."
    ::= { slbMaintStats 1 }

slbIncorrectVports OBJECT-TYPE 
    SYNTAX  Counter  
    ACCESS  read-only
    STATUS  mandatory 
    DESCRIPTION 
        "Incorrect Virtual ports specified for Server Load Balancing."
    ::= { slbMaintStats 2 }

slbNoRealServs OBJECT-TYPE 
    SYNTAX  Counter  
    ACCESS  read-only
    STATUS  mandatory 
    DESCRIPTION 
        "No Real Servers specified for Server Load Balancing."
    ::= { slbMaintStats 3 }

wapMaintStats    OBJECT IDENTIFIER ::= { slbMaintStats  4 }

radiusAcctReqsStats     OBJECT IDENTIFIER ::= { wapMaintStats 1 }
tpcpAddSessReqsStats    OBJECT IDENTIFIER ::= { wapMaintStats 2 }
tpcpDeleteSessReqsStats OBJECT IDENTIFIER ::= { wapMaintStats 3 }

radiusAcctReqs OBJECT-TYPE 
    SYNTAX  Counter 
    ACCESS  read-only
    STATUS  mandatory 
    DESCRIPTION 
        "Radius Account Request."
    ::= { radiusAcctReqsStats 1 }

radiusAcctWrapReqs OBJECT-TYPE 
    SYNTAX  Counter 
    ACCESS  read-only
    STATUS  mandatory 
    DESCRIPTION 
        "Radius Account Wrap Request."
    ::= { radiusAcctReqsStats 2 }

radiusAcctStartReqs OBJECT-TYPE 
    SYNTAX  Counter 
    ACCESS  read-only
    STATUS  mandatory 
    DESCRIPTION 
        "Radius Account Start Request."
    ::= { radiusAcctReqsStats 3 }

radiusAcctUpdateReqs OBJECT-TYPE 
    SYNTAX  Counter 
    ACCESS  read-only
    STATUS  mandatory 
    DESCRIPTION 
        "Radius Account Update Request."
    ::= { radiusAcctReqsStats 4 }

radiusAcctStopReqs OBJECT-TYPE 
    SYNTAX  Counter 
    ACCESS  read-only
    STATUS  mandatory 
    DESCRIPTION 
        "Radius Account stop Request."
    ::= { radiusAcctReqsStats 5 }

radiusAcctBadReqs OBJECT-TYPE 
    SYNTAX  Counter 
    ACCESS  read-only
    STATUS  mandatory 
    DESCRIPTION 
        "Radius Account Bad Request."
    ::= { radiusAcctReqsStats 6 }

radiusAcctAddSessionReqs OBJECT-TYPE 
    SYNTAX  Counter 
    ACCESS  read-only
    STATUS  mandatory 
    DESCRIPTION 
        "Radius Account add session Request."
    ::= { radiusAcctReqsStats 7 }

radiusAcctDeleteSessionReqs OBJECT-TYPE 
    SYNTAX  Counter 
    ACCESS  read-only
    STATUS  mandatory 
    DESCRIPTION 
        "Radius Account delete session Request."
    ::= { radiusAcctReqsStats 8 }

radiusAcctReqFailsQFull OBJECT-TYPE 
    SYNTAX  Counter 
    ACCESS  read-only
    STATUS  mandatory 
    DESCRIPTION 
        "Radius Account request fails Queue Full."
    ::= { radiusAcctReqsStats 9 }

radiusAcctReqFailsSPDead OBJECT-TYPE 
    SYNTAX  Counter 
    ACCESS  read-only
    STATUS  mandatory 
    DESCRIPTION 
        "Radius Account request fails SP Dead."
    ::= { radiusAcctReqsStats 10 }

radiusAcctReqFailsDMAFails OBJECT-TYPE 
    SYNTAX  Counter 
    ACCESS  read-only
    STATUS  mandatory 
    DESCRIPTION 
        "Radius Account request fails DMA fails."
    ::= { radiusAcctReqsStats 11 }

radiusAcctMaxEntriesInUse OBJECT-TYPE 
    SYNTAX  Counter 
    ACCESS  read-only
    STATUS  mandatory 
    DESCRIPTION 
        "Radius Account Maximum Entries in use."
    ::= { radiusAcctReqsStats 12 }

tpcpAddSessReqs OBJECT-TYPE 
    SYNTAX  Counter 
    ACCESS  read-only
    STATUS  mandatory 
    DESCRIPTION 
        "WAP add Session requests." 
    ::= { tpcpAddSessReqsStats 1 }

tpcpAddSessReqsFailsQFull OBJECT-TYPE 
    SYNTAX  Counter 
    ACCESS  read-only
    STATUS  mandatory 
    DESCRIPTION 
        "WAP add Session Fails as the Queue is Full."
    ::= { tpcpAddSessReqsStats 2 }

tpcpAddSessReqsFailsSPDead OBJECT-TYPE 
    SYNTAX  Counter 
    ACCESS  read-only
    STATUS  mandatory 
    DESCRIPTION 
        "WAP add Session Fails as the SP is dead."
    ::= { tpcpAddSessReqsStats 3 }

tpcpAddSessReqsEntriesInUse OBJECT-TYPE 
    SYNTAX  Counter 
    ACCESS  read-only
    STATUS  mandatory 
    DESCRIPTION 
        "WAP add Session Entries currently in use."
    ::= { tpcpAddSessReqsStats 4 }

tpcpAddSessReqsMaxEntriesInUse OBJECT-TYPE 
    SYNTAX  Counter 
    ACCESS  read-only
    STATUS  mandatory 
    DESCRIPTION 
        "The allowable maximum number of WAP add Session Entries."
    ::= { tpcpAddSessReqsStats 5 }

tpcpDeleteSessReqs OBJECT-TYPE 
    SYNTAX  Counter 
    ACCESS  read-only
    STATUS  mandatory 
    DESCRIPTION 
        "TPCP Delete Session Requests." 
    ::= { tpcpDeleteSessReqsStats 1 }

tpcpDeleteSessReqsFailsQFull OBJECT-TYPE 
    SYNTAX  Counter 
    ACCESS  read-only
    STATUS  mandatory 
    DESCRIPTION 
        "TPCP Delete Session Fails as the Queue is Full."
    ::= { tpcpDeleteSessReqsStats 2 }

tpcpDeleteSessReqsFailsSPDead OBJECT-TYPE 
    SYNTAX  Counter 
    ACCESS  read-only
    STATUS  mandatory 
    DESCRIPTION 
        "TPCP Delete Session Fails as the SP is dead."
    ::= { tpcpDeleteSessReqsStats 3 }

tpcpDeleteSessReqsEntriesInUse OBJECT-TYPE 
    SYNTAX  Counter 
    ACCESS  read-only
    STATUS  mandatory 
    DESCRIPTION 
        "TPCP Delete Session Entries currently in use."
    ::= { tpcpDeleteSessReqsStats 4 }

tpcpDeleteSessReqsMaxEntriesInUse OBJECT-TYPE 
    SYNTAX  Counter 
    ACCESS  read-only
    STATUS  mandatory 
    DESCRIPTION 
        "The allowable maximum number of TPCP delete Session Entries."
    ::= { tpcpDeleteSessReqsStats 5 }

wapRequestToWrongSP OBJECT-TYPE 
    SYNTAX  Counter 
    ACCESS  read-only
    STATUS  mandatory 
    DESCRIPTION 
        "The  WAP delete Session Entries sent to wrong SP."
    ::= { wapMaintStats 4 }

-- SLB General Statistics

slbStatMaintBackupServActs OBJECT-TYPE
    SYNTAX  Counter
    ACCESS  read-only
    STATUS  mandatory
    DESCRIPTION
        "The total number of times that backup servers become active due 
         to failure of primary servers."
    ::= { slbStats 3 }

slbStatMaintOverflowServActs OBJECT-TYPE
    SYNTAX  Counter
    ACCESS  read-only
    STATUS  mandatory
    DESCRIPTION
        "The total number of times that backup servers become
	 active due to primary servers reach overflow situation."
    ::= { slbStats 4 }

-- Filter Statistics

fltStatTable OBJECT-TYPE
    SYNTAX  SEQUENCE OF FltStatTableEntry
    ACCESS  not-accessible
    STATUS  mandatory
    DESCRIPTION
        "The filter statistics table."
    ::= { filterStats 1 }

fltStatTableEntry OBJECT-TYPE
    SYNTAX  FltStatTableEntry
    ACCESS  not-accessible
    STATUS  mandatory
    DESCRIPTION
        "A row in filter statistics table."
    INDEX   { fltStatFltIndex }
    ::= { fltStatTable 1 }

FltStatTableEntry ::= SEQUENCE {
    fltStatFltIndex     INTEGER,
    fltStatFltFirings	Counter
    }

fltStatFltIndex OBJECT-TYPE 
    SYNTAX  INTEGER 
    ACCESS  read-only
    STATUS  mandatory 
    DESCRIPTION 
        "The number that identifies the filter." 
    ::= { fltStatTableEntry 1 }

fltStatFltFirings OBJECT-TYPE 
    SYNTAX  Counter 
    ACCESS  read-only
    STATUS  mandatory 
    DESCRIPTION 
        "The number of instances that the received packet matches the 
         filter rule."
    ::= { fltStatTableEntry 2 }

-- Global SLB Statitistics

-- GSLB Remote Real Server Statistics

gslbStatRemRealServerTable OBJECT-TYPE
    SYNTAX  SEQUENCE OF GslbStatRemRealServerEntry
    ACCESS  not-accessible
    STATUS  mandatory
    DESCRIPTION
        "The GSLB remote real server statistics table."
    ::= { gslbStats 1 }

gslbStatRemRealServerEntry OBJECT-TYPE
    SYNTAX  GslbStatRemRealServerEntry
    ACCESS  not-accessible
    STATUS  mandatory
    DESCRIPTION
        "A row in the remote real server statistics table."
    INDEX   { gslbStatRemRealServerIndex }
    ::= { gslbStatRemRealServerTable 1 }

GslbStatRemRealServerEntry ::=	SEQUENCE {
    gslbStatRemRealServerIndex          INTEGER,
    gslbStatRemRealServerDnsHandoffs    Counter,
    gslbStatRemRealServerHttpRedirs     Counter
    }

gslbStatRemRealServerIndex OBJECT-TYPE 
    SYNTAX  INTEGER 
    ACCESS  read-only
    STATUS  mandatory 
    DESCRIPTION 
        "The server number that identifies the remote real server." 
    ::= { gslbStatRemRealServerEntry 1 }

gslbStatRemRealServerDnsHandoffs OBJECT-TYPE 
    SYNTAX  Counter 
    ACCESS  read-only
    STATUS  mandatory 
    DESCRIPTION 
        "The number of DNS hanfoffs by the remote real server."
    ::= { gslbStatRemRealServerEntry 2 }

gslbStatRemRealServerHttpRedirs OBJECT-TYPE 
    SYNTAX  Counter 
    ACCESS  read-only
    STATUS  mandatory 
    DESCRIPTION 
        "The number of HTTP redirections by the remote real server."
    ::= { gslbStatRemRealServerEntry 3 }

-- The GSLB Maintenance Statistics

gslbStatMaintInGoodSiteUpdates OBJECT-TYPE 
    SYNTAX  Counter 
    ACCESS  read-only
    STATUS  mandatory 
    DESCRIPTION 
        "The number of good remote site updates which are received."
    ::= { gslbMaintStats 1 }

gslbStatMaintInBadSiteUpdates OBJECT-TYPE 
    SYNTAX  Counter 
    ACCESS  read-only
    STATUS  mandatory 
    DESCRIPTION 
        "The number of bad remote site updates which are received."
    ::= { gslbMaintStats 2 }

-- The URL Redirection/Load Balancing Statistics

urlRedirStats    OBJECT IDENTIFIER ::= { urlStats  1 }

urlStatRedRedirs OBJECT-TYPE 
    SYNTAX  Counter 
    ACCESS  read-only
    STATUS  mandatory 
    DESCRIPTION 
        "The number of instances that the received packet matches the 
         specified URL expressions and redirected to specified group of 
         real servers."
    ::= { urlRedirStats 1 }

urlStatRedOrigSrvs OBJECT-TYPE 
    SYNTAX  Counter 
    ACCESS  read-only
    STATUS  mandatory 
    DESCRIPTION 
        "The number of instances that the received packet is sent to the 
         origin server due to mis-match with the specified URL expressions 
         or detecting of HTTP non-GETs,user cookies, and no-cache as users 
         configuration."
    ::= { urlRedirStats 2 }

urlStatRedNonGets OBJECT-TYPE 
    SYNTAX  Counter 
    ACCESS  read-only
    STATUS  mandatory 
    DESCRIPTION 
        "The number of instances that the received packet contains 
         none GETs(POST ,HEAD ,PUT..) methods."
    ::= { urlRedirStats 3 }

urlStatRedCookie OBJECT-TYPE 
    SYNTAX  Counter 
    ACCESS  read-only
    STATUS  mandatory 
    DESCRIPTION 
        "The number of instances that the received packet contains
         a 'Cookie: ' header."
    ::= { urlRedirStats 4 }

urlStatRedNoCache OBJECT-TYPE 
    SYNTAX  Counter 
    ACCESS  read-only
    STATUS  mandatory 
    DESCRIPTION 
        "The number of instances that the received packet contains
         a no-cache header value."
    ::= { urlRedirStats 5 }

urlSlbStats    OBJECT IDENTIFIER ::= { urlStats  2 }

urlStatSlbPathTable OBJECT-TYPE
    SYNTAX  SEQUENCE OF UrlStatSlbPathTableEntry
    ACCESS  not-accessible
    STATUS  mandatory
    DESCRIPTION
        "The statistics table of instances that URL pathes matched."
    ::= { urlSlbStats 1 }

urlStatSlbPathTableEntry OBJECT-TYPE
    SYNTAX  UrlStatSlbPathTableEntry
    ACCESS  not-accessible
    STATUS  mandatory
    DESCRIPTION
        "Information about the number of instances that are 
	 load-balanced due to match of a particular URL path."
    INDEX   { slbCurCfgUrlLbPathIndex }
    ::= { urlStatSlbPathTable 1 }

UrlStatSlbPathTableEntry ::= SEQUENCE {
    urlStatSlbPathIndex       INTEGER,
    urlStatSlbPathHits        Counter
    }

urlStatSlbPathIndex OBJECT-TYPE
    SYNTAX  INTEGER
    ACCESS  read-only
    STATUS  mandatory
    DESCRIPTION
        "The URL path table index."
    ::= { urlStatSlbPathTableEntry 1 }

urlStatSlbPathHits OBJECT-TYPE
    SYNTAX  Counter
    ACCESS  read-only
    STATUS  mandatory
    DESCRIPTION
        "The number of instances that are load-balanced due to match of 
         the particular URL path."
    ::= { urlStatSlbPathTableEntry 2 }

-- TCP Statistics

tcpStatCurConns OBJECT-TYPE
    SYNTAX  Gauge 
    ACCESS  read-only
    STATUS  mandatory
    DESCRIPTION
	"The number of outstanding TCP current connections have been 
	 established."
    ::= { tcpStats 1 }

tcpStatHalfOpens OBJECT-TYPE
    SYNTAX  Gauge 
    ACCESS  read-only
    STATUS  mandatory
    DESCRIPTION
	"The number of outstanding TCP connections have been half opened.
	 This statistics is valid only when URL parsing has been truned on.
	 It is incremented when the switch respond to TCP SYN packet and 
	 decremented upon receiving TCP SYN ACK packet from the requester."
    ::= { tcpStats 2 }

-- FTP Passive SLB/NAT Statistics

ftpSlbStats      OBJECT IDENTIFIER ::= { ftpStats  1 }

ftpSlbStatTotal  OBJECT-TYPE
    SYNTAX  Counter
    ACCESS  read-only
    STATUS  mandatory
    DESCRIPTION
        "The total number of ftp control sesssion for SLB received after 
         FTP parsing turn on."
    ::= { ftpSlbStats 1 }

ftpNatStatTotal  OBJECT-TYPE
    SYNTAX  Counter
    ACCESS  read-only
    STATUS  mandatory
    DESCRIPTION
	"The total number of FTP control session for NAT received after 
         active FTP is turn on."
    ::= { ftpSlbStats 2 } 

-- RURL statistics

-- RURL Error Statisitics

rurlErrorStats    OBJECT IDENTIFIER ::= { rurlStats  1 }

rurlErrorStatConnect OBJECT-TYPE 
    SYNTAX  Counter 
    ACCESS  read-only
    STATUS  mandatory 
    DESCRIPTION 
        "Total number of session connect errors to the iSD."
    ::= { rurlErrorStats 1 }

rurlErrorStatPack OBJECT-TYPE 
    SYNTAX  Counter 
    ACCESS  read-only
    STATUS  mandatory 
    DESCRIPTION 
        "Total number of errors associated with packaging the RURL data
         frame received from the iSD."
    ::= { rurlErrorStats 2 }

rurlErrorStatUnpack OBJECT-TYPE 
    SYNTAX  Counter 
    ACCESS  read-only
    STATUS  mandatory 
    DESCRIPTION 
        "Total number of errors associated with unpackaging the RURL data
         frame received from the iSD."
    ::= { rurlErrorStats 3 }

rurlErrorStatDma OBJECT-TYPE 
    SYNTAX  Counter 
    ACCESS  read-only
    STATUS  mandatory 
    DESCRIPTION 
        "Total number of DMA write errors."
    ::= { rurlErrorStats 4 }

rurlErrorStatBuf OBJECT-TYPE 
    SYNTAX  Counter 
    ACCESS  read-only
    STATUS  mandatory 
    DESCRIPTION 
        "Total number of errors associated with no available buffers to
         to store the RURL redirection information."
    ::= { rurlErrorStats 5 }

rurlErrorStatBufWrap OBJECT-TYPE 
    SYNTAX  Counter 
    ACCESS  read-only
    STATUS  mandatory 
    DESCRIPTION 
        "Total number of errors associated with buffer wrap copies."
    ::= { rurlErrorStats 6 }

rurlErrorStatProto OBJECT-TYPE 
    SYNTAX  Counter 
    ACCESS  read-only
    STATUS  mandatory 
    DESCRIPTION 
        "Total number of errors associated with packets containing an 
         invalid protocol type. Expected protocol types are TCP and UDP."
    ::= { rurlErrorStats 7 }

-- RURL Information Statistics

rurlInfoStats     OBJECT IDENTIFIER ::= { rurlStats  2 }

rurlInfoStatClientWrap OBJECT-TYPE 
    SYNTAX  Counter 
    ACCESS  read-only
    STATUS  mandatory 
    DESCRIPTION 
        "Total number of client packets processed using frame wrap buffers."
    ::= { rurlInfoStats 1 }

rurlInfoStatServerWrap OBJECT-TYPE 
    SYNTAX  Counter 
    ACCESS  read-only
    STATUS  mandatory 
    DESCRIPTION 
        "Total number of server packets processed using frame wrap buffers."
    ::= { rurlInfoStats 2 }

rurlInfoStatBufWrap OBJECT-TYPE 
    SYNTAX  Counter 
    ACCESS  read-only
    STATUS  mandatory 
    DESCRIPTION 
        "Total number of packets processed using RURL wrap copy mechanism."
    ::= { rurlInfoStats 3 }

rurlInfoStatFreeRingCalls OBJECT-TYPE 
    SYNTAX  Counter 
    ACCESS  read-only
    STATUS  mandatory 
    DESCRIPTION 
        "Total number of RURL sequence buffer frees."
    ::= { rurlInfoStats 4 }

rurlInfoStatClientResets OBJECT-TYPE 
    SYNTAX  Counter 
    ACCESS  read-only
    STATUS  mandatory 
    DESCRIPTION 
        "Total number of client resets by the switch."
    ::= { rurlInfoStats 5 }

rurlInfoStatServerResets OBJECT-TYPE 
    SYNTAX  Counter 
    ACCESS  read-only
    STATUS  mandatory 
    DESCRIPTION 
        "Total number of server resets by the switch."
    ::= { rurlInfoStats 6 }

rurlInfoStatFramePassThru OBJECT-TYPE 
    SYNTAX  Counter 
    ACCESS  read-only
    STATUS  mandatory 
    DESCRIPTION 
        "Total number of packets dropped to L2 processing due to the switch
         running out of resources."
    ::= { rurlInfoStats 7 }

rurlInfoStatParseFiltMiss OBJECT-TYPE 
    SYNTAX  Counter 
    ACCESS  read-only
    STATUS  mandatory 
    DESCRIPTION 
        "Total number of packets leaking from RURL parsing to URL parsing."
    ::= { rurlInfoStats 8 }

rurlInfoStatExceedBufLen OBJECT-TYPE 
    SYNTAX  Counter 
    ACCESS  read-only
    STATUS  mandatory 
    DESCRIPTION 
        "Total number of occurences where the client request bytes exceed the 
         maximum buffer size allocated by the switch."
    ::= { rurlInfoStats 9 }

rurlInfoStatExceedFrameDepth OBJECT-TYPE 
    SYNTAX  Counter 
    ACCESS  read-only
    STATUS  mandatory 
    DESCRIPTION 
        "Total number of occurences where the client request bytes exceed the 
         maximum buffer depth allocated by the switch."
    ::= { rurlInfoStats 10 }

rurlInfoStatZeroContentLen OBJECT-TYPE 
    SYNTAX  Counter 
    ACCESS  read-only
    STATUS  mandatory 
    DESCRIPTION 
        "Total number of occurences where the Content-Length of the HTTP 
         request is zero."
    ::= { rurlInfoStats 11 }

rurlInfoStatNonTypicalOffsets OBJECT-TYPE 
    SYNTAX  Counter 
    ACCESS  read-only
    STATUS  mandatory 
    DESCRIPTION 
        "Total number of occurences where the RURL header offsets are 
         non-typical."
    ::= { rurlInfoStats 12 }

rurlInfoStatFINRSTSessSetup OBJECT-TYPE 
    SYNTAX  Counter 
    ACCESS  read-only
    STATUS  mandatory 
    DESCRIPTION 
        "Total number of occurences where a FIN or RST packet is used to 
         establish a new session in the switch."
    ::= { rurlInfoStats 13 }

rurlInfoStatPSHSessSetup OBJECT-TYPE 
    SYNTAX  Counter 
    ACCESS  read-only
    STATUS  mandatory 
    DESCRIPTION 
        "Total number of occurences where a PSH packet is used to 
         establish a new session in the switch."
    ::= { rurlInfoStats 14 }

rurlInfoStatNonSYNSessSetup OBJECT-TYPE 
    SYNTAX  Counter 
    ACCESS  read-only
    STATUS  mandatory 
    DESCRIPTION 
        "Total number of occurences where a non-SYN packet is used to 
         establish a new session in the switch."
    ::= { rurlInfoStats 15 }

rurlInfoStatL7BindCalls OBJECT-TYPE 
    SYNTAX  Counter 
    ACCESS  read-only
    STATUS  mandatory 
    DESCRIPTION 
        "Total number of requests to bind a session."
    ::= { rurlInfoStats 16 }

rurlInfoStatSessSetups OBJECT-TYPE 
    SYNTAX  Counter 
    ACCESS  read-only
    STATUS  mandatory 
    DESCRIPTION 
        "Total number of RURL session setups encountered."
    ::= { rurlInfoStats 17 }

rurlInfoStatMiscProcess OBJECT-TYPE 
    SYNTAX  Counter 
    ACCESS  read-only
    STATUS  mandatory 
    DESCRIPTION 
        "Total number of sessions falling through the filter processing."
    ::= { rurlInfoStats 18 }

rurlInfoStatClientPktsIn OBJECT-TYPE 
    SYNTAX  Counter 
    ACCESS  read-only
    STATUS  mandatory 
    DESCRIPTION 
        "Total number of client packets processed by the RURL filter."
    ::= { rurlInfoStats 19 }

rurlInfoStatClientSYNsIn OBJECT-TYPE 
    SYNTAX  Counter 
    ACCESS  read-only
    STATUS  mandatory 
    DESCRIPTION 
        "Total number of client SYN packets processed by the RURL filter."
    ::= { rurlInfoStats 20 }

rurlInfoStatClientReTXSYNsSeen OBJECT-TYPE 
    SYNTAX  Counter 
    ACCESS  read-only
    STATUS  mandatory 
    DESCRIPTION 
        "Total number of client retransmitted SYN packets processed by 
         the RURL filter."
    ::= { rurlInfoStats 21 }

rurlInfoStatClientSYNACKsSent OBJECT-TYPE 
    SYNTAX  Counter 
    ACCESS  read-only
    STATUS  mandatory 
    DESCRIPTION 
        "Total number of switch-to-client SYN/ACK packets processed by 
         the RURL filter."
    ::= { rurlInfoStats 22 }

rurlInfoStatClientACKsIn OBJECT-TYPE 
    SYNTAX  Counter 
    ACCESS  read-only
    STATUS  mandatory 
    DESCRIPTION 
        "Total number of client ACK packets processed by the RURL filter."
    ::= { rurlInfoStats 23 }

rurlInfoStatClientDataIn OBJECT-TYPE 
    SYNTAX  Counter 
    ACCESS  read-only
    STATUS  mandatory 
    DESCRIPTION 
        "Total number of client PSH packets processed by the RURL filter."
    ::= { rurlInfoStats 24 }

rurlInfoStatClientDataRetx OBJECT-TYPE 
    SYNTAX  Counter 
    ACCESS  read-only
    STATUS  mandatory 
    DESCRIPTION 
        "Total number of client data retransmit packets processed by 
         the RURL filter."
    ::= { rurlInfoStats 25 }

rurlInfoStatServerSYNsSent OBJECT-TYPE 
    SYNTAX  Counter 
    ACCESS  read-only
    STATUS  mandatory 
    DESCRIPTION 
        "Total number of SYN packets sent to the server by the switch."
    ::= { rurlInfoStats 26 }

rurlInfoStatServerSYNACKsIn OBJECT-TYPE 
    SYNTAX  Counter 
    ACCESS  read-only
    STATUS  mandatory 
    DESCRIPTION 
        "Total number of swtich-to-server SYN/ACK packets processed by 
         the RURL filter."
    ::= { rurlInfoStats 27 }

rurlInfoStatServerACKsSent OBJECT-TYPE 
    SYNTAX  Counter 
    ACCESS  read-only
    STATUS  mandatory 
    DESCRIPTION 
        "Total number of ACK packets sent to the server by the switch."
    ::= { rurlInfoStats 28 }

rurlInfoStatServerACKsIn OBJECT-TYPE 
    SYNTAX  Counter 
    ACCESS  read-only
    STATUS  mandatory 
    DESCRIPTION 
        "Total number of server-to-switch ACK packets processed by the 
         RURL filters."
    ::= { rurlInfoStats 29 }

rurlInfoStatServerSYNsRetx OBJECT-TYPE 
    SYNTAX  Counter 
    ACCESS  read-only
    STATUS  mandatory 
    DESCRIPTION 
        "Total number of retransmitted SYN packets sent to the server by 
         the switch that resulted in an error."
    ::= { rurlInfoStats 30 }

rurlInfoStatServerSYNsRetxErrors OBJECT-TYPE 
    SYNTAX  Counter 
    ACCESS  read-only
    STATUS  mandatory 
    DESCRIPTION 
        "Total number of ACK packets sent to the server by the switch."
    ::= { rurlInfoStats 31 }

rurlInfoStatL7SessionReuse OBJECT-TYPE 
    SYNTAX  Counter 
    ACCESS  read-only
    STATUS  mandatory 
    DESCRIPTION 
        "Total number of SYN requests that matched a session lookup due 
         to an accidental reuse of a session table entry. This is typically 
         a result of port wrap/reuse on a client generally running 
         performance testing."
    ::= { rurlInfoStats 32 }

rurlInfoStatConnSpliced OBJECT-TYPE 
    SYNTAX  Counter 
    ACCESS  read-only
    STATUS  mandatory 
    DESCRIPTION 
        "Total number of connections successfully spliced by the switch."
    ::= { rurlInfoStats 33 }

-- RURL Maintenance Statistics

rurlMaintStats    OBJECT IDENTIFIER ::= { rurlStats  3 }

rurlMaintStatOrgServerHits OBJECT-TYPE 
    SYNTAX  Counter 
    ACCESS  read-only
    STATUS  mandatory 
    DESCRIPTION 
        "Total number of session setups to the end server."
    ::= { rurlMaintStats 1 }

rurlMaintStatHTTPRedirs OBJECT-TYPE 
    SYNTAX  Counter 
    ACCESS  read-only
    STATUS  mandatory 
    DESCRIPTION 
        "Total number of HTTP redirect responses to the client."
    ::= { rurlMaintStats 2 }

rurlMaintStatServerReqs OBJECT-TYPE 
    SYNTAX  Counter 
    ACCESS  read-only
    STATUS  mandatory 
    DESCRIPTION 
        "Total number of request packets sent from the switch to the iSD."
    ::= { rurlMaintStats 3 }

rurlMaintStatServerAcks OBJECT-TYPE 
    SYNTAX  Counter 
    ACCESS  read-only
    STATUS  mandatory 
    DESCRIPTION 
        "Total number of response packets sent from the iSD to the switch."
    ::= { rurlMaintStats 4 }

rurlMaintStatSessCnt OBJECT-TYPE 
    SYNTAX  Counter 
    ACCESS  read-only
    STATUS  mandatory 
    DESCRIPTION 
        "Total number of session connections to the iSD made by the switch."
    ::= { rurlMaintStats 5 }

rurlMaintStatLastFrameCnt OBJECT-TYPE 
    SYNTAX  Counter 
    ACCESS  read-only
    STATUS  mandatory 
    DESCRIPTION 
        "Total number of 'last frame' packets sent from the iSD to the switch."
    ::= { rurlMaintStats 6 }

rurlMaintStatConnectRxmit OBJECT-TYPE 
    SYNTAX  Counter 
    ACCESS  read-only
    STATUS  mandatory 
    DESCRIPTION 
        "Total number of client retransmissions encountered."
    ::= { rurlMaintStats 7 }

rurlMaintStatResetRxmit OBJECT-TYPE 
    SYNTAX  Counter 
    ACCESS  read-only
    STATUS  mandatory 
    DESCRIPTION 
        "Total number of client resets due to excessive retransmissions."
    ::= { rurlMaintStats 8 }

rurlMaintStatCurRdirIPEntries OBJECT-TYPE 
    SYNTAX  Gauge
    ACCESS  read-only
    STATUS  mandatory 
    DESCRIPTION 
        "Current IP redirection table entries."
    ::= { rurlMaintStats 9 }

rurlMaintStatHighRdirIPEntries OBJECT-TYPE 
    SYNTAX  Counter
    ACCESS  read-only
    STATUS  mandatory 
    DESCRIPTION 
        "Highest IP redirection table entries."
    ::= { rurlMaintStats 10 }

rurlMaintStatCurRdirPORTEntries OBJECT-TYPE 
    SYNTAX  Gauge
    ACCESS  read-only
    STATUS  mandatory 
    DESCRIPTION 
        "Current PORT redirection table entries."
    ::= { rurlMaintStats 11 }

rurlMaintStatHighRdirPORTEntries OBJECT-TYPE 
    SYNTAX  Counter
    ACCESS  read-only
    STATUS  mandatory 
    DESCRIPTION 
        "Highest PORT redirection table entries."
    ::= { rurlMaintStats 12 }

rurlMaintStatCurRdirIPPORTEntries OBJECT-TYPE 
    SYNTAX  Gauge
    ACCESS  read-only
    STATUS  mandatory 
    DESCRIPTION 
        "Current IP/PORT redirection table entries."
    ::= { rurlMaintStats 13 }

rurlMaintStatHighRdirIPPORTEntries OBJECT-TYPE 
    SYNTAX  Counter
    ACCESS  read-only
    STATUS  mandatory 
    DESCRIPTION 
        "Highest IP/PORT redirection table entries."
    ::= { rurlMaintStats 14 }

rurlMaintStatCurRSEQBufEntries OBJECT-TYPE 
    SYNTAX  Gauge
    ACCESS  read-only
    STATUS  mandatory 
    DESCRIPTION 
        "Current RURL sequence table entries."
    ::= { rurlMaintStats 15 }

rurlMaintStatHighRSEQBufEntries OBJECT-TYPE 
    SYNTAX  Counter
    ACCESS  read-only
    STATUS  mandatory 
    DESCRIPTION 
        "Highest RURL sequence table entries."
    ::= { rurlMaintStats 16 }

rurlMaintStatCurRBUFBufEntries OBJECT-TYPE 
    SYNTAX  Gauge
    ACCESS  read-only
    STATUS  mandatory 
    DESCRIPTION 
        "Current RURL frame buffer entries."
    ::= { rurlMaintStats 17 }

rurlMaintStatHighRBUFBufEntries OBJECT-TYPE 
    SYNTAX  Counter
    ACCESS  read-only
    STATUS  mandatory 
    DESCRIPTION 
        "Highest RURL frame buffer entries."
    ::= { rurlMaintStats 18 }

rurlMaintStatRSEQBufAllocs OBJECT-TYPE 
    SYNTAX  Counter
    ACCESS  read-only
    STATUS  mandatory 
    DESCRIPTION 
        "Total number of successful RURL sequence buffer Allocs."
    ::= { rurlMaintStats 19 }

rurlMaintStatRSEQBufFrees OBJECT-TYPE 
    SYNTAX  Counter
    ACCESS  read-only
    STATUS  mandatory 
    DESCRIPTION 
        "Total number of successful RURL sequence buffer Frees."
    ::= { rurlMaintStats 20 }

rurlMaintStatRSEQFailBufAllocs OBJECT-TYPE 
    SYNTAX  Counter
    ACCESS  read-only
    STATUS  mandatory 
    DESCRIPTION 
        "Total number of failed RURL sequence buffer Allocs."
    ::= { rurlMaintStats 21 }

rurlMaintStatRSEQFailBufFrees OBJECT-TYPE 
    SYNTAX  Counter
    ACCESS  read-only
    STATUS  mandatory 
    DESCRIPTION 
        "Total number of failed RURL sequence buffer Frees."
    ::= { rurlMaintStats 22 }

rurlMaintStatRBUFBufAllocs OBJECT-TYPE 
    SYNTAX  Counter
    ACCESS  read-only
    STATUS  mandatory 
    DESCRIPTION 
        "Total number of successful RURL frame buffer Allocs."
    ::= { rurlMaintStats 23 }

rurlMaintStatRBUFBufFrees OBJECT-TYPE 
    SYNTAX  Counter
    ACCESS  read-only
    STATUS  mandatory 
    DESCRIPTION 
        "Total number of successful RURL frame buffer Frees."
    ::= { rurlMaintStats 24 }

rurlMaintStatRBUFFailBufAllocs OBJECT-TYPE 
    SYNTAX  Counter
    ACCESS  read-only
    STATUS  mandatory 
    DESCRIPTION 
        "Total number of failed RURL frame buffer Allocs."
    ::= { rurlMaintStats 25 }

rurlMaintStatRBUFFailBufFrees OBJECT-TYPE 
    SYNTAX  Counter
    ACCESS  read-only
    STATUS  mandatory 
    DESCRIPTION 
        "Total number of failed RURL frame buffer Frees."
    ::= { rurlMaintStats 26 }

rurlMaintStatRBUFRetransmit OBJECT-TYPE 
    SYNTAX  Counter
    ACCESS  read-only
    STATUS  mandatory 
    DESCRIPTION 
        "Total number of retransmissions of an existing RURL frame buffer."
    ::= { rurlMaintStats 27 }

rurlMaintStatRBUFChanged OBJECT-TYPE 
    SYNTAX  Counter
    ACCESS  read-only
    STATUS  mandatory 
    DESCRIPTION 
        "Total number of retransmissions of an existing RURL frame buffer
         that has changed in length."
    ::= { rurlMaintStats 28 }

-- RTSP Statistics

rtspStatControlConns OBJECT-TYPE 
    SYNTAX  Gauge
    ACCESS  read-only
    STATUS  mandatory 
    DESCRIPTION 
        "Total number of active RTSP control connections."
    ::= { rtspStats 1 }

rtspStatUDPStreams OBJECT-TYPE 
    SYNTAX  Gauge
    ACCESS  read-only
    STATUS  mandatory 
    DESCRIPTION 
        "Total number of active UDP streams."
    ::= { rtspStats 2 }

rtspStatRedirects OBJECT-TYPE 
    SYNTAX  Counter
    ACCESS  read-only
    STATUS  mandatory 
    DESCRIPTION 
        "Total number of switch redirects."
    ::= { rtspStats 3 }

rtspStatConnDenied OBJECT-TYPE 
    SYNTAX  Counter
    ACCESS  read-only
    STATUS  mandatory 
    DESCRIPTION 
        "Total connections denied due to RTSP connection limit."
    ::= { rtspStats 4 }

rtspStatAllocFails OBJECT-TYPE 
    SYNTAX  Counter
    ACCESS  read-only
    STATUS  mandatory 
    DESCRIPTION 
        "Total cases of heap memory allocation failures."
    ::= { rtspStats 5 }

-- TCP Rate Limiting Statistics
tcpLimitStatHoldDowns OBJECT-TYPE 
    SYNTAX  Counter
    ACCESS  read-only
    STATUS  mandatory 
    DESCRIPTION 
        "Total number of client hold downs triggered."
    ::= { tcpLimitStats 1 }

tcpLimitStatClientEntries OBJECT-TYPE 
    SYNTAX  Gauge
    ACCESS  read-only
    STATUS  mandatory 
    DESCRIPTION 
        "Current number of TCP rate limiting per-client state entries."
    ::= { tcpLimitStats 2 }

-- NASA Statistics Table at SP

nasaStatSpTable OBJECT-TYPE
    SYNTAX  SEQUENCE OF NasaStatSpEntry
    ACCESS  not-accessible
    STATUS  mandatory
    DESCRIPTION
        "The table of NASA statistics at SP."
    ::= { nasaStats 1 }

nasaStatSpEntry OBJECT-TYPE
    SYNTAX  NasaStatSpEntry
    ACCESS  not-accessible
    STATUS  mandatory
    DESCRIPTION
        "A row in the NASA base port statistcs table."
    INDEX   { nasaStatSpPortIndex }
    ::= { nasaStatSpTable 1 }

NasaStatSpEntry ::= SEQUENCE {
    nasaStatSpPortIndex                 INTEGER,
    nasaStatSpCtlTunnelIn               Counter,
    nasaStatSpCtlTunnelInvalidPkt       Counter,
    nasaStatSpReqSessCnt                Counter,
    nasaStatSpSessAddCnt                Counter,
    nasaStatSpSessDelCnt                Counter,
    nasaStatSpSessUpdCnt                Counter,
    nasaStatSpSessRdCnt                 Counter,
    nasaStatSpSessCharCnt               Counter,
    nasaStatSpReqSessNoIsd              Counter,
    nasaStatSpCtlTunnelToMp             Counter,
    nasaStatSpBcastTunnelCnt            Counter,
    nasaStatSpBcastTunnelToMp           Counter,
    nasaStatSpBcastTunnelToIsd          Counter,
    nasaStatSpRurlTunnelCnt             Counter,
    nasaStatSpIpDatagramCnt             Counter,
    nasaStatSpCliRedirectCnt            Counter,
    nasaStatSpInvalidVersion            Counter,
    nasaStatSpAckTx                     Counter,
    nasaStatSpAckRx                     Counter,
    nasaStatSpAckAlloc                  Counter,
    nasaStatSpAckFree                   Counter,
    nasaStatSpAllocAckFail              Counter,
    nasaStatSpAllocFrmFail              Counter,
    nasaStatSpRexmitFail                Counter,
    nasaStatSpInvalidIsd                Counter,
    nasaStatSpInvalidPkts               Counter
    }

nasaStatSpPortIndex OBJECT-TYPE
    SYNTAX  INTEGER
    ACCESS  read-only
    STATUS  mandatory
    DESCRIPTION
        "The port number for which the statistics apply."
    ::= { nasaStatSpEntry 1 }

nasaStatSpCtlTunnelIn OBJECT-TYPE
    SYNTAX  Counter
    ACCESS  read-only
    STATUS  mandatory
    DESCRIPTION
        "The number of packet in for control tunnel on the port."
    ::= { nasaStatSpEntry 2 }

nasaStatSpCtlTunnelInvalidPkt OBJECT-TYPE
    SYNTAX  Counter
    ACCESS  read-only
    STATUS  mandatory
    DESCRIPTION
        "The number of invalid packet in for control tunnel on the port."
    ::= { nasaStatSpEntry 3 }

nasaStatSpReqSessCnt OBJECT-TYPE
    SYNTAX  Counter
    ACCESS  read-only
    STATUS  mandatory
    DESCRIPTION
        "The number of session request message in for control tunnel on the port."
    ::= { nasaStatSpEntry 4 }

nasaStatSpSessAddCnt OBJECT-TYPE
    SYNTAX  Counter
    ACCESS  read-only
    STATUS  mandatory
    DESCRIPTION
        "The number of session add mesage for control tunnel on the port."
    ::= { nasaStatSpEntry 5 }

nasaStatSpSessDelCnt OBJECT-TYPE
    SYNTAX  Counter
    ACCESS  read-only
    STATUS  mandatory
    DESCRIPTION
        "The number of session delete message for control tunnel on the port."
    ::= { nasaStatSpEntry 6 }

nasaStatSpSessUpdCnt OBJECT-TYPE
    SYNTAX  Counter
    ACCESS  read-only
    STATUS  mandatory
    DESCRIPTION
        "The number of session update message for control tunnel on the port."
    ::= { nasaStatSpEntry 7 }

nasaStatSpSessRdCnt OBJECT-TYPE
    SYNTAX  Counter
    ACCESS  read-only
    STATUS  mandatory
    DESCRIPTION
        "The number of session read message for control tunnel on the port."
    ::= { nasaStatSpEntry 8 }

nasaStatSpSessCharCnt OBJECT-TYPE
    SYNTAX  Counter
    ACCESS  read-only
    STATUS  mandatory
    DESCRIPTION
        "The number of session characteristics message for control tunnel on the port."
    ::= { nasaStatSpEntry 9 }

nasaStatSpReqSessNoIsd OBJECT-TYPE
    SYNTAX  Counter
    ACCESS  read-only
    STATUS  mandatory
    DESCRIPTION
        "The number of session request message no isd for control tunnel on the port."
    ::= { nasaStatSpEntry 10 }

nasaStatSpCtlTunnelToMp OBJECT-TYPE
    SYNTAX  Counter
    ACCESS  read-only
    STATUS  mandatory
    DESCRIPTION
        "The number of packet sent to MP for control tunnel on the port."
    ::= { nasaStatSpEntry 11 }

nasaStatSpBcastTunnelCnt OBJECT-TYPE
    SYNTAX  Counter
    ACCESS  read-only
    STATUS  mandatory
    DESCRIPTION
        "The number of packet in for broadcast tunnel on the port."
    ::= { nasaStatSpEntry 12 }

nasaStatSpBcastTunnelToMp OBJECT-TYPE
    SYNTAX  Counter
    ACCESS  read-only
    STATUS  mandatory
    DESCRIPTION
        "The number of packet sent to MP for broadcast tunnel on the port."
    ::= { nasaStatSpEntry 13 }

nasaStatSpBcastTunnelToIsd OBJECT-TYPE
    SYNTAX  Counter
    ACCESS  read-only
    STATUS  mandatory
    DESCRIPTION
        "The number of packet sent to ISD for broadcast tunnel on the port."
    ::= { nasaStatSpEntry 14 }

nasaStatSpRurlTunnelCnt OBJECT-TYPE
    SYNTAX  Counter
    ACCESS  read-only
    STATUS  mandatory
    DESCRIPTION
        "The number of RURL tunnel count on the port."
    ::= { nasaStatSpEntry 15 }

nasaStatSpIpDatagramCnt OBJECT-TYPE
    SYNTAX  Counter
    ACCESS  read-only
    STATUS  mandatory
    DESCRIPTION
        "The number of IP datagram tunnel count on the port."
    ::= { nasaStatSpEntry 16 }

nasaStatSpCliRedirectCnt OBJECT-TYPE
    SYNTAX  Counter
    ACCESS  read-only
    STATUS  mandatory
    DESCRIPTION
        "The number of client redirect tunnel count on the port."
    ::= { nasaStatSpEntry 17 }

nasaStatSpInvalidVersion OBJECT-TYPE
    SYNTAX  Counter
    ACCESS  read-only
    STATUS  mandatory
    DESCRIPTION
        "The number of invalid NA/SA version packet in on the port."
    ::= { nasaStatSpEntry 18 }


nasaStatSpAckTx OBJECT-TYPE
    SYNTAX  Counter
    ACCESS  read-only
    STATUS  mandatory
    DESCRIPTION
        "The number of ack packet sent at link level on the port."
    ::= { nasaStatSpEntry 19 }

nasaStatSpAckRx OBJECT-TYPE
    SYNTAX  Counter
    ACCESS  read-only
    STATUS  mandatory
    DESCRIPTION
        "The number of ack packet received at link level on the port."
    ::= { nasaStatSpEntry 20 }

nasaStatSpAckAlloc OBJECT-TYPE
    SYNTAX  Counter
    ACCESS  read-only
    STATUS  mandatory
    DESCRIPTION
        "The number of ack packet allocated at link level on the port."
    ::= { nasaStatSpEntry 21 }

nasaStatSpAckFree OBJECT-TYPE
    SYNTAX  Counter
    ACCESS  read-only
    STATUS  mandatory
    DESCRIPTION
        "The number of ack packet freed at link level on the port."
    ::= { nasaStatSpEntry 22 }

nasaStatSpAllocAckFail OBJECT-TYPE
    SYNTAX  Counter
    ACCESS  read-only
    STATUS  mandatory
    DESCRIPTION
        "The number of allocated ack packet failed at link level on the port."
    ::= { nasaStatSpEntry 23 }

nasaStatSpAllocFrmFail OBJECT-TYPE
    SYNTAX  Counter
    ACCESS  read-only
    STATUS  mandatory
    DESCRIPTION
        "The number of allocated data packet failed at link level on the port."
    ::= { nasaStatSpEntry 24 }

nasaStatSpRexmitFail OBJECT-TYPE
    SYNTAX  Counter
    ACCESS  read-only
    STATUS  mandatory
    DESCRIPTION
        "The number of re-transmit failed at link level on the port."
    ::= { nasaStatSpEntry 25 }

nasaStatSpInvalidIsd OBJECT-TYPE
    SYNTAX  Counter
    ACCESS  read-only
    STATUS  mandatory
    DESCRIPTION
        "The number of packet form unknown ISD at link level on the port."
    ::= { nasaStatSpEntry 26 }

nasaStatSpInvalidPkts OBJECT-TYPE
    SYNTAX  Counter
    ACCESS  read-only
    STATUS  mandatory
    DESCRIPTION
        "The number of invalid packet at link level on the port."
    ::= { nasaStatSpEntry 27 }

-- NASA Statistics at MP

nasaMpStats         OBJECT IDENTIFIER ::= { nasaStats  2 }

nasaStatMpTotalRx OBJECT-TYPE
    SYNTAX  Counter
    ACCESS  read-only
    STATUS  mandatory
    DESCRIPTION
        "The number of messages received on MP side."
    ::= { nasaMpStats 1 }

nasaStatMpTotalTx OBJECT-TYPE
    SYNTAX  Counter
    ACCESS  read-only
    STATUS  mandatory
    DESCRIPTION
        "The number of messages transmitted on MP side."
    ::= { nasaMpStats 2 }

nasaStatMpBadCksum OBJECT-TYPE
    SYNTAX  Counter
    ACCESS  read-only
    STATUS  mandatory
    DESCRIPTION
        "The number of messages received with bad checksum on MP side."
    ::= { nasaMpStats 3 }

nasaStatMpInvalidRx OBJECT-TYPE
    SYNTAX  Counter
    ACCESS  read-only
    STATUS  mandatory
    DESCRIPTION
        "The number of invalid messages received on MP side."
    ::= { nasaMpStats 4 }

nasaStatMpPingRequests OBJECT-TYPE
    SYNTAX  Counter
    ACCESS  read-only
    STATUS  mandatory
    DESCRIPTION
        "The number of broadcast pings received on MP side."
    ::= { nasaMpStats 5 }

nasaStatMpPingResponses OBJECT-TYPE
    SYNTAX  Counter
    ACCESS  read-only
    STATUS  mandatory
    DESCRIPTION
        "The number broadcast ping responses transmitted on MP side."
    ::= { nasaMpStats 6 }

nasaStatMpRegRequests OBJECT-TYPE
    SYNTAX  Counter
    ACCESS  read-only
    STATUS  mandatory
    DESCRIPTION
        "The number registration requests received on MP side."
    ::= { nasaMpStats 7 }

nasaStatMpCapResponses OBJECT-TYPE
    SYNTAX  Counter
    ACCESS  read-only
    STATUS  mandatory
    DESCRIPTION
        "The number of capability responses transmitted on MP side."
    ::= { nasaMpStats 8 }

nasaStatMpRegConfirmations OBJECT-TYPE
    SYNTAX  Counter
    ACCESS  read-only
    STATUS  mandatory
    DESCRIPTION
        "The number of registration confirmations received on MP side."
    ::= { nasaMpStats 9 }

nasaStatMpUnregRequests OBJECT-TYPE
    SYNTAX  Counter
    ACCESS  read-only
    STATUS  mandatory
    DESCRIPTION
        "The number of unregistration requests received on MP side."
    ::= { nasaMpStats 10 }

nasaStatMpHealthRequests OBJECT-TYPE
    SYNTAX  Counter
    ACCESS  read-only
    STATUS  mandatory
    DESCRIPTION
        "The number of heartbeat requests transmitted on MP side."
    ::= { nasaMpStats 11 }

nasaStatMpHealthResponses OBJECT-TYPE
    SYNTAX  Counter
    ACCESS  read-only
    STATUS  mandatory
    DESCRIPTION
        "The number of heartbeat responses received on MP side."
    ::= { nasaMpStats 12 }

nasaStatMpCmdRequests OBJECT-TYPE
    SYNTAX  Counter
    ACCESS  read-only
    STATUS  mandatory
    DESCRIPTION
        "The number NASA CLI cmd requests received on MP side."
    ::= { nasaMpStats 13 }

nasaStatMpCmdResponses OBJECT-TYPE
    SYNTAX  Counter
    ACCESS  read-only
    STATUS  mandatory
    DESCRIPTION
        "The number NASA CLI cmd responses received on MP side."
    ::= { nasaMpStats 14 }

-- DNS SLB Statistics

dnsSlbStatTCPQueries OBJECT-TYPE 
    SYNTAX  Counter
    ACCESS  read-only
    STATUS  mandatory 
    DESCRIPTION 
        "Total number of TCP DNS queries."
    ::= { dnsSlbStats 1 }

dnsSlbStatUDPQueries OBJECT-TYPE 
    SYNTAX  Counter
    ACCESS  read-only
    STATUS  mandatory 
    DESCRIPTION 
        "Total number of UDP DNS queries."
    ::= { dnsSlbStats 2 }

dnsSlbStatInvalidQueries OBJECT-TYPE 
    SYNTAX  Counter
    ACCESS  read-only
    STATUS  mandatory 
    DESCRIPTION 
        "Total number of invalid DNS queries."
    ::= { dnsSlbStats 3 }

dnsSlbStatMultipleQueries OBJECT-TYPE 
    SYNTAX  Counter
    ACCESS  read-only
    STATUS  mandatory 
    DESCRIPTION 
        "Total number of multiple DNS queries."
    ::= { dnsSlbStats 4 }

dnsSlbStatDnameParseErrors OBJECT-TYPE 
    SYNTAX  Counter
    ACCESS  read-only
    STATUS  mandatory 
    DESCRIPTION 
        "Total number of domain name parse errors."
    ::= { dnsSlbStats 5 }

dnsSlbStatFailedMatches OBJECT-TYPE 
    SYNTAX  Counter
    ACCESS  read-only
    STATUS  mandatory 
    DESCRIPTION 
        "Total number of failed real server name matches."
    ::= { dnsSlbStats 6 }

dnsSlbStatInternalErrors OBJECT-TYPE 
    SYNTAX  Counter
    ACCESS  read-only
    STATUS  mandatory 
    DESCRIPTION 
        "Total number of DNS parsing internal errors."
    ::= { dnsSlbStats 7 }

-- SLB Switch FailOver Information Table

slbFailOverInfoTable OBJECT-TYPE -- obsoleted
    SYNTAX  SEQUENCE OF SlbFailOverInfoEntry
    ACCESS  not-accessible
    STATUS  mandatory
    DESCRIPTION
        "The table of switch fail-over run-time status."
    ::= { slb-info 1 }

slbFailOverInfoEntry OBJECT-TYPE
    SYNTAX  SlbFailOverInfoEntry
    ACCESS  not-accessible
    STATUS  mandatory
    DESCRIPTION
                "A row in the switch fail-over information table."
        INDEX   { slbFailOverInfoIndex }
    ::= { slbFailOverInfoTable 1 }
 
SlbFailOverInfoEntry ::= SEQUENCE {
        slbFailOverInfoIndex           INTEGER,
        slbFailOverInfoPrimaryIp       IpAddress,
	slbFailOverInfoPrimaryStatus   INTEGER,
	slbFailOverInfoPrimaryState    INTEGER,
        slbFailOverInfoSecondaryIp     IpAddress,
	slbFailOverInfoSecondaryStatus INTEGER,
	slbFailOverInfoSecondaryState  INTEGER
	}

slbFailOverInfoIndex OBJECT-TYPE
    SYNTAX  INTEGER
    ACCESS  read-only
    STATUS  mandatory
    DESCRIPTION
                "The index of switch fail-over information table."
    ::= { slbFailOverInfoEntry 1 }

slbFailOverInfoPrimaryIp OBJECT-TYPE
    SYNTAX  IpAddress
    ACCESS  read-only
    STATUS  mandatory
    DESCRIPTION
                "IP address of the primary switch." 
    ::= { slbFailOverInfoEntry 2 }


slbFailOverInfoPrimaryStatus OBJECT-TYPE
    SYNTAX  INTEGER { 
                up(1), 
                down(2)
                } 
    ACCESS  read-only
    STATUS  mandatory
    DESCRIPTION
                "The current operational status of the primary switch." 
    ::= { slbFailOverInfoEntry 3 }

slbFailOverInfoPrimaryState OBJECT-TYPE
    SYNTAX  INTEGER { 
                active(1), 
                standby(2)
                } 
    ACCESS  read-only
    STATUS  mandatory
    DESCRIPTION
                "The current operational state of the primary switch." 
    ::= { slbFailOverInfoEntry 4 }

slbFailOverInfoSecondaryIp OBJECT-TYPE
    SYNTAX  IpAddress
    ACCESS  read-only
    STATUS  mandatory
    DESCRIPTION
                "IP address of the secondary switch." 
    ::= { slbFailOverInfoEntry 5 }

slbFailOverInfoSecondaryStatus OBJECT-TYPE
    SYNTAX  INTEGER { 
                up(1), 
                down(2)
                } 
    ACCESS  read-only
    STATUS  mandatory
    DESCRIPTION
                "The current operational status of the secondary switch." 
    ::= { slbFailOverInfoEntry 6 }

slbFailOverInfoSecondaryState OBJECT-TYPE
    SYNTAX  INTEGER { 
                active(1), 
                standby(2)
                } 
    ACCESS  read-only
    STATUS  mandatory
    DESCRIPTION
                "The current operational state of the secondary switch." 
    ::= { slbFailOverInfoEntry 7 }


-- Real Server Information Table

slbRealServerInfoTable OBJECT-TYPE
    SYNTAX  SEQUENCE OF SlbRealServerInfoEntry
    ACCESS  not-accessible
    STATUS  mandatory
    DESCRIPTION
        "The table of real server run-time information."
    ::= { slb-info 2 }

slbRealServerInfoEntry OBJECT-TYPE
    SYNTAX  SlbRealServerInfoEntry
    ACCESS  not-accessible
    STATUS  mandatory
    DESCRIPTION
        "A row in the real server information table."
    INDEX   { slbRealServerInfoIndex }
    ::= { slbRealServerInfoTable 1 }
 
SlbRealServerInfoEntry ::= SEQUENCE {
    slbRealServerInfoIndex           INTEGER,
    slbRealServerInfoIpAddr          IpAddress,
    slbRealServerMacAddr             PhysAddress,
    slbRealServerInfoSwitchPort      INTEGER,
    slbRealServerInfoHealthLayer     INTEGER,
    slbRealServerInfoOverflow        INTEGER,
    slbRealServerInfoState           INTEGER
    }

slbRealServerInfoIndex OBJECT-TYPE
    SYNTAX  INTEGER
    ACCESS  read-only
    STATUS  mandatory
    DESCRIPTION
        "The real server index" 
    ::= { slbRealServerInfoEntry 1 }

slbRealServerInfoIpAddr OBJECT-TYPE
    SYNTAX  IpAddress
    ACCESS  read-only
    STATUS  mandatory
    DESCRIPTION
        "IP address of the real server." 
    ::= { slbRealServerInfoEntry 2 }

slbRealServerMacAddr OBJECT-TYPE
    SYNTAX  PhysAddress
    ACCESS  read-only
    STATUS  mandatory
    DESCRIPTION
        "The MAC address of the real server." 
    ::= { slbRealServerInfoEntry 3 }

slbRealServerInfoSwitchPort OBJECT-TYPE
    SYNTAX  INTEGER
    ACCESS  read-only
    STATUS  mandatory
    DESCRIPTION
        "The switch port that the real server is connected to." 
    ::= { slbRealServerInfoEntry 4 }

slbRealServerInfoHealthLayer  OBJECT-TYPE
    SYNTAX  INTEGER { 
        other(1), 
        layer3(2),
        layer4(3)  
        } 
    ACCESS  read-only
    STATUS  mandatory
    DESCRIPTION
        "The OSI layer at whitch real server functionality is verified."
    ::= { slbRealServerInfoEntry 5 }

slbRealServerInfoOverflow OBJECT-TYPE
    SYNTAX  INTEGER {
	overflow(1),
        no-overflow(2) 
        } 
    ACCESS  read-only
    STATUS  mandatory
    DESCRIPTION
        "The overflow state of the real server." 
    ::= { slbRealServerInfoEntry 6 }

slbRealServerInfoState OBJECT-TYPE
    SYNTAX  INTEGER {
        running(2),
        failed(3),
        disabled(4)
        } 
    ACCESS  read-only
    STATUS  mandatory
    DESCRIPTION
        "The state of the real server."
    ::= { slbRealServerInfoEntry 7 }

-- NASA ISD Information Table

nasaIsdInfoTable OBJECT-TYPE
    SYNTAX  SEQUENCE OF NasaIsdInfoEntry
    ACCESS  not-accessible
    STATUS  mandatory
    DESCRIPTION
        "The table of NASA ISD run-time information."
    ::= { slb-info 3 }

nasaIsdInfoEntry OBJECT-TYPE
    SYNTAX  NasaIsdInfoEntry
    ACCESS  not-accessible
    STATUS  mandatory
    DESCRIPTION
        "A row in the real server information table."
    INDEX   { nasaIsdInfoIndex }
    ::= { nasaIsdInfoTable 1 }
 
NasaIsdInfoEntry ::= SEQUENCE {
    nasaIsdInfoIndex           INTEGER,
    nasaIsdInfoIpAddr          IpAddress,
    nasaIsdMacAddr             PhysAddress,
    nasaIsdInfoSwitchPort      INTEGER,
    nasaIsdInfoGdi	       INTEGER,
    nasaIsdInfoState	       INTEGER,
    nasaIsdInfoStateChange     INTEGER
    }

nasaIsdInfoIndex OBJECT-TYPE
    SYNTAX  INTEGER
    ACCESS  read-only
    STATUS  mandatory
    DESCRIPTION
        "The ISD index" 
    ::= { nasaIsdInfoEntry 1 }

nasaIsdInfoIpAddr OBJECT-TYPE
    SYNTAX  IpAddress
    ACCESS  read-only
    STATUS  mandatory
    DESCRIPTION
        "IP address of the ISD." 
    ::= { nasaIsdInfoEntry 2 }

nasaIsdMacAddr OBJECT-TYPE
    SYNTAX  PhysAddress
    ACCESS  read-only
    STATUS  mandatory
    DESCRIPTION
        "The MAC address of the ISD." 
    ::= { nasaIsdInfoEntry 3 }

nasaIsdInfoSwitchPort OBJECT-TYPE
    SYNTAX  INTEGER
    ACCESS  read-only
    STATUS  mandatory
    DESCRIPTION
        "The switch port that the ISD is connected to." 
    ::= { nasaIsdInfoEntry 4 }

nasaIsdInfoGdi OBJECT-TYPE
    SYNTAX  INTEGER 
    ACCESS  read-only
    STATUS  mandatory
    DESCRIPTION
        "VLAN ID of the ISD."
    ::= { nasaIsdInfoEntry 5 }

nasaIsdInfoState OBJECT-TYPE
    SYNTAX  INTEGER {
	isd-invalid(1),
	isd-unregistered(2),
        isd-access(3),
	isd-up(4),
	isd-down(5),
	isd-mip(6)
        } 
    ACCESS  read-only
    STATUS  mandatory
    DESCRIPTION
        "The current state of the ISD." 
    ::= { nasaIsdInfoEntry 6 }

nasaIsdInfoStateChange OBJECT-TYPE
    SYNTAX  INTEGER
    ACCESS  read-only
    STATUS  mandatory
    DESCRIPTION
        "The number of ISD state transitions from up to down."
    ::= { nasaIsdInfoEntry 7 }

-- Switch Oper Commands (for Alteon internal usage only)

operSlbPortTable OBJECT-TYPE
    SYNTAX  SEQUENCE OF OperSlbPortEntry
    ACCESS  not-accessible
    STATUS  mandatory
    DESCRIPTION
        "The table of ports that the Oper commands apply to."
    ::= { operCmds 1 }

operSlbPortEntry OBJECT-TYPE
    SYNTAX  OperSlbPortEntry
    ACCESS  not-accessible
    STATUS  mandatory
    DESCRIPTION
        "A row in the operSlbPortTable "
    INDEX   { operSlbPortIndex }
    ::= { operSlbPortTable 1 }

OperSlbPortEntry ::= SEQUENCE {
    operSlbPortIndex              INTEGER,
    operSlbPortClrSessionTab      INTEGER
    }

operSlbPortIndex OBJECT-TYPE
    SYNTAX  INTEGER
    ACCESS  read-only
    STATUS  mandatory
    DESCRIPTION
        "The switch port number." 
    ::= { operSlbPortEntry 1 }

operSlbPortClrSessionTab OBJECT-TYPE
    SYNTAX  INTEGER {
	ok(1),
	clear(2)
	}
    ACCESS  read-write
    STATUS  mandatory
    DESCRIPTION
        "This an action object to clear session buinding table for the 
         specified port.  ok(1) is returned when read."
    ::= { operSlbPortEntry 2 }

slbOperRealServerTable OBJECT-TYPE
    SYNTAX  SEQUENCE OF SlbOperRealServerEntry
    ACCESS  not-accessible
    STATUS  mandatory
    DESCRIPTION
        "The table of real servers."
    ::= { slbOper 1 }

slbOperRealServerEntry OBJECT-TYPE
    SYNTAX  SlbOperRealServerEntry
    ACCESS  not-accessible
    STATUS  mandatory
    DESCRIPTION
        "A row in the slbOperRealServerTable "
    INDEX   { slbOperRealServerIndex }
    ::= { slbOperRealServerTable 1 }

SlbOperRealServerEntry ::= SEQUENCE {
    slbOperRealServerIndex              INTEGER,
    slbOperRealServerStatus             INTEGER
    }

slbOperRealServerIndex OBJECT-TYPE
    SYNTAX  INTEGER
    ACCESS  read-only
    STATUS  mandatory
    DESCRIPTION
        "The index for the  real server." 
    ::= { slbOperRealServerEntry 1 }

slbOperRealServerStatus OBJECT-TYPE
    SYNTAX  INTEGER {
	enable(1),
	disable(2),
	cookiepersistent(3)
	}
    ACCESS  read-write
    STATUS  mandatory
    DESCRIPTION
        "This an action object which is used to temporarily enable/disable a
         real server. The real server will be returned to its configured
         operational mode when the switch is reset. Setting the value to 
         'cookiepersistant' allows cookie persistent HTTP 1.0 sessions
         when the real server is offline."
    ::= { slbOperRealServerEntry 2 }

slbOperConfigSync OBJECT-TYPE
    SYNTAX  INTEGER {
	ok(1),
	sync(2)
	}
    ACCESS  read-write
    STATUS  mandatory
    DESCRIPTION
        "When set to a value of 'sync(2)' it synchronizes the SLB, filter
         and VRRP configuration on a peer switch. To take effect, peers must
         be configured on the switches and the administrator password on the
         switches must be identical. 
         'ok(1)' is returned when the object os read."
    ::= { slbOper 2 }

END
