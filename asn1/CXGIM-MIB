CXGIM-MIB DEFINITIONS ::= BEGIN

--#CURRENT_VERSION 1

IMPORTS
   Counter         FROM RFC1155-SMI
   OBJECT-TYPE     FROM RFC-1212
   DisplayString           FROM RFC1213-MIB
   cxGim,SapIndex,Alias, ThruputClass
            FROM CXProduct-SMI;

-- Proprietary Data Types
PSapIndex       ::=     INTEGER (0..255)
TypeIndex       ::=     INTEGER (0..255)
DteIndex       ::=     INTEGER (1..255)
SubRef  ::=     INTEGER (0..255)

PacketSize      ::=     INTEGER {
            bytes16         (4),
            bytes32         (5),
            bytes64         (6),
            bytes128        (7),
            bytes256        (8),
            bytes512        (9),
            bytes1024       (10),
            bytes2048       (11),
            bytes4096       (12)
            }



gimSysRouteConnectInterval OBJECT-TYPE
   SYNTAX  INTEGER (10..900)
   ACCESS  read-write
   STATUS  mandatory
   DESCRIPTION
"Determines the number of seconds between attempts to establish a 
connection for a X25 system route. A connection is attempted only for 
defined non-connected routes.

Range of Values: 10 - 900 seconds

Default Value: 30 seconds

Configuration Changed: administrative and operative"
   DEFVAL {30 }
   ::= { cxGim 1 }

gimMibLevel OBJECT-TYPE
   SYNTAX  INTEGER
   ACCESS  read-only
   STATUS  mandatory
   DESCRIPTION
"Used to determine current MIB module release supported
by the agent. Object is in decimal."
   DEFVAL { 0 }
   --#STARTING_VERSION 1
   ::= { cxGim 2 }


-- gap (8) for future global parameters



--  Service Access Point Configuration Table

--  The table describing:
--      parameters required to configure a X25 convergence service access 
--      point
--
--      controls available to manipulate a X25 convergence service access 
--      point
--
--      status available for monitoring the X25 convergence service access 
--      point
--      statistics available for monitoring any X25 convergence service 
--      access point

--  Service access points of this type exist at the upper interface of the 
--  X25
--  Convergence layer, and are used to communicate with the X25 or 
--  IAM layers.


gimSapTable OBJECT-TYPE
   SYNTAX  SEQUENCE OF GimSapEntry
   ACCESS  not-accessible
   STATUS  mandatory
   DESCRIPTION
"A table containing configuration information about each X25 convergence 
service access point. Service access points of this type exist at the 
upper interface of the X25 Convergence layer, and are used to communicate 
with the X25 or IAM layers."
   ::= { cxGim 10 }


   gimSapEntry OBJECT-TYPE
      SYNTAX  GimSapEntry
      ACCESS  not-accessible
      STATUS  mandatory
      DESCRIPTION
"Defines a row in the Service Access Point Configuration table. Each row 
contains the objects which are used to define a service access point upper 
interface of the X25 Convergence layer."
      INDEX { gimSapType, gimSapNumber }
      ::= { gimSapTable 1 }


   GimSapEntry ::=
      SEQUENCE {
-- Parameters
         gimSapType                          TypeIndex,
         gimSapNumber                      PSapIndex,
         gimSapRowStatus                  INTEGER,
         gimSapAlias                           Alias,
         gimSapCompanionAlias        Alias,
         gimSapInactivityTimer          INTEGER,
         gimSapProtocolId                  DisplayString,
         gimSapAddress                      DisplayString,

-- Control
         gimSapControl                      INTEGER,
-- Status
         gimSapState                        INTEGER,
         gimSapLinkState                  INTEGER,
-- Statistics
         gimSapTxFrames                     Counter,
         gimSapRxFrames                     Counter,
         gimSapTxOctets                     Counter,
         gimSapRxOctets                     Counter,
         gimSapOutSuccessfullConnects       Counter,
         gimSapOutUnsuccessfullConnects      Counter,
         gimSapInSuccessfullConnects         Counter,
         gimSapInUnsuccessfullConnects       Counter,
         gimSapUnopenedServiceDiscards       Counter,
         gimSapTxResets                              Counter,
         gimSapRxResets                              Counter,

-- Parameters (cont)
         gimSapTxThruputClass                    ThruputClass,
         gimSapRxThruputClass                    ThruputClass,   
         gimSapTxPacketSize                        PacketSize,
         gimSapRxPacketSize                        PacketSize,
         gimSapTxWindowSize                      INTEGER,
         gimSapRxWindowSize                      INTEGER   	


}


gimSapType OBJECT-TYPE
      SYNTAX  TypeIndex
      ACCESS  read-only
      STATUS  mandatory
      DESCRIPTION
"Identifies the type of this SAP (service access point) with a numerical value. Values 
are unique for each type."
      ::= { gimSapEntry 1 }


   gimSapNumber OBJECT-TYPE
      SYNTAX  PSapIndex
      ACCESS  read-only
      STATUS  mandatory
      DESCRIPTION
"Identifies this SAP (service access point) with a numerical value. Values 
are unique for each service access point."
      ::= { gimSapEntry 2 }


   gimSapRowStatus OBJECT-TYPE
      SYNTAX  INTEGER {
               invalid         (1),
               valid           (2)
               }
      ACCESS  read-write
      STATUS  mandatory
      DESCRIPTION
"Determines the status of the objects in a table row.

Options:
invalid (1): Row is deleted from the table immediately, however values are 
still in effect until the next reset. 

valid (2): Use this value to add a new row to the table, or modify an 
existing row.

Default Value: valid (2)

Configuration Changed: administrative"
      ::= { gimSapEntry 3 }


gimSapAlias OBJECT-TYPE
      SYNTAX  Alias
      ACCESS  read-write
      STATUS  mandatory
      DESCRIPTION
"Identifies this service access point by a textual name. Names must be 
unique across all service access points at all layers. 

Range of Values: 1 -16 alphanumeric characters (first character must be a 
letter)

Default Value: none

Configuration Changed: administrative"
      ::= { gimSapEntry 4 }


gimSapCompanionAlias OBJECT-TYPE
      SYNTAX  Alias
      ACCESS  read-write
      STATUS  mandatory
      DESCRIPTION
"Determines the name which uniquely identifies the X.25 Upper SAP (service access 
point) which will communicate with this SAP.

Range of Values: 1 -16 alphanumeric characters (first character must be a 
letter)

Default Value: none

Configuration Changed: administrative"
      ::= { gimSapEntry 5 }


   gimSapInactivityTimer OBJECT-TYPE
      SYNTAX  INTEGER (0..3600)
      ACCESS  read-write
      STATUS  mandatory
      DESCRIPTION
"Defines the time of inactivity, in seconds, after which the SAP (service 
access point) will send a disconnect request to the X25 layer.  The timer 
starts whenever data is received from the X25 layer or the IAM layer.

Range of Values: 0 to 3600

Note: A value of 0 means that the timer is disabled. The circuit is permanently open.

Default Value: 90

Configuration Changed: Operative "
      REFERENCE  "RFC 1356   Section 3.9"
      DEFVAL { 90 }
      ::= { gimSapEntry 6 }


   gimSapProtocolId OBJECT-TYPE
      SYNTAX DisplayString (SIZE (7..11))
      ACCESS  read-write
      STATUS  mandatory
      DESCRIPTION
"Defines the protocol format that is used for incoming call or call request 
packets to the X.25 call data field. 

The field consists of 4 hexadecimal octets where the first octet is coded as 
follows:

ASYNC PAD

bits 8 & 7

- 00 for CCITT use
- 01 for national use
- 10 reserved for international user bodies
- 11 for DTE-DTE use

When bits 8 & 7 are equal to 00, bits 6 to 1 will be equal to 000001.  The first 
octet is shown as 01, 00, 00, 00.  The first 0 in each number is optional and 
may be shown as 1, 0, 0, 0.

IP over X.25

The value hex CC is required for IP.

All bits of octets 2, 3 and 4 are set to 0.  They are reserved as a future 
mechanism for providing the called PAD or packet mode DTE (user) with 
additional information pertaining to the calling party.

A value of  00,00,00,00 will disable the protocol id formatting for x.25 call request packet or validation for incoming call.

Default Value:   01,00,00,00

Configuration Changed: Operative "
      REFERENCE       "CCITT X.28 3.1.3, X.29 4.2, RFC 1356  3.2"
      DEFVAL { "01,00,00,00" }
      ::= { gimSapEntry 7 }


gimSapAddress OBJECT-TYPE
      SYNTAX  DisplayString (SIZE (0..15))
      ACCESS  read-write
      STATUS  mandatory
      DESCRIPTION
"Defines the calling address for this SAP (service access point).

Range of Values: 1 to 15 digits

Default Value: 0

Configuration Changed: Operative "
       DEFVAL {""}
      ::= { gimSapEntry 8 }


-- gap (1) for future configuration parameters  

-- Control 
   gimSapControl OBJECT-TYPE
      SYNTAX  INTEGER {
               clearStats              (1)
               }
      ACCESS  write-only
      STATUS  mandatory
      DESCRIPTION
"Permits control of a specific SAP (service access point).

Options:
clearStats (1): Clear all statistics stored by statistics objects.

Configuration Changed: operative"
      ::= { gimSapEntry 10 }

-- gap (1) for future Control parameters  

-- Status
gimSapState OBJECT-TYPE
      SYNTAX  INTEGER {
               offLine         (1),
               unbound         (2),
               notConnected            (3),
               inProgress              (4),
               connected               (5)
               }
      ACCESS  read-only
      STATUS  mandatory
      DESCRIPTION
"Indicates the current state of this SAP (service access point).

Options:
offLine (1): Indicates a newly created service access point whose 
configuration has not yet been sent to the X25 Convergence layer.

unbound (2): SAP is not yet bound to its companion SAP at an upper layer.

notConnected (3): The associated route with this SAP is not connected, or 
there is no route associated with this SAP.

inProgress (4): The associated route is in the process of connecting. 

connected (5): The associated route is connected."
      DEFVAL { unbound }
      ::= { gimSapEntry 12 }

gimSapLinkState OBJECT-TYPE
      SYNTAX  INTEGER {
	notConnected            (1),
               inProgress              (2),
               connected               (3)
               }
      ACCESS  read-only
      STATUS  mandatory
      DESCRIPTION
"Indicates the current state of the x25 link for this SAP (service access point).

Options:
notConnected (1): There is no x25 circuit established associated with this SAP.

inProgress (2): The associated x25 call is in the process of being established. 

connected (3): The associated x25 call is established."
      DEFVAL { notConnected }
      ::= { gimSapEntry 13 }

-- gap (1) for future Status parameters  

-- Statistics
   gimSapTxFrames OBJECT-TYPE
      SYNTAX  Counter
      ACCESS  read-only
      STATUS  mandatory
      DESCRIPTION
"Indicates the number of frames transmitted by this service access point."
      ::= { gimSapEntry 15 }


   gimSapRxFrames OBJECT-TYPE
      SYNTAX  Counter
      ACCESS  read-only
      STATUS  mandatory
      DESCRIPTION
"Indicates the number of frames received by this service access point."
      ::= { gimSapEntry 16 }


   gimSapTxOctets OBJECT-TYPE
      SYNTAX  Counter
      ACCESS  read-only
      STATUS  mandatory
      DESCRIPTION
"Indicates the number of octets transmitted by this service access point."
      ::= { gimSapEntry 17 }


   gimSapRxOctets OBJECT-TYPE
      SYNTAX  Counter
      ACCESS  read-only
      STATUS  mandatory
      DESCRIPTION
"Indicates the number of octets received by this service access point."
      ::= { gimSapEntry 18 }


   gimSapOutSuccessfullConnects OBJECT-TYPE
      SYNTAX  Counter
      ACCESS  read-only
      STATUS  mandatory
      DESCRIPTION
"Indicates the number of successful outgoing connections established by 
this SAP (service access point). An outgoing connection is always 
attempted from X25 convergence to the Inter-Application Module (IAM).

At the PSAP, this object represents the total number of outgoing 
connections established by all SAPs. At each individual SAP, this object 
represents the number of outgoing connections established by only that 
SAP."
      ::= { gimSapEntry 19 }


   gimSapOutUnsuccessfullConnects OBJECT-TYPE
      SYNTAX  Counter
      ACCESS  read-only
      STATUS  mandatory
      DESCRIPTION
"Indicates the number of unsuccessful outgoing connections attempted by 
this SAP (service access point). An outgoing connection is always 
attempted from X25 convergence to the Inter-Application Module (IAM).

At the PSAP, this object represents the total number of unsuccessful 
outgoing connections attempted by all SAPs. At each individual SAP, this 
object represents the number of unsuccessful outgoing connections 
attempted by only that SAP."
      ::= { gimSapEntry 20 }


   gimSapInSuccessfullConnects OBJECT-TYPE
      SYNTAX  Counter
      ACCESS  read-only
      STATUS  mandatory
      DESCRIPTION
"Indicates the number of successful incoming connections established at 
this SAP (service access point). An incoming connection is always 
attempted from the Inter-Application Module (IAM) to X25 convergence.

At the PSAP, this object represents the total number of successful 
incoming connections for all SAPs. At each individual SAP, this object 
represents the number of successful incoming connections for only that 
SAP."
      ::= { gimSapEntry 21 }


   gimSapInUnsuccessfullConnects OBJECT-TYPE
      SYNTAX  Counter
      ACCESS  read-only
      STATUS  mandatory
      DESCRIPTION
"Indicates the number of unsuccessful incoming connections attempted at 
this SAP (service access point). An incoming connection is always 
attempted from the Inter-Application Module (IAM) to X25 convergence.

At the PSAP, this object represents the total number of unsuccessful 
incoming connections for all SAPs. At each individual SAP, this object 
represents the number of unsuccessful incoming connections for only that 
SAP."
      ::= { gimSapEntry 22 }


   gimSapUnopenedServiceDiscards OBJECT-TYPE
      SYNTAX  Counter
      ACCESS  read-only
      STATUS  mandatory
      DESCRIPTION
"This object applies only to the PSAP (public service access point).

Indicates the number of frames received and discarded by the PSAP because:

- no route was associated with the frame

- the frame was destined for a route that is not connected"
      ::= { gimSapEntry 23 }


   gimSapTxResets OBJECT-TYPE
      SYNTAX  Counter
      ACCESS  read-only
      STATUS  mandatory
      DESCRIPTION
"This object applies only to the PSAP (public service access point).

Indicates the number of Inter- Application Module (IAM) reset frames sent 
by the PSAP."
      ::= { gimSapEntry 24 }


   gimSapRxResets OBJECT-TYPE
      SYNTAX  Counter
      ACCESS  read-only
      STATUS  mandatory
      DESCRIPTION
"This object applies only to the PSAP.

Indicates the number of Inter- Application Module (IAM) reset frames 
received by the PSAP."
      ::= { gimSapEntry 25 }

-- gap (15) for future statistics parameters  

-- Configuration parameters (cont)

gimSapRxThruputClass OBJECT-TYPE
      SYNTAX  ThruputClass
      ACCESS  read-write
      STATUS  mandatory
      DESCRIPTION
"Defines the default receive throughput class that is used at this SAP (service 
access point).

Range of Values: 75 - 64000 bps

Default Value: 9600 bps

Configuration Changed: Operative "
      REFERENCE  "CCITT(1988) Section 7.2.2.2 and Table 30/X.25"
      DEFVAL { bps9600 }
      --#STARTING_VERSION 1
      ::= { gimSapEntry 50 }


   gimSapTxThruputClass OBJECT-TYPE
      SYNTAX  ThruputClass
      ACCESS  read-write
      STATUS  mandatory
      DESCRIPTION
"Defines the default transmit throughput class that is used at this SAP 
(service access point).

Range of Values: 75 to 64000 bps

Default Value: 9600 bps

Configuration Changed: Operative "
      REFERENCE  "CCITT(1988) Section 7.2.2.2 and Table 30/X.25"
      DEFVAL { bps9600 }
      --#STARTING_VERSION 1
      ::= { gimSapEntry 51 }


gimSapTxPacketSize OBJECT-TYPE
      SYNTAX  PacketSize
      ACCESS  read-write
      STATUS  mandatory
      DESCRIPTION
"Defines the size of the transmit packet for the Xim layer.

Range of Values: 16 to 4096 bytes

Default Value: 128 bytes

Configuration Changed: Operative "
      DEFVAL { bytes128 }
      --#STARTING_VERSION 1
      ::= { gimSapEntry 52}

   
   gimSapRxPacketSize OBJECT-TYPE
      SYNTAX  PacketSize
      ACCESS  read-write
      STATUS  mandatory
      DESCRIPTION
"Defines the size of the receive packet for the Xim layer.

Range of Values: 16 to 4096 bytes

Default Value: 128 bytes

Configuration Changed: Operative "
      DEFVAL { bytes128 }
      --#STARTING_VERSION 1
      ::= { gimSapEntry 53 }


   gimSapTxWindowSize OBJECT-TYPE
      SYNTAX  INTEGER (1..127)
      ACCESS  read-write
      STATUS  mandatory
      DESCRIPTION
"Defines the size of the transmit window for the Xim layer.  

Range of Values: 1 to 127

Default Value: 2

Configuration Changed: Operative "
      DEFVAL { 2 }
      --#STARTING_VERSION 1
     ::= { gimSapEntry 54 }


   gimSapRxWindowSize OBJECT-TYPE
      SYNTAX  INTEGER (1..127)
      ACCESS  read-write
      STATUS  mandatory
      DESCRIPTION
"Defines the size of the receive window for the Xim layer.  

Range of Values: 1 to 127

Default Value: 2

Configuration Changed: Operative "
      DEFVAL { 2 }
      --#STARTING_VERSION 1
      ::= { gimSapEntry 55 }



--  GIM System Route Table

--  The table containing routes permitting GIM logical links to be 
--   established between:
--
--    The GIM layer on this card and the GIM layer on another similar card
--    within the same chassis (future use within CX1000).
--
--    The GIM layer on this card and a GIM layer across the frame
--    relay network.


gimSysRouteTable OBJECT-TYPE
   SYNTAX  SEQUENCE OF GimSysRouteEntry
   ACCESS  not-accessible
   STATUS  mandatory
   DESCRIPTION
"A table containing information about each X25 system route. Routes allow 
this X25  layer to link with another X25  layer across a frame relay 
network, or with the X25 layer on another similar card in the same 
chassis (for future use with the CX1000)."
   ::= {  cxGim 11 }


   gimSysRouteEntry OBJECT-TYPE
      SYNTAX  GimSysRouteEntry
      ACCESS  not-accessible
      STATUS  mandatory
      DESCRIPTION
"Defines a row in the gimSysRouteTable. Each row contains the objects 
which define a system route."
      INDEX { gimSRSapType, gimSRSapNumber }
      ::= { gimSysRouteTable 1 }


   GimSysRouteEntry ::=
      SEQUENCE {
         gimSRSapType                TypeIndex,
         gimSRSapNumber                SapIndex,
         gimSRRowStatus                INTEGER,
         gimSRDestAlias                Alias,
         gimSRSubRef                   SubRef,
-- Status
         gimSRRouteStatus             INTEGER,
         gimSRClearStatus             INTEGER
         }

 gimSRSapType OBJECT-TYPE
      SYNTAX  TypeIndex
      ACCESS  read-only
      STATUS  mandatory
      DESCRIPTION
"Identifies the type of service access point this route entry is associated with."
      ::= { gimSysRouteEntry 1 }


gimSRSapNumber OBJECT-TYPE
      SYNTAX  SapIndex
      ACCESS  read-only
      STATUS  mandatory
      DESCRIPTION
"Identifies the service access point this route entry is associated with."
      ::= { gimSysRouteEntry 2 }


   gimSRRowStatus OBJECT-TYPE
      SYNTAX  INTEGER {
               invalid         (1),
               valid           (2)
               }
      ACCESS  read-write
      STATUS  mandatory
      DESCRIPTION
"Determines the status of the objects in a table row. 

Options:
invalid (1): Row is deleted from the table immediately, however values are 
still in effect until the next reset. 

valid (2): Use this value to add a new row to the table, or modify an 
existing row.

Default Value: none

Configuration Changed: administrative and operative"
      ::= { gimSysRouteEntry 3 }


   gimSRDestAlias OBJECT-TYPE
      SYNTAX  Alias
      ACCESS  read-write
      STATUS  mandatory
      DESCRIPTION
"Determines the textual name of the destination service this route 
connects to. When attempting a X25 connection across Frame Relay, this 
object specifies the name of the outgoing circuit at the Frame Relay 
layer. 

When attempting a X25 connection between cards within the same chassis 
(future use within CX1000), this object specifies the name of the X25 
Convergence SAP on the remote card.

Range of Values: 1 -16 characters (first character must be a letter)

Default Value: none

Configuration Changed: administrative and operative"
      ::= { gimSysRouteEntry 4 }


   gimSRSubRef OBJECT-TYPE
      SYNTAX  SubRef
      ACCESS  read-write
      STATUS  mandatory
      DESCRIPTION
"Specifies a reference number that uniquely identifies this route. This 
number is used by the FRIM (Frame Relay Interface Module) to identify 
routes using the same DLCI (enables PVC consolidation). This number must 
be unique for all routes sharing the same DLCI.

Range of Values: 1 - 255 (when using PVC consolidation)

0 (when not using PVC consolidation)

Default Value: 0

Configuration Changed: administrative and operative"
      ::= { gimSysRouteEntry 5 }


-- gap (5) for future configuration parameters  


   gimSRRouteStatus OBJECT-TYPE
      SYNTAX  INTEGER {
               offLine         (1),
               notConnected            (2),
               inProgress              (3),
               connected               (4)
               }
      ACCESS  read-only
      STATUS  mandatory
      DESCRIPTION
"Indicates the connection status of this X25 route.

Options:
offLine (1): Indicates that the X25 Convergence SAP this route is 
associated with does not exist or is offline.

notConnected (2): Indicates that the remote destination does not exist, or 
has refused the connection.

inProgress (3): Indicates that the connection is in the process of being 
established. This is a transient state.

connected (4): Indicates that the connection is established and is ready 
for data transfer."
      ::= { gimSysRouteEntry 10 }


   gimSRClearStatus OBJECT-TYPE
      SYNTAX  INTEGER {
               noFailure                       (1),
               internalError                   (2),
               localAllocFailure               (3),
               remoteAllocFailure              (4),
               localNoAccess                   (5),
               remoteNoAccess          (6),
               localPvcDown                    (7),
               remotePvcDown           (8),
               localPvcBusy                    (9),
               remotePvcBusy           (10),
               localFcnFailure         (11),
               remoteFcnFailure                (12),
               localDsnFailure         (13),
               localRefInUse                   (14),
               remoteAliasNotFound             (15),
               remoteNoPvcService              (16),
               mpeInvalidSubref                (17)

               }
      ACCESS  read-only
      STATUS  mandatory
      DESCRIPTION
"Indicates the status of a failed connection. The value of this object is 
only valid only between attempts to establish the route connection 
(gimSRRouteStatus = notConnected), and may or may not change after 
successive failed attempts.

Options:
noFailure (1): Once a system route has been successfully connected, this 
value is maintained for the duration of the connection.

internalError (2): An internal error has occurred.

localAllocFailure (3): There is insufficient memory available for X25 
Convergence to establish this connection.

remoteAllocFailure (4): There is insufficient memory available for the 
destination protocol layer to establish this connection.

localNoAccess (5): This route is associated with a SAP that does not 
exist.

remoteNoAccess (6): This route is associated with a SAP that does not 
exist at the destination layer.

localPvcDown (7): For future use.

remotePvcDown (8): The PVC at the destination protocol layer is down.

localPvcBusy (9): The SAP associated with this route is already connected.

remotePvcBusy (10): The destination associated with this route is already 
connected. This typically occurs when the route is a non-MPE (PVC 
consolidating) circuit.

localFcnFailure (11): Flow control negotiation failed.

remoteFcnFailure (12): Flow control negotiation failed at the destination 
protocol layer.

localDsnFailure (13): Data size negotiation failed.

localRefInUse (14): Data size negotiation failed at the destination 
protocol layer.

remoteAliasNotFound (15): The destination alias (gimSRDestAlias) does 
not exist.

remoteNoPvcService (16): The destination protocol layer does not support 
PVC service.

mpeInvalidSubref (17): The value of gimSRSubRef is invalid at the 
destination protocol layer. (i.e., lapcnvSRSubRef is set to '0' and the 
destination frame relay circuit is configured for PVC consolidation)."
      ::= { gimSysRouteEntry 11 }



--  XIM DTE Table

--  The table describing:
--      parameters required to form an X.25 Call Request when a logical connections is attempted 
--      whenever an IP or Voice datagrams are received by the XIM from the IAM module.

ximDteTable OBJECT-TYPE
   SYNTAX  SEQUENCE OF XimDteEntry
   ACCESS  not-accessible
   STATUS  mandatory
   DESCRIPTION
"A table containing the DTE X.28 Selection command objects for each defined 
'abbreviated address'."
    --#STARTING_VERSION 1
  ::= { cxGim 12 }


   ximDteEntry OBJECT-TYPE
      SYNTAX  XimDteEntry
      ACCESS  not-accessible
      STATUS  mandatory
      DESCRIPTION
"The objects for a specific DTE X.28 Selection entry."
      INDEX { ximDteSapNumber , ximDteDteNumber }
      ::= { ximDteTable 1 }


   XimDteEntry ::=
      SEQUENCE {
 -- Parameters
ximDteSapNumber                    	SapIndex,
ximDteDteNumber                    	DteIndex,
ximDteRowStatus                 	INTEGER,
ximDteCalledAddress 		DisplayString,                  
ximDteFacilityField                     	DisplayString,                  
ximDteUserDataField                     	DisplayString                  
}                       


ximDteSapNumber OBJECT-TYPE
      SYNTAX  SapIndex
      ACCESS  read-only
      STATUS  mandatory
      DESCRIPTION
"Associates the DTE entries defined by the object 'ximDteDteNumber' with an xim sap number."
      ::= { ximDteEntry 1 }


ximDteDteNumber OBJECT-TYPE
      SYNTAX  DteIndex
      ACCESS  read-only
      STATUS  mandatory
      DESCRIPTION
"Associates this DTE entry with the xim sap number defined by the object 'ximDteSapNumber',

Currently the XIM will support ONLY one entry. "
      ::= { ximDteEntry 2 }


   ximDteRowStatus OBJECT-TYPE
      SYNTAX  INTEGER {
               invalid         (1),
               valid           (2)
               }
      ACCESS  read-write
      STATUS  mandatory
      DESCRIPTION
"Indicates whether this specific entry is configured within the MIB.  
Entries (rows) may be created by setting this object value to 'valid', 
or deleted by changing this object value to 'invalid'."
      ::= { ximDteEntry 3 }


ximDteCalledAddress OBJECT-TYPE
      SYNTAX DisplayString (SIZE (0..15))
      ACCESS  read-write
      STATUS  mandatory
      DESCRIPTION
"Defines the network address of a remote device for this DTE entry.
 Allowable values: 1 to 15 numerical digits. "
      REFERENCE  "CCITT X.28 3.5.15.2.1, CCiTT X.25, CCITT X.121"
      DEFVAL { "" }
      ::= { ximDteEntry 5 }

-- gap (7) for future entries 

   ximDteFacilityField OBJECT-TYPE
      SYNTAX DisplayString (SIZE (0..64))
      ACCESS  read-write
      STATUS  mandatory
      DESCRIPTION
"Defines the facility codes and parameters requires for the X.28 
Selection command for this DTE entry. The facility codes and parameters
must be entered as defined in the CCITT X.28 Recommendation.  
The following facilities are supported:

- Reverse charge  ('R')

A value of null string (blank) means no facilities. "
      REFERENCE       "CCITT X.28 3.5.15.1"
      DEFVAL { "" }
      ::= { ximDteEntry 12 }


   ximDteUserDataField OBJECT-TYPE
      SYNTAX DisplayString (SIZE (0..12))
      ACCESS  read-write
      STATUS  mandatory
      DESCRIPTION
"Defines the user data field of the X.28 Selection command for this DTE 
entry.  A value of nul string (blank) means no user data. "
      REFERENCE       "CCITT X.28 3.5.15.3"
      DEFVAL { "" }
      ::= { ximDteEntry 13 }


END
