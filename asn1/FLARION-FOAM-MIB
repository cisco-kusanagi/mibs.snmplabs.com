-- $Id: FLARION-FOAM-MIB.txt,v 1.1.2.1 2004/11/01 21:56:19 mkanaka Exp $



FLARION-FOAM-MIB DEFINITIONS ::= BEGIN

IMPORTS
        OBJECT-TYPE, Unsigned32, Counter32
                FROM SNMPv2-SMI

        DisplayString
                FROM SNMPv2-TC

        AdminState, oem, rrBaseBandUnit
                FROM FLARION-MIB;

foam              OBJECT IDENTIFIER ::= { oem 3 }


-- Card operational state
CardOpState ::= INTEGER {
    cardOpStateUnknown(0),
    cardOpStateNotPresent(1),
    cardOpStateStandby(2),
    cardOpStateActive(3),
    cardOpStateDown(4)
}

-- Card temperature status
CardTempStatus ::= INTEGER {
    tempUnknown(0),
    tempNominal(1),
    tempHigh(2),
    tempSevere(3),
    tempCritical(4)
}

-- Card voltage status
CardVoltageStatus ::= INTEGER {
    voltageUnknown(0),
    voltageNominal(1),
    voltageLow(2),
    voltageHigh(3)
}



foamSerialNumber    OBJECT-TYPE
    SYNTAX          DisplayString
    MAX-ACCESS      read-only
    STATUS          current
    DESCRIPTION     "Foam serial number."
    ::= { foam 1 }

foamProductionDate  OBJECT-TYPE
    SYNTAX          DisplayString
    MAX-ACCESS      read-only
    STATUS          current
    DESCRIPTION     "Foam production date (mm/dd/yyyy)."
    ::= { foam 2 }

foamPartNumber      OBJECT-TYPE
    SYNTAX          DisplayString
    MAX-ACCESS      read-only
    STATUS          current
    DESCRIPTION     "Foam part number."
    ::= { foam 3 }

foamDescription     OBJECT-TYPE
    SYNTAX          DisplayString
    MAX-ACCESS      read-only
    STATUS          current
    DESCRIPTION     "Foam description."
    ::= { foam 4 }


foamHardwareVersion OBJECT-TYPE
    SYNTAX          DisplayString
    MAX-ACCESS      read-only
    STATUS          current
    DESCRIPTION     "Foam hardware version."
    ::= { foam 5 }

foamAssemblyId   OBJECT-TYPE
    SYNTAX          DisplayString
    MAX-ACCESS      read-only
    STATUS          current
    DESCRIPTION     "Foam assembly ID."
    ::= { foam 6 }

foamSlotID          OBJECT-TYPE
    SYNTAX          INTEGER
    MAX-ACCESS      read-only
    STATUS          current
    DESCRIPTION     "Slot of foam reside on."
    ::= {foam 7}

foamBtsIdentifier   OBJECT-TYPE
    SYNTAX          DisplayString
    MAX-ACCESS      read-only
    STATUS          current
    DESCRIPTION     "BTS Identifier."
    ::= {foam 8}
    
foamBscNameIdentifier   OBJECT-TYPE
    SYNTAX              DisplayString
    MAX-ACCESS          read-only
    STATUS              current
    DESCRIPTION         "BSC name Identifier."
    ::= {foam 9}

foamOpState      OBJECT-TYPE
    SYNTAX          CardOpState
    MAX-ACCESS      read-only
    STATUS          current
    DESCRIPTION     "Foam operational state."
    ::= { foam 10 }
    
foamAdminState       OBJECT-TYPE
    SYNTAX              AdminState
    MAX-ACCESS          read-write
    STATUS              current
    DESCRIPTION         "Foam administrative state."
    ::= { foam 11 }

foamLed     OBJECT IDENTIFIER ::= { foam 14 }

foamRedLed          OBJECT-TYPE
    SYNTAX          INTEGER {
                        on(1),
                        off(2),
                        flashing(3)
                    }
    MAX-ACCESS      read-only
    STATUS          current
    DESCRIPTION     "Foam Red LED state."
    ::= { foamLed 1 }

foamAmberLed        OBJECT-TYPE
    SYNTAX          INTEGER {
                        on(1),
                        off(2),
                        flashing(3)
                    }
    MAX-ACCESS      read-only
    STATUS          current
    DESCRIPTION     "Foam Amber LED state."
    ::= { foamLed 2 }

foamGreenLed        OBJECT-TYPE
    SYNTAX          INTEGER {
                        on(1),
                        off(2),
                        flashing(3)
                    }
    MAX-ACCESS      read-only
    STATUS          current
    DESCRIPTION     "Foam Green LED state."
    ::= { foamLed 3 }
                
--
-- Main Controller Unit (MCU) --

foamMcu                 OBJECT IDENTIFIER ::= { foam 15 }

foamMcuTable        OBJECT-TYPE
    SYNTAX          SEQUENCE OF FoamMcuEntry
    MAX-ACCESS      not-accessible
    STATUS          current
    DESCRIPTION     ""
    ::= { foamMcu 1 }

foamMcuEntry        OBJECT-TYPE
    SYNTAX          FoamMcuEntry
    MAX-ACCESS      not-accessible
    STATUS          current
    DESCRIPTION     ""
    INDEX           { foamBbuIndex }
    ::= { foamMcuTable 1 }

FoamMcuEntry ::= SEQUENCE {
    foamMcuIndex             INTEGER,
    foamMcuOpState           CardOpState,
    foamMcuTempStatus        CardTempStatus,
    foamMcuVoltageStatus     CardVoltageStatus,
    foamMcuSerialNumber      DisplayString,
    foamMcuProductionDate    DisplayString,
    foamMcuPartNumber        DisplayString,
    foamMcuDescription       DisplayString,
    foamMcuHardwareVersion   DisplayString,
    foamMcuAssemblyId        DisplayString,
    foamMcuAdminState        AdminState
}

foamMcuIndex        OBJECT-TYPE
    SYNTAX          INTEGER
    MAX-ACCESS      read-only
    STATUS          current
    DESCRIPTION     "MCU index."
    ::= { foamMcuEntry 1 }
    
foamMcuOpState      OBJECT-TYPE
    SYNTAX          CardOpState
    MAX-ACCESS      read-only
    STATUS          current
    DESCRIPTION     "MCU operational state."
    ::= { foamMcuEntry 2 }
    
foamMcuTempStatus   OBJECT-TYPE
    SYNTAX          CardTempStatus
    MAX-ACCESS      read-only
    STATUS          current
    DESCRIPTION     "MCU temperature status."
    ::= { foamMcuEntry 4 }

foamMcuVoltageStatus    OBJECT-TYPE
    SYNTAX              CardVoltageStatus
    MAX-ACCESS          read-only
    STATUS              current
    DESCRIPTION         "MCU voltage status."
    ::= { foamMcuEntry 5 }

foamMcuSerialNumber     OBJECT-TYPE
    SYNTAX              DisplayString
    MAX-ACCESS          read-only
    STATUS              current
    DESCRIPTION         "MCU serial number."
    ::= { foamMcuEntry 6 }

foamMcuProductionDate   OBJECT-TYPE
    SYNTAX              DisplayString
    MAX-ACCESS          read-only
    STATUS              current
    DESCRIPTION         "MCU production date."
    ::= { foamMcuEntry 7 }

foamMcuPartNumber    OBJECT-TYPE
    SYNTAX           DisplayString
    MAX-ACCESS       read-only
    STATUS           current
    DESCRIPTION      "MCU part number."
    ::= { foamMcuEntry 8 }

foamMcuDescription   OBJECT-TYPE
    SYNTAX           DisplayString
    MAX-ACCESS       read-only
    STATUS           current
    DESCRIPTION      "MCU description."
    ::= { foamMcuEntry 9 }

foamMcuHardwareVersion  OBJECT-TYPE
    SYNTAX              DisplayString
    MAX-ACCESS          read-only
    STATUS              current
    DESCRIPTION         "MCU hardware version."
    ::= { foamMcuEntry 10 }

foamMcuAssemblyId   OBJECT-TYPE
    SYNTAX          DisplayString
    MAX-ACCESS      read-only
    STATUS          current
    DESCRIPTION     "MCU assembly ID."
    ::= { foamMcuEntry 12 }


foamMcuAdminState       OBJECT-TYPE
    SYNTAX              AdminState
    MAX-ACCESS          read-write
    STATUS              current
    DESCRIPTION         "MCU administrative state."
    ::= { foamMcuEntry 20 }



foamBbu                 OBJECT IDENTIFIER ::= { foam 16 }    
--
-- Base Band Unit (BBU) Table
--
foamBbuTable        OBJECT-TYPE
    SYNTAX          SEQUENCE OF FoamBbuEntry
    MAX-ACCESS      not-accessible
    STATUS          current
    DESCRIPTION     ""
    ::= { foamBbu 1 }

foamBbuEntry        OBJECT-TYPE
    SYNTAX          FoamBbuEntry
    MAX-ACCESS      not-accessible
    STATUS          current
    DESCRIPTION     ""
    INDEX           { foamBbuIndex }
    ::= { foamBbuTable 1 }

FoamBbuEntry ::= SEQUENCE {
    foamBbuIndex             INTEGER,
    foamBbuOpState           CardOpState,
    foamBbuTempStatus        CardTempStatus,
    foamBbuVoltageStatus     CardVoltageStatus,
    foamBbuSerialNumber      DisplayString,
    foamBbuProductionDate    DisplayString,
    foamBbuPartNumber        DisplayString,
    foamBbuDescription       DisplayString,
    foamBbuHardwareVersion   DisplayString,
    foamBbuAssemblyId        DisplayString,
    foamBbuAdminState        AdminState
}

foamBbuIndex        OBJECT-TYPE
    SYNTAX          INTEGER
    MAX-ACCESS      read-only
    STATUS          current
    DESCRIPTION     "BBU index."
    ::= { foamBbuEntry 1 }

foamBbuOpState      OBJECT-TYPE
    SYNTAX          CardOpState
    MAX-ACCESS      read-only
    STATUS          current
    DESCRIPTION     "BBU operational state."
    ::= { foamBbuEntry 2 }

foamBbuTempStatus   OBJECT-TYPE
    SYNTAX          CardTempStatus
    MAX-ACCESS      read-only
    STATUS          current
    DESCRIPTION     "BBU temperature status."
    ::= { foamBbuEntry 4 }

foamBbuVoltageStatus    OBJECT-TYPE
    SYNTAX              CardVoltageStatus
    MAX-ACCESS          read-only
    STATUS              current
    DESCRIPTION         "BBU voltage status."
    ::= { foamBbuEntry 5 }

foamBbuSerialNumber     OBJECT-TYPE
    SYNTAX              DisplayString
    MAX-ACCESS          read-only
    STATUS              current
    DESCRIPTION         "BBU serial number."
    ::= { foamBbuEntry 6 }

foamBbuProductionDate   OBJECT-TYPE
    SYNTAX              DisplayString
    MAX-ACCESS          read-only
    STATUS              current
    DESCRIPTION         "BBU production date."
    ::= { foamBbuEntry 7 }

foamBbuPartNumber       OBJECT-TYPE
    SYNTAX              DisplayString
    MAX-ACCESS          read-only
    STATUS              current
    DESCRIPTION         "BBU part number."
    ::= { foamBbuEntry 8 }

foamBbuDescription      OBJECT-TYPE
    SYNTAX              DisplayString
    MAX-ACCESS          read-only
    STATUS              current
    DESCRIPTION         "BBU description."
    ::= { foamBbuEntry 9 }

foamBbuHardwareVersion  OBJECT-TYPE
    SYNTAX              DisplayString
    MAX-ACCESS          read-only
    STATUS              current
    DESCRIPTION         "BBU hardware version."
    ::= { foamBbuEntry 10 }

foamBbuAssemblyId       OBJECT-TYPE
    SYNTAX              DisplayString
    MAX-ACCESS          read-only
    STATUS              current
    DESCRIPTION         "BBU assembly Id."
    ::= { foamBbuEntry 12 }

foamBbuAdminState       OBJECT-TYPE
    SYNTAX              AdminState
    MAX-ACCESS          read-write
    STATUS              current
    DESCRIPTION         "BBU administrative state."
    ::= { foamBbuEntry 20 }


--
-- BBU System Table
--
foamBbuSysTable     OBJECT-TYPE
    SYNTAX          SEQUENCE OF FoamBbuSysEntry
    MAX-ACCESS      not-accessible
    STATUS          current
    DESCRIPTION     "Base Band Unit system information."
    ::= { foamBbu 2 }

foamBbuSysEntry     OBJECT-TYPE
    SYNTAX          FoamBbuSysEntry
    MAX-ACCESS      not-accessible
    STATUS          current
    DESCRIPTION     "Base Band Unit system table entry."
    INDEX           { bbuSysId }
    ::= { foamBbuSysTable 1 }

FoamBbuSysEntry ::= SEQUENCE {
    foamBbuSysId                INTEGER,
    foamBbuDspVer               DisplayString,
    foamBbuLlcVer               DisplayString,
    foamBbuTxFpgaVer            DisplayString,
    foamBbuRxFpgaVer            DisplayString,
    foamBbuLdpcVer              Unsigned32,
    foamBbuRfChanNum            INTEGER,
    foamBbuExtGainTx            INTEGER,
    foamBbuExtGainRx            INTEGER,
    foamBbuRfGainRx0            INTEGER,
    foamBbuRfGainRx1            INTEGER,
    foamBbuRfBand               INTEGER,
    foamBbuRfPowerTx0           INTEGER,
    foamBbuRfPowerTx1           INTEGER,
    foamBbuRfuEnableMask        INTEGER,
    foamBbuSlope                INTEGER,
    foamBbuSleepInactivityTimer INTEGER,
    foamBbuLuTimer              INTEGER,
    foamTxPowerRxParitySectorId INTEGER,
    foamTxPowerThresholdValue   INTEGER,
    foamTxPowerActualValue      INTEGER,
    foamRxParityReportPeriod   INTEGER,
    foamRxParityThresholdValue  INTEGER,
    foamRxParityErrorCount      INTEGER
}

foamBbuSysId        OBJECT-TYPE
    SYNTAX          INTEGER
    MAX-ACCESS      read-only
    STATUS          current
    DESCRIPTION     "BBU ID."
    ::= { foamBbuSysEntry 1 }

foamBbuDspVer       OBJECT-TYPE
    SYNTAX          DisplayString
    MAX-ACCESS      read-only
    STATUS          current
    DESCRIPTION     "The DSP code version."
    ::= { foamBbuSysEntry 2 }

foamBbuLlcVer       OBJECT-TYPE
    SYNTAX          DisplayString
    MAX-ACCESS      read-only
    STATUS          current
    DESCRIPTION     "The Link List Controller FPGA firmware version."
    ::= { foamBbuSysEntry 3 }

foamBbuTxFpgaVer    OBJECT-TYPE
    SYNTAX          DisplayString
    MAX-ACCESS      read-only
    STATUS          current
    DESCRIPTION     "The Transmit FPGA firmware version."
    ::= { foamBbuSysEntry 4 }

foamBbuRxFpgaVer    OBJECT-TYPE
    SYNTAX          DisplayString
    MAX-ACCESS      read-only
    STATUS          current
    DESCRIPTION     "The Receive FPGA firmware version."
    ::= { foamBbuSysEntry 5 }

foamBbuLdpcVer      OBJECT-TYPE
    SYNTAX          Unsigned32
    MAX-ACCESS      read-only
    STATUS          current
    DESCRIPTION     "The Low Density Parity Check (LDPC) code version."
    ::= { foamBbuSysEntry 6 }

foamBbuRfChanNum    OBJECT-TYPE
    SYNTAX          INTEGER (0..2000)
    MAX-ACCESS      read-write
    STATUS          current
    DESCRIPTION     "The RF channel number. Editable offline."
    DEFVAL          { 295 }
    ::= { foamBbuSysEntry 50 }

foamBbuExtGainTx    OBJECT-TYPE 
    SYNTAX          INTEGER (-1600..2240)
    MAX-ACCESS      read-write
    STATUS          current
    DESCRIPTION     "External Tx gain."
    DEFVAL          { 1376 }
    ::= { foamBbuSysEntry 51 }

foamBbuExtGainRx    OBJECT-TYPE
    SYNTAX          INTEGER (-1600..2240)
    MAX-ACCESS      read-write
    STATUS          current
    DESCRIPTION     "External Rx gain."
    DEFVAL          { 1376 }
    ::= { foamBbuSysEntry 52 }

foamBbuRfGainRx0    OBJECT-TYPE
    SYNTAX          INTEGER (-10..75)
    MAX-ACCESS      read-write
    STATUS          current
    DESCRIPTION     "RF gain on Rx0 channel."
    DEFVAL          { 42 }
    ::= { foamBbuSysEntry 53 }

foamBbuRfGainRx1    OBJECT-TYPE
    SYNTAX          INTEGER (-10..75)
    MAX-ACCESS      read-write
    STATUS          current
    DESCRIPTION     "RF gain on Rx1 channel."
    DEFVAL          { 42 }
    ::= { foamBbuSysEntry 54 }

foamBbuRfBand       OBJECT-TYPE
    SYNTAX          INTEGER (0..255)
    MAX-ACCESS      read-write
    STATUS          current
    DESCRIPTION     "RF band. Editable offline."
    DEFVAL          { 0 }
    ::= { foamBbuSysEntry 55 }

foamBbuRfPowerTx0   OBJECT-TYPE
    SYNTAX          INTEGER (-20..10)
    MAX-ACCESS      read-write
    STATUS          current
    DESCRIPTION     "Target RF signal strength from the TXU on channel 0."
    DEFVAL          { 0 }
    ::= { foamBbuSysEntry 56 }

foamBbuRfPowerTx1   OBJECT-TYPE
    SYNTAX          INTEGER (-20..10)
    MAX-ACCESS      read-write
    STATUS          current
    DESCRIPTION     "Target RF signal strneght from the TXU on channel 1."
    DEFVAL          { 0 }
    ::= { foamBbuSysEntry 57 }

foamBbuRfuEnableMask    OBJECT-TYPE
    SYNTAX              INTEGER (0..15)
    MAX-ACCESS          read-write
    STATUS              current
    DESCRIPTION     "This is a bit mask to choose between the 0 and 1 channels
                    for Rx and Tx. The value should be an OR of the channels
                    selected, where: Tx0 = 0001
                                     Tx1 = 0010
                                     Rx0 = 0100
                                     Rx1 = 1000
                    For example, set this object to 6 if Rx0 and Tx1 need to 
                    be enabled."
    DEFVAL          { 15 }
    ::= { foamBbuSysEntry 59 }

foamBbuSlope        OBJECT-TYPE
    SYNTAX          INTEGER (1..112)
    MAX-ACCESS      read-write
    STATUS          current
    DESCRIPTION     "Slope. Editable offline."
    DEFVAL          { 10 }
    ::= { foamBbuSysEntry 70 }

foamBbuSleepInactivityTimer OBJECT-TYPE
    SYNTAX                  INTEGER (0..3600)
    MAX-ACCESS              read-write
    STATUS                  current
    DESCRIPTION             "Time, in seconds, of inactivity after which a mobile moves
                            to the Sleep state."
    DEFVAL          { 0 }
    ::= { foamBbuSysEntry 91 }

foamBbuLuTimer      OBJECT-TYPE
    SYNTAX          INTEGER (0..86400)
    MAX-ACCESS      read-write
    STATUS          current
    DESCRIPTION     "Periodicity of location update done by a mobile."
    DEFVAL          { 900 }
    ::= { foamBbuSysEntry 100 }

foamTxPowerThresholdValue   OBJECT-TYPE
    SYNTAX                  INTEGER (0..65535)
    MAX-ACCESS              read-write
    STATUS                  current
    DESCRIPTION             "Tx power threshold value, provisioned."
    DEFVAL {65535}
    ::= {foamBbuSysEntry 200}

foamTxPowerActualValue  OBJECT-TYPE
    SYNTAX              INTEGER (0..65535)
    MAX-ACCESS          read-only
    STATUS              current
    DESCRIPTION         "Actual Tx Power value, runtime data."
    ::= {foamBbuSysEntry 201}

foamRxParityReportPeriod   OBJECT-TYPE
    SYNTAX                  INTEGER
    UNITS                   "seconds"
    MAX-ACCESS              read-write
    STATUS                  current
    DESCRIPTION             "Rx parity error reporting period, provisioned."
    DEFVAL {1}
    ::= {foamBbuSysEntry 202}

foamRxParityThresholdValue  OBJECT-TYPE
    SYNTAX                  INTEGER
    MAX-ACCESS              read-write
    STATUS                  current
    DESCRIPTION             "Rx parity error threshold value, provisioned."
    DEFVAL {1}
    ::= {foamBbuSysEntry 203}

foamRxParityErrorCount  OBJECT-TYPE
    SYNTAX              INTEGER
    MAX-ACCESS          read-only
    STATUS              current
    DESCRIPTION         "Actual Rx parity error count in the given reporting
                                period, runtime data."
    ::= {foamBbuSysEntry 204}



foamBhu                 OBJECT IDENTIFIER ::= { foam 17 }

foamBhuTable        OBJECT-TYPE
    SYNTAX          SEQUENCE OF FoamBhuEntry
    MAX-ACCESS      not-accessible
    STATUS          current
    DESCRIPTION     ""
    ::= { foamBhu 1 }

foamBhuEntry        OBJECT-TYPE
    SYNTAX          FoamBhuEntry
    MAX-ACCESS      not-accessible
    STATUS          current
    DESCRIPTION     ""
    INDEX           { foamBhuIndex }
    ::= { foamBhuTable 1 }

FoamBhuEntry ::= SEQUENCE {
    foamBhuIndex             INTEGER,
    foamBhuOpState           CardOpState
}

foamBhuIndex        OBJECT-TYPE
    SYNTAX          INTEGER
    MAX-ACCESS      read-only
    STATUS          current
    DESCRIPTION     "BHU index."
    ::= { foamBhuEntry 1 }

foamBhuOpState      OBJECT-TYPE
    SYNTAX          CardOpState
    MAX-ACCESS      read-only
    STATUS          current
    DESCRIPTION     "BHU operational state."
    ::= { foamBhuEntry 2 }

    
foamBackplane           OBJECT IDENTIFIER ::= { foam 18 }


foamBackplaneTempStatus   OBJECT-TYPE
    SYNTAX          CardTempStatus
    MAX-ACCESS      read-only
    STATUS          current
    DESCRIPTION     "Backplane temperature status."
    ::= { foamBackplane 1 }

foamBackplaneVoltageStatus    OBJECT-TYPE
    SYNTAX              CardVoltageStatus
    MAX-ACCESS          read-only
    STATUS              current
    DESCRIPTION         "Backplane voltage status."
    ::= { foamBackplane 2 }


foamBackplaneSerialNumber    OBJECT-TYPE
    SYNTAX          DisplayString
    MAX-ACCESS      read-only
    STATUS          current
    DESCRIPTION     "Backplane serial number."
    ::= { foamBackplane 3 }

foamBackplaneProductionDate  OBJECT-TYPE
    SYNTAX          DisplayString
    MAX-ACCESS      read-only
    STATUS          current
    DESCRIPTION     "Backplane production date (mm/dd/yyyy)."
    ::= { foamBackplane 4 }

foamBackplanePartNumber      OBJECT-TYPE
    SYNTAX          DisplayString
    MAX-ACCESS      read-only
    STATUS          current
    DESCRIPTION     "Backplane part number."
    ::= { foamBackplane 5 }

foamBackplaneDescription     OBJECT-TYPE
    SYNTAX          DisplayString
    MAX-ACCESS      read-only
    STATUS          current
    DESCRIPTION     "Backplane description."
    ::= { foamBackplane 6 }

foamBackplaneHardwareVersion OBJECT-TYPE
    SYNTAX          DisplayString
    MAX-ACCESS      read-only
    STATUS          current
    DESCRIPTION     "Backplane hardware version."
    ::= { foamBackplane 7 }

foamBackplaneAssemblyId   OBJECT-TYPE
    SYNTAX          DisplayString
    MAX-ACCESS      read-only
    STATUS          current
    DESCRIPTION     "Backplane assembly ID."
    ::= { foamBackplane 8 }


foamHsspc               OBJECT IDENTIFIER ::= { foam 19 }    

foamForwardLinkParity   OBJECT-TYPE
    SYNTAX              INTEGER
    MAX-ACCESS          read-only
    STATUS              current
    DESCRIPTION         "Forward path parity error count."
    ::= {foamHsspc 1}

foamLargeErrorCount     OBJECT-TYPE
    SYNTAX              INTEGER
    MAX-ACCESS          read-only
    STATUS              current
    DESCRIPTION         "Large error count."
    ::= {foamHsspc 2}

foamReverseLinkParity   OBJECT-TYPE
    SYNTAX              INTEGER
    MAX-ACCESS          read-only
    STATUS              current
    DESCRIPTION         "Reverse link parity error count."
    ::= {foamHsspc 3}


foamCoreConnectFailure  OBJECT-TYPE
    SYNTAX              INTEGER
    MAX-ACCESS          read-only
    STATUS              current
    DESCRIPTION         "The connection to the CORE has been lost"
    ::= {foamHsspc 4}

foamLinkDisruption      OBJECT-TYPE
    SYNTAX              INTEGER
    MAX-ACCESS          read-only
    STATUS              current
    DESCRIPTION         "The link has been disrupted."
    ::= {foamHsspc 5}

foamEvenSecondNotSynced     OBJECT-TYPE
    SYNTAX                  INTEGER
    MAX-ACCESS              read-only
    STATUS                  current
    DESCRIPTION             "MBP's even second signal is not synchronized."
    ::= {foamHsspc 6}

foamPLLNotLocked        OBJECT-TYPE
    SYNTAX              INTEGER
    MAX-ACCESS          read-only
    STATUS              current
    DESCRIPTION         "CEM Interconnect Board's 32 fc frequency synthesizer (PLL) 
                        is not locked to its 52 fc reference."
    ::= {foamHsspc 7}

foamMuxFifoError        OBJECT-TYPE
    SYNTAX              INTEGER
    MAX-ACCESS          read-only
    STATUS              current
    DESCRIPTION         "Error with the CEM Interconnect Board's multiplexor FIFO"
    ::= {foamHsspc 8}

foamDemuxFifoError      OBJECT-TYPE
    SYNTAX              INTEGER
    MAX-ACCESS          read-only
    STATUS              current
    DESCRIPTION         "Error with the CEM Interconnect Board's demultiplexor FIFO."
    ::= {foamHsspc 9}

foamI2CError            OBJECT-TYPE
    SYNTAX              INTEGER
    MAX-ACCESS          read-only
    STATUS              current
    DESCRIPTION         "Communication error on the IIC bus"
    ::= {foamHsspc 10}

foamI2CFailure          OBJECT-TYPE
    SYNTAX              INTEGER
    MAX-ACCESS          read-only
    STATUS              current
    DESCRIPTION         "The communication with the HSSPC across the I2C is still 
                        failing after attempted recovery."
    ::= {foamHsspc 11}

foamTransmitParityError     OBJECT-TYPE
    SYNTAX                  INTEGER
    MAX-ACCESS              read-only
    STATUS                  current
    DESCRIPTION             "HSSPC transmit parity error."
    ::= {foamHsspc 12}

foamMultTransParityErrors    OBJECT-TYPE
    SYNTAX                   INTEGER
    MAX-ACCESS               read-only
    STATUS                   current
    DESCRIPTION              "Three HSSPC transmit parity errors occur within a 
                             period of 15 parity interrupt calls. "
    ::= {foamHsspc 13}


foamOam                OBJECT IDENTIFIER ::= {foam 20}

--
-- Tx Power threshold crossing table
--


foamDcgTxRxStatusTable      OBJECT-TYPE
    SYNTAX                  SEQUENCE OF FoamDcgTxRxStatusEntry
    MAX-ACCESS              not-accessible
    STATUS                  current
    DESCRIPTION             "Table of Tx/Rx status on DCG side."
    ::= {foamOam 1}

foamDcgTxRxStatusEntry      OBJECT-TYPE
    SYNTAX                  FoamDcgTxRxStatusEntry
    MAX-ACCESS              not-accessible
    STATUS                  current
    DESCRIPTION             "Tx/Rx status table entry."
    INDEX                   {dcgTxRxsectorId}
    ::= {foamDcgTxRxStatusTable 1}

FoamDcgTxRxStatusEntry ::= SEQUENCE {
    foamDcgTxRxsectorId         INTEGER,
    foamDcgTxOpState            INTEGER,
    foamDcgTxAdminState         INTEGER,
    foamDcgTxAvailibility       INTEGER,
    foamDcgRxOpState            INTEGER,
    foamDcgRxAdminState         INTEGER    
}

foamDcgTxRxsectorId     OBJECT-TYPE
    SYNTAX              INTEGER
    MAX-ACCESS          read-only
    STATUS              current
    DESCRIPTION         "Sector Id."
    ::= {foamDcgTxRxStatusEntry 1}

foamDcgTxOpState    OBJECT-TYPE
    SYNTAX          INTEGER {
                            disabled(0),
                            enabled(1),
                            invalidOrUnknown(255)
                            }
    MAX-ACCESS      read-only
    STATUS          current
    DESCRIPTION     "Tx operational state on DCG side."
    ::= {foamDcgTxRxStatusEntry 2}

foamDcgTxAdminState OBJECT-TYPE
    SYNTAX          INTEGER {
                            locked(0),
                            shuttingDown(1),
                            unlocked(2),
                            invalidOrUnknown(255)
                            }
    MAX-ACCESS      read-only
    STATUS          current
    DESCRIPTION     "Tx admin state on DCG side."
    ::= {foamDcgTxRxStatusEntry 3}

foamDcgTxAvailibility   OBJECT-TYPE
    SYNTAX              INTEGER
    MAX-ACCESS          read-only
    STATUS              current
    DESCRIPTION         "Tx availability state on DCG side."
    ::= {foamDcgTxRxStatusEntry 4}

foamDcgRxOpState    OBJECT-TYPE
    SYNTAX          INTEGER {
                            disabled(0),
                            enabled(1),
                            invalidOrUnknown(255)
                            }
    MAX-ACCESS      read-only
    STATUS          current
    DESCRIPTION     "Rx operational state on DCG side."
    ::= {foamDcgTxRxStatusEntry 5}

foamDcgRxAdminState OBJECT-TYPE
    SYNTAX          INTEGER {
                            locked(0),
                            shuttingDown(1),
                            unlocked(2),
                            invalidOrUnknown(255)
                            }
    MAX-ACCESS      read-only
    STATUS          current
    DESCRIPTION     "Rx admin state on DCG side."
    ::= {foamDcgTxRxStatusEntry 6}

foamFrequencyRefStatus   OBJECT IDENTIFIER ::= {foamOam 2}

foamFrequencyRefOpState OBJECT-TYPE
    SYNTAX              INTEGER {
                                disabled(0),
                                enabled(1),
                                invalidOrUnknown(255)
                                }
    MAX-ACCESS          read-only
    STATUS              current
    DESCRIPTION         "Frequency reference operational state."
    ::= {foamFrequencyRefStatus 1}

foamfrequencyRefAdminState  OBJECT-TYPE
    SYNTAX                  INTEGER {
                                    locked(0),
                                    shuttingDown(1),
                                    unlocked(2),
                                    invalidOrUnknown(255)
                                    }
    MAX-ACCESS              read-only
    STATUS                  current
    DESCRIPTION             "Frequency reference admin state."
    ::= {foamFrequencyRefStatus 2}

foamGpsOperationalMode      OBJECT-TYPE
    SYNTAX                  INTEGER {
                                    powerUp(1),
                                    normal(2),
                                    unlocked(3),
                                    holdover(4),
                                    recovery(5),
                                    invalidOrUnknown(255)
                                    }
    MAX-ACCESS              read-only
    STATUS                  current
    DESCRIPTION             "GPS operational mode."
    ::= {foamFrequencyRefStatus 3}

foamGpsHoldoverDuratiuon    OBJECT-TYPE
    SYNTAX                  INTEGER
    MAX-ACCESS              read-only
    STATUS                  current
    DESCRIPTION             "GPS holdover duration."
    ::= {foamFrequencyRefStatus 4}

foamGpsLatitude OBJECT IDENTIFIER ::= {foamFrequencyRefStatus 5}

foamGpsLatitudeDegree   OBJECT-TYPE
    SYNTAX              INTEGER (0..90)
    MAX-ACCESS          read-only
    STATUS              current
    DESCRIPTION         "GPS latitude -- degrees."
    ::= {foamGpsLatitude 1}

foamGpsLatitudeMinute   OBJECT-TYPE
    SYNTAX              INTEGER (0..59)
    MAX-ACCESS          read-only
    STATUS              current
    DESCRIPTION         "GPS latitude -- minutes."
    ::= {foamGpsLatitude 2}

foamGpsLatitudeSecond   OBJECT-TYPE
    SYNTAX              INTEGER (0..59)
    MAX-ACCESS          read-only
    STATUS              current
    DESCRIPTION         "GPS latitude -- seconds."
    ::= {foamGpsLatitude 3}

foamGpsLatitudeMillSecond   OBJECT-TYPE
    SYNTAX                  INTEGER (0..999)
    MAX-ACCESS              read-only
    STATUS                  current
    DESCRIPTION             "GPS latitude -- milliseconds."
    ::= {foamGpsLatitude 4}

foamGpsLatitudeHemisphere   OBJECT-TYPE
    SYNTAX                  INTEGER {
                                    north(78),
                                    south(83),
                                    invalidOrUnknown(255)
                                    }
    MAX-ACCESS              read-only
    STATUS                  current
    DESCRIPTION             "GPS latitude -- hemisphere."
    ::= {foamGpsLatitude 5}

foamGpsLongitude OBJECT IDENTIFIER ::= {foamFrequencyRefStatus 6}

foamGpsLongitudeDegree  OBJECT-TYPE
    SYNTAX              INTEGER (0..180)
    MAX-ACCESS          read-only
    STATUS              current
    DESCRIPTION         "GPS longitude -- degrees."
    ::= {foamGpsLongitude 1}

foamGpsLongitudeMinute  OBJECT-TYPE
    SYNTAX              INTEGER (0..59)
    MAX-ACCESS          read-only
    STATUS              current
    DESCRIPTION         "GPS longitude -- minutes."
    ::= {foamGpsLongitude 2}

foamGpsLongitudeSecond  OBJECT-TYPE
    SYNTAX              INTEGER (0..59)
    MAX-ACCESS          read-only
    STATUS              current
    DESCRIPTION         "GPS longitude -- seconds."
    ::= {foamGpsLongitude 3}

foamGpsLongitudeMillSecond  OBJECT-TYPE
    SYNTAX                  INTEGER (0..999)
    MAX-ACCESS              read-only
    STATUS                  current
    DESCRIPTION             "GPS longitude -- milliseconds."
    ::= {foamGpsLongitude 4}

foamGpsLongitudeHemisphere  OBJECT-TYPE
    SYNTAX                  INTEGER {
                                    east(69),
                                    west(87),
                                    invalidOrUnknown(255)
                                    }
    MAX-ACCESS              read-only
    STATUS                  current
    DESCRIPTION             "GPS longitude -- hemisphere."
    ::= {foamGpsLongitude 5}
   
foamGpsElevation        OBJECT-TYPE
    SYNTAX              INTEGER (-1000..10000)
    UNITS               "meters"
    MAX-ACCESS          read-only
    STATUS              current
    DESCRIPTION         "GPS elevation."
    ::= {foamFrequencyRefStatus 7}

foamLeapSecondInfo   OBJECT IDENTIFIER ::= {foamOam 3}

foamGpsTimeOfDay   OBJECT IDENTIFIER ::= {foamLeapSecondInfo 1}

foamGpsTodYear      OBJECT-TYPE
    SYNTAX          INTEGER (1900..65535)
    MAX-ACCESS      read-only
    STATUS          current
    DESCRIPTION     "GPS leap second time of day -- year."
    ::= {foamGpsTimeOfDay 1}

foamGpsTodMonth     OBJECT-TYPE
    SYNTAX          INTEGER (1..12)
    MAX-ACCESS      read-only
    STATUS          current
    DESCRIPTION     "GPS leap second time of day -- month."
    ::= {foamGpsTimeOfDay 2}

foamGpsTodDay       OBJECT-TYPE
    SYNTAX          INTEGER (1..31)
    MAX-ACCESS      read-only
    STATUS          current
    DESCRIPTION     "GPS leap second time of day -- day."
    ::= {foamGpsTimeOfDay 3}

foamGpsTodHour      OBJECT-TYPE
    SYNTAX          INTEGER (0..23)
    MAX-ACCESS      read-only
    STATUS          current
    DESCRIPTION     "GPS leap second time of day -- hour."
    ::= {foamGpsTimeOfDay 4}

foamGpsTodMinute    OBJECT-TYPE
    SYNTAX          INTEGER (0..59)
    MAX-ACCESS      read-only
    STATUS          current
    DESCRIPTION     "GPS leap second time of day -- minute."
    ::= {foamGpsTimeOfDay 5}


foamGpsTodSecond    OBJECT-TYPE
    SYNTAX          INTEGER (0..59)
    MAX-ACCESS      read-only
    STATUS          current
    DESCRIPTION     "GPS leap second time of day -- second."
    ::= {foamGpsTimeOfDay 6}

foamGpsTodMillSecond    OBJECT-TYPE
    SYNTAX              INTEGER
    MAX-ACCESS          read-only
    STATUS              current
    DESCRIPTION         "GPS leap second time of day -- millisecond."
    ::= {foamGpsTimeOfDay 7}
    
foamGpsUtcAccumulation  OBJECT-TYPE
    SYNTAX              INTEGER
    UNITS               "seconds"
    MAX-ACCESS          read-only
    STATUS              current
    DESCRIPTION         "The number of seconds between GPS time and UTC time due to
        the insertion of leap seconds."
    ::= {foamLeapSecondInfo 2}

foamGpsNextLSAdj   OBJECT IDENTIFIER ::= {foamLeapSecondInfo 3}

foamGpsNextLSAdjYear    OBJECT-TYPE
    SYNTAX              INTEGER (1900..65535)
    MAX-ACCESS          read-only
    STATUS              current
    DESCRIPTION         "GPS next leap second adjustment -- year."
    ::= {foamGpsNextLSAdj 1}

foamGpsNextLSAdjMonth   OBJECT-TYPE
    SYNTAX              INTEGER (1..12)
    MAX-ACCESS          read-only
    STATUS              current
    DESCRIPTION         "GPS next leap second adjustment -- month."
    ::= {foamGpsNextLSAdj 2}

foamGpsNextLSAdjDay     OBJECT-TYPE
    SYNTAX              INTEGER (1..31)
    MAX-ACCESS          read-only
    STATUS              current
    DESCRIPTION         "GPS next leap second adjustment -- day."
    ::= {foamGpsNextLSAdj 3}

foamGpsNextLSAdjHour    OBJECT-TYPE
    SYNTAX              INTEGER (0..23)
    MAX-ACCESS          read-only
    STATUS              current
    DESCRIPTION         "GPS next leap second adjustment -- hour."
    ::= {foamGpsNextLSAdj 4}

foamGpsNextLSAdjMinute  OBJECT-TYPE
    SYNTAX              INTEGER (0..59)
    MAX-ACCESS          read-only
    STATUS              current
    DESCRIPTION         "GPS next leap second adjustment -- minute."
    ::= {foamGpsNextLSAdj 5}

foamGpsNextLSAdjSecond  OBJECT-TYPE
    SYNTAX              INTEGER (0..59)
    MAX-ACCESS          read-only
    STATUS              current
    DESCRIPTION         "GPS next leap second adjustment -- second."
    ::= {foamGpsNextLSAdj 6}

foamGpsNextLSAdjMillSecond  OBJECT-TYPE
    SYNTAX                  INTEGER (0..999)
    MAX-ACCESS              read-only
    STATUS                  current
    DESCRIPTION             "GPS next leap second adjustment -- millisecond."
    ::= {foamGpsNextLSAdj 7}
    
foamDistributionDelayTable  OBJECT-TYPE
    SYNTAX                  SEQUENCE OF FoamDistributionDelayEntry
    MAX-ACCESS              not-accessible
    STATUS                  current
    DESCRIPTION             "Table of distribution delay."
    ::= {foamOam 4}

foamDistributionDelayEntry  OBJECT-TYPE
    SYNTAX                  FoamDistributionDelayEntry
    MAX-ACCESS              not-accessible
    STATUS                  current
    DESCRIPTION             "Distribution delay table entry."
    INDEX                   {dcgTxRxsectorId}
    ::= {foamDistributionDelayTable 1}

FoamDistributionDelayEntry ::= SEQUENCE {
    foamDistDelaySectorId       INTEGER,
    foamForwardDisDelay         INTEGER,
    foamReverseDisDelay         INTEGER
}

foamDistDelaySectorId   OBJECT-TYPE
    SYNTAX              INTEGER
    MAX-ACCESS          read-only
    STATUS              current
    DESCRIPTION         "Sector Id."
    ::= {foamDistributionDelayEntry 1}

foamForwardDisDelay     OBJECT-TYPE
    SYNTAX              INTEGER (0..1024)
    UNITS               "1/8chip"
    MAX-ACCESS          read-only
    STATUS              current
    DESCRIPTION         "Forward distribution delay."
    ::= {foamDistributionDelayEntry 2}

foamReverseDisDelay     OBJECT-TYPE
    SYNTAX              INTEGER (0..1024)
    UNITS               "1/8chip"
    MAX-ACCESS          read-only
    STATUS              current
    DESCRIPTION         "Reverse distribution delay."
    ::= {foamDistributionDelayEntry 3}


foamCarrierInformation   OBJECT IDENTIFIER ::= {foamOam 5}

foamCarrierInfoCdmaFrequency    OBJECT-TYPE
    SYNTAX                      INTEGER (0..2047)
    MAX-ACCESS                  read-only
    STATUS                      current
    DESCRIPTION                 "CDMA frequency assignment."
    ::= {foamCarrierInformation 1}

foamCarrierInfoBandClass    OBJECT-TYPE
    SYNTAX                  INTEGER {
                                    mHz800(0),
                                    mHz1900(1),
                                    invalidOrUnknown(255)
                                    }
    MAX-ACCESS              read-only
    STATUS                  current
    DESCRIPTION             "Base Band frequency assigned to carrier."
    ::= {foamCarrierInformation 2}

foamForwardBasebandTimeslot OBJECT-TYPE
    SYNTAX                  INTEGER {
                                    timeslot1(0),
                                    timeslot2(1),
                                    invalidOrUnknown(255)
                                    }
    MAX-ACCESS              read-only
    STATUS                  current
    DESCRIPTION             "Timeslot within the format 1 baseband format in the forward
        direction."
    ::= {foamCarrierInformation 3}

foamReverseBasebandTimeslot OBJECT-TYPE
    SYNTAX                  INTEGER {
                                    timeslot1(0),
                                    timeslot2(1),
                                    timeslot3(2),
                                    invalidOrUnknown(255)
                                    }
    MAX-ACCESS              read-only
    STATUS                  current
    DESCRIPTION             "Timeslot within the format 1 baseband format in the reverse
        direction."
    ::= {foamCarrierInformation 4}

foamBtsInformation   OBJECT IDENTIFIER ::= {foamOam 6}

foamBtsIdTable          OBJECT-TYPE
    SYNTAX              SEQUENCE OF FoamBtsIdEntry
    MAX-ACCESS          not-accessible
    STATUS              current
    DESCRIPTION         "Bts information table."
    ::= {foamBtsInformation 1}

foamBtsIdEntry          OBJECT-TYPE
    SYNTAX              FoamBtsIdEntry
    MAX-ACCESS          not-accessible
    STATUS              current
    DESCRIPTION         "Bts information table entry."
    INDEX               {btsIdSectorId}
    ::= {foamBtsIdTable 1}

FoamBtsIdEntry ::= SEQUENCE {
    foamBbtsIdSectorId  INTEGER,
    foamBtsSid          DisplayString,
    foamBtsNid          DisplayString,
    foamBtsBscId        DisplayString
}

foamBbtsIdSectorId  OBJECT-TYPE
    SYNTAX          INTEGER
    MAX-ACCESS      read-only
    STATUS          current
    DESCRIPTION     "Sector ID."
    ::= {foamBtsIdEntry 1}

foamBtsSid          OBJECT-TYPE
    SYNTAX          DisplayString 
    MAX-ACCESS      read-only
    STATUS          current
    DESCRIPTION     "Basestation system identifier."
    ::= {foamBtsIdEntry 2}

foamBtsNid          OBJECT-TYPE
    SYNTAX          DisplayString
    MAX-ACCESS      read-only
    STATUS          current
    DESCRIPTION     "Basestation network identifier."
    ::= {foamBtsIdEntry 3}

foamBtsBscId        OBJECT-TYPE
    SYNTAX          DisplayString
    MAX-ACCESS      read-only
    STATUS          current
    DESCRIPTION     "Basestation BSC identifier."
    ::= {foamBtsIdEntry 4}
    

foamResetReason     OBJECT-TYPE
    SYNTAX          INTEGER {
                            dcgReset(1),
                            mainbtenanceFromCraftperson(2),
                            faultDetectedByDCG(3),
                            spuriousReset(4),
                            foamHsspcLinkFailed(5),
                            dcgSWACT(6),
                            invalidOrUnknown(255)
                            }
    MAX-ACCESS      read-only
    STATUS          current
    DESCRIPTION     "Reset reason from DCG."
    ::= {foamOam 7}


END
