HTTPEXT-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, IpAddress, Integer32
			FROM SNMPv2-SMI
		RowStatus, DisplayString
			FROM SNMPv2-TC
		httpExt
			FROM APENT-MIB;


    httpExtMib MODULE-IDENTITY
	   LAST-UPDATED "9801282000Z" -- Wed January 28 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for HTTP transfer administration records"
      ::= { httpExt 1}


apHttpTable OBJECT-TYPE
	SYNTAX      SEQUENCE OF ApHttpEntry
	MAX-ACCESS  not-accessible
	STATUS      current
	DESCRIPTION
		"A table of HTTP administrative records"
	::= {httpExt 2}

apHttpEntry OBJECT-TYPE
	SYNTAX      ApHttpEntry
	MAX-ACCESS  not-accessible
	STATUS      current
	DESCRIPTION
	       "ArrowPoint HTTP record"
	INDEX  { apHttpRecordName}
	::= {apHttpTable 1}

ApHttpEntry ::=
	SEQUENCE 
	{
	apHttpRecordName			DisplayString,
	apHttpIpAddress				IpAddress,
	apHttpPort                  Integer32,
	apHttpUserName				DisplayString,
	apHttpPassword				DisplayString,
	apHttpEncryptedPassword		DisplayString,
	apHttpBaseDirectory			DisplayString,
	apHttpStatus				RowStatus
	}

apHttpRecordName OBJECT-TYPE
	SYNTAX      DisplayString(SIZE (0..16))
	MAX-ACCESS  read-create
	STATUS      current
	DESCRIPTION
	       "A name which uniquely identifies this record"
	::= {apHttpEntry 1}

apHttpIpAddress OBJECT-TYPE
	SYNTAX      IpAddress
	MAX-ACCESS  read-create
	STATUS      current
	DESCRIPTION
	       "This IP Address of the HTTP server"
	::= {apHttpEntry 2}

apHttpPort OBJECT-TYPE
	SYNTAX      Integer32
	MAX-ACCESS  read-create
	STATUS      current
	DESCRIPTION
	       "This port of the HTTP server"
	::= {apHttpEntry 3}

apHttpUserName OBJECT-TYPE
	SYNTAX      DisplayString(SIZE (0..16))
	MAX-ACCESS  read-create
	STATUS      current
	DESCRIPTION
	       "A username used for login puposes with this HTTP record"
	::= {apHttpEntry 4}

apHttpPassword OBJECT-TYPE
	SYNTAX      DisplayString(SIZE (0..16))
	MAX-ACCESS  read-create
	STATUS      current
	DESCRIPTION
	       "A password used for login purposes with this HTTP record"
	::= {apHttpEntry 5}

apHttpEncryptedPassword OBJECT-TYPE
	SYNTAX      DisplayString(SIZE (0..64))
	MAX-ACCESS  read-create
	STATUS      current
	DESCRIPTION
	       "An encrypted password used for login purposes with this HTTP 
			record"
	::= {apHttpEntry 6}

apHttpBaseDirectory OBJECT-TYPE
	SYNTAX      DisplayString(SIZE (0..64))
	MAX-ACCESS  read-create
	STATUS      current
	DESCRIPTION
	       "A base directory which is used for all access to this HTTP daemon"
	::= {apHttpEntry 7}

apHttpStatus OBJECT-TYPE
	SYNTAX      RowStatus
	MAX-ACCESS  read-create
	STATUS      current
	DESCRIPTION
	       "This status object for this row"
	::= {apHttpEntry 8}

END
