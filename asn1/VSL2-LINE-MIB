-- extracted from draft-ietf-adslmib-vdsl2-00.txt
-- at Tue Feb  7 06:15:01 2006

   VSL2-LINE-MIB DEFINITIONS ::= BEGIN


   IMPORTS
      MODULE-IDENTITY,
      OBJECT-TYPE,
      transmission,
      Unsigned32,
      NOTIFICATION-TYPE,
      Integer32,
      Counter32
         FROM SNMPv2-SMI

      ifIndex
         FROM IF-MIB

      TruthValue,
      RowStatus
          FROM SNMPv2-TC

      SnmpAdminString
         FROM SNMP-FRAMEWORK-MIB

      HCPerfIntervalThreshold,
      HCPerfTimeElapsed
         FROM  HC-PerfHist-TC-MIB   -- [RFC3705]

      Xdsl2Unit,
      Xdsl2Direction,
      Xdsl2TransmissionModeType,
      Xdsl2RaMode,
      Xdsl2InitResult,
      Xdsl2OperationModes,
      Xdsl2PowerMngState,
      Xdsl2ConfPmsForce,
      Xdsl2LConfProfPmMode,
      Xdsl2LineLdsf,
      Xdsl2LdsfResult,
      Xdsl2SymbolProtection,
      Xdsl2MaxBer,
      Xdsl2ScMaskDs,
      Xdsl2ScMaskUs,
      Xdsl2RfiDs,
      Xdsl2PsdMaskDs,
      Xdsl2PsdMaskUs,
      Xdsl2Tssi,
      Xdsl2LastTransmittedState,
      Xdsl2LineStatus,
      Xdsl2ChAtmStatus,
      Xdsl2ChPtmStatus
             FROM   VSL2-LINE-TC-MIB        -- [This document]

      MODULE-COMPLIANCE,
      OBJECT-GROUP,
      NOTIFICATION-GROUP
         FROM SNMPv2-CONF;

   vsl2MIB MODULE-IDENTITY
      LAST-UPDATED "200601220000Z" -- January 22, 2006
      ORGANIZATION "ADSLMIB Working Group"
      CONTACT-INFO "WG-email:  adslmib@ietf.org
      Info:      https://www1.ietf.org/mailman/listinfo/adslmib


                Chair:     Mike Sneed
                           Sand Channel Systems
                Postal:    P.O. Box 37324
                           Raleigh NC 27627-732
                Email:     sneedmike@hotmail.com
                Phone:     +1 206 600 7022

                Co-Chair:  Menachem Dodge
                           ECI Telecom Ltd.
                Postal:    30 Hasivim St.
                           Petach Tikva 49517,
                           Israel.
                Email:     mbdodge@ieee.org
                Phone:     +972 3 926 8421

                Co-editor: Moti Morgenstern
                           ECI Telecom Ltd.
                Postal:    30 Hasivim St.
                           Petach Tikva 49517,
                           Israel.
                Email:     moti.morgenstern@ecitele.com
                Phone:     +972 3 926 6258

                Co-editor: Scott Baillie
                           NEC Australia
                Postal:    649-655 Springvale Road,
                           Mulgrave, Victoria 3170,
                           Australia.
                Email:     scott.baillie@nec.com.au
                Phone:     +61 3 9264 3986

                Co-editor: Umberto Bonollo
                           NEC Australia
                Postal:    649-655 Springvale Road,
                           Mulgrave, Victoria 3170,
                           Australia.
                Email:     umberto.bonollo@nec.com.au
                Phone:     +61 3 9264 3385
               "
      DESCRIPTION
           "
            This document defines a Management Information Base (MIB)
            module for use with network management protocols in the
            Internet community for the purpose of managing VDSL2, ADSL,
            ADSL2, and ADSL2+ lines.

            The MIB module described in RFC 2662 [RFC2662] defines
            objects used for managing Asymmetric Bit-Rate DSL (ADSL)
            interfaces per [T1E1.413], [G.992.1], and [G.992.2].
            These object descriptions are based upon the specifications
            for the ADSL Embedded Operations Channel (EOC) as defined
            in American National Standards Institute (ANSI) T1E1.413
            [T1E1.413] and International Telecommunication Union (ITU-T)
            G.992.1 [G.992.1] and G.992.2 [G.992.2].

            The MIB module described in RFC xxxx [RFCxxx] defines
            objects used for managing ADSL2 interfaces per [G.992.3]
            and [G.992.4], and ADSL2+ interfaces per [g.992.5]. That MIB
            is also capable of managing ADSL interfaces per [T1E1.413],
            [G.992.1], and [G.992.2].

            This document does not obsolete RFC 2662 [RFC2662] and
            RFCxxxx [RFCxxxx], but rather provides a more comprehensive
            management model that manages VDSL2 interfaces per G.993.2
            [G.993.2] as well as ADSL, ADSL2 and ADSL2+ technologies
            per T1E1.413, G.992.1, G.992.2, G.992.3, G.992.4, and
            G.992.5
            ([T1E1.413], [G.992.1], [G.992.2], [G.992.3], [G.992.4], and
            [G.992.5] respectively).

           Additionally, the management framework for VDSL2 lines
           specified by the Digital Subscriber Line Forum
           (DSLF) has been taken into consideration [TR-129].  That
           framework is based on ITU-T G.997.1 standard [G.997.1].

           The MIB module is located in the MIB tree under MIB 2
           transmission, as discussed in the MIB-2 Integration (RFC 2863
           [RFC2863]) section of this document.

           Copyright (C) The Internet Society (2006).  This version of
           this MIB module is part of RFC XXXX: see the RFC itself for
           full legal notices."

   -- RFC Ed.: replace XXXX with assigned number & remove this note
      REVISION "200601220000Z" --     January 22, 2006
      DESCRIPTION "Initial version, published as RFC XXXX."
   -- RFC Ed.: replace XXXX with assigned number & remove this note
         ::= { transmission xxx }
   -- IANA, we suggest to put it under { transmission xxx } because
   --          this is the first available number.
   -- RFC Ed.: Please fill in xxx once assigned by IANA.


     vdsl2            OBJECT IDENTIFIER ::= { vdsl2MIB 1 }
     ------------------------------------------------
     xdsl2Line          OBJECT IDENTIFIER ::= { vdsl2 1 }
     xdsl2Status        OBJECT IDENTIFIER ::= { vdsl2 2 }
     xdsl2Inventory     OBJECT IDENTIFIER ::= { vdsl2 3 }
     xdsl2PM            OBJECT IDENTIFIER ::= { vdsl2 4 }
     xdsl2Profile       OBJECT IDENTIFIER ::= { vdsl2 5 }
     xdsl2Scalar        OBJECT IDENTIFIER ::= { vdsl2 6 }
     xdsl2Notifications OBJECT IDENTIFIER ::= { vdsl2 0 }
     xdsl2Conformance   OBJECT IDENTIFIER ::= { vdsl2 8 }
     ------------------------------------------------
     xdsl2PMLine      OBJECT IDENTIFIER ::= { xdsl2PM 1 }
     xdsl2PMChannel   OBJECT IDENTIFIER ::= { xdsl2PM 2 }
     ------------------------------------------------
     xdsl2ProfileLine      OBJECT IDENTIFIER ::= { xdsl2Profile 1 }
     xdsl2ProfileChannel   OBJECT IDENTIFIER ::= { xdsl2Profile 2 }
     xdsl2ProfileAlarmConf OBJECT IDENTIFIER ::= { xdsl2Profile 3 }
     ------------------------------------------------
     xdsl2ScalarSC         OBJECT IDENTIFIER ::= { xdsl2Scalar 1 }
     ------------------------------------------------

   ------*****************************************************
   ----- Should revise all references in this MIB
   ------*****************************************************

   ------------------------------------------------
   --          xdsl2LineTable                    --
   ------------------------------------------------
   xdsl2LineTable  OBJECT-TYPE
      SYNTAX      SEQUENCE  OF  Xdsl2LineEntry
      MAX-ACCESS  not-accessible
      STATUS      current
      DESCRIPTION
         "The table adsl2LineTable contains configuration,
          command and status parameters of the VDSL2/ADSL/ADSL2
          or ADSL2+ line.
          The index of this table is an interface index where the
          interface has an ifType of vdsl2(xxx).

          Several objects in this table MUST be maintained in a
          persistent manner. "
      ::= { xdsl2Line 1 }

   xdsl2LineEntry  OBJECT-TYPE
      SYNTAX      Adsl2LineEntry
      MAX-ACCESS  not-accessible
      STATUS      current
      DESCRIPTION
         "The table xdsl2LineTable contains configuration,
         commands and status parameters of the VDSL2/ADSL/ADSL2
         or ADSL2+ line."
      INDEX  { ifIndex }
      ::= { xdsl2LineTable 1 }

   Xdsl2LineEntry  ::=
      SEQUENCE {
         xdsl2LineCnfgTemplate            SnmpAdminString,
         xdsl2LineAlarmCnfgTemplate       SnmpAdminString,
         xdsl2LineCmndConfPmsf            Xdsl2ConfPmsForce,
         xdsl2LineCmndConfLdsf            Xdsl2LineLdsf,
         xdsl2LineCmndConfLdsfFailReason  Xdsl2LdsfResult,
         xdsl2LineCmndAutomodeColdStart   TruthValue,
         xdsl2LineStatusXtuTransSys       Xdsl2TransmissionModeType,
         xdsl2LineStatusPwrMngState       Xdsl2PowerMngState,
         xdsl2LineStatusInitResult        Xdsl2InitResult,
         xdsl2LineStatusLastStateDs       Xdsl2LastTransmittedState,
         xdsl2LineStatusLastStateUs       Xdsl2LastTransmittedState,
         xdsl2LineStatusXtur              Xdsl2LineStatus,
         xdsl2LineStatusXtuc              Xdsl2LineStatus,
         xdsl2LineStatusLnAttenDs         Unsigned32,
         xdsl2LineStatusLnAttenUs         Unsigned32,
         xdsl2LineStatusSigAttenDs        Unsigned32,
         xdsl2LineStatusSigAttenUs        Unsigned32,
         xdsl2LineStatusSnrMarginDs       Integer32,
         xdsl2LineStatusSnrMarginUs       Integer32,
         xdsl2LineStatusAttainableRateDs  Unsigned32,
         xdsl2LineStatusAttainableRateUs  Unsigned32,
         xdsl2LineStatusActPsdDs          Integer32,
         xdsl2LineStatusActPsdUs          Integer32,
         xdsl2LineStatusActAtpDs          Integer32,
         xdsl2LineStatusActAtpUs          Integer32
      }

   xdsl2LineCnfgTemplate  OBJECT-TYPE
      SYNTAX      SnmpAdminString (SIZE(1..32))
      MAX-ACCESS  read-write
      STATUS      current
      DESCRIPTION
         "The value of this object identifies the row in the xDSL2 Line
          Configuration Templates Table, (xdsl2LineConfTemplateTable),
          which applies for this line.

          This object MUST be maintained in a persistent manner."
      REFERENCE    "DSL Forum TR-129, paragraph 5.1.1"
      DEFVAL       { "DEFVAL" }
      ::= { xdsl2LineEntry 1 }

   xdsl2LineAlarmCnfgTemplate  OBJECT-TYPE
      SYNTAX      SnmpAdminString (SIZE(1..32))
      MAX-ACCESS  read-write
      STATUS      current
      DESCRIPTION
         "The value of this object identifies the row in the xDSL2 Line
         Alarm Configuration Template Table,
         (xdsl2LineAlarmConfTemplateTable), which applies to this line.

         This object MUST be maintained in a persistent manner."
      REFERENCE    "DSL Forum TR-129, paragraph 5.1.1"
      DEFVAL       { "DEFVAL" }
      ::= { xdsl2LineEntry 2 }

   xdsl2LineCmndConfPmsf  OBJECT-TYPE
      SYNTAX      Xdsl2ConfPmsForce
      MAX-ACCESS  read-write
      STATUS      current
      DESCRIPTION
         "Power management state forced.  Defines the line states to be
          forced by the near-end xTU on this line.  The various possible
          values are:
             l3toL0 (0),
             l0toL2 (2),
             l0orL2toL3 (3).

          This object MUST be maintained in a persistent manner."
      REFERENCE    "ITU-T G.997.1, paragraph 7.3.1.1.3"
      DEFVAL       { l3toL0 }
      ::= { xdsl2LineEntry 3 }

   xdsl2LineCmndConfLdsf  OBJECT-TYPE
      SYNTAX      Xdsl2LineLdsf
      MAX-ACCESS  read-write
      STATUS      current
      DESCRIPTION
         "Loop diagnostics mode forced (LDSF).  Defines whether the line
          should be forced into the loop diagnostics mode by the
          near-end xTU on this line or only be responsive to loop
          diagnostics initiated by the far-end xTU.

          This object MUST be maintained in a persistent manner.
          However, in case the operator forces loop diagnostics mode
          then the access node should reset the object (inhibit) when
          loop diagnostics mode procedures are completed."
      REFERENCE    "ITU-T G.997.1, paragraph 7.3.1.1.8"
      DEFVAL       { inhibit }
      ::= { xdsl2LineEntry 4 }

   xdsl2LineCmndConfLdsfFailReason  OBJECT-TYPE
      SYNTAX      Xdsl2LdsfResult
      MAX-ACCESS  read-only
      STATUS      current
      DESCRIPTION
         "The status of the recent occasion the Loop diagnostics mode
          forced (LDSF) was issued for the associated line.  Possible
          values are:
             none        (1) - The default value in case LDSF was never
                               requested for the associated line.
             success     (2) - The recent command completed
                               successfully.
             inProgress  (3) - The Loop Diagnostics process is in
                               progress.
             unsupported (4) - The NE or the line card doesn't support
                               LDSF.
             cannotRun   (5) - The NE cannot initiate the command, due
                               to a non specific reason.
             aborted     (6) - The Loop Diagnostics process aborted.
             failed      (7) - The Loop Diagnostics process failed.
             illegalMode (8) - The NE cannot initiate the command, due
                               to the specific mode of the relevant
                               line.
             adminUp     (9) - The NE cannot initiate the command, as
                               the relevant line is administratively
                               'Up'.
             tableFull   (10)- The NE cannot initiate the command, due
                               to reaching the maximum number of rows
                               in the results table.
             noResources (11)- The NE cannot initiate the command, due
                               to lack of internal memory resources."
      DEFVAL       { none }
      ::= { xdsl2LineEntry 5 }

      xdsl2LineCmndAutomodeColdStart   OBJECT-TYPE
         SYNTAX      TruthValue
         MAX-ACCESS  read-write
         STATUS      current
         DESCRIPTION
            "Automode cold start forced.  This parameter is defined
             in order to improve testing of the performance of xTUs
             supporting automode when it is enabled in the MIB.
             Change the value of this parameter to 'true' indicates
             a change in loop conditions applied to the devices under
             test.  The xTUs shall reset any historical information
             used for automode and for shortening G.994.1 handshake
             and initialization.

             Automode is the case where multiple operation-modes are
             enabled through the xdsl2LConfProfAtuTransSysEna object
             in the line configuration profile being used for the
             line, and where the selection of the actual
             operation-mode depends not only on the common
             capabilities of both xTUs (as exchanged in G.994.1), but
             also on achievable data rates under given loop
             conditions.

             This object MUST be maintained in a persistent manner."

         REFERENCE    "ITU-T G.997.1, paragraph 7.3.1.1.10"
         DEFVAL       { false }
         ::= { xdsl2LineEntry 6 }


   xdsl2LineStatusAtuTransSys  OBJECT-TYPE
      SYNTAX      Xdsl2TransmissionModeType
      MAX-ACCESS  read-only
      STATUS      current
      DESCRIPTION
         "The xTU Transmission System (xTS) in use.
          It is coded in a bit-map representation with one bit set to
          '1' (the selected coding for the DSL line).  This parameter
          may be derived from the handshaking procedures defined in
          Recommendation G.994.1.  A set of xDSL line transmission
          modes, with one bit per mode.  "
      REFERENCE    "ITU-T G.997.1, paragraph 7.3.1.1.1"
      ::= { xdsl2LineEntry 7 }

   xdsl2LineStatusPwrMngState  OBJECT-TYPE
      SYNTAX      Xdsl2PowerMngState
      MAX-ACCESS  read-only
      STATUS      current
      DESCRIPTION
         "The current power management state.  One of four possible
          power management states:
             L0 - Synchronized and full transmission (i.e., Showtime),
             L1 - Low Power with reduced net data rate (G.992.2 only),
             L2 - Low Power with reduced net data rate (G.992.3 and
                  G.992.4 only),
             L3 - No power
         The various possible values are:l0(1), l1(2), l2(3), l3(4)."
      REFERENCE    "ITU-T G.997.1, paragraph 7.5.1.2"
         ::= { xdsl2LineEntry 8 }

   xdsl2LineStatusInitResult  OBJECT-TYPE
      SYNTAX      Xdsl2InitResult
      MAX-ACCESS  read-only
      STATUS      current
      DESCRIPTION
         "Indicates the result of the last full initialization performed
          on the line.  It is an enumeration type with the following
          values: noFailure(0), configError(1), configNotFeasible(2),
          commFail(3), noPeerAtu(4), otherCause(5)."
      REFERENCE    "ITU-T G.997.1, paragraph 7.5.1.3"
      ::= { xdsl2LineEntry 9 }

   xdsl2LineStatusLastStateDs  OBJECT-TYPE
      SYNTAX      Xdsl2LastTransmittedState
      MAX-ACCESS  read-only
      STATUS      current
      DESCRIPTION
         "The last successful transmitted initialization state in
          the downstream direction in the last full initialization
          performed on the line."
      REFERENCE    "ITU-T G.997.1, paragraph 7.5.1.4"
      ::= { xdsl2LineEntry 10 }

   xdsl2LineStatusLastStateUs  OBJECT-TYPE
      SYNTAX      Xdsl2LastTransmittedState
      MAX-ACCESS  read-only
      STATUS      current
      DESCRIPTION
         "The last successful transmitted initialization state in the
          upstream direction in the last full initialization performed
          on the line."
      REFERENCE    "ITU-T G.997.1, paragraph 7.5.1.5"
      ::= { xdsl2LineEntry 11 }

   xdsl2LineStatusXtur  OBJECT-TYPE
      SYNTAX      Xdsl2LineStatus
      MAX-ACCESS  read-only
      STATUS      current
      DESCRIPTION
         "Indicates current state (existing failures) of the xTU-R.
          This is a bit-map of possible conditions. "
      REFERENCE    "ITU-T G.997.1, paragraph 7.1.1.2"
      ::= { xdsl2LineEntry 12 }

   xdsl2LineStatusXtuc  OBJECT-TYPE
      SYNTAX      Xdsl2LineStatus
      MAX-ACCESS  read-only
      STATUS      current
      DESCRIPTION
         "Indicates current state (existing failures) of the xTU-C.
          This is a bit-map of possible conditions. "
      REFERENCE    "ITU-T G.997.1, paragraph 7.1.1.1"
      ::= { xdsl2LineEntry 13 }

   xdsl2LineStatusLnAttenDs  OBJECT-TYPE
      SYNTAX      Unsigned32
      UNITS       "0.1 dB"
      MAX-ACCESS  read-only
      STATUS      current
      DESCRIPTION
         "The measured difference in the total power transmitted by the
          xTU-C and the total power received by the xTU-R over all sub-
          carriers during diagnostics mode and initialization.  It
          ranges from 0 to 1270 units of 0.1 dB (Physical values
          are 0 to 127 dB).  A value of all 1's indicates the line
          attenuation is out of range to be represented."
      REFERENCE    "ITU-T G.997.1, paragraph 7.5.1.6"
      ::= { xdsl2LineEntry 14 }

   xdsl2LineStatusLnAttenUs  OBJECT-TYPE
      SYNTAX      Unsigned32
      UNITS       "0.1 dB"
      MAX-ACCESS  read-only
      STATUS      current
      DESCRIPTION
         "The measured difference in the total power transmitted by the
          xTU-R and the total power received by the xTU-C over all sub-
          carriers during diagnostics mode and initialization.
          It ranges from 0 to 1270 units of 0.1 dB (Physical values are
          0 to 127 dB).  A value of all 1's indicates the line
          attenuation is out of range to be represented."
      REFERENCE    "ITU-T G.997.1, paragraph 7.5.1.7"
      ::= { xdsl2LineEntry 15 }

   xdsl2LineStatusSigAttenDs  OBJECT-TYPE
      SYNTAX      Unsigned32
      UNITS       "0.1 dB"
      MAX-ACCESS  read-only
      STATUS      current
      DESCRIPTION
         "The measured difference in the total power transmitted by the
          xTU-C and the total power received by the xTU-R over all sub-
          carriers during Showtime.  It ranges from 0 to 1270 units of
          0.1 dB (Physical values are 0 to 127 dB).  A value of all
          1's indicates the line attenuation is out of range to be
          represented."
      REFERENCE    "ITU-T G.997.1, paragraph 7.5.1.8"
      ::= { xdsl2LineEntry 16 }

   xdsl2LineStatusSigAttenUs  OBJECT-TYPE
      SYNTAX      Unsigned32
      UNITS       "0.1 dB"
      MAX-ACCESS  read-only
      STATUS      current
      DESCRIPTION
         "The measured difference in the total power transmitted by the
          xTU-R and the total power received by the xTU-C over all sub-
          carriers during Showtime.  It ranges from 0 to 1270 units of
          0.1 dB (Physical values are 0 to 127 dB).  A value of all
          1's indicates the line attenuation is out of range to be
          represented."

      REFERENCE    "ITU-T G.997.1, paragraph 7.5.1.9"
      ::= { xdsl2LineEntry 17 }

   xdsl2LineStatusSnrMarginDs  OBJECT-TYPE
      SYNTAX      Integer32
      UNITS       "0.1 dB"
      MAX-ACCESS  read-only
      STATUS      current
      DESCRIPTION
         "Downstream SNR Margin is the maximum increase in dB of the
          noise power received at the xTU-R, such that the BER
          requirements are met for all downstream bearer channels.  It
          ranges from -640 to 630 units of 0.1 dB (Physical values are
          -64 to 63 dB).  A value of all 1's indicates the line
          attenuation is out of range to be represented."
      REFERENCE    "ITU-T G.997.1, paragraph 7.5.1.10"
      ::= { xdsl2LineEntry 18 }

   xdsl2LineStatusSnrMarginUs  OBJECT-TYPE
      SYNTAX      Integer32
      UNITS       "0.1 dB"
      MAX-ACCESS  read-only
      STATUS      current
      DESCRIPTION
         "Upstream SNR Margin is the maximum increase in dB of the noise
          power received at the xTU-C, such that the BER requirements
          are met for all downstream bearer channels.  It ranges from
          -640 to 630 units of 0.1 dB (Physical values are -64 to
          63 dB).  A value of all 1's indicates the line attenuation
          is out of range to be represented."
      REFERENCE    "ITU-T G.997.1, paragraph 7.5.1.11"
      ::= { xdsl2LineEntry 19 }

   xdsl2LineStatusAttainableRateDs  OBJECT-TYPE
      SYNTAX      Unsigned32
      UNITS       "bits/second"
      MAX-ACCESS  read-only
      STATUS      current
      DESCRIPTION
         "Maximum Attainable Data Rate Downstream.
          The maximum downstream net data rate currently attainable by
          the xTU-C transmitter and the xTU-R receiver, coded in bit/s."
      REFERENCE    "ITU-T G.997.1, paragraph 7.5.1.12"
      ::= { xdsl2LineEntry 20 }

   xdsl2LineStatusAttainableRateUs  OBJECT-TYPE
      SYNTAX      Unsigned32
      UNITS       "bits/second"
      MAX-ACCESS  read-only
      STATUS      current
      DESCRIPTION
         "Maximum Attainable Data Rate Upstream.
          The maximum upstream net data rate currently attainable by the
          xTU-R transmitter and the xTU-C receiver, coded in bit/s."
      REFERENCE    "ITU-T G.997.1, paragraph 7.5.1.13"
      ::= { xdsl2LineEntry 21 }

   xdsl2LineStatusActPsdDs OBJECT-TYPE
      SYNTAX      Integer32
      UNITS       "0.1 dB"
      MAX-ACCESS  read-only
      STATUS      current
      DESCRIPTION
         "Actual Power Spectrum Density (PSD) Downstream.  The average
          downstream transmit PSD over the sub-carriers used for
          downstream.  It ranges from -900 to 0 units of 0.1 dB
          (Physical values are -90 to 0 dBm/Hz).  A value of all 1's
          indicates the measurement is out of range to be represented."
      REFERENCE    "ITU-T G.997.1, paragraph 7.5.1.14"
      ::= { xdsl2LineEntry 22 }

   xdsl2LineStatusActPsdUs OBJECT-TYPE
      SYNTAX      Integer32
      UNITS       "0.1 dB"
      MAX-ACCESS  read-only
      STATUS      current
      DESCRIPTION
         "Actual Power Spectrum Density (PSD) Upstream.  The average
          upstream transmit PSD over the sub-carriers used for upstream.
          It ranges from -900 to 0 units of 0.1 dB (Physical values
          are -90 to 0 dBm/Hz).  A value of all 1's indicates the
          measurement is out of range to be represented."
      REFERENCE    "ITU-T G.997.1, paragraph 7.5.1.15"
      ::= { xdsl2LineEntry 23 }

   xdsl2LineStatusActAtpDs  OBJECT-TYPE
      SYNTAX      Integer32
      UNITS       "0.1 dB"
      MAX-ACCESS  read-only
      STATUS      current
      DESCRIPTION
         "Actual Aggregate Transmit Power Downstream.  The total amount
          of transmit power delivered by the xTU-C at the U-C reference
          point, at the instant of measurement.  It ranges from -310 to
          310 units of 0.1 dB (Physical values are -31 to 31 dBm).  A
          value of all 1's indicates the measurement is out of range to
          be represented."
      REFERENCE    "ITU-T G.997.1, paragraph 7.5.1.16"
      ::= { xdsl2LineEntry 24 }

   xdsl2LineStatusActAtpUs  OBJECT-TYPE
      SYNTAX      Integer32
      UNITS       "0.1 dB"
      MAX-ACCESS  read-only
      STATUS      current
      DESCRIPTION
         "Actual Aggregate Transmit Power Upstream.  The total amount of
          transmit power delivered by the xTU-R at the U-R
          reference point, at the instant of measurement.  It ranges
          from -310 to 310 units of 0.1 dB (Physical values are -31
          to 31 dBm).  A value of all 1's indicates the measurement
          is out of range to be represented."
      REFERENCE    "ITU-T G.997.1, paragraph 7.5.1.17"
      ::= { xdsl2LineEntry 25 }


   ------------------------------------------------
   --        xdsl2ChannelStatusTable             --
   ------------------------------------------------
   xdsl2ChannelStatusTable  OBJECT-TYPE
      SYNTAX      SEQUENCE  OF  Xdsl2ChannelStatusEntry
      MAX-ACCESS  not-accessible
      STATUS      current
      DESCRIPTION
         "The table xdsl2ChannelStatusTable contains status
          parameters of VDSL2/ADSL/ADSL2 or ADSL2+ channel.
          This table contains live data from equipment.  As such,
          it is NOT persistent."
      ::= { xdsl2Status 1 }

   xdsl2ChannelStatusEntry  OBJECT-TYPE
      SYNTAX      Xdsl2ChannelStatusEntry
      MAX-ACCESS  not-accessible
      STATUS      current
      DESCRIPTION
         "The table xdsl2ChannelStatusTable contains status
          parameters of VDSL2/ADSL/ADSL2 or ADSL2+ channel.
          The index of this table is an interface index where
          the interface has an ifType value that is applicable
          for a DSL channel and the termination unit."
      INDEX  { ifIndex, xdsl2ChStatusUnit }
      ::= { adsl2ChannelStatusTable 1 }

   Adsl2ChannelStatusEntry  ::=
      SEQUENCE {
         adsl2ChStatusUnit                Xdsl2Unit,
         xdsl2ChStatusChannelNum          Unsigned32,
         xdsl2ChStatusActDataRate         Unsigned32,
         xdsl2ChStatusPrevDataRate        Unsigned32,
         xdsl2ChStatusActDelay            Unsigned32,
         xdsl2ChStatusAtmStatus           Xdsl2ChAtmStatus,
         xdsl2ChStatusPtmStatus           Xdsl2ChPtmStatus
      }

   xdsl2ChStatusUnit  OBJECT-TYPE
      SYNTAX      Xdsl2Unit
      MAX-ACCESS  not-accessible
      STATUS      current
      DESCRIPTION
         "The termination unit xtuc(1) or xtur(2)."
      ::= { xdsl2ChannelStatusEntry 1 }

   xdsl2ChStatusChannelNum  OBJECT-TYPE
      SYNTAX      Unsigned32
      MAX-ACCESS  read-only
      STATUS      current
      DESCRIPTION
         "Provides the bearer channel number associated with this
          row (i.e., the channel ifIndex).
          This enables determining the channel configuration profile
          and the channel thresholds profile applicable for this
          bearer channel."
      ::= { xdsl2ChannelStatusEntry 2 }

   xdsl2ChStatusActDataRate  OBJECT-TYPE
      SYNTAX      Unsigned32(0..200000000)
      UNITS       "bits/second"
      MAX-ACCESS  read-only
      STATUS      current
      DESCRIPTION
         "The actual net data rate that the bearer channel is operating
          at, if in L0 power management state.  In L1 or L2 states, it
          relates to the previous L0 state.  The data rate is coded in
          bit/s."
      REFERENCE    "ITU-T G.997.1, paragraph 7.5.2.1"
      ::= { xdsl2ChannelStatusEntry 3 }

   xdsl2ChStatusPrevDataRate  OBJECT-TYPE
      SYNTAX      Unsigned32(0..200000000)
      UNITS       "bits/second"
      MAX-ACCESS  read-only
      STATUS      current
      DESCRIPTION
         "The previous net data rate that the bearer channel was
          operating at just before the latest rate change event.  This
          could be a full or short initialization, fast retrain, DRA or
          power management transitions, excluding transitions between L0
          state and L1 or L2 states.  The data rate is coded in bit/s."
      REFERENCE    "ITU-T G.997.1, paragraph 7.5.2.2"
      ::= { xdsl2ChannelStatusEntry 4 }

   xdsl2ChStatusActDelay  OBJECT-TYPE
      SYNTAX      Unsigned32(0..8176)
      UNITS       "milliseconds"
      MAX-ACCESS  read-only
      STATUS      current
      DESCRIPTION
         "The actual one-way interleaving delay introduced by the
          PMS-TC in the direction of the bearer channel, if in L0
          power management state.  In L1 or L2 states, it relates to
          the previous L0 state.  It is coded in ms (rounded to the
          nearest ms)."
      REFERENCE    "ITU-T G.997.1, paragraph 7.5.2.3"
      ::= { xdsl2ChannelStatusEntry 5 }

   xdsl2ChStatusAtmStatus  OBJECT-TYPE
      SYNTAX      Xdsl2ChAtmStatus
      MAX-ACCESS  read-only
      STATUS      current
      DESCRIPTION
         "Indicates current state (existing failures) of the DSL
          channel in case its Data Path is ATM.  This is a bit-map of
          possible conditions.  The various bit positions are:
             noFailure(0),
             noCellDelineation(1),
             lossOfCellDelineation (2).
         In case the channel is not of ATM Data Path the object is set
         to '0'."
      REFERENCE    "ITU-T G.997.1, paragraph 7.1.4"
      ::= { xdsl2ChannelStatusEntry 6 }

   xdsl2ChStatusPtmStatus  OBJECT-TYPE
      SYNTAX      Xdsl2ChPtmStatus
      MAX-ACCESS  read-only
      STATUS      current
      DESCRIPTION
         "Indicates current state (existing failures) of the DSL
          channel in case its Data Path is PTM.  This is a bit-map of
          possible conditions.  The various bit positions are:
             noFailure(0),
             outOfSync (1).
         In case the channel is not of PTM Data Path the object is set
         to '0'."
      REFERENCE    "ITU-T G.997.1, paragraph 7.1.5"
      ::= { xdsl2ChannelStatusEntry 7 }


   ------------------------------------------------
   --        Scalars that relate to the xdsl2SCStatusTable.
   ------------------------------------------------

   xdsl2ScalarSCMaxInterfaces  OBJECT-TYPE
      SYNTAX      Unsigned32
      MAX-ACCESS  read-only
      STATUS      current
      DESCRIPTION
         "This value determines the upper size of xdsl2SCStatusTable.
          The maximum number of entries in xdsl2SCStatusTable is equal
          to two times the value of this attribute."
      ::= { xdsl2ScalarSC 1 }

   xdsl2ScalarSCAvailInterfaces  OBJECT-TYPE
      SYNTAX      Unsigned32
      MAX-ACCESS  read-only
      STATUS      current
      DESCRIPTION
         "This value determines the amount of space that is
          currently available in xdsl2SCStatusTable.
          The number of entries available in xdsl2SCStatusTable is equal
          to two times the value of this attribute."
      ::= { xdsl2ScalarSC 2 }


   ------*****************************************************
   ----- Should revise The following table.
   ----- 1. There should be a reference to the SC groups
   ----- 2. We should solve the issue of too long data structures
   -----    caused by supporting 4096 sub-carriers.
   ------*****************************************************

   ------------------------------------------------
   --        xdsl2SCStatusTable                --
   ------------------------------------------------

   xdsl2SCStatusTable  OBJECT-TYPE
      SYNTAX      SEQUENCE  OF  Xdsl2SCStatusEntry
      MAX-ACCESS  not-accessible
      STATUS      current
      DESCRIPTION
         "The table xdsl2SCStatusTable contains status parameters
          of VDSL2/ADSL/ADSL2 and ADSL2+ sub-carriers.  This table
          contains live data from equipment.  As such, it is NOT
          persistent."
      ::= { xdsl2Status 2 }

   xdsl2SCStatusEntry  OBJECT-TYPE
      SYNTAX      Xdsl2SCStatusEntry
      MAX-ACCESS  not-accessible
      STATUS      current
      DESCRIPTION
         "The table Hfxdsl2SCStatusEntry contains status parameters
          of VDSL2/ADSL/ADSL2 and ADSL2+ sub-carriers.
          The index of this table is an interface index where the
          interface has an ifType of vdsl2(xxx)."
      INDEX  { ifIndex, xdsl2SCStatusDirection }
      ::= { xdsl2SCStatusTable 1 }

   Xdsl2SCStatusEntry  ::=
      SEQUENCE {
         xdsl2SCStatusDirection         Xdsl2Direction,
         xdsl2SCStatusMtime             Unsigned32,
         xdsl2SCStatusSnr               OCTET STRING,
         xdsl2SCStatusBitsAlloc         OCTET STRING,
         xdsl2SCStatusGainAlloc         OCTET STRING,
         xdsl2SCStatusTssi              Xdsl2Tssi,
         xdsl2SCStatusLinScale          Unsigned32,
         xdsl2SCStatusLinReal           OCTET STRING,
         xdsl2SCStatusLinImg            OCTET STRING,
         xdsl2SCStatusLogMt             Unsigned32,
         xdsl2SCStatusLog               OCTET STRING,
         xdsl2SCStatusQlnMt             Unsigned32,
         xdsl2SCStatusQln               OCTET STRING,
         xdsl2SCStatusLnAtten           Unsigned32,
         xdsl2SCStatusSigAtten          Unsigned32,
         xdsl2SCStatusSnrMargin         Integer32,
         xdsl2SCStatusAttainableRate    Unsigned32,
         xdsl2SCStatusActAtp            Integer32,
         xdsl2SCStatusRowStatus         RowStatus
      }

   xdsl2SCStatusDirection  OBJECT-TYPE
        SYNTAX      Xdsl2Direction
        MAX-ACCESS  not-accessible
        STATUS      current
        DESCRIPTION
        "The direction of the sub-carrier either
        upstream or downstream"
        ::= { xdsl2SCStatusEntry 1 }

   xdsl2SCStatusMtime  OBJECT-TYPE
        SYNTAX      Unsigned32
        UNITS       "symbols"
        MAX-ACCESS  read-only
        STATUS      current
        DESCRIPTION
        "SNR Measurement Time.  The number of symbols used to
         measure the SNR values on the respective transmission
         direction.  It should correspond to the value specified in the
         recommendation (e.g., the number of symbols in 1 second
         time interval for G.992.3).  This parameter corresponds to
         1 second in loop diagnostic procedure and should be updated
         otherwise"
      REFERENCE    "ITU-T G.997.1, paragraph 7.5.1.20.1 (SNRMTds)
                    and paragraph 7.5.1.20.3 (SNRMTus)"
        ::= { xdsl2SCStatusEntry 2 }

   xdsl2SCStatusSnr  OBJECT-TYPE
        SYNTAX      OCTET STRING  (SIZE(0..512))
        MAX-ACCESS  read-only
        STATUS      current
        DESCRIPTION
        "The SNR Margin per sub-carrier, expressing the ratio between
         the received signal power and received noise power per
         subscriber.  It is an array of 512 bytes, designed for
         supporting up to 512 (downstream) sub-carriers.
         The number of utilized octets on downstream direction depends
         on NSCds, and on upstream direction it depends on NSCus.  This
         value is referred here as NSC.
         Byte i (0 <= i < NSC) is set to a value in the range 0 to
         254 to indicate that the respective downstream or upstream sub-
         carrier i has SNR of: (-32 + Xdsl2SubcarrierSnr(i)/2) in dB
         (i.e., -32 to 95dB).
         The special value 255 means that no measurement could be done
         for the subcarrier because it is out of the PSD mask passband
         or that the noise PSD is out of range to be represented.
         Each value in this array is 8 bits wide."
      REFERENCE    "ITU-T G.997.1, paragraph 7.5.1.20.2 (SNRpsds)
                    and paragraph 7.5.1.20.4 (SNRpsus)"
        ::= { xdsl2SCStatusEntry 3 }

   xdsl2SCStatusBitsAlloc  OBJECT-TYPE
        SYNTAX      OCTET STRING  (SIZE(0..256))
        UNITS       "bits"
        MAX-ACCESS  read-only
        STATUS      current
        DESCRIPTION
        "The bits allocation per sub-carrier.  An array of 256 bytes
         (512 nibbles), designed for supporting up to 512 (downstream)
         sub-carriers.
         The number of utilized nibbles on downstream direction depends
         on NSCds, and on upstream direction it depends on NSCus.  This
         value is referred here as NSC.
         Nibble i (0 <= i < NSC) is set to a value in the range 0
         to 15 to indicate that the respective downstream or upstream
         sub-carrier i has the same amount of bits allocation."
      REFERENCE    "ITU-T G.997.1, paragraph 7.5.1.21.1 (BITSpsds)
                    and paragraph 7.5.1.21.2 (BITSpsus)"
        ::= { xdsl2SCStatusEntry 4 }

   xdsl2SCStatusGainAlloc  OBJECT-TYPE
        SYNTAX      OCTET STRING  (SIZE(0..1024))
        MAX-ACCESS  read-only
        STATUS      current
        DESCRIPTION
        "The gain allocation per sub-carrier.  An array of 512 16-bits
        values, designed for supporting up to 512 (downstream) sub-
        carriers.
        The number of utilized octets on downstream direction depends
        on NSCds, and on upstream direction it depends on NSCus.  This
        value is referred here as NSC.
        Value i (0 <= i < NSC) is in the range 0 to 4093 to indicate
        that the respective downstream or upstream sub-carrier i has the
        same amount of gain value.
        The gain value is represented as a multiple of 1/512 on
        linear scale.  Each value in this array is 16 bits wide and is
        stored in big endian format."
      REFERENCE    "ITU-T G.997.1, paragraph 7.5.1.21.3 (GAINSpsds)
                    and paragraph 7.5.1.21.4 (GAINSpsus)"
        ::= { xdsl2SCStatusEntry 5 }

   xdsl2SCStatusTssi  OBJECT-TYPE
        SYNTAX      Xdsl2Tssi
        MAX-ACCESS  read-only
        STATUS      current
        DESCRIPTION
        "The transmit spectrum shaping (TSSi) breakpoints expressed
        as the set of breakpoints exchanged during G.994.1.
        Each breakpoint is a pair of values occupying 3 octets with the
        following structure:
        First 2 octets - Index of the subcarrier used in the context of
                         the breakpoint.
        Third octet    - The shaping parameter at the breakpoint.
        Subcarrier index is an unsigned number in the range 1 to either
        NSCds (downstream direction) or NSCus (upstream direction).
        The shaping parameter value is in the range 0 to 127 (units of
        -0.5dB). The special value 127 indicates that the subcarrier
        is not transmitted."
      REFERENCE  "ITU-T G.997.1, paragraph 7.5.1.21.5 (TSSpsds)
                  and paragraph 7.5.1.21.6 (TSSpsus)"
        ::= { xdsl2SCStatusEntry 6 }

   xdsl2SCStatusLinScale  OBJECT-TYPE
        SYNTAX      Unsigned32
        MAX-ACCESS  read-only
        STATUS      current
        DESCRIPTION
        "The scale factor to be applied to the H(f) linear
        representation values for the respective transmission direction.
        This parameter is only available after a loop diagnostic
        procedure."
      REFERENCE  "ITU-T G.997.1, paragraph 7.5.1.18.1 (HLINSCds)
                  and paragraph 7.5.1.18.5 (HLINSCus)"
        ::= { xdsl2SCStatusEntry 7 }

   xdsl2SCStatusLinReal  OBJECT-TYPE
        SYNTAX      OCTET STRING  (SIZE(0..1024))
        MAX-ACCESS  read-only
        STATUS      current
        DESCRIPTION
        "An array of up to 512 complex H(f) linear representation
        values in linear scale for the respective transmission
        direction.  It is designed to support up to 512 (downstream)
        sub-carriers.
        The number of utilized values on downstream direction depends
        on NSCds, and on upstream direction it depends on NSCus.  This
        value is referred here as NSC.
        Each array entry represents the real component [referred here as
        a(i)] of Hlin(f = i*Df) value for a particular sub-carrier index
        i (0 <= i < NSC).
        Hlin(f) is represented as ((scale/2^15)*((a(i)+j*b(i))/2^15)),
        where scale is Xdsl2SubcarrierLinScale and a(i) and b(i)
        [provided by the Xdsl2SubcarrierLinImg object] are in the range
        (-2^15+1) to (+2^15-1).
        A special value a(i)=b(i)= -2^15 indicates that no measurement
        could be done for the subcarrier because it is out of the
        passband or that the attenuation is out of range to be
        represented.  This parameter is only available after a loop
        diagnostic procedure.
        Each value in this array is 16 bits wide and is stored in big
        endian format."

      REFERENCE  "ITU-T G.997.1, paragraph 7.5.1.18.2 (HLINpsds)
                  and paragraph 7.5.1.18.6 (HLINpsds)"
        ::= { xdsl2SCStatusEntry 8 }

   xdsl2SCStatusLinImg  OBJECT-TYPE
        SYNTAX      OCTET STRING  (SIZE(0..1024))
        MAX-ACCESS  read-only
        STATUS      current
        DESCRIPTION
        "An array of up to 512 complex H(f) linear representation
        values in linear scale for the respective transmission
        direction.  It is designed to support up to 512 (downstream)
        sub-carriers.
        The number of utilized values on downstream direction depends
        on NSCds, and on upstream direction it depends on NSCus.  This
        value is referred here as NSC.
        Each array entry represents the imaginary component [referred
        here as b(i)] of Hlin(f = i*Df) value for a particular sub-
        carrier index i (0 <= i < NSC).
        Hlin(f) is represented as ((scale/2^15)*((a(i)+j*b(i))/2^15)),
        where scale is Xdsl2SubcarrierLinScale and a(i) [provided by
        the Xdsl2SubcarrierLinReal object] and b(i) are in the range
        (-2^15+1) to (+2^15-1).
        A special value a(i)=b(i)= -2^15 indicates that no measurement
        could be done for the subcarrier because it is out of the
        passband or that the attenuation is out of range to be
        represented.  This parameter is only available after a loop
        diagnostic procedure.
        Each value in this array is 16 bits wide and is stored in big
        endian format."
      REFERENCE  "ITU-T G.997.1, paragraph 7.5.1.18.2 (HLINpsds)
                  and paragraph 7.5.1.18.6 (HLINpsds)"
        ::= { xdsl2SCStatusEntry 9 }

   xdsl2SCStatusLogMt  OBJECT-TYPE
        SYNTAX      Unsigned32
        MAX-ACCESS  read-only
        STATUS      current
        DESCRIPTION
        "The number of symbols used to measure the H(f) logarithmic
        measurement values for the respective transmission direction.
        This parameter should correspond to the value specified in the
        recommendation (e.g., the number of symbols in 1 second
        time interval for G.992.3).  This parameter corresponds to 1
        second in loop diagnostic procedure and should be updated in
        initialization"
      REFERENCE  "ITU-T G.997.1, paragraph 7.5.1.18.3 (HLOGMTds)
                  and paragraph 7.5.1.18.7 (HLOGMTus)"
        ::= { xdsl2SCStatusEntry 10 }

   xdsl2SCStatusLog  OBJECT-TYPE
        SYNTAX      OCTET STRING  (SIZE(0..1024))
        MAX-ACCESS  read-only
        STATUS      current
        DESCRIPTION
        "An array of up to 512 real H(f) logarithmic representation
         values in dB for the respective transmission direction.  It is
         designed to support up to 512 (downstream) sub-carriers
         The number of utilized values on downstream direction depends
         on NSCds, and on upstream direction it depends on NSCus.  This
         value is referred here as NSC.
         Each array entry represents the real Hlog(f = i*Df) value for a
         particular sub-carrier index i, (0 <= i < NSC).
         The real Hlog(f) value is represented as (6-m(i)/10), with m(i)
         in the range 0 to 1022.  A special value m=1023 indicates that
         no measurement could be done for the subcarrier because it is
         out of the passband or that the attenuation is out of range to
         be represented.  This parameter is applicable in loop
         diagnostic procedure and initialization.
         Each value in this array is 16 bits wide and is stored
         in big endian format."
      REFERENCE  "ITU-T G.997.1, paragraph 7.5.1.18.4 (HLOGpsds)
                  and paragraph 7.5.1.18.8 (HLOGpsus)"
        ::= { xdsl2SCStatusEntry 11 }

   xdsl2SCStatusQlnMt  OBJECT-TYPE
        SYNTAX      Unsigned32
        MAX-ACCESS  read-only
        STATUS      current
        DESCRIPTION
        "The number of symbols used to measure the Quiet Line Noise
         values on the respective transmission direction.   This
         parameter should correspond to the value specified in the
         recommendation (e.g., the number of symbols in 1 second time
         interval for G.992.3).  This parameter corresponds to 1 second
         in loop diagnostic procedure and should be updated in
         initialization "
      REFERENCE  "ITU-T G.997.1, paragraph 7.5.1.19.1 (QLNMTds)
                  and paragraph 7.5.1.19.3 (QLNMTus)"
        ::= { xdsl2SCStatusEntry 12 }

   xdsl2SCStatusQln  OBJECT-TYPE
        SYNTAX      OCTET STRING  (SIZE(0..512))
        UNITS       "dBm/Hz"
        MAX-ACCESS  read-only
        STATUS      current
        DESCRIPTION
        "An array of up to 512 real Quiet Line Noise values in dBm/Hz
        for the respective transmission direction.  It is designed for
        up to 512 (downstream) sub-carriers
        The number of utilized values on downstream direction depends
        on NSCds, and on upstream direction it depends on NSCus.  This
        value is referred here as NSC.
        Each array entry represents the QLN(f = i*Df) value for a
        particular sub-carrier index i, (0 <= i < NSC).
        The QLN(f) is represented as ( -23-n(i)/2), with n(i) in the
        range 0 to 254.  A special value n(i)=255 indicates that no
        measurement could be done for the subcarrier because it is out
        of the passband or that the noise PSD is out of range to be
        represented.
        This parameter is applicable in loop diagnostic procedure and
        initialization.  Each value in this array is 8 bits wide."
      REFERENCE  "ITU-T G.997.1, paragraph 7.5.1.19.2 (QLNpsds)
                  and paragraph 7.5.1.19.4 (QLNpsus)"
        ::= { xdsl2SCStatusEntry 13 }

   xdsl2SCStatusLnAtten  OBJECT-TYPE
      SYNTAX      Unsigned32
      UNITS       "0.1 dB"
      MAX-ACCESS  read-only
      STATUS      current
      DESCRIPTION
         "When referring to the downstream direction, it is the measured
          difference in the total power transmitted by the XTU-C and the
          total power received by the XTU-R over all sub-carriers during
          diagnostics mode.
          When referring to the upstream direction, it is the measured
          difference in the total power transmitted by the XTU-R and the
          total power received by the XTU-C over all sub-carriers during
          diagnostics mode.
          It ranges from 0 to 1270 units of 0.1 dB (Physical values are
          0 to 127 dB).  A value of all 1's indicates the line
          attenuation is out of range to be represented.
          This object reflects the value of the parameter following the
          most recent DELT performed on the associated line.  Once
          the DELT process is over, the parameter no longer changes
          until the row is deleted or a new DELT process is initiated. "
      REFERENCE  "ITU-T G.997.1, paragraph 7.5.1.6 (LATNds)
                  and paragraph 7.5.1.7 (LATNus)"
      ::= { xdsl2SCStatusEntry 14 }

   xdsl2SCStatusSigAtten  OBJECT-TYPE
      SYNTAX      Unsigned32
      UNITS       "0.1 dB"
      MAX-ACCESS  read-only
      STATUS      current
      DESCRIPTION
         "When referring to the downstream direction, it is the measured
          difference in the total power transmitted by the
          XTU-C and the total power received by the XTU-R over all sub
          carriers during Showtime after the diagnostics mode.
          When referring to the upstream direction, it is the measured
          difference in the total power transmitted by the
          XTU-R and the total power received by the XTU-C over all sub
          carriers during Showtime after the diagnostics mode.
          It ranges from 0 to 1270 units of 0.1 dB (Physical values
          are 0 to 127 dB).  A value of all 1's indicates the line
          attenuation is out of range to be represented.
          This object reflects the value of the parameter following the
          most recent DELT performed on the associated line.  Once
          the DELT process is over, the parameter no longer changes
          until the row is deleted or a new DELT process is initiated. "
      REFERENCE  "ITU-T G.997.1, paragraph 7.5.1.8 (SATNds)
                  and paragraph 7.5.1.9 (SATNus)"
      ::= { xdsl2SCStatusEntry 15 }

   xdsl2SCStatusSnrMargin  OBJECT-TYPE
      SYNTAX      Integer32
      UNITS       "0.1 dB"
      MAX-ACCESS  read-only
      STATUS      current
      DESCRIPTION
         "SNR Margin is the maximum increase in dB of the noise power
          received at the XTU (XTU-R on downstream direction and XATU-C
          on upstream direction), such that the BER requirements are met
          for all bearer channels received at the XTU.  It ranges from
          -640 to 630 units of 0.1 dB (Physical values are -64 to
          63 dB).  A value of all 1's indicates the SNR margin is
          out of range to be represented.
          This object reflects the value of the parameter following the
          most recent DELT performed on the associated line.  Once
          the DELT process is over, the parameter no longer changes
          until the row is deleted or a new DELT process is initiated. "
      REFERENCE  "ITU-T G.997.1, paragraph 7.5.1.10 (SNRMds)
                  and paragraph 7.5.1.11 (SNRMus)"
      ::= { xdsl2SCStatusEntry 16 }

   xdsl2SCStatusAttainableRate  OBJECT-TYPE
      SYNTAX      Unsigned32
      UNITS       "bits/second"
      MAX-ACCESS  read-only
      STATUS      current
      DESCRIPTION
         "Maximum Attainable Data Rate.  The maximum net data rate
          currently attainable by the XTU-C transmitter and XTU-R
          receiver (when referring to downstream direction) or by the
          XTU-R transmitter and XTU-C receiver (when referring to
          upstream direction).  Value is coded in bits/s.
          This object reflects the value of the parameter following the
          most recent DELT performed on the associated line.  Once
          the DELT process is over, the parameter no longer changes
          until the row is deleted or a new DELT process is initiated. "
      REFERENCE  "ITU-T G.997.1, paragraph 7.5.1.12 (ATTNDRds)
                  and paragraph 7.5.1.13 (ATTNDRus)"
      ::= { xdsl2SCStatusEntry 17 }

   xdsl2SCStatusActAtp  OBJECT-TYPE
      SYNTAX      Integer32
      UNITS       "0.1 dB"
      MAX-ACCESS  read-only
      STATUS      current
      DESCRIPTION
         "Actual Aggregate Transmit Power from the XTU (XTU-R on
          downstream direction and XTU-C on upstream direction), at the
          instant of measurement.  It ranges from -310 to 310 units of
          0.1 dB (Physical values are -31 to 31 dBm).  A value of all
          1's indicates the measurement is out of range to be
          represented.
          This object reflects the value of the parameter following the
          most recent DELT performed on the associated line.  Once
          the DELT process is over, the parameter no longer changes
          until the row is deleted or a new DELT process is initiated. "
      REFERENCE  "ITU-T G.997.1, paragraph 7.5.1.14 (ACTPSDds)
                  and paragraph 7.5.1.15 (ACTPSDus)"
      ::= { xdsl2SCStatusEntry 18 }

   xdsl2SCStatusRowStatus  OBJECT-TYPE
        SYNTAX      RowStatus
        MAX-ACCESS  read-write
        STATUS      current
        DESCRIPTION
        "Row Status.  The SNMP agent should create a row in this
         table for storing the results of a DELT performed on the
         associated line, if such a row does not already exist.
         The SNMP agent may have limited resources; therefore, if
         multiple rows co-exist in the table, it may fail to add
         new rows to the table or allocate memory resources for a new
         DELT process.  If that occurs, the SNMP agent responds with
         either the value 'tableFull' or the value
         'noResources' (for xdsl2LineCmndConfLdsfFailReason
         object in xdsl2LineTable)
         The management system (the operator) may delete rows according
         to any scheme.  E.g., after retrieving the results."
        ::= { xdsl2SCStatusEntry 19 }

   ------------------------------------------------
   --        xdsl2LineInventoryTable             --
   ------------------------------------------------
   xdsl2LineInventoryTable  OBJECT-TYPE
      SYNTAX      SEQUENCE  OF  Xdsl2LineInventoryEntry
      MAX-ACCESS  not-accessible
      STATUS      current
      DESCRIPTION
         "The table xdsl2LineInventoryTable contains inventory of DSL
          termination unit.
          The objects in this table are NOT persistent."
      ::= { xdsl2Inventory 1 }

   xdsl2LineInventoryEntry  OBJECT-TYPE
      SYNTAX      Xdsl2LineInventoryEntry
      MAX-ACCESS  not-accessible
      STATUS      current
      DESCRIPTION
         "The table xdsl2LineInventoryTable contains inventory of DSL
          termination unit.
          The index of this table is an interface index where the
          interface has an ifType of vdsl2(xxx)."
      INDEX  { ifIndex, xdsl2LInvUnit }
      ::= { xdsl2LineInventoryTable 1 }

   Xdsl2LineInventoryEntry  ::=
      SEQUENCE {
         xdsl2LInvUnit                      Xdsl2Unit,
         xdsl2LInvG994VendorId              OCTET STRING,
         xdsl2LInvSystemVendorId            OCTET STRING,
         xdsl2LInvVersionNumber             OCTET STRING,
         xdsl2LInvSerialNumber              OCTET STRING,
         xdsl2LInvSelfTestResult            OCTET STRING,
         xdsl2LInvTransmissionCapabilities  Xdsl2TransmissionModeType
      }

   xdsl2LInvUnit  OBJECT-TYPE
      SYNTAX      Xdsl2Unit
      MAX-ACCESS  not-accessible
      STATUS      current
      DESCRIPTION
         "The termination unit xtuc{1} or xtur{2}."
      ::= { xdsl2LineInventoryEntry 1 }

   xdsl2LInvG994VendorId  OBJECT-TYPE
      SYNTAX      OCTET STRING  (SIZE(0..8))
      MAX-ACCESS  read-only
      STATUS      current
      DESCRIPTION
         "The ATU G.994.1 Vendor ID as inserted in the G.994.1 CL/CLR
          message.  It consists of 8 binary octets, including a country
          code followed by a (regionally allocated) provider code, as
          defined in Recommendation T.35."
      REFERENCE    "ITU-T G.997.1, paragraph 7.4"
      ::= { xdsl2LineInventoryEntry 2 }

   xdsl2LInvSystemVendorId  OBJECT-TYPE
      SYNTAX      OCTET STRING  (SIZE(0..8))
      MAX-ACCESS  read-only
      STATUS      current
      DESCRIPTION
         "The ATU System Vendor ID (identifies the XTU system
          integrator) as inserted in the Overhead Messages (both XTUs
          for G.992.3 and G.992.4) or in the Embedded Operations
          Channel (only XTU-R in G.992.1 and G.992.2).  It consists of
          8 binary octets, with same format as used for
          Xdsl2InvG994VendorId."
      REFERENCE    "ITU-T G.997.1, paragraph 7.4"
      ::= { xdsl2LineInventoryEntry 3 }

   xdsl2LInvVersionNumber  OBJECT-TYPE
      SYNTAX      OCTET STRING  (SIZE(0..16))
      MAX-ACCESS  read-only
      STATUS      current
      DESCRIPTION
         "The XTU version number (vendor specific information) as
          inserted in the Overhead Messages (both XTUs for G.992.3 and
          G.992.4) or in the Embedded Operations Channel (only XTU-R in
          G.992.1 and G.992.2).  It consists of up to 16 binary octets."
      REFERENCE    "ITU-T G.997.1, paragraph 7.4"
      ::= { xdsl2LineInventoryEntry 4 }

   xdsl2LInvSerialNumber  OBJECT-TYPE
      SYNTAX      OCTET STRING  (SIZE(0..32))
      MAX-ACCESS  read-only
      STATUS      current
      DESCRIPTION
         "The XTU serial number (vendor specific information) as
          inserted in the Overhead Messages (both XTUs for G.992.3 and
          G.992.4) or in the Embedded Operations Channel (only XTU-R in
          G.992.1 and G.992.2).  It is vendor specific information.  It
          consists of up to 32 ASCII characters."

      REFERENCE    "ITU-T G.997.1, paragraph 7.4"
      ::= { xdsl2LineInventoryEntry 5 }

   xdsl2LInvSelfTestResult  OBJECT-TYPE
      SYNTAX      OCTET STRING  (SIZE(0..4))
      MAX-ACCESS  read-only
      STATUS      current
      DESCRIPTION
         "The XTU self-test result, coded as a 32-bit integer.  The
          most significant octet of this object is '0' if the self-test
          passed, and '1' if the self-test failed.  The interpretation
          of the other octets is vendor discretionary."
      REFERENCE    "ITU-T G.997.1, paragraph 7.4"
      ::= { xdsl2LineInventoryEntry 6 }

   xdsl2LInvTransmissionCapabilities  OBJECT-TYPE
      SYNTAX      Xdsl2TransmissionModeType
      MAX-ACCESS  read-only
      STATUS      current
      DESCRIPTION
         "The XTU transmission system capability list of the different
          coding types.  It is coded in a bit-map representation with 1
          or more bits set.  A bit set to '1' means that the XTU
          supports the respective coding.  The value may be derived
          from the handshaking procedures defined in G.994.1.  A set
          of xDSL line transmission modes, with one bit per mode."
      REFERENCE    "ITU-T G.997.1, paragraph 7.4"
      ::= { xdsl2LineInventoryEntry 7 }


   ------------------------------------------------
   --        xdsl2LineConfTemplateTable          --
   ------------------------------------------------
   xdsl2LineConfTemplateTable  OBJECT-TYPE
      SYNTAX      SEQUENCE  OF  Xdsl2LineConfTemplateEntry
      MAX-ACCESS  not-accessible
      STATUS      current
      DESCRIPTION
         "The table xdsl2LineConfTemplateTable contains VDSL2/ADSL/
          ADSL2 and ADSL2+ line configuration template.

          Entries in this table MUST be maintained in a
          persistent manner."
      ::= { xdsl2ProfileLine 1 }

   xdsl2LineConfTemplateEntry  OBJECT-TYPE
      SYNTAX      Xdsl2LineConfTemplateEntry
      MAX-ACCESS  not-accessible
      STATUS      current
      DESCRIPTION
         "The table xdsl2LineConfTemplateTable contains VDSL2/ADSL/
          ADSL2 and ADSL2+ line configuration template.

          A default template with an index of 'DEFVAL' will
          always exist and its parameters will be set to vendor-specific
          values, unless otherwise specified in this document"
      INDEX  { xdsl2LConfTempTemplateName }
      ::= { xdsl2LineConfTemplateTable 1 }

   Xdsl2LineConfTemplateEntry  ::=
      SEQUENCE {
         xdsl2LConfTempTemplateName      SnmpAdminString,
         xdsl2LConfTempLineProfile       SnmpAdminString,
         xdsl2LConfTempChan1ConfProfile  SnmpAdminString,
         xdsl2LConfTempChan1RaRatioDs    Unsigned32,
         xdsl2LConfTempChan1RaRatioUs    Unsigned32,
         xdsl2LConfTempChan2ConfProfile  SnmpAdminString,
         xdsl2LConfTempChan2RaRatioDs    Unsigned32,
         xdsl2LConfTempChan2RaRatioUs    Unsigned32,
         xdsl2LConfTempChan3ConfProfile  SnmpAdminString,
         xdsl2LConfTempChan3RaRatioDs    Unsigned32,
         xdsl2LConfTempChan3RaRatioUs    Unsigned32,
         xdsl2LConfTempChan4ConfProfile  SnmpAdminString,
         xdsl2LConfTempChan4RaRatioDs    Unsigned32,
         xdsl2LConfTempChan4RaRatioUs    Unsigned32,
         xdsl2LConfTempRowStatus         RowStatus
      }

   xdsl2LConfTempTemplateName  OBJECT-TYPE
      SYNTAX      SnmpAdminString (SIZE(1..32))
      MAX-ACCESS  not-accessible
      STATUS      current
      DESCRIPTION
         "This object identifies a row in this table."
      REFERENCE    "DSL Forum TR-90, paragraph 5.1.4"
      ::= { xdsl2LineConfTemplateEntry 1 }

   xdsl2LConfTempLineProfile  OBJECT-TYPE
      SYNTAX      SnmpAdminString (SIZE(1..32))
      MAX-ACCESS  read-create
      STATUS      current
      DESCRIPTION
         "The value of this object identifies the row in the VDSL2/ADSL/
          ADSL2 and ADSL2+ line configuration Profile Table,
          (Xdsl2LineConfProfileTable),
          which applies for this DSL line."

      REFERENCE    "DSL Forum TR-90, paragraph 5.1.4"
      DEFVAL       { "DEFVAL" }
      ::= { xdsl2LineConfTemplateEntry 2 }

   xdsl2LConfTempChan1ConfProfile  OBJECT-TYPE
      SYNTAX      SnmpAdminString (SIZE(1..32))
      MAX-ACCESS  read-create
      STATUS      current
      DESCRIPTION
         "The value of this object identifies the row in the VDSL2/ADSL/
          ADSL2 and ADSL2+ channel configuration Profile Table,
          (Xdsl2ChanConfProfileTable) that applies to DSL bearer
          channel #1.  The channel profile name specified here must
          match the name of an existing row in the
          xdsl2ChConfProfileTable table."
      DEFVAL       { "DEFVAL" }
      ::= { xdsl2LineConfTemplateEntry 3 }

   xdsl2LConfTempChan1RaRatioDs  OBJECT-TYPE
      SYNTAX      Unsigned32(0..100)
      UNITS       "percents"
      MAX-ACCESS  read-create
      STATUS      current
      DESCRIPTION
         "Rate Adaptation Ratio.  The ratio (in %) that should be taken
          into account for the bearer channel #1 when performing rate
          adaptation on Downstream.  The ratio refers to the available
          data rate in excess of the Minimum Data Rate, summed over all
          bearer channels.  Also, the 100 -
          Xdsl2ConfTemplateChan1RaRatioDs is the ratio of excess data
          rate to be assigned to all other bearer channels on Downstream
          direction.  The sum of rate adaptation ratios over all bearers
          on the same direction shall be equal to 100%."
      REFERENCE    "ITU-T G.997.1, paragraph 7.3.2.1"
      DEFVAL       { 100 }
      ::= { xdsl2LineConfTemplateEntry 4 }

   xdsl2LConfTempChan1RaRatioUs  OBJECT-TYPE
      SYNTAX      Unsigned32(0..100)
      UNITS       "percents"
      MAX-ACCESS  read-create
      STATUS      current
      DESCRIPTION
         "Rate Adaptation Ratio.  The ratio (in %) that should be taken
          into account for the bearer channel #1 when performing rate
          adaptation on Upstream.  The ratio refers to the available
          data rate in excess of the Minimum Data Rate, summed over all
          bearer channels.  Also, the
          100 - Xdsl2ConfTemplateChan1RaRatioUs is the ratio of excess
          data rate to be assigned to all other bearer channels on
          Upstream direction.  The sum of rate adaptation ratios over
          all bearers on the same direction shall be equal to 100 %."
      REFERENCE    "ITU-T G.997.1, paragraph 7.3.2.1"
      DEFVAL       { 100 }
      ::= { xdsl2LineConfTemplateEntry 5 }

   xdsl2LConfTempChan2ConfProfile  OBJECT-TYPE
      SYNTAX      SnmpAdminString (SIZE(0..32))
      MAX-ACCESS  read-create
      STATUS      current
      DESCRIPTION
         "The value of this object identifies the row in the VDSL2/ADSL/
          ADSL2 and ADSL2+ channel configuration Profile Table,
          (Xdsl2ChanConfProfileTable) that applies to DSL bearer
          channel #2.  If the channel is unused, then the object is set
          to a zero length string.
          This object may be set to a zero length string only if
          xdsl2LConfTempChan3ConfProfile contains a zero length
          string."

      DEFVAL       { "" }
      ::= { xdsl2LineConfTemplateEntry 6 }

   xdsl2LConfTempChan2RaRatioDs  OBJECT-TYPE
      SYNTAX      Unsigned32(0..100)
      UNITS       "percents"
      MAX-ACCESS  read-create
      STATUS      current
      DESCRIPTION
         "Rate Adaptation Ratio.  The ratio (in %) that should be taken
          into account for the bearer channel #2 when performing rate
          adaptation on Downstream.  The ratio refers to the available
          data rate in excess of the Minimum Data Rate, summed over all
          bearer channels.  Also, the
          100 - Xdsl2ConfTemplateChan2RaRatioDs is the ratio of excess
          data rate to be assigned to all other bearer channels on
          Downstream direction.  The sum of rate adaptation ratios
          over all bearers on the same direction shall be equal to
          100%."
      REFERENCE    "ITU-T G.997.1, paragraph 7.3.2.1"
      DEFVAL       { 0 }
      ::= { xdsl2LineConfTemplateEntry 7 }

   xdsl2LConfTempChan2RaRatioUs  OBJECT-TYPE
      SYNTAX      Unsigned32(0..100)
      UNITS       "percents"
      MAX-ACCESS  read-create
      STATUS      current
      DESCRIPTION
         "Rate Adaptation Ratio.  The ratio (in %) that should be taken
          into account for the bearer channel #2 when performing rate
          adaptation on Upstream.  The ratio refers to the available
          data rate in excess of the Minimum Data Rate, summed over all
          bearer channels.  Also, the
          100 - Xdsl2ConfTemplateChan2RaRatioUs is the ratio of excess
          data rate to be assigned to all other bearer channels on
          Upstream direction.  The sum of rate adaptation ratios over
          all bearers on the same direction shall be equal to 100 %."
      REFERENCE    "ITU-T G.997.1, paragraph 7.3.2.1"
      DEFVAL       { 0 }
      ::= { xdsl2LineConfTemplateEntry 8 }

   xdsl2LConfTempChan3ConfProfile  OBJECT-TYPE
      SYNTAX      SnmpAdminString (SIZE(0..32))
      MAX-ACCESS  read-create
      STATUS      current
      DESCRIPTION
         "The value of this object identifies the row in the VDSL2/ADSL/
          ADSL2 and ADSL2+ channel configuration Profile Table,
          (Xdsl2ChanConfProfileTable) that applies to DSL bearer
          channel #3.  If the channel is unused, then the object is set
          to a zero length string.
          This object may be set to a zero length string only if
          xdsl2LConfTempChan4ConfProfile contains a zero length
          string.
          This object may be set to a non-zero length string only if
          xdsl2LConfTempChan2ConfProfile contains a non-zero length
          string."
      DEFVAL       { "" }
      ::= { xdsl2LineConfTemplateEntry 9 }

   xdsl2LConfTempChan3RaRatioDs  OBJECT-TYPE
      SYNTAX      Unsigned32(0..100)
      UNITS       "percents"
      MAX-ACCESS  read-create
      STATUS      current
      DESCRIPTION
         "Rate Adaptation Ratio.  The ratio (in %) that should be taken
          into account for the bearer channel #3 when performing rate
          adaptation on Downstream.  The ratio refers to the available
          data rate in excess of the Minimum Data Rate, summed over all
          bearer channels.  Also, the 100 -
          Xdsl2ConfTemplateChan3RaRatioDs is the ratio of excess data
          rate to be assigned to all other bearer channels on Downstream
          direction.  The sum of rate adaptation ratios over all bearers
          on the same direction shall be equal to 100%."
      REFERENCE    "ITU-T G.997.1, paragraph 7.3.2.1"
      DEFVAL       { 0 }
      ::= { xdsl2LineConfTemplateEntry 10 }

   xdsl2LConfTempChan3RaRatioUs  OBJECT-TYPE
      SYNTAX      Unsigned32(0..100)
      UNITS       "percents"
      MAX-ACCESS  read-create
      STATUS      current
      DESCRIPTION
         "Rate Adaptation Ratio.  The ratio (in %) that should be taken
          into account for the bearer channel #3 when performing rate
          adaptation on Upstream.  The ratio refers to the available
          data rate in excess of the Minimum Data Rate, summed over all
          bearer channels.  Also, the
          100 - Xdsl2ConfTemplateChan3RaRatioUs is the ratio of excess
          data rate to be assigned to all other bearer channels on
          Upstream direction.  The sum of rate adaptation ratios over
          all bearers on the same direction shall be equal to 100%."
      REFERENCE    "ITU-T G.997.1, paragraph 7.3.2.1"
      DEFVAL       { 0 }
      ::= { xdsl2LineConfTemplateEntry 11 }

   xdsl2LConfTempChan4ConfProfile  OBJECT-TYPE
      SYNTAX      SnmpAdminString (SIZE(0..32))
      MAX-ACCESS  read-create
      STATUS      current
      DESCRIPTION
         "The value of this object identifies the row in the VDSL2/ADSL/
          ADSL2 and ADSL2+ channel configuration Profile Table,
          (Xdsl2ChanConfProfileTable) that applies to DSL bearer
          channel #4.  If the channel is unused, then the object is set
          to a zero length string.
          This object may be set to a non-zero length string only if
          xdsl2LConfTempChan3ConfProfile contains a non-zero length
          string."
      DEFVAL       { "" }
      ::= { xdsl2LineConfTemplateEntry 12 }

   xdsl2LConfTempChan4RaRatioDs  OBJECT-TYPE
      SYNTAX      Unsigned32(0..100)
      UNITS       "percents"
      MAX-ACCESS  read-create
      STATUS      current
      DESCRIPTION
         "Rate Adaptation Ratio.  The ratio (in %) that should be taken
          into account for the bearer channel #4 when performing rate
          adaptation on Downstream.  The ratio refers to the available
          data rate in excess of the Minimum Data Rate, summed over all
          bearer channels.  Also, the 100 -

          xdsl2LConfTempChan4RaRatioDs is the ratio of
          excess data rate to be assigned to all other bearer channels.
          The sum of rate adaptation ratios over all bearers on the same
          direction shall sum to 100%."
      REFERENCE    "ITU-T G.997.1, paragraph 7.3.2.1"
      DEFVAL       { 0 }
      ::= { xdsl2LineConfTemplateEntry 13 }

   xdsl2LConfTempChan4RaRatioUs  OBJECT-TYPE
      SYNTAX      Unsigned32(0..100)
      UNITS       "percents"
      MAX-ACCESS  read-create
      STATUS      current
      DESCRIPTION
         "Rate Adaptation Ratio.  The ratio (in %) that should be taken
          into account for the bearer channel #4 when performing rate
          adaptation on Upstream.  The ratio refers to the available
          data rate in excess of the Minimum Data Rate, summed over
          all bearer channels.  Also, the 100 -

          xdsl2LConfTempChan4RaRatioUs is the
          ratio of excess data rate to be assigned to all other bearer
          channels.  The sum of rate adaptation ratios over all bearers
          on the same direction shall sum to 100%."
      REFERENCE    "ITU-T G.997.1, paragraph 7.3.2.1"
      DEFVAL       { 0 }
      ::= { xdsl2LineConfTemplateEntry 14 }

   xdsl2LConfTempRowStatus  OBJECT-TYPE
      SYNTAX      RowStatus
      MAX-ACCESS  read-create
      STATUS      current
      DESCRIPTION
         "This object is used to create a new row or to modify or
         delete an existing row in this table.

         A template is activated by setting this object to 'active'.
         When 'active' is set, the system will validate the template.
         Template modification is prohibited while this object is set
         to 'active'.

         Before a template can be deleted or taken out of service
         (by setting this object to 'destroy' or 'notInService'),
         it must be first unreferenced from all associated
         lines."
      ::= { xdsl2LineConfTemplateEntry 15 }


   ------------------------------------------
   --        xdsl2LineConfProfTable        --
   ------------------------------------------
   xdsl2LineConfProfTable  OBJECT-TYPE
      SYNTAX      SEQUENCE  OF  Xdsl2LineConfProfEntry
      MAX-ACCESS  not-accessible
      STATUS      current
      DESCRIPTION
         "The table xdsl2LineConfProfTable contains VDSL2/ADSL/
          ADSL2 and ADSL2+ line configuration profile.

          Entries in this table MUST be maintained in a
          persistent manner."
      ::= { xdsl2ProfileLine 2 }

   xdsl2LineConfProfEntry  OBJECT-TYPE
      SYNTAX      Xdsl2LineConfProfEntry
      MAX-ACCESS  not-accessible
      STATUS      current
      DESCRIPTION
         "The table xdsl2LineConfProfTable contains VDSL2/ADSL/
          ADSL2 and ADSL2+ line configuration profile.

          A default profile with an index of 'DEFVAL' will
          always exist and its parameters will be set to vendor-specific
          values, unless otherwise specified in this document"
      INDEX  { xdsl2LConfProfProfileName }
      ::= { xdsl2LineConfProfTable 1 }

   Xdsl2LineConfProfEntry  ::=
      SEQUENCE {
         xdsl2LConfProfProfileName          SnmpAdminString,
         xdsl2LConfProfScMaskDs             Xdsl2ScMaskDs,
         xdsl2LConfProfScMaskUs             Xdsl2ScMaskUs,
         xdsl2LConfProfRfiBandsDs           Xdsl2RfiDs,
         xdsl2LConfProfRaModeDs             Xdsl2RaMode,
         xdsl2LConfProfRaModeUs             Xdsl2RaMode,
         xdsl2LConfProfRaUsNrmDs            Unsigned32,
         xdsl2LConfProfRaUsNrmUs            Unsigned32,
         xdsl2LConfProfRaUsTimeDs           Unsigned32,
         xdsl2LConfProfRaUsTimeUs           Unsigned32,
         xdsl2LConfProfRaDsNrmsDs           Unsigned32,
         xdsl2LConfProfRaDsNrmsUs           Unsigned32,
         xdsl2LConfProfRaDsTimeDs           Unsigned32,
         xdsl2LConfProfRaDsTimeUs           Unsigned32,
         xdsl2LConfProfTargetSnrmDs         Unsigned32,
         xdsl2LConfProfTargetSnrmUs         Unsigned32,
         xdsl2LConfProfMaxSnrmDs            Unsigned32,
         xdsl2LConfProfMaxSnrmUs            Unsigned32,
         xdsl2LConfProfMinSnrmDs            Unsigned32,
         xdsl2LConfProfMinSnrmUs            Unsigned32,
         xdsl2LConfProfMsgMinUs             Unsigned32,
         xdsl2LConfProfMsgMinDs             Unsigned32,
         xdsl2LConfProfXtuTransSysEna       Xdsl2TransmissionModeType,
         xdsl2LConfProfPmMode               Xdsl2LConfProfPmMode,
         xdsl2LConfProfL0Time               Unsigned32,
         xdsl2LConfProfL2Time               Unsigned32,
         xdsl2LConfProfL2Atpr               Unsigned32,
         xdsl2LConfProfL2Atprt              Unsigned32,
         xdsl2LConfProfRowStatus            RowStatus
      }

   xdsl2LConfProfProfileName  OBJECT-TYPE
      SYNTAX      SnmpAdminString (SIZE(1..32))
      MAX-ACCESS  not-accessible
      STATUS      current
      DESCRIPTION
         "This object identifies a row in this table."
        ::= { xdsl2LineConfProfEntry 1 }

   xdsl2LConfProfScMaskDs  OBJECT-TYPE
      SYNTAX      Xdsl2ScMaskDs
      MAX-ACCESS  read-create
      STATUS      current
      DESCRIPTION
         "Sub-carriers mask.  A bitmap of 4096 bits that allows masking
          up to 4096 downstream sub-carriers, depending on NSCds.  If
          bit i (0 <= i < NSCds) is set to '1', the respective
          downstream sub-carrier i is masked, and if set to '0', the
          respective sub-carrier is unmasked.  Note that there should
          always be unmasked sub-carriers (i.e., the object cannot be
          all 1's).  Also note that if NSCds < 4096, all bits
          i (NSCds i <= 4096) should be set to '1'."
      REFERENCE    "ITU-T G.997.1, paragraph 7.3.1.2.6"
      ::= { xdsl2LineConfProfEntry 2 }

   xdsl2LConfProfScMaskUs  OBJECT-TYPE
      SYNTAX      Xdsl2ScMaskUs
      MAX-ACCESS  read-create
      STATUS      current
      DESCRIPTION
         "Sub-carriers mask.  A bitmap of 4096 bits that allows masking
          up to 4096 downstream sub-carriers, depending on NSCds.  If
          bit i (0 <= i < NSCus) is set to '1', the respective
          upstream sub-carrier i is masked, and if set to '0', the
          respective sub-carrier is unmasked.  Note that there
          should always be unmasked sub-carriers (i.e., the object
          cannot be all 1's).  Also note that if NSCus <
          4096, all bits i (NSCus < i <= 4096) should be set to '1'."
      REFERENCE    "ITU-T G.997.1, paragraph 7.3.1.2.7"
      ::= { xdsl2LineConfProfEntry 3 }

   xdsl2LConfProfRfiBandsDs  OBJECT-TYPE
      SYNTAX      Xdsl2RfiDs
      MAX-ACCESS  read-create
      STATUS      current
      DESCRIPTION
          "The subset of downstream PSD mask breakpoints that shall be
          used to notch an RFI band.
          The specific interpolation around these points is defined in
          G.992.5.  It is a bitmap of 4096 bits that allows referring to
          up to 4096 downstream sub-carriers, depending on NSCds.  If
          bit i (0 <= i < NSCds) is set to '1', the respective
          downstream sub-carrier i is part of a notch filter, and if
          set to '0', the respective sub-carrier is not
          part of a notch filter.
          This information complements the specification provided by
          xdsl2LconfProfPsdMaskDs.
          Note that if NSCds < 4096, all bits i (NSCds<i< 4096)
          should be set to '0'. "
      REFERENCE    "ITU-T G.997.1, paragraph 7.3.1.2.9"
      ::= { xdsl2LineConfProfEntry 4 }

   xdsl2LConfProfRaModeDs  OBJECT-TYPE
      SYNTAX      Xdsl2RaMode
      MAX-ACCESS  read-create
      STATUS      current
      DESCRIPTION
         "The mode of operation of a rate-adaptive xTU-C in the transmit
          direction.  The parameter can take three values:
             manual (1),
             raInit (2),
             dynamicRa (3)."
      REFERENCE    "ITU-T G.997.1, paragraph 7.3.1.4.1"
      DEFVAL       { manual }
      ::= { xdsl2LineConfProfEntry 5 }

   xdsl2LConfProfRaModeUs  OBJECT-TYPE
      SYNTAX      Xdsl2RaMode
      MAX-ACCESS  read-create
      STATUS      current
      DESCRIPTION
         "The mode of operation of a rate-adaptive xTU-R in the transmit
          direction.  The parameter can take three values:
             manual (1),
             raInit (2),
             dynamicRa (3)."
      REFERENCE    "ITU-T G.997.1, paragraph 7.3.1.4.2"
      DEFVAL       { manual }
      ::= { xdsl2LineConfProfEntry 6 }

   xdsl2LConfProfRaUsNrmDs  OBJECT-TYPE
      SYNTAX      Unsigned32(0..310)
      UNITS       "0.1 dB"
      MAX-ACCESS  read-create
      STATUS      current
      DESCRIPTION
         "The Downstream Up-Shift Noise Margin value, to be used when
          Xdsl2LineConfRaModeDs is set to DynamicRa.  If the downstream
          noise margin is above this value and stays above it for
          more than the time specified by the Xdsl2LineConfRaUsTimeDs,
          the xTU-R shall attempt to increase the downstream net data
          rate.  The Downstream Up-shift Noise Margin ranges from 0 to
          310 units of 0.1 dB (Physical values are 0 to 31 dB)."
      REFERENCE    "ITU-T G.997.1, paragraph 7.3.1.4.3"
      DEFVAL       { 10 }
      ::= { xdsl2LineConfProfEntry 7 }

   xdsl2LConfProfRaUsNrmUs  OBJECT-TYPE
      SYNTAX      Unsigned32(0..310)
      UNITS       "0.1 dB"
      MAX-ACCESS  read-create
      STATUS      current
      DESCRIPTION
         "The Upstream Up-Shift Noise Margin value, to be used when
          Xdsl2LineConfRaModeUs is set to DynamicRa.  If the upstream
          noise margin is above this value and stays above it for more
          than the time specified by the Xdsl2LineConfRaUsTimeUs, the
          xTU-C shall attempt to increase the upstream net data rate.
          The Upstream Up-shift Noise Margin ranges from 0 to 310 units
          of 0.1 dB (Physical values are 0 to 31 dB)."
      REFERENCE    "ITU-T G.997.1, paragraph 7.3.1.4.4"
      DEFVAL       { 10 }
      ::= { xdsl2LineConfProfEntry 8 }

   xdsl2LConfProfRaUsTimeDs  OBJECT-TYPE
      SYNTAX      Unsigned32(0..16383)
      UNITS       "seconds"
      MAX-ACCESS  read-create
      STATUS      current
      DESCRIPTION
         "The Downstream Up-Shift Time Interval, to be used when
          Xdsl2LineConfRaModeDs is set to DynamicRa.  The interval of
          time that the downstream noise margin should stay above the
          Downstream Up-shift Noise Margin before the xTU-R shall
          attempt to increase the downstream net data rate.  The time
          interval ranges from 0 to 16383 seconds."
      REFERENCE    "ITU-T G.997.1, paragraph 7.3.1.4.5"
      DEFVAL       { 3600 }
      ::= { xdsl2LineConfProfEntry 9 }

   xdsl2LConfProfRaUsTimeUs  OBJECT-TYPE
      SYNTAX      Unsigned32(0..16383)
      UNITS       "seconds"
      MAX-ACCESS  read-create
      STATUS      current
      DESCRIPTION
         "The Upstream Up-Shift Time Interval, to be used when
          Xdsl2LineConfRaModeUs is set to DynamicRa.  The interval of
          time the upstream noise margin should stay above the
          Upstream Up-shift Noise Margin before the xTU-C shall
          attempt to increase the upstream net data rate.  The time
          interval ranges from 0 to 16383 seconds."
      REFERENCE    "ITU-T G.997.1, paragraph 7.3.1.4.6"
      DEFVAL       { 3600 }
      ::= { xdsl2LineConfProfEntry 10 }

   xdsl2LConfProfRaDsNrmsDs  OBJECT-TYPE
      SYNTAX      Unsigned32(0..310)
      UNITS       "0.1 dB"
      MAX-ACCESS  read-create
      STATUS      current
      DESCRIPTION
         "The Downstream Down-Shift Noise Margin value, to be used when
          Xdsl2LineConfRaModeDs is set to DynamicRa.  If the downstream
          noise margin is below this value and stays below that for more
          than the time specified by the Xdsl2LineConfRaDsTimeDs, the
          xTU-R shall attempt to decrease the downstream net data rate.
          The Downstream Down-shift Noise Margin ranges from 0 to 310
          units of 0.1 dB (Physical values are 0 to 31 dB)."
      REFERENCE    "ITU-T G.997.1, paragraph 7.3.1.4.7"
      DEFVAL       { 10 }
      ::= { xdsl2LineConfProfEntry 11 }

   xdsl2LConfProfRaDsNrmsUs  OBJECT-TYPE
      SYNTAX      Unsigned32(0..310)
      UNITS       "0.1 dB"
      MAX-ACCESS  read-create
      STATUS      current
      DESCRIPTION
         "The Upstream Downshift Noise Margin value, to be used when
          Xdsl2LineConfRaModeUs is set to DynamicRa.  If the upstream
          noise margin is below this value and stays below that for more
          than the time specified by the Xdsl2LineConfRaDsTimeUs, the
          xTU-C shall attempt to decrease the upstream net data rate.
          The Upstream Down-shift Noise Margin ranges from 0 to 310
          units of 0.1 dB (Physical values are 0 to 31 dB)."
      REFERENCE    "ITU-T G.997.1, paragraph 7.3.1.4.8"
      DEFVAL       { 10 }
      ::= { xdsl2LineConfProfEntry 12 }

   xdsl2LConfProfRaDsTimeDs  OBJECT-TYPE
      SYNTAX      Unsigned32(0..16383)
      UNITS       "seconds"
      MAX-ACCESS  read-create
      STATUS      current
      DESCRIPTION
         "The Downstream Downshift Time Interval, to be used when
          Xdsl2LineConfRaModeDs is set to DynamicRa.  The interval of
          time the downstream noise margin should stay below the
          Downstream Down-shift Noise Margin before the xTU-R shall
          attempt to decrease the downstream net data rate.  The time
          interval ranges from 0 to 16383 seconds."
      REFERENCE    "ITU-T G.997.1, paragraph 7.3.1.4.9"
      DEFVAL       { 3600 }
      ::= { xdsl2LineConfProfEntry 13 }

   xdsl2LConfProfRaDsTimeUs  OBJECT-TYPE
      SYNTAX      Unsigned32(0..16383)
      UNITS       "seconds"
      MAX-ACCESS  read-create
      STATUS      current
      DESCRIPTION
         "The Upstream Down-Shift Time Interval, to be used when
          Xdsl2LineConfRaModeUs is set to DynamicRa.  The interval of
          time the upstream noise margin should stay below the Upstream
          Down-shift Noise Margin before the xTU-C shall attempt to
          decrease the upstream net data rate.  The time interval ranges
          from 0 to 16383 seconds."
      REFERENCE    "ITU-T G.997.1, paragraph 7.3.1.4.10"
      DEFVAL       { 3600 }
      ::= { xdsl2LineConfProfEntry 14 }

   xdsl2LConfProfTargetSnrmDs  OBJECT-TYPE
      SYNTAX      Unsigned32(0..310)
      UNITS       "0.1 dB"
      MAX-ACCESS  read-create
      STATUS      current
      DESCRIPTION
         "The minimum Noise Margin the xTU-R receiver shall achieve,

          relative to the BER requirement for each of the downstream

          bearer channels, to successfully complete initialization.
          The target noise margin ranges from 0 to 310 units of 0.1 dB
          (Physical values are 0 to 31 dB)."
      REFERENCE    "ITU-T G.997.1, paragraph 7.3.1.3.1"
      DEFVAL       { 60 }
      ::= { xdsl2LineConfProfEntry 15 }

   xdsl2LConfProfTargetSnrmUs  OBJECT-TYPE
      SYNTAX      Unsigned32(0..310)
      UNITS       "0.1 dB"
      MAX-ACCESS  read-create
      STATUS      current
      DESCRIPTION
         "The minimum Noise Margin the xTU-C receiver shall achieve,

          relative to the BER requirement for each of the upstream

          bearer channels, to successfully complete initialization.
          The target noise margin ranges from 0 to 310 units of 0.1 dB
          (Physical values are 0 to 31 dB)."
      REFERENCE    "ITU-T G.997.1, paragraph 7.3.1.3.2"
      DEFVAL       { 60 }
      ::= { xdsl2LineConfProfEntry 16 }

   xdsl2LConfProfMaxSnrmDs  OBJECT-TYPE
      SYNTAX      Unsigned32
      UNITS       "0.1 dB"
      MAX-ACCESS  read-create
      STATUS      current
      DESCRIPTION
         "The maximum Noise Margin the xTU-R receiver shall try to
          sustain.  If the Noise Margin is above this level, the xTU-R
          shall request that the xTU-C reduce the xTU-C transmit power
          to get a noise margin below this limit (if this functionality
          is supported).  The maximum noise margin ranges from 0 to 310
          units of 0.1 dB (Physical values are 0 to 31 dB).  A value of
          all 1's means that there is no maximum."
      REFERENCE    "ITU-T G.997.1, paragraph 7.3.1.3.3"
      DEFVAL       { 310 }
      ::= { xdsl2LineConfProfEntry 17 }

   xdsl2LConfProfMaxSnrmUs  OBJECT-TYPE
      SYNTAX      Unsigned32
      UNITS       "0.1 dB"
      MAX-ACCESS  read-create
      STATUS      current
      DESCRIPTION
         "The maximum Noise Margin the xTU-C receiver shall try to
          sustain.  If the Noise Margin is above this level, the xTU-C
          shall request that the xTU-R reduce the xTU-R transmit power
          to get a noise margin below this limit (if this functionality
          is supported).  The maximum noise margin ranges from 0 to 310
          units of 0.1 dB (Physical values are 0 to 31 dB).  A value of
          all 1's means that there is no maximum."
      REFERENCE    "ITU-T G.997.1, paragraph 7.3.1.3.4"
      DEFVAL       { 310 }
      ::= { xdsl2LineConfProfEntry 18 }

   xdsl2LConfProfMinSnrmDs  OBJECT-TYPE
      SYNTAX      Unsigned32(0..310)
      UNITS       "0.1 dB"
      MAX-ACCESS  read-create
      STATUS      current
      DESCRIPTION
         "The minimum Noise Margin the xTU-R receiver shall tolerate.
          If the noise margin falls below this level, the xTU-R shall
          request that the xTU-C increase the xTU-C transmit power.
          If an increase to xTU-C transmit power is not possible, a
          loss-of-margin (LOM) defect occurs, the xTU-R shall fail and
          attempt to reinitialize and the NMS shall be notified.  The
          minimum noise margin ranges from 0 to 310 units of
          0.1 dB (Physical values are 0 to 31 dB).  A value of 0 means
          that there is no minimum."
      REFERENCE    "ITU-T G.997.1, paragraph 7.3.1.3.5"
      DEFVAL       { 10 }
      ::= { xdsl2LineConfProfEntry 19 }

   xdsl2LConfProfMinSnrmUs  OBJECT-TYPE
      SYNTAX      Unsigned32(0..310)
      UNITS       "0.1 dB"
      MAX-ACCESS  read-create
      STATUS      current
      DESCRIPTION
         "The minimum Noise Margin the xTU-C receiver shall tolerate.
          If the noise margin falls below this level, the xTU-C shall
          request that the xTU-R increase the xTU-R transmit power.
          If an increase of xTU-R transmit power is not possible, a
          loss-of-margin (LOM) defect occurs, the xTU-C shall fail and
          attempt to re-initialize and the NMS shall be notified.  The
          minimum noise margin ranges from 0 to 310 units of
          0.1 dB (Physical values are 0 to 31 dB).  A value of 0 means
          that there is no minimum."
      REFERENCE    "ITU-T G.997.1, paragraph 7.3.1.3.6"
      DEFVAL       { 10 }
      ::= { xdsl2LineConfProfEntry 20 }

   xdsl2LConfProfMsgMinUs  OBJECT-TYPE
      SYNTAX      Unsigned32(4000..63000)
      UNITS       "bits/second"
      MAX-ACCESS  read-create
      STATUS      current
      DESCRIPTION
         "Minimum Overhead Rate Upstream.  Defines the minimum rate of
          the message-based overhead that shall be maintained by the xTU
          in upstream direction.  Expressed in bits per second and
          ranges from 4000 to 63000 bps."
      REFERENCE    "ITU-T G.997.1, paragraph 7.3.1.5.1"
      DEFVAL       { 4000 }
     ::= { xdsl2LineConfProfEntry 21 }

   xdsl2LConfProfMsgMinDs  OBJECT-TYPE
      SYNTAX      Unsigned32(4000..63000)
      UNITS       "bits/second"
      MAX-ACCESS  read-create
      STATUS      current
      DESCRIPTION
         "Minimum Overhead Rate Downstream.  Defines the minimum rate of
          the message-based overhead that shall be maintained by the xTU
          in downstream direction.  Expressed in bits per second and
          ranges from 4000 to 63000 bps."
      REFERENCE    "ITU-T G.997.1, paragraph 7.3.1.5.2"
      DEFVAL       { 4000 }
      ::= { xdsl2LineConfProfEntry 22 }

   xdsl2LConfProfXtuTransSysEna  OBJECT-TYPE
      SYNTAX      Xdsl2TransmissionModeType
      MAX-ACCESS  read-create
      STATUS      current
      DESCRIPTION
         "xTU Transmission System Enabling (xTSE).  A list of the
          different coding types enabled in this profile.  It is coded
          in a bit-map representation with 1 or more bits set.  A bit
          set to  '1' means that the xTUs may apply the respective
          coding for the DSL line.  A bit set to '0' means that
          the xTUs cannot apply the respective coding for the ADSL
          line.  All 'reserved' bits should be set to '0'."
      REFERENCE    "ITU-T G.997.1, paragraph 7.3.1.1.1"
      ::= { xdsl2LineConfProfEntry 23 }

   xdsl2LConfProfPmMode  OBJECT-TYPE
      SYNTAX      Xdsl2LConfProfPmMode
      MAX-ACCESS  read-create
      STATUS      current
      DESCRIPTION
         "Power management state Enabling.  Defines the power states the
          xTU-C or xTU-R may autonomously transition to on this line.
          The various bit positions are: allowTransitionsToIdle (0) and
          allowTransitionsToLowPower (1).  A bit with a '1' value means
          that the xTU is allowed to transit into the respective state
          and a '0' value means that the xTU is not allowed
          to transit into the respective state."
      REFERENCE    "ITU-T G.997.1, paragraph 7.3.1.1.4"
      DEFVAL  { { allowTransitionsToIdle, allowTransitionsToLowPower } }
      ::= { xdsl2LineConfProfEntry 24 }

   xdsl2LConfProfL0Time  OBJECT-TYPE
      SYNTAX      Unsigned32 (0..255)
      UNITS       "seconds"
      MAX-ACCESS  read-create
      STATUS      current
      DESCRIPTION
         "This minimum time (in seconds) between an Exit from the L2
          state and the next Entry into the L2 state.  It ranges from 0
          to 255 seconds."
      REFERENCE    "ITU-T G.997.1, paragraph 7.3.1.1.5"
      DEFVAL       { 255 }
      ::= { xdsl2LineConfProfEntry 25 }

   xdsl2LConfProfL2Time  OBJECT-TYPE
      SYNTAX      Unsigned32 (0..255)
      UNITS       "seconds"
      MAX-ACCESS  read-create
      STATUS      current
      DESCRIPTION
         "This minimum time (in seconds) between an Entry into the
         L2 state and the first Power Trim in the L2 state and between
         two consecutive Power Trims in the L2 State.
         It ranges from 0 to 255 seconds."
      REFERENCE    "ITU-T G.997.1, paragraph 7.3.1.1.6"
      DEFVAL       { 255 }
      ::= { xdsl2LineConfProfEntry 26 }

   xdsl2LConfProfL2Atpr  OBJECT-TYPE
      SYNTAX      Unsigned32 (0..31)
      UNITS       "dB"
      MAX-ACCESS  read-create
      STATUS      current
      DESCRIPTION
         "The maximum aggregate transmit power reduction (in dB) that
          can be performed at transition of L0 to L2 state or through a
          single Power Trim in the L2 state.
          It ranges from 0 dB to 31 dB."
      REFERENCE    "ITU-T G.997.1 (amendment 1), 7.3.1.1.7"
      DEFVAL       { 10 }
      ::= { xdsl2LineConfProfEntry 27 }

   xdsl2LConfProfL2Atprt  OBJECT-TYPE
      SYNTAX      Unsigned32 (0..31)
      UNITS       "dB"
      MAX-ACCESS  read-create
      STATUS      current
      DESCRIPTION
         "The total maximum aggregate transmit power reduction
         (in dB) that can be performed in an L2 state. This is the
         sum of all reductions of L2 Request (i.e., at transition of
         L0 to L2 state) and Power Trims."
      REFERENCE    "ITU-T G.997.1 (amendment 1), 7.3.1.1.9"
      DEFVAL       { 31 }
      ::= { xdsl2LineConfProfEntry 28 }

   xdsl2LConfProfRowStatus  OBJECT-TYPE
      SYNTAX      RowStatus
      MAX-ACCESS  read-create
      STATUS      current
      DESCRIPTION
         "This object is used to create a new row or to modify or
         delete an existing row in this table.

         A profile is activated by setting this object to 'active'.
         When 'active' is set, the system will validate the profile.
         Profile modification is prohibited while this object is set
         to 'active'.

         Before a profile can be deleted or taken out of service
         (by setting this object to 'destroy' or 'notInService'),
         it must be first unreferenced from all associated
         templates."
      ::= { xdsl2LineConfProfEntry 29 }

   ------*****************************************************
   ----- The following table should be changed. Instead of the
   ----- current modes list we'll have a list that follows the xTSE
   ------*****************************************************

   ------------------------------------------
   --    xdsl2LineConfProfModeSpecTable    --
   ------------------------------------------
   xdsl2LineConfProfModeSpecTable  OBJECT-TYPE
      SYNTAX      SEQUENCE  OF  Xdsl2LineConfProfModeSpecEntry
      MAX-ACCESS  not-accessible
      STATUS      current
      DESCRIPTION
         "The table xdsl2LineConfProfModeSpecTable extends the
          DSL line configuration profile by xDSL Mode Specific
          parameters.
          A row in this table that has an index of
          xdsl2LconfProfXdslMode == defMode(1), is called a
          'mandatory' row.
          A row in this table that has an index such that
          xdsl2LconfProfXdslMode is not equal to defMode(1),
          is called an 'optional' row.
          When a row in the xdsl2LineConfProfTable table
          (the parent row) is created, the SNMP agent will
          automatically create a 'mandatory' row in this table.
          When the parent row is deleted, the SNMP agent will
          automatically delete all associated rows in this table.
          Any attempt to delete the 'mandatory' row using the
          xdsl2LConfProfModeSpecRowStatus attribute will be
          rejected by the SNMP agent.
          The manager MAY create an 'optional' row in this table
          using the xdsl2LConfProfModeSpecRowStatus attribute if
          the parent row exists.
          The manager MAY delete an 'optional' row in this table
          using the xdsl2LConfProfModeSpecRowStatus attribute at
          any time.
          If the actual transmission mode of a DSL line does not
          match one of the 'optional' rows in this table, then
          the line will use the PSD configuration from the
          'mandatory' row.

          Entries in this table MUST be maintained in a
          persistent manner."
      ::= { xdsl2ProfileLine 3 }

   xdsl2LineConfProfModeSpecEntry  OBJECT-TYPE
      SYNTAX      Xdsl2LineConfProfModeSpecEntry
      MAX-ACCESS  not-accessible
      STATUS      current
      DESCRIPTION
         "The table xdsl2LineConfProfModeSpecTable extends the
          DSL line configuration profile by DSL Mode Specific
          parameters."
      INDEX  { xdsl2LConfProfProfileName, xdsl2LconfProfXdslMode }
      ::= { xdsl2LineConfProfModeSpecTable 1 }

   Xdsl2LineConfProfModeSpecEntry  ::=
      SEQUENCE {
         xdsl2LconfProfXdslMode             Xdsl2OperationModes,
         xdsl2LConfProfMaxNomPsdDs          Integer32,
         xdsl2LConfProfMaxNomPsdUs          Integer32,
         xdsl2LConfProfMaxNomAtpDs          Unsigned32,
         xdsl2LConfProfMaxNomAtpUs          Unsigned32,
         xdsl2LConfProfMaxAggRxPwrUs        Integer32,
         xdsl2LConfProfPsdMaskDs            Xdsl2PsdMaskDs,
         xdsl2LConfProfPsdMaskUs            Xdsl2PsdMaskUs,
         xdsl2LConfProfPsdMaskSelectUs      Unsigned32,
         xdsl2LConfProfModeSpecRowStatus    RowStatus
      }

   xdsl2LconfProfXdslMode    OBJECT-TYPE
      SYNTAX      Xdsl2OperationModes
      MAX-ACCESS  not-accessible
      STATUS      current
      DESCRIPTION
         "The DSL Mode is a way of categorizing the various xDSL
          transmission modes into groups, each group (xDSL Mode) shares
          the same PSD configuration.
          There should be multiple entries in this table for a given
          line profile in case multiple bits are set in
          xdsl2LConfProfAtuTransSysEna for that profile. "
      REFERENCE    "DSL Forum TR-90, paragraph 5.1.8"
      ::= { xdsl2LineConfProfModeSpecEntry 1 }

   xdsl2LConfProfMaxNomPsdDs  OBJECT-TYPE
      SYNTAX      Integer32(-600..-300)
      UNITS       "0.1 dBm/Hz"
      MAX-ACCESS  read-create
      STATUS      current
      DESCRIPTION
         "The maximum nominal transmit PSD in the downstream
          direction during initialization and Showtime.  It ranges from
          -600 to -300 units of 0.1 dBm/Hz.  (physical values are -60 to
          -30 dBm/Hz).  "
      REFERENCE    "ITU-T G.997.1, paragraph 7.3.1.2"
      DEFVAL       { -300 }
     ::= { xdsl2LineConfProfModeSpecEntry 2 }

   xdsl2LConfProfMaxNomPsdUs  OBJECT-TYPE
      SYNTAX      Integer32(-600..-300)
      UNITS       "0.1 dBm/Hz"
      MAX-ACCESS  read-create
      STATUS      current
      DESCRIPTION
         "The maximum nominal transmit PSD in the upstream direction
          during initialization and Showtime.  It ranges from -600 to
          -300 units of 0.1 dBm/Hz.  (physical values are -60 to
          -30 dBm/Hz).  "
      REFERENCE    "ITU-T G.997.1, paragraph 7.3.1.2"
      DEFVAL       { -300 }
      ::= { xdsl2LineConfProfModeSpecEntry 3 }

   xdsl2LConfProfMaxNomAtpDs  OBJECT-TYPE
      SYNTAX      Unsigned32 (0..255)
      UNITS       "0.1 dBm"
      MAX-ACCESS  read-create
      STATUS      current
      DESCRIPTION
         "The maximum nominal aggregate transmit power in the
          downstream direction during initialization and Showtime.  It
          ranges from 0 to 255 units of 0.1 dBm (physical values are 0
          to 25.5 dBm)."
      REFERENCE    "ITU-T G.997.1, paragraph 7.3.1.2"
      DEFVAL       { 255 }
      ::= { xdsl2LineConfProfModeSpecEntry 4 }

   xdsl2LConfProfMaxNomAtpUs  OBJECT-TYPE
      SYNTAX      Unsigned32 (0..255)
      UNITS       "0.1 dBm"
      MAX-ACCESS  read-create
      STATUS      current
      DESCRIPTION
         "The maximum nominal aggregate transmit power in the upstream
          direction during initialization and Showtime.  It ranges from
          0 to 255 units of 0.1 dBm (physical values are 0 to 25.5
          dBm)."
      REFERENCE    "ITU-T G.997.1, paragraph 7.3.1.2"
      DEFVAL       { 255 }
      ::= { xdsl2LineConfProfModeSpecEntry 5 }

   xdsl2LConfProfMaxAggRxPwrUs  OBJECT-TYPE
      SYNTAX      Integer32(-255..2147483647)
      UNITS       "0.1 dBm"
      MAX-ACCESS  read-create
      STATUS      current
      DESCRIPTION
         "The maximum upstream aggregate receive power over the relevant
          set of sub-carriers.  The xTU-C should verify that the
          upstream power cutback is such that this maximum aggregate
          receive power value is honored.  It ranges from -255 to 255
          units of 0.1 dBm (physical values are -25.5 to 25.5 dBm).
          A value of all ones means that there is no limit."
      REFERENCE    "ITU-T G.997.1, paragraph 7.3.1.2"
      DEFVAL       { 255 }
      ::= { xdsl2LineConfProfModeSpecEntry 6 }

   xdsl2LConfProfPsdMaskDs   OBJECT-TYPE
      SYNTAX      Xdsl2PsdMaskDs
      MAX-ACCESS  read-create
      STATUS      current
      DESCRIPTION
        "The downstream PSD mask applicable at the U-C2 reference
         point.
        This parameter is used only for G.992.5 and it may impose PSD
        restrictions (breakpoints) in addition to the Limit PSD mask
        defined in G.992.5.
        This is a string of 32 pairs of values in the following
        structure:
        Octets 0+1 - Index of 1st sub-carrier used in the context
                     of a first breakpoint.
        Octet 2    - The PSD reduction for the sub-carrier indicated in
                     octets 0 and 1.
        Octets 3-5 - Same, for a 2nd breakpoint.
        Octets 6-8 - Same, for a 3rd breakpoint.
        This architecture continues until octets 94-95, which are
        associated with a 32nd breakpoint.
        Each subcarrier index is an unsigned number in the range 1 and
        NSCds.  Each PSD reduction value is in the range 0 (0dBm/Hz) to
        255 (-127.5dBm/Hz) with steps of 0.5dBm/Hz.  Valid values are
        in the range 0 to 190 (0 to -95dBm/Hz).
        When the number of breakpoints is less than 32, all remaining
        octets are set to the value 0.  Note that the content of this
        object should be correlated with the sub-carriers mask and with
        the RFI setup. "
      REFERENCE    "ITU-T G.997.1, paragraph 7.3.1.2"
        ::= { xdsl2LineConfProfModeSpecEntry 7 }

   xdsl2LConfProfPsdMaskUs   OBJECT-TYPE
      SYNTAX      Xdsl2PsdMaskUs
      MAX-ACCESS  read-create
      STATUS      current
      DESCRIPTION
        "The upstream PSD mask applicable at the U-R2 reference
         point.

        This parameter is used only for G.992.5 and it may impose PSD
        restrictions (breakpoints) in addition to the Limit PSD mask
        defined in G.992.5.
        This is a string of 16 pairs of values in the following
        structure:
        Octets 0+1 - Index of 1st sub-carrier used in the context
                     of a first breakpoint.
        Octet 2    - The PSD reduction for the sub-carrier indicated in
                     octets 0 and 1.
        Octets 3-5 - Same, for a 2nd breakpoint.
        Octets 6-8 - Same, for a 3rd breakpoint.
        This architecture continues until octets 9-47, which are
        associated with a 16th breakpoint.
        Each subcarrier index is an unsigned number in the range 1 and
        NSCus.  Each PSD reduction value is in the range 0 (0dBm/Hz) to
        255 (-127.5dBm/Hz) with steps of 0.5dBm/Hz.  Valid values are
        in the range 0 to 190 (0 to -95dBm/Hz).
        When the number of breakpoints is less than 16, all remaining
        octets are set to the value 0.  Note that the content of this
        object should be correlated with the sub-carriers mask and with
        the RFI setup. "
      REFERENCE    "ITU-T G.997.1, paragraph 7.3.1.2"
        ::= { xdsl2LineConfProfModeSpecEntry 8 }

   xdsl2LConfProfPsdMaskSelectUs  OBJECT-TYPE
      SYNTAX      Unsigned32(1..9)
      MAX-ACCESS  read-create
      STATUS      current
      DESCRIPTION
        "The selected upstream PSD mask.  This parameter is used only
         for annexes J and M of G.992.3 and G.992.5, and the same
         selection is used for all relevant enabled bits in
         xdsl2LConfProfAtuTransSysEna. "
      REFERENCE    "ITU-T G.997.1 (amendment 1), 7.3.1.10"
      DEFVAL       { 1 }
       ::= { xdsl2LineConfProfModeSpecEntry 9 }

   xdsl2LConfProfModeSpecRowStatus  OBJECT-TYPE
      SYNTAX      RowStatus
      MAX-ACCESS  read-create
      STATUS      current
      DESCRIPTION

         "This object is used to create a new row or to modify or
         delete an existing row in this table.

         A profile is activated by setting this object to 'active'.
         When 'active' is set, the system will validate the profile.
         Profile modification is prohibited while this object is set
         to 'active'.

         Before a profile can be deleted or taken out of service
         (by setting this object to 'destroy' or 'notInService'),
         it must be first unreferenced from all associated
         templates."

      ::= { xdsl2LineConfProfModeSpecEntry 10 }

   ------------------------------------------------
   --          xdsl2ChConfProfileTable           --
   ------------------------------------------------
   xdsl2ChConfProfileTable  OBJECT-TYPE
      SYNTAX      SEQUENCE  OF  Xdsl2ChConfProfileEntry
      MAX-ACCESS  not-accessible
      STATUS      current
      DESCRIPTION
         "The table xdsl2ChConfProfileTable contains DSL channel
          profile configuration.

          Entries in this table MUST be maintained in a
          persistent manner."
      ::= { xdsl2ProfileChannel 1 }

   xdsl2ChConfProfileEntry  OBJECT-TYPE
      SYNTAX      Xdsl2ChConfProfileEntry
      MAX-ACCESS  not-accessible
      STATUS      current
      DESCRIPTION
         "The table xdsl2ChConfProfileTable contains DSL channel
          profile configuration.
          A default profile with an index of 'DEFVAL' will
          always exist and its parameters will be set to vendor-specific
          values, unless otherwise specified in this document"
      INDEX  { xdsl2ChConfProfProfileName }
      ::= { xdsl2ChConfProfileTable 1 }

   Xdsl2ChConfProfileEntry  ::=
      SEQUENCE {
         xdsl2ChConfProfProfileName          SnmpAdminString,
         xdsl2ChConfProfMinDataRateDs        Unsigned32,
         xdsl2ChConfProfMinDataRateUs        Unsigned32,
         xdsl2ChConfProfMinResDataRateDs     Unsigned32,
         xdsl2ChConfProfMinResDataRateUs     Unsigned32,
         xdsl2ChConfProfMaxDataRateDs        Unsigned32,
         xdsl2ChConfProfMaxDataRateUs        Unsigned32,
         xdsl2ChConfProfMinDataRateLowPwrDs  Unsigned32,
         xdsl2ChConfProfMaxDelayDs           Unsigned32,
         xdsl2ChConfProfMaxDelayUs           Unsigned32,
         xdsl2ChConfProfMinProtectionDs      Xdsl2SymbolProtection,
         xdsl2ChConfProfMinProtectionUs      Xdsl2SymbolProtection,
         xdsl2ChConfProfMaxBerDs             Xdsl2MaxBer,
         xdsl2ChConfProfMaxBerUs             Xdsl2MaxBer,
         xdsl2ChConfProfUsDataRateDs         Unsigned32,
         xdsl2ChConfProfDsDataRateDs         Unsigned32,
         xdsl2ChConfProfUsDataRateUs         Unsigned32,
         xdsl2ChConfProfDsDataRateUs         Unsigned32,
         xdsl2ChConfProfImaEnabled           TruthValue,
         xdsl2ChConfProfRowStatus            RowStatus
      }

   xdsl2ChConfProfProfileName  OBJECT-TYPE
      SYNTAX      SnmpAdminString (SIZE(1..32))
      MAX-ACCESS  not-accessible
      STATUS      current
      DESCRIPTION
         "This object identifies a row in this table."
      ::= { xdsl2ChConfProfileEntry 1 }

   xdsl2ChConfProfMinDataRateDs  OBJECT-TYPE
      SYNTAX      Unsigned32(0..200000000)
      UNITS       "bits/second"
      MAX-ACCESS  read-create
      STATUS      current
      DESCRIPTION
         "Minimum Data Rate on Downstream direction.  The minimum net
          data rate for the bearer channel, coded in bit/s."
      REFERENCE    "ITU-T G.997.1, paragraph 7.3.2.1"
      ::= { xdsl2ChConfProfileEntry 2 }

   xdsl2ChConfProfMinDataRateUs  OBJECT-TYPE
      SYNTAX      Unsigned32(0..200000000)
      UNITS       "bits/second"
      MAX-ACCESS  read-create
      STATUS      current
      DESCRIPTION
         "Minimum Data Rate on Upstream direction.  The minimum net data
          rate for the bearer channel, coded in bit/s."
      REFERENCE    "ITU-T G.997.1, paragraph 7.3.2.1"
      ::= { xdsl2ChConfProfileEntry 3 }

   xdsl2ChConfProfMinResDataRateDs  OBJECT-TYPE
      SYNTAX      Unsigned32(0..200000000)
      UNITS       "bits/second"
      MAX-ACCESS  read-create
      STATUS      current
      DESCRIPTION
         "Minimum Reserved Data Rate on Downstream direction.  The
          minimum reserved net data rate for the bearer channel, coded
          in bit/s.  This parameter is used only if the Rate Adaptation
          Mode in the direction of the bearer channel (i.e.,
          Xdsl2LineConfRaModeDs) is set to DynamicRa."
      REFERENCE    "ITU-T G.997.1, paragraph 7.3.2.1"
      ::= { xdsl2ChConfProfileEntry 4 }

   xdsl2ChConfProfMinResDataRateUs  OBJECT-TYPE
      SYNTAX      Unsigned32(0..200000000)
      UNITS       "bits/second"
      MAX-ACCESS  read-create
      STATUS      current
      DESCRIPTION
         "Minimum Reserved Data Rate on Upstream direction.  The minimum
          reserved net data rate for the bearer channel, coded in
          bit/s.  This parameter is used only if the Rate Adaptation
          Mode in the direction of the bearer channel (i.e.,
          Xdsl2LineConfRaModeUs) is set to DynamicRa."
      REFERENCE    "ITU-T G.997.1, paragraph 7.3.2.1"
      ::= { xdsl2ChConfProfileEntry 5 }

   xdsl2ChConfProfMaxDataRateDs  OBJECT-TYPE
      SYNTAX      Unsigned32(0..200000000)
      UNITS       "bits/second"
      MAX-ACCESS  read-create
      STATUS      current
      DESCRIPTION
         "Maximum Data Rate on Downstream direction.  The maximum net
          data rate for the bearer channel, coded in bit/s."
      REFERENCE    "ITU-T G.997.1, paragraph 7.3.2.1"
      ::= { xdsl2ChConfProfileEntry 6 }

   xdsl2ChConfProfMaxDataRateUs  OBJECT-TYPE
      SYNTAX      Unsigned32(0..200000000)
      UNITS       "bits/second"
      MAX-ACCESS  read-create
      STATUS      current
      DESCRIPTION
         "Maximum Data Rate on Upstream direction.  The maximum net data
          rate for the bearer channel, coded in bit/s."
      REFERENCE    "ITU-T G.997.1, paragraph 7.3.2.1"
      ::= { xdsl2ChConfProfileEntry 7 }

   xdsl2ChConfProfMinDataRateLowPwrDs  OBJECT-TYPE
      SYNTAX      Unsigned32(0..200000000)
      UNITS       "bits/second"
      MAX-ACCESS  read-create
      STATUS      current
      DESCRIPTION
         "Minimum Data Rate in Low Power state on Downstream direction.
          The minimum net data rate for the bearer channel, coded in
          bit/s., during the low power state (L1 in G.992.2, L2 in
          G.992.3)."
      REFERENCE    "ITU-T G.997.1, paragraph 7.3.2.1"
      ::= { xdsl2ChConfProfileEntry 8 }

   xdsl2ChConfProfMaxDelayDs  OBJECT-TYPE
      SYNTAX      Unsigned32(0..63)
      UNITS       "milliseconds"
      MAX-ACCESS  read-create
      STATUS      current
      DESCRIPTION
         "Maximum Interleave Delay on Downstream direction.  The maximum
          one-way interleaving delay introduced by the PMS-TC on
          Downstream direction.  The xTUs shall choose the S (factor)
          and D (depth) values such that the actual one-way interleaving
          delay (Xdsl2ChanStatusActDelay) is as close as possible to,
          but less than or equal to, Xdsl2ChanConfMaxDelayDs.  The
          delay is coded in ms, with the value 0 indicating no delay
          bound is being imposed."
      REFERENCE    "ITU-T G.997.1, paragraph 7.3.2.2"
      ::= { xdsl2ChConfProfileEntry 9 }

   xdsl2ChConfProfMaxDelayUs  OBJECT-TYPE
      SYNTAX      Unsigned32(0..63)
      UNITS       "milliseconds"
      MAX-ACCESS  read-create
      STATUS      current
      DESCRIPTION
         "Maximum Interleave Delay on Upstream direction.  The maximum
          one-way interleaving delay introduced by the PMS-TC on
          Upstream direction.  The xTUs shall choose the S (factor) and
          D (depth) values such that the actual one-way interleaving
          delay (Xdsl2ChanStatusActDelay) is as close as possible to,
          but less than or equal to, Xdsl2ChanConfMaxDelayUs.  The
          delay is coded in ms, with the value 0 indicating no delay
          bound is being imposed."
      REFERENCE    "ITU-T G.997.1, paragraph 7.3.2.2"
      ::= { xdsl2ChConfProfileEntry 10 }

   xdsl2ChConfProfMinProtectionDs  OBJECT-TYPE
      SYNTAX      Xdsl2SymbolProtection
      UNITS       "symbols"
      MAX-ACCESS  read-create
      STATUS      current
      DESCRIPTION
         "Minimum Impulse Noise Protection on Downstream direction.  The
          minimum impulse noise protection for the bearer channel,
          expressed in symbols.  The parameter can take the following
          values: noProtection (i.e., INP not required), halfSymbol
          (i.e., INP length is 1/2 symbol) and 1-16 symbols in steps
          of 1 symbol."
      REFERENCE    "ITU-T G.997.1, paragraph 7.3.2.3"
      DEFVAL       { noProtection }
      ::= { xdsl2ChConfProfileEntry 11 }

   xdsl2ChConfProfMinProtectionUs  OBJECT-TYPE
      SYNTAX      Xdsl2SymbolProtection
      UNITS       "symbols"
      MAX-ACCESS  read-create
      STATUS      current
      DESCRIPTION
         "Minimum Impulse Noise Protection on Upstream direction.  The
          minimum impulse noise protection for the bearer channel,
          expressed in symbols.  The parameter can take the following
          values:
             noProtection (1),
             halfSymbol (2),
             singleSymbol (3),
             twoSymbols (4),
             fourSymbols (5),
             eightSymbols (6),
             sixteenSymbols (7)."
      REFERENCE    "ITU-T G.997.1, paragraph 7.3.2.3"
      DEFVAL       { noProtection }
      ::= { xdsl2ChConfProfileEntry 12 }

   xdsl2ChConfProfMaxBerDs  OBJECT-TYPE
      SYNTAX      Xdsl2MaxBer
      MAX-ACCESS  read-create
      STATUS      current
      DESCRIPTION
         "Maximum Bit Error Ratio on Downstream direction.  The maximum
          bit error ratio for the bearer channel.  The parameter can
          take the following values (for 1E-3, 1E-5 or 1E-7):
             eminus3 (1),
             eminus5 (2),
             eminus7 (3)"
      REFERENCE    "ITU-T G.997.1, paragraph 7.3.2.4"
      DEFVAL       { eminus5 }
     ::= { xdsl2ChConfProfileEntry 13 }

   xdsl2ChConfProfMaxBerUs  OBJECT-TYPE
      SYNTAX      Xdsl2MaxBer
      MAX-ACCESS  read-create
      STATUS      current
      DESCRIPTION
         "Maximum Bit Error Ratio on Upstream direction.  The maximum
          bit error ratio for the bearer channel.  The parameter can
          take the following values (for 1E-3, 1E-5 or 1E-7):
             eminus3 (1),
             eminus5 (2),
             eminus7 (3)"
      REFERENCE    "ITU-T G.997.1, paragraph 7.3.2.4"
      DEFVAL       { eminus5 }
      ::= { xdsl2ChConfProfileEntry 14 }

   xdsl2ChConfProfUsDataRateDs  OBJECT-TYPE
      SYNTAX      Unsigned32(0..200000000)
      UNITS       "bits/second"
      MAX-ACCESS  read-create
      STATUS      current
      DESCRIPTION
         "Data Rate Threshold Up shift for downstream direction.  An
          'Up-shift rate change' event is triggered when the actual
          downstream data rate exceeds, by more than the threshold, the
          data rate at the last entry into Showtime.  The parameter is
          coded in bit/s."
      REFERENCE    "ITU-T G.997.1, paragraph 7.3.2.6"
      ::= { xdsl2ChConfProfileEntry 15 }

   xdsl2ChConfProfDsDataRateDs  OBJECT-TYPE
      SYNTAX      Unsigned32(0..200000000)
      UNITS       "bits/second"
      MAX-ACCESS  read-create
      STATUS      current
      DESCRIPTION
         "Data Rate Threshold Downshift for downstream direction.  A
          'Down-shift rate change' event is triggered when the actual
          downstream data rate is below the data rate at the last entry
          into Showtime, by more than the threshold.  The parameter is
          coded in bit/s."
      REFERENCE    "ITU-T G.997.1, paragraph 7.3.2.6"
      ::= { xdsl2ChConfProfileEntry 16 }

   xdsl2ChConfProfUsDataRateUs  OBJECT-TYPE
      SYNTAX      Unsigned32(0..200000000)
      UNITS       "bits/second"
      MAX-ACCESS  read-create
      STATUS      current
      DESCRIPTION
         "Data Rate Threshold Up shift for upstream direction.  An
          'Up-shift rate change' event is triggered when the actual
          upstream data rate exceeds, by more than the threshold, the
          data rate at the last entry into Showtime.  The parameter is
          coded in bit/s."
      REFERENCE    "ITU-T G.997.1, paragraph 7.3.2.6"
      ::= { xdsl2ChConfProfileEntry 17 }

   xdsl2ChConfProfDsDataRateUs  OBJECT-TYPE
      SYNTAX      Unsigned32(0..200000000)
      UNITS       "bits/second"
      MAX-ACCESS  read-create
      STATUS      current
      DESCRIPTION
         "Data Rate Threshold Downshift for upstream direction.  A
          'Down-shift rate change' event is triggered when the actual
          upstream data rate is below the data rate at the last entry
          into Showtime, by more than the threshold.  The parameter is
          coded in bit/s."
      REFERENCE    "ITU-T G.997.1, paragraph 7.3.2.6"
      ::= { xdsl2ChConfProfileEntry 18 }

   xdsl2ChConfProfImaEnabled  OBJECT-TYPE
      SYNTAX      TruthValue
      MAX-ACCESS  read-create
      STATUS      current
      DESCRIPTION
         "IMA Mode Enable.  The parameter enables the IMA operation mode
          in the ATM Data Path.  Relevant only if the channel is of ATM
          Data Path.  When in 'enable' state, the ATM data path should
          comply with the requirements for IMA transmission."
      REFERENCE    "ITU-T G.997.1, paragraph 7.3.4.1"
      DEFVAL       { false }
    ::= { xdsl2ChConfProfileEntry 19 }

   xdsl2ChConfProfRowStatus  OBJECT-TYPE
      SYNTAX      RowStatus
      MAX-ACCESS  read-create
      STATUS      current
      DESCRIPTION
         "This object is used to create a new row or to modify or
         delete an existing row in this table.

         A profile is activated by setting this object to 'active'.
         When 'active' is set, the system will validate the profile.
         Profile modification is prohibited while this object is set
         to 'active'.
         Before a profile can be deleted or taken out of service
         (by setting this object to 'destroy' or 'notInService'),
         it must be first unreferenced from all associated
         templates."
      ::= { xdsl2ChConfProfileEntry 20 }

   ------------------------------------------------
   --        xdsl2LineAlarmConfTemplateTable          --
   ------------------------------------------------
   xdsl2LineAlarmConfTemplateTable  OBJECT-TYPE
      SYNTAX      SEQUENCE  OF  Xdsl2LineAlarmConfTemplateEntry
      MAX-ACCESS  not-accessible
      STATUS      current
      DESCRIPTION
         "The table xdsl2LineAlarConfTemplateTable contains DSL
         line alarm configuration template.

          Entries in this table MUST be maintained in a
          persistent manner."
      ::= { xdsl2ProfileAlarmConf 1 }

   xdsl2LineAlarmConfTemplateEntry  OBJECT-TYPE
      SYNTAX      Xdsl2LineAlarmConfTemplateEntry
      MAX-ACCESS  not-accessible
      STATUS      current
      DESCRIPTION
         "The table xdsl2LineAlarmConfTemplateTable contains DSL
         line PM thresholds template.
         A default template with an index of 'DEFVAL' will
         always exist and its parameters will be set to vendor
         specific values, unless otherwise specified in this
         document"
      INDEX  { xdsl2LAlarmConfTempTemplateName }
      ::= { xdsl2LineAlarmConfTemplateTable 1 }

   Xdsl2LineAlarmConfTemplateEntry  ::=
      SEQUENCE {
         xdsl2LAlarmConfTempTemplateName      SnmpAdminString,
         xdsl2LAlarmConfTempLineProfile       SnmpAdminString,
         xdsl2LAlarmConfTempChan1ConfProfile  SnmpAdminString,
         xdsl2LAlarmConfTempChan2ConfProfile  SnmpAdminString,
         xdsl2LAlarmConfTempChan3ConfProfile  SnmpAdminString,
         xdsl2LAlarmConfTempChan4ConfProfile  SnmpAdminString,
         xdsl2LAlarmConfTempRowStatus         RowStatus
      }

   xdsl2LAlarmConfTempTemplateName  OBJECT-TYPE
      SYNTAX      SnmpAdminString (SIZE(1..32))
      MAX-ACCESS  not-accessible
      STATUS      current
      DESCRIPTION
         "This object identifies a row in this table."
      ::= { xdsl2LineAlarmConfTemplateEntry 1 }

   xdsl2LAlarmConfTempLineProfile  OBJECT-TYPE
      SYNTAX      SnmpAdminString (SIZE(1..32))
      MAX-ACCESS  read-create
      STATUS      current
      DESCRIPTION
         "The value of this object identifies the row in the DSL Line
          Thresholds Configuration Profile Table
          (xdsl2LineAlarmConfProfileTable) that applies to this line."
      REFERENCE    "DSL Forum TR-90, paragraph 5.4.1"
      DEFVAL       { "DEFVAL" }
      ::= { xdsl2LineAlarmConfTemplateEntry 2 }

   xdsl2LAlarmConfTempChan1ConfProfile  OBJECT-TYPE
      SYNTAX      SnmpAdminString (SIZE(1..32))
      MAX-ACCESS  read-create
      STATUS      current
      DESCRIPTION
         "The value of this object identifies the row in the DSL
          Channel Thresholds Configuration Profile Table
          (xdsl2ChAlarmConfProfileTable) that applies for DSL
          bearer channel #1.  The channel profile name specified here
          must match the name of an existing row in the
          xdsl2ChAlarmConfProfileTable table."
      REFERENCE    "DSL Forum TR-90, paragraph 5.4.1"
      DEFVAL       { "DEFVAL" }
      ::= { xdsl2LineAlarmConfTemplateEntry 3 }

   xdsl2LAlarmConfTempChan2ConfProfile  OBJECT-TYPE
      SYNTAX      SnmpAdminString (SIZE(0..32))
      MAX-ACCESS  read-create
      STATUS      current
      DESCRIPTION
         "The value of this object identifies the row in the DSL
          Channel Thresholds Configuration Profile Table
          (xdsl2ChAlarmConfProfileTable) that applies for DSL
          bearer channel #2.  The channel profile name specified here
          must match the name of an existing row in the
          xdsl2ChAlarmConfProfileTable table.  If the channel is unused,
          then the object is set to a zero length string."
      REFERENCE    "DSL Forum TR-90, paragraph 5.4.1"
      DEFVAL       { "" }
      ::= { xdsl2LineAlarmConfTemplateEntry 4 }

   xdsl2LAlarmConfTempChan3ConfProfile  OBJECT-TYPE
      SYNTAX      SnmpAdminString (SIZE(0..32))
      MAX-ACCESS  read-create
      STATUS      current
      DESCRIPTION
         "The value of this object identifies the row in the DSL
          Channel Thresholds Configuration Profile Table
          (xdsl2ChAlarmConfProfileTable) that applies for DSL
          bearer channel #3.  The channel profile name specified here
          must match the name of an existing row in the
          xdsl2ChAlarmConfProfileTable table.
          This object may be set to a non-zero length string only if
          xdsl2LAlarmConfTempChan2ConfProfile contains a non-zero
          length string."
      REFERENCE    "DSL Forum TR-90, paragraph 5.4.1"
      DEFVAL       { "" }
      ::= { xdsl2LineAlarmConfTemplateEntry 5 }

   xdsl2LAlarmConfTempChan4ConfProfile  OBJECT-TYPE
      SYNTAX      SnmpAdminString (SIZE(0..32))
      MAX-ACCESS  read-create
      STATUS      current
      DESCRIPTION
         "The value of this object identifies the row in the DSL
          Channel Thresholds Configuration Profile Table
          (xdsl2ChAlarmConfProfileTable) that applies for DSL
          bearer channel #4.  The channel profile name specified here
          must match the name of an existing row in the
          xdsl2ChAlarmConfProfileTable table.
          This object may be set to a non-zero length string only if
          xdsl2LAlarmConfTempChan3ConfProfile contains a non-zero
          length string."
      REFERENCE    "DSL Forum TR-90, paragraph 5.4.1"
      DEFVAL       { "" }
      ::= { xdsl2LineAlarmConfTemplateEntry 6 }

   xdsl2LAlarmConfTempRowStatus  OBJECT-TYPE
      SYNTAX      RowStatus
      MAX-ACCESS  read-create
      STATUS      current
      DESCRIPTION
         "This object is used to create a new row or to modify or
         delete an existing row in this table.

         A template is activated by setting this object to 'active'.
         When 'active' is set, the system will validate the template.
         Template modification is prohibited while this object is set
         to 'active'.
         Before a template can be deleted or taken out of service
         (by setting this object to 'destroy' or 'notInService'),
         it must be first unreferenced from all associated
         lines."
      ::= { xdsl2LineAlarmConfTemplateEntry 7 }

   ------------------------------------------------
   --      xdsl2LineAlarmConfProfileTable        --
   ------------------------------------------------

   xdsl2LineAlarmConfProfileTable  OBJECT-TYPE
        SYNTAX      SEQUENCE  OF  Xdsl2LineAlarmConfProfileEntry
        MAX-ACCESS  not-accessible
        STATUS      current
        DESCRIPTION
         "The table xdsl2LineAlarmConfProfileTable contains DSL
         line PM thresholds profiles.

          Entries in this table MUST be maintained in a
          persistent manner."
        ::= { xdsl2ProfileAlarmConf 2 }

   xdsl2LineAlarmConfProfileEntry  OBJECT-TYPE
        SYNTAX      Xdsl2LineAlarmConfProfileEntry
        MAX-ACCESS  not-accessible
        STATUS      current
        DESCRIPTION
         "The table xdsl2LineAlarmConfProfileTable contains DSL
         line PM thresholds profiles.
         A default profile with an index of 'DEFVAL' will
         always exist and its parameters will be set to vendor
         specific values, unless otherwise specified in this
         document"
        INDEX  { xdsl2LineAlarmConfProfileName }
        ::= { xdsl2LineAlarmConfProfileTable 1 }

   Xdsl2LineAlarmConfProfileEntry ::=
        SEQUENCE {
        xdsl2LineAlarmConfProfileName                SnmpAdminString,
        xdsl2LineAlarmConfProfileXtucThresh15MinFecs
                                             HCPerfIntervalThreshold,
        xdsl2LineAlarmConfProfileXtucThresh15MinEs
                                             HCPerfIntervalThreshold,
        xdsl2LineAlarmConfProfileXtucThresh15MinSes
                                              HCPerfIntervalThreshold,
        xdsl2LineAlarmConfProfileXtucThresh15MinLoss
                                              HCPerfIntervalThreshold,
        xdsl2LineAlarmConfProfileXtucThresh15MinUas
                                              HCPerfIntervalThreshold,
        xdsl2LineAlarmConfProfileXturThresh15MinFecs
                                              HCPerfIntervalThreshold,
        xdsl2LineAlarmConfProfileXturThresh15MinEs
                                              HCPerfIntervalThreshold,
        xdsl2LineAlarmConfProfileXturThresh15MinSes
                                              HCPerfIntervalThreshold,
        xdsl2LineAlarmConfProfileXturThresh15MinLoss
                                              HCPerfIntervalThreshold,
        xdsl2LineAlarmConfProfileXturThresh15MinUas
                                              HCPerfIntervalThreshold,

        xdsl2LineAlarmConfProfileThresh15MinFailedFullInt   Unsigned32,
        xdsl2LineAlarmConfProfileThresh15MinFailedShrtInt   Unsigned32,

        xdsl2LineAlarmConfProfileRowStatus                   RowStatus
        }

   xdsl2LineAlarmConfProfileName  OBJECT-TYPE
        SYNTAX      SnmpAdminString (SIZE(1..32))
        MAX-ACCESS  not-accessible
        STATUS      current
        DESCRIPTION
        "This object identifies a row in this table."
        ::= { xdsl2LineAlarmConfProfileEntry 1 }

   xdsl2LineAlarmConfProfileXtucThresh15MinFecs  OBJECT-TYPE
        SYNTAX      HCPerfIntervalThreshold
        UNITS       "seconds"
        MAX-ACCESS  read-create
        STATUS      current
        DESCRIPTION
        "A threshold for the xdsl2PMLCurr15MFecs counter,
        when xdsl2PMLCurrUnit is xtuc {1}.
        The value 0 means that no threshold is specified for the
        associated counter."
      REFERENCE    "ITU-T G.997.1, paragraph 7.3.1"
      DEFVAL       { 0 }
        ::= { xdsl2LineAlarmConfProfileEntry 2 }

   xdsl2LineAlarmConfProfileXtucThresh15MinEs  OBJECT-TYPE
        SYNTAX      HCPerfIntervalThreshold
        UNITS       "seconds"
        MAX-ACCESS  read-create
        STATUS      current
        DESCRIPTION
        "A threshold for the xdsl2PMLCurr15MEs counter,
        when xdsl2PMLCurrUnit is xtuc {1}.
        The value 0 means that no threshold is specified for the
        associated counter."
      REFERENCE    "ITU-T G.997.1, paragraph 7.3.1"
      DEFVAL       { 0 }
        ::= { xdsl2LineAlarmConfProfileEntry 3 }

   xdsl2LineAlarmConfProfileXtucThresh15MinSes  OBJECT-TYPE
        SYNTAX      HCPerfIntervalThreshold
        UNITS       "seconds"
        MAX-ACCESS  read-create
        STATUS      current
        DESCRIPTION
        "A threshold for the xdsl2PMLCurr15MSes counter,
        when xdsl2PMLCurrUnit is xtuc {1}.
        The value 0 means that no threshold is specified for the
        associated counter."
      REFERENCE    "ITU-T G.997.1, paragraph 7.3.1"
      DEFVAL       { 0 }
        ::= { xdsl2LineAlarmConfProfileEntry 4 }

   xdsl2LineAlarmConfProfileXtucThresh15MinLoss  OBJECT-TYPE
        SYNTAX      HCPerfIntervalThreshold
        UNITS       "seconds"
        MAX-ACCESS  read-create
        STATUS      current
        DESCRIPTION
        "A threshold for the xdsl2PMLCurr15MLoss counter,
        when xdsl2PMLCurrUnit is xtuc {1}.
        The value 0 means that no threshold is specified for the
        associated counter."
      REFERENCE    "ITU-T G.997.1, paragraph 7.3.1"
      DEFVAL       { 0 }
        ::= { xdsl2LineAlarmConfProfileEntry 5 }

   xdsl2LineAlarmConfProfileXtucThresh15MinUas  OBJECT-TYPE
        SYNTAX      HCPerfIntervalThreshold
        UNITS       "seconds"
        MAX-ACCESS  read-create
        STATUS      current
        DESCRIPTION
        "A threshold for the xdsl2PMLCurr15MUas counter,
        when xdsl2PMLCurrUnit is xtuc {1}.
        The value 0 means that no threshold is specified for the
        associated counter."
      REFERENCE    "ITU-T G.997.1, paragraph 7.3.1"
      DEFVAL       { 0 }
        ::= { xdsl2LineAlarmConfProfileEntry 6 }

   xdsl2LineAlarmConfProfileXturThresh15MinFecs  OBJECT-TYPE
        SYNTAX      HCPerfIntervalThreshold
        UNITS       "seconds"
        MAX-ACCESS  read-create
        STATUS      current
        DESCRIPTION
        "A threshold for the xdsl2PMLCurr15MFecs counter,
        when xdsl2PMLCurrUnit is xtur {2}.
        The value 0 means that no threshold is specified for the
        associated counter."
      REFERENCE    "ITU-T G.997.1, paragraph 7.3.1"
      DEFVAL       { 0 }
        ::= { xdsl2LineAlarmConfProfileEntry 7 }

   xdsl2LineAlarmConfProfileXturThresh15MinEs  OBJECT-TYPE
        SYNTAX      HCPerfIntervalThreshold
        UNITS       "seconds"
        MAX-ACCESS  read-create
        STATUS      current
        DESCRIPTION
        "A threshold for the xdsl2PMLCurr15MEs counter,
        when xdsl2PMLCurrUnit is xtur {2}.
        The value 0 means that no threshold is specified for the
        associated counter."
      REFERENCE    "ITU-T G.997.1, paragraph 7.3.1"
      DEFVAL       { 0 }
        ::= { xdsl2LineAlarmConfProfileEntry 8 }

   xdsl2LineAlarmConfProfileXturThresh15MinSes  OBJECT-TYPE
        SYNTAX      HCPerfIntervalThreshold
        UNITS       "seconds"
        MAX-ACCESS  read-create
        STATUS      current
        DESCRIPTION
        "A threshold for the xdsl2PMLCurr15MSes counter,
        when xdsl2PMLCurrUnit is xtur {2}.
        The value 0 means that no threshold is specified for the
        associated counter."
      REFERENCE    "ITU-T G.997.1, paragraph 7.3.1"
      DEFVAL       { 0 }
        ::= { xdsl2LineAlarmConfProfileEntry 9 }

   xdsl2LineAlarmConfProfileXturThresh15MinLoss  OBJECT-TYPE
        SYNTAX      HCPerfIntervalThreshold
        UNITS       "seconds"
        MAX-ACCESS  read-create
        STATUS      current
        DESCRIPTION
        "A threshold for the xdsl2PMLCurr15MLoss counter,
        when xdsl2PMLCurrUnit is xtur {2}.
        The value 0 means that no threshold is specified for the
        associated counter."
      REFERENCE    "ITU-T G.997.1, paragraph 7.3.1"
      DEFVAL       { 0 }
        ::= { xdsl2LineAlarmConfProfileEntry 10 }

   xdsl2LineAlarmConfProfileXturThresh15MinUas  OBJECT-TYPE
        SYNTAX      HCPerfIntervalThreshold
        UNITS       "seconds"
        MAX-ACCESS  read-create
        STATUS      current
        DESCRIPTION
        "A threshold for the xdsl2PMLCurr15MUas counter,
        when xdsl2PMLCurrUnit is xtur {2}.
        The value 0 means that no threshold is specified for the
        associated counter."
      REFERENCE    "ITU-T G.997.1, paragraph 7.3.1"
      DEFVAL       { 0 }
        ::= { xdsl2LineAlarmConfProfileEntry 11 }

   xdsl2LineAlarmConfProfileThresh15MinFailedFullInt  OBJECT-TYPE
        SYNTAX      Unsigned32
        MAX-ACCESS  read-create
        STATUS      current
        DESCRIPTION
        "A threshold for the xdsl2PMLCurrInit15MfailedFullInits
        counter.
        The value 0 means that no threshold is specified for the
        associated counter."
      REFERENCE    "ITU-T G.997.1, paragraph 7.3.1"
      DEFVAL       { 0 }
        ::= { xdsl2LineAlarmConfProfileEntry 12 }

   xdsl2LineAlarmConfProfileThresh15MinFailedShrtInt  OBJECT-TYPE
        SYNTAX      Unsigned32
        MAX-ACCESS  read-create
        STATUS      current
        DESCRIPTION
        "A threshold for the xdsl2PMLCurrInit15MFailedShortInits
        counter.
        The value 0 means that no threshold is specified for the
        associated counter."
      REFERENCE    "ITU-T G.997.1, paragraph 7.3.1"
      DEFVAL       { 0 }
        ::= { xdsl2LineAlarmConfProfileEntry 13 }

   xdsl2LineAlarmConfProfileRowStatus  OBJECT-TYPE
        SYNTAX      RowStatus
        MAX-ACCESS  read-create
        STATUS      current
        DESCRIPTION
         "This object is used to create a new row or to modify or
         delete an existing row in this table.

         A profile is activated by setting this object to 'active'.
         When 'active' is set, the system will validate the profile.
         Profile modification is prohibited while this object is set
         to 'active'.

         Before a profile can be deleted or taken out of service
         (by setting this object to 'destroy' or 'notInService'),
         it must be first unreferenced from all associated
         templates."
        ::= { xdsl2LineAlarmConfProfileEntry 14 }


   ------------------------------------------------
   --      xdsl2ChAlarmConfProfileTable        --
   ------------------------------------------------

   xdsl2ChAlarmConfProfileTable  OBJECT-TYPE
        SYNTAX      SEQUENCE  OF  Xdsl2ChAlarmConfProfileEntry
        MAX-ACCESS  not-accessible
        STATUS      current
        DESCRIPTION
         "The table xdsl2ChAlarmConfProfileTable contains DSL
         channel PM thresholds profiles.

          Entries in this table MUST be maintained in a
          persistent manner."
        ::= { xdsl2ProfileAlarmConf 3 }

   xdsl2ChAlarmConfProfileEntry  OBJECT-TYPE
        SYNTAX      Xdsl2ChAlarmConfProfileEntry
        MAX-ACCESS  not-accessible
        STATUS      current
        DESCRIPTION
         "The table xdsl2ChAlarmConfProfileTable contains DSL
         channel PM thresholds profiles.
         A default profile with an index of 'DEFVAL' will
         always exist and its parameters will be set to vendor-specific
         values, unless otherwise specified in this document"
        INDEX  { xdsl2ChAlarmConfProfileName }
        ::= { xdsl2ChAlarmConfProfileTable 1 }

   Xdsl2ChAlarmConfProfileEntry ::=
        SEQUENCE {
        xdsl2ChAlarmConfProfileName
                                                        SnmpAdminString,
        xdsl2ChAlarmConfProfileXtucThresh15MinCodingViolations
                                                        Unsigned32,
        xdsl2ChAlarmConfProfileXtucThresh15MinCorrected Unsigned32,
        xdsl2ChAlarmConfProfileXturThresh15MinCodingViolations
                                                        Unsigned32,
        xdsl2ChAlarmConfProfileXturThresh15MinCorrected Unsigned32,
        xdsl2ChAlarmConfProfileRowStatus                RowStatus
        }

   xdsl2ChAlarmConfProfileName  OBJECT-TYPE
        SYNTAX      SnmpAdminString (SIZE(1..32))
        MAX-ACCESS  not-accessible
        STATUS      current
        DESCRIPTION
        "This object identifies a row in this table."
        ::= { xdsl2ChAlarmConfProfileEntry 1 }

   xdsl2ChAlarmConfProfileXtucThresh15MinCodingViolations OBJECT-TYPE
        SYNTAX      Unsigned32
        MAX-ACCESS  read-create
        STATUS      current
        DESCRIPTION
        "A threshold for the xdsl2PMChCurr15MCodingViolations
        counter, when xdsl2PMChCurrUnit is xtuc {1}.
        The value 0 means that no threshold is specified for the
        associated counter."
      REFERENCE    "ITU-T G.997.1, paragraph 7.3.2"
      DEFVAL       { 0 }
        ::= { xdsl2ChAlarmConfProfileEntry 2 }

   xdsl2ChAlarmConfProfileXtucThresh15MinCorrected  OBJECT-TYPE
        SYNTAX      Unsigned32
        MAX-ACCESS  read-create
        STATUS      current
        DESCRIPTION
        "A threshold for the xdsl2PMChCurr15MCorrectedBlocks
        counter, when xdsl2PMChCurrUnit is xtuc {1}.
        The value 0 means that no threshold is specified for the
        associated counter."
      REFERENCE    "ITU-T G.997.1, paragraph 7.3.2"
      DEFVAL       { 0 }
        ::= { xdsl2ChAlarmConfProfileEntry 3 }

   xdsl2ChAlarmConfProfileXturThresh15MinCodingViolations  OBJECT-TYPE
        SYNTAX      Unsigned32
        MAX-ACCESS  read-create
        STATUS      current
        DESCRIPTION
        "A threshold for the xdsl2PMChCurr15MCodingViolations
        counter, when xdsl2PMChCurrUnit is xtur {2}.
        The value 0 means that no threshold is specified for the
        associated counter."
      REFERENCE    "ITU-T G.997.1, paragraph 7.3.2"
      DEFVAL       { 0 }
        ::= { xdsl2ChAlarmConfProfileEntry 4 }

   xdsl2ChAlarmConfProfileXturThresh15MinCorrected  OBJECT-TYPE
        SYNTAX      Unsigned32
        MAX-ACCESS  read-create
        STATUS      current
        DESCRIPTION
        "A threshold for the xdsl2PMChCurr15MCorrectedBlocks
        counter, when xdsl2PMChCurrUnit is xtur {2}.
        The value 0 means that no threshold is specified for the
        associated counter."
      REFERENCE    "ITU-T G.997.1, paragraph 7.3.2"
      DEFVAL       { 0 }
        ::= { xdsl2ChAlarmConfProfileEntry 5 }

   xdsl2ChAlarmConfProfileRowStatus  OBJECT-TYPE
        SYNTAX      RowStatus
        MAX-ACCESS  read-create
        STATUS      current
        DESCRIPTION
         "This object is used to create a new row or to modify or
         delete an existing row in this table.

         A profile is activated by setting this object to 'active'.
         When 'active' is set, the system will validate the profile.
         Profile modification is prohibited while this object is set
         to 'active'.

         Before a profile can be deleted or taken out of service
         (by setting this object to 'destroy' or 'notInService'),
         it must be first unreferenced from all associated
         templates."
        ::= { xdsl2ChAlarmConfProfileEntry 6 }

   ------------------------------------------------
   --          PM line current counters          --
   ------------------------------------------------
   xdsl2PMLineCurrTable  OBJECT-TYPE
      SYNTAX      SEQUENCE  OF  Xdsl2PMLineCurrEntry
      MAX-ACCESS  not-accessible
      STATUS      current
      DESCRIPTION
         "The table xdsl2PMLineCurrTable contains current Performance
          Monitoring results of DSL line.  The objects in this table
          are NOT persistent."
      ::= { xdsl2PMLine 1 }

   xdsl2PMLineCurrEntry  OBJECT-TYPE
      SYNTAX      Xdsl2PMLineCurrEntry
      MAX-ACCESS  not-accessible
      STATUS      current
      DESCRIPTION
         "The table xdsl2PMLineCurrTable contains current Performance
          Monitoring results of DSL line.
          The index of this table is an interface index where the
          interface has an ifType of vdsl2(xxx) and the termination
          unit."
      INDEX  { ifIndex, xdsl2PMLCurrUnit }
      ::= { xdsl2PMLineCurrTable 1 }

   Xdsl2PMLineCurrEntry  ::=
      SEQUENCE {
         xdsl2PMLCurrUnit                    Xdsl2Unit,
         xdsl2PMLCurrValidIntervals          Unsigned32,
         xdsl2PMLCurrInvalidIntervals        Unsigned32,
         xdsl2PMLCurr15MTimeElapsed          HCPerfTimeElapsed,
         xdsl2PMLCurr15MFecs                 Counter32,
         xdsl2PMLCurr15MEs                   Counter32,
         xdsl2PMLCurr15MSes                  Counter32,
         xdsl2PMLCurr15MLoss                 Counter32,
         xdsl2PMLCurr15MUas                  Counter32,
         xdsl2PMLCurr1DayValidIntervals      Unsigned32,
         xdsl2PMLCurr1DayInvalidIntervals    Unsigned32,
         xdsl2PMLCurr1DayTimeElapsed         HCPerfTimeElapsed,
         xdsl2PMLCurr1DayFecs                Counter32,
         xdsl2PMLCurr1DayEs                  Counter32,
         xdsl2PMLCurr1DaySes                 Counter32,
         xdsl2PMLCurr1DayLoss                Counter32,
         xdsl2PMLCurr1DayUas                 Counter32
      }

   xdsl2PMLCurrUnit  OBJECT-TYPE
      SYNTAX      Xdsl2Unit
      MAX-ACCESS  not-accessible
      STATUS      current
      DESCRIPTION
         "The termination unit xtuc{1} or xtur{2}."
      ::= { xdsl2PMLineCurrEntry 1 }

   xdsl2PMLCurrValidIntervals  OBJECT-TYPE
      SYNTAX      Unsigned32
      MAX-ACCESS  read-only
      STATUS      current
      DESCRIPTION
         "Valid intervals."
      ::= { xdsl2PMLineCurrEntry 2 }

   xdsl2PMLCurrInvalidIntervals  OBJECT-TYPE
      SYNTAX      Unsigned32
      MAX-ACCESS  read-only
      STATUS      current
      DESCRIPTION
         "Invalid intervals."
      ::= { xdsl2PMLineCurrEntry 3 }

   xdsl2PMLCurr15MTimeElapsed  OBJECT-TYPE
      SYNTAX      HCPerfTimeElapsed
      UNITS       "seconds"
      MAX-ACCESS  read-only
      STATUS      current
      DESCRIPTION
         "Total elapsed seconds in this interval"
      ::= { xdsl2PMLineCurrEntry 4 }

   xdsl2PMLCurr15MFecs  OBJECT-TYPE
      SYNTAX      Counter32
      UNITS       "seconds"
      MAX-ACCESS  read-only
      STATUS      current
      DESCRIPTION
         "Count of seconds during this interval that there was at least
          one FEC correction event for one or more bearer channels in
          this line.  This parameter is inhibited during UAS or SES."
      REFERENCE    "ITU-T G.997.1, paragraph 7.2.1"
      ::= { xdsl2PMLineCurrEntry 5 }

   xdsl2PMLCurr15MEs  OBJECT-TYPE
      SYNTAX      Counter32
      UNITS       "seconds"
      MAX-ACCESS  read-only
      STATUS      current
      DESCRIPTION
         "Count of seconds during this interval that there was:
             xtu-c: CRC-8 >= 1 for one or more bearer channels OR
                    LOS >= 1 OR SEF >=1 OR LPR >= 1
             xtu-r: FEBE >= 1 for one or more bearer channels OR
                    LOS-FE >=1 OR RDI >=1 OR LPR-FE >=1 .
          This parameter is inhibited during UAS."
      REFERENCE    "ITU-T G.997.1, paragraph 7.2.1"
      ::= { xdsl2PMLineCurrEntry 6 }

   xdsl2PMLCurr15MSes  OBJECT-TYPE
      SYNTAX      Counter32
      UNITS       "seconds"
      MAX-ACCESS  read-only
      STATUS      current
      DESCRIPTION
         "Count of seconds during this interval that there was:
             xtu-c: (CRC-8 summed over all bearer channels) >= 18 OR
                    LOS >= 1 OR SEF >= 1 OR LPR >= 1
             xtu-r: (FEBE summed over all bearer channels) >= 18 OR
                    LOS-FE >= 1 OR RDI >= 1 OR LPR-FE >= 1 .
          This parameter is inhibited during UAS."
      REFERENCE    "ITU-T G.997.1, paragraph 7.2.1"
      ::= { xdsl2PMLineCurrEntry 7 }

   xdsl2PMLCurr15MLoss  OBJECT-TYPE
      SYNTAX      Counter32
      UNITS       "seconds"
      MAX-ACCESS  read-only
      STATUS      current
      DESCRIPTION
         "Count of seconds during this interval that there was LOS (or
          LOS-FE for xtu-r)."
      REFERENCE    "ITU-T G.997.1, paragraph 7.2.1"
      ::= { xdsl2PMLineCurrEntry 8 }

   xdsl2PMLCurr15MUas  OBJECT-TYPE
      SYNTAX      Counter32
      UNITS       "seconds"
      MAX-ACCESS  read-only
      STATUS      current
      DESCRIPTION
         "Count of seconds in Unavailability State during this
          interval.  Unavailability begins at the onset of 10
          contiguous severely-errored seconds, and ends at the
          onset of 10 contiguous seconds with no severely-errored
          seconds."
      REFERENCE    "ITU-T G.997.1, paragraph 7.2.1"
      ::= { xdsl2PMLineCurrEntry 9 }

   xdsl2PMLCurr1DayValidIntervals  OBJECT-TYPE
      SYNTAX      Unsigned32
      MAX-ACCESS  read-only
      STATUS      current
      DESCRIPTION
         "Valid intervals."
      ::= { xdsl2PMLineCurrEntry 10 }

   xdsl2PMLCurr1DayInvalidIntervals  OBJECT-TYPE
      SYNTAX      Unsigned32
      MAX-ACCESS  read-only
      STATUS      current
      DESCRIPTION
         "Invalid intervals."
      ::= { xdsl2PMLineCurrEntry 11 }

   xdsl2PMLCurr1DayTimeElapsed  OBJECT-TYPE
      SYNTAX      HCPerfTimeElapsed
      UNITS       "seconds"
      MAX-ACCESS  read-only
      STATUS      current
      DESCRIPTION
         "Total elapsed seconds in this interval."
      ::= { xdsl2PMLineCurrEntry 12 }

   xdsl2PMLCurr1DayFecs  OBJECT-TYPE
      SYNTAX      Counter32
      UNITS       "seconds"
      MAX-ACCESS  read-only
      STATUS      current
      DESCRIPTION
         "Count of seconds during this interval that there was at least
          one FEC correction event for one or more bearer channels in
          this line.  This parameter is inhibited during UAS or SES."
      REFERENCE    "ITU-T G.997.1, paragraph 7.2.1"
      ::= { xdsl2PMLineCurrEntry 13 }

   xdsl2PMLCurr1DayEs  OBJECT-TYPE
      SYNTAX      Counter32
      UNITS       "seconds"
      MAX-ACCESS  read-only
      STATUS      current
      DESCRIPTION
         "Count of seconds during this interval that there was:
             xtu-c: CRC-8 >= 1 for one or more bearer channels OR
                    LOS >= 1 OR SEF >= 1 OR LPR >= 1
             xtu-r: FEBE >= 1 for one or more bearer channels OR
                    LOS-FE >= 1 OR RDI >= 1 OR LPR-FE >= 1.
          This parameter is inhibited during UAS."

      REFERENCE    "ITU-T G.997.1, paragraph 7.2.1"
      ::= { xdsl2PMLineCurrEntry 14 }

   xdsl2PMLCurr1DaySes  OBJECT-TYPE
      SYNTAX      Counter32
      UNITS       "seconds"
      MAX-ACCESS  read-only
      STATUS      current
      DESCRIPTION
         "Count of seconds during this interval that there was:
             xtu-c: (CRC-8 summed over all bearer channels) >= 18 OR
                     LOS >= 1 OR SEF >= 1 OR LPR >= 1
             xtu-r: (FEBE summed over all bearer channels) >= 18 OR
                    LOS-FE >= 1 OR RDI >= 1 OR LPR-FE >= 1
          This parameter is inhibited during UAS."
      REFERENCE    "ITU-T G.997.1, paragraph 7.2.1"
      ::= { xdsl2PMLineCurrEntry 15 }

   xdsl2PMLCurr1DayLoss  OBJECT-TYPE
      SYNTAX      Counter32
      UNITS       "seconds"
      MAX-ACCESS  read-only
      STATUS      current
      DESCRIPTION
         "Count of seconds during this interval that there was LOS (or
          LOS-FE for xtu-r)."
      REFERENCE    "ITU-T G.997.1, paragraph 7.2.1"
      ::= { xdsl2PMLineCurrEntry 16 }

   xdsl2PMLCurr1DayUas  OBJECT-TYPE
      SYNTAX      Counter32
      UNITS       "seconds"
      MAX-ACCESS  read-only
      STATUS      current
      DESCRIPTION
         "Count of seconds in Unavailability State during this interval.
          Unavailability begins at the onset of 10 contiguous severely
          -errored seconds, and ends at the onset of 10 contiguous
          seconds with no severely-errored seconds."
      REFERENCE    "ITU-T G.997.1, paragraph 7.2.1"
      ::= { xdsl2PMLineCurrEntry 17 }


   ------------------------------------------------
   --          PM line init current counters     --
   ------------------------------------------------

   xdsl2PMLineCurrInitTable   OBJECT-TYPE
      SYNTAX      SEQUENCE  OF  Xdsl2PMLineCurrInitEntry
      MAX-ACCESS  not-accessible
      STATUS      current
      DESCRIPTION
         "The table xdsl2PMLineCurrInitTable contains current
          initialization counters of DSL line.  The objects in
          this table are NOT persistent."
      ::= { xdsl2PMLine 2 }

   xdsl2PMLineCurrInitEntry  OBJECT-TYPE
      SYNTAX      Xdsl2PMLineCurrInitEntry
      MAX-ACCESS  not-accessible
      STATUS      current
      DESCRIPTION
         "The table xdsl2PMLineCurrInitTable contains current
          initialization counters of DSL line.
          The index of this table is an interface index where the
          interface has an ifType of vdsl2(xxx) and the termination
          unit."
      INDEX  { ifIndex }
      ::= { xdsl2PMLineCurrInitTable 1 }

   Xdsl2PMLineCurrInitEntry  ::=
      SEQUENCE {
         xdsl2PMLCurrInit15MTimeElapsed          Unsigned32,
         xdsl2PMLCurrInit15MFullInits            Unsigned32,
         xdsl2PMLCurrInit15MFailedFullInits      Unsigned32,
         xdsl2PMLCurrInit15MShortInits           Unsigned32,
         xdsl2PMLCurrInit15MFailedShortInits     Unsigned32,
         xdsl2PMLCurrInit1DayTimeElapsed         Unsigned32,
         xdsl2PMLCurrInit1DayFullInits           Unsigned32,
         xdsl2PMLCurrInit1DayFailedFullInits     Unsigned32,
         xdsl2PMLCurrInit1DayShortInits          Unsigned32,
         xdsl2PMLCurrInit1DayFailedShortInits    Unsigned32
      }

   xdsl2PMLCurrInit15MTimeElapsed  OBJECT-TYPE
      SYNTAX      Unsigned32
      UNITS       "seconds"
      MAX-ACCESS  read-only
      STATUS      current
      DESCRIPTION
         "Total elapsed seconds in this interval."
      ::= { xdsl2PMLineCurrInitEntry 1 }

   xdsl2PMLCurrInit15MFullInits  OBJECT-TYPE
      SYNTAX      Unsigned32
      MAX-ACCESS  read-only
      STATUS      current
      DESCRIPTION
         "Count of full initializations attempted on the line
          (successful and failed) during this interval."
      REFERENCE    "ITU-T G.997.1, paragraph 7.2.1"
      ::= { xdsl2PMLineCurrInitEntry 2 }

   xdsl2PMLCurrInit15MFailedFullInits  OBJECT-TYPE
      SYNTAX      Unsigned32
      MAX-ACCESS  read-only
      STATUS      current
      DESCRIPTION
         "Count of failed full initializations on the line during this
          interval."
      REFERENCE    "ITU-T G.997.1, paragraph 7.2.1"
      ::= { xdsl2PMLineCurrInitEntry 3 }

   xdsl2PMLCurrInit15MShortInits  OBJECT-TYPE
      SYNTAX      Unsigned32
      MAX-ACCESS  read-only
      STATUS      current
      DESCRIPTION
         "Count of short initializations attempted on the line
          (successful and failed) during this interval."
      REFERENCE    "ITU-T G.997.1, paragraph 7.2.1"
      ::= { xdsl2PMLineCurrInitEntry 4 }

   xdsl2PMLCurrInit15MFailedShortInits  OBJECT-TYPE
      SYNTAX      Unsigned32
      MAX-ACCESS  read-only
      STATUS      current
      DESCRIPTION
         "Count of failed short initializations on the line during this
          interval."
      REFERENCE    "ITU-T G.997.1, paragraph 7.2.1"
      ::= { xdsl2PMLineCurrInitEntry 5 }

   xdsl2PMLCurrInit1DayTimeElapsed  OBJECT-TYPE
      SYNTAX      Unsigned32
      UNITS       "seconds"
      MAX-ACCESS  read-only
      STATUS      current
      DESCRIPTION
         "Total elapsed seconds in this interval."
      ::= { xdsl2PMLineCurrInitEntry 6 }

   xdsl2PMLCurrInit1DayFullInits  OBJECT-TYPE
      SYNTAX      Unsigned32
      MAX-ACCESS  read-only
      STATUS      current
      DESCRIPTION
         "Count of full initializations attempted on the line
          (successful and failed) during this interval."
      REFERENCE    "ITU-T G.997.1, paragraph 7.2.1"
      ::= { xdsl2PMLineCurrInitEntry 7 }

   xdsl2PMLCurrInit1DayFailedFullInits  OBJECT-TYPE
      SYNTAX      Unsigned32
      MAX-ACCESS  read-only
      STATUS      current
      DESCRIPTION
         "Count of failed full initializations on the line during this
          interval."
      REFERENCE    "ITU-T G.997.1, paragraph 7.2.1"
      ::= { xdsl2PMLineCurrInitEntry 8 }

   xdsl2PMLCurrInit1DayShortInits  OBJECT-TYPE
      SYNTAX      Unsigned32
      MAX-ACCESS  read-only
      STATUS      current
      DESCRIPTION
         "Count of short initializations attempted on the line
          (successful and failed) during this interval."
      REFERENCE    "ITU-T G.997.1, paragraph 7.2.1"
      ::= { xdsl2PMLineCurrInitEntry 9 }

   xdsl2PMLCurrInit1DayFailedShortInits  OBJECT-TYPE
      SYNTAX      Unsigned32
      MAX-ACCESS  read-only
      STATUS      current
      DESCRIPTION
         "Count of failed short initializations on the line during this
          interval."
      REFERENCE    "ITU-T G.997.1, paragraph 7.2.1"
      ::= { xdsl2PMLineCurrInitEntry 10 }



   -------------------------------------------
   --       PM line history 15 Minutes      --
   -------------------------------------------
   xdsl2PMLineHist15MinTable    OBJECT-TYPE
      SYNTAX      SEQUENCE  OF  Xdsl2PMLineHist15MinEntry
      MAX-ACCESS  not-accessible
      STATUS      current
      DESCRIPTION
         "The table xdsl2PMLineHist15MinTable contains PM line history
         for 15min intervals of DSL line.  The objects in this table
         are NOT persistent."
      ::= { xdsl2PMLine 3 }

   xdsl2PMLineHist15MinEntry  OBJECT-TYPE
      SYNTAX      Xdsl2PMLineHist15MinEntry
      MAX-ACCESS  not-accessible
      STATUS      current
      DESCRIPTION
         "The table xdsl2PMLineHist15MinTable contains PM line history
          for 15min intervals of DSL line.
          The index of this table is an interface index where the
          interface has an ifType of vdsl2(xxx), the termination unit,
          and an interval number."
      INDEX  { ifIndex,
               xdsl2PMLHist15MUnit,
               xdsl2PMLHist15MInterval }
      ::= { xdsl2PMLineHist15MinTable 1 }

   Xdsl2PMLineHist15MinEntry  ::=
      SEQUENCE {
         xdsl2PMLHist15MUnit                 Xdsl2Unit,
         xdsl2PMLHist15MInterval             Unsigned32,
         xdsl2PMLHist15MMonitoredTime        Unsigned32,
         xdsl2PMLHist15MFecs                 Counter32,
         xdsl2PMLHist15MEs                   Counter32,
         xdsl2PMLHist15MSes                  Counter32,
         xdsl2PMLHist15MLoss                 Counter32,
         xdsl2PMLHist15MUas                  Counter32,
         xdsl2PMLHist15MValidInterval        TruthValue
      }

   xdsl2PMLHist15MUnit  OBJECT-TYPE
      SYNTAX      Xdsl2Unit
      MAX-ACCESS  not-accessible
      STATUS      current
      DESCRIPTION
         "The termination unit xtuc{1} or xtur{2}."
      ::= { xdsl2PMLineHist15MinEntry 1 }

   xdsl2PMLHist15MInterval  OBJECT-TYPE
      SYNTAX      Unsigned32 (1..96)
      MAX-ACCESS  not-accessible
      STATUS      current
      DESCRIPTION
         "The interval number."
      ::= { xdsl2PMLineHist15MinEntry 2 }

   xdsl2PMLHist15MMonitoredTime  OBJECT-TYPE
      SYNTAX      Unsigned32
      UNITS       "seconds"
      MAX-ACCESS  read-only
      STATUS      current
      DESCRIPTION
         "Total seconds monitored in this interval."
      ::= { xdsl2PMLineHist15MinEntry 3 }

   xdsl2PMLHist15MFecs  OBJECT-TYPE
      SYNTAX      Counter32
      UNITS       "seconds"
      MAX-ACCESS  read-only
      STATUS      current
      DESCRIPTION
         "Count of seconds during this interval that there was at least
          one FEC correction event for one or more bearer channels in
          this line.  This parameter is inhibited during UAS or SES."
      REFERENCE    "ITU-T G.997.1, paragraph 7.2.1"
      ::= { xdsl2PMLineHist15MinEntry 4 }

   xdsl2PMLHist15MEs  OBJECT-TYPE
      SYNTAX      Counter32
      UNITS       "seconds"
      MAX-ACCESS  read-only
      STATUS      current
      DESCRIPTION
         "Count of seconds during this interval that there was:
             xtu-c: CRC-8 >= 1 for one or more bearer channels OR
                    LOS >= 1 OR SEF >= 1 OR LPR >= 1
             xtu-r: FEBE >= 1 for one or more bearer channels OR
                    LOS-FE >= 1 OR RDI >= 1 OR LPR-FE >= 1.
          This parameter is inhibited during UAS."
      REFERENCE    "ITU-T G.997.1, paragraph 7.2.1"
      ::= { xdsl2PMLineHist15MinEntry 5 }

   xdsl2PMLHist15MSes  OBJECT-TYPE
      SYNTAX      Counter32
      UNITS       "seconds"
      MAX-ACCESS  read-only
      STATUS      current
      DESCRIPTION
         "Count of seconds during this interval that there was:
             xtu-c: (CRC-8 summed over all bearer channels) >= 18 OR
                    LOS >= 1 OR SEF >= 1 OR LPR >= 1
             xtu-r: (FEBE summed over all bearer channels) >= 18 OR
                    LOS-FE >= 1 OR RDI >= 1 OR LPR-FE >= 1.
          This parameter is inhibited during UAS."

      REFERENCE    "ITU-T G.997.1, paragraph 7.2.1"
      ::= { xdsl2PMLineHist15MinEntry 6 }

   xdsl2PMLHist15MLoss  OBJECT-TYPE
      SYNTAX      Counter32
      UNITS       "seconds"
      MAX-ACCESS  read-only
      STATUS      current
      DESCRIPTION
         "Count of seconds during this interval that there was LOS (or
          LOS-FE for xtu-r)."
      REFERENCE    "ITU-T G.997.1, paragraph 7.2.1"
      ::= { xdsl2PMLineHist15MinEntry 7 }

   xdsl2PMLHist15MUas  OBJECT-TYPE
      SYNTAX      Counter32
      UNITS       "seconds"
      MAX-ACCESS  read-only
      STATUS      current
      DESCRIPTION
         "Count of seconds in Unavailability State during this interval.
          Unavailability begins at the onset of 10 contiguous severely
          -errored seconds, and ends at the onset of 10 contiguous
          seconds with no severely-errored seconds."
      REFERENCE    "ITU-T G.997.1, paragraph 7.2.1"
      ::= { xdsl2PMLineHist15MinEntry 8 }

   xdsl2PMLHist15MValidInterval  OBJECT-TYPE
      SYNTAX      TruthValue
      MAX-ACCESS  read-only
      STATUS      current
      DESCRIPTION
         "This variable indicates if the data for this interval is
          valid."
      ::= { xdsl2PMLineHist15MinEntry 9 }



   ---------------------------------------
   --       PM line history 1 Day       --
   ---------------------------------------
   xdsl2PMLineHist1DayTable     OBJECT-TYPE
      SYNTAX      SEQUENCE  OF  Xdsl2PMLineHist1DayEntry
      MAX-ACCESS  not-accessible
      STATUS      current
      DESCRIPTION
         "The table xdsl2PMLineHist1DayTable contains PM line history
          for 24 hours intervals of DSL line.  The objects in this
          table are NOT persistent."
      ::= { xdsl2PMLine 4 }

   xdsl2PMLineHist1DayEntry  OBJECT-TYPE
      SYNTAX      Xdsl2PMLineHist1DayEntry
      MAX-ACCESS  not-accessible
      STATUS      current
      DESCRIPTION
         "The table xdsl2PMLineHist1DayTable contains PM line history
          for 24 hours intervals of DSL line.
          The indexes of this table is an interface index where the
          interface has an ifType of vdsl2(xxx), the termination unit
          and an interval number."

      INDEX  { ifIndex,
               xdsl2PMLHist1DUnit,
               xdsl2PMLHist1DInterval }
      ::= { xdsl2PMLineHist1DayTable 1 }

   Xdsl2PMLineHist1DayEntry  ::=
      SEQUENCE {
         xdsl2PMLHist1DUnit              Xdsl2Unit,
         xdsl2PMLHist1DInterval          Unsigned32,
         xdsl2PMLHist1DMonitoredTime     Unsigned32,
         xdsl2PMLHist1DFecs              Counter32,
         xdsl2PMLHist1DEs                Counter32,
         xdsl2PMLHist1DSes               Counter32,
         xdsl2PMLHist1DLoss              Counter32,
         xdsl2PMLHist1DUas               Counter32,
         xdsl2PMLHist1DValidInterval     TruthValue
      }

   xdsl2PMLHist1DUnit  OBJECT-TYPE
      SYNTAX      Xdsl2Unit
      MAX-ACCESS  not-accessible
      STATUS      current
      DESCRIPTION
         "The termination unit."
      ::= { xdsl2PMLineHist1DayEntry 1 }

   xdsl2PMLHist1DInterval  OBJECT-TYPE
      SYNTAX      Unsigned32 (1..30)
      MAX-ACCESS  not-accessible
      STATUS      current
      DESCRIPTION
         "The interval number."
      ::= { xdsl2PMLineHist1DayEntry 2 }

   xdsl2PMLHist1DMonitoredTime  OBJECT-TYPE
      SYNTAX      Unsigned32
      UNITS       "seconds"
      MAX-ACCESS  read-only
      STATUS      current
      DESCRIPTION
         "Total seconds monitored in this interval."
      ::= { xdsl2PMLineHist1DayEntry 3 }

   xdsl2PMLHist1DFecs  OBJECT-TYPE
      SYNTAX      Counter32
      UNITS       "seconds"
      MAX-ACCESS  read-only
      STATUS      current
      DESCRIPTION
         "Count of seconds during this interval that there was at least
          one FEC correction event for one or more bearer channels in
          this line.  This parameter is inhibited during UAS or SES."
      REFERENCE    "ITU-T G.997.1, paragraph 7.2.1"
      ::= { xdsl2PMLineHist1DayEntry 4 }

   xdsl2PMLHist1DEs  OBJECT-TYPE
      SYNTAX      Counter32
      UNITS       "seconds"
      MAX-ACCESS  read-only
      STATUS      current
      DESCRIPTION
         "Count of seconds during this interval that there was:
             xtu-c: CRC-8 >= 1 for one or more bearer channels OR
                    LOS >= 1 OR SEF >= 1 OR LPR >= 1
             xtu-r: FEBE >= 1 for one or more bearer channels OR
                    LOS-FE >= 1 OR RDI >= 1 OR LPR-FE >= 1.
          This parameter is inhibited during UAS."
      REFERENCE    "ITU-T G.997.1, paragraph 7.2.1"
      ::= { xdsl2PMLineHist1DayEntry 5 }

   xdsl2PMLHist1DSes  OBJECT-TYPE
      SYNTAX      Counter32
      UNITS       "seconds"
      MAX-ACCESS  read-only
      STATUS      current
      DESCRIPTION
         "Count of seconds during this interval that there was:
             xtu-c: (CRC-8 summed over all bearer channels) >= 18 OR
                     LOS >= 1 OR SEF >> 1 OR LPR >= 1
             xtu-r: (FEBE summed over all bearer channels) >= 18 OR
                     LOS-FE >= 1 OR RDI >= 1 OR LPR-FE >= 1.
          This parameter is inhibited during UAS."

      REFERENCE    "ITU-T G.997.1, paragraph 7.2.1"
      ::= { xdsl2PMLineHist1DayEntry 6 }

   xdsl2PMLHist1DLoss  OBJECT-TYPE
      SYNTAX      Counter32
      UNITS       "seconds"
      MAX-ACCESS  read-only
      STATUS      current
      DESCRIPTION
         "Count of seconds during this interval that there was LOS (or
          LOS-FE for xtu-r)."
      REFERENCE    "ITU-T G.997.1, paragraph 7.2.1"
      ::= { xdsl2PMLineHist1DayEntry 7 }

   xdsl2PMLHist1DUas  OBJECT-TYPE
      SYNTAX      Counter32
      UNITS       "seconds"
      MAX-ACCESS  read-only
      STATUS      current
      DESCRIPTION
         "Count of seconds in Unavailability State during this interval.
          Unavailability begins at the onset of 10 contiguous severely
          -errored seconds, and ends at the onset of 10 contiguous
          seconds with no severely-errored seconds."
      REFERENCE    "ITU-T G.997.1, paragraph 7.2.1"
      ::= { xdsl2PMLineHist1DayEntry 8 }

   xdsl2PMLHist1DValidInterval  OBJECT-TYPE
      SYNTAX      TruthValue
      MAX-ACCESS  read-only
      STATUS      current
      DESCRIPTION
         "This variable indicates if the data for this interval is
          valid."
      ::= { xdsl2PMLineHist1DayEntry 9 }




   -------------------------------------------
   --     PM line init history 15 Minutes   --
   -------------------------------------------

   xdsl2PMLineInitHist15MinTable      OBJECT-TYPE
      SYNTAX      SEQUENCE  OF  Xdsl2PMLineInitHist15MinEntry
      MAX-ACCESS  not-accessible
      STATUS      current
      DESCRIPTION
         "The table xdsl2PMLineInitHist15MinTable contains PM line
          initialization history for 15 minutes intervals of DSL
          line.  The objects in this table are NOT persistent."
      ::= { xdsl2PMLine 5 }

   xdsl2PMLineInitHist15MinEntry  OBJECT-TYPE
      SYNTAX      Xdsl2PMLineInitHist15MinEntry
      MAX-ACCESS  not-accessible
      STATUS      current
      DESCRIPTION
         "The table xdsl2PMLineInitHist15MinTable contains PM line
          initialization history for 15 minutes intervals of DSL
          line.
          The index of this table is an interface index where the
          interface has an ifType of vdsl2(xxx) and an interval number."

      INDEX  { ifIndex,
               xdsl2PMLHistInit15MInterval }
      ::= { xdsl2PMLineInitHist15MinTable 1 }

   Xdsl2PMLineInitHist15MinEntry  ::=
      SEQUENCE {
         xdsl2PMLHistInit15MInterval              Unsigned32,
         xdsl2PMLHistInit15MMonitoredTime         Unsigned32,
         xdsl2PMLHistInit15MFullInits             Unsigned32,
         xdsl2PMLHistInit15MFailedFullInits       Unsigned32,
         xdsl2PMLHistInit15MShortInits            Unsigned32,
         xdsl2PMLHistInit15MFailedShortInits      Unsigned32,
         xdsl2PMLHistInit15MValidInterval         TruthValue
      }

   xdsl2PMLHistInit15MInterval  OBJECT-TYPE
      SYNTAX      Unsigned32 (1..96)
      MAX-ACCESS  not-accessible
      STATUS      current
      DESCRIPTION
         "The interval number."
      ::= { xdsl2PMLineInitHist15MinEntry 1 }

   xdsl2PMLHistInit15MMonitoredTime  OBJECT-TYPE
      SYNTAX      Unsigned32
      UNITS       "seconds"
      MAX-ACCESS  read-only
      STATUS      current
      DESCRIPTION
         "Total seconds monitored in this interval."
      ::= { xdsl2PMLineInitHist15MinEntry 2 }

   xdsl2PMLHistInit15MFullInits  OBJECT-TYPE
      SYNTAX      Unsigned32
      MAX-ACCESS  read-only
      STATUS      current
      DESCRIPTION
         "Count of full initializations attempted on the line
          (successful and failed) during this interval."
      REFERENCE    "ITU-T G.997.1, paragraph 7.2.1"
      ::= { xdsl2PMLineInitHist15MinEntry 3 }

   xdsl2PMLHistInit15MFailedFullInits  OBJECT-TYPE
      SYNTAX      Unsigned32
      MAX-ACCESS  read-only
      STATUS      current
      DESCRIPTION
         "Count of failed full initializations on the line during this
          interval."
      REFERENCE    "ITU-T G.997.1, paragraph 7.2.1"
      ::= { xdsl2PMLineInitHist15MinEntry 4 }

   xdsl2PMLHistInit15MShortInits  OBJECT-TYPE
      SYNTAX      Unsigned32
      MAX-ACCESS  read-only
      STATUS      current
      DESCRIPTION
         "Count of short initializations attempted on the line
          (successful and failed) during this interval."
      REFERENCE    "ITU-T G.997.1, paragraph 7.2.1"
      ::= { xdsl2PMLineInitHist15MinEntry 5 }

   xdsl2PMLHistInit15MFailedShortInits  OBJECT-TYPE
      SYNTAX      Unsigned32
      MAX-ACCESS  read-only
      STATUS      current
      DESCRIPTION
         "Count of failed short initializations on the line during this
          interval."
      REFERENCE    "ITU-T G.997.1, paragraph 7.2.1"
      ::= { xdsl2PMLineInitHist15MinEntry 6 }

   xdsl2PMLHistInit15MValidInterval  OBJECT-TYPE
      SYNTAX      TruthValue
      MAX-ACCESS  read-only
      STATUS      current
      DESCRIPTION
         "This variable indicates if the data for this interval is
          valid."
      ::= { xdsl2PMLineInitHist15MinEntry 7 }

   -------------------------------------------
   --       PM line init history 1 Day      --
   -------------------------------------------
   xdsl2PMLineInitHist1DayTable       OBJECT-TYPE
      SYNTAX      SEQUENCE  OF  Xdsl2PMLineInitHist1DayEntry
      MAX-ACCESS  not-accessible
      STATUS      current
      DESCRIPTION
         "The table xdsl2PMLineInitHist1DayTable contains PM line
          initialization history for 24 hours intervals of DSL
          line.  The objects in this table are NOT persistent."
      ::= { xdsl2PMLine 6 }

   xdsl2PMLineInitHist1DayEntry  OBJECT-TYPE
      SYNTAX      Xdsl2PMLineInitHist1DayEntry
      MAX-ACCESS  not-accessible
      STATUS      current
      DESCRIPTION
         "The table xdsl2PMLineInitHist1DayTable contains PM line
          initialization history for 24 hours intervals of DSL
          line.
          The indexes of this table is an interface index where the
          interface has an ifType of vdsl2(xxx) and an interval number."
      INDEX  { ifIndex,
               xdsl2PMLHistinit1DInterval }
      ::= { xdsl2PMLineInitHist1DayTable 1 }

   Xdsl2PMLineInitHist1DayEntry  ::=
      SEQUENCE {
         xdsl2PMLHistinit1DInterval              Unsigned32,
         xdsl2PMLHistinit1DMonitoredTime         Unsigned32,
         xdsl2PMLHistinit1DFullInits             Unsigned32,
         xdsl2PMLHistinit1DFailedFullInits       Unsigned32,
         xdsl2PMLHistinit1DShortInits            Unsigned32,
         xdsl2PMLHistinit1DFailedShortInits      Unsigned32,
         xdsl2PMLHistinit1DValidInterval         TruthValue
      }

   xdsl2PMLHistinit1DInterval  OBJECT-TYPE
      SYNTAX      Unsigned32 (1..30)
      MAX-ACCESS  not-accessible
      STATUS      current
      DESCRIPTION
         "The interval number."
      ::= { xdsl2PMLineInitHist1DayEntry 1 }

   xdsl2PMLHistinit1DMonitoredTime  OBJECT-TYPE
      SYNTAX      Unsigned32
      UNITS       "seconds"
      MAX-ACCESS  read-only
      STATUS      current
      DESCRIPTION
         "Total seconds monitored in this interval."
      ::= { xdsl2PMLineInitHist1DayEntry 2 }

   xdsl2PMLHistinit1DFullInits  OBJECT-TYPE
      SYNTAX      Unsigned32
      MAX-ACCESS  read-only
      STATUS      current
      DESCRIPTION
         "Count of full initializations attempted on the line
          (successful and failed) during this interval."
      REFERENCE    "ITU-T G.997.1, paragraph 7.2.1"
       ::= { xdsl2PMLineInitHist1DayEntry 3 }

   xdsl2PMLHistinit1DFailedFullInits  OBJECT-TYPE
      SYNTAX      Unsigned32
      MAX-ACCESS  read-only
      STATUS      current
      DESCRIPTION
         "Count of failed full initializations on the line during this
          interval."
      REFERENCE    "ITU-T G.997.1, paragraph 7.2.1"
      ::= { xdsl2PMLineInitHist1DayEntry 4 }

   xdsl2PMLHistinit1DShortInits  OBJECT-TYPE
      SYNTAX      Unsigned32
      MAX-ACCESS  read-only
      STATUS      current
      DESCRIPTION
         "Count of short initializations attempted on the line
          (successful and failed) during this interval."
      REFERENCE    "ITU-T G.997.1, paragraph 7.2.1"
      ::= { xdsl2PMLineInitHist1DayEntry 5 }

   xdsl2PMLHistinit1DFailedShortInits  OBJECT-TYPE
      SYNTAX      Unsigned32
      MAX-ACCESS  read-only
      STATUS      current
      DESCRIPTION
         "Count of failed short initializations on the line during this
          interval."
      REFERENCE    "ITU-T G.997.1, paragraph 7.2.1"
      ::= { xdsl2PMLineInitHist1DayEntry 6 }

   xdsl2PMLHistinit1DValidInterval  OBJECT-TYPE
      SYNTAX      TruthValue
      MAX-ACCESS  read-only
      STATUS      current
      DESCRIPTION
         "This variable indicates if the data for this interval is
          valid."
      ::= { xdsl2PMLineInitHist1DayEntry 7 }



   ---------------------------------------------------
   --          PM channel current counters          --
   ---------------------------------------------------
   xdsl2PMChCurrTable        OBJECT-TYPE
      SYNTAX      SEQUENCE  OF  Xdsl2PMChCurrEntry
      MAX-ACCESS  not-accessible
      STATUS      current
      DESCRIPTION
         "The table xdsl2PMChCurrTable contains current Performance
          Monitoring results of DSL channel.  The objects in this
          table are NOT persistent."
      ::= { xdsl2PMChannel 1 }

   xdsl2PMChCurrEntry  OBJECT-TYPE
      SYNTAX      Xdsl2PMChCurrEntry
      MAX-ACCESS  not-accessible
      STATUS      current
      DESCRIPTION
         "The table xdsl2PMChCurrTable contains current Performance
          Monitoring results of DSL channel.
          The indexes of this table is an interface index where
          the interface has an ifType value which is applicable
          for a DSL channel and the termination unit."
      INDEX  { ifIndex, xdsl2PMChCurrUnit }
      ::= { xdsl2PMChCurrTable 1 }

   Xdsl2PMChCurrEntry  ::=
      SEQUENCE {
         xdsl2PMChCurrUnit                     Xdsl2Unit,
         xdsl2PMChCurrValidIntervals           Unsigned32,
         xdsl2PMChCurrInvalidIntervals         Unsigned32,
         xdsl2PMChCurr15MTimeElapsed           HCPerfTimeElapsed,
         xdsl2PMChCurr15MCodingViolations      Unsigned32,
         xdsl2PMChCurr15MCorrectedBlocks       Unsigned32,
         xdsl2PMChCurr1DayValidIntervals       Unsigned32,
         xdsl2PMChCurr1DayInvalidIntervals     Unsigned32,
         xdsl2PMChCurr1DayTimeElapsed          HCPerfTimeElapsed,
         xdsl2PMChCurr1DayCodingViolations     Unsigned32,
         xdsl2PMChCurr1DayCorrectedBlocks      Unsigned32
      }

   xdsl2PMChCurrUnit  OBJECT-TYPE
      SYNTAX      Xdsl2Unit
      MAX-ACCESS  not-accessible
      STATUS      current
      DESCRIPTION
      "The termination unit."
      ::= { xdsl2PMChCurrEntry 1 }

   xdsl2PMChCurrValidIntervals  OBJECT-TYPE
      SYNTAX      Unsigned32
      MAX-ACCESS  read-only
      STATUS      current
      DESCRIPTION
         "Valid intervals."
      ::= { xdsl2PMChCurrEntry 2 }

   xdsl2PMChCurrInvalidIntervals  OBJECT-TYPE
      SYNTAX      Unsigned32
      MAX-ACCESS  read-only
      STATUS      current
      DESCRIPTION
         "Invalid intervals."
       ::= { xdsl2PMChCurrEntry 3 }

   xdsl2PMChCurr15MTimeElapsed  OBJECT-TYPE
      SYNTAX      HCPerfTimeElapsed
      UNITS       "seconds"
      MAX-ACCESS  read-only
      STATUS      current
      DESCRIPTION
         "Total elapsed seconds in this interval."
      ::= { xdsl2PMChCurrEntry 4 }

   xdsl2PMChCurr15MCodingViolations  OBJECT-TYPE
      SYNTAX      Unsigned32
      MAX-ACCESS  read-only
      STATUS      current
      DESCRIPTION
         "Count of CRC-8 (FEBE for xtu-r) anomalies occurring in the
          channel during the interval.  This parameter is inhibited
          during UAS or SES.  If the CRC is applied over multiple
          channels, then each related CRC-8 (or FEBE) anomaly should
          increment each of the counters related to the individual
          channels."
      REFERENCE    "ITU-T G.997.1, paragraph 7.2.2"
     ::= { xdsl2PMChCurrEntry 5 }

   xdsl2PMChCurr15MCorrectedBlocks  OBJECT-TYPE
      SYNTAX      Unsigned32
      MAX-ACCESS  read-only
      STATUS      current
      DESCRIPTION
         "Count of FEC (FFEC for xtu-r) anomalies (corrected code words)
          occurring in the channel during the interval.  This parameter
          is inhibited during UAS or SES.  If the FEC is applied over
          multiple channels, then each related FEC (or FFEC) anomaly
          should increment each of the counters related to the
          individual channels."
      REFERENCE    "ITU-T G.997.1, paragraph 7.2.2"
      ::= { xdsl2PMChCurrEntry 6 }

   xdsl2PMChCurr1DayValidIntervals  OBJECT-TYPE
      SYNTAX      Unsigned32
      MAX-ACCESS  read-only
      STATUS      current
      DESCRIPTION
         "Valid intervals."
      ::= { xdsl2PMChCurrEntry 7 }

   xdsl2PMChCurr1DayInvalidIntervals  OBJECT-TYPE
      SYNTAX      Unsigned32
      MAX-ACCESS  read-only
      STATUS      current
      DESCRIPTION
         "Invalid intervals."
      ::= { xdsl2PMChCurrEntry 8 }

   xdsl2PMChCurr1DayTimeElapsed  OBJECT-TYPE
      SYNTAX      HCPerfTimeElapsed
      UNITS       "seconds"
      MAX-ACCESS  read-only
      STATUS      current
      DESCRIPTION
         "Total elapsed seconds in this interval."
      ::= { xdsl2PMChCurrEntry 9 }

   xdsl2PMChCurr1DayCodingViolations  OBJECT-TYPE
      SYNTAX      Unsigned32
      MAX-ACCESS  read-only
      STATUS      current
      DESCRIPTION
         "Count of CRC-8 (FEBE for xtu-r) anomalies occurring in the
          channel during the interval.  This parameter is inhibited
          during UAS or SES.  If the CRC is applied over multiple
          channels, then each related CRC-8 (or FEBE) anomaly should
          increment each of the counters related to the individual
          channels."
      REFERENCE    "ITU-T G.997.1, paragraph 7.2.2"
      ::= { xdsl2PMChCurrEntry 10 }

   xdsl2PMChCurr1DayCorrectedBlocks  OBJECT-TYPE
      SYNTAX      Unsigned32
      MAX-ACCESS  read-only
      STATUS      current
      DESCRIPTION
         "Count of FEC (FFEC for xtu-r) anomalies (corrected code words)
          occurring in the channel during the interval.  This parameter
          is inhibited during UAS or SES.  If the FEC is applied over
          multiple channels, then each related FEC (or FFEC) anomaly
          should increment each of the counters related to the
          individual channels."
      REFERENCE    "ITU-T G.997.1, paragraph 7.2.2"
      ::= { xdsl2PMChCurrEntry 11 }



   -------------------------------------------
   --    PM channel history 15 Minutes      --
   -------------------------------------------
   xdsl2PMChHist15MinTable         OBJECT-TYPE
      SYNTAX      SEQUENCE  OF  Xdsl2PMChHist15MinEntry
      MAX-ACCESS  not-accessible
      STATUS      current
      DESCRIPTION
         "The table xdsl2PMChCurrTable contains current Performance
          Monitoring results of DSL channel.  The objects in this
          table are NOT persistent."
      ::= { xdsl2PMChannel 2 }

   xdsl2PMChHist15MinEntry  OBJECT-TYPE
      SYNTAX      Xdsl2PMChHist15MinEntry
      MAX-ACCESS  not-accessible
      STATUS      current
      DESCRIPTION
         "The table xdsl2PMChCurrTable contains current Performance
          Monitoring results of DSL channel.
          The indexes of this table is an interface index where
          the interface has an ifType value which is applicable
          for a DSL channel, the termination unit and the
          interval number."
      INDEX  { ifIndex,
               xdsl2PMChHist15MUnit,
               xdsl2PMChHist15MInterval }
      ::= { xdsl2PMChHist15MinTable 1 }

   Xdsl2PMChHist15MinEntry  ::=
      SEQUENCE {
         xdsl2PMChHist15MUnit                     Xdsl2Unit,
         xdsl2PMChHist15MInterval                 Unsigned32,
         xdsl2PMChHist15MMonitoredTime            Unsigned32,
         xdsl2PMChHist15MCodingViolations         Unsigned32,
         xdsl2PMChHist15MCorrectedBlocks          Unsigned32,
         xdsl2PMChHist15MValidInterval            TruthValue
      }

   xdsl2PMChHist15MUnit  OBJECT-TYPE
      SYNTAX      Xdsl2Unit
      MAX-ACCESS  not-accessible
      STATUS      current
      DESCRIPTION
         "The termination unit."
      ::= { xdsl2PMChHist15MinEntry 1 }

   xdsl2PMChHist15MInterval  OBJECT-TYPE
      SYNTAX      Unsigned32 (1..96)
      MAX-ACCESS  not-accessible
      STATUS      current
      DESCRIPTION
         "The interval number."
      ::= { xdsl2PMChHist15MinEntry 2 }

   xdsl2PMChHist15MMonitoredTime  OBJECT-TYPE
      SYNTAX      Unsigned32
      UNITS       "seconds"
      MAX-ACCESS  read-only
      STATUS      current
      DESCRIPTION
         "Total seconds monitored in this interval."
      ::= { xdsl2PMChHist15MinEntry 3 }

   xdsl2PMChHist15MCodingViolations  OBJECT-TYPE
      SYNTAX      Unsigned32
      MAX-ACCESS  read-only
      STATUS      current
      DESCRIPTION
         "Count of CRC-8 (FEBE for xtu-r) anomalies occurring in the
          channel during the interval.  This parameter is inhibited
          during UAS or SES.  If the CRC is applied over multiple
          channels, then each related CRC-8 (or FEBE) anomaly should
          increment each of the counters related to the individual
          channels."
      REFERENCE    "ITU-T G.997.1, paragraph 7.2.2"
      ::= { xdsl2PMChHist15MinEntry 4 }

   xdsl2PMChHist15MCorrectedBlocks  OBJECT-TYPE
      SYNTAX      Unsigned32
      MAX-ACCESS  read-only
      STATUS      current
      DESCRIPTION
         "Count of FEC (FFEC for xtu-r) anomalies (corrected code words)
          occurring in the channel during the interval.  This parameter
          is inhibited during UAS or SES.  If the FEC is applied over
          multiple channels, then each related FEC (or FFEC) anomaly
          should increment each of the counters related to the
          individual channels."
      REFERENCE    "ITU-T G.997.1, paragraph 7.2.2"
      ::= { xdsl2PMChHist15MinEntry 5 }

   xdsl2PMChHist15MValidInterval  OBJECT-TYPE
      SYNTAX      TruthValue
      MAX-ACCESS  read-only
      STATUS      current
      DESCRIPTION
         "This variable indicates if the data for this interval is
          valid."
      ::= { xdsl2PMChHist15MinEntry 6 }



   ------------------------------------------
   --        PM channel history 1 Day      --
   ------------------------------------------
   xdsl2PMChHist1DTable         OBJECT-TYPE
      SYNTAX      SEQUENCE  OF  Xdsl2PMChHist1DEntry
      MAX-ACCESS  not-accessible
      STATUS      current
      DESCRIPTION
         "The table xdsl2PMChHist1DayTable contains PM channel history
          for 1 day intervals of DSL.  The objects in this table are
          NOT persistent."
      ::= { xdsl2PMChannel 3 }

   xdsl2PMChHist1DEntry  OBJECT-TYPE
      SYNTAX      Xdsl2PMChHist1DEntry
      MAX-ACCESS  not-accessible
      STATUS      current
      DESCRIPTION
         "The table xdsl2PMChHist1DayTable contains PM channel history
          for 1 day intervals of DSL.
          The indexes of this table is an interface index where
          the interface has an ifType value which is applicable
          for a DSL channel, the termination unit and the
          interval number."

      INDEX  { ifIndex,
               xdsl2PMChHist1DUnit,
               xdsl2PMChHist1DInterval }
      ::= { xdsl2PMChHist1DTable 1 }

   Xdsl2PMChHist1DEntry  ::=
      SEQUENCE {
         xdsl2PMChHist1DUnit                      Xdsl2Unit,
         xdsl2PMChHist1DInterval                  Unsigned32,
         xdsl2PMChHist1DMonitoredTime             Unsigned32,
         xdsl2PMChHist1DCodingViolations          Unsigned32,
         xdsl2PMChHist1DCorrectedBlocks           Unsigned32,
         xdsl2PMChHist1DValidInterval             TruthValue
      }

   xdsl2PMChHist1DUnit  OBJECT-TYPE
      SYNTAX      Xdsl2Unit
      MAX-ACCESS  not-accessible
      STATUS      current
      DESCRIPTION
         "The termination unit."
       ::= { xdsl2PMChHist1DEntry 1 }

   xdsl2PMChHist1DInterval  OBJECT-TYPE
      SYNTAX      Unsigned32 (1..30)
      MAX-ACCESS  not-accessible
      STATUS      current
      DESCRIPTION
         "The interval number."
      ::= { xdsl2PMChHist1DEntry 2 }

   xdsl2PMChHist1DMonitoredTime  OBJECT-TYPE
      SYNTAX      Unsigned32
      UNITS       "seconds"
      MAX-ACCESS  read-only
      STATUS      current
      DESCRIPTION
         "Total seconds monitored in this interval."
      ::= { xdsl2PMChHist1DEntry 3 }

   xdsl2PMChHist1DCodingViolations  OBJECT-TYPE
      SYNTAX      Unsigned32
      MAX-ACCESS  read-only
      STATUS      current
      DESCRIPTION
         "Count of CRC-8 (FEBE for xtu-r) anomalies occurring in the
          channel during the interval.  This parameter is inhibited
          during UAS or SES.  If the CRC is applied over multiple
          channels, then each related CRC-8 (or FEBE) anomaly should
          increment each of the counters related to the individual
          channels."
      REFERENCE    "ITU-T G.997.1, paragraph 7.2.2"
      ::= { xdsl2PMChHist1DEntry 4 }

   xdsl2PMChHist1DCorrectedBlocks  OBJECT-TYPE
      SYNTAX      Unsigned32
      MAX-ACCESS  read-only
      STATUS      current
      DESCRIPTION
         "Count of FEC (FFEC for xtu-r) anomalies (corrected code words)
          occurring in the channel during the interval.  This parameter
          is inhibited during UAS or SES.  If the FEC is applied over
          multiple channels, then each related FEC (or FFEC) anomaly
          should increment each of the counters related to the
          individual channels."
      REFERENCE    "ITU-T G.997.1, paragraph 7.2.2"
      ::= { xdsl2PMChHist1DEntry 5 }

   xdsl2PMChHist1DValidInterval  OBJECT-TYPE
      SYNTAX      TruthValue
      MAX-ACCESS  read-only
      STATUS      current
      DESCRIPTION
         "This variable indicates if the data for this interval is
          valid."
      ::= { xdsl2PMChHist1DEntry 6 }

   -------------------------------------------
   --          Notifications Group          --
   -------------------------------------------

   xdsl2LinePerfFECSThreshXtuc NOTIFICATION-TYPE
      OBJECTS
      {
      xdsl2PMLCurr15MFecs,
      xdsl2LineAlarmConfProfileXtucThresh15MinFecs
      }
      STATUS     current
      DESCRIPTION
        "This notification indicates that the FEC seconds threshold
         has been reached/exceeded for the referred XTU-C."
      ::= { xdsl2Notifications 1 }

   xdsl2LinePerfFECSThreshXtur NOTIFICATION-TYPE
      OBJECTS
      {
      xdsl2PMLCurr15MFecs,
      xdsl2LineAlarmConfProfileXturThresh15MinFecs
      }
      STATUS     current
      DESCRIPTION
        "This notification indicates that the FEC seconds threshold
         has been reached/exceeded for the referred XTU-R."
      ::= { xdsl2Notifications 2 }

   xdsl2LinePerfESThreshXtuc NOTIFICATION-TYPE
      OBJECTS
      {
      xdsl2PMLCurr15MEs,
      xdsl2LineAlarmConfProfileXtucThresh15MinEs
      }
      STATUS     current
      DESCRIPTION
        "This notification indicates that the errored seconds threshold
         has been reached/exceeded for the referred XTU-C."
      ::= { xdsl2Notifications 3 }

   xdsl2LinePerfESThreshXtur NOTIFICATION-TYPE
      OBJECTS
      {
      xdsl2PMLCurr15MEs,
      xdsl2LineAlarmConfProfileXturThresh15MinEs
      }
      STATUS     current
      DESCRIPTION
        "This notification indicates that the errored seconds threshold
         has been reached/exceeded for the referred XTU-R."
      ::= { xdsl2Notifications 4 }

   xdsl2LinePerfSESThreshXtuc NOTIFICATION-TYPE
      OBJECTS
      {
      xdsl2PMLCurr15MSes,
      xdsl2LineAlarmConfProfileXtucThresh15MinSes
      }
      STATUS     current
      DESCRIPTION
        "This notification indicates that the severely-errored seconds
         threshold has been reached/exceeded for the referred XTU-C."
      ::= { xdsl2Notifications 5 }

   xdsl2LinePerfSESThreshXtur NOTIFICATION-TYPE
      OBJECTS
      {
      xdsl2PMLCurr15MSes,
      xdsl2LineAlarmConfProfileXturThresh15MinSes
      }
      STATUS     current
      DESCRIPTION
        "This notification indicates that the severely-errored seconds
         threshold has been reached/exceeded for the referred XTU-R."
      ::= { xdsl2Notifications 6 }

   xdsl2LinePerfLOSSThreshXtuc NOTIFICATION-TYPE
      OBJECTS
      {
      xdsl2PMLCurr15MLoss,
      xdsl2LineAlarmConfProfileXtucThresh15MinLoss
      }
      STATUS     current
      DESCRIPTION
        "This notification indicates that the LOS seconds
         threshold has been reached/exceeded for the referred XTU-C."
      ::= { xdsl2Notifications 7 }

   xdsl2LinePerfLOSSThreshXtur NOTIFICATION-TYPE
      OBJECTS
      {
      xdsl2PMLCurr15MLoss,
      xdsl2LineAlarmConfProfileXturThresh15MinLoss
      }
      STATUS     current
      DESCRIPTION
        "This notification indicates that the LOS seconds
         threshold has been reached/exceeded for the referred XTU-R."
      ::= { xdsl2Notifications 8 }

   xdsl2LinePerfUASThreshXtuc NOTIFICATION-TYPE
      OBJECTS
      {
      xdsl2PMLCurr15MUas,
      xdsl2LineAlarmConfProfileXtucThresh15MinUas
      }
      STATUS     current
      DESCRIPTION
        "This notification indicates that the unavailable seconds
         threshold has been reached/exceeded for the referred XTU-C."
      ::= { xdsl2Notifications 9 }

   xdsl2LinePerfUASThreshXtur NOTIFICATION-TYPE
      OBJECTS
      {
      xdsl2PMLCurr15MUas,
      xdsl2LineAlarmConfProfileXturThresh15MinUas
      }
      STATUS     current
      DESCRIPTION
        "This notification indicates that the unavailable seconds
         threshold has been reached/exceeded for the referred XTU-R."
      ::= { xdsl2Notifications 10 }

   xdsl2LinePerfCodingViolationsThreshXtuc NOTIFICATION-TYPE
      OBJECTS
      {
      xdsl2PMChCurr15MCodingViolations,
      xdsl2ChAlarmConfProfileXtucThresh15MinCodingViolations
      }
      STATUS     current
      DESCRIPTION
        "This notification indicates that the coding violations
         threshold has been reached/exceeded for the referred XTU-C."
      ::= { xdsl2Notifications 11 }

   xdsl2LinePerfCodingViolationsThreshXtur NOTIFICATION-TYPE
      OBJECTS
      {
      xdsl2PMChCurr15MCodingViolations,
      xdsl2ChAlarmConfProfileXturThresh15MinCodingViolations
      }
      STATUS     current
      DESCRIPTION
        "This notification indicates that the coding violations
         threshold has been reached/exceeded for the referred XTU-R."
      ::= { xdsl2Notifications 12 }

   xdsl2LinePerfCorrectedThreshXtuc NOTIFICATION-TYPE
      OBJECTS
      {
      xdsl2PMChCurr15MCorrectedBlocks,
      xdsl2ChAlarmConfProfileXtucThresh15MinCorrected
      }
      STATUS     current
      DESCRIPTION
        "This notification indicates that the corrected blocks
         (FEC events) threshold has been reached/exceeded for the
         referred XTU-C."
      ::= { xdsl2Notifications 13 }

   xdsl2LinePerfCorrectedThreshXtur NOTIFICATION-TYPE
      OBJECTS
      {
      xdsl2PMChCurr15MCorrectedBlocks,
      xdsl2ChAlarmConfProfileXturThresh15MinCorrected
      }
      STATUS     current
      DESCRIPTION
        "This notification indicates that the corrected blocks
         (FEC events) threshold has been reached/exceeded for the
         referred XTU-R."
      ::= { xdsl2Notifications 14 }

   xdsl2LinePerfFailedFullInitThresh NOTIFICATION-TYPE
      OBJECTS
      {
      xdsl2PMLCurrInit15MFailedFullInits,
      xdsl2LineAlarmConfProfileThresh15MinFailedFullInt
      }
      STATUS     current
      DESCRIPTION
        "This notification indicates that the failed full
         initializations threshold has been reached/exceeded for the
         referred ADSL/ADSL2 or ADSL2 line."
      ::= { xdsl2Notifications 15 }

   xdsl2LinePerfFailedShortInitThresh NOTIFICATION-TYPE
      OBJECTS
      {
      xdsl2PMLCurrInit15MFailedShortInits,
      xdsl2LineAlarmConfProfileThresh15MinFailedShrtInt
      }
      STATUS     current
      DESCRIPTION
        "This notification indicates that the failed short
         initializations threshold has been reached/exceeded for the
         referred VDSL2/ADSL/ADSL2 or ADSL2+ line."
      ::= { xdsl2Notifications 16 }

   xdsl2LineStatusChangeXtuc NOTIFICATION-TYPE
      OBJECTS
      {
      xdsl2LineStatusXtuc
      }
      STATUS     current
      DESCRIPTION
        "This notification indicates that a status change is
         detected for the referred XTU-C."
      ::= { xdsl2Notifications 17 }

   xdsl2LineStatusChangeXtur NOTIFICATION-TYPE
      OBJECTS
      {
      xdsl2LineStatusXtur
      }
      STATUS     current
      DESCRIPTION
        "This notification indicates that a status change is
         detected for the referred XTU-R."
      ::= { xdsl2Notifications 18 }


      -- conformance information

      vdsl2Groups OBJECT IDENTIFIER ::= { vdsl2Conformance 1 }
      vdsl2Compliances OBJECT IDENTIFIER ::= { vdsl2Conformance 2 }

      vdsl2LineMibCompliance MODULE-COMPLIANCE
         STATUS  current
         DESCRIPTION
             "The compliance statement for SNMP entities which
             manage VDSL2/ADSL/ADSL2 and ADSL2+ interfaces."
         MODULE  -- this module
         MANDATORY-GROUPS
             {
             vdsl2LineGroup,
             vdsl2ChannelStatusGroup,
             vdsl2SCStatusGroup,
             vdsl2LineInventoryGroup,
             vdsl2LineConfTemplateGroup,
             vdsl2LineConfProfGroup,
             vdsl2LineConfProfModeSpecGroup,
             vdsl2ChConfProfileGroup,
             vdsl2LineAlarmConfTemplateGroup,
             vdsl2PMLineCurrGroup,
             vdsl2PMLineCurrInitGroup,
             vdsl2PMLineHist15MinGroup,
             vdsl2PMLineHist1DayGroup,
             vdsl2PMLineInitHist15MinGroup,
             vdsl2PMLineInitHist1DayGroup,
             vdsl2PMChCurrGroup,
             vdsl2PMChHist15MinGroup,
             vdsl2PMChHist1DGroup
             }

      GROUP  vdsl2ChannelStatusAtmGroup
         DESCRIPTION
           "The group of status objects required when the data path
           is ATM."

      GROUP  vdsl2ChannelStatusPtmGroup
         DESCRIPTION
           "The group of status objects required when the data path
           is PTM."

      GROUP  vdsl2LineConfProfRaGroup
         DESCRIPTION
           "The group of objects required for controlling the rate
           adaptive behavior of the line."

      GROUP  vdsl2LineConfProfMsgMinGroup
         DESCRIPTION
           "The group of objects required for controlling the rate
           reserved for Overhead traffic."

      GROUP  vdsl2LineAlarmConfProfileGroup
         DESCRIPTION
           "The group of objects that define the alarm thresholds
           on line level PM counters."

      GROUP  vdsl2ChAlarmConfProfileGroup
         DESCRIPTION
           "The group of objects that define the alarm thresholds
           on channel level PM counters."

      GROUP  vdsl2ChConfProfileAtmGroup
         DESCRIPTION
           "The group of configuration objects required when the data
           path is ATM."

      GROUP  vdsl2ChConfProfileMinResGroup
         DESCRIPTION
           "The group of configuration objects required for the
           reserved data rate."

      GROUP  vdsl2PMLineCurrInitShortGroup
         DESCRIPTION
           "The group of PM counters for the current intervals
           short initializations."

      GROUP  vdsl2PMLineInitHist15MinShortGroup
         DESCRIPTION
           "The group of PM counters for the previous 15 minutes
           intervals short initializations."

      GROUP  vdsl2PMLineInitHist1DayShortGroup
         DESCRIPTION
           "The group of PM counters for the previous 24 hours
           intervals short initializations."

      GROUP  vdsl2ScalarSCGroup
         DESCRIPTION
           "The group of objects that report the available memory
           resources for DELT processes."

      GROUP  vdsl2ThreshNotificationGroup
         DESCRIPTION
           "The group of thresholds crossing notifications."

      GROUP  vdsl2StatusChangeNotificationGroup
         DESCRIPTION
           "The group of status change notifications."

         ::= { vdsl2Compliances 1 }

      -- units of conformance

      vdsl2LineGroup OBJECT-GROUP
         OBJECTS
             {
             xdsl2LineCnfgTemplate,
             xdsl2LineAlarmCnfgTemplate,
             xdsl2LineCmndConfPmsf,
             xdsl2LineCmndConfLdsf,
             xdsl2LineCmndConfLdsfFailReason,
             xdsl2LineCmndAutomodeColdStart,
             xdsl2LineStatusXtuTransSys,
             xdsl2LineStatusPwrMngState,
             xdsl2LineStatusInitResult,
             xdsl2LineStatusLastStateDs,
             xdsl2LineStatusLastStateUs,
             xdsl2LineStatusXtur,
             xdsl2LineStatusXtuc,
             xdsl2LineStatusLnAttenDs,
             xdsl2LineStatusLnAttenUs,
             xdsl2LineStatusSigAttenDs,
             xdsl2LineStatusSigAttenUs,
             xdsl2LineStatusSnrMarginDs,
             xdsl2LineStatusSnrMarginUs,
             xdsl2LineStatusAttainableRateDs,
             xdsl2LineStatusAttainableRateUs,
             xdsl2LineStatusActPsdDs,
             xdsl2LineStatusActPsdUs,
             xdsl2LineStatusActAtpDs,
             xdsl2LineStatusActAtpUs
             }
         STATUS     current
         DESCRIPTION
             "The group of configuration, status, and commands objects
             on the line level."
         ::= { vdsl2Groups 1 }

      vdsl2ChannelStatusGroup OBJECT-GROUP
         OBJECTS
             {
             xdsl2ChStatusChannelNum,
             xdsl2ChStatusActDataRate,
             xdsl2ChStatusPrevDataRate,
             xdsl2ChStatusActDelay
             }
         STATUS     current
         DESCRIPTION
             "The group of status objects on the channel level."
         ::= { vdsl2Groups 2 }

      vdsl2ChannelStatusAtmGroup OBJECT-GROUP
         OBJECTS
             {
             xdsl2ChStatusAtmStatus
             }
         STATUS     current
         DESCRIPTION
             "The group of status objects on the data path level
             when it is ATM."
         ::= { vdsl2Groups 3 }

      vdsl2ChannelStatusPtmGroup OBJECT-GROUP
         OBJECTS
             {
             xdsl2ChStatusPtmStatus
             }
         STATUS     current
         DESCRIPTION
             "The group of status objects on the data path level
             when it is PTM."
         ::= { vdsl2Groups 4 }

      vdsl2SCStatusGroup OBJECT-GROUP
         OBJECTS
             {
             xdsl2SCStatusMtime,
             xdsl2SCStatusSnr,
             xdsl2SCStatusBitsAlloc,
             xdsl2SCStatusGainAlloc,
             xdsl2SCStatusTssi,
             xdsl2SCStatusLinScale,
             xdsl2SCStatusLinReal,
             xdsl2SCStatusLinImg,
             xdsl2SCStatusLogMt,
             xdsl2SCStatusLog,
             xdsl2SCStatusQlnMt,
             xdsl2SCStatusQln,
             xdsl2SCStatusLnAtten,
             xdsl2SCStatusSigAtten,
             xdsl2SCStatusSnrMargin,
             xdsl2SCStatusAttainableRate,
             xdsl2SCStatusActAtp,
             xdsl2SCStatusRowStatus
             }
         STATUS     current
         DESCRIPTION
             "The group of status objects on the sub-carrier level.
             They are updated as a result of a DELT process."
         ::= { vdsl2Groups 5 }

      vdsl2LineInventoryGroup OBJECT-GROUP
         OBJECTS
             {
             xdsl2LInvG994VendorId,
             xdsl2LInvSystemVendorId,
             xdsl2LInvVersionNumber,
             xdsl2LInvSerialNumber,
             xdsl2LInvSelfTestResult,
             xdsl2LInvTransmissionCapabilities
             }
         STATUS     current
         DESCRIPTION
             "The group of inventory objects per xTU."
         ::= { vdsl2Groups 6 }

      vdsl2LineConfTemplateGroup OBJECT-GROUP
         OBJECTS
             {
             xdsl2LConfTempLineProfile,
             xdsl2LConfTempChan1ConfProfile,
             xdsl2LConfTempChan1RaRatioDs,
             xdsl2LConfTempChan1RaRatioUs,
             xdsl2LConfTempChan2ConfProfile,
             xdsl2LConfTempChan2RaRatioDs,
             xdsl2LConfTempChan2RaRatioUs,
             xdsl2LConfTempChan3ConfProfile,
             xdsl2LConfTempChan3RaRatioDs,
             xdsl2LConfTempChan3RaRatioUs,
             xdsl2LConfTempChan4ConfProfile,
             xdsl2LConfTempChan4RaRatioDs,
             xdsl2LConfTempChan4RaRatioUs,
             xdsl2LConfTempRowStatus
             }
         STATUS     current
         DESCRIPTION
             "The group of objects in a line configuration template."
         ::= { vdsl2Groups 7 }

      vdsl2LineConfProfGroup OBJECT-GROUP
         OBJECTS
             {
             xdsl2LConfProfScMaskDs,
             xdsl2LConfProfScMaskUs,
             xdsl2LConfProfRfiBandsDs,
             xdsl2LConfProfRaModeDs,
             xdsl2LConfProfRaModeUs,
             xdsl2LConfProfTargetSnrmDs,
             xdsl2LConfProfTargetSnrmUs,
             xdsl2LConfProfMaxSnrmDs,
             xdsl2LConfProfMaxSnrmUs,
             xdsl2LConfProfMinSnrmDs,
             xdsl2LConfProfMinSnrmUs,
             xdsl2LConfProfAtuTransSysEna,
             xdsl2LConfProfPmMode,
             xdsl2LConfProfL0Time,
             xdsl2LConfProfL2Time,
             xdsl2LConfProfL2Atpr,
             xdsl2LConfProfL2Atprt,
             xdsl2LConfProfRowStatus
             }
         STATUS     current
         DESCRIPTION
             "The group of objects in a line configuration profile."
         ::= { vdsl2Groups 8 }

      vdsl2LineConfProfRaGroup OBJECT-GROUP
         OBJECTS
             {
             xdsl2LConfProfRaUsNrmDs,
             xdsl2LConfProfRaUsNrmUs,
             xdsl2LConfProfRaUsTimeDs,
             xdsl2LConfProfRaUsTimeUs,
             xdsl2LConfProfRaDsNrmsDs,
             xdsl2LConfProfRaDsNrmsUs,
             xdsl2LConfProfRaDsTimeDs,
             xdsl2LConfProfRaDsTimeUs
             }
         STATUS     current
         DESCRIPTION
           "The group of objects required for controlling the rate
           adaptive behavior of the line."
         ::= { vdsl2Groups 9 }

      vdsl2LineConfProfMsgMinGroup OBJECT-GROUP
         OBJECTS
             {
             xdsl2LConfProfMsgMinUs,
             xdsl2LConfProfMsgMinDs
             }
         STATUS     current
         DESCRIPTION
           "The group of objects required for controlling the rate
           reserved for Overhead traffic."
         ::= { vdsl2Groups 10 }

      vdsl2LineConfProfModeSpecGroup OBJECT-GROUP
         OBJECTS
             {
             xdsl2LConfProfMaxNomPsdDs,
             xdsl2LConfProfMaxNomPsdUs,
             xdsl2LConfProfMaxNomAtpDs,
             xdsl2LConfProfMaxNomAtpUs,
             xdsl2LConfProfMaxAggRxPwrUs,
             xdsl2LConfProfPsdMaskDs,
             xdsl2LConfProfPsdMaskUs,
             xdsl2LConfProfPsdMaskSelectUs,
             xdsl2LConfProfModeSpecRowStatus
             }
         STATUS     current
         DESCRIPTION
             "The group of objects in a line configuration profile
             that have an instance for each operation mode allowed."
         ::= { vdsl2Groups 11 }

      vdsl2ChConfProfileGroup OBJECT-GROUP
         OBJECTS
             {
             xdsl2ChConfProfMinDataRateDs,
             xdsl2ChConfProfMinDataRateUs,
             xdsl2ChConfProfMaxDataRateDs,
             xdsl2ChConfProfMaxDataRateUs,
             xdsl2ChConfProfMinDataRateLowPwrDs,
             xdsl2ChConfProfMaxDelayDs,
             xdsl2ChConfProfMaxDelayUs,
             xdsl2ChConfProfMinProtectionDs,
             xdsl2ChConfProfMinProtectionUs,
             xdsl2ChConfProfMaxBerDs,
             xdsl2ChConfProfMaxBerUs,
             xdsl2ChConfProfUsDataRateDs,
             xdsl2ChConfProfDsDataRateDs,
             xdsl2ChConfProfUsDataRateUs,
             xdsl2ChConfProfDsDataRateUs,
             xdsl2ChConfProfRowStatus
             }
         STATUS     current
         DESCRIPTION
            "The group of objects in a channel configuration profile."
         ::= { vdsl2Groups 12 }

      vdsl2ChConfProfileAtmGroup OBJECT-GROUP
         OBJECTS
             {
             xdsl2ChConfProfImaEnabled,
             xdsl2ChStatusAtmStatus
             }
         STATUS     current
         DESCRIPTION
           "The group of configuration objects required when the data
           path is ATM."
         ::= { vdsl2Groups 13 }

      vdsl2ChConfProfileMinResGroup OBJECT-GROUP
         OBJECTS
             {
             xdsl2ChConfProfMinResDataRateDs,
             xdsl2ChConfProfMinResDataRateUs
             }
         STATUS     current
         DESCRIPTION
           "The group of configuration objects required for the
           reserved data rate."
         ::= { vdsl2Groups 14 }

      vdsl2LineAlarmConfTemplateGroup OBJECT-GROUP
         OBJECTS
             {
             xdsl2LAlarmConfTempLineProfile,
             xdsl2LAlarmConfTempChan1ConfProfile,
             xdsl2LAlarmConfTempChan2ConfProfile,
             xdsl2LAlarmConfTempChan3ConfProfile,
             xdsl2LAlarmConfTempChan4ConfProfile,
             xdsl2LAlarmConfTempRowStatus
             }
         STATUS     current
         DESCRIPTION
             "The group of objects in a line alarm
              template."
         ::= { vdsl2Groups 15 }

      vdsl2LineAlarmConfProfileGroup OBJECT-GROUP
         OBJECTS
             {
             xdsl2LineAlarmConfProfileXtucThresh15MinFecs,
             xdsl2LineAlarmConfProfileXtucThresh15MinEs,
             xdsl2LineAlarmConfProfileXtucThresh15MinSes,
             xdsl2LineAlarmConfProfileXtucThresh15MinLoss,
             xdsl2LineAlarmConfProfileXtucThresh15MinUas,
             xdsl2LineAlarmConfProfileXturThresh15MinFecs,
             xdsl2LineAlarmConfProfileXturThresh15MinEs,
             xdsl2LineAlarmConfProfileXturThresh15MinSes,
             xdsl2LineAlarmConfProfileXturThresh15MinLoss,
             xdsl2LineAlarmConfProfileXturThresh15MinUas,
             xdsl2LineAlarmConfProfileThresh15MinFailedFullInt,
             xdsl2LineAlarmConfProfileThresh15MinFailedShrtInt,
             xdsl2LineAlarmConfProfileRowStatus
             }
         STATUS     current
         DESCRIPTION
             "The group of objects in a line alarm profile."
         ::= { vdsl2Groups 16 }

      vdsl2ChAlarmConfProfileGroup OBJECT-GROUP
         OBJECTS
             {
             xdsl2ChAlarmConfProfileAtucThresh15MinCodingViolations,
             xdsl2ChAlarmConfProfileAtucThresh15MinCorrected,
             xdsl2ChAlarmConfProfileAturThresh15MinCodingViolations,
             xdsl2ChAlarmConfProfileAturThresh15MinCorrected,
             xdsl2ChAlarmConfProfileRowStatus
             }
         STATUS     current
         DESCRIPTION
             "The group of objects in a channel alarm profile."
         ::= { vdsl2Groups 17 }

      vdsl2PMLineCurrGroup OBJECT-GROUP
         OBJECTS
             {
             xdsl2PMLCurrValidIntervals,
             xdsl2PMLCurrInvalidIntervals,
             xdsl2PMLCurr15MTimeElapsed,
             xdsl2PMLCurr15MFecs,
             xdsl2PMLCurr15MEs,
             xdsl2PMLCurr15MSes,
             xdsl2PMLCurr15MLoss,
             xdsl2PMLCurr15MUas,
             xdsl2PMLCurr1DayValidIntervals,
             xdsl2PMLCurr1DayInvalidIntervals,
             xdsl2PMLCurr1DayTimeElapsed,
             xdsl2PMLCurr1DayFecs,
             xdsl2PMLCurr1DayEs,
             xdsl2PMLCurr1DaySes,
             xdsl2PMLCurr1DayLoss,
             xdsl2PMLCurr1DayUas
             }
         STATUS     current
         DESCRIPTION
           "The group of objects that report the line level
           counters for current PM intervals."
         ::= { vdsl2Groups 18 }

      vdsl2PMLineCurrInitGroup OBJECT-GROUP
         OBJECTS
             {
             xdsl2PMLCurrInit15MTimeElapsed,
             xdsl2PMLCurrInit15MFullInits,
             xdsl2PMLCurrInit15MFailedFullInits,
             xdsl2PMLCurrInit1DayTimeElapsed,
             xdsl2PMLCurrInit1DayFullInits,
             xdsl2PMLCurrInit1DayFailedFullInits
             }
         STATUS     current
         DESCRIPTION
           "The group of objects that report the full
           initializations counters for current PM intervals."
         ::= { vdsl2Groups 19 }

      vdsl2PMLineCurrInitShortGroup OBJECT-GROUP
         OBJECTS
             {
             xdsl2PMLCurrInit15MShortInits,
             xdsl2PMLCurrInit15MFailedShortInits,
             xdsl2PMLCurrInit1DayShortInits,
             xdsl2PMLCurrInit1DayFailedShortInits
             }
         STATUS     current
         DESCRIPTION
           "The group of objects that report the short
           initializations counters for current PM intervals."
         ::= { vdsl2Groups 20 }

      vdsl2PMLineHist15MinGroup OBJECT-GROUP
         OBJECTS
             {
             xdsl2PMLHist15MMonitoredTime,
             xdsl2PMLHist15MFecs,
             xdsl2PMLHist15MEs,
             xdsl2PMLHist15MSes,
             xdsl2PMLHist15MLoss,
             xdsl2PMLHist15MUas,
             xdsl2PMLHist15MValidInterval
             }
         STATUS     current
         DESCRIPTION
           "The group of line level PM counters for the previous
           15 minutes intervals."
         ::= { vdsl2Groups 21 }

      vdsl2PMLineHist1DayGroup OBJECT-GROUP
         OBJECTS
             {
             xdsl2PMLHist1DMonitoredTime,
             xdsl2PMLHist1DFecs,
             xdsl2PMLHist1DEs,
             xdsl2PMLHist1DSes,
             xdsl2PMLHist1DLoss,
             xdsl2PMLHist1DUas,
             xdsl2PMLHist1DValidInterval
             }
         STATUS     current
         DESCRIPTION
           "The group of line level PM counters for the previous
           24 hours intervals."
         ::= { vdsl2Groups 22 }

      vdsl2PMLineInitHist15MinGroup OBJECT-GROUP
         OBJECTS
             {
             xdsl2PMLHistInit15MMonitoredTime,
             xdsl2PMLHistInit15MFullInits,
             xdsl2PMLHistInit15MFailedFullInits,
             xdsl2PMLHistInit15MValidInterval
             }
         STATUS     current
         DESCRIPTION
           "The group of PM counters for the previous 15 minutes
           intervals full initializations."
         ::= { vdsl2Groups 23 }

      vdsl2PMLineInitHist15MinShortGroup OBJECT-GROUP
         OBJECTS
             {
             xdsl2PMLHistInit15MShortInits,
             xdsl2PMLHistInit15MFailedShortInits
             }
         STATUS     current
         DESCRIPTION
           "The group of PM counters for the previous 15 minutes
           intervals short initializations."
         ::= { vdsl2Groups 24 }

      vdsl2PMLineInitHist1DayGroup OBJECT-GROUP
         OBJECTS
             {
             xdsl2PMLHistinit1DMonitoredTime,
             xdsl2PMLHistinit1DFullInits,
             xdsl2PMLHistinit1DFailedFullInits,
             xdsl2PMLHistinit1DValidInterval
             }
         STATUS     current
         DESCRIPTION
           "The group of PM counters for the previous 24 hours
           intervals full initializations."
         ::= { vdsl2Groups 25 }

      vdsl2PMLineInitHist1DayShortGroup OBJECT-GROUP
         OBJECTS
             {
             xdsl2PMLHistinit1DShortInits,
             xdsl2PMLHistinit1DFailedShortInits
             }
         STATUS     current
         DESCRIPTION
           "The group of PM counters for the previous 24 hours
           intervals short initializations."
         ::= { vdsl2Groups 26 }

      vdsl2PMChCurrGroup OBJECT-GROUP
         OBJECTS
             {
             xdsl2PMChCurrValidIntervals,
             xdsl2PMChCurrInvalidIntervals,
             xdsl2PMChCurr15MTimeElapsed,
             xdsl2PMChCurr15MCodingViolations,
             xdsl2PMChCurr15MCorrectedBlocks,
             xdsl2PMChCurr1DayValidIntervals,
             xdsl2PMChCurr1DayInvalidIntervals,
             xdsl2PMChCurr1DayTimeElapsed,
             xdsl2PMChCurr1DayCodingViolations,
             xdsl2PMChCurr1DayCorrectedBlocks
             }
         STATUS     current
         DESCRIPTION
           "The group of objects that report the channel level
           counters for current PM intervals."
         ::= { vdsl2Groups 27 }

      vdsl2PMChHist15MinGroup OBJECT-GROUP
         OBJECTS
             {
             xdsl2PMChHist15MMonitoredTime,
             xdsl2PMChHist15MCodingViolations,
             xdsl2PMChHist15MCorrectedBlocks,
             xdsl2PMChHist15MValidInterval
             }
         STATUS     current
         DESCRIPTION
           "The group of objects that report the channel level
           counters for previous 15 minutes PM intervals."
         ::= { vdsl2Groups 28 }

      vdsl2PMChHist1DGroup OBJECT-GROUP
         OBJECTS
             {
             xdsl2PMChHist1DMonitoredTime,
             xdsl2PMChHist1DCodingViolations,
             xdsl2PMChHist1DCorrectedBlocks,
             xdsl2PMChHist1DValidInterval
             }
         STATUS     current
         DESCRIPTION
           "The group of objects that report the channel level
           counters for previous 24 hours PM intervals."
         ::= { vdsl2Groups 29 }

      vdsl2ScalarSCGroup OBJECT-GROUP
         OBJECTS
             {
             xdsl2ScalarSCMaxInterfaces,
             xdsl2ScalarSCAvailInterfaces
             }
         STATUS     current
         DESCRIPTION
           "The group of objects that report the available memory
           resources for DELT processes."
         ::= { vdsl2Groups 30 }

      vdsl2ThreshNotificationGroup NOTIFICATION-GROUP
         NOTIFICATIONS
         {
         xdsl2LinePerfFECSThreshAtuc,
         xdsl2LinePerfFECSThreshAtur,
         xdsl2LinePerfESThreshAtuc,
         xdsl2LinePerfESThreshAtur,
         xdsl2LinePerfSESThreshAtuc,
         xdsl2LinePerfSESThreshAtur,
         xdsl2LinePerfLOSSThreshAtuc,
         xdsl2LinePerfLOSSThreshAtur,
         xdsl2LinePerfUASThreshAtuc,
         xdsl2LinePerfUASThreshAtur,
         xdsl2LinePerfCodingViolationsThreshAtuc,
         xdsl2LinePerfCodingViolationsThreshAtur,
         xdsl2LinePerfCorrectedThreshAtuc,
         xdsl2LinePerfCorrectedThreshAtur,
         xdsl2LinePerfFailedFullInitThresh,
         xdsl2LinePerfFailedShortInitThresh
         }
         STATUS      current
         DESCRIPTION
           "This group supports notifications of significant conditions
           associated with DSL lines."
         ::= { vdsl2Groups 31 }

      vdsl2StatusChangeNotificationGroup NOTIFICATION-GROUP
         NOTIFICATIONS
         {
         xdsl2LineStatusChangeAtuc,
         xdsl2LineStatusChangeAtur
         }
         STATUS      current
         DESCRIPTION
           "This group supports notifications of thresholds crossing
           associated with DSL lines."
         ::= { vdsl2Groups 32 }

   END

-- 
--    Copyright (C) The Internet Society (2006).  This document is subject
--    to the rights, licenses and restrictions contained in BCP 78, and
--    except as set forth therein, the authors retain all their rights.
-- 
-- 
-- Acknowledgment
-- 
--    Funding for the RFC Editor function is currently provided by the
--    Internet Society.
