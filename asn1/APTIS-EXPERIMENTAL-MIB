--
--	Aptis Enterprise MIB
--	Administractive Actions Module
-- 
--	Nortel Networks
--	11 Elizabeth Drive
--	Chelmsford, MA 01824
--
--	Copyright (c) 1997-2000 Nortel Networks
--	All Rights Reserved.
--

APTIS-EXPERIMENTAL-MIB DEFINITIONS ::= BEGIN

    IMPORTS
        aptis-exp, Boolean
            FROM APTIS-MIB
	aptis-modules
 	    FROM APTIS-REG-MIB
        MODULE-IDENTITY, OBJECT-TYPE, IpAddress
            FROM SNMPv2-SMI
        DisplayString, RowStatus
            FROM SNMPv2-TC;

    aptisExpModule MODULE-IDENTITY
        LAST-UPDATED "9801010000Z"
        ORGANIZATION "Aptis Communications, Inc."
        CONTACT-INFO
            "        Customer Service Department
                     Aptis Communications, Inc.

             Email: support@aptis.com"

        DESCRIPTION
            "The following variables describe the administrative actions
            that may be invoked through SNMP."

    ::= { aptis-modules 6 }


--
--	This section is currently empty.
--

END
