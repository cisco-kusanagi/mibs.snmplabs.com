-- *****************************************
-- Network System Corporation Enterprise MIB
-- *****************************************
--
-- Title:           NSC-TCP-EXCEL-TRAP
-- Purpose:         This MIB defines the managed objects for NSC TCPexcel.
-- Required MIBS:   nsc.mib
--
-- Version:         1.0
-- 1st Edition:     Nov. 22, 1994     Tony Johnson
-- Last Update:     Mar. 17, 1995     Tony Johnson


 NSC-TCP-EXCEL-MIB DEFINITIONS ::= BEGIN

          IMPORTS
                  IpAddress, Counter, Gauge     FROM RFC1155-SMI
		  nscDx                         FROM NSC-MIB
                  OBJECT-TYPE                   FROM RFC-1212
                  DisplayString         	FROM RFC1213-MIB;


          --  This is the MIB module for the PDTCP3 objects 
          --  based on MIB-II (same prefix as MIB-I)
          --  with extended statistics

          nscDxTcpXcel      OBJECT IDENTIFIER ::= { nscDx 6 }


          -- groups in the PDTCP3 MIB module 


          nscDxTcpXcelTcp          OBJECT IDENTIFIER ::= { nscDxTcpXcel 1 }

          nscDxTcpXcelUdp          OBJECT IDENTIFIER ::= { nscDxTcpXcel 2 }


          -- the TCP group

          -- Implementation of the TCP group is mandatory for all
          -- systems that implement the TCP.

          -- Note that instances of object types that represent
          -- information about a particular TCP connection are
          -- transient; they persist only as long as the connection
          -- in question.

          nscDxTcpXcelTcpRtoAlgorithm OBJECT-TYPE
              SYNTAX  INTEGER {
                          other(1),    -- none of the following
                          constant(2), -- a constant rto
                          rsre(3),     -- MIL-STD-1778, Appendix B
                          vanj(4)      -- Van Jacobson's algorithm [10]
                      }
              ACCESS  read-only
              STATUS  mandatory
              DESCRIPTION
                      "The algorithm used to determine the timeout value
                      used for retransmitting unacknowledged octets."
              ::= { nscDxTcpXcelTcp 1 }

          nscDxTcpXcelTcpRtoMin OBJECT-TYPE
              SYNTAX  INTEGER
              ACCESS  read-only
              STATUS  mandatory
              DESCRIPTION
                      "The minimum value permitted by a TCP
                      implementation for the retransmission timeout,
                      measured in milliseconds.  More refined semantics
                      for objects of this type depend upon the algorithm
                      used to determine the retransmission timeout.  In
                      particular, when the timeout algorithm is rsre(3),
                      an object of this type has the semantics of the
                      LBOUND quantity described in RFC 793."
              ::= { nscDxTcpXcelTcp 2 }


          nscDxTcpXcelTcpRtoMax OBJECT-TYPE
              SYNTAX  INTEGER
              ACCESS  read-only
              STATUS  mandatory
              DESCRIPTION
                      "The maximum value permitted by a TCP
                      implementation for the retransmission timeout,
                      measured in milliseconds.  More refined semantics
                      for objects of this type depend upon the algorithm
                      used to determine the retransmission timeout.  In
                      particular, when the timeout algorithm is rsre(3),
                      an object of this type has the semantics of the
                      UBOUND quantity described in RFC 793."
              ::= { nscDxTcpXcelTcp 3 }

          nscDxTcpXcelTcpMaxConn OBJECT-TYPE
              SYNTAX  INTEGER
              ACCESS  read-only
              STATUS  mandatory
              DESCRIPTION
                      "The limit on the total number of TCP connections
                      the entity can support.  In entities where the
                      maximum number of connections is dynamic, this
                      object should contain the value -1."
              ::= { nscDxTcpXcelTcp 4 }

          nscDxTcpXcelTcpActiveOpens OBJECT-TYPE
              SYNTAX  Counter
              ACCESS  read-only
              STATUS  mandatory
              DESCRIPTION
                      "The number of times TCP connections have made a
                      direct transition to the SYN-SENT state from the
                      CLOSED state."
              ::= { nscDxTcpXcelTcp 5 }

          nscDxTcpXcelTcpPassiveOpens OBJECT-TYPE
              SYNTAX  Counter
              ACCESS  read-only
              STATUS  mandatory
              DESCRIPTION
                      "The number of times TCP connections have made a
                      direct transition to the SYN-RCVD state from the
                      LISTEN state."
              ::= { nscDxTcpXcelTcp 6 }
          nscDxTcpXcelTcpAttemptFails OBJECT-TYPE
              SYNTAX  Counter
              ACCESS  read-only
              STATUS  mandatory
              DESCRIPTION
                      "The number of times TCP connections have made a
                      direct transition to the CLOSED state from either
                      the SYN-SENT state or the SYN-RCVD state, plus the
                      number of times TCP connections have made a direct
                      transition to the LISTEN state from the SYN-RCVD
                      state."
              ::= { nscDxTcpXcelTcp 7 }

          nscDxTcpXcelTcpEstabResets OBJECT-TYPE
              SYNTAX  Counter
              ACCESS  read-only
              STATUS  mandatory
              DESCRIPTION
                      "The number of times TCP connections have made a
                      direct transition to the CLOSED state from either
                      the ESTABLISHED state or the CLOSE-WAIT state."
              ::= { nscDxTcpXcelTcp 8 }

          nscDxTcpXcelTcpCurrEstab OBJECT-TYPE
              SYNTAX  Gauge
              ACCESS  read-only
              STATUS  mandatory
              DESCRIPTION
                      "The number of TCP connections for which the
                      current state is either ESTABLISHED or CLOSE-
                      WAIT."
              ::= { nscDxTcpXcelTcp 9 }

          nscDxTcpXcelTcpInSegs OBJECT-TYPE
              SYNTAX  Counter
              ACCESS  read-only
              STATUS  mandatory
              DESCRIPTION
                      "The total number of segments received, including
                      those received in error.  This count includes
                      segments received on currently established
                      connections."
              ::= { nscDxTcpXcelTcp 10 }

          nscDxTcpXcelTcpOutSegs OBJECT-TYPE
              SYNTAX  Counter
              ACCESS  read-only
              STATUS  mandatory
              DESCRIPTION
                      "The total number of segments sent, including
                      those on current connections but excluding those
                      containing only retransmitted octets."
              ::= { nscDxTcpXcelTcp 11 }

          nscDxTcpXcelTcpRetransSegs OBJECT-TYPE
              SYNTAX  Counter
              ACCESS  read-only
              STATUS  mandatory
              DESCRIPTION
                      "The total number of segments retransmitted - that
                      is, the number of TCP segments transmitted
                      containing one or more previously transmitted
                      octets."
              ::= { nscDxTcpXcelTcp 12 }


          -- the TCP Connection table

          -- The TCP connection table contains information about this
          -- entity's existing TCP connections.

          nscDxTcpXcelTcpConnTable OBJECT-TYPE
              SYNTAX  SEQUENCE OF NscDxTcpXcelTcpConnEntry
              ACCESS  not-accessible
              STATUS  mandatory
              DESCRIPTION
                      "A table containing TCP connection-specific
                      information."
              ::= { nscDxTcpXcelTcp 13 }

          nscDxTcpXcelTcpConnEntry OBJECT-TYPE
              SYNTAX  NscDxTcpXcelTcpConnEntry
              ACCESS  not-accessible
              STATUS  mandatory
              DESCRIPTION
                      "Information about a particular current TCP
                      connection.  An object of this type is transient,
                      in that it ceases to exist when (or soon after)
                      the connection makes the transition to the CLOSED
                      state."
              INDEX   { nscDxTcpXcelTcpSapId }
              ::= { nscDxTcpXcelTcpConnTable 1 }

          NscDxTcpXcelTcpConnEntry ::=
              SEQUENCE {
                 nscDxTcpXcelTcpSapId
                      INTEGER (1..65535),
                 nscDxTcpXcelTcpHostIdx
                      INTEGER (1..3),
                 nscDxTcpXcelTcpHostName
                      DisplayString (SIZE (0..255)),
                 nscDxTcpXcelTcpConnState
                      INTEGER,
                 nscDxTcpXcelTcpConnLocalAddress
                      IpAddress,
                 nscDxTcpXcelTcpConnLocalPort
                      INTEGER (0..65535),
                 nscDxTcpXcelTcpConnRemAddress
                      IpAddress,
                 nscDxTcpXcelTcpConnRemPort
                      INTEGER (0..65535)
              }

          nscDxTcpXcelTcpSapId OBJECT-TYPE
              SYNTAX  INTEGER (1..65535)
              ACCESS  read-only
              STATUS  mandatory
              DESCRIPTION
                      "The SAP ID number for this TCP listener."
              ::= { nscDxTcpXcelTcpConnEntry 1 }

          nscDxTcpXcelTcpHostIdx OBJECT-TYPE
              SYNTAX  INTEGER (1..3)
              ACCESS  read-only
              STATUS  mandatory
              DESCRIPTION
                      "The logical host number for this TCP connection."
              ::= { nscDxTcpXcelTcpConnEntry 2 }

          nscDxTcpXcelTcpHostName OBJECT-TYPE
              SYNTAX  DisplayString (SIZE (0..255))
              ACCESS  read-only
              STATUS  mandatory
              DESCRIPTION
                      "The logical host name for this TCP connection."
              ::= { nscDxTcpXcelTcpConnEntry 3 }

          nscDxTcpXcelTcpConnState OBJECT-TYPE
              SYNTAX  INTEGER {
                          closed(1),
                          listen(2),
                          synSent(3),
                          synReceived(4),
                          established(5),
                          finWait1(6),
                          finWait2(7),
                          closeWait(8),
                          lastAck(9),
                          closing(10),
                          timeWait(11)
                      }
              ACCESS  read-only
              STATUS  mandatory
              DESCRIPTION
                      "The state of this TCP connection."
              ::= { nscDxTcpXcelTcpConnEntry 4 }

          nscDxTcpXcelTcpConnLocalAddress OBJECT-TYPE
              SYNTAX  IpAddress
              ACCESS  read-only
              STATUS  mandatory
              DESCRIPTION
                      "The local IP address for this TCP connection.  In
                      the case of a connection in the listen state which
                      is willing to accept connections for any IP
                      interface associated with the node, the value
                      0.0.0.0 is used."
              ::= { nscDxTcpXcelTcpConnEntry 5 }

          nscDxTcpXcelTcpConnLocalPort OBJECT-TYPE
              SYNTAX  INTEGER (0..65535)
              ACCESS  read-only
              STATUS  mandatory
              DESCRIPTION
                      "The local port number for this TCP connection."
              ::= { nscDxTcpXcelTcpConnEntry 6 }

          nscDxTcpXcelTcpConnRemAddress OBJECT-TYPE
              SYNTAX  IpAddress
              ACCESS  read-only
              STATUS  mandatory
              DESCRIPTION
                      "The remote IP address for this TCP connection."
              ::= { nscDxTcpXcelTcpConnEntry 7 }

          nscDxTcpXcelTcpConnRemPort OBJECT-TYPE
              SYNTAX  INTEGER (0..65535)
              ACCESS  read-only
              STATUS  mandatory
              DESCRIPTION
                      "The remote port number for this TCP connection."
              ::= { nscDxTcpXcelTcpConnEntry 8 }



          -- additional TCP objects

          nscDxTcpXcelTcpInErrs OBJECT-TYPE
              SYNTAX  Counter
              ACCESS  read-only
              STATUS  mandatory
              DESCRIPTION
                      "The total number of segments received in error
                      (e.g., bad TCP checksums)."
              ::= { nscDxTcpXcelTcp 14 }

          nscDxTcpXcelTcpOutRsts OBJECT-TYPE
              SYNTAX  Counter
              ACCESS  read-only
              STATUS  mandatory
              DESCRIPTION
                      "The number of TCP segments sent containing the
                      RST flag. This object is not supported in this
                      version."
              ::= { nscDxTcpXcelTcp 15 }


         -- extended   TCP statistics
         -- collected by PDTCP3


        nscDxTcpXcelTcpConnAttempt OBJECT-TYPE
              SYNTAX  Counter
              ACCESS  read-only
              STATUS  mandatory
              DESCRIPTION
                      "The total number of connections initiated. "
              ::= { nscDxTcpXcelTcp 16 }

         nscDxTcpXcelTcpClosed OBJECT-TYPE
              SYNTAX  Counter
              ACCESS  read-only
              STATUS  mandatory
              DESCRIPTION
                      "The total number of connections closed."
              ::= { nscDxTcpXcelTcp 17 }

        nscDxTcpXcelTcpSegsTimed OBJECT-TYPE
              SYNTAX  Counter
              ACCESS  read-only
              STATUS  mandatory
              DESCRIPTION
                      "The total number of segments we tried to get rtt."
                  ::= { nscDxTcpXcelTcp 18 }

         nscDxTcpXcelTcpRttUpdated OBJECT-TYPE
              SYNTAX  Counter
              ACCESS  read-only
              STATUS  mandatory
              DESCRIPTION
                      "The total number of rtt segments updated."
                   ::= { nscDxTcpXcelTcp 19 }

        nscDxTcpXcelTcpDelAck OBJECT-TYPE
              SYNTAX  Counter
              ACCESS  read-only
              STATUS  mandatory
              DESCRIPTION
                      "The total number of delayed acks sent."
                      ::= { nscDxTcpXcelTcp 20 }

         nscDxTcpXcelTcpTimeoutDrop OBJECT-TYPE
              SYNTAX  Counter
              ACCESS  read-only
              STATUS  mandatory
              DESCRIPTION
                      "The total number of conn. dropped in rxmt timeout."
                    ::= { nscDxTcpXcelTcp 21 }

        nscDxTcpXcelTcpRexmtTimeo OBJECT-TYPE
              SYNTAX  Counter
              ACCESS  read-only
              STATUS  mandatory
              DESCRIPTION
                      "The total number of retransmit timeouts."
                ::= { nscDxTcpXcelTcp 22 }

         nscDxTcpXcelTcpPersistTimeo OBJECT-TYPE
              SYNTAX  Counter
              ACCESS  read-only
              STATUS  mandatory
              DESCRIPTION
                      "The total number of persist timeouts."
              ::= { nscDxTcpXcelTcp  23 }

        nscDxTcpXcelTcpKeepTimeo OBJECT-TYPE
              SYNTAX  Counter
              ACCESS  read-only
              STATUS  mandatory
              DESCRIPTION
                      "The total number of keepalive timeouts."
                ::= { nscDxTcpXcelTcp 24 }

         nscDxTcpXcelTcpKeepProbe OBJECT-TYPE
              SYNTAX  Counter
              ACCESS  read-only
              STATUS  mandatory
              DESCRIPTION
                      "The total number of keepalive probes sent."
                    ::= { nscDxTcpXcelTcp 25 }

        nscDxTcpXcelTcpKeepDrop OBJECT-TYPE
              SYNTAX  Counter
              ACCESS  read-only
              STATUS  mandatory
              DESCRIPTION
                      "The total number of connections dropped in keepalive."
                  ::= { nscDxTcpXcelTcp 26 }

         nscDxTcpXcelTcpSndPack OBJECT-TYPE
              SYNTAX  Counter
              ACCESS  read-only
              STATUS  mandatory
              DESCRIPTION
                      "The total number of data packets sent."
              ::= { nscDxTcpXcelTcp 27 }

        nscDxTcpXcelTcpSndByte OBJECT-TYPE
              SYNTAX  Counter
              ACCESS  read-only
              STATUS  mandatory
              DESCRIPTION
                      "The total number of data bytes sent."
              ::= { nscDxTcpXcelTcp 28 }

         nscDxTcpXcelTcpSndRexmitPack OBJECT-TYPE
              SYNTAX  Counter
              ACCESS  read-only
              STATUS  mandatory
              DESCRIPTION
                      "The total number of data packets retransmitted."
                ::= { nscDxTcpXcelTcp 29 }

        nscDxTcpXcelTcpSndRexmitByte OBJECT-TYPE
              SYNTAX  Counter
              ACCESS  read-only
              STATUS  mandatory
              DESCRIPTION
                      "The total number of data bytes retransmitted."
               ::= { nscDxTcpXcelTcp 30 }

         nscDxTcpXcelTcpSndAcks OBJECT-TYPE
              SYNTAX  Counter
              ACCESS  read-only
              STATUS  mandatory
              DESCRIPTION
                      "The total number of ack-only packets sent."
              ::= { nscDxTcpXcelTcp 31 }

        nscDxTcpXcelTcpSndProbe OBJECT-TYPE
              SYNTAX  Counter
              ACCESS  read-only
              STATUS  mandatory
              DESCRIPTION
                      "The total number of window probes sent."
                ::= { nscDxTcpXcelTcp 32 }

         nscDxTcpXcelTcpSndUrg OBJECT-TYPE
              SYNTAX  Counter
              ACCESS  read-only
              STATUS  mandatory
              DESCRIPTION
                      "The total number of packets sent with URG only."
                      ::= { nscDxTcpXcelTcp 33 }

        nscDxTcpXcelTcpSndWinUp OBJECT-TYPE
              SYNTAX  Counter
              ACCESS  read-only
              STATUS  mandatory
              DESCRIPTION
                      "The total number of window update only packets sent."
               ::= { nscDxTcpXcelTcp 34}

         nscDxTcpXcelTcpSndCtrl OBJECT-TYPE
              SYNTAX  Counter
              ACCESS  read-only
              STATUS  mandatory
              DESCRIPTION
                      "The total number of control (syn|fin|rst) packets sent."
                   ::= { nscDxTcpXcelTcp 35 }

        nscDxTcpXcelTcpPcbCacheMiss OBJECT-TYPE
              SYNTAX  Counter
              ACCESS  read-only
              STATUS  mandatory
              DESCRIPTION
                      "The total number of input packets missing
                      pcb cache."
               ::= { nscDxTcpXcelTcp 36 }

         nscDxTcpXcelTcpRcvPack OBJECT-TYPE
              SYNTAX  Counter
              ACCESS  read-only
              STATUS  mandatory
              DESCRIPTION
                      "The total number of packets received in sequence."
              ::= { nscDxTcpXcelTcp 37 }

        nscDxTcpXcelTcpRcvBytes OBJECT-TYPE
              SYNTAX  Counter
              ACCESS  read-only
              STATUS  mandatory
              DESCRIPTION
                      "The total number of bytes received in Sequence."
               ::= { nscDxTcpXcelTcp 38 }

         nscDxTcpXcelTcpRcvByteAfterWin OBJECT-TYPE
              SYNTAX  Counter
              ACCESS  read-only
              STATUS  mandatory
              DESCRIPTION
                      "The total number of bytes rcvd after window."
              ::= { nscDxTcpXcelTcp 39 }

        nscDxTcpXcelTcpRcvAfterClose OBJECT-TYPE
              SYNTAX  Counter
              ACCESS  read-only
              STATUS  mandatory
              DESCRIPTION
                      "The total number of bytes rcvd after close."
              ::= { nscDxTcpXcelTcp 40 }

         nscDxTcpXcelTcpRcvWinProbe OBJECT-TYPE
              SYNTAX  Counter
              ACCESS  read-only
              STATUS  mandatory
              DESCRIPTION
                      "The total number of rcvd window probe packets."
                       ::= { nscDxTcpXcelTcp 41 }

        nscDxTcpXcelTcpRcvdUpack OBJECT-TYPE
              SYNTAX  Counter
              ACCESS  read-only
              STATUS  mandatory
              DESCRIPTION
                      "The total number of received duplicate acks."
                    ::= { nscDxTcpXcelTcp 42 }

         nscDxTcpXcelTcpRcvAckTooMuch OBJECT-TYPE
              SYNTAX  Counter
              ACCESS  read-only
              STATUS  mandatory
              DESCRIPTION
                      "The total number of rcvd acks for unsent data."
                 ::= { nscDxTcpXcelTcp 43 }

        nscDxTcpXcelTcpRcvAckPack OBJECT-TYPE
              SYNTAX  Counter
              ACCESS  read-only
              STATUS  mandatory
              DESCRIPTION
                      "The total number of rcvd ack packets."
                 ::= { nscDxTcpXcelTcp 44 }

         nscDxTcpXcelTcpRcvAckByte OBJECT-TYPE
              SYNTAX  Counter
              ACCESS  read-only
              STATUS  mandatory
              DESCRIPTION
                      "The total number of bytes acked by rcvd acks."
               ::= { nscDxTcpXcelTcp 45 }

         nscDxTcpXcelTcpRcvWinUpd OBJECT-TYPE
              SYNTAX  Counter
              ACCESS  read-only
              STATUS  mandatory
              DESCRIPTION
                      "The total number of rcvd window update packets."
               ::= { nscDxTcpXcelTcp 46 }

          -- the UDP group

          -- Implementation of the UDP group is mandatory for all
          -- systems which implement the UDP.

          nscDxTcpXcelUdpInDatagrams OBJECT-TYPE
              SYNTAX  Counter
              ACCESS  read-only
              STATUS  mandatory
              DESCRIPTION
                      "The total number of UDP datagrams delivered to
                      UDP users."
              ::= { nscDxTcpXcelUdp 1 }

          nscDxTcpXcelUdpNoPorts OBJECT-TYPE
              SYNTAX  Counter
              ACCESS  read-only
              STATUS  mandatory
              DESCRIPTION
                      "The total number of received UDP datagrams for
                      which there was no application at the destination
                      port."
              ::= { nscDxTcpXcelUdp 2 }

          nscDxTcpXcelUdpInErrors OBJECT-TYPE
              SYNTAX  Counter
              ACCESS  read-only
              STATUS  mandatory
              DESCRIPTION
                      "The number of received UDP datagrams that could
                      not be delivered for reasons other than the lack
                      of an application at the destination port."
              ::= { nscDxTcpXcelUdp 3 }

          nscDxTcpXcelUdpOutDatagrams OBJECT-TYPE
              SYNTAX  Counter
              ACCESS  read-only
              STATUS  mandatory
              DESCRIPTION
                      "The total number of UDP datagrams sent from this
                      entity."
              ::= { nscDxTcpXcelUdp 4 }

          nscDxTcpXcelUdpNoPortBcast OBJECT-TYPE
              SYNTAX  Counter
              ACCESS  read-only
              STATUS  mandatory
              DESCRIPTION
                       "The total number of received UDP datagrams for
                      which there was no application at the destination
                      port and arrived as broadcast."
             ::= { nscDxTcpXcelUdp 5 }

          nscDxTcpXcelUdpPcbCacheMissing OBJECT-TYPE
              SYNTAX  Counter
              ACCESS  read-only
              STATUS  mandatory
              DESCRIPTION
                       "The total number of received UDP datagrams which
                       does not have a pcb cache."
             ::= { nscDxTcpXcelUdp 6 }


          -- the UDP Listener table

          -- The UDP listener table contains information about this
          -- entity's UDP end-points on which a local application is
          -- currently accepting datagrams.

          nscDxTcpXcelUdpTable OBJECT-TYPE
              SYNTAX  SEQUENCE OF NscDxTcpXcelUdpEntry
              ACCESS  not-accessible
              STATUS  mandatory
              DESCRIPTION
                      "A table containing UDP listener information."
              ::= { nscDxTcpXcelUdp 7 }

          nscDxTcpXcelUdpEntry OBJECT-TYPE
              SYNTAX  NscDxTcpXcelUdpEntry
              ACCESS  not-accessible
              STATUS  mandatory
              DESCRIPTION
                      "Information about a particular current UDP
                      listener."
              INDEX   { nscDxTcpXcelUdpSapId }
              ::= { nscDxTcpXcelUdpTable 1 }

          NscDxTcpXcelUdpEntry ::=
              SEQUENCE {
                  nscDxTcpXcelUdpSapId
                      INTEGER (1..65535),
                  nscDxTcpXcelUdpHostIdx
                      INTEGER (1..3),
                  nscDxTcpXcelUdpHostName
                      DisplayString (SIZE (0..255)),
                  nscDxTcpXcelUdpLocalAddress
                      IpAddress,
                  nscDxTcpXcelUdpLocalPort
                      INTEGER (0..65535)
              }

          nscDxTcpXcelUdpSapId OBJECT-TYPE
              SYNTAX  INTEGER (1..65535)
              ACCESS  read-only
              STATUS  mandatory
              DESCRIPTION
                      "The SAP ID number for this UDP listener."
              ::= { nscDxTcpXcelUdpEntry 1 }

          nscDxTcpXcelUdpHostIdx OBJECT-TYPE
              SYNTAX  INTEGER (1..3)
              ACCESS  read-only
              STATUS  mandatory
              DESCRIPTION
                      "The logical host number for this UDP listener."
              ::= { nscDxTcpXcelUdpEntry 2 }

         nscDxTcpXcelUdpHostName OBJECT-TYPE
              SYNTAX  DisplayString (SIZE (0..255))
              ACCESS  read-only
              STATUS  mandatory
              DESCRIPTION
                      "The logical host name for this UDP listener."
              ::= { nscDxTcpXcelUdpEntry 3 }

          nscDxTcpXcelUdpLocalAddress OBJECT-TYPE
              SYNTAX  IpAddress
              ACCESS  read-only
              STATUS  mandatory
              DESCRIPTION
                      "The local IP address for this UDP listener.  In
                      the case of a UDP listener which is willing to
                      accept datagrams for any IP interface associated
                      with the node, the value 0.0.0.0 is used."
              ::= { nscDxTcpXcelUdpEntry 4 }

          nscDxTcpXcelUdpLocalPort OBJECT-TYPE
              SYNTAX  INTEGER (0..65535)
              ACCESS  read-only
              STATUS  mandatory
              DESCRIPTION
                      "The local port number for this UDP listener."
              ::= { nscDxTcpXcelUdpEntry 5 }


          END
