--***********************************************************************\
--*                                                                       *
--*               INTEL CORPORATION PROPRIETARY INFORMATION               *
--*  This software is supplied under the terms of a license agreement or  *
--*  nondisclosure agreement with Intel Corporation and may not be copied *
--*   or disclosed except in accordance with the terms of that agreement. *
--*        Copyright (c) 1998 Intel Corporation. All Rights Reserved.     *
--*                                                                       *
--\***********************************************************************/

--/**************************************************************************
--*
--* NAME:
--*   aolnprxy.mib
--*
--* DESCRIPTION:
--* 	Alert on LAN MIB
--*	  
--*  
--*  $WorkFile: $  
--*  $Revision: 10 $  
--*  $ModTime:  $  
--*  $Author: Psaranga $  
--*
--***************************************************************************

AOLAN-MIB

DEFINITIONS ::= BEGIN

-- Title : Alert on LAN MIB version 1.0.

IMPORTS
  MODULE-IDENTITY,  
  OBJECT-TYPE,
  Integer32, IpAddress  
  FROM SNMPv2-SMI
    enterprises
	  FROM RFC1155-SMI
	DisplayString
	  FROM RFC1213-MIB
	    TRAP-TYPE
		  FROM RFC-1215
	  ;


intel                       OBJECT IDENTIFIER ::= { enterprises 343 }
products                    OBJECT IDENTIFIER ::= { intel 2 }
mangement-products          OBJECT IDENTIFIER ::= { products 8 }
tCO-products                OBJECT IDENTIFIER ::= { mangement-products 1 }
alert-on-LAN                OBJECT IDENTIFIER ::= { tCO-products 1 }



-- MODULE IDENTIFICATION

-- Alert-on-LAN MODULE-IDENTITY
--  LAST-UPDATED "9807210000Z"
--  ORGANIZATION "Intel Corporation"
--  CONTACT-INFO
--   " Alert On LAN* Software
--     Intel Corporation, JF3-4
--	 Hillsboro, OR. "
--  DESCRIPTION
--  " This is the Alert on LAN MIB. Version 1.0 "
-- ::= { management 1 }

-- We should be able to plug this branch into any tree from this point forward


--system information branch. Gives system related information like
--System Type, GUID, System state.

-- ****************************************
-- SYSTEM INFORMATION BRANCH STARTS HERE.
-- ****************************************



systemName OBJECT-TYPE
 SYNTAX OCTET STRING ( SIZE(16) )
 ACCESS read-only
 STATUS current
 DESCRIPTION
  "System NetBIOS name"
::= { alert-on-LAN 1 }

systemGUID OBJECT-TYPE
 SYNTAX DisplayString ( SIZE(0..256) )
 ACCESS read-only
 STATUS current
 DESCRIPTION
  "System's GUID"
::= { alert-on-LAN 2 }

eventString OBJECT-TYPE
 SYNTAX DisplayString ( SIZE(0..256) )
 ACCESS read-only
 STATUS current
 DESCRIPTION
  "Additional event information string."
::= { alert-on-LAN 3 }

eventInfo OBJECT-TYPE
 SYNTAX OCTET STRING ( SIZE(9) ) 
 ACCESS read-only
 STATUS current
 DESCRIPTION
  "Additional information associated with the event."
::= { alert-on-LAN 4 }

iPAddress OBJECT-TYPE
 SYNTAX OCTET STRING ( SIZE(16) ) 
 ACCESS read-only
 STATUS current
 DESCRIPTION
  "IP Address of trap originator."
::= { alert-on-LAN 5 }
--
-- Event trap definitions.
--

presenceHeartbeat TRAP-TYPE
 ENTERPRISE alert-on-LAN
 VARIABLES  { systemName}
 DESCRIPTION 
  "Presence Heartbeat Expired"
 ::= 0

coverTamper TRAP-TYPE
 ENTERPRISE alert-on-LAN
 VARIABLES  { systemName}
 DESCRIPTION 
  "Cover Tamper"
 ::= 1

voltage-Fan-Temperature TRAP-TYPE
 ENTERPRISE alert-on-LAN
 VARIABLES  { systemName}
 DESCRIPTION 
  "Voltage/Fan/Temperature Out of Specification"
 ::= 2

lANLeash TRAP-TYPE
 ENTERPRISE alert-on-LAN
 VARIABLES  { systemName}
 DESCRIPTION 
  "LAN Leash Tamper"
 ::= 3

temperature TRAP-TYPE
 ENTERPRISE alert-on-LAN
 VARIABLES  { systemName}
 DESCRIPTION 
  "Temperature Out of Specification"
 ::= 4

processorMissing TRAP-TYPE
 ENTERPRISE alert-on-LAN
 VARIABLES  { systemName}
 DESCRIPTION 
  "Processor Missing"
 ::= 5

processorTemperature TRAP-TYPE
 ENTERPRISE alert-on-LAN
 VARIABLES  { systemName}
 DESCRIPTION 
  "Processor Over Temperature"
 ::= 6

watchdog TRAP-TYPE
 ENTERPRISE alert-on-LAN
 VARIABLES  { systemName}
 DESCRIPTION 
  "Watchdog Event"
 ::= 7

p-O-S-T TRAP-TYPE
 ENTERPRISE alert-on-LAN
 VARIABLES  { systemName}
 DESCRIPTION 
  "P.O.S.T."
 ::= 8

unknownEvent TRAP-TYPE
 ENTERPRISE alert-on-LAN
 VARIABLES  { systemName}
 DESCRIPTION 
  "Unknown Event"
 ::= 9

processor-0-Missing TRAP-TYPE
 ENTERPRISE alert-on-LAN
 VARIABLES  { systemName}
 DESCRIPTION 
  "Processor 0 Missing"
 ::= 10

processor-1-Missing TRAP-TYPE
 ENTERPRISE alert-on-LAN
 VARIABLES  { systemName}
 DESCRIPTION 
  "Processor 1 Missing"
 ::= 11

voltage-Fan TRAP-TYPE
 ENTERPRISE alert-on-LAN
 VARIABLES  { systemName}
 DESCRIPTION 
  "Voltage/Fan Out of Specification"
 ::= 12

voltage TRAP-TYPE
 ENTERPRISE alert-on-LAN
 VARIABLES  { systemName}
 DESCRIPTION 
  "Voltage Out of Specification"
 ::= 13

fan TRAP-TYPE
 ENTERPRISE alert-on-LAN
 VARIABLES  { systemName}
 DESCRIPTION 
  "Fan Out of Specification"
 ::= 14

fan-Temperature TRAP-TYPE
 ENTERPRISE alert-on-LAN
 VARIABLES  { systemName}
 DESCRIPTION 
  "Fan/Temperature Out of Specification"
 ::= 15

voltage-Temperature TRAP-TYPE
 ENTERPRISE alert-on-LAN
 VARIABLES  { systemName}
 DESCRIPTION 
  "Voltage/Temperature Out of Specification"
 ::= 16

undock TRAP-TYPE
 ENTERPRISE alert-on-LAN
 VARIABLES  { systemName}
 DESCRIPTION 
  "Surprised Undock event"
 ::= 17 

eventClear TRAP-TYPE
 ENTERPRISE alert-on-LAN
 VARIABLES  { systemName}
 DESCRIPTION 
  "Event clear"
 ::= 18 

clientAdded TRAP-TYPE
 ENTERPRISE alert-on-LAN
 VARIABLES  { systemName}
 DESCRIPTION 
  "Client added"
 ::= 19 

clientDeleted TRAP-TYPE
 ENTERPRISE alert-on-LAN
 VARIABLES  { systemName}
 DESCRIPTION 
  "Client deleted"
 ::= 20

END
