ChrComProtectionVcNextPeerSetVc-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComProtectionVc			FROM  Chromatis-MIB;

-- chrComProtectionVcNextPeerSetVc Table

chrComProtectionVcNextPeerSetVcTable		OBJECT-TYPE
	SYNTAX		SEQUENCE OF ChrComProtectionVcNextPeerSetVcEntry
	MAX-ACCESS	not-accessible
	STATUS		current
	DESCRIPTION
	""
	::= { chrComProtectionVc 3}

chrComProtectionVcNextPeerSetVcEntry		OBJECT-TYPE
	SYNTAX		ChrComProtectionVcNextPeerSetVcEntry
	MAX-ACCESS	not-accessible
	STATUS		current
	DESCRIPTION
	""
	INDEX  {  chrComProtectionVcNextVCPeerSetID }

--DEFAULT  get-function-async  MNIL_GetRoutine
--DEFAULT  set-function-async  MNIL_SetRoutine
--DEFAULT  next-function-async MNIL_NextRoutine
--DEFAULT  test-function-async MNIL_TestRoutine
--DEFAULT  cookie "nextPeerSetVc"
	::= { chrComProtectionVcNextPeerSetVcTable  1 }

ChrComProtectionVcNextPeerSetVcEntry  ::=
	SEQUENCE  {
	chrComProtectionVcNextVCPeerSetID		Unsigned32	(0..4294967295)
}

chrComProtectionVcNextVCPeerSetID 	OBJECT-TYPE
	SYNTAX		Unsigned32	(0..4294967295)
	MAX-ACCESS 	read-only
	STATUS 		current
	DESCRIPTION
	"The next vacant PeerSet  ID in the VC Protection PeerSet  Table
This field enables the NMS to create new VC protection Peers
"
	::= { chrComProtectionVcNextPeerSetVcEntry  1 }


END
