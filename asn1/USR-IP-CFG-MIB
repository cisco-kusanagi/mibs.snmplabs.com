USR-IP-CFG-MIB DEFINITIONS ::= BEGIN
	IMPORTS
          OBJECT-TYPE, MODULE-IDENTITY,
          Integer32
                  FROM SNMPv2-SMI
          common, UsrDisplayString
                  FROM USR-DEFINITIONS-MIB;
usrIpCfg MODULE-IDENTITY
        LAST-UPDATED "200205051800Z"
        ORGANIZATION "CommWorks Corporation, a 3Com Company"
        CONTACT-INFO "Customer Support"
        DESCRIPTION
           "The commWorks enterprise defined MIB objects IP
            Configuration."
--      REVISION "200205051800Z"
--      DESCRIPTION "Converted to SNMPv2"
        ::= { common 13 }
   -- Begin managed object definitions here...
usrIpCfgNetworkTable OBJECT-TYPE
	SYNTAX SEQUENCE OF UsrIpCfgNetworkEntry
	MAX-ACCESS not-accessible
	STATUS     current
	DESCRIPTION
		"This table is the same as the usrIpNetworkTable definied above,
		 with the exception that it is indexed by the Network Name defined
		 in the usrCfgNetworkTable. This table will be used only by the
		 the Configuration File Manager process to load permament configuration
		 file records for named networks at system boot time. Any attempt
		 to set this table from either the CLI process or SNMP will
		 fail."
::= { usrIpCfg 1 }
usrIpCfgNetworkEntry OBJECT-TYPE
	SYNTAX UsrIpCfgNetworkEntry
	MAX-ACCESS not-accessible
	STATUS     current
	DESCRIPTION
		"A (conceptual) entry for one IP Network."
	INDEX { usrIpCfgNetName }
::= { usrIpCfgNetworkTable 1 }
UsrIpCfgNetworkEntry ::= SEQUENCE {
	usrIpCfgNetName			    UsrDisplayString,
	usrIpCfgNetBcastAddr		Integer32,
	usrIpCfgNetReasmMaxSize		Integer32,
	usrIpCfgNetRoutingProtocol	INTEGER,  -- deprecated
	usrIpCfgNetSendDefaultRoutePolicy 		INTEGER,
	usrIpCfgNetSendRoutesPolicy 			INTEGER,
	usrIpCfgNetSendSubnetsOnlyPolicy 		INTEGER,
	usrIpCfgNetAcceptDefaultRoutePolicy 	INTEGER,
	usrIpCfgNetSilentPolicy 				INTEGER,
	usrIpCfgNetSplitHorizonPolicy 		INTEGER,
	usrIpCfgNetPoisonReversePolicy 		INTEGER,
	usrIpCfgNetFlashUpdatePolicy 			INTEGER,
	usrIpCfgNetSimpleAuthenPolicy			INTEGER,
	usrIpCfgNetSendRipV1CompatPolicy 		INTEGER,
	usrIpCfgNetRcvRipV1Policy	 		INTEGER,
	usrIpCfgNetRcvRipV2Policy	 		INTEGER,
	usrIpCfgNetRip2AuthKey			OCTET STRING,
	usrIpCfgNetRoutingMetric       		Integer32,
	usrIpCfgNetExportMetric       		Integer32,
	usrIpCfgNetRoutingNone			     INTEGER,
	usrIpCfgNetRoutingRipV1				INTEGER,
	usrIpCfgNetRoutingRipV2				INTEGER,
	usrIpCfgNetRoutingOspf				INTEGER
	}
usrIpCfgNetName OBJECT-TYPE
	SYNTAX          UsrDisplayString (SIZE (1..32))
	MAX-ACCESS      not-accessible
	STATUS          current
	DESCRIPTION
		"The name of this network. Network names can either be assigned
           by a network administrator when the Network is created. Or it will
           generated by the Configuration Process when it adds the network to
		 its internal table."
::= { usrIpCfgNetworkEntry 1}
usrIpCfgNetBcastAddr OBJECT-TYPE
     SYNTAX  Integer32
     MAX-ACCESS  read-write
	STATUS      current
     DESCRIPTION
          "The value of the least-significant bit in the IP
           broadcast address used for sending datagrams on
           the (logical) interface associated with the IP
           address of this entry.  For example, when the
           Internet standard all-ones broadcast address is
           used, the value will be 1.  This value applies to
           both the subnet and network broadcasts addresses
           used by the entity on this (logical) interface."
	--CONFIGURABLE
::= { usrIpCfgNetworkEntry 4 }
usrIpCfgNetReasmMaxSize OBJECT-TYPE
     SYNTAX  Integer32 (0..65535)
     MAX-ACCESS  read-write
     STATUS      current
     DESCRIPTION
		"The size of the largest IP datagram which this
           entity can re-assemble from incoming IP fragmented
           datagrams received on this interface."
	--CONFIGURABLE
::= { usrIpCfgNetworkEntry 5 }
usrIpCfgNetRoutingProtocol	OBJECT-TYPE
	SYNTAX INTEGER {
			none(0),
			ripv1(1),
			ripv2(2)
		}
	MAX-ACCESS read-write
	STATUS deprecated
	DESCRIPTION
		"The routing protocol to be operated on this IP network.  Currently,
		 there are none, rip version 1 and rip version 2."
     -- CONFIGURABLE
::= { usrIpCfgNetworkEntry 6 }
usrIpCfgNetSendDefaultRoutePolicy OBJECT-TYPE
	SYNTAX	INTEGER {
		disable(0),
		enable(1)
	}
	MAX-ACCESS	read-write
	STATUS	    current
	DESCRIPTION
		"Allows disabling or enabling of the send default route RIP policy.
		 This policy is enabled by default."
	--CONFIGURABLE
::= { usrIpCfgNetworkEntry 7 }
usrIpCfgNetSendRoutesPolicy OBJECT-TYPE
	SYNTAX	INTEGER {
		disable(0),
		enable(1)
	}
	MAX-ACCESS	read-write
	STATUS	    current
	DESCRIPTION
		"Allows disabling or enabling of the send routes RIP policy.
		 This policy is enabled by default."
	--CONFIGURABLE
::= { usrIpCfgNetworkEntry 8 }
usrIpCfgNetSendSubnetsOnlyPolicy OBJECT-TYPE
	SYNTAX	INTEGER {
		disable(0),
		enable(1)
	}
	MAX-ACCESS	read-write
	STATUS	    current
	DESCRIPTION
		"Allows disabling or enabling of the send subnets only RIP policy.
		 This policy is enabled by default."
	--CONFIGURABLE
::= { usrIpCfgNetworkEntry 9 }
usrIpCfgNetAcceptDefaultRoutePolicy OBJECT-TYPE
	SYNTAX	INTEGER {
		disable(0),
		enable(1)
	}
	MAX-ACCESS	read-write
	STATUS	    current
	DESCRIPTION
		"Allows disabling or enabling of the accept default route RIP policy.
		 This policy is disabled by default."
	--CONFIGURABLE
::= { usrIpCfgNetworkEntry 10 }
usrIpCfgNetSilentPolicy OBJECT-TYPE
	SYNTAX	INTEGER {
		disable(0),
		enable(1)
	}
	MAX-ACCESS	read-write
	STATUS	    current
	DESCRIPTION
		"Allows disabling or enabling of the silent policy.
		 This policy is disabled by default."
	--CONFIGURABLE
::= { usrIpCfgNetworkEntry 11 }
usrIpCfgNetSplitHorizonPolicy OBJECT-TYPE
	SYNTAX	INTEGER {
		disable(0),
		enable(1)
	}
	MAX-ACCESS	read-write
	STATUS	    current
	DESCRIPTION
		"Allows disabling or enabling of the split horizon RIP policy.
		 This policy is enabled by default."
	--CONFIGURABLE
::= { usrIpCfgNetworkEntry 12 }
usrIpCfgNetPoisonReversePolicy OBJECT-TYPE
	SYNTAX	INTEGER {
		disable(0),
		enable(1)
	}
	MAX-ACCESS	read-write
	STATUS	    current
	DESCRIPTION
		"Allows disabling or enabling of the poison reverse RIP policy.
	 	 This policy is enabled by default."
	--CONFIGURABLE
::= { usrIpCfgNetworkEntry 13 }
usrIpCfgNetFlashUpdatePolicy OBJECT-TYPE
	SYNTAX	INTEGER {
		disable(0),
		enable(1)
	}
	MAX-ACCESS	read-write
	STATUS	    current
	DESCRIPTION
		"Allows disabling or enabling of the flash update RIP policy.
		 This policy is enabled by default."
	--CONFIGURABLE
::= { usrIpCfgNetworkEntry 14 }
usrIpCfgNetSimpleAuthenPolicy OBJECT-TYPE
	SYNTAX	INTEGER {
		disable(0),
		enable(1)
	}
	MAX-ACCESS	read-write
	STATUS	    current
	DESCRIPTION
		"Allows disabling or enabling of the simple authentication RIP policy.
		 This policy is valid for RIPV2 only and is enabled by default when
		 RIPV2 is selected as the routing protocol."
	--CONFIGURABLE
::= { usrIpCfgNetworkEntry 15 }
usrIpCfgNetSendRipV1CompatPolicy OBJECT-TYPE
	SYNTAX	INTEGER {
		disable(0),
		enable(1)
	}
	MAX-ACCESS	read-write
	STATUS	    current
	DESCRIPTION
		"Allows disabling or enabling of the send RipV1 compatible policy.
		 This policy is enabled by default."
	--CONFIGURABLE
::= { usrIpCfgNetworkEntry 16 }
usrIpCfgNetRcvRipV1Policy OBJECT-TYPE
	SYNTAX	INTEGER {
		disable(0),
		enable(1)
	}
	MAX-ACCESS	read-write
	STATUS	    current
	DESCRIPTION
		"Allows disabling or enabling of the receive RipV1 policy.
		 This policy is enabled by default."
	--CONFIGURABLE
::= { usrIpCfgNetworkEntry 17 }
usrIpCfgNetRcvRipV2Policy OBJECT-TYPE
	SYNTAX	INTEGER {
		disable(0),
		enable(1)
	}
	MAX-ACCESS	read-write
	STATUS	    current
	DESCRIPTION
		"Allows disabling or enabling of the receive RipV2 policy.
		 This policy is enabled by default."
	--CONFIGURABLE
::= { usrIpCfgNetworkEntry 18 }
usrIpCfgNetRip2AuthKey OBJECT-TYPE
	SYNTAX OCTET STRING (SIZE(16))
	MAX-ACCESS read-write
	STATUS     current
	DESCRIPTION
		"this variable defines the authentication key for ip rip2.  when
		 this varialbe is set, by default, the authentication type is also
		 set to simple."
	--CONFIGURABLE
::= { usrIpCfgNetworkEntry 19 }
usrIpCfgNetRoutingMetric OBJECT-TYPE
        SYNTAX Integer32 (1..16)
        MAX-ACCESS read-write
        STATUS     current
        DESCRIPTION
                "The routing metric for using this IP network."
        --CONFIGURABLE
::= { usrIpCfgNetworkEntry 20 }
usrIpCfgNetExportMetric OBJECT-TYPE
        SYNTAX Integer32 (0..15)
        MAX-ACCESS read-write
        STATUS     current
        DESCRIPTION
                "The  metric for advertising routes through this IP network."
        --CONFIGURABLE
::= { usrIpCfgNetworkEntry 21 }
usrIpCfgNetRoutingNone	OBJECT-TYPE
	SYNTAX INTEGER {
			disable(0),
			enable(1)
		}
	MAX-ACCESS read-write
	STATUS     current
	DESCRIPTION
		"Specifies that no routing protocol will be operating on this 
           IP network."
	--CONFIGURABLE
::= { usrIpCfgNetworkEntry 22 }
usrIpCfgNetRoutingRipV1	OBJECT-TYPE
	SYNTAX INTEGER {
			disable(0),
			enable(1)
		}
	MAX-ACCESS read-write
	STATUS     current
	DESCRIPTION
		"Specifies that the RIPv1 routing protocol will be operating
           on this IP network."
	--CONFIGURABLE
::= { usrIpCfgNetworkEntry 23 } 
usrIpCfgNetRoutingRipV2	OBJECT-TYPE
	SYNTAX INTEGER {
			disable(0),
			enable(1)
		}
	MAX-ACCESS read-write
	STATUS     current
	DESCRIPTION
		"Specifies that the RIPv2 routing protocol will be operating
           on this IP network."
	--CONFIGURABLE
::= { usrIpCfgNetworkEntry 24 }
usrIpCfgNetRoutingOspf	OBJECT-TYPE
	SYNTAX INTEGER {
			disable(0),
			enable(1)
		}
	MAX-ACCESS read-write
	STATUS     current
	DESCRIPTION
		"Specifies that the OSPF routing protocol will be operating
           on this IP network."
	--CONFIGURABLE
::= { usrIpCfgNetworkEntry 25 }
END         -- End Template MIB definitions
