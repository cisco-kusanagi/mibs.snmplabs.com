SALIX-DS0-RTP-MIB DEFINITIONS ::= BEGIN

IMPORTS
	MODULE-COMPLIANCE, OBJECT-GROUP FROM SNMPv2-CONF
         MODULE-IDENTITY, OBJECT-TYPE, Integer32,
         IpAddress, Counter32             FROM SNMPv2-SMI
         
         TimeStamp, RowStatus             FROM SNMPv2-TC         
         
         DisplayString                    FROM RFC1213-MIB  
         
         InterfaceIndex                   FROM IF-MIB                        

         platform1                        FROM SALIX-MIB;

salixDsx0RtpMIB MODULE-IDENTITY
     LAST-UPDATED "9810130000Z"
     ORGANIZATION "SALIX Technologies"
     CONTACT-INFO "904 Wind River Lane
                   Suite 101
                   Gaithersburg, MD  20878
                   (301)-417-0017"
     DESCRIPTION  "The MIB describing Salix specific DS0-RTP connection
                   objects"
     ::= { platform1 3 } 
     
   salixDsx0RtpMIBObjects OBJECT IDENTIFIER ::= { salixDsx0RtpMIB 1 }
   salixDsx0RtpMIBTraps   OBJECT IDENTIFIER ::= { salixDsx0RtpMIB 2 }
   salixDsx0RtpMIBCompliance OBJECT IDENTIFIER ::= { salixDsx0RtpMIB 3 }
   salixDsx0RtpMIBTrapPrefix   OBJECT IDENTIFIER ::= { salixDsx0RtpMIBTraps 0 }
   
   -- ITX DS0-RTP Connection Table
   
      salixDsx0RtpConnectionTable OBJECT-TYPE
         SYNTAX      SEQUENCE OF ItxDsx0RtpConnectionEntry
         MAX-ACCESS  not-accessible
         STATUS      current
         DESCRIPTION
            "A table describing the current DS0 to RTP connections.
             There should be one entry for each DS0-RTP connection
             in the system"
         ::= { salixDsx0RtpMIBObjects 1 }
      
      salixDsx0RtpConnectionEntry OBJECT-TYPE
         SYNTAX     ItxDsx0RtpConnectionEntry
         MAX-ACCESS not-accessible
         STATUS     current
         DESCRIPTION
            "An entry in the ITX DS0-RTP Table.  The entry provides
             information on the status and other attributes of the 
             connection"
         INDEX { salixDsx0RtpConnectionInterface,
                 salixDsx0RtpConnectionSrcIpAddress,
                 salixDsx0RtpConnectionSrcPort,
                 salixDsx0RtpConnectionDestIpAddress,
                 salixDsx0RtpConnectionDestPort }
         ::= { salixDsx0RtpConnectionTable 1 }         
      
      ItxDsx0RtpConnectionEntry ::= SEQUENCE {
         salixDsx0RtpConnectionInterface             InterfaceIndex,
         salixDsx0RtpConnectionSrcIpAddress          IpAddress,
         salixDsx0RtpConnectionSrcPort               INTEGER,
         salixDsx0RtpConnectionDestIpAddress         IpAddress,
         salixDsx0RtpConnectionDestPort              INTEGER,
         salixDsx0RtpConnectionDirection             INTEGER,
         salixDsx0RtpConnectionOperStatus            INTEGER,
         salixDsx0RtpConnectionRowStatus             RowStatus
      }  
      
      salixDsx0RtpConnectionInterface OBJECT-TYPE
         SYNTAX     InterfaceIndex
         MAX-ACCESS not-accessible
         STATUS     current
         DESCRIPTION
            "The ifIndex that identifies the DS0 channel being connected
             to the RTP session"
         ::= { salixDsx0RtpConnectionEntry 1 }
         
      salixDsx0RtpConnectionSrcIpAddress OBJECT-TYPE
         SYNTAX     IpAddress
         MAX-ACCESS not-accessible
         STATUS     current
         DESCRIPTION
            "The Source IP Address for the RTP Session
             part of the DS0-RTP connection"
         ::= { salixDsx0RtpConnectionEntry 2 }
         
      salixDsx0RtpConnectionSrcPort OBJECT-TYPE
         SYNTAX     INTEGER (0..65535)
         MAX-ACCESS not-accessible
         STATUS     current
         DESCRIPTION
            "The Source Port for the RTP Session
             part of the DS0-RTP connection"
         ::= { salixDsx0RtpConnectionEntry 3 }
               
      salixDsx0RtpConnectionDestIpAddress OBJECT-TYPE
         SYNTAX     IpAddress
         MAX-ACCESS not-accessible
         STATUS     current
         DESCRIPTION
            "The Destination IP Address for the RTP Session
             part of the DS0-RTP connection"
         ::= { salixDsx0RtpConnectionEntry 4 }
               
      salixDsx0RtpConnectionDestPort OBJECT-TYPE
         SYNTAX     INTEGER (0..65535)
         MAX-ACCESS not-accessible
         STATUS     current
         DESCRIPTION
            "The Destination Port for the RTP Session
             part of the DS0-RTP connection"
         ::= { salixDsx0RtpConnectionEntry 5 }
               
      salixDsx0RtpConnectionDirection OBJECT-TYPE
         SYNTAX     INTEGER { rtp2dsx0(1),
                              dsx02rtp(2),
                              bidirectional(3) }
         MAX-ACCESS read-only
         STATUS     current
         DESCRIPTION
            "This attribute describes the direction of 
             traffic flow in a connection.
            
                  rtp2dsx0 (1)      - Traffic flows from the RTP
                                      session to the DS0 channel
                  dsx02rtp (2)      - Traffic flows from the DS0 
                                      channel to the RTP session
                  bidirectional (3) - Traffic flows in both directions
                                      in the connection"
         ::= { salixDsx0RtpConnectionEntry 6 }               
                  
      salixDsx0RtpConnectionOperStatus OBJECT-TYPE
         SYNTAX     INTEGER { up(1),
                              down(2),
                              unknown(3) }
         MAX-ACCESS read-only
         STATUS     current
         DESCRIPTION
            "This attribute indicates the operational state of the 
            DS0-RTP connection.
            
                  up (1)      - The connection is up and active
                  down (2)    - The connection is down and inactive
                  unknown (3) - The status of the connection is unknown"
         ::= { salixDsx0RtpConnectionEntry 7 }         
            
      salixDsx0RtpConnectionRowStatus OBJECT-TYPE
         SYNTAX     RowStatus  
         MAX-ACCESS read-write
         STATUS     current
         DESCRIPTION
            "The status of this entry in the salixDsx0RtpConnectTable.
            This object is used to delete a salixDsx0RtpConnectTable
            entry.
            
            To delete the connection, set this object to destory(6)
            
            Row status values:
            
            active(1)       - set by the agent after this entry is created
            notInService(2) - not applicable
            notReady(3)     - not applicable
            createAndGo(4)  - not applicable
            createAndWait(5)- not applicable
            destroy(6)      - set by the management entity to destroy entry"
         ::= { salixDsx0RtpConnectionEntry 8 }  
         
-- Conformance Statements

salixDsx0RtpGroups      OBJECT IDENTIFIER  ::= { salixDsx0RtpMIBCompliance 1 }
salixDsx0RtpCompliances OBJECT IDENTIFIER  ::= { salixDsx0RtpMIBCompliance 2 }            
            
   salixDsx0RtpGroup OBJECT-GROUP
      OBJECTS {
         salixDsx0RtpConnectionDirection,
         salixDsx0RtpConnectionOperStatus,
         salixDsx0RtpConnectionRowStatus 
      }
      STATUS            current
      DESCRIPTION       "Current Statistics for Dsx0Rtp Sessions"
      ::= {salixDsx0RtpGroups 3}
      
-- Compliance Statements

salixDsx0RtpCompliance MODULE-COMPLIANCE
     STATUS       current
     DESCRIPTION
                  "The basic implementation requirements for the SALIX-DS0-RTP-MIB."
     MODULE       -- This module
     MANDATORY-GROUPS { salixDsx0RtpGroup }
     ::= { salixDsx0RtpCompliances 1 }             

END
