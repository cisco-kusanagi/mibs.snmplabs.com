-- 
--  Copyright 1996, Com21 Inc.  All Rights Reserved.
--
 
COM21-HCXSTU-MIB DEFINITIONS ::= BEGIN
        IMPORTS
		  MODULE-IDENTITY, OBJECT-TYPE, NOTIFICATION-TYPE, Integer32,
        IpAddress, Gauge32
        FROM SNMPv2-SMI
        DisplayString, MacAddress
        FROM SNMPv2-TC
		  Gauge FROM RFC1155-SMI
        com21, com21Hcx
        FROM COM21-HCX-MIB
        com21Traps FROM COM21-HCX-MIB
		  hcxAlmSeverity, hcxEventLogTime
        FROM COM21-HCXALM-MIB;


        com21HcxStu MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"

                DESCRIPTION
                        "This is the Com21 ComPort Control MIB module.
                         All data defined in this MIB is held upon the
                         ComController. COM21 Part# 005-0025-00"
                ::= { com21Hcx 50 }

        com21HcxStuStatusGroup          OBJECT IDENTIFIER ::= {com21Hcx 51}
	com21HcxStuSrcIpAddrGroup	OBJECT IDENTIFIER ::= {com21Hcx 52}
	com21HcxStuIpFiltGroup		OBJECT IDENTIFIER ::= {com21Hcx 53}
	com21HcxStuIpFiltStatsGroup	OBJECT IDENTIFIER ::= {com21Hcx 55}
	com21HcxStuDstIpAddrGroup       OBJECT IDENTIFIER ::= {com21Hcx 57}


	FrequencyKhz     ::= INTEGER (0..800000)
        Com21RowStatus   ::= INTEGER { active(1), create(2), destroy(3),
				       deactive(4) }
	StuGain          ::= INTEGER (18..58)


        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the 
	-- SNMP interface and the MIB II Interfaces Group for both the 
	-- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        -- This MIB contains the following groups :
        -- 
        --   com21HcxStuStatusGroup      - this group controls the system level
        --                                 configuration of individual ComPorts.
        --                                 This include configuration and
        --                                 authorization state. This data is
        --                                 held upon the ComController.
        -- 
	--   com21HcxStuIpFiltGroup      - this group provides for the control
	--				   of IP level filtering.
	--
	--   com21HcxStuIpFiltStatsGroup - this group stores the various
	--				   statistics relative to the IP
	--				   filtering.
	--
	--   com21HcxStuSrcIpAddrGroup   - defines the per ComPort IP source
	--				   addresses and mask used in the 
	--				   filtering operations.
	--
	--   com21HcxStuDstIpAddrGroup   - defines the per ComPort IP 
	--				   destination addresses and mask used 
	--				   in the filtering operations.
	--
        -- -- -- -- -- -- -- -- -- -- -- -- -- -- -- -- -- -- -- -- -- -- -- --
        -- -- -- -- -- -- -- -- -- -- -- -- -- -- -- -- -- -- -- -- -- -- -- --


        -- -- -- -- -- -- -- -- -- -- -- -- -- -- -- -- -- -- -- -- -- -- -- --
        -- -- -- -- -- -- -- -- -- -- -- -- -- -- -- -- -- -- -- -- -- -- -- --
        --
        -- com21HcxStuStatusGroup
        --
        -- defines the attributes related to the management of the ComPort
        -- Topology and Acquisition. This attribute data is stored and
	-- managed by the ComController - the ComPorts are NOT accessed.
        --
        -- -- -- -- -- -- -- -- -- -- -- -- -- -- -- -- -- -- -- -- -- -- -- --
        -- -- -- -- -- -- -- -- -- -- -- -- -- -- -- -- -- -- -- -- -- -- -- --

	com21HcxStuStatusTable OBJECT-TYPE
                SYNTAX SEQUENCE OF HcxStuStatusEntry
                MAX-ACCESS not-accessible
                STATUS current
                DESCRIPTION "."
                ::= { com21HcxStuStatusGroup 1 }

	com21HcxStuStatusEntry OBJECT-TYPE
                SYNTAX HcxStuStatusEntry
                MAX-ACCESS not-accessible
                STATUS current
                DESCRIPTION "."
		INDEX { hcxStuStatusMacAddr }
                ::= { com21HcxStuStatusTable 1 }

	HcxStuStatusEntry ::= SEQUENCE {
		hcxStuStatusMacAddr	 MacAddress,
		hcxStuConfigured	 INTEGER,
		hcxStuAcquired		 INTEGER,
		hcxStuAcqFailInfo	 INTEGER,
                hcxStuAuthorized         INTEGER,
		hcxStuLedFlashTest 	 INTEGER,
		hcxStuUpstreamTest	 INTEGER,
		hcxStuVlanId		 INTEGER,
		hcxStuRxShelfId		 INTEGER,
		hcxStuRxSlotId		 INTEGER,
		hcxStuRxPortId		 INTEGER,
		hcxStuServiceType	 Integer32,
		hcxStuConfSwImage	 DisplayString,
		hcxStuPingTestAction	 INTEGER,
		hcxStuPingTestResult	 INTEGER,
		hcxStuEthTestAction	 INTEGER,
		hcxStuEthTestResult	 INTEGER,
		hcxStuRetPathSelect	 INTEGER,
		hcxStuEth8022Filter	 INTEGER,
		hcxStuDnstrmFwdCntrl	 INTEGER,
		hcxStuStatsCollect	 INTEGER,
		hcxStuPowerRangeState	 INTEGER,
		hcxStuRpmIPortId	 INTEGER,
		hcxStuEthLpbkTestUpRate  Integer32,
		hcxStuEthLpbkTestLatency Integer32,
		hcxStuModelName		 INTEGER,
		hcxStuEthTestDnRate      Integer32,
		hcxStuEthLpbkTestDuration INTEGER }

        hcxStuStatusMacAddr OBJECT-TYPE
                SYNTAX MacAddress
                MAX-ACCESS read-only
                STATUS current
                DESCRIPTION "
                        Contains IEEE 802 medium access control address 
			of the ComPort device."
                ::= { com21HcxStuStatusEntry 1 }
 
        hcxStuConfigured OBJECT-TYPE
                SYNTAX INTEGER { true (1), false (2) }
                MAX-ACCESS read-create
                STATUS current
                DESCRIPTION "
                        This attribute defines the configured state of 
			the ComPort. This value will be set to true when
			the NMAPS creates a new entry. If this value is 
			false, the hcxStuAcquired attribute is false and 
			the hcxStuAuthorized flag is set to deauthorized
                        then the entry shall be deleted. Note that this 
			value cannot be set to false if the 
			hcxStuAuthorized flag is set to true."
                ::= { com21HcxStuStatusEntry 2 }

        hcxStuAcquired OBJECT-TYPE
                SYNTAX INTEGER { true (1), false (2) }
                MAX-ACCESS read-only
                STATUS current
                DESCRIPTION "
                        This attribute defines the acquired state of 
			the ComPort. Note that is state is set once an
			ComPort can be managed. We could have a condition
			were an ComPort is acquired but full service cannot
			be provided. In that case the hcxStuAcqFailInfo
			attribute shall indicate a problem.
			If an unknown ComPort is acquired then an entry is 
			created with this value set to true and both 
			hcxStuAuthorized and hcxStuConfigured set to 
			false."
                ::= { com21HcxStuStatusEntry 3 }

        hcxStuAcqEvent NOTIFICATION-TYPE
                OBJECTS { hcxAlmSeverity, hcxEventLogTime,
				 hcxStuStatusMacAddr }
                STATUS current
                DESCRIPTION "
                        This trap is issued only when the acquisition
			trap is enabled via the hcxStuAcqTrapEnable
			attribute. Severity WARNING."
                ::= { com21Traps 90 }

        hcxStuDeacqEvent NOTIFICATION-TYPE
                OBJECTS { hcxAlmSeverity, hcxEventLogTime,
				 hcxStuStatusMacAddr }
                STATUS current
                DESCRIPTION "
                        This trap is issued only when the acquisition
                        trap is enabled via the hcxStuAcqTrapEnable
                        attribute. Severity WARNING."
                ::= { com21Traps 91 }

	hcxStuAcqFailInfo OBJECT-TYPE
                SYNTAX INTEGER {
				noFailure(1),
				vlanFailure(2),
				servGrpInvalid(3),
				bandwidthUnavail(4),
				unauthorized(5) }
                MAX-ACCESS read-only
                STATUS current
                DESCRIPTION "
                        This attribute provides secondary information
			related to an ComPort acquisition. If there is a
			failure in the system that prevents a user
			from receiving full service, then it will be
			indicated by this attribute. If an ComPort is
			unacquired or no problems were encountered
			then this attribute shall equal noFailure."
                ::= { com21HcxStuStatusEntry 4 }

				
        hcxStuAuthorized OBJECT-TYPE
                SYNTAX INTEGER { true (1), false (2) }
                MAX-ACCESS read-write
                STATUS current
                DESCRIPTION "
                        This attribute defines the verified state of
                        the ComPort. This state can only be set by the
                        NMAPS. If this attribute is false, then all
                        cells rates shall be set to 0 on the appropriate
                        Ethernet and RF Receiver cards."
                ::= { com21HcxStuStatusEntry 5 }

	hcxStuLedFlashTest OBJECT-TYPE
                SYNTAX INTEGER { nil(1), start(2), stop(3) }
                MAX-ACCESS read-write
                STATUS current
                DESCRIPTION "
                        Used to invoke an ComPort LED test. Setting the
			the attribute to start will invoke test. Setting
			to stop will terminate the test. When reading
			this attribute, nil shall be returned if no test
			is active and start if the test is in progress."
                ::= { com21HcxStuStatusEntry 6 }

	hcxStuUpstreamTest OBJECT-TYPE
                SYNTAX INTEGER { nil(1), start(2), stop(3) }
                MAX-ACCESS read-write
                STATUS current
                DESCRIPTION "
                        Used to invoke an ComPort Upstream RF test. Setting
			the attribute to start will invoke test. Setting
			to stop will terminate the test. When reading
			this attribute, nil shall be returned if no test
			is active and start if the test is in progress.
			Note that the hcxStuUpstrmTestFreq shall be 
			validated before initiating the test."
                ::= { com21HcxStuStatusEntry 7 }

        hcxStuVlanId OBJECT-TYPE
                SYNTAX INTEGER (1..64)
                MAX-ACCESS read-write
                STATUS current
                DESCRIPTION "
                        This attribute defines the virtual LAN id 
			associated with the ComPort. No default, must be
			set. Note, in the case of an acquired but
                        unconfigured ComPort, a value of 0 will be returned."
                ::= { com21HcxStuStatusEntry 8 }

        hcxStuRxShelfId OBJECT-TYPE
                SYNTAX INTEGER (0..2)
                MAX-ACCESS read-only
                STATUS current
                DESCRIPTION "
                        This attribute specifies the shelf id associated
			with the RX the ComPort is currently assigned to. If
			ComPort is unacquired then the value shall be 0."
                ::= { com21HcxStuStatusEntry 9 }

        hcxStuRxSlotId OBJECT-TYPE
                SYNTAX INTEGER (0..10)
                MAX-ACCESS read-only
                STATUS current
                DESCRIPTION "
                        This attribute specifies the slot id of the
                        RX card to which the ComPort is currently assigned.
			If ComPort is unacquired then the value shall be 0."
                ::= { com21HcxStuStatusEntry 10 }

        hcxStuRxPortId OBJECT-TYPE
                SYNTAX INTEGER (0..1)
                MAX-ACCESS read-only
                STATUS current
                DESCRIPTION "  
                        This attribute specifies the RX port to which 
			the ComPort is assigned. Presently only one port
			supported. If the ComPort is unacquired then the 
			attribute shall be set to 0."
                ::= { com21HcxStuStatusEntry 11 }

	hcxStuServiceType OBJECT-TYPE
                SYNTAX Integer32
                MAX-ACCESS read-write
                STATUS current
                DESCRIPTION "
                        This attribute defines the Service Type
                        associated with the ComPort. This equals the
			associated hcxServiceTypeId attribute. The
			default shall be 0, indicating no assigned
			service type."
                ::= { com21HcxStuStatusEntry 12 }

        -- -- -- -- -- -- -- -- -- -- -- -- -- -- -- -- -- -- -- -- -- -- -- --
        -- -- -- 1 Attribute Deprecated
        -- -- -- -- -- -- -- -- -- -- -- -- -- -- -- -- -- -- -- -- -- -- -- --


	hcxStuConfSwImage OBJECT-TYPE
                SYNTAX DisplayString (SIZE(16))
                MAX-ACCESS read-write
                STATUS current
                DESCRIPTION "
                        Contains the configured software image to be downloaded
			to the ComPort. The Common Controller download process 
			shall check this value when a download is requested. 
			If this image does not support the hardware specified 
			by the ComPort then an incompatible software version 
			trap shall be generated. It is then up to the user to 
			correct this field.
			When this field is set, the agent shall check if there
			is an image of the specified type loaded. If this is 
			not the case then a  unavailable software version trap
			shall be generated. Again, it is the responsibility of
			the user to ensure that the required image is
			downloaded.
			The image identifier shall be represented by 4 numbers
			deliminated by periods. i.e. a.b.c.d. Each number
			shall have a value between 0 and 255. This allows
			storage within a single (four byte) word."
                ::= { com21HcxStuStatusEntry 14 }

        hcxIncompSwVersion NOTIFICATION-TYPE
                OBJECTS { hcxAlmSeverity, hcxEventLogTime,
		            hcxStuStatusMacAddr }
                STATUS current
                DESCRIPTION "
			This trap is issued if the configured sw version (in
			hcxStuConfSwImage) is not applicable to the hw
			version/hw options reported by the ComPort. This an 
			event with no clear condition. Only severity is 
			WARNING."
                ::= { com21Traps 100 }

        hcxUnavailSwVersion NOTIFICATION-TYPE
                OBJECTS { hcxAlmSeverity, hcxEventLogTime,
		            hcxStuStatusMacAddr }
                STATUS current
                DESCRIPTION "
			This trap is issued if the configured image cannot be
			located on the ComController. This an event with no 
			clear condition. Only severity is WARNING."
                ::= { com21Traps 101 }

	hcxStuPingTestAction OBJECT-TYPE
		SYNTAX INTEGER { nil(1), execute(2) }
		MAX-ACCESS read-write
		STATUS current
		DESCRIPTION "
			Used to invoke a ping of the ComPort. Sends an OAM
			Ping message. When the user reads this attribute
			a nil response shall be given if no test is
			active and execute shall be return if a test is
			active."
		::= { com21HcxStuStatusEntry 15 }

        hcxStuPingTestComplete NOTIFICATION-TYPE
                OBJECTS { hcxAlmSeverity, hcxEventLogTime,
                            hcxStuStatusMacAddr, hcxStuPingTestResult }
                STATUS current
                DESCRIPTION "
			This trap is issued when the ping test is completed.
			This an event with no clear condition. Only severity 
			is WARNING."
                ::= { com21Traps 102 }

	hcxStuPingTestResult OBJECT-TYPE
		SYNTAX INTEGER { 
				inprogress(1),
				success(2), 
				failure(3) }
		MAX-ACCESS read-only
		STATUS current
		DESCRIPTION "
			contains result of last ping test. invalid is
			returned if ping test cannot be run. Examples
			being an unacquired ComPort or a ComPort."
		::= { com21HcxStuStatusEntry 16 }

        hcxStuEthTestAction OBJECT-TYPE
                SYNTAX INTEGER { nil(1), lpBkTest(2), dnStrmTest(3) }
                MAX-ACCESS read-write
                STATUS current
                DESCRIPTION "
                        This attribute is used to invoke the ComPort Ethernet
                        test. 
			If lpBkTest is selected, the ComController 
			will place the ComPort in the loopback state, 
			transmit a number of ethernet packets 
			and validate the returned packets. 
			hcxStuEthLpbkTestUpRate and hcxStuEthLpbkTestLatency 
			attributes contain the Rate and Latency for
			the upstream path
			If dnStrmTest is selected, the ComController
			will transmit a number of ethernet packets
			and calculate the downstream rate.	
			hcxStuEthTestDnRate attribute will contain
			the rate for the downstream path. "
                ::= { com21HcxStuStatusEntry 17 }

        hcxStuEthTestComplete NOTIFICATION-TYPE
                OBJECTS { hcxAlmSeverity, hcxEventLogTime,
                            hcxStuStatusMacAddr, hcxStuEthTestResult }
                STATUS current
                DESCRIPTION "
                        This notification is generated whenever the ComPort
                        loopback test is completed. This shall either be
                        completed after reception of looped back packet(s)
                        or after a timeout. This an event with no clear
                        condition. Only severity is WARNING."
                ::= { com21Traps 103 }
 
        hcxStuEthTestResult OBJECT-TYPE
                SYNTAX INTEGER { 
				inprogress(1),
				success(2), 
				noResponse(3), 
				corruptPacket(4) }
                MAX-ACCESS read-only
                STATUS current
                DESCRIPTION "
                        This attribute contains the result of the last ComPort
                        test."
                ::= { com21HcxStuStatusEntry 18 }

	hcxStuRetPathSelect OBJECT-TYPE
                SYNTAX INTEGER {
                                twoWay(1),
				teleRet(2) }
                MAX-ACCESS read-write
                STATUS current
                DESCRIPTION "
                        This attribute specifies the return path mode of the 
			ComPort. Default is two way cable."
                ::= { com21HcxStuStatusEntry 19 }
 
        hcxStuAcqRangeFail NOTIFICATION-TYPE
                OBJECTS { hcxAlmSeverity, hcxEventLogTime,
		            hcxStuStatusMacAddr }
                STATUS current
                DESCRIPTION "
			This trap is issued if an RX card reports a failure
			to range a previously acquired ComPort. Note that the
			ComPort states are defined in the proxy ComPort MIB. 
			This an event with no clear condition. Only severity is 
			WARNING."
                ::= { com21Traps 104 }

        hcxStuAcqOnlineFail NOTIFICATION-TYPE
                OBJECTS { hcxAlmSeverity, hcxEventLogTime,
		            hcxStuStatusMacAddr }
                STATUS current
                DESCRIPTION "
			This trap is issued if an RX card successfully
			acquires an ComPort, but the ComPort cannot be placed
			online due to a ComController or ComPort failure. 
			Only severity is WARNING."
                ::= { com21Traps 105 }

        hcxStuEth8022Filter OBJECT-TYPE
                SYNTAX INTEGER { true (1), false (2) }
                MAX-ACCESS read-write
                STATUS current
                DESCRIPTION "
                        This attribute is used to control the filtering of
			802.2 Ethernet packets for a specific ComPORT. When 
			this is enabled (true), all Ethernet packets of this 
			type shall be dropped. Default is true."
                ::= { com21HcxStuStatusEntry 20 }

        hcxStuDnstrmFwdCntrl OBJECT-TYPE
                SYNTAX INTEGER { true (1), false (2) }
                MAX-ACCESS read-write
                STATUS current
                DESCRIPTION "  
                        This attribute is used to control the forwarding
                        of packets downstream which where received in the
			upstream from a specific ComPORT. If set to true, 
			then the data will NOT be forwarded downstream but 
			out the WAN interface only. Default is true. Not
			that the logic here is reversed when compared to
			the hcxVlanPeerToPeerFlag attribute in the VLAN
			group."
                ::= { com21HcxStuStatusEntry 21 } 

        hcxStuStatsCollect OBJECT-TYPE
                SYNTAX INTEGER { enable (1), disable (2) }
                MAX-ACCESS read-write
                STATUS current
                DESCRIPTION "
                        This attribute is used to control whether
			statistics are collected periodically from the
			ComPort. Default is enable for two-way ComPorts
			and disable for ComPorts configured for telephone
			return operation."
                ::= { com21HcxStuStatusEntry 22 }

	hcxStuPowerRangeState OBJECT-TYPE
                SYNTAX INTEGER {
				noProblem (1),
				powerLow (2),
				powerHigh (3) }
                MAX-ACCESS read-only
                STATUS current
                DESCRIPTION "  
                        This attribute describes the power ranging state
			of the ComPort. An unacquired ComPort or one
			operating within the power specifications shall
			have a state of noProblem."
                ::= { com21HcxStuStatusEntry 23 }

        hcxStuRangFailPowerLow NOTIFICATION-TYPE
                OBJECTS { hcxAlmSeverity, hcxEventLogTime,
			    hcxStuStatusMacAddr }
                STATUS current
                DESCRIPTION "
                        This trap is generated when the RX card cannot
			set a ComPort's power level correctly - the ComPort
			has too low a power level. This alarm is generated
			once and cleared only when the condition is 
			corrected or the ComPort is deacquired. Default 
			severity is MINOR."
                ::= { com21Traps 108 }

        hcxStuRangFailLowClear NOTIFICATION-TYPE
                OBJECTS { hcxAlmSeverity, hcxEventLogTime,
                            hcxStuStatusMacAddr }
                STATUS current
                DESCRIPTION "
                        This trap is generated when the RX card successful
			ranges a ComPort that was previously reported as
			in the low power state or when a ComPort in that
			state is deacquired. Severity is CLEARED."
                ::= { com21Traps 140 }

        hcxStuRangFailPowerHigh NOTIFICATION-TYPE
                OBJECTS { hcxAlmSeverity, hcxEventLogTime,
			    hcxStuStatusMacAddr }
                STATUS current
                DESCRIPTION "
			This trap is generated when the RX card cannot
                        set a ComPort's power level correctly - the ComPort
                        has too high a power level. This alarm is generated
                        once and cleared only when the condition is
                        corrected or the ComPort is deacquired. Default
                        severity is MINOR."
                ::= { com21Traps 109 }

        hcxStuRangFailHighClear NOTIFICATION-TYPE
                OBJECTS { hcxAlmSeverity, hcxEventLogTime,
                            hcxStuStatusMacAddr }
                STATUS current
                DESCRIPTION "
                        This trap is generated when the RX card successful
                        ranges a ComPort that was previously reported as
                        in the high power state or when a ComPort in that
                        state is deacquired. Severity is CLEARED."
                ::= { com21Traps 141 }

        hcxStuRpmIPortId OBJECT-TYPE
                SYNTAX INTEGER (0..8)
                MAX-ACCESS read-only
                STATUS current
                DESCRIPTION "
                        This attribute specifies the RPM I-Port to
			which the ComPort is associated. 0 will be
			reported if the ComPort has never been acquired
			or is not connected via an RPM. The last known 
			I-Port will be reported if the ComPort is 
			unacquired but have been acquired previously."
                ::= { com21HcxStuStatusEntry 24 }

        hcxStuEthLpbkTestUpRate OBJECT-TYPE
                SYNTAX Integer32
                MAX-ACCESS read-only
                STATUS current
                DESCRIPTION "
                        This attribute contains the rate recorded for the
                        last loopback test. Will be 0 if test failed."
                ::= { com21HcxStuStatusEntry 25 }

        hcxStuEthLpbkTestLatency OBJECT-TYPE
                SYNTAX Integer32
                MAX-ACCESS read-only
                STATUS current
                DESCRIPTION "
                        This attribute contains the round trip packet
                        latency recorded by the last loopback test. Again
                        0 if test failed."
                ::= { com21HcxStuStatusEntry 26 }

        hcxStuModelName OBJECT-TYPE
                SYNTAX INTEGER {
				uninitialized (1),
				invalid(2),
				cp1000 (3),
				cp1000A (4),
				cp1000B (5),
				cp1000C (6),
				cp1000D (7),
				cp1100 (8),
				cp1100A (9),
				cp1100B (10),
				cp1100C (11),
				cp1100D (12),
				cp2000 (13),
				cp2000A (14),
				cp2100 (15),
				cp2100A (16),
				cp5020 (17),
				cp5120 (18) }
                MAX-ACCESS read-only
                STATUS current
                DESCRIPTION "
                        This attribute defines the ComPort Model Type read
			from the ComPort. Prior to the acquisition of the
			ComPort for the first time, this attribute will be
			uninitialized. Invalid will be set if the model
			number is not recongnized."
                ::= { com21HcxStuStatusEntry 27 }

        hcxStuEthTestDnRate OBJECT-TYPE
                SYNTAX Integer32
                MAX-ACCESS read-only
                STATUS current
                DESCRIPTION "
                        This attribute contains the downstream rate
			(in bps) recorded by the last hcxStuEthTestAction test.
                        0 if test failed."
                ::= { com21HcxStuStatusEntry 28 }

	hcxStuEthLpbkTestDuration OBJECT-TYPE
		SYNTAX INTEGER (5..80)
		MAX-ACCESS read-write
		STATUS current
		DESCRIPTION "
			This attribute specifies the duration of the
			loopback test in seconds. Default is 5 seconds."
		::= { com21HcxStuStatusEntry 30 }


        -- -- -- -- -- -- -- -- -- -- -- -- -- -- -- -- -- -- -- -- -- -- -- --
        -- -- -- -- -- -- -- -- -- -- -- -- -- -- -- -- -- -- -- -- -- -- -- --
        --
        -- com21HcxStuSrcIpAddrGroup
        --
        -- defines the source IP addresses, and associated masks, supported 
	-- by an individual ComPort. The ComController CC shall intercept all 
	-- ARP messages travelling upstream and check if filtering is enabled 
	-- for the ComPort - indicated by the hcxStuArpFiltEnable attribute.
	-- If filtering is enabled, then the source IP address shall be 
	-- checked against the permitted address list. If the IP 
	-- address is not found then a trap shall be generated.
	-- Also included in this group is a MAC address. This is used whenever
	-- the address of a device connected to the ComPort must be 
	-- preconfigured.
        --
        -- -- -- -- -- -- -- -- -- -- -- -- -- -- -- -- -- -- -- -- -- -- -- --
        -- -- -- -- -- -- -- -- -- -- -- -- -- -- -- -- -- -- -- -- -- -- -- --
 
        com21HcxStuSrcIpAddrTable OBJECT-TYPE
                SYNTAX SEQUENCE OF HcxStuSrcIpAddrEntry
                MAX-ACCESS not-accessible
                STATUS current
                DESCRIPTION "."
                ::= { com21HcxStuSrcIpAddrGroup 1 }
 
        com21HcxStuSrcIpAddrEntry OBJECT-TYPE
                SYNTAX HcxStuSrcIpAddrEntry
                MAX-ACCESS not-accessible
                STATUS current
                DESCRIPTION "
			Holds the IP addresses and associated masks
			for ARP filtering. There are 8 addresses per
			ComPort."
                INDEX { hcxStuSrcIpAddrMacAddr, hcxStuSrcIpAddrEntryId }
                ::= { com21HcxStuSrcIpAddrTable 1 }
 
        HcxStuSrcIpAddrEntry ::= SEQUENCE {
                hcxStuSrcIpAddrMacAddr		MacAddress,
                hcxStuSrcIpAddrIPAddr		IpAddress,
                hcxStuSrcIpAddrIPMask		IpAddress,
		hcxStuSrcIpAddrUserMacAddr	MacAddress,
		hcxStuSrcIpAddrIPStatus		Com21RowStatus,
		hcxStuSrcIpAddrEtherIPAddr	IpAddress,
		hcxStuSrcIpAddrEntryId		INTEGER,
	        hcxStuSrcIpAddrType		INTEGER,
		hcxStuSrcIpAddrLeaseTimer	Integer32}

        hcxStuSrcIpAddrMacAddr OBJECT-TYPE
                SYNTAX MacAddress
                MAX-ACCESS read-only
                STATUS current
                DESCRIPTION "
                        Contains IEEE 802 medium access control address
                        of the ComPort device."
                ::= { com21HcxStuSrcIpAddrEntry 1 }

        hcxStuSrcIpAddrIPAddr OBJECT-TYPE
                SYNTAX IpAddress
                MAX-ACCESS read-write
                STATUS current
                DESCRIPTION "
                        allowable IP Address for ComPort. Default 0.0.0.0."
                ::= { com21HcxStuSrcIpAddrEntry 2 }

        hcxStuSrcIpAddrIPMask OBJECT-TYPE
                SYNTAX IpAddress
                MAX-ACCESS read-write
                STATUS current
                DESCRIPTION "
                        IP mask for ComPort. Default is ff.ff.ff.ff."
                ::= { com21HcxStuSrcIpAddrEntry 3 }

        hcxStuSrcIpAddrUserMacAddr OBJECT-TYPE
                SYNTAX MacAddress
                MAX-ACCESS read-write
                STATUS current
                DESCRIPTION "  
                        allowable MAC Address for ComPort. Default is 
			0:0:0:0:0:0"
                ::= { com21HcxStuSrcIpAddrEntry 4 }

        hcxStuSrcIpAddrIPStatus OBJECT-TYPE
                SYNTAX Com21RowStatus
                MAX-ACCESS read-create
                STATUS current
                DESCRIPTION "
                        Used to delete or create an entry."
                ::= { com21HcxStuSrcIpAddrEntry 5 }

	hcxStuSrcIpAddrEtherIPAddr OBJECT-TYPE
                SYNTAX IpAddress
                MAX-ACCESS read-write
                STATUS current
                DESCRIPTION "
                        IP address of Ethernet Interface on users PC.
			Applicable only to telephone return."
                ::= { com21HcxStuSrcIpAddrEntry 6 }

        hcxStuSrcIpAddrEntryId OBJECT-TYPE  
                SYNTAX INTEGER (1..8)
                MAX-ACCESS read-only
                STATUS current
                DESCRIPTION "  
                        Contains table entry id."
                ::= { com21HcxStuSrcIpAddrEntry 7 }

        hcxStuSrcIpAddrType OBJECT-TYPE
                SYNTAX INTEGER { static (1), dynamic (2) }
                MAX-ACCESS read-only
                STATUS current
                DESCRIPTION "
                        This attribute indicates if the specified IP
                        address/mask combination is Statically configured
                        by NMAPS or dynamically learnt via DHCP"
                ::= { com21HcxStuSrcIpAddrEntry 8 }

        hcxStuSrcIpAddrLeaseTimer OBJECT-TYPE       
                SYNTAX Integer32
                MAX-ACCESS read-only
                STATUS current
                DESCRIPTION "
                        This attribute indicates the lease timer value
                        associated with a dynamically learnt IP
                        address"
                ::= { com21HcxStuSrcIpAddrEntry 9 }



        -- -- -- -- -- -- -- -- -- -- -- -- -- -- -- -- -- -- -- -- -- -- -- --
        -- -- -- -- -- -- -- -- -- -- -- -- -- -- -- -- -- -- -- -- -- -- -- --
        --
        -- com21HcxStuDstIpAddrGroup
        --
        -- defines the per ComPort destination IP addresses and mask used in 
	-- the filter operations.
        --
        -- -- -- -- -- -- -- -- -- -- -- -- -- -- -- -- -- -- -- -- -- -- -- --
        -- -- -- -- -- -- -- -- -- -- -- -- -- -- -- -- -- -- -- -- -- -- -- --
 
        com21HcxStuDstIpAddrTable OBJECT-TYPE
                SYNTAX SEQUENCE OF HcxStuDstIpAddrEntry
                MAX-ACCESS not-accessible
                STATUS current
                DESCRIPTION "."
                ::= { com21HcxStuDstIpAddrGroup 1 }
 
        com21HcxStuDstIpAddrEntry OBJECT-TYPE
                SYNTAX HcxStuDstIpAddrEntry
                MAX-ACCESS not-accessible
                STATUS current
                DESCRIPTION "
                        Holds the IP addresses and associated masks
                        for ARP filtering. There are 8 addresses per
                        ComPort."
                INDEX { hcxStuDstIpAddrMacAddr, hcxStuDstIpAddrEntryId }
                ::= { com21HcxStuDstIpAddrTable 1 }
 
        HcxStuDstIpAddrEntry ::= SEQUENCE {
                hcxStuDstIpAddrMacAddr     MacAddress,
                hcxStuDstIpAddrIPAddr      IpAddress,
                hcxStuDstIpAddrIPMask      IpAddress,
                hcxStuDstIpAddrIPStatus    Com21RowStatus,
                hcxStuDstIpAddrEntryId     INTEGER }

        hcxStuDstIpAddrMacAddr OBJECT-TYPE
                SYNTAX MacAddress
                MAX-ACCESS read-only
                STATUS current
                DESCRIPTION "
                        Contains IEEE 802 medium access control address
                        of the ComPort device."
                ::= { com21HcxStuDstIpAddrEntry 1 }

        hcxStuDstIpAddrIPAddr OBJECT-TYPE
                SYNTAX IpAddress
                MAX-ACCESS read-write
                STATUS current
                DESCRIPTION "
                        allowable IP Address for ComPort. Default 0.0.0.0."
                ::= { com21HcxStuDstIpAddrEntry 2 }
 
        hcxStuDstIpAddrIPMask OBJECT-TYPE
                SYNTAX IpAddress
                MAX-ACCESS read-write
                STATUS current
                DESCRIPTION "
                        IP mask for ComPort. Default is ff.ff.ff.ff."
                ::= { com21HcxStuDstIpAddrEntry 3 }
 
        hcxStuDstIpAddrIPStatus OBJECT-TYPE
                SYNTAX Com21RowStatus
                MAX-ACCESS read-create
                STATUS current
                DESCRIPTION "
                        Used to delete or create an entry."
                ::= { com21HcxStuDstIpAddrEntry 4 }
 
        hcxStuDstIpAddrEntryId OBJECT-TYPE
                SYNTAX INTEGER (1..8)
                MAX-ACCESS read-only
                STATUS current
                DESCRIPTION "
                        Contains table entry id."
                ::= { com21HcxStuDstIpAddrEntry 5 }
 

 
        -- -- -- -- -- -- -- -- -- -- -- -- -- -- -- -- -- -- -- -- -- -- -- --
        -- -- -- -- -- -- -- -- -- -- -- -- -- -- -- -- -- -- -- -- -- -- -- --
        --
        -- com21HcxStuIpFiltGroup
        --
        -- this group controls the filter operations performed for each ComPort.
	-- This includes various address, bootp and dhcp filtering.
        --
        -- -- -- -- -- -- -- -- -- -- -- -- -- -- -- -- -- -- -- -- -- -- -- --
        -- -- -- -- -- -- -- -- -- -- -- -- -- -- -- -- -- -- -- -- -- -- -- --

        com21HcxStuIpFiltTable OBJECT-TYPE
                SYNTAX SEQUENCE OF HcxStuIpFiltEntry
                MAX-ACCESS not-accessible
                STATUS current
                DESCRIPTION "."
                ::= { com21HcxStuIpFiltGroup 1 }
 
        com21HcxStuIpFiltEntry OBJECT-TYPE
                SYNTAX HcxStuIpFiltEntry
                MAX-ACCESS not-accessible
                STATUS current
                DESCRIPTION "."
                INDEX { hcxStuIpFiltMacAddr }
                ::= { com21HcxStuIpFiltTable 1 }

        HcxStuIpFiltEntry ::= SEQUENCE {
                hcxStuIpFiltMacAddr        MacAddress,
                hcxStuIpArpFiltEnable      INTEGER,
                hcxStuIpArpFiltInvalidAddr IpAddress,
                hcxStuIpArpFiltBadServAddr IpAddress,
		hcxStuIpSrcFiltEnable      INTEGER,
		hcxStuIpDstFiltEnable      INTEGER,
		hcxStuIpBootpReqFiltEnbl   INTEGER,
		hcxStuIpBootpReplyFiltEnbl INTEGER,
		hcxStuIpDhcpSnoopFiltEnbl  INTEGER,
                hcxStuL2SnapFiltEnbl       INTEGER,
                hcxStuL2NonSnapFiltEnbl    INTEGER,
                hcxStuL2EnetFiltEnbl       INTEGER,
                hcxStuL2ArpIpv4FiltEnbl    INTEGER,
                hcxStuL2Ipv4FiltEnbl       INTEGER,
                hcxStuL2Ipv6FiltEnbl       INTEGER,
                hcxStuL2IpxFiltEnbl        INTEGER,
                hcxStuL2AppletalkFiltEnbl  INTEGER,
                hcxStuL2OthersFiltEnbl     INTEGER,
                hcxStuIpNetbiosFiltEnbl    INTEGER }
 
        hcxStuIpFiltMacAddr OBJECT-TYPE
                SYNTAX MacAddress
                MAX-ACCESS read-only
                STATUS current
                DESCRIPTION "
                        Contains IEEE 802 medium access control address
                        of the ComPort device."
                ::= { com21HcxStuIpFiltEntry 1 }

        hcxStuIpArpFiltEnable OBJECT-TYPE           
                SYNTAX INTEGER { true (1), false (2) }
                MAX-ACCESS read-write
                STATUS current
                DESCRIPTION "
                        Specifies whether ARP authentication filtering
                        should be enabled for this ComPort. This filter
                        is applicable to 10BT, 100BT, and OC3 cards.
                        It filters traffic in the upstream direction.
                        Default is false.  This filter can also be
                        enabled for an entire VLAN via the MIB attribute
                        hcxVlanIpArpFiltEnbl."
                ::= { com21HcxStuIpFiltEntry 2 }
         
        hcxStuIpArpFiltInvalidAddr OBJECT-TYPE      
                SYNTAX IpAddress
                MAX-ACCESS read-only
                STATUS current
                DESCRIPTION "
                        Contains the last invalid IP Address used by
                        the ComPort. This value is cleared on the quarter
                        hour."
                ::= { com21HcxStuIpFiltEntry 3 }
 
        hcxStuArpInvalidAddr NOTIFICATION-TYPE
                OBJECTS { hcxAlmSeverity, hcxEventLogTime,
			    hcxStuIpFiltMacAddr, hcxStuIpArpFiltInvalidAddr }
                STATUS current
                DESCRIPTION "
                        this trap is generated whenever an invalid ARP IP
			source address is detected. Severity is WARNING."
                ::= { com21Traps 106 }
 
        hcxStuIpArpFiltBadServAddr OBJECT-TYPE
                SYNTAX IpAddress
                MAX-ACCESS read-only
                STATUS current
                DESCRIPTION "
                        Contains the last ComController Server IP Address
                        used by the ComPort. This value is cleared on the
                        quarter hour."
                ::= { com21HcxStuIpFiltEntry 4 }
 
        hcxStuArpBadServerAddr NOTIFICATION-TYPE
                OBJECTS { hcxAlmSeverity, hcxEventLogTime,
			    hcxStuIpFiltMacAddr, hcxStuIpArpFiltBadServAddr }
                STATUS current
                DESCRIPTION "
                        this trap is generated whenever the ComPort is
			detected as utilizing a reserved server address as
			its source IP address. Severity is WARNING."
                ::= { com21Traps 107 }

        hcxStuIpSrcFiltEnable  OBJECT-TYPE
                SYNTAX INTEGER { true (1), false (2) }
                MAX-ACCESS  read-write
                STATUS  current
                DESCRIPTION "
                        Specifies whether IP source address filtering
                        should be enabled for this ComPort. This filter
                        is applicable to 100BT, and OC3 cards.  It
                        is not applicable to 10BT card.  It filters
                        traffic in the upstream direction.  Default
                        is false.  This filter can also be enabled
                        for an entire VLAN via the MIB attribute
                        hcxVlanIpSrcFiltEnbl."
                ::= { com21HcxStuIpFiltEntry 5 }
 
        hcxStuIpDstFiltEnable  OBJECT-TYPE
                SYNTAX INTEGER { true (1), false (2) }
                MAX-ACCESS  read-write
                STATUS  current
                DESCRIPTION "
                        Specifies whether IP destination address
                        filtering should be enabled for this ComPort.
                        This filter is applicable to 100BT, and OC3
                        cards.  It is not applicable to to 10BT card.
                        It filters traffic in the upstream direction.
                        Default is false.  This filter can also be
                        enabled for an entire VLAN via the MIB
                        attribute hcxVlanIpDstFiltEnbl."
                ::= { com21HcxStuIpFiltEntry 6 }
 
        hcxStuIpBootpReqFiltEnbl  OBJECT-TYPE
                SYNTAX INTEGER { true (1), false (2) }
                MAX-ACCESS  read-write
                STATUS  deprecated
                DESCRIPTION "
                        Allows enabling or disabling BOOTP Request Filter
                        for this STU. 
			Default: FALSE"
                ::= { com21HcxStuIpFiltEntry 7 }

        hcxStuIpBootpReplyFiltEnbl  OBJECT-TYPE
                SYNTAX INTEGER { true (1), false (2) }
                MAX-ACCESS  read-write
                STATUS  current
                DESCRIPTION "
                        Specifies whether BOOTP replies, or DHCPOFFER,
                        or DHCPACK packets should be filtered for this
                        ComPort. This filter is applicable to 100BT, and
                        OC3 cards.  It it not applicable to 10BT card.
                        It filters traffic in the upstream direction.
                        Default is false.  This filter can also be
                        enabled for an entire VLAN via the MIB attribute
                        hcxVlanIpBootpReplyFiltEnbl."
                ::= { com21HcxStuIpFiltEntry 8 }
 
 
        hcxStuIpDhcpSnoopFiltEnbl  OBJECT-TYPE
                SYNTAX INTEGER { true (1), false (2) }
                MAX-ACCESS  read-write
                STATUS  current
                DESCRIPTION "
                        Specifies whether DHCP snooping should be
                        enabled for this ComPort. This filter is applicable
                        to 100BT, and OC3 cards.  It is not applicable
                        to 10BT card.  It snoops traffic in the downstream
                        direction for DHCPACK packets, and in the upstream
                        direction for DHCPDECLINE or DHCPRELEASE packets.
                        Dynamic IP address assigments thus learned are
                        stored in the valid source IP address table
                        (com21HcxStuSrcIpAddrGroup.) Default is false.
                        This filter can also be enabled for an entire
                        VLAN via the MIB attribute hcxVlanIpDhcpSnoopFiltEnbl."
                ::= { com21HcxStuIpFiltEntry 9 }

        hcxStuL2SnapFiltEnbl OBJECT-TYPE
                SYNTAX INTEGER { true (1), false (2) }
                MAX-ACCESS read-write
                STATUS current
                DESCRIPTION "
                        Specifies whether SNAP-encoded IEEE 802.3 packets
                        should be filtered for this ComPort. This filter
                        is applicable to 100BT, and OC3 cards.  It is not
                        applicable to 10BT card.  It filters traffic
                        in both upstream and downstream directions.
                        Default is false.  This filter can also be
                        enabled for an entire VLAN via the MIB
                        attribute hcxVlanL2SnapFiltEnbl."
                ::= { com21HcxStuIpFiltEntry 10 }
 
        hcxStuL2NonSnapFiltEnbl OBJECT-TYPE
                SYNTAX INTEGER { true (1), false (2) }
                MAX-ACCESS read-write
                STATUS current
                DESCRIPTION "
                        Specifies whether non-SNAP-encoded IEEE 802.3
                        packets should be filtered for this ComPort.
                        This filter is applicable to 10BT, 100BT, and
                        OC3 cards.  It filters traffic in both upstream
                        and downstream directions.  Default is false.
                        This filter can also be enabled for an entire
                        VLAN via the MIB attribute hcxVlanL2NonSnapFiltEnbl."
                ::= { com21HcxStuIpFiltEntry 11 }
 
        hcxStuL2EnetFiltEnbl OBJECT-TYPE
                SYNTAX INTEGER { true (1), false (2) }
                MAX-ACCESS read-write
                STATUS deprecated
                DESCRIPTION "
                        Specifies whether Ethernet packets should be 
			filtered for this ComPort.  This filter is applicable 
			to 100BT and  OC3 cards.  It is not applicable to 10BT 
			card.  It filters traffic in both upstream and 
			downstream directions.  Default is false.
                        This filter can also be enabled for an entire
                        VLAN via the MIB attribute hcxVlanL2EnetFiltEnbl."
                ::= { com21HcxStuIpFiltEntry 12 }
 
        hcxStuL2ArpIpv4FiltEnbl OBJECT-TYPE
                SYNTAX INTEGER { true (1), false (2) }
                MAX-ACCESS read-write
                STATUS deprecated
                DESCRIPTION "
                        Specifies whether ARP packets should be 
                        filtered for this ComPort.  This filter is applicable 
                        to 100BT and  OC3 cards.  It is not applicable to 10BT 
                        card.  It filters traffic in both upstream and 
                        downstream directions.  Default is false.
                        This filter can also be enabled for an entire  
                        VLAN via the MIB attribute hcxVlanL2ArpIpv4FiltEnbl."  
                ::= { com21HcxStuIpFiltEntry 13 }
 
        hcxStuL2Ipv4FiltEnbl OBJECT-TYPE
                SYNTAX INTEGER { true (1), false (2) }
                MAX-ACCESS read-write
                STATUS deprecated
                DESCRIPTION "
                        Specifies whether IPv4 packets should be 
                        filtered for this ComPort.  This filter is applicable 
                        to 100BT and  OC3 cards.  It is not applicable to 10BT 
                        card.  It filters traffic in both upstream and 
                        downstream directions.  Default is false.
                        This filter can also be enabled for an entire  
                        VLAN via the MIB attribute hcxVlanL2Ipv4FiltEnbl."  
                ::= { com21HcxStuIpFiltEntry 14 }
 
        hcxStuL2Ipv6FiltEnbl OBJECT-TYPE
                SYNTAX INTEGER { true (1), false (2) }
                MAX-ACCESS read-write
                STATUS deprecated
                DESCRIPTION "
                        Specifies whether IPv6 packets should be 
                        filtered for this ComPort.  This filter is applicable 
                        to 100BT and  OC3 cards.  It is not applicable to 10BT 
                        card.  It filters traffic in both upstream and 
                        downstream directions.  Default is false.
                        This filter can also be enabled for an entire  
                        VLAN via the MIB attribute hcxVlanL2Ipv6FiltEnbl."  
                ::= { com21HcxStuIpFiltEntry 15 }
 
        hcxStuL2IpxFiltEnbl OBJECT-TYPE
                SYNTAX INTEGER { true (1), false (2) }
                MAX-ACCESS read-write
                STATUS deprecated
                DESCRIPTION "
                        Specifies whether IPX packets should be 
                        filtered for this ComPort.  This filter is applicable 
                        to 100BT and  OC3 cards.  It is not applicable to 10BT 
                        card.  It filters traffic in both upstream and 
                        downstream directions.  Default is false.
                        This filter can also be enabled for an entire  
                        VLAN via the MIB attribute hcxVlanL2IpxFiltEnbl."  
                ::= { com21HcxStuIpFiltEntry 16 }
 
        hcxStuL2AppletalkFiltEnbl OBJECT-TYPE
                SYNTAX INTEGER { true (1), false (2) }
                MAX-ACCESS read-write
                STATUS deprecated
                DESCRIPTION "
                        Specifies whether AppleTalk packets should be 
                        filtered for this ComPort.  This filter is applicable 
                        to 100BT and  OC3 cards.  It is not applicable to 10BT 
                        card.  It filters traffic in both upstream and 
                        downstream directions.  Default is false.  This 
			filter can also be enabled for an entire  VLAN via 
			the MIB attribute hcxVlanL2AppleTalkFiltEnbl."  
                ::= { com21HcxStuIpFiltEntry 17 }
 
        hcxStuL2OthersFiltEnbl OBJECT-TYPE
                SYNTAX INTEGER { true (1), false (2) }
                MAX-ACCESS read-write
                STATUS deprecated
                DESCRIPTION "
                        Specifies whether all layer 2 packets that are
                        none of the above (ARP, IPv4, IPv6, IPX, AppleTalk) 
			should be filtered for this ComPort. 
			This filter is applicable to 100BT and OC3 cards.
			It is not applicable to 10BT card. This filter 
			filters traffic in both directions. This filter
			can also be enabled for an entire VLAN via the
			MIB attribute hcxVlanL2OthersFiltEnbl.
			Default is false."
                ::= { com21HcxStuIpFiltEntry 18 }
 
        hcxStuIpNetbiosFiltEnbl OBJECT-TYPE
                SYNTAX INTEGER { true (1), false (2) }
                MAX-ACCESS read-write
                STATUS current
                DESCRIPTION "
                        Specifies whether NetBIOS-over-IP packets
                        should be filtered for this ComPort. This filter is 
			applicable to 100BT and OC3 cards. It  is not
			applicable to 10BT card. 
			This filter filters traffic in the upstream direction. 
			Default is false. This filter can also be enabled
			for an entire VLAN via the MIB attribute 
			hcxVlanIpNetbiosFiltEnbl."
                ::= { com21HcxStuIpFiltEntry 19 }




        -- -- -- -- -- -- -- -- -- -- -- -- -- -- -- -- -- -- -- -- -- -- -- --
        -- -- -- -- -- -- -- -- -- -- -- -- -- -- -- -- -- -- -- -- -- -- -- --
        --
        -- com21HcxStuIpFiltStatsGroup
        -- 
        -- defines the IP filter related statistics for each ComPort.
        -- 
        -- -- -- -- -- -- -- -- -- -- -- -- -- -- -- -- -- -- -- -- -- -- -- --
        -- -- -- -- -- -- -- -- -- -- -- -- -- -- -- -- -- -- -- -- -- -- -- --

        com21HcxStuIpFiltStatsTable OBJECT-TYPE
                SYNTAX  SEQUENCE OF HcxStuIpFiltStatsEntry
                MAX-ACCESS  not-accessible
                STATUS  current
                DESCRIPTION "."
                ::= { com21HcxStuIpFiltStatsGroup 1 }

        com21HcxStuIpFiltStatsEntry OBJECT-TYPE
                SYNTAX  HcxStuIpFiltStatsEntry
                MAX-ACCESS  not-accessible
                STATUS  current
                DESCRIPTION "."
                INDEX { hcxStuIpFiltStatsMacAddr }
                ::= { com21HcxStuIpFiltStatsTable 1 }

        HcxStuIpFiltStatsEntry ::= SEQUENCE {
                hcxStuIpFiltStatsMacAddr        MacAddress,
                hcxStuIpCurrArpFiltStat         Gauge32,
                hcxStuIpCurrSrcFiltStat         Gauge32,
                hcxStuIpCurrDstFiltStat         Gauge32,
                hcxStuIpCurrBootpReqFiltStat    Gauge32,
                hcxStuIpCurrBootpReplyFiltStat  Gauge32,
                hcxStuIpCurrDhcpSnoopFiltStat   Gauge32,
                hcxStuL2CurrSnapFiltStat        Gauge32,
                hcxStuL2CurrNonSnapFiltStat     Gauge32,
                hcxStuL2CurrEnetFiltStat        Gauge32,
                hcxStuL2CurrArpIpv4FiltStat     Gauge32,
                hcxStuL2CurrIpv4FiltStat        Gauge32,
                hcxStuL2CurrIpv6FiltStat        Gauge32,
                hcxStuL2CurrIpxFiltStat         Gauge32,
                hcxStuL2CurrAppletalkFiltStat   Gauge32,
                hcxStuL2CurrOthersFiltStat      Gauge32,
                hcxStuIpCurrNetbiosFiltStat     Gauge32, 
                hcxStuIpPrevArpFiltStat         Gauge32,
                hcxStuIpPrevSrcFiltStat         Gauge32,
                hcxStuIpPrevDstFiltStat         Gauge32,
                hcxStuIpPrevBootpReqFiltStat    Gauge32,
                hcxStuIpPrevBootpReplyFiltStat  Gauge32,
                hcxStuIpPrevDhcpSnoopFiltStat   Gauge32,
                hcxStuL2PrevSnapFiltStat        Gauge32,
                hcxStuL2PrevNonSnapFiltStat     Gauge32,
                hcxStuL2PrevEnetFiltStat        Gauge32,
                hcxStuL2PrevArpIpv4FiltStat     Gauge32,
                hcxStuL2PrevIpv4FiltStat        Gauge32,
                hcxStuL2PrevIpv6FiltStat        Gauge32,
                hcxStuL2PrevIpxFiltStat         Gauge32,
                hcxStuL2PrevAppletalkFiltStat   Gauge32,
                hcxStuL2PrevOthersFiltStat      Gauge32,
                hcxStuIpPrevNetbiosFiltStat     Gauge32,
		hcxStuIpClearStats		Gauge }
 
        hcxStuIpFiltStatsMacAddr OBJECT-TYPE
                SYNTAX MacAddress
                MAX-ACCESS read-only
                STATUS current
                DESCRIPTION "
                        Contains IEEE 802 medium access control address
                        of the ComPort device."
                ::= { com21HcxStuIpFiltStatsEntry 1 }
 
        hcxStuIpCurrArpFiltStat OBJECT-TYPE
                SYNTAX Gauge32
                MAX-ACCESS read-only
                STATUS current
                DESCRIPTION "
                        Contains the number of ARP packets from this ComPort 
                        dropped due to authentication filtering in the
                        current 15 minute collection period."
                ::= { com21HcxStuIpFiltStatsEntry 2 }
 
        hcxStuIpCurrSrcFiltStat OBJECT-TYPE
                SYNTAX Gauge32
                MAX-ACCESS read-only
                STATUS current
                DESCRIPTION "
                        Contains the number of IP packets from this ComPort
                        dropped due to source address filtering in the
                        current 15 minute collection period."
                ::= { com21HcxStuIpFiltStatsEntry 3 }

        hcxStuIpCurrDstFiltStat OBJECT-TYPE           
                SYNTAX Gauge32
                MAX-ACCESS read-only
                STATUS current
                DESCRIPTION "
                        Contains the number of IP packets from this ComPort
                        dropped due to destination address filtering in the
                        current 15 minute collection period."
                ::= { com21HcxStuIpFiltStatsEntry 4 }

        hcxStuIpCurrBootpReqFiltStat OBJECT-TYPE      
                SYNTAX Gauge32
                MAX-ACCESS read-only
                STATUS current
                DESCRIPTION "
                        Contains the number of bootp Req packets from this
                        ComPort dropped due to filtering in the current 15 
			minute collection period."
                ::= { com21HcxStuIpFiltStatsEntry 5 }

        hcxStuIpCurrBootpReplyFiltStat OBJECT-TYPE    
                SYNTAX Gauge32
                MAX-ACCESS read-only
                STATUS current
                DESCRIPTION "
                        Contains the number of bootp Reply packets from this 
                        ComPort dropped due to filtering in the current 15 
			minute collection period."
                ::= { com21HcxStuIpFiltStatsEntry 6 }
 
        hcxStuIpCurrDhcpSnoopFiltStat OBJECT-TYPE
                SYNTAX Gauge32
                MAX-ACCESS read-only
                STATUS current
                DESCRIPTION "
                        Contains the number of DHCP Ack packets from this ComPort
                        snooped due to filtering in the current 15 minute
                        collection period."
                ::= { com21HcxStuIpFiltStatsEntry 7 }

        hcxStuIpPrevArpFiltStat OBJECT-TYPE           
                SYNTAX Gauge32
                MAX-ACCESS read-only
                STATUS current
                DESCRIPTION "
                        Contains the number of ARP packets from this ComPort
                        dropped due to authentication filtering in the
                        previous 15 minute collection period."
                ::= { com21HcxStuIpFiltStatsEntry 8 }

        hcxStuIpPrevSrcFiltStat OBJECT-TYPE
                SYNTAX Gauge32
                MAX-ACCESS read-only
                STATUS current
                DESCRIPTION "
                        Contains the number of IP packets from this ComPort
                        dropped due to source address filtering in the
                        previous 15 minute collection period."
                ::= { com21HcxStuIpFiltStatsEntry 9 }
 
        hcxStuIpPrevDstFiltStat OBJECT-TYPE
                SYNTAX Gauge32
                MAX-ACCESS read-only
                STATUS current
                DESCRIPTION "
                        Contains the number of IP packets from this ComPort
                        dropped due to destination address filtering in the
                        previous 15 minute collection period."
                ::= { com21HcxStuIpFiltStatsEntry 10 }
 
        hcxStuIpPrevBootpReqFiltStat OBJECT-TYPE
                SYNTAX Gauge32
                MAX-ACCESS read-only
                STATUS current
                DESCRIPTION "
                        Contains the number of bootp Req packets from this 
                        ComPort dropped due to filtering in the previous 15 
			minute collection period."
                ::= { com21HcxStuIpFiltStatsEntry 11 }
 
        hcxStuIpPrevBootpReplyFiltStat OBJECT-TYPE
                SYNTAX Gauge32
                MAX-ACCESS read-only
                STATUS current
                DESCRIPTION "
                        Contains the number of bootp Reply packets from this 
                        ComPort dropped due to filtering in the previous 15 
			minute collection period."
                ::= { com21HcxStuIpFiltStatsEntry 12 }
 
        hcxStuIpPrevDhcpSnoopFiltStat OBJECT-TYPE
                SYNTAX Gauge32
                MAX-ACCESS read-only
                STATUS current
                DESCRIPTION "
                        Contains the number of DHCP Ack packets from this ComPort
                        snooped due to filtering in the previous 15 minute
                        collection period."
                ::= { com21HcxStuIpFiltStatsEntry 13 }

        hcxStuIpClearStats OBJECT-TYPE      
		SYNTAX INTEGER { nil(1), clear(2) }
                MAX-ACCESS read-write
                STATUS current
                DESCRIPTION "
                        This attribute is used to clear all IP Filter
                        statistics counters in this group. This operation
                        is only possible if the hcxStatsControl attribute
                        is set to wrapCurr."
                ::= { com21HcxStuIpFiltStatsEntry 14 }


        hcxStuL2CurrSnapFiltStat OBJECT-TYPE
                SYNTAX Gauge32
                MAX-ACCESS read-only
                STATUS current
                DESCRIPTION "
                        Contains the number of SNAP-encoded IEEE 802.3 packets 
			filtered in the current 15 min collection period."
                ::= { com21HcxStuIpFiltStatsEntry 15 }

        hcxStuL2CurrNonSnapFiltStat OBJECT-TYPE
                SYNTAX Gauge32
                MAX-ACCESS read-only
                STATUS current
                DESCRIPTION "
                        Contains the number of non-SNAP-encoded IEEE 802.3 packets 
                        filtered in the current 15 min collection period."
                ::= { com21HcxStuIpFiltStatsEntry 16 }

        hcxStuL2CurrEnetFiltStat OBJECT-TYPE
                SYNTAX Gauge32
                MAX-ACCESS read-only
                STATUS deprecated
                DESCRIPTION "
                        Contains the number of Ethernet packets 
                        filtered in the current 15 min collection period."
                ::= { com21HcxStuIpFiltStatsEntry 17 }

        hcxStuL2CurrArpIpv4FiltStat OBJECT-TYPE
                SYNTAX Gauge32
                MAX-ACCESS read-only
                STATUS deprecated
                DESCRIPTION "
                        Contains the number of ARP for IPv4 packets 
                        filtered in the current 15 min collection period."
                ::= { com21HcxStuIpFiltStatsEntry 18 }


        hcxStuL2CurrIpv4FiltStat OBJECT-TYPE
                SYNTAX Gauge32
                MAX-ACCESS read-only
                STATUS deprecated
                DESCRIPTION "
                        Contains the number of IPv4 packets 
                        filtered in the current 15 min collection period."
                ::= { com21HcxStuIpFiltStatsEntry 19 }

        hcxStuL2CurrIpv6FiltStat OBJECT-TYPE
                SYNTAX Gauge32
                MAX-ACCESS read-only
                STATUS deprecated
                DESCRIPTION "
                        Contains the number of IPv6 packets 
                        filtered in the current 15 min collection period."
                ::= { com21HcxStuIpFiltStatsEntry 20 }

        hcxStuL2CurrIpxFiltStat OBJECT-TYPE
                SYNTAX Gauge32
                MAX-ACCESS read-only
                STATUS deprecated
                DESCRIPTION "
                        Contains the number of IPX packets 
                        filtered in the current 15 min collection period."
                ::= { com21HcxStuIpFiltStatsEntry 21 }

        hcxStuL2CurrAppletalkFiltStat OBJECT-TYPE
                SYNTAX Gauge32
                MAX-ACCESS read-only
                STATUS deprecated
                DESCRIPTION "
                        Contains the number of Appletalk packets 
                        filtered in the current 15 min collection period."
                ::= { com21HcxStuIpFiltStatsEntry 22 }

        hcxStuL2CurrOthersFiltStat OBJECT-TYPE
                SYNTAX Gauge32
                MAX-ACCESS read-only
                STATUS deprecated
                DESCRIPTION "
                        Contains the number of packets that are non
			of the above that are 
                        filtered in the current 15 min collection period."
                ::= { com21HcxStuIpFiltStatsEntry 23 }


        hcxStuIpCurrNetbiosFiltStat OBJECT-TYPE
                SYNTAX Gauge32
                MAX-ACCESS read-only
                STATUS current
                DESCRIPTION "
                        Contains the number of Netbios packets
                        filtered in the current 15 min collection period."
                ::= { com21HcxStuIpFiltStatsEntry 24 }

        hcxStuL2PrevSnapFiltStat OBJECT-TYPE
                SYNTAX Gauge32
                MAX-ACCESS read-only
                STATUS current
                DESCRIPTION "
                        Contains the number of SNAP-encoded IEEE 802.3 packets
                        filtered in the previous 15 min collection period."
                ::= { com21HcxStuIpFiltStatsEntry 25 }
 
        hcxStuL2PrevNonSnapFiltStat OBJECT-TYPE
                SYNTAX Gauge32
                MAX-ACCESS read-only
                STATUS current
                DESCRIPTION "
                        Contains the number of non-SNAP-encoded IEEE 802.3 packets
                        filtered in the previous 15 min collection period."
                ::= { com21HcxStuIpFiltStatsEntry 26 }
 
        hcxStuL2PrevEnetFiltStat OBJECT-TYPE
                SYNTAX Gauge32
                MAX-ACCESS read-only
                STATUS deprecated
                DESCRIPTION "
                        Contains the number of Ethernet packets
                        filtered in the previous 15 min collection period."
                ::= { com21HcxStuIpFiltStatsEntry 27 }
 
        hcxStuL2PrevArpIpv4FiltStat OBJECT-TYPE
                SYNTAX Gauge32
                MAX-ACCESS read-only
                STATUS deprecated
                DESCRIPTION "
                        Contains the number of ARP for IPv4 packets
                        filtered in the previous 15 min collection period."
                ::= { com21HcxStuIpFiltStatsEntry 28 }
 
 
        hcxStuL2PrevIpv4FiltStat OBJECT-TYPE
                SYNTAX Gauge32
                MAX-ACCESS read-only
                STATUS deprecated
                DESCRIPTION "
                        Contains the number of IPv4 packets
                        filtered in the previous 15 min collection period."
                ::= { com21HcxStuIpFiltStatsEntry 29 }
 
        hcxStuL2PrevIpv6FiltStat OBJECT-TYPE
                SYNTAX Gauge32
                MAX-ACCESS read-only
                STATUS deprecated
                DESCRIPTION "
                        Contains the number of IPv6 packets
                        filtered in the previous 15 min collection period."
                ::= { com21HcxStuIpFiltStatsEntry 30 }
 
        hcxStuL2PrevIpxFiltStat OBJECT-TYPE
                SYNTAX Gauge32
                MAX-ACCESS read-only
                STATUS deprecated
                DESCRIPTION "
                        Contains the number of IPX packets
                        filtered in the previous 15 min collection period."
                ::= { com21HcxStuIpFiltStatsEntry 31 }
 
 
        hcxStuL2PrevAppletalkFiltStat OBJECT-TYPE
                SYNTAX Gauge32
                MAX-ACCESS read-only
                STATUS deprecated
                DESCRIPTION "
                        Contains the number of Appletalk packets
                        filtered in the previous 15 min collection period."
                ::= { com21HcxStuIpFiltStatsEntry 32 }
 
        hcxStuL2PrevOthersFiltStat OBJECT-TYPE
                SYNTAX Gauge32
                MAX-ACCESS read-only
                STATUS deprecated
                DESCRIPTION "
                        Contains the number of packets that are non
                        of the above that are
                        filtered in the previous 15 min collection period."
                ::= { com21HcxStuIpFiltStatsEntry 33 }
 
 
        hcxStuIpPrevNetbiosFiltStat OBJECT-TYPE
                SYNTAX Gauge32
                MAX-ACCESS read-only
                STATUS current
                DESCRIPTION "
                        Contains the number of Netbios packets
                        filtered in the previous 15 min collection period."
                ::= { com21HcxStuIpFiltStatsEntry 34 }


        -- -- -- -- -- -- -- -- -- -- -- -- -- -- -- -- -- -- -- -- -- -- -- --
END
