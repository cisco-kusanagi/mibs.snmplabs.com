WS-SMI DEFINITIONS ::= BEGIN
 
		IMPORTS
			enterprises, MODULE-IDENTITY, OBJECT-IDENTITY			
				FROM SNMPv2-SMI;
	
	
		-- 1.3.6.1.4.1.388
		symbol MODULE-IDENTITY 
			LAST-UPDATED "200509232337Z"		-- September 23, 2005 at 23:37 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"symbol smi mib"
			REVISION "200605241346Z"		-- May 24, 2006 at 13:46 GMT
			DESCRIPTION 
				"01a06"
			REVISION "200509242337Z"		-- September 24, 2005 at 23:37 GMT
			DESCRIPTION 
				"01a05"
			REVISION "200507071202Z"		-- July 07, 2005 at 12:02 GMT
			DESCRIPTION 
				"01a04"
			REVISION "200505171107Z"		-- May 17, 2005 at 11:07 GMT
			DESCRIPTION 
				"01a03"
			REVISION "200505051111Z"		-- May 05, 2005 at 11:11 GMT
			DESCRIPTION 
				"01a02"
			REVISION "200505041022Z"		-- May 04, 2005 at 10:22 GMT
			DESCRIPTION 
				"01a01"
			::= { enterprises 388 }

		
	
--
-- Node definitions
--
	
		-- 1.3.6.1.4.1.388.1
		spectrum24 OBJECT IDENTIFIER ::= { symbol 1 }

		
		-- 1.3.6.1.4.1.388.2
		wnms OBJECT IDENTIFIER ::= { symbol 2 }

		
		-- 1.3.6.1.4.1.388.3
		wlan OBJECT IDENTIFIER ::= { symbol 3 }

		
		-- 1.3.6.1.4.1.388.4
		customProducts1 OBJECT IDENTIFIER ::= { symbol 4 }

		
		-- 1.3.6.1.4.1.388.5
		customProducts2 OBJECT IDENTIFIER ::= { symbol 5 }

		
		-- 1.3.6.1.4.1.388.6
		ws5000 OBJECT IDENTIFIER ::= { symbol 6 }

		
		-- 1.3.6.1.4.1.388.7
		symbolProducts OBJECT IDENTIFIER ::= { symbol 7 }

		
		-- 1.3.6.1.4.1.388.8
		uk OBJECT IDENTIFIER ::= { symbol 8 }

		
		-- 1.3.6.1.4.1.388.9
		emm OBJECT IDENTIFIER ::= { symbol 9 }

		
		-- 1.3.6.1.4.1.388.10
		mk OBJECT IDENTIFIER ::= { symbol 10 }

		
		-- 1.3.6.1.4.1.388.11
		wsd OBJECT IDENTIFIER ::= { symbol 11 }

		
		-- 1.3.6.1.4.1.388.11.1
		sysoids OBJECT IDENTIFIER ::= { wsd 1 }

		
		-- 1.3.6.1.4.1.388.11.1.1
		ws2000 OBJECT-IDENTITY
			STATUS current
			DESCRIPTION 
				"Description."
			::= { sysoids 1 }

		
		-- 1.3.6.1.4.1.388.11.1.2
		ap513 OBJECT-IDENTITY
			STATUS current
			DESCRIPTION 
				"Description."
			::= { sysoids 2 }

		
		-- 1.3.6.1.4.1.388.11.1.3
		pinnacle OBJECT-IDENTITY
			STATUS current
			DESCRIPTION 
				"Description."
			::= { sysoids 3 }

		
		-- 1.3.6.1.4.1.388.11.3
		wsdProduct OBJECT-IDENTITY
			STATUS current
			DESCRIPTION 
				"Description."
			::= { wsd 3 }

		
		-- 1.3.6.1.4.1.388.11.4
		wsdFeature OBJECT-IDENTITY
			STATUS current
			DESCRIPTION 
				"Description."
			::= { wsd 4 }

		
		-- 1.3.6.1.4.1.388.14
		ws OBJECT IDENTIFIER ::= { symbol 14 }

		
		-- 1.3.6.1.4.1.388.14.1
		wsInfra OBJECT IDENTIFIER ::= { ws 1 }

		
		-- 1.3.6.1.4.1.388.14.2
		wsSw OBJECT IDENTIFIER ::= { ws 2 }

		
		-- 1.3.6.1.4.1.388.14.3
		wsCc OBJECT IDENTIFIER ::= { ws 3 }

		
		-- 1.3.6.1.4.1.388.14.4
		wsMgmt OBJECT IDENTIFIER ::= { ws 4 }

		
		-- 1.3.6.1.4.1.388.14.5
		wsTrap OBJECT IDENTIFIER ::= { ws 5 }

		
		-- 1.3.6.1.4.1.388.14.6
		wsSec OBJECT IDENTIFIER ::= { ws 6 }

		
	
	END
