-- Copyright 1998 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     14-Oct-98  C. Amorossi     Initial Revision

HDSLGT1020-MIB DEFINITIONS ::= BEGIN

IMPORTS
	OBJECT-TYPE			FROM RFC-1212
	DisplayString			FROM RFC1213-MIB
	hdslGT1020                      FROM GDCHDSL-MIB;

hdslGT1020System          OBJECT IDENTIFIER ::= { hdslGT1020 1 }
hdslGT1020Version         OBJECT IDENTIFIER ::= { hdslGT1020System 1 }

-- This mib is a subset of the HDSL mib for the GT1020 product.

-- ***************************************************************************
-- The interfaces are defined as follows:
--	Unit	0
--	E1	1
--	Loop1	2
-- ***************************************************************************

gdcGT1020SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdslGT1020Version 1 }

-- ********************************************************************
-- GDC Hdsl Alarm Object Identifier Definitions
-- ********************************************************************
hdslGT1020Alarms                OBJECT IDENTIFIER ::= { hdslGT1020 2 }

hdslGT1020NoResponseAlm		OBJECT IDENTIFIER ::= { hdslGT1020Alarms 1 }
hdslGT1020DiagRxErrAlm		OBJECT IDENTIFIER ::= { hdslGT1020Alarms 2 }
hdslGT1020PowerUpAlm		OBJECT IDENTIFIER ::= { hdslGT1020Alarms 3 }
hdslGT1020UnitFailure           OBJECT IDENTIFIER ::= { hdslGT1020Alarms 4 }
hdslGT1020ChecksumCorrupt       OBJECT IDENTIFIER ::= { hdslGT1020Alarms 5 }
hdslGT1020LossofSignal		OBJECT IDENTIFIER ::= { hdslGT1020Alarms 6 }
hdslGT1020UnavailableSec	OBJECT IDENTIFIER ::= { hdslGT1020Alarms 7 }
hdslGT1020ErrorSec		OBJECT IDENTIFIER ::= { hdslGT1020Alarms 8 }
hdslGT1020LossofSyncWord	OBJECT IDENTIFIER ::= { hdslGT1020Alarms 9 }
hdslGT1020LossofFrameAlign	OBJECT IDENTIFIER ::= { hdslGT1020Alarms 10 }
hdslGT1020AllOnes		OBJECT IDENTIFIER ::= { hdslGT1020Alarms 11 }
hdslGT1020RemoteLossofSig	OBJECT IDENTIFIER ::= { hdslGT1020Alarms 12 }
hdslGT1020RemoteAlarmInd	OBJECT IDENTIFIER ::= { hdslGT1020Alarms 13 }
hdslGT1020MajorBER      	OBJECT IDENTIFIER ::= { hdslGT1020Alarms 14 }
hdslGT1020MinorBER		OBJECT IDENTIFIER ::= { hdslGT1020Alarms 15 }


-- ALARM			Maskable	Valid Interfaces
--===============================================================
--hdslGT1020NoResponseAlm	No		Unit
--hdslGT1020DiagRxErrAlm        No              Unit
--hdslGT1020PowerUpAlm		No		Unit
--hdslGT1020UnitFailure         No              Unit
--hdslGT1020ChecksumCorrupt     No              Unit
--hdslGT1020LossofSignal	Yes		E1, L1 
--hdslGT1020UnavailableSec	Yes		E1, L1
--hdslGT1020ErrorSec		Yes		E1, L1
--hdslGT1020LossofSyncWord	Yes		L1
--hdslGT1020LossofFrameAlign	Yes		E1
--hdslGT1020AllOnes		Yes		E1
--hdslGT1020RemoteLossofSig	Yes		E1
--hdslGT1020RemoteAlarmInd	Yes		E1 
--hdslGT1020MajorBER		Yes		L1
--hdslGT1020MinorBER		Yes		L1


END
