TERAWAVE-teraTDM-MIB DEFINITIONS ::= BEGIN
        -- Created by sml2mib compiler 
        IMPORTS

	Counter32 FROM SNMPv2-SMI
 enterprises,  OBJECT-TYPE,  Counter,  Gauge,  TimeTicks
        FROM RFC1155-SMI;

terawave OBJECT IDENTIFIER ::=  { enterprises 4513 }

teraCDS3Group OBJECT IDENTIFIER ::=  { terawave 8 }

     -- teraTDMCardStatsTable

teraTDMCardStatsTable OBJECT-TYPE
     SYNTAX SEQUENCE OF TeraTDMCardStatsTableEntryType
     ACCESS not-accessible
     STATUS mandatory
     DESCRIPTION
          " table teraTDMCardStatsTable"
     ::= { teraCDS3Group 8 }

teraTDMCardStatsTableEntry OBJECT-TYPE
          SYNTAX TeraTDMCardStatsTableEntryType
          ACCESS not-accessible
          STATUS mandatory
          DESCRIPTION
               " table entry teraTDMCardStatsTableEntry "
          INDEX {                   teraTDMSlotIndex }
     ::= { teraTDMCardStatsTable 1 }

TeraTDMCardStatsTableEntryType ::= SEQUENCE {
          teraTDMSlotIndex   
             Counter32,
          teraTDMPeabodyLSBState   
             INTEGER,
          teraTDMPeabodyLSBCrcCount   
             Counter32,
          teraTDMPeabodyTransitionUpCount   
             Counter32,
          teraTDMPeabodyLSBCrcLastSlot   
             INTEGER,
          teraTDMPeabodyVersion   
             INTEGER,
          teraTDMPeabodyFeature   
             INTEGER
}

teraTDMSlotIndex OBJECT-TYPE
          SYNTAX Counter32
          ACCESS read-only
          STATUS mandatory
          DESCRIPTION
               ""
          ::= { teraTDMCardStatsTableEntry 1 }

teraTDMPeabodyLSBState OBJECT-TYPE
          SYNTAX INTEGER
                  {
                  idle(1),
                  waitForBus(2),
                  monitoringBus(3)
                  }
          ACCESS read-only
          STATUS mandatory
          DESCRIPTION
               ""
          ::= { teraTDMCardStatsTableEntry 2 }

teraTDMPeabodyLSBCrcCount OBJECT-TYPE
          SYNTAX Counter32
          ACCESS read-only
          STATUS mandatory
          DESCRIPTION
               ""
          ::= { teraTDMCardStatsTableEntry 3 }

teraTDMPeabodyTransitionUpCount OBJECT-TYPE
          SYNTAX Counter32
          ACCESS read-only
          STATUS mandatory
          DESCRIPTION
               ""
          ::= { teraTDMCardStatsTableEntry 4 }

teraTDMPeabodyLSBCrcLastSlot OBJECT-TYPE
          SYNTAX INTEGER
          ACCESS read-only
          STATUS mandatory
          DESCRIPTION
               ""
          ::= { teraTDMCardStatsTableEntry 5 }

teraTDMPeabodyVersion OBJECT-TYPE
          SYNTAX INTEGER
          ACCESS read-only
          STATUS mandatory
          DESCRIPTION
               ""
          ::= { teraTDMCardStatsTableEntry 6 }

teraTDMPeabodyFeature OBJECT-TYPE
          SYNTAX INTEGER
          ACCESS read-only
          STATUS mandatory
          DESCRIPTION
               ""
          ::= { teraTDMCardStatsTableEntry 7 }

END
