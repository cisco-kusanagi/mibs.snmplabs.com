NETBOTZ-PRD-CRL-MIB2TRAP-MIB DEFINITIONS ::= BEGIN

IMPORTS
   OBJECT-TYPE FROM RFC-1212
   TRAP-TYPE FROM RFC-1215
   DisplayString FROM RFC1213-MIB
   IpAddress FROM RFC1155-SMI
   netBotz-ismetric FROM NETBOTZ-DEVICE-MIB
   netBotz-prd-crltrap FROM NETBOTZ-PRODUCTS-MIB
   netBotz-prd-crl-mib2-ping, netBotz-prd-crl-mib2-uptime, 
       netBotz-prd-crl-mib2-snmpstatus, netBotz-prd-crl-mib2if-opstatus 
       FROM NETBOTZ-PRD-CRL-MIB2-MIB;

netBotz-prd-crl-trap-index OBJECT-TYPE
	SYNTAX		INTEGER
	ACCESS		read-only
	STATUS		mandatory
	DESCRIPTION	"The ID of the crawler which sent the last trap."
	REFERENCE 	"NetBotz Last Trap ID"
	::= { netBotz-prd-crltrap 20 }

netBotz-prd-crl-trap-address OBJECT-TYPE
	SYNTAX		IpAddress
	ACCESS		read-only
	STATUS		mandatory
	DESCRIPTION	"The IP address of the last trap."
	REFERENCE 	"NetBotz Last Trap Address"
	::= { netBotz-prd-crltrap 21 }                 

netBotz-prd-crl-trap-oid OBJECT-TYPE
	SYNTAX		OBJECT IDENTIFIER
	ACCESS		read-only
	STATUS		mandatory
	DESCRIPTION	"The object id of the attribute on the target device which is the concern of the last trap."
	REFERENCE 	"NetBotz Target Trap Attribute OID"
	::= { netBotz-prd-crltrap 22 }                 

netBotz-prd-crl-trap-botoid OBJECT-TYPE
	SYNTAX		OBJECT IDENTIFIER
	ACCESS		read-only
	STATUS		mandatory
	DESCRIPTION	"The object id of the attribute on the NetBotz device which is the concern of the last trap."
	REFERENCE 	"NetBotz Botz Trap Attribute OID"
	::= { netBotz-prd-crltrap 23 }

netBotz-prd-crl-trap-value OBJECT-TYPE
	SYNTAX		INTEGER
	ACCESS		read-only
	STATUS		mandatory
	DESCRIPTION	"The value of the attribute associated with the last trap."
	REFERENCE 	"NetBotz Trap Attribute Value"
	::= { netBotz-prd-crltrap 24 }

netBotz-prd-crl-trap-date OBJECT-TYPE
	SYNTAX		INTEGER
	ACCESS		read-only
	STATUS		mandatory
	DESCRIPTION	
	"The date and time of a specific trap. This field
	contains the number of seconds elapsed since 
	midnight (00:00:00), January 1, 1970"
	REFERENCE 	"NetBotz Trap Date"
	::= { netBotz-prd-crltrap 25 }

netBotz-prd-crl-trap-attrib OBJECT-TYPE
	SYNTAX		INTEGER
	ACCESS		read-only
	STATUS		mandatory
	DESCRIPTION	"The identification number of the attribute in error"
	REFERENCE 	"NetBotz Trap Attribute ID Number"
	::= { netBotz-prd-crltrap 26 }

netBotz-prd-crl-trap-desc OBJECT-TYPE
	SYNTAX		DisplayString
	ACCESS		read-only
	STATUS		mandatory
	DESCRIPTION	"Description or name of the attribute in error"
	REFERENCE 	"NetBotz Trap Attribute Description"
	::= { netBotz-prd-crltrap 27 }


netBotz-prd-crl-ping-offline-trap TRAP-TYPE
	ENTERPRISE netBotz-prd-crl-mib2-ping
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION 
	"Netbotz Ping Trap. This trap indicates that replies to a set of pings were not received from a monitored IP address."
	REFERENCE 	"NetBotz Ping Offline Trap"
	::= 4

netBotz-prd-crl-ping-online-trap TRAP-TYPE
	ENTERPRISE netBotz-prd-crl-mib2-ping
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION 
	"Netbotz Ping Trap. This trap indicates that replies to a set of pings were received from a monitored IP address after
	a period when no replies had been received."
	REFERENCE 	"NetBotz Ping Online Trap"
	::= 5

netBotz-prd-crl-snmp-offline-trap TRAP-TYPE
	ENTERPRISE netBotz-prd-crl-mib2-snmpstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION 
	"Netbotz SNMP Offline Trap. This trap indicates that an SNMP request was
	not possible on an IP address."
	REFERENCE 	"NetBotz SNMP Offline Trap"
	::= 4

netBotz-prd-crl-snmp-online-trap TRAP-TYPE
	ENTERPRISE netBotz-prd-crl-mib2-snmpstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION 
	"Netbotz SNMP Online Trap. This trap indicates that an SNMP request succeeded
	on an IP address where it had previously failed."
	REFERENCE 	"NetBotz SNMP Online Trap"
	::= 5

netBotz-prd-crl-uptime-online-trap TRAP-TYPE
	ENTERPRISE netBotz-prd-crl-mib2-uptime
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION 
	"Netbotz Uptime Trap. This trap indicates that a device restart has been detected due to the uptime of the device
        being reported as less than the previously reported reading."
	REFERENCE 	"NetBotz Ping Uptime Trap"
	::= 5

netBotz-prd-crl-opstatus-offline-trap TRAP-TYPE
	ENTERPRISE netBotz-prd-crl-mib2if-opstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION 
	"Netbotz Interface Offline Trap. This trap indicates that an interface on a device
	did not respond to an SNMP query on the ifAdminStatus or ifOperStatus objects."
	REFERENCE 	"NetBotz Opstatus Offline Trap"
	::= 4

netBotz-prd-crl-opstatus-mismatch-trap TRAP-TYPE
	ENTERPRISE netBotz-prd-crl-mib2if-opstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION 
	"Netbotz Interface Status Mismatch Trap. This trap indicates that the operational 
	status of a device interface does not match the administrative status."
	REFERENCE 	"NetBotz Interface Mismatch Trap"
	::= 1

netBotz-prd-crl-opstatus-match-trap TRAP-TYPE
	ENTERPRISE netBotz-prd-crl-mib2if-opstatus
	VARIABLES {
		netBotz-prd-crl-trap-index,
		netBotz-prd-crl-trap-address,
		netBotz-prd-crl-trap-oid,
		netBotz-prd-crl-trap-botoid,
		netBotz-prd-crl-trap-value,
		netBotz-prd-crl-trap-date,
		netBotz-prd-crl-trap-attrib,
		netBotz-prd-crl-trap-desc,
		netBotz-ismetric
		}
	DESCRIPTION 
	"Netbotz Interface Status Match Trap. This trap indicates that the operational 
	status of a device interface now matches the administrative status. This trap indicates
	a transition from a state in which the administrative and operational status did not match."
	REFERENCE 	"NetBotz Interface Match Trap"
	::= 2

END
