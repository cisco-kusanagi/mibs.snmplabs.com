ChrComIfOpticsOCH-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfOptics				FROM  Chromatis-MIB
	chrComIfifIndex					FROM  ChrComIfifTable-MIB
	InterfaceRate				FROM  InterfaceRate-MIB
	Oc48ControlType				FROM  OC48ControlType-MIB
	RestartMode				FROM  RestartModes-MIB
	TruthValue				FROM  ChrTyp-MIB
	OCHLaserState				FROM  OCHTXLaserActualState-MIB;

-- chrComIfOpticsOCH Table

chrComIfOpticsOCHTable		OBJECT-TYPE
	SYNTAX		SEQUENCE OF ChrComIfOpticsOCHEntry
	MAX-ACCESS	not-accessible
	STATUS		current
	DESCRIPTION
	""
	::= { chrComIfOptics 5}

chrComIfOpticsOCHEntry		OBJECT-TYPE
	SYNTAX		ChrComIfOpticsOCHEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "OCH"
	::= { chrComIfOpticsOCHTable  1 }

ChrComIfOpticsOCHEntry  ::=
	SEQUENCE  {
	chrComIfOpticsInterfaceRate		InterfaceRate,
	chrComIfOpticsOchRPower		Integer32	(-501..300),
	chrComIfOpticsOchSPower		Integer32	(-501..300),
	chrComIfOpticsOchSActualPowerControlMode Oc48ControlType,
	chrComIfOpticsOchSExpectedPower	Integer32	(-101..100),
	chrComIfOpticsOchSRangeOfAllowablePwrMin Integer32	(-101..100),
	chrComIfOpticsOchSRangeOfAllowablePwrMax Integer32	(-101..100),
	chrComIfOpticsOchRParamForRxLambdaLOOCThr Integer32	(-500..301),
	chrComIfOpticsOchRNumOfPrecedingOPAs	Integer32	(-1..32),
	chrComIfOpticsOchRRxLambdaLOOCThr	Integer32	(-501..300),
	chrComIfOpticsOchRRx1310LOOCThr	Integer32	(-501..300),
	chrComIfOpticsOchRReceiverOverloadThr	Integer32	(-501..300),
	chrComIfOpticsOchRReceiverDamageThr	Integer32	(-501..300),
	chrComIfOpticsOchSLOOCThr		Integer32	(-501..300),
	chrComIfOpticsOchSLaserBiasCurrent	Integer32	(-1..4000),
	chrComIfOpticsOchSLaserTemperature	Integer32	(-1..500),
	chrComIfOpticsOchSTransmitterMode	RestartMode,
	chrComIfOpticsOchSTransmitterRestartAction TruthValue,
	chrComIfOpticsOchSTransmitterActivationStatus OCHLaserState,
	chrComIfOpticsAlarmVector		Unsigned32	(0..4294967295),
	chrComIfOpticsAlarmSeverityProfileIndex Unsigned32	(0..4294967295)
}

chrComIfOpticsInterfaceRate 	OBJECT-TYPE
	SYNTAX		InterfaceRate
	MAX-ACCESS 	read-only
	STATUS 		current
	DESCRIPTION
	""
	::= { chrComIfOpticsOCHEntry  1 }

chrComIfOpticsOchRPower 	OBJECT-TYPE
	SYNTAX		Integer32	(-501..300)
	MAX-ACCESS 	read-only
	STATUS 		current
	DESCRIPTION
	"Monitored Optical Power on OCM Receiver input."
	::= { chrComIfOpticsOCHEntry  2 }

chrComIfOpticsOchSPower 	OBJECT-TYPE
	SYNTAX		Integer32	(-501..300)
	MAX-ACCESS 	read-only
	STATUS 		current
	DESCRIPTION
	"Monitored Optical Power on OCM Transmitter output"
	::= { chrComIfOpticsOCHEntry  3 }

chrComIfOpticsOchSActualPowerControlMode 	OBJECT-TYPE
	SYNTAX		Oc48ControlType
	MAX-ACCESS 	read-write
	STATUS 		current
	DESCRIPTION
	"Shows the actual power control mode of the transmitter."
	::= { chrComIfOpticsOCHEntry  4 }

chrComIfOpticsOchSExpectedPower 	OBJECT-TYPE
	SYNTAX		Integer32	(-101..100)
	MAX-ACCESS 	read-write
	STATUS 		current
	DESCRIPTION
	""
	::= { chrComIfOpticsOCHEntry  5 }

chrComIfOpticsOchSRangeOfAllowablePwrMin 	OBJECT-TYPE
	SYNTAX		Integer32	(-101..100)
	MAX-ACCESS 	read-only
	STATUS 		current
	DESCRIPTION
	"The value of the output power as controlled by the user for the Chromatis Direct Modulation Transmitter (DMT) or EA Modulation Transmitter (EAT)."
	::= { chrComIfOpticsOCHEntry  6 }

chrComIfOpticsOchSRangeOfAllowablePwrMax 	OBJECT-TYPE
	SYNTAX		Integer32	(-101..100)
	MAX-ACCESS 	read-only
	STATUS 		current
	DESCRIPTION
	"The maximum power a user may enter as OCH-S  Expected Power."
	::= { chrComIfOpticsOCHEntry  7 }

chrComIfOpticsOchRParamForRxLambdaLOOCThr 	OBJECT-TYPE
	SYNTAX		Integer32	(-500..301)
	MAX-ACCESS 	read-write
	STATUS 		current
	DESCRIPTION
	"Input parameter for calculating OCH-R Received lambda LOOC threshold.

"
	::= { chrComIfOpticsOCHEntry  8 }

chrComIfOpticsOchRNumOfPrecedingOPAs 	OBJECT-TYPE
	SYNTAX		Integer32	(-1..32)
	MAX-ACCESS 	read-write
	STATUS 		current
	DESCRIPTION
	"Number of OPAs prior to the respective Module."
	::= { chrComIfOpticsOCHEntry  9 }

chrComIfOpticsOchRRxLambdaLOOCThr 	OBJECT-TYPE
	SYNTAX		Integer32	(-501..300)
	MAX-ACCESS 	read-only
	STATUS 		current
	DESCRIPTION
	"This threshold is applied on OCH-R  Power of the lambda channels (only) and indicates weather the optical power reaching the receiver contains an optical signal.


"
	::= { chrComIfOpticsOCHEntry  10 }

chrComIfOpticsOchRRx1310LOOCThr 	OBJECT-TYPE
	SYNTAX		Integer32	(-501..300)
	MAX-ACCESS 	read-write
	STATUS 		current
	DESCRIPTION
	"This threshold is applied on OCH-R  Power of the 1310 channel (only) and indicates the minimum received power for proper BER operation.



"
	::= { chrComIfOpticsOCHEntry  11 }

chrComIfOpticsOchRReceiverOverloadThr 	OBJECT-TYPE
	SYNTAX		Integer32	(-501..300)
	MAX-ACCESS 	read-only
	STATUS 		current
	DESCRIPTION
	"This threshold is applied on OCH-R  Power and indicates the maximum received power for proper BER operation."
	::= { chrComIfOpticsOCHEntry  12 }

chrComIfOpticsOchRReceiverDamageThr 	OBJECT-TYPE
	SYNTAX		Integer32	(-501..300)
	MAX-ACCESS 	read-only
	STATUS 		current
	DESCRIPTION
	"This threshold is applied on OCH-R  Power and indicates the maximum received power before damaging the corresponding transmitter."
	::= { chrComIfOpticsOCHEntry  13 }

chrComIfOpticsOchSLOOCThr 	OBJECT-TYPE
	SYNTAX		Integer32	(-501..300)
	MAX-ACCESS 	read-write
	STATUS 		current
	DESCRIPTION
	"This threshold is applied on OCH-S Power and indicates that the transmitter is active.



"
	::= { chrComIfOpticsOCHEntry  14 }

chrComIfOpticsOchSLaserBiasCurrent 	OBJECT-TYPE
	SYNTAX		Integer32	(-1..4000)
	MAX-ACCESS 	read-only
	STATUS 		current
	DESCRIPTION
	""
	::= { chrComIfOpticsOCHEntry  15 }

chrComIfOpticsOchSLaserTemperature 	OBJECT-TYPE
	SYNTAX		Integer32	(-1..500)
	MAX-ACCESS 	read-only
	STATUS 		current
	DESCRIPTION
	""
	::= { chrComIfOpticsOCHEntry  16 }

chrComIfOpticsOchSTransmitterMode 	OBJECT-TYPE
	SYNTAX		RestartMode
	MAX-ACCESS 	read-write
	STATUS 		current
	DESCRIPTION
	""
	::= { chrComIfOpticsOCHEntry  17 }

chrComIfOpticsOchSTransmitterRestartAction 	OBJECT-TYPE
	SYNTAX		TruthValue
	MAX-ACCESS 	read-write
	STATUS 		current
	DESCRIPTION
	""
	::= { chrComIfOpticsOCHEntry  18 }

chrComIfOpticsOchSTransmitterActivationStatus 	OBJECT-TYPE
	SYNTAX		OCHLaserState
	MAX-ACCESS 	read-only
	STATUS 		current
	DESCRIPTION
	""
	::= { chrComIfOpticsOCHEntry  19 }

chrComIfOpticsAlarmVector 	OBJECT-TYPE
	SYNTAX		Unsigned32	(0..4294967295)
	MAX-ACCESS 	read-only
	STATUS 		current
	DESCRIPTION
	""
	::= { chrComIfOpticsOCHEntry  20 }

chrComIfOpticsAlarmSeverityProfileIndex 	OBJECT-TYPE
	SYNTAX		Unsigned32	(0..4294967295)
	MAX-ACCESS 	read-write
	STATUS 		current
	DESCRIPTION
	""
	::= { chrComIfOpticsOCHEntry  21 }


END
