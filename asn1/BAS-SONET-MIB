BAS-SONET-MIB DEFINITIONS ::= BEGIN

IMPORTS
	MODULE-IDENTITY, 
	OBJECT-TYPE, 
	Counter32, 
	Integer32	
		FROM SNMPv2-SMI
	ifIndex		
		FROM IF-MIB
	TimeStamp,	
	TEXTUAL-CONVENTION
		FROM SNMPv2-TC
        OBJECT-GROUP,
        MODULE-COMPLIANCE
                FROM SNMPv2-CONF
	basSonet 
		FROM BAS-MIB;

          
basSonetMib MODULE-IDENTITY
	LAST-UPDATED "9810071415Z"
	ORGANIZATION "Broadband Access Systems"
	CONTACT-INFO
		" Tech Support
		  Broadband Access Systems
		  4 Technology Drive
		  Westborough, MA  01581
		  U.S.A.
		  
		  508-366-8833
		  support@basystems.com"
	DESCRIPTION
		"This MIB module defines the configuration and 
		 status MIB objects for a Broadband Access System 
		 SONET interface."
	::= { basSonet 1 }


basSonetObjects	       	OBJECT IDENTIFIER ::= { basSonetMib 1 }


--
-- Bas SONET Table
--
basSonetPathTable   OBJECT-TYPE
	SYNTAX	      SEQUENCE OF BasSonetPathEntry
        MAX-ACCESS    not-accessible
        STATUS	      current
        DESCRIPTION
		"A table containing SONET Path specific variables
		for this POS implementation."
	::= { basSonetObjects 1}

basSonetPathEntry   OBJECT-TYPE
	SYNTAX	      BasSonetPathEntry
	MAX-ACCESS    not-accessible
	STATUS	      current
	DESCRIPTION
		"Management information about a particular POS
		Link."
	INDEX     { ifIndex }
	::= { basSonetPathTable 1 }

BasSonetPathEntry ::= SEQUENCE {
		 basSonetPathB3Err	     Counter32,
		 basSonetPathG1Err	     Counter32,
		 basSonetPathPais	     Counter32,
		 basSonetPathPrdi	     Counter32,
		 basSonetPathPlop	     Counter32,
		 basSonetPathB3Threshold     Integer32,
		 basSonetPathRxJ1	     Integer32,
		 basSonetPathRxC2	     Integer32,
		 basSonetPathRxG1	     Integer32
		 }

basSonetPathB3Err   OBJECT-TYPE
	SYNTAX	   Counter32
	MAX-ACCESS read-only
	STATUS	   current
	DESCRIPTION
	    "The number of packets received on this link
	    with B3 bit errors. Bit Interleaved Parity 8 is 
	    calculated over all bits in the SPE of each frame."
	    ::= { basSonetPathEntry 1 }

basSonetPathG1Err   OBJECT-TYPE
	SYNTAX	   Counter32
	MAX-ACCESS read-only
	STATUS	   current
	DESCRIPTION
	    "The number of B3 errors that were detected by 
	    the remote terminal in its received signal. "
	::= { basSonetPathEntry 2 }

basSonetPathPais    OBJECT-TYPE
	SYNTAX     Counter32
	MAX-ACCESS read-only
	STATUS	   current
	DESCRIPTION
	    "The number of times a Path Alarm Indication Signal
	    has been detected.  A PAIS occurs if all the H1/H2 
	    pointer bytes in the received SONET frame are 01."
	::= { basSonetPathEntry 3}

basSonetPathPrdi    OBJECT-TYPE
	SYNTAX     Counter32
	MAX-ACCESS read-only
	STATUS	   current
	DESCRIPTION
	    "The number of times a Path Remote Defect Indication
	    has been detected.   A PRDI occurs if bits 5,6 and 7 of
	    the G1 byte received with the same value for 5
	    onsecutive frames."
	::= { basSonetPathEntry 4}

basSonetPathPlop    OBJECT-TYPE
	SYNTAX     Counter32
	MAX-ACCESS read-only
	STATUS	   current
	DESCRIPTION
	    "The number of times a Path Loss of Pointer has been 
	    detected.  A PLOP occurs if all the H1/H2 pointer 
	    bytes in the received SONET frame are not all 01
	    indicating PRDI or the first pair equals 00 and all 
	    other pairs equaling 11 indicating normal operation."
	::= { basSonetPathEntry 5}

basSonetPathB3Threshold   OBJECT-TYPE
	SYNTAX		 Integer32(3..9)
	MAX-ACCESS       read-write
	STATUS		 current 
	DESCRIPTION
	    "The number of packets received with B3 errors hits
	    this threshold issue an alarm." 
	DEFVAL     { 6 }
	::= { basSonetPathEntry 6}

basSonetPathRxJ1   OBJECT-TYPE
	SYNTAX     Integer32
	MAX-ACCESS read-only
	STATUS     current 
	DESCRIPTION
	    "The first J1 byte received in last packet." 
	::= { basSonetPathEntry 7}

basSonetPathRxC2	OBJECT-TYPE
	SYNTAX		Integer32
	MAX-ACCESS	read-only
	STATUS		current 
	DESCRIPTION
	    "C2 byte received in last packet." 
	::= { basSonetPathEntry 8}

basSonetPathRxG1	   OBJECT-TYPE
	SYNTAX		   Integer32
	MAX-ACCESS	   read-only
	STATUS		   current 
	DESCRIPTION
	    "G1 byte received in last packet." 
	::= { basSonetPathEntry 9}

basSonetLineTable   OBJECT-TYPE
	SYNTAX	      SEQUENCE OF BasSonetLineEntry
        MAX-ACCESS    not-accessible
        STATUS	      current
        DESCRIPTION
		"A table containing SONET Line specific variables
		for this POS implementation."
	::= { basSonetObjects 2 }

basSonetLineEntry   OBJECT-TYPE
	SYNTAX	      BasSonetLineEntry
	MAX-ACCESS    not-accessible
	STATUS	      current
	DESCRIPTION
		"Management information about a particular POS
		Link."
	INDEX     {ifIndex}
	::= { basSonetLineTable 1 }

BasSonetLineEntry ::= SEQUENCE {
		 basSonetLineTxErr	     Counter32,
		 basSonetLineB1Err	     Counter32,
		 basSonetLineB2Err	     Counter32,
		 basSonetLineM1Err	     Counter32, 
		 basSonetLineRxFifoOverflow  Counter32,
		 basSonetLineRxAbort	     Counter32,
		 basSonetLineRxRunts	     Counter32,
		 basSonetLineLoc	     Counter32,
		 basSonetLineLof	     Counter32,
		 basSonetLineLos	     Counter32,
		 basSonetLineLais	     Counter32,
		 basSonetLineLrdi	     Counter32,
		 basSonetLineB1Threshold     Integer32,
		 basSonetLineB2Threshold     Integer32,
		 basSonetLineSFThreshold     Integer32,
		 basSonetLineSDThreshold     Integer32,
		 basSonetLineLastCleared     TimeStamp,
		 basSonetLineRxK1	     Integer32,	     
		 basSonetLineRxK2	     Integer32,
		 basSonetLineRxGiants	     Counter32
		 }

basSonetLineTxErr   OBJECT-TYPE
	SYNTAX	   Counter32
	MAX-ACCESS read-only
	STATUS	   current
	DESCRIPTION
	    "The sum of all transmit errors that caused the 
	    packet to not be transmitted.  These errors 
	    consist of tx fifo error, link layer errors, 
	    minimum packet size violations, maximum 
	    packet size violations and tx parity errors."
	::= { basSonetLineEntry 1}

basSonetLineB1Err   OBJECT-TYPE
	SYNTAX	   Counter32
	MAX-ACCESS read-only
	STATUS	   current
	DESCRIPTION
	    "The number of packets received on this link
	    with B1 bit errors.  Bit Interleaved Parity 8 is 
	    calculated over all bytes of each frame. "
	::= { basSonetLineEntry 2}

basSonetLineB2Err   OBJECT-TYPE
	SYNTAX	   Counter32
	MAX-ACCESS read-only
	STATUS	   current
	DESCRIPTION
	    "The number of packets received on this link
	    with B2 bit errors.  Bit Interleaved Parity 8 is 
	    calculated over all bytes of each frame except
	    for the first three rows of the TOH "
	::= { basSonetLineEntry 3}

basSonetLineM1Err   OBJECT-TYPE
	SYNTAX	   Counter32
	MAX-ACCESS read-only
	STATUS	   current
	DESCRIPTION
	    "The number of B2 errors that were detected by 
	    the remote terminal in its received signal."
	::= { basSonetLineEntry 4}

basSonetLineRxFifoOverflow   OBJECT-TYPE
	SYNTAX		    Counter32
	MAX-ACCESS	    read-only
	STATUS		    current
	DESCRIPTION
	    "The number of packets received on this link
	    with an error detected in the receive fifo."
	::= { basSonetLineEntry 5}

basSonetLineRxAbort   OBJECT-TYPE
	SYNTAX	   Counter32
	MAX-ACCESS read-only
	STATUS	   current
	DESCRIPTION
	    "The number of packets received on this link
	    in which the abort sequence is detected."
	::= { basSonetLineEntry  6}

basSonetLineRxRunts   OBJECT-TYPE
	SYNTAX	   Counter32
	MAX-ACCESS read-only
	STATUS	   current
	DESCRIPTION
	    "The number of packets received on this link
	    which are smaller than the minimum packet size."
	::= { basSonetLineEntry 7}

basSonetLineLoc	   OBJECT-TYPE
	SYNTAX	   Counter32
	MAX-ACCESS read-only
	STATUS	   current
	DESCRIPTION
	    "The number of times a loss of clock has been
	    detected.  LOC occurs if no transitions are
	    detected on the receive SONET clock for 16 
	    periods of the transmit clock.."
	::= { basSonetLineEntry 8}

basSonetLineLof     OBJECT-TYPE
	SYNTAX	   Counter32
	MAX-ACCESS read-only
	STATUS	   current
	DESCRIPTION
	    "The number of times a loss of frame has been
	    detected.  LOF occurs if RX_OOF (out-of-frame) 
	    is active continuously for 24 consecutive frames 
	    (3 ms)."
        ::= { basSonetLineEntry 9}

basSonetLineLos     OBJECT-TYPE
	SYNTAX     Counter32
	MAX-ACCESS read-only
	STATUS	   current
	DESCRIPTION
	    "The number of times a loss of signal has been 
	    detected.  A LOS indicates to the framer that there 
	    is no signal present from the optical receiver."
	::= { basSonetLineEntry  10}

basSonetLineLais    OBJECT-TYPE
	SYNTAX     Counter32
	MAX-ACCESS read-only
	STATUS	   current
	DESCRIPTION
	    "The number of times a Line Alarm Indication Signal
	    has been detected.  A LAIS occurs if the 3 LSBs of K2
	    are received as '111' for 5 consecutive frames"
	::= { basSonetLineEntry 11}

basSonetLineLrdi    OBJECT-TYPE
	SYNTAX     Counter32
	MAX-ACCESS read-only
	STATUS	   current
	DESCRIPTION
	    "The number of times a Line Remote Defect Indication
	    has been detected.  A LRDI occurs if the 3 LSBs of K2
	    are not received as '110' for 5 consecutive frames."
	::= { basSonetLineEntry 12}

basSonetLineB1Threshold   OBJECT-TYPE
	SYNTAX		 Integer32(3..9)
	MAX-ACCESS       read-write
	STATUS		 current 
	DESCRIPTION
	    "The number of packets received with B1 errors hits
	    this threshold issue an alarm."
	DEFVAL     { 6 }
	::= { basSonetLineEntry 13}

basSonetLineB2Threshold   OBJECT-TYPE
	SYNTAX		 Integer32(3..9)
	MAX-ACCESS       read-write
	STATUS		 current 
	DESCRIPTION
	    "The number of packets received with B2 errors hits
	    this threshold issue an alarm."
	DEFVAL     { 6 }
	::= { basSonetLineEntry 14}

basSonetLineSFThreshold   OBJECT-TYPE
	SYNTAX		 Integer32(3..9)
	MAX-ACCESS       read-write
	STATUS		 current 
	DESCRIPTION
	    "The number of packets received with B2 errors hits
	    this threshold issue a signal fail alarm." 
	DEFVAL     { 3 }
	::= { basSonetLineEntry 15}

basSonetLineSDThreshold   OBJECT-TYPE
	SYNTAX		 Integer32(3..9)
	MAX-ACCESS       read-write
	STATUS		  current 
	DESCRIPTION
	    "The number of packets received with B2 errors hits
	    this threshold issue a signal degrade alarm." 
	DEFVAL     { 6 }
	::= { basSonetLineEntry 16}

basSonetLineLastCleared   OBJECT-TYPE
	SYNTAX	       TimeStamp
	MAX-ACCESS     read-only
	STATUS	       current
	DESCRIPTION
	    "The value of sysUpTime when these Counter32s were 
	    last cleared."
	::= { basSonetLineEntry  17}

basSonetLineRxK1    OBJECT-TYPE
	SYNTAX	   Integer32
	MAX-ACCESS read-only
	STATUS	   current 
	DESCRIPTION
	    "K1 byte received in last packet." 
	::= { basSonetLineEntry 18}

basSonetLineRxK2    OBJECT-TYPE
	SYNTAX     Integer32
	MAX-ACCESS read-only
	STATUS     current 
	DESCRIPTION
	    "K2 byte received in last packet." 
	::= { basSonetLineEntry 19}

basSonetLineRxGiants   OBJECT-TYPE
	SYNTAX	   Counter32
	MAX-ACCESS read-only
	STATUS	   current
	DESCRIPTION
	    "The number of packets received on this link
	    which are larger than the maximum packet size."
	::= { basSonetLineEntry 20}

END
