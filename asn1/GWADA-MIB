-- GWADA MIB
-- Novell GroupWise Admin Agent Management Information Base (MIB)
-- Copyright (C) 1994, 1995, 1996, 1997 Novell Inc.,  All Rights Reserved
-- Naming Tree: 1.3.6.1.4.1.922
--      iso(1) org(3) dod(6) internet(1) private(4) enterprises(1) novell(23)
-- Date: January 15, 1997
-- added platform and version variables
-- table structure and moved traps into their enterprise
-- changed from wpcorp (922) to novell (23)

GWADA-MIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

novell         OBJECT IDENTIFIER   ::= { enterprises 23 }
mibDoc         OBJECT IDENTIFIER   ::= { novell       2 }
gwada          OBJECT IDENTIFIER   ::= { mibDoc      39 }
ada            OBJECT IDENTIFIER   ::= { gwada        1 }
adaTrapInfo    OBJECT IDENTIFIER   ::= { gwada        2 }
adaTraps       OBJECT IDENTIFIER   ::= { gwada        3 }


-- ====================================== ADA Get/Set Variables =========
adaTable OBJECT-TYPE
	SYNTAX SEQUENCE OF ADAEntry
	ACCESS not-accessible
	STATUS mandatory
	DESCRIPTION "A table of ADA objects"
	::= { ada 1 }

adaEntry OBJECT-TYPE
	SYNTAX ADAEntry
	ACCESS not-accessible
	STATUS mandatory
	DESCRIPTION "An entry in the ADA Table"
	INDEX  { adaIndex }
	::= { adaTable 1 }
	
ADAEntry ::=
	SEQUENCE {
			adaIndex             INTEGER,
			adaName              DisplayString,
			adaOperationMode     INTEGER,
			adaTotalPostOffices  Gauge,					
			adaClosedPostOffices Gauge,
			adaCompletedMsgs     Counter,
			adaErrorMsgs         Counter,
			adaUptime            TimeTicks,
			adaCurrentLogFile    DisplayString,
			adaLogLevel          INTEGER,
			adaFileLogging       INTEGER,
			adaMaxLogFileAge     INTEGER,
			adaMaxLogDiskSpace   INTEGER,
			adaRestart			 INTEGER,
			adaGUID	 			 DisplayString,
			adaOS           	 DisplayString,
			adaVersion		     DisplayString

			}

adaIndex OBJECT-TYPE
       SYNTAX  INTEGER
       ACCESS  read-write
       STATUS  mandatory
       DESCRIPTION
       "Index into the ADA table"
   ::= { adaEntry 1 }

adaName OBJECT-TYPE
       SYNTAX  DisplayString (SIZE (0..255))
       ACCESS  read-only
       STATUS  mandatory
       DESCRIPTION
       "The facility for which this Administration Agent operates."
   ::= { adaEntry 2 }

adaOperationMode OBJECT-TYPE
       SYNTAX  INTEGER { normal(1), domain(2), postOffice(3) }
       ACCESS  read-write
       STATUS  mandatory
       DESCRIPTION
      "The Operation Mode of this Administration Agent: 
      			Normal, Domain, or Post Office"
   ::= { adaEntry 3 }

adaTotalPostOffices OBJECT-TYPE
       SYNTAX  Gauge
       ACCESS  read-only
       STATUS  mandatory
       DESCRIPTION
      "The number of Post Offices serviced by this agent."
   ::= { adaEntry 4 }

adaClosedPostOffices OBJECT-TYPE
       SYNTAX  Gauge
       ACCESS  read-only
       STATUS  mandatory
       DESCRIPTION
      "The number of closed Post Offices serviced by this agent."
   ::= { adaEntry 5 }

adaCompletedMsgs OBJECT-TYPE
       SYNTAX  Counter
       ACCESS  read-only
       STATUS  mandatory
       DESCRIPTION
      "The number of completed messages."
   ::= { adaEntry 6 }

adaErrorMsgs OBJECT-TYPE
       SYNTAX  Counter
       ACCESS  read-only
       STATUS  mandatory
       DESCRIPTION
      "The number of error messages."
   ::= { adaEntry 7 }

adaUptime OBJECT-TYPE
       SYNTAX  TimeTicks
       ACCESS  read-only
       STATUS  mandatory
       DESCRIPTION
      "Uptime of this Administration Agent."
   ::= { adaEntry 8 }

adaCurrentLogFile OBJECT-TYPE
       SYNTAX  DisplayString (SIZE (0..255))
       ACCESS  read-only
       STATUS  mandatory
       DESCRIPTION
      "Current log file."
   ::= { adaEntry 9 }

adaLogLevel OBJECT-TYPE
       SYNTAX  INTEGER { normal(1), verbose(2) }
       ACCESS  read-write
       STATUS  mandatory
       DESCRIPTION
      "Administration Agent log level: Normal or Verbose"
   ::= { adaEntry 10 }
   
adaFileLogging OBJECT-TYPE
       SYNTAX  INTEGER { no(0), yes(1) }
       ACCESS  read-write
       STATUS  mandatory
       DESCRIPTION
      "Administration Agent disk logging: YES or NO"
   ::= { adaEntry 11 }

adaMaxLogFileAge OBJECT-TYPE
       SYNTAX  INTEGER
       ACCESS  read-write
       STATUS  mandatory
       DESCRIPTION
      "Maximum age for Administration Agent log files."
   ::= { adaEntry 12 }

adaMaxLogDiskSpace OBJECT-TYPE
       SYNTAX  INTEGER
       ACCESS  read-write
       STATUS  mandatory
       DESCRIPTION
      "Maximum disk space for Administration Agent log files."
   ::= { adaEntry 13 }

adaRestart OBJECT-TYPE
       SYNTAX  INTEGER { no(0), yes(1) }
       ACCESS  read-write
       STATUS  mandatory
      DESCRIPTION
      "Administration Agent Restart: Yes or No."
   ::= { adaEntry 14 }

adaGUID OBJECT-TYPE
       SYNTAX  DisplayString (SIZE (0..36))
       ACCESS  read-only
       STATUS  mandatory
       DESCRIPTION
      "Administration Agent globally unique identifier."
   ::= { adaEntry 15 }

adaOS OBJECT-TYPE
       SYNTAX  DisplayString (SIZE (0..64))
       ACCESS  read-only
       STATUS  mandatory
       DESCRIPTION
       "Operating System name and version"
   ::= { adaEntry 16 }

adaVersion OBJECT-TYPE
       SYNTAX  DisplayString (SIZE (0..64))
       ACCESS  read-only
       STATUS  mandatory
       DESCRIPTION
       "Version and date this agent."
   ::= { adaEntry 17 }


-- ================================================== adaTrapInfo ========= 
-- The adaTrapInfo group  
-- These objects are used only in traps produced by ADA

adaTrapTime OBJECT-TYPE
		SYNTAX  INTEGER
		ACCESS  not-accessible
		STATUS  mandatory
		DESCRIPTION "The time the trap occurred. Seconds since Jan 1, 1970 (GMT)"
	::= { adaTrapInfo 1 }

adaFacilityName OBJECT-TYPE
       SYNTAX  DisplayString (SIZE (0..255))
       ACCESS  not-accessible
       STATUS  mandatory
       DESCRIPTION "A Domain or Post Office name."
   ::= { adaTrapInfo 2 }

adaFacilityLink OBJECT-TYPE
       SYNTAX  DisplayString (SIZE (0..255))
       ACCESS  not-accessible
       STATUS  mandatory
       DESCRIPTION "A Domain or Post Office link."
   ::= { adaTrapInfo 3 }

adaRecoveredDB OBJECT-TYPE
       SYNTAX  DisplayString (SIZE (0..255))
       ACCESS  not-accessible
       STATUS  mandatory
       DESCRIPTION "The Admin database that was recovered."
   ::= { adaTrapInfo 4 }

-- ================================================== ADA Traps ========= 
   
adaStartTrap TRAP-TYPE
		ENTERPRISE    adaTraps
		VARIABLES     {adaTrapTime, adaName, adaGUID}
		DESCRIPTION   "GroupWise Administration Agent start."
		--ManageWise Trap annotation
		--#TYPE       "ADA has started."
		--#SUMMARY    "GroupWise Administration Agent at %s has started."
		--#ARGUMENTS  { 1 }
		--#SEVERITY   INFORMATIONAL
		--#TIMEINDEX  0
		--#HELP       "GWALARM.HLP"
		--#HELPTAG    101		
		--#STATE      OPERATIONAL
		::= 1

adaShutdownTrap TRAP-TYPE
		ENTERPRISE    adaTraps
		VARIABLES     {adaTrapTime, adaName, adaGUID}
		DESCRIPTION   "GroupWise Administration Agent has shut down."
		--ManageWise Trap annotation
		--#TYPE       "ADA has shut down."
		--#SUMMARY    "GroupWise Administration Agent for %s has shut down."
		--#ARGUMENTS  { 1 }
		--#SEVERITY   CRITICAL
		--#TIMEINDEX  0
		--#HELP       "GWALARM.HLP"
		--#HELPTAG    102		
		--#STATE      NONOPERATIONAL
		::= 2

adaFacilityBlockedTrap TRAP-TYPE
		ENTERPRISE    adaTraps
		VARIABLES     {adaTrapTime, adaFacilityLink, adaFacilityName, adaGUID}
		DESCRIPTION   "GWADA: a link to a facility's database is closed."
		--ManageWise Trap annotation
		--#TYPE       "A facility link changed from open to closed."
		--#SUMMARY    "GWADA: the link %s to facility %s is closed."
		--#ARGUMENTS  { 1, 2 }
		--#SEVERITY   CRITICAL
		--#TIMEINDEX  0
		--#HELP       "GWALARM.HLP"
		--#HELPTAG    103		
		--#STATE      NONOPERATIONAL
		::= 3

adaFacilityOpenTrap TRAP-TYPE
		ENTERPRISE    adaTraps
		VARIABLES     { adaTrapTime, adaFacilityLink, adaFacilityName, adaGUID }
		DESCRIPTION   "GWADA: a link a Post Office database is open."
		--ManageWise Trap annotation
		--#TYPE       "A facility link changed from closed to open."
		--#SUMMARY    "GWADA: the link %s to facility %s is open again."
		--#ARGUMENTS  { 1, 2 }
		--#SEVERITY   CRITICAL
		--#TIMEINDEX  0
		--#HELP       "GWALARM.HLP"
		--#HELPTAG    104		
		--#STATE      OPERATIONAL
		::= 4

adaDBRecoverOkay TRAP-TYPE
		ENTERPRISE    adaTraps
		VARIABLES     { adaTrapTime,  adaRecoveredDB, adaGUID }
		DESCRIPTION   "GWADA: an Admin database recovery has completed."
		--ManageWise Trap annotation
		--#TYPE       "An Admin database recovery completed."
		--#SUMMARY    "GWADA: the recovery process for the Admin database at %s has completed."
		--#ARGUMENTS  { 1 }
		--#SEVERITY   INFORMATIONAL
		--#TIMEINDEX  0
		--#HELP       "GWALARM.HLP"
		--#HELPTAG    105
		--#STATE      OPERATIONAL
		::= 5

adaDBRecoverError TRAP-TYPE
		ENTERPRISE    adaTraps
		VARIABLES     { adaTrapTime, adaRecoveredDB, adaGUID }
		DESCRIPTION   "GWADA: An Admin database recovery has failed."
		--ManageWise Trap annotation
		--#TYPE       "An Admin database recovery failed."
		--#SUMMARY    "GWADA: the recovery process for the Admin database at %s has failed."
		--#ARGUMENTS  { 1 }
		--#SEVERITY   CRITICAL
		--#TIMEINDEX  0
		--#HELP       "GWALARM.HLP"
		--#HELPTAG    106
		--#STATE      NONOPERATIONAL
		::= 6

adaDBRecoverWarn TRAP-TYPE
		ENTERPRISE    adaTraps
		VARIABLES     { adaTrapTime, adaRecoveredDB, adaGUID }
		DESCRIPTION   "GWADA: WARNING - Data loss occured during an Admin Database recovery."
		--ManageWise Trap annotation
		--#TYPE       "Data Loss occured during DB recovery."
		--#SUMMARY    "GWADA: WARNING - Data loss occured during the recovery process for the Admin database at %s."
		--#ARGUMENTS  { 1 }
		--#SEVERITY   CRITICAL
		--#TIMEINDEX  0
		--#HELP       "GWALARM.HLP"
		--#HELPTAG    107
		--#STATE      OPERATIONAL
		::= 7

adaRestartTrap TRAP-TYPE
		ENTERPRISE    adaTraps
		VARIABLES     { adaTrapTime, adaFacilityName, adaGUID }
		DESCRIPTION   "GroupWise Administration Agent restart initiated."
		--ManageWise Trap annotation
		--#TYPE       "GroupWise Administration Agent restart initiated."
		--#SUMMARY    "GroupWise Administration Agent %s was restarted."
		--#ARGUMENTS  { 1 }
		--#SEVERITY   CRITICAL
		--#TIMEINDEX  0
		--#HELP       "GWALARM.HLP"
		--#HELPTAG    108		
		--#STATE      OPERATIONAL
		::= 8


END
