FLOWPOINT-MIB DEFINITIONS ::= BEGIN

        IMPORTS
                  NetworkAddress, IpAddress, Counter, Gauge, enterprises
                          FROM RFC1155-SMI
                  DisplayString
                          FROM RFC1213-MIB
                  OBJECT-TYPE
                          FROM RFC-1212;

        --  This MIB module uses the extended OBJECT-TYPE macro as
        --  defined in [14];


        -- FlowPoint enterprise MIB

        flowpoint       OBJECT IDENTIFIER ::= { enterprises 1548 }


        --
        -- groups in FlowPoint enterprise MIB
        --

        fpdod           OBJECT IDENTIFIER ::= { flowpoint 1 }

        fpether         OBJECT IDENTIFIER ::= { flowpoint 2 }

        fpisdn          OBJECT IDENTIFIER ::= { flowpoint 3 }

        fpsys           OBJECT IDENTIFIER ::= { flowpoint 4 }

        fplogin         OBJECT IDENTIFIER ::= { flowpoint 5 }

        fpWan           OBJECT IDENTIFIER ::= { flowpoint 6 }

        fppots          OBJECT IDENTIFIER ::= { flowpoint 7 }

        fpdownload      OBJECT IDENTIFIER ::= { flowpoint 8 }

        fpiptranslate   OBJECT IDENTIFIER ::= { flowpoint 9 }

        fpdhcp          OBJECT IDENTIFIER ::= { flowpoint 10 }

        fpdir          OBJECT IDENTIFIER ::= { flowpoint 11 }

        fpatm          OBJECT IDENTIFIER ::= { flowpoint 12 }

        fpfr           OBJECT IDENTIFIER ::= { flowpoint 13 }

        --
        -- The dod (Dialup On Demand) group SYNTAX definition
        --

        IpxNetAddress   ::= OCTET STRING (SIZE (4))
        MacAddress      ::= OCTET STRING (SIZE (6)) 
        ConnectionType  ::= INTEGER { async(1), isdn(2), fr(3), dds(4), x25(5) }
        AuthenProtoType ::= INTEGER { none(1), pap(2), chap(3) }
        RowStatus       ::= INTEGER { active(1),        -- r/s enabled
                                      notInService(2),  -- r/s disabled
                                      notReady(3),      -- r   missing info
                                      createAndGo(4),   --   s create/disabled 
                                      createAndWait(5), --   s create/enabled
                                      destroy(6)        --   s delete entry
                                    }
        DhcpOptionType  ::= INTEGER { none(1),      -- No value for option
                                      byte(2),      -- Values is bytes
                                      word(3),      -- Values is words
                                      long(4),      -- Values is signed long
                                      longint(5),   -- Values is unsigned long
                                      binary(6),    -- Value is binary 0 or 1
                                      ipaddress(7), -- Values is IP addresses
                                      string(8)     -- Value is a string
                                    }


        --  The dod basic configuration table
        --
        --  This group provides the basic configuration for Dial On Demand.
        --  The table is based on destination name as index.
        --

        dodTable OBJECT-TYPE
            SYNTAX  SEQUENCE OF DodEntry
            ACCESS  not-accessible
            STATUS  mandatory
            DESCRIPTION
                    "The DOD basic configuration table for each remote
                    connection.  All of the DOD tables are indexed
                    (identified) by DestinationName. "
            ::= { fpdod 1 }

        dodEntry OBJECT-TYPE
            SYNTAX  DodEntry
            ACCESS  not-accessible
            STATUS  mandatory
            DESCRIPTION
                    ""
            INDEX { dodDestinationName }
            ::= { dodTable 1}

        DodEntry ::=
            SEQUENCE {
                        dodTableID
                                INTEGER,
                        dodDestinationName
                                DisplayString (SIZE (0..20)),
                        dodPassword
                                DisplayString (SIZE (0..40)),
                        dodAuthenProtocol
                                AuthenProtoType,
                        dodMaxLinks
                                INTEGER,
                        dodBWThreshold
                                INTEGER,
                        dodPreferType
                                ConnectionType,
                        dodTearDownTimer
                                INTEGER,
                        dodSourceIPAddress
                                IpAddress,
                        dodRemoteIPAddress
                                IpAddress,
                        dodSourceIPMask
                                IpAddress,
                        dodRemoteIPMask
                                IpAddress,
                        dodIPXNetAddress
                                IpxNetAddress,
                        dodIPFilters
                                Counter,
                        dodIPXFilters
                                Counter,
                        dodRemoteIPNets
                                Counter,
                        dodRemoteIPXNets
                                Counter,
                        dodRemoteIPXSAPs
                                Counter,
                        dodRemoteMacState
                                INTEGER,
                        dodRemoteMacs
                                Counter,
                        dodLastActivityTime
                                INTEGER,
                        dodTableOperation
                                INTEGER,
                        dodMinLinks
                                INTEGER,
                        dodBODType
                                INTEGER,
                        dodIpOptRecvRIP
                                INTEGER,
                        dodIpOptSendRIP
                                INTEGER,
                        dodIpOptRecvRIPDefault
                                INTEGER,
                        dodIpOptSendRIPDefault
                                INTEGER,
                        dodIpOptKeepPrivate
                                INTEGER,
                        dodBrOptUseStp
                                INTEGER,
                        dodPPPOptUseLCPEcho
                                INTEGER,
                        dodEntryIsDisabled
                                INTEGER,
                        dodCallbackOption
                                INTEGER,
                        dodSendDataAsVoice
                                INTEGER,
                        dodIPXNetStrAddress
                                DisplayString (SIZE(1..8)),
                        dodOurSystemName
                                DisplayString (SIZE (0..40)),
                        dodOurPassword
                                DisplayString (SIZE (0..40)),
                        dodPPPCallbackOption
                                INTEGER,
                        dodPPPCallbackInfo
                                DisplayString (SIZE(0..40)),
                        dodDontAuthenticate
                                INTEGER,
                        dodIPAddressTranslation
                                INTEGER,
                        dodIpOptRecvRIP1
                                INTEGER,
                        dodIpOptSendRIP1
                                INTEGER,
                        dodIpOptRecvRIP2
                                INTEGER,
                        dodIpOptSendRIP2
                                INTEGER,
                        dodProtocol
                                INTEGER,
                        dodCompression
                                INTEGER,
                        dodPasswordSpecified
                                INTEGER,
                        dodOurPasswordSpecified
                                INTEGER,
                        dodBlockNetBIOS
                                INTEGER,
                        dodMtu
                                INTEGER,
                        dodIpSlaveMode
                                INTEGER,
                        dodReacquireIpAddr
                                INTEGER,
                        dodIpxOptRIPSAP
                                 INTEGER
                        }

        dodTableID  OBJECT-TYPE
            SYNTAX  INTEGER
            ACCESS  read-only
            STATUS  obsolete
            DESCRIPTION
                    "The identifier number of this remote name.  Each dod
                    table will have a unique identifier number for it.
                    The ID number is issued when the dod table of the
                    destination name is created on the agent side.
                    This object is obsoleted: use dodDestinationName
                    as the index."
            ::= { dodEntry 1 }

        dodDestinationName  OBJECT-TYPE
            SYNTAX  DisplayString  (SIZE (0..20))
            ACCESS  read-only
            STATUS  mandatory
            DESCRIPTION
                    "A textual description of the remote destination.  The
                    name is given by the manager side when the manager uses
                    object dodTableOperation to create a new Dod record.
                    The dodDestination is important. It will be used
                    throughout all of the Dod database as index to
                    access each object. "
            ::= { dodEntry 2 }

        dodPassword OBJECT-TYPE
            SYNTAX  DisplayString (SIZE (0..40))
            ACCESS  read-write
            STATUS  mandatory
            DESCRIPTION
                    "The password for this remote connection.  It is used to
                    check the remote's password when the remote client or
                    server dials in. It is also used when authentication
                    is enabled during outgoing calls.  GENERR is returned
                    if not authorized to read the dodPassword."
            ::= { dodEntry 3 }

        dodAuthenProtocol OBJECT-TYPE
            SYNTAX  AuthenProtoType
            ACCESS  read-write
            STATUS  mandatory
            DESCRIPTION
                    "The minimum authentication protocol this remote
                    connection is using.  It is one of CHAP or PAP
                    or NONE.  The actual authentication phase can be
                    performed with a better protocol than specified here:
                    for instance if set to PAP and the remote supports
                    CHAP (as negotiated during the LCP phase), CHAP
                    authentication will be performed. None means that
                    authentication of this remote is disabled during
                    outgoing calls.  All incoming calls are ALWAYS
                    authenticated, so setting this to none prevents
                    from accepting incoming calls."
            ::= { dodEntry 4 }

        dodMaxLinks OBJECT-TYPE
            SYNTAX  INTEGER (1..2)
            ACCESS  read-write
            STATUS  mandatory
            DESCRIPTION
                    "The maximum number of links to be used when
                    the system dials out or accepts incoming calls.
                    Should be 1 or 2 for BRI lines."
            ::= { dodEntry 5 }

        dodBWThreshold OBJECT-TYPE
            SYNTAX  INTEGER (0..100)
            ACCESS  read-write
            STATUS  mandatory
            DESCRIPTION
                    "The threshold of bandwidth utilization of established
                    links used to trigger an additional call, expressed as
                    an integer percentage, i.e. 0 to 100.  0 means that
                    all available links are dialed at once while 100
                    means that no additional links are used.  The type
                    of bandwidth measured by this object is defined by
                    dodBODType."
            ::= { dodEntry 6 }

        dodPreferType OBJECT-TYPE
            SYNTAX  ConnectionType
            ACCESS  read-write
            STATUS  mandatory
            DESCRIPTION
                    "The preferred line connection type."
            ::= { dodEntry 7 }

        dodTearDownTimer OBJECT-TYPE
            SYNTAX  INTEGER
            ACCESS  read-write
            STATUS  mandatory
            DESCRIPTION
                    "The timeout limit to tear down the link when there is
                    no activity for the link, expressed in seconds. "
            ::= { dodEntry 8 }

        dodSourceIPAddress OBJECT-TYPE
            SYNTAX  IpAddress
            ACCESS  read-write
            STATUS  mandatory
            DESCRIPTION
                    "The local IP address of the WAN port.  It is used to
                    negotiate with the remote side when dialing in or out.
                    When nonzero, it overrides the default address,
                    coming from the LAN port IP address (ethernet). "
            ::= { dodEntry 9 }

        dodRemoteIPAddress OBJECT-TYPE
            SYNTAX  IpAddress
            ACCESS  read-write
            STATUS  mandatory
            DESCRIPTION
                    "The remote IP address of the WAN port, if needed.
                    Set to 0 otherwise. "
            ::= { dodEntry 10 }

        dodSourceIPMask OBJECT-TYPE
            SYNTAX  IpAddress
            ACCESS  read-write
            STATUS  mandatory
            DESCRIPTION
                    "The local IP net mask of the WAN port. It is used
                    with dodSourceIPAddress."
            ::= { dodEntry 11 }

        dodRemoteIPMask OBJECT-TYPE
            SYNTAX  IpAddress
            ACCESS  read-write
            STATUS  mandatory
            DESCRIPTION
                    "The remote side IP network mask. "
            ::= { dodEntry 12 }

        dodIPXNetAddress OBJECT-TYPE
            SYNTAX  IpxNetAddress
            ACCESS  read-write
            STATUS  mandatory
            DESCRIPTION
                    "The IPX network address associated with the WAN link
                    when connected to this remote."
            ::= { dodEntry 13 }

        dodIPFilters OBJECT-TYPE
            SYNTAX  Counter
            ACCESS  read-only
            STATUS  mandatory
            DESCRIPTION
                    "Number of IP filters currently defined for this remote."
            ::= { dodEntry 14 }

        dodIPXFilters OBJECT-TYPE
            SYNTAX  Counter
            ACCESS  read-only
            STATUS  mandatory
            DESCRIPTION
                    "Number of IPX filters currently defined for this remote"
            ::= { dodEntry 15 }

        dodRemoteIPNets OBJECT-TYPE
            SYNTAX  Counter
            ACCESS  read-only
            STATUS  mandatory
            DESCRIPTION
                    "This object describes the number of static IP routing
                    entries for this destination name or connection. The
                    static IP routing table is defined in another group."
            ::= { dodEntry 16 }

        dodRemoteIPXNets OBJECT-TYPE
            SYNTAX  Counter
            ACCESS  read-only
            STATUS  mandatory
            DESCRIPTION
                    "This object describes the number of static IPX routing
                    entries for this destination.  The static IPX routing
                    table is defined in another group. "
            ::= { dodEntry 17 }

        dodRemoteIPXSAPs OBJECT-TYPE
            SYNTAX  Counter
            ACCESS  read-only
            STATUS  mandatory
            DESCRIPTION
                    "This object describes the number of static IPX SAP
                    entries for this destination.  The static IPX SAP
                    table is defined in another group. "
            ::= { dodEntry 18 }

        dodRemoteMacState OBJECT-TYPE
            SYNTAX  INTEGER { enable(1), disable(2) }
            ACCESS  read-write
            STATUS  mandatory
            DESCRIPTION
                    "This object controls the current bridge state (enabled
                    or disabled) for this destination.

                    When one of the remote destinations is turned on, the
                    LAN port (ethernet) bridge capability will be turned
                    on also, after a reboot.  If this destination's bridge
                    state is disabled and the bridge state of all the other
                    destinations is also disabled, the LAN port bridge
                    state will be disabled.  Otherwise, if another
                    destination's bridge state is still enabled, the LAN
                    port bridge state will stay enabled.  This mechanism
                    is implemented in the system."
            ::= { dodEntry 19 }

        dodRemoteMacs OBJECT-TYPE
            SYNTAX  Counter
            ACCESS  read-only
            STATUS  mandatory
            DESCRIPTION
                    "The number of specific MAC addresses defined to be
                    statically bridged to this remote."
            ::= { dodEntry 20 }

        dodLastActivityTime OBJECT-TYPE
            SYNTAX  INTEGER
            ACCESS  read-only
            STATUS  mandatory
            DESCRIPTION
                    "The last activity time with this destination"
            ::= { dodEntry 21 }

        dodTableOperation OBJECT-TYPE
            SYNTAX  INTEGER { add(1), remove(2) }
            ACCESS  write-only
            STATUS  mandatory
            DESCRIPTION
                    "This object is used to create a new DOD record or
                    to delete a DOD record."
            ::= { dodEntry 22 }

        dodMinLinks OBJECT-TYPE
            SYNTAX  INTEGER (0..2)
            ACCESS  read-write
            STATUS  mandatory
            DESCRIPTION
                    "The minimum number of links to be used when
                    the system dials out or accepts incoming calls.
                    Must be lower or equal to dodMaxLinks."
            ::= { dodEntry 23 }

        dodBODType OBJECT-TYPE
            SYNTAX  INTEGER {
                      both(1),        -- incoming and outgoing traffic
                      output(2),      -- outgoing traffic only (to WAN)
                      input (3)       -- incoming traffic only (from WAN)
                    }
            ACCESS  read-write
            STATUS  mandatory
            DESCRIPTION
                    "The type of traffic to which bandwidth measurement
                    (defined by dodBWThreshold) applies."
            ::= { dodEntry 24 }

        dodIpOptRecvRIP OBJECT-TYPE
            SYNTAX  INTEGER { enable(1), disable(2) }
            ACCESS  read-write
            STATUS  mandatory
            DESCRIPTION
                    "Allows processing of RIP packets received from this
                    destination, when connected and IP routing is enabled
                    in a RIP 1 compatible manner.
                    dodIpOptRecvRIP, dodIpOptRecvRIP1, and dodIpOptRecvRIP2
                    are mutually exclusive."
            ::= { dodEntry 25 }

        dodIpOptSendRIP OBJECT-TYPE
            SYNTAX  INTEGER { enable(1), disable(2) }
            ACCESS  read-write
            STATUS  mandatory
            DESCRIPTION
                    "Allows sending of RIP packets to this destination
                    when connected and IP routing is enabled in a
                    RIP 1 compatible manner.
                    dodIpOptSendRIP, dodIpOptSendRIP1, and dodIpOptSendRIP2
                    are mutually exclusive."
            ::= { dodEntry 26 }

        dodIpOptRecvRIPDefault OBJECT-TYPE
            SYNTAX  INTEGER { enable(1), disable(2) }
            ACCESS  read-write
            STATUS  mandatory
            DESCRIPTION
                    "Allows updating of the IP default route when
                    receiving a RIP packet from this destination
                    for the route 0.0.0.0."
            ::= { dodEntry 27 }

        dodIpOptSendRIPDefault OBJECT-TYPE
            SYNTAX  INTEGER { enable(1), disable(2) }
            ACCESS  read-write
            STATUS  mandatory
            DESCRIPTION
                    "Allows sending of the IP default route (if known) to
                    this destination when connected, as 0.0.0.0."
            ::= { dodEntry 28 }

        dodIpOptKeepPrivate OBJECT-TYPE
            SYNTAX  INTEGER { enable(1), disable(2) }
            ACCESS  read-write
            STATUS  mandatory
            DESCRIPTION
                    "Allows to keep the route to this destination
                    private, i.e. don't advertise it to other destinations"
            ::= { dodEntry 29 }

        dodBrOptUseStp OBJECT-TYPE
            SYNTAX  INTEGER { enable(1), disable(2) }
            ACCESS  read-write
            STATUS  mandatory
            DESCRIPTION
                    "Allows use of Bridging Spanning Tree Protocol when
                    connected to this destination (causes a 40 second
                    startup delay): use when topology loops are likely."
            ::= { dodEntry 30 }

        dodPPPOptUseLCPEcho OBJECT-TYPE
            SYNTAX  INTEGER { enable(1), disable(2) }
            ACCESS  read-write
            STATUS  mandatory
            DESCRIPTION
                    "Perform a PPP LCP Echo request at regular intervals
                    when connected to this destination."
            ::= { dodEntry 31 }

        dodEntryIsDisabled OBJECT-TYPE
            SYNTAX  INTEGER { yes(1), no(2) }
            ACCESS  read-write
            STATUS  mandatory
            DESCRIPTION
                    "This database entry is active (enabled) or temporarily
                    disabled (i.e. bypassed when searching the database).
                    This eliminates the need for constant add/removes."
            ::= { dodEntry 32 }

        dodCallbackOption OBJECT-TYPE
            SYNTAX  INTEGER {
                            enable(1),       -- call him and dial back
                            disable(2),      -- never dial back this remote
                            callback-only(3) -- call only to perform dial-back.
                            }
            ACCESS  read-write
            STATUS  mandatory
            DESCRIPTION
                    "This option defines under what circumstances this system
                    is allowed to dial the specified remote. The setting
                    'enable' means that this system is free to call the
                    specified remote on its own and also to dial it back.
                    Under the 'disable' setting, dialing back is never a
                    possibility, but this system can dial the remote on its
                    own if a phone number exists for it.  The 'callback-only'
                    setting prevents this system from calling the remote
                    on its own: it will only perform the dial-back service.

                    Note: in order to implement dial-back, Caller entries
                          for this remote must exist (in dodCallerTable).
                          This allows this system to identify what remote
                          is calling, locating its database information
                          and possibly calling it back.  Caller Id verification
                          (in fpSysCallerIdTable) is independent but uses
                          the same dodCallerTable information."
            ::= { dodEntry 33 }

        dodSendDataAsVoice OBJECT-TYPE
            SYNTAX  INTEGER { enable(1), disable(2) }
            ACCESS  read-write
            STATUS  mandatory
            DESCRIPTION
                    "This option determines whether ISDN data calls issued to
                    this remote should be generated as voice calls instead
                    of restricted or unrestricted digital (ISDN only)."
            ::= { dodEntry 34 }

        dodIPXNetStrAddress OBJECT-TYPE
            SYNTAX  DisplayString (SIZE (1..8))
            ACCESS  read-write
            STATUS  mandatory
            DESCRIPTION
                    "The IPX network address associated with the WAN link
                    when connected to this remote. This is an alternative
                    to the dodIPXNetAddress object to be used when OCTET
                    STRINGs are not implemented.  In this case, specify the
                    IPX network number as an ASCII string containing from
                    1 to 8 characters, to be converted to hexadecimal by
                    the firmware."
            ::= { dodEntry 35 }

        dodOurSystemName OBJECT-TYPE
            SYNTAX  DisplayString (SIZE (0..40))
            ACCESS  write-only
            STATUS  mandatory
            DESCRIPTION
                    "Our system name (also called user name) when initiating
                    a communication with this remote.  It is used to override
                    the global system name (fpSysName) and is useful when the
                    name was assigned by the remote system admin, not
                    by this system admin, in order to avoid using the same
                    name (not under our control) for all connections."
            ::= { dodEntry 36 }

        dodOurPassword OBJECT-TYPE
            SYNTAX  DisplayString (SIZE (0..40))
            ACCESS  read-write
            STATUS  mandatory
            DESCRIPTION
                    "Our system password when initiating a communication
                    with this remote.  It is used to override the global
                    system password (when not empty) and is useful when the
                    password was assigned by the remote system admin, not
                    by this system admin, in order to avoid using the same
                    password (not under our control) for all connections.
                    GENERR is returned if not authorized to read the
                    dodOurPassword."
            ::= { dodEntry 37 }

        dodPPPCallbackOption OBJECT-TYPE
            SYNTAX  INTEGER {
                            none(1),            -- don't do PPP callback
                            authentication(2),  -- based on authentication
                            dial-string(3),     -- give phone # in CallbackInfo
                            location-string(4), -- give location in CallbackInfo
                            e164-string(5),     -- give phone # in CallbackInfo
                            name-string(6)      -- give name in CallbackInfo
                            }
            ACCESS  read-write
            STATUS  mandatory
            DESCRIPTION
                    "This option defines under what circumstances this system
                    is requesting a callback by using a method within the PPP
                    protocol suite (as opposed to an ISDN callback). The 
                    possibilities are:
                    - don't do any PPP callback (none)
                    - ask the peer to us back based on the database record
                      that he has for us (authentication).
                    - supply the string (i.e. phone number, including prefixes
                      etc,...) that the peer should use to call us back.
                    - supply a location information which the peer will use
                      in addition to our user name to call us back.
                    - supply a E.164 string to the peer to call us back.
                    - supply a generic string (name-string) to the peer so
                      that it can use to it call us back using whatever
                      method it deems appropriate. This router will force
                      this to be the same as the remote name (index in the
                      remote database) if it receives such a string."
            ::= { dodEntry 38 }

        dodPPPCallbackInfo OBJECT-TYPE
            SYNTAX  DisplayString (SIZE (0..40))
            ACCESS  read-write
            STATUS  mandatory
            DESCRIPTION
                    "When the dodPPPCallbackOption is set to something
                    other than none(1), this fields contains the additional
                    information sent to the PPP peer when requested a
                    callback."
            ::= { dodEntry 39 }


        dodDontAuthenticate OBJECT-TYPE
            SYNTAX  INTEGER { enable(1), disable(2) }
            ACCESS  read-write
            STATUS  mandatory
            DESCRIPTION
                    "When enabled (1), do not request any authentication
                    protocol when dialing out this destination.  Note that
                    an incoming call from this remote still requires some
                    form of authentication (to find this remote entry record),
                    as the key to the record is the authenticated name."
            ::= { dodEntry 40 }

        dodIPAddressTranslation OBJECT-TYPE
            SYNTAX  INTEGER { enable(1), disable(2) }
            ACCESS  read-write
            STATUS  mandatory
            DESCRIPTION
                    "When enabled (1), do IP address translation for traffic
                    to/from this remote."
            ::= { dodEntry 41 }

        dodIpOptRecvRIP1 OBJECT-TYPE
            SYNTAX  INTEGER { enable(1), disable(2) }
            ACCESS  read-write
            STATUS  mandatory
            DESCRIPTION
                    "Allows processing of RIP packets received from this
                    destination, when connected and IP routing is enabled
                    using RIP 1 only.
                    dodIpOptRecvRIP, dodIpOptRecvRIP1, and dodIpOptRecvRIP2
                    are mutually exclusive."
            ::= { dodEntry 42 }

        dodIpOptSendRIP1 OBJECT-TYPE
            SYNTAX  INTEGER { enable(1), disable(2) }
            ACCESS  read-write
            STATUS  mandatory
            DESCRIPTION
                    "Allows sending of RIP packets to this destination
                    when connected and IP routing is enabled using RIP 1 only.
                    dodIpOptSendRIP, dodIpOptSendRIP1, and dodIpOptSendRIP2
                    are mutually exclusive."
            ::= { dodEntry 43 }

        dodIpOptRecvRIP2 OBJECT-TYPE
            SYNTAX  INTEGER { enable(1), disable(2) }
            ACCESS  read-write
            STATUS  mandatory
            DESCRIPTION
                    "Allows processing of RIP packets received from this
                    destination, when connected and IP routing is enabled
                    using RIP 2 only.
                    dodIpOptRecvRIP, dodIpOptRecvRIP1, and dodIpOptRecvRIP2
                    are mutually exclusive."
            ::= { dodEntry 44 }

        dodIpOptSendRIP2 OBJECT-TYPE
            SYNTAX  INTEGER { enable(1), disable(2) }
            ACCESS  read-write
            STATUS  mandatory
            DESCRIPTION
                    "Allows sending of RIP packets to this destination
                    when connected and IP routing is enabled using RIP 2 only.
                    dodIpOptSendRIP, dodIpOptSendRIP1, and dodIpOptSendRIP2
                    are mutually exclusive."
            ::= { dodEntry 45 }


        dodProtocol OBJECT-TYPE
            SYNTAX  INTEGER {
                            protocolppp(1),         -- PPP VC-multiplexed
                            protocol1483pppllc(2),  -- PPP LLC-multiplexed
                            protocol1483snap(3),    -- RFC1483/1490 (SNAP)
                            protocol1483snapmer(4), -- RFC1483/1490 MAC Encapsulated Routing
                            protocol1483snapfr(5),  -- FRF.8 compatibility
                            protocolrawip(6)        -- No Encapsulation: Raw IP
                            }
            ACCESS  read-write
            STATUS  mandatory
            DESCRIPTION
                    "Type of protocol used for communicating with this remote."
            ::= { dodEntry 46 }

        dodCompression OBJECT-TYPE
            SYNTAX  INTEGER { enable(1), disable(2) }
            ACCESS  read-write
            STATUS  mandatory
            DESCRIPTION
                    "When enabled (1), do compression for traffic
                    to/from this remote."
            ::= { dodEntry 47 }

        dodPasswordSpecified OBJECT-TYPE
            SYNTAX  INTEGER { true(1), false(2) }
            ACCESS  read-only
            STATUS  mandatory
            DESCRIPTION
                    "Return true if the password for this remote connection
                    has been specified."
            ::= { dodEntry 48 }

        dodOurPasswordSpecified OBJECT-TYPE
            SYNTAX  INTEGER { true(1), false(2) }
            ACCESS  read-only
            STATUS  mandatory
            DESCRIPTION
                    "Return true if our system password for this 
                    remote connnection has been specified."
            ::= { dodEntry 49 }

        dodBlockNetBIOS OBJECT-TYPE
            SYNTAX  INTEGER { enable(1), disable(2) }
            ACCESS  read-write
            STATUS  mandatory
            DESCRIPTION
                    "When enabled (1), block NetBIOS traffic
                    to this remote."
            ::= { dodEntry 50 }

        dodMtu OBJECT-TYPE
            SYNTAX  INTEGER
            ACCESS  read-write
            STATUS  mandatory
            DESCRIPTION
                    "When non-zero, the desired MTU size for this remote.
                    When zero, use the default MTU size for the interface.
                    The MTU size used is the minimum of the desired MTU size
                    for this remote and the maximum MTU size allowed for 
                    the interface."
            ::= { dodEntry 51 }

        dodIpSlaveMode OBJECT-TYPE
            SYNTAX  INTEGER { enable(1), disable(2) }
            ACCESS  read-write
            STATUS  mandatory
            DESCRIPTION
                    "When enabled (1), always accept peer proposal for our
                    IP address for our WAN interface."
            ::= { dodEntry 52 }

        dodReacquireIpAddr OBJECT-TYPE
            SYNTAX  INTEGER { enable(1), disable(2) }
            ACCESS  read-write
            STATUS  mandatory
            DESCRIPTION
                    "When enabled (1), try to reacquire the last used
                    IP address for this interface IF we believe any
                    TCP connections are still active to this remote."
            ::= { dodEntry 53 }

        dodIpxOptRIPSAP OBJECT-TYPE
            SYNTAX  INTEGER { enable(1), disable(2) }
            ACCESS  read-write
            STATUS  mandatory
            DESCRIPTION
                    "When enabled (1), allows IPXCP to negotiate the use of
                    RIP and SAP IPX traffic. Actual use of the RIP and SAP
                    protocols will depend on the capabilities of the remote
                    at the time the PPP connection is established."
            ::= { dodEntry 54 }

        --
        -- Call IDs (phone, DLCI ....) table.
        --

        dodCallIDTable OBJECT-TYPE
            SYNTAX  SEQUENCE OF DodCallIDEntry
            ACCESS  not-accessible
            STATUS  mandatory
            DESCRIPTION
                    "A list of Call identifiers (phone number, DLCI ....)
                    for a particular destination name and link type (ISDN).
                    This table includes only two entries, type and phone
                    number count."
            ::= { fpdod 2 }

        dodCallIDEntry OBJECT-TYPE
            SYNTAX  DodCallIDEntry
            ACCESS  not-accessible
            STATUS  mandatory
            DESCRIPTION
                    "An entry of Call identifier for each connection type."
            INDEX {
                    dodDestinationName,
                    dodCallIDType
                  }
            ::= { dodCallIDTable 1}

        DodCallIDEntry ::=
            SEQUENCE {
                        dodCallIDType
                            ConnectionType,
                        dodCallIDPhones
                            Counter
                     }

        dodCallIDType OBJECT-TYPE
            SYNTAX  ConnectionType
            ACCESS  read-only
            STATUS  mandatory
            DESCRIPTION
                    "The connection type."
            ::= { dodCallIDEntry 1 }

        dodCallIDPhones OBJECT-TYPE
            SYNTAX  Counter
            ACCESS  read-only
            STATUS  mandatory
            DESCRIPTION
                    "Number of entries in the dodPhoneTable for this
                    type of connection and this remote."
            ::= { dodCallIDEntry 2 }

        --
        -- DOD phone numbers table.
        -- It is based on three indexes:
        ---      phone index, CallIDType, Destination name.
        --

        dodPhoneTable OBJECT-TYPE
            SYNTAX  SEQUENCE OF DodPhoneEntry
            ACCESS  not-accessible
            STATUS  mandatory
            DESCRIPTION
                    ""
            ::= { fpdod 3 }

        dodPhoneEntry OBJECT-TYPE
            SYNTAX  DodPhoneEntry
            ACCESS  not-accessible
            STATUS  mandatory
            DESCRIPTION
                    ""
            INDEX { 
                    dodDestinationName,
                    dodCallIDType,
                    dodPhoneIndex
                  }
            ::= { dodPhoneTable 1 }

        DodPhoneEntry ::=
            SEQUENCE {
                        dodPhoneIndex
                            INTEGER,
                        dodPhoneSpeed
                            INTEGER,
                        dodPhoneNumber
                            DisplayString (SIZE (0..30))
                    }

        dodPhoneIndex OBJECT-TYPE
            SYNTAX  INTEGER (1..2)
            ACCESS  read-only
            STATUS  mandatory
            DESCRIPTION
                    "It is an index to recognize which phone number
                    is in the table with the specified CallIDType and
                    DestinationName. "
            ::= { dodPhoneEntry 1 }

        dodPhoneSpeed OBJECT-TYPE
            SYNTAX  INTEGER
            ACCESS  read-write
            STATUS  mandatory
            DESCRIPTION
                    "The line speed (in bits per seconds) for asynchronous
                    connections."
            ::= { dodPhoneEntry 2 }

        dodPhoneNumber OBJECT-TYPE
            SYNTAX  DisplayString (SIZE (0..30))
            ACCESS  read-write
            STATUS  mandatory
            DESCRIPTION
                    "The phone number string."
            ::= { dodPhoneEntry 3 }


        --
        -- Remote bridge MAC address table
        --

        dodRemoteMacTable OBJECT-TYPE
            SYNTAX  SEQUENCE OF DodRemoteMacEntry
            ACCESS  not-accessible
            STATUS  mandatory
            DESCRIPTION
                    "A table of MAC addresses for bridging of the
                    specified destination name.  The table is indexed
                    by destination name and MAC address.  "
            ::= { fpdod 4 }

        dodRemoteMacEntry OBJECT-TYPE
            SYNTAX  DodRemoteMacEntry
            ACCESS  not-accessible
            STATUS  mandatory
            DESCRIPTION
                    ""
            INDEX {
                    dodDestinationName,
                    dodRemoteMacAddress
                  }
            ::= { dodRemoteMacTable 1 }

        DodRemoteMacEntry ::=
            SEQUENCE {
                        dodRemoteMacIndex
                            INTEGER,
                        dodRemoteMacAddress
                            MacAddress,
                        dodRemoteMacOperation
                            INTEGER
                    }

        dodRemoteMacIndex OBJECT-TYPE
            SYNTAX  INTEGER
            ACCESS  read-only
            STATUS  obsolete
            DESCRIPTION
                    "The index number is not used currently.
                    User don't need to implement it currently.
                    The table is indexed by the MAC address."
            ::= { dodRemoteMacEntry 1 }

        dodRemoteMacAddress OBJECT-TYPE
            SYNTAX  MacAddress
            ACCESS  read-write
            STATUS  mandatory
            DESCRIPTION
                    "Contains the IEEE unique MAC address of statically
                    configured devices for bridging purposes. When all of
                    the 6 bytes of this MAC address are zero, the entry is
                    called the unknown address. Any packet with a destination
                    address not in the static or dynamic MAC table of any
                    remote bridge will be sent to the default remote bridge
                    (which has a dodRemoteMacAddress entry defined for the
                    unknown MAC address)..

                    There can be only one remote destination specified as
                    default bridge, i.e. containing the unknown MAC address."
            ::= { dodRemoteMacEntry 2 }

        dodRemoteMacOperation OBJECT-TYPE
            SYNTAX INTEGER { add(1), remove(2) }
            ACCESS write-only
            STATUS mandatory
            DESCRIPTION
                    " add    -- add a static MAC address to be bridge to
                                this remote destination.
                      remove -- remove a static MAC address."
            ::= { dodRemoteMacEntry 3 }

        --
        -- Remote IP Network table for IP routing
        --
        dodRemoteIPNetTable OBJECT-TYPE
            SYNTAX  SEQUENCE OF DodRemoteIPNetEntry
            ACCESS  not-accessible
            STATUS  mandatory
            DESCRIPTION
                    "The static IP routing table.  It is based on indexes
                    of destination name and IP net address."
            ::= { fpdod 5 }

        dodRemoteIPNetEntry OBJECT-TYPE
            SYNTAX  DodRemoteIPNetEntry
            ACCESS  not-accessible
            STATUS  mandatory
            DESCRIPTION
                    ""
            INDEX {
                    dodDestinationName,
                    dodRemoteIPNetAddress
                  }
            ::= { dodRemoteIPNetTable 1 }

        DodRemoteIPNetEntry ::=
            SEQUENCE {
                        dodRemoteIPNetIndex
                              INTEGER,
                        dodRemoteIPNetAddress
                              IpAddress,
                        dodRemoteIPNetMask
                              IpAddress,
                        dodRemoteIPNetHops
                              INTEGER,
                        dodRemoteIPNetOperation
                              INTEGER,
                        dodRemoteIPNetGateway
                              IpAddress
                     }

        dodRemoteIPNetIndex OBJECT-TYPE
            SYNTAX  INTEGER
            ACCESS  read-only
            STATUS  obsolete
            DESCRIPTION
                    "This index is not currently in use."
            ::= { dodRemoteIPNetEntry 1 }

        dodRemoteIPNetAddress OBJECT-TYPE
            SYNTAX  IpAddress
            ACCESS  read-only
            STATUS  mandatory
            DESCRIPTION
                    "The IP network address of an entry of the static IP
                    routing table. "
            ::= { dodRemoteIPNetEntry 2 }

        dodRemoteIPNetMask OBJECT-TYPE
            SYNTAX  IpAddress
            ACCESS  read-write
            STATUS  mandatory
            DESCRIPTION
                    "The IP network mask of an entry of the static IP
                    routing table.  "
            ::= { dodRemoteIPNetEntry 3 }

        dodRemoteIPNetHops OBJECT-TYPE
            SYNTAX  INTEGER (1..15)
            ACCESS  read-write
            STATUS  mandatory
            DESCRIPTION
                    "The hop count for the specified IP network address
                    and destination name. "
            ::= { dodRemoteIPNetEntry 4 }

        dodRemoteIPNetOperation OBJECT-TYPE
            SYNTAX INTEGER { add(1), remove(2) }
            ACCESS write-only
            STATUS mandatory
            DESCRIPTION
                    "add    -- add a static IP route to this destination.
                     remove -- delete a static IP route to this destination.

                    To access the other objects in this entry (mask, hops)
                    the SNMP manager should add an entry first and then set
                    those other objects."
            ::= { dodRemoteIPNetEntry 5 }

        dodRemoteIPNetGateway OBJECT-TYPE
            SYNTAX  IpAddress
            ACCESS  read-write
            STATUS  mandatory
            DESCRIPTION
                    "The IP address of the gateway to which packets are sent
                     when the static route is over a broadcast medium, such as
                     when dodProtocol is RFC1483 with Mac Encapsulated Routing.
                     When the medium is point-to-point, this field is ignored."
            ::= { dodRemoteIPNetEntry 6 }

        --
        -- Remote IPX network table
        --

        dodRemoteIPXNetTable OBJECT-TYPE
            SYNTAX  SEQUENCE OF DodRemoteIPXNetEntry
            ACCESS  not-accessible
            STATUS  mandatory
            DESCRIPTION
                    "The static IPX routing table. It is based on indexes
                    of destination name and IPX network number."
            ::= { fpdod 6 }

        dodRemoteIPXNetEntry OBJECT-TYPE
            SYNTAX  DodRemoteIPXNetEntry
            ACCESS  not-accessible
            STATUS  mandatory
            DESCRIPTION
                    ""
            INDEX {
                    dodDestinationName,
                    dodRemoteIPXNetAddress
                  }
            ::= { dodRemoteIPXNetTable 1 }

        DodRemoteIPXNetEntry ::=
            SEQUENCE {
                        dodRemoteIPXNetIndex
                              INTEGER,
                        dodRemoteIPXNetAddress
                              IpxNetAddress,
                        dodRemoteIPXNetMetric
                              INTEGER,
                        dodRemoteIPXNetTicks
                              INTEGER,
                        dodRemoteIPXNetOperation
                              INTEGER,
                        dodRemoteIPXNetStrAddress
                              DisplayString (SIZE(1..8))
                     }

        dodRemoteIPXNetIndex OBJECT-TYPE
            SYNTAX  INTEGER
            ACCESS  read-only
            STATUS  obsolete
            DESCRIPTION
                    "Use dodRemoteIPXNetAddress as the index."
            ::= { dodRemoteIPXNetEntry 1 }

        dodRemoteIPXNetAddress OBJECT-TYPE
            SYNTAX  IpxNetAddress
            ACCESS  read-only
            STATUS  mandatory
            DESCRIPTION
                    "The IPX network address of an entry of the static IPX
                    routing table. "
            ::= { dodRemoteIPXNetEntry 2 }

        dodRemoteIPXNetMetric OBJECT-TYPE
            SYNTAX  INTEGER (1..15)
            ACCESS  read-write
            STATUS  mandatory
            DESCRIPTION
                    "The number of hops to reach this IPX network (via this
                    destination)."
            ::= { dodRemoteIPXNetEntry 3 }

        dodRemoteIPXNetTicks OBJECT-TYPE
            SYNTAX  INTEGER
            ACCESS  read-write
            STATUS  mandatory
            DESCRIPTION
                    "Number of 1/18th of seconds ticks necessary to reach
                    this IPX network number (via this destination)."
            ::= { dodRemoteIPXNetEntry 4 }

        dodRemoteIPXNetOperation OBJECT-TYPE
            SYNTAX INTEGER { add(1), remove(2) }
            ACCESS write-only
            STATUS mandatory
            DESCRIPTION
                    "add    -- add a static IPX route to this destination
                     remove -- delete a static IPX route for this destination

                    For IPX metric and ticks, the SNMP manager should create
                    the entry first and then set those attributes."
            ::= { dodRemoteIPXNetEntry 5 }

        dodRemoteIPXNetStrAddress OBJECT-TYPE
            SYNTAX  DisplayString (SIZE (1..8))
            ACCESS  read-only
            STATUS  mandatory
            DESCRIPTION
                    "The IPX network address of an entry of the static IPX
                    routing table. This is an alternative to the
                    dodRemoteIPXNetAddress object to be used when OCTET
                    STRINGs are not implemented.  In this case, specify the
                    IPX network number as an ASCII string containing from
                    1 to 8 characters, to be converted to hexadecimal by
                    the firmware."
            ::= { dodRemoteIPXNetEntry 6 }


        --
        -- The remote IPX SAP table
        --

        dodRemoteIPXSAPTable OBJECT-TYPE
            SYNTAX  SEQUENCE OF DodRemoteIPXSAPEntry
            ACCESS  not-accessible
            STATUS  mandatory
            DESCRIPTION
                    "The remote IPX SAP table. It is based on indexes of
                    DOD destination name, IPX network address, IPX node
                    number, and IPX socket number."
            ::= { fpdod 7 }

        dodRemoteIPXSAPEntry OBJECT-TYPE
            SYNTAX  DodRemoteIPXSAPEntry
            ACCESS  not-accessible
            STATUS  mandatory
            DESCRIPTION
                    ""
            INDEX {
                    dodDestinationName,
                    dodRemoteIPXSAPNetAddress,
                    dodRemoteIPXSAPNodeAddress,
                    dodRemoteIPXSAPSocket
                  }
            ::= { dodRemoteIPXSAPTable 1 }

        DodRemoteIPXSAPEntry ::=
            SEQUENCE {
                        dodRemoteIPXSAPIndex
                              INTEGER,
                        dodRemoteIPXSAPName
                              DisplayString (SIZE (0..48)),
                        dodRemoteIPXSAPNetAddress
                              IpxNetAddress,
                        dodRemoteIPXSAPNodeAddress
                              MacAddress,
                        dodRemoteIPXSAPSocket
                              OCTET STRING (SIZE (2)),
                        dodRemoteIPXSAPType
                              OCTET STRING (SIZE (2)),
                        dodRemoteIPXSAPHops
                              INTEGER,
                        dodRemoteIPXSAPOperation
                              INTEGER,
                        dodRemoteIPXSAPStrNetAddress
                              DisplayString (SIZE (1..8)),
                        dodRemoteIPXSAPStrSocket
                              DisplayString (SIZE (1..4)),
                        dodRemoteIPXSAPStrType
                              DisplayString (SIZE (1..4))
                     }

        dodRemoteIPXSAPIndex OBJECT-TYPE
            SYNTAX  INTEGER
            ACCESS  read-only
            STATUS  obsolete
            DESCRIPTION
                    "Use dodRemoteIPXSAPNetAddress, dodRemoteIPXSAPNodeAddress
                    dodRemoteIPXSAPSocket as indexes.  Not used."
            ::= { dodRemoteIPXSAPEntry 1 }

        dodRemoteIPXSAPName OBJECT-TYPE
            SYNTAX  DisplayString (SIZE (0..48))
            ACCESS  read-write
            STATUS  mandatory
            DESCRIPTION
                    "The name by which this IPX service is known."
            ::= { dodRemoteIPXSAPEntry 2 }

        dodRemoteIPXSAPNetAddress OBJECT-TYPE
            SYNTAX  IpxNetAddress
            ACCESS  read-only
            STATUS  mandatory
            DESCRIPTION
                    "The internal IPX network number of the server providing
                    this particular IPX service."
            ::= { dodRemoteIPXSAPEntry 3 }

        dodRemoteIPXSAPNodeAddress OBJECT-TYPE
            SYNTAX  MacAddress
            ACCESS  read-only
            STATUS  mandatory
            DESCRIPTION
                    "The node address on the IPX network number on which
                    a server provides this particular IPX service."
            ::= { dodRemoteIPXSAPEntry 4 }

        dodRemoteIPXSAPSocket OBJECT-TYPE
            SYNTAX  OCTET STRING (SIZE (2))
            ACCESS  read-only
            STATUS  mandatory
            DESCRIPTION
                    "The socket (i.e. internal port number) at which the
                    specified IPX service is provided in the server."
            ::= { dodRemoteIPXSAPEntry 5 }

        dodRemoteIPXSAPType OBJECT-TYPE
            SYNTAX  OCTET STRING (SIZE (2))
            ACCESS  read-write
            STATUS  mandatory
            DESCRIPTION
                    "The well-known type of service (i.e. File Service,
                    Advertising Print Service, etc...)"
            ::= { dodRemoteIPXSAPEntry 6 }

        dodRemoteIPXSAPHops OBJECT-TYPE
            SYNTAX  INTEGER (1..15)
            ACCESS  read-write
            STATUS  mandatory
            DESCRIPTION
                    "The number of hops necessary to reach the provider
                    of this service."
            ::= { dodRemoteIPXSAPEntry 7 }

        dodRemoteIPXSAPOperation OBJECT-TYPE
            SYNTAX INTEGER { add(1), remove (2) }
            ACCESS write-only
            STATUS mandatory
            DESCRIPTION
                    "add    -- add a new IPX SAP service to this destination
                     remove -- delete an IPX SAP service from this destination

                    For the IPX network address, node address, socket number,
                    type and hops, the SNMP manager should set those after
                    creating the entry. "
            ::= { dodRemoteIPXSAPEntry 9 }

        dodRemoteIPXSAPStrNetAddress OBJECT-TYPE
            SYNTAX  DisplayString (SIZE (1..8))
            ACCESS  read-only
            STATUS  mandatory
            DESCRIPTION
                    "The internal IPX network number of the server providing
                    this particular IPX service, expressed as an ASCII string,
                    converted to hexadecimal by the firmware."
            ::= { dodRemoteIPXSAPEntry 10 }

        dodRemoteIPXSAPStrSocket OBJECT-TYPE
            SYNTAX  DisplayString (SIZE (1..4))
            ACCESS  read-only
            STATUS  mandatory
            DESCRIPTION
                    "The socket (i.e. internal port number) at which the
                    specified IPX service is provided in the server, expressed
                    as an ASCII string, converted to hexadecimal by the
                    firmware."
            ::= { dodRemoteIPXSAPEntry 11 }

        dodRemoteIPXSAPStrType OBJECT-TYPE
            SYNTAX  DisplayString (SIZE (1..4))
            ACCESS  read-write
            STATUS  mandatory
            DESCRIPTION
                    "The well-known type of service (i.e. File Service,
                    Advertising Print Service, etc...), expressed as an
                    ASCII string, converted to hexadecimal by the firmware."
            ::= { dodRemoteIPXSAPEntry 12 }

        --
        -- IP filter table.
        --

        dodIPFilterTable OBJECT-TYPE
            SYNTAX  SEQUENCE OF DodIPFilterEntry
            ACCESS  not-accessible
            STATUS  mandatory
            DESCRIPTION
                  "A set of IP filters defined for this remote."
            ::= { fpdod 8 }

        dodIPFilterEntry OBJECT-TYPE
            SYNTAX  DodIPFilterEntry
            ACCESS  not-accessible
            STATUS  mandatory
            DESCRIPTION
                  ""
            INDEX {
                    dodDestinationName,
                    dodIPFilterIndex
                  }
            ::= { dodIPFilterTable 1}

        DodIPFilterEntry ::=
            SEQUENCE {
                        dodIPFilterIndex
                            INTEGER,
                        dodIPFilterDstNetAddr
                            IpAddress,
                        dodIPFilterSrcNetAddr
                            IpAddress,
                        dodIPFilterAllow
                            INTEGER
                     }

        dodIPFilterIndex OBJECT-TYPE
            SYNTAX  INTEGER (1..65536)
            ACCESS  read-only
            STATUS  mandatory
            DESCRIPTION
                    ""
            ::= { dodIPFilterEntry 1 }

        dodIPFilterDstNetAddr OBJECT-TYPE
            SYNTAX  IpAddress
            ACCESS  read-write
            STATUS  mandatory
            DESCRIPTION
                    ""
            ::= { dodIPFilterEntry 2 }

        dodIPFilterSrcNetAddr OBJECT-TYPE
            SYNTAX  IpAddress
            ACCESS  read-write
            STATUS  mandatory
            DESCRIPTION
                    ""
            ::= { dodIPFilterEntry 3 }

        dodIPFilterAllow OBJECT-TYPE
            SYNTAX  INTEGER {allow(1), deny(2)}
            ACCESS  read-write
            STATUS  mandatory
            DESCRIPTION
                    ""
            ::= { dodIPFilterEntry 4 }


        --
        --  IPX filter table
        --

        dodIPXFilterTable OBJECT-TYPE
            SYNTAX  SEQUENCE OF DodIPXFilterEntry
            ACCESS  not-accessible
            STATUS  mandatory
            DESCRIPTION
                  "A set of IPX filters defined for this remote."
            ::= { fpdod 9 }

        dodIPXFilterEntry OBJECT-TYPE
            SYNTAX  DodIPXFilterEntry
            ACCESS  not-accessible
            STATUS  mandatory
            DESCRIPTION
                  ""
            INDEX {
                    dodDestinationName,
                    dodIPXFilterIndex
                  }
            ::= { dodIPXFilterTable 1}

        DodIPXFilterEntry ::=
            SEQUENCE {
                        dodIPXFilterIndex
                            INTEGER,
                        dodIPXFilterDstNetAddr
                            IpxNetAddress,
                        dodIPXFilterDstNodeAddr
                            MacAddress,
                        dodIPXFilterDstSocket
                            OCTET STRING (SIZE (2)),
                        dodIPXFilterSrcNetAddr
                            IpxNetAddress,
                        dodIPXFilterSrcNodeAddr
                            MacAddress,
                        dodIPXFilterSrcSocket
                            OCTET STRING (SIZE (2)),
                        dodIPXFilterAllow
                            INTEGER
                     }

        dodIPXFilterIndex OBJECT-TYPE
            SYNTAX  INTEGER (1..65536)
            ACCESS  read-only
            STATUS  mandatory
            DESCRIPTION
                    ""
            ::= { dodIPXFilterEntry 1 }

        dodIPXFilterDstNetAddr OBJECT-TYPE
            SYNTAX  IpxNetAddress
            ACCESS  read-write
            STATUS  mandatory
            DESCRIPTION
                    ""
            ::= { dodIPXFilterEntry 2 }

        dodIPXFilterDstNodeAddr OBJECT-TYPE
            SYNTAX  MacAddress
            ACCESS  read-write
            STATUS  mandatory
            DESCRIPTION
                    ""
            ::= { dodIPXFilterEntry 3 }

        dodIPXFilterDstSocket OBJECT-TYPE
            SYNTAX  OCTET STRING (SIZE (2))
            ACCESS  read-write
            STATUS  mandatory
            DESCRIPTION
                    ""
            ::= { dodIPXFilterEntry 4 }

        dodIPXFilterSrcNetAddr OBJECT-TYPE
            SYNTAX  IpxNetAddress
            ACCESS  read-write
            STATUS  mandatory
            DESCRIPTION
                    ""
            ::= { dodIPXFilterEntry 5 }

        dodIPXFilterSrcNodeAddr OBJECT-TYPE
            SYNTAX  MacAddress
            ACCESS  read-write
            STATUS  mandatory
            DESCRIPTION
                    ""
            ::= { dodIPXFilterEntry 6 }

        dodIPXFilterSrcSocket OBJECT-TYPE
            SYNTAX  OCTET STRING (SIZE (2))
            ACCESS  read-write
            STATUS  mandatory
            DESCRIPTION
                    ""
            ::= { dodIPXFilterEntry 7 }

        dodIPXFilterAllow OBJECT-TYPE
            SYNTAX  INTEGER { allow(1), deny(2)}
            ACCESS  read-write
            STATUS  mandatory
            DESCRIPTION
                    ""
            ::= { dodIPXFilterEntry 8 }


        --
        -- Operation for dod to save/load configuration data to/from
        -- FLASH memory.
        --

        dodOperation OBJECT-TYPE
            SYNTAX  INTEGER { save(1), load(2), erase(3) }
            ACCESS  write-only
            STATUS  mandatory
            DESCRIPTION
                    " Use this object to give commands to save, load or
                      erase DOD configuration in FLASH memory."
            ::= { fpdod 10 }


        --
        -- The destination name of default bridge.
        -- This particular allow user to know which destination is specified
        -- as default bridge or to change the destination for default bridging.
        --

        dodRemoteMacDefault OBJECT-TYPE
            SYNTAX  DisplayString (SIZE (0..40))
            ACCESS  read-write
            STATUS  mandatory
            DESCRIPTION
                    " for GET :
                            This object gives the remote destination
                            name of default bridge.

                      for SET :

                            To set new default bridge, just give the
                            the desired destination name.

                            To delete and disable existing default bridge,
                            just give a NULL string."
           ::= { fpdod 11 }

        --
        -- The Callers table
        --

        dodCallerTable OBJECT-TYPE
            SYNTAX  SEQUENCE OF DodCallerEntry
            ACCESS  not-accessible
            STATUS  mandatory
            DESCRIPTION
                    "The Caller table: this is the list of numbers to search
                    when receiving an incoming call, to identify the remote
                    peer which made that call and thus find the corresponding
                    dodEntry record.  This table is used to implement
                    dial-back and also to implement Caller ID verification
                    (i.e. denying access to an unknown caller)."
            ::= { fpdod 12 }

        dodCallerEntry OBJECT-TYPE
            SYNTAX  DodCallerEntry
            ACCESS  not-accessible
            STATUS  mandatory
            DESCRIPTION
                    "Telephone numbers (or call information) of potential
                    callers."
            INDEX {
                    dodDestinationName,
                    dodCallIDType,
                    dodCallerNumber
                  }
            ::= { dodCallerTable 1}

        DodCallerEntry ::=
            SEQUENCE {
                        dodCallerNumber
                                DisplayString (SIZE (0..30)),
                        dodCallerOperation
                                INTEGER
                      }

        dodCallerNumber OBJECT-TYPE
            SYNTAX  DisplayString (SIZE (0..30))
            ACCESS  read-write
            STATUS  mandatory
            DESCRIPTION
                    "The number against which caller ID verification takes
                    place or used to find out which peer is calling before
                    dial-back takes place."
            ::= { dodCallerEntry 1 }

        dodCallerOperation OBJECT-TYPE
            SYNTAX  INTEGER { add(1), remove(2) }
            ACCESS  write-only
            STATUS  mandatory
            DESCRIPTION
                    "The operation being performed on a Caller data set:
                    add or remove an entry for the specified remote and
                    connection type."
            ::= { dodCallerEntry 2 }

        --
        -- The dod Server IP Translation Server table
        --

        dodIPTranslationServerTable OBJECT-TYPE
            SYNTAX  SEQUENCE OF DodIPTranslationServerEntry
            ACCESS  not-accessible
            STATUS  mandatory
            DESCRIPTION
                    "The IP Translation Server Table.  Used to select a
                    server when doing IP address translation."
            ::= { fpdod 13 }

        dodIPTranslationServerEntry OBJECT-TYPE
            SYNTAX  DodIPTranslationServerEntry
            ACCESS  not-accessible
            STATUS  mandatory
            DESCRIPTION
                    ""
            INDEX {
                    dodDestinationName,
                    dodIPTranslationServerIPAddress,
                    dodIPTranslationProtocol,
                    dodIPFirstTranslationPort
                  }
            ::= { dodIPTranslationServerTable 1 }

        DodIPTranslationServerEntry ::=
            SEQUENCE {
                        dodIPTranslationServerIPAddress
                              IpAddress,
                        dodIPTranslationProtocol
                              OCTET STRING (SIZE (1)),
                        dodIPFirstTranslationPort
                              OCTET STRING (SIZE (2)),
                        dodIPLastTranslationPort
                              OCTET STRING (SIZE (2)),
                        dodIPFirstPrivatePort
                              OCTET STRING (SIZE (2)),
                        dodIPTranslationStatus
                              RowStatus
                     }

        dodIPTranslationServerIPAddress OBJECT-TYPE
            SYNTAX  IpAddress
            ACCESS  read-only
            STATUS  mandatory
            DESCRIPTION
                    "The IP address of the Server when doing IP Address
                    translation. "
            ::= { dodIPTranslationServerEntry 1 }

        dodIPTranslationProtocol OBJECT-TYPE
            SYNTAX  OCTET STRING (SIZE (1))
            ACCESS  read-only
            STATUS  mandatory
            DESCRIPTION
                    "The protocol used by this Server."
            ::= { dodIPTranslationServerEntry 2 }

        dodIPFirstTranslationPort OBJECT-TYPE
            SYNTAX  OCTET STRING (SIZE (2))
            ACCESS  read-only
            STATUS  mandatory
            DESCRIPTION
                    "First public port in range used by this server.  
                    This port is what is referenced by the client.
                    A port of 0 is a wild-card signifying any port."
            ::= { dodIPTranslationServerEntry 3 }

        dodIPLastTranslationPort OBJECT-TYPE
            SYNTAX  OCTET STRING (SIZE (2))
            ACCESS  read-only
            STATUS  mandatory
            DESCRIPTION
                    "Last public port in range used by this server.
                    This port is the last port in range and is referenced
                    by the client..  This value must be greater than or equal 
                    first public port in range."
            ::= { dodIPTranslationServerEntry 4 }

        dodIPFirstPrivatePort OBJECT-TYPE
            SYNTAX  OCTET STRING (SIZE (2))
            ACCESS  read-only
            STATUS  mandatory
            DESCRIPTION
                    "This is the first private port in range as seen by the
                    server.  The public port range is mapped to this private
                    port range.  If the public port range is to be the same
                    as the private port range, this port should be the same
                    as the first public port."
            ::= { dodIPTranslationServerEntry 5 }

        dodIPTranslationStatus OBJECT-TYPE
            SYNTAX RowStatus
            ACCESS read-write
            STATUS mandatory
            DESCRIPTION
                    "The status column used for creating, modifying, and
                     deleting instances of the columnar objects in this table."
            ::= { dodIPTranslationServerEntry 6 }

        --
        -- The dod NAT Host Mapping table
        --

        dodNatHostMappingTable OBJECT-TYPE
            SYNTAX  SEQUENCE OF DodNatHostMappingEntry
            ACCESS  not-accessible
            STATUS  mandatory
            DESCRIPTION
                    "The NAT Host Mapping Table.  Used to select a
                    NAT Host Mapping when doing IP address translation."
            ::= { fpdod 14 }

        dodNatHostMappingEntry OBJECT-TYPE
            SYNTAX  DodNatHostMappingEntry
            ACCESS  not-accessible
            STATUS  mandatory
            DESCRIPTION
                    ""
            INDEX {
                    dodDestinationName,
                    dodFirstPrivateIPAddress,
                    dodLastPrivateIPAddress,
                    dodFirstPublicIPAddress
                  }
            ::= { dodNatHostMappingTable 1 }

        DodNatHostMappingEntry ::=
            SEQUENCE {
                        dodFirstPrivateIPAddress
                              IpAddress,
                        dodLastPrivateIPAddress
                              IpAddress,
                        dodFirstPublicIPAddress
                              IpAddress,
                        dodNatHostMappingStatus
                              RowStatus
                     }

        dodFirstPrivateIPAddress OBJECT-TYPE
            SYNTAX  IpAddress
            ACCESS  read-only
            STATUS  mandatory
            DESCRIPTION
                    "The first private IP address which starts the range
                    of private IP addresses which are mapped to public
                    IP addresses."
            ::= { dodNatHostMappingEntry 1 }

        dodLastPrivateIPAddress OBJECT-TYPE
            SYNTAX  IpAddress
            ACCESS  read-only
            STATUS  mandatory
            DESCRIPTION
                    "The last private IP address which ends the range
                    of private IP addresses which are mapped to public
                    IP addresses."
            ::= { dodNatHostMappingEntry 2 }

        dodFirstPublicIPAddress OBJECT-TYPE
            SYNTAX  IpAddress
            ACCESS  read-only
            STATUS  mandatory
            DESCRIPTION
                    "The first public IP address which starts the range of
                    public IP Addresses which are mapped to private IP
                    addresses.  The last public IP address in the range
                    is calculated by counting the number of private IP
                    addresses in the private IP address range and creating
                    an equivalent number of IP addresses in the public
                    IP address range so there is a one to one mapping
                    of public IP addresses to private IP addresses."
            ::= { dodNatHostMappingEntry 3 }

        dodNatHostMappingStatus OBJECT-TYPE
            SYNTAX RowStatus
            ACCESS read-write
            STATUS mandatory
            DESCRIPTION
                    "The status column used for creating, modifying, and
                    deleting instances of the columnar objects in this table."
            ::= { dodNatHostMappingEntry 4 }


        --
        --
        -- The ether group (i.e. LAN port)
        -- This group manages the configuration of the LAN interfaces
        -- This includes enabling/disabling IP/IPX on the interface.
        --

        fpEtherTable OBJECT-TYPE
            SYNTAX  SEQUENCE OF FpEtherEntry
            ACCESS  not-accessible
            STATUS  mandatory
            DESCRIPTION
                    "The Ethernet interface configuration table for each port"
            ::= { fpether 1 }

        fpEtherEntry OBJECT-TYPE
            SYNTAX  FpEtherEntry
            ACCESS  not-accessible
            STATUS  mandatory
            DESCRIPTION
                     ""
            INDEX { fpPortNum }
            ::= { fpEtherTable 1}

        FpEtherEntry ::=
              SEQUENCE {
                        fpPortNum
                              INTEGER,
                        fpBridgeState
                              INTEGER,
                        fpIpState
                              INTEGER,
                        fpIpxState
                              INTEGER,
                        fpIpNetAddress
                              IpAddress,
                        fpIpNetMask
                              IpAddress,
                        fpIpxNetAddress
                              IpxNetAddress,
                        fpIpxFrameType
                              INTEGER,
                        fpEtherIpOptRecvRIP
                              INTEGER,
                        fpEtherIpOptSendRIP
                              INTEGER,
                        fpEtherIpOptRecvRIPDefault
                              INTEGER,
                        fpEtherIpOptSendRIPDefault
                              INTEGER,
                        fpIpxStrNetAddress
                              DisplayString (SIZE(1..8)),
                        fpIpDefaultGateway
                              IpAddress,
                        fpEtherIpOptRecvRIP1
                              INTEGER,
                        fpEtherIpOptSendRIP1
                              INTEGER,
                        fpEtherIpOptRecvRIP2
                              INTEGER,
                        fpEtherIpOptSendRIP2
                              INTEGER,
                        fpIpRIPMulticastAddress
                              IpAddress,
                        fpNATState
                              INTEGER,
                        fpMtu
                              INTEGER
                       }

        fpPortNum  OBJECT-TYPE
            SYNTAX  INTEGER (1..2)
            ACCESS  read-only
            STATUS  mandatory
            DESCRIPTION
                    "The identifier number of this interface port."
            ::= { fpEtherEntry 1 }

        fpBridgeState  OBJECT-TYPE
            SYNTAX  INTEGER { enable(1), disable(2) }
            ACCESS  read-write
            STATUS  mandatory
            DESCRIPTION
                    "The object is used to show current state (enabled/
                    disabled) of the bridging the LAN port (ethernet).
                              1 -- the bridging is enabled.
                              2 -- the bridging is disabled.
                    The bridging is enabled/disabled by controlling the
                    dodRemoteMacState object of all the destinations.
                    This field is only writeable on systems that don't
                    support remote destinations (the DOD table)."
            ::= { fpEtherEntry 2 }

        fpIpState  OBJECT-TYPE
            SYNTAX  INTEGER { enable(1), disable(2) }
            ACCESS  read-write
            STATUS  mandatory
            DESCRIPTION
                    "Determines whether the IP protocol is routed (enable)
                    or not (disable) via this LAN interface. A change
                    requires rebooting. If the IP address and the network
                    mask are defined and IP routing is not enabled, this
                    system acts as an IP host only."
            ::= { fpEtherEntry 3 }

        fpIpxState  OBJECT-TYPE
            SYNTAX  INTEGER { enable(1), disable(2) }
            ACCESS  read-write
            STATUS  mandatory
            DESCRIPTION
                    "Determines whether the IPX protocol is routed (enable)
                    or not (disable) via this LAN interface.  A change
                    requires rebooting."
            ::= { fpEtherEntry 4 }

        fpIpNetAddress  OBJECT-TYPE
            SYNTAX  IpAddress
            ACCESS  read-write
            STATUS  mandatory
            DESCRIPTION
                    "This object allows to get or set the IP address for
                    this LAN interface: a change requires rebooting."
            ::= { fpEtherEntry 5 }

        fpIpNetMask  OBJECT-TYPE
            SYNTAX  IpAddress
            ACCESS  read-write
            STATUS  mandatory
            DESCRIPTION
                    "This object allows to get or set the IP network mask
                    for this LAN interface: a change requires rebooting."
            ::= { fpEtherEntry 6 }

        fpIpxNetAddress  OBJECT-TYPE
            SYNTAX  IpxNetAddress
            ACCESS  read-write
            STATUS  mandatory
            DESCRIPTION
                    "This objects allows to get or set the IPX external
                    network  number for this LAN port: a change requires
                    rebooting."
            ::= { fpEtherEntry 7 }

        fpIpxFrameType  OBJECT-TYPE
            SYNTAX  INTEGER { frame-8022(1), frame-8023(2), frame-dix(3) }
            ACCESS  read-write
            STATUS  mandatory
            DESCRIPTION
                    "This objects allows to get or set the IPX frame type
                    generated by the router for this LAN port: a change
                    requires rebooting. Possible values are: 802.2 (using
                    the Novell SAP 0xE0), 802.3 (the IPX packet follows
                    the Ethernet header immediately with no type) and
                    Ethernet-II (named DIX) where the Ethertype is 0x8137."
            ::= { fpEtherEntry 8 }

        fpEtherIpOptRecvRIP  OBJECT-TYPE
            SYNTAX  INTEGER { enable(1), disable(2) }
            ACCESS  read-write
            STATUS  mandatory
            DESCRIPTION
                    "Allows the processing of IP RIP 1 and RIP 2 packets 
                    received from for this LAN port: a change requires 
                    rebooting.  This setting is enabled by default.
                    fpEtherIpOptRecvRIP, fpEtherIpOptRecvRIP1, and 
                    fpEtherIpOptRecvRIP2 are mutually exclusive."

            ::= { fpEtherEntry 9 }

        fpEtherIpOptSendRIP  OBJECT-TYPE
            SYNTAX  INTEGER { enable(1), disable(2) }
            ACCESS  read-write
            STATUS  mandatory
            DESCRIPTION
                    "Allows sending IP RIP 1 compatible packets to this LAN
                    port when IP routing is enabled: a change requires 
                    rebooting.  This setting is enabled by default.
                    fpEtherIpOptSendRIP, fpEtherIpOptSendRIP1, and 
                    fpEtherIpOptSendRIP2 are mutually exclusive."
            ::= { fpEtherEntry 10 }

        fpEtherIpOptRecvRIPDefault  OBJECT-TYPE
            SYNTAX  INTEGER { enable(1), disable(2) }
            ACCESS  read-write
            STATUS  mandatory
            DESCRIPTION
                    "Allows updating the IP routing table with the default
                    route (i.e. 0.0.0.0) received from this LAN port when
                    IP routing is enabled: this setting is enabled by default.
                    A change on this object requires rebooting."
            ::= { fpEtherEntry 11 }

        fpEtherIpOptSendRIPDefault  OBJECT-TYPE
            SYNTAX  INTEGER { enable(1), disable(2) }
            ACCESS  read-write
            STATUS  mandatory
            DESCRIPTION
                    "Allows this system to advertise itself as the default
                    router on this LAN port when IP routing is enabled.
                    This setting is enabled by default. A change requires
                    rebooting."
            ::= { fpEtherEntry 12 }

        fpIpxStrNetAddress  OBJECT-TYPE
            SYNTAX  DisplayString (SIZE (1..8))
            ACCESS  read-write
            STATUS  mandatory
            DESCRIPTION
                    "This objects allows to get or set the IPX external
                    network  number for this LAN port: a change requires
                    rebooting. This object is expressed as an ASCII string,
                    converted to hexadecimal by the firmware: use this object
                    instead of fpIpxNetAddress when OCTET STRING is not
                    implemented."
            ::= { fpEtherEntry 13 }

        fpIpDefaultGateway  OBJECT-TYPE
            SYNTAX  IpAddress
            ACCESS  read-write
            STATUS  mandatory
            DESCRIPTION
                    "This object allows to get or set the IP address for
                    the default Gateway (default route), and assign it to
                    the interface specified by fpPortNum. This is particularly
                    useful when the device operates as an end-system (host)
                    as opposed to performing IP routing.  There can be only
                    one default route in the whole system. When set to 0.0.0.0,
                    no default is defined statically, and it may be discovered
                    dynamically if RIP is allowed on the LAN interface."
            ::= { fpEtherEntry 14 }

        fpEtherIpOptRecvRIP1  OBJECT-TYPE
            SYNTAX  INTEGER { enable(1), disable(2) }
            ACCESS  read-write
            STATUS  mandatory
            DESCRIPTION
                    "Allows the processing of IP RIP 1 packets received from
                    for this LAN port: a change requires rebooting.
                    fpEtherIpOptRecvRIP, fpEtherIpOptRecvRIP1, and 
                    fpEtherIpOptRecvRIP2 are mutually exclusive."
            ::= { fpEtherEntry 15 }

        fpEtherIpOptSendRIP1  OBJECT-TYPE
            SYNTAX  INTEGER { enable(1), disable(2) }
            ACCESS  read-write
            STATUS  mandatory
            DESCRIPTION
                    "Allows sending IP RIP 1 packets to this LAN port when
                    IP routing is enabled: a change requires rebooting.
                    fpEtherIpOptSendRIP, fpEtherIpOptSendRIP1, and 
                    fpEtherIpOptSendRIP2 are mutually exclusive."
            ::= { fpEtherEntry 16 }

        fpEtherIpOptRecvRIP2  OBJECT-TYPE
            SYNTAX  INTEGER { enable(1), disable(2) }
            ACCESS  read-write
            STATUS  mandatory
            DESCRIPTION
                    "Allows the processing of IP RIP 2 packets received from
                    for this LAN port: a change requires rebooting.
                    fpEtherIpOptRecvRIP, fpEtherIpOptRecvRIP1, and 
                    fpEtherIpOptRecvRIP2 are mutually exclusive."
            ::= { fpEtherEntry 17 }

        fpEtherIpOptSendRIP2  OBJECT-TYPE
            SYNTAX  INTEGER { enable(1), disable(2) }
            ACCESS  read-write
            STATUS  mandatory
            DESCRIPTION
                    "Allows sending IP RIP 2 packets to this LAN port when
                    IP routing is enabled: a change requires rebooting.
                    fpEtherIpOptSendRIP, fpEtherIpOptSendRIP1, and 
                    fpEtherIpOptSendRIP2 are mutually exclusive."
            ::= { fpEtherEntry 18 }

        fpIpRIPMulticastAddress  OBJECT-TYPE
            SYNTAX  IpAddress
            ACCESS  read-write
            STATUS  mandatory
            DESCRIPTION
                    "This object allows to get or set the RIP 2 Multicast
                    address for this LAN interface: set to 0.0.0.0 to restore
                    the default multicast address (i.e. 224.0.0.9).  A change
                    requires rebooting."
            ::= { fpEtherEntry 19 }

        fpNATState  OBJECT-TYPE
            SYNTAX  INTEGER { enable(1), disable(2) }
            ACCESS  read-write
            STATUS  mandatory
            DESCRIPTION
                    "Determines whether IP address/port translation is
                    performed via this LAN interface if the IP protocol is 
                    routed (enable) through this LAN interface.  A change
                    requires rebooting."
            ::= { fpEtherEntry 20 }

        fpMtu  OBJECT-TYPE
            SYNTAX  INTEGER
            ACCESS  read-write
            STATUS  mandatory
            DESCRIPTION
                    "When non-zero, the desired MTU size for this interface.
                    When zero, use the default MTU size for the interface.
                    The MTU size used is the minimum of the desired MTU size
                    for this interface and the maximum MTU size allowed for 
                    the interface."
            ::= { fpEtherEntry 21 }

        fpEtherOperation  OBJECT-TYPE
            SYNTAX  INTEGER { save(1), load(2), erase(3) }
            ACCESS  write-only
            STATUS  mandatory
            DESCRIPTION
                    "This object is used to save/load/erase the LAN port
                    (ethernet) configuration to/from FLASH."
            ::= { fpether 2 }

        --
        -- The ethernet NAT Host Mapping table
        --

        etherNatHostMappingTable OBJECT-TYPE
            SYNTAX  SEQUENCE OF EtherNatHostMappingEntry
            ACCESS  not-accessible
            STATUS  mandatory
            DESCRIPTION
                    "The NAT Host Mapping Table.  Used to select a
                    NAT Host Mapping when doing IP address translation."
            ::= { fpether 3 }

        etherNatHostMappingEntry OBJECT-TYPE
            SYNTAX  EtherNatHostMappingEntry
            ACCESS  not-accessible
            STATUS  mandatory
            DESCRIPTION
                    ""
            INDEX {
                    fpPortNum,
                    etherFirstPrivateIPAddress,
                    etherLastPrivateIPAddress,
                    etherFirstPublicIPAddress
                  }
            ::= { etherNatHostMappingTable 1 }

        EtherNatHostMappingEntry ::=
            SEQUENCE {
                        etherFirstPrivateIPAddress
                              IpAddress,
                        etherLastPrivateIPAddress
                              IpAddress,
                        etherFirstPublicIPAddress
                              IpAddress,
                        etherNatHostMappingStatus
                              RowStatus
                     }

        etherFirstPrivateIPAddress OBJECT-TYPE
            SYNTAX  IpAddress
            ACCESS  read-only
            STATUS  mandatory
            DESCRIPTION
                    "The first private IP address which starts the range
                    of private IP addresses which are mapped to public
                    IP addresses."
            ::= { etherNatHostMappingEntry 1 }

        etherLastPrivateIPAddress OBJECT-TYPE
            SYNTAX  IpAddress
            ACCESS  read-only
            STATUS  mandatory
            DESCRIPTION
                    "The last private IP address which ends the range
                    of private IP addresses which are mapped to public
                    IP addresses."
            ::= { etherNatHostMappingEntry 2 }

        etherFirstPublicIPAddress OBJECT-TYPE
            SYNTAX  IpAddress
            ACCESS  read-only
            STATUS  mandatory
            DESCRIPTION
                    "The first public IP address which starts the range of
                    public IP Addresses which are mapped to private IP
                    addresses.  The last public IP address in the range
                    is calculated by counting the number of private IP
                    addresses in the private IP address range and creating
                    an equivalent number of IP addresses in the public
                    IP address range so there is a one to one mapping
                    of public IP addresses to private IP addresses."
            ::= { etherNatHostMappingEntry 3 }

        etherNatHostMappingStatus OBJECT-TYPE
            SYNTAX RowStatus
            ACCESS read-write
            STATUS mandatory
            DESCRIPTION
                    "The status column used for creating, modifying, and
                    deleting instances of the columnar objects in this table."
            ::= { etherNatHostMappingEntry 4 }

        --
        -- The ethernet Server IP Translation Server table
        --

        etherIPTranslationServerTable OBJECT-TYPE
            SYNTAX  SEQUENCE OF EtherIPTranslationServerEntry
            ACCESS  not-accessible
            STATUS  mandatory
            DESCRIPTION
                    "The IP Translation Server Table.  Used to select a
                    server when doing IP address translation."
            ::= { fpether 4 }

        etherIPTranslationServerEntry OBJECT-TYPE
            SYNTAX  EtherIPTranslationServerEntry
            ACCESS  not-accessible
            STATUS  mandatory
            DESCRIPTION
                    ""
            INDEX {
                    fpPortNum,
                    etherIPTranslationServerIPAddress,
                    etherIPTranslationProtocol,
                    etherIPFirstTranslationPort
                  }
            ::= { etherIPTranslationServerTable 1 }

        EtherIPTranslationServerEntry ::=
            SEQUENCE {
                        etherIPTranslationServerIPAddress
                              IpAddress,
                        etherIPTranslationProtocol
                              OCTET STRING (SIZE (1)),
                        etherIPFirstTranslationPort
                              OCTET STRING (SIZE (2)),
                        etherIPLastTranslationPort
                              OCTET STRING (SIZE (2)),
                        etherIPFirstPrivatePort
                              OCTET STRING (SIZE (2)),
                        etherIPTranslationStatus
                              RowStatus
                     }

        etherIPTranslationServerIPAddress OBJECT-TYPE
            SYNTAX  IpAddress
            ACCESS  read-only
            STATUS  mandatory
            DESCRIPTION
                    "The IP address of the Server when doing IP Address
                    translation. "
            ::= { etherIPTranslationServerEntry 1 }

        etherIPTranslationProtocol OBJECT-TYPE
            SYNTAX  OCTET STRING (SIZE (1))
            ACCESS  read-only
            STATUS  mandatory
            DESCRIPTION
                    "The protocol used by this Server."
            ::= { etherIPTranslationServerEntry 2 }

        etherIPFirstTranslationPort OBJECT-TYPE
            SYNTAX  OCTET STRING (SIZE (2))
            ACCESS  read-only
            STATUS  mandatory
            DESCRIPTION
                    "First public port in range used by this server.  
                    This port is what is referenced by the client.
                    A port of 0 is a wild-card signifying any port."
            ::= { etherIPTranslationServerEntry 3 }

        etherIPLastTranslationPort OBJECT-TYPE
            SYNTAX  OCTET STRING (SIZE (2))
            ACCESS  read-only
            STATUS  mandatory
            DESCRIPTION
                    "Last public port in range used by this server.
                    This port is the last port in range and is referenced
                    by the client..  This value must be greater than or equal 
                    first public port in range."
            ::= { etherIPTranslationServerEntry 4 }

        etherIPFirstPrivatePort OBJECT-TYPE
            SYNTAX  OCTET STRING (SIZE (2))
            ACCESS  read-only
            STATUS  mandatory
            DESCRIPTION
                    "This is the first private port in range as seen by the
                    server.  The public port range is mapped to this private
                    port range.  If the public port range is to be the same
                    as the private port range, this port should be the same
                    as the first public port."
            ::= { etherIPTranslationServerEntry 5 }

        etherIPTranslationStatus OBJECT-TYPE
            SYNTAX RowStatus
            ACCESS read-write
            STATUS mandatory
            DESCRIPTION
                    "The status column used for creating, modifying, and
                     deleting instances of the columnar objects in this table."
            ::= { etherIPTranslationServerEntry 6 }

        --
        -- The FlowPoint ISDN configuration group
        --

        fpIsdnCh1Spid   OBJECT-TYPE
            SYNTAX  DisplayString (SIZE (0..30))
            ACCESS  read-write
            STATUS  mandatory
            DESCRIPTION
                    "The spid number string for 1st B channel."
            ::= { fpisdn 1 }

        fpIsdnCh2Spid   OBJECT-TYPE
            SYNTAX  DisplayString (SIZE (0..30))
            ACCESS  read-write
            STATUS  mandatory
            DESCRIPTION
                    "The spid number string for 2nd B channel."
            ::= { fpisdn 2 }

        fpIsdnCh1DirectoryNum   OBJECT-TYPE
            SYNTAX  DisplayString (SIZE (0..30))
            ACCESS  read-write
            STATUS  mandatory
            DESCRIPTION
                    "The directory number string for 1st B channel."
            ::= { fpisdn 3 }

        fpIsdnCh2DirectoryNum   OBJECT-TYPE
            SYNTAX  DisplayString (SIZE (0..30))
            ACCESS  read-write
            STATUS  mandatory
            DESCRIPTION
                    "The directory number string for 2nd B channel."
            ::= { fpisdn 4 }

        fpIsdnSwitchType  OBJECT-TYPE
            SYNTAX  INTEGER {
                             att5ess(2),   -- AT&T 5ESS w/custom software
                             dms100(5),    -- Northern Telecom DMS-100
                             kdd(7),       -- Kokusai Denshin Denwa (Japan)
                             net3(8),      -- NET-3 ETSI
                             net3swiss(9), -- Swiss NET-3 variant
                             ni1(10),      -- National ISDN-1
                             ntt(12),      -- Nippon Telegraph and Telephone
                             auto(14)      -- Auto switch type
                            }
            ACCESS  read-write
            STATUS  mandatory
            DESCRIPTION
                    "Specifies the ISDN switch type."
            ::= { fpisdn 5 }

        fpIsdnOperation OBJECT-TYPE
            SYNTAX  INTEGER { save(1), load(2), erase(3) }
            ACCESS  write-only
            STATUS  mandatory
            DESCRIPTION
                    "To save or load or erase the ISDN configuration
                    to/from FLASH memory."
            ::= { fpisdn 6 }

        fpIsdnCh1Status  OBJECT-TYPE
            SYNTAX  INTEGER {
                            idle(1),           -- Standby state
                            opening(2),        -- Establishing a call
                            connected(3),      -- Connected to remote
                            closing(4),        -- Tearing down call
                            alerting(5),       -- Incoming call
                            dialing(6),        -- Outgoing call
                            out-of-service(7), -- DSL out of service
                            in-use-by-pots(8)  -- POTS has use of channel
                            }
            ACCESS  read-only
            STATUS  mandatory
            DESCRIPTION
                    "This object shows the current status of B channel 1."
            ::= { fpisdn 7 }

        fpIsdnCh2Status  OBJECT-TYPE
            SYNTAX  INTEGER {
                            idle(1),           -- Standby state
                            opening(2),        -- Establishing a call
                            connected(3),      -- Connected to remote
                            closing(4),        -- Tearing down call
                            alerting(5),       -- Incoming call
                            dialing(6),        -- Outgoing call
                            out-of-service(7), -- DSL out of service
                            in-use-by-pots(8)  -- POTS has use of channel
                            }
            ACCESS  read-only
            STATUS  mandatory
            DESCRIPTION
                    "This object shows the current status of B channel 2."
            ::= { fpisdn 8 }


        fpIsdnCh1ClearCode  OBJECT-TYPE
            SYNTAX  INTEGER
            ACCESS  read-only
            STATUS  mandatory
            DESCRIPTION
                    "The clearing code of the last call, (0 if a call is in
                    progress) for B channel 1."
            ::= { fpisdn 9 }

        fpIsdnCh2ClearCode  OBJECT-TYPE
            SYNTAX  INTEGER
            ACCESS  read-only
            STATUS  mandatory
            DESCRIPTION
                    "The clearing code of the last call, (0 if a call is in
                    progress) for B channel 2."
            ::= { fpisdn 10 }


        fpIsdnCh1ClearReason  OBJECT-TYPE
            SYNTAX  DisplayString
            ACCESS  read-only
            STATUS  mandatory
            DESCRIPTION
                    "An explanation (in ASCII) of why the last called was
                    cleared for B channel 1 (the null string if a call is
                    in progress)."
            ::= { fpisdn 11 }

        fpIsdnCh2ClearReason  OBJECT-TYPE
            SYNTAX  DisplayString
            ACCESS  read-only
            STATUS  mandatory
            DESCRIPTION
                    "An explanation (in ASCII) of why the last called was
                    cleared for B channel 2 (the null string if a call is
                    in progress)."
            ::= { fpisdn 12 }

        fpIsdnSpeed OBJECT-TYPE
            SYNTAX  INTEGER { auto(1), speed-56k(2) }
            ACCESS  read-write
            STATUS  mandatory
            DESCRIPTION
                    "Whether the ISDN calls are made at a speed determined
                    by the speed defined in the remote database and processed
                    as indicated by the network (auto) or locked at 56Kb/s,
                    regardless of the remote database settings and the
                    parameters indicated by the network in incoming calls."
            ::= { fpisdn 13 }

        fpIsdnDataCallsIn OBJECT-TYPE
            SYNTAX  INTEGER { enable(1), disable(2) }
            ACCESS  read-write
            STATUS  mandatory
            DESCRIPTION
                    "This object determines whether ISDN data calls can be
                    received."
            ::= { fpisdn 14 }

        fpIsdnDataCallsOut OBJECT-TYPE
            SYNTAX  INTEGER { enable(1), disable(2) }
            ACCESS  read-write
            STATUS  mandatory
            DESCRIPTION
                    "This object determines whether ISDN data calls can be
                    generated by the device. This can be useful to let the
                    device place voice calls only while ensuring that no
                    data call is ever placed because the filtering/spoofing
                    did not eliminate spurious traffic."
            ::= { fpisdn 15 }

        fpIsdnLineStatus  OBJECT-TYPE
            SYNTAX  INTEGER {
                            activated(1),           -- line activated
                            deactivated(2)          -- line not activated
                            }
            ACCESS  read-only
            STATUS  mandatory
            DESCRIPTION
                    "This object shows the current status of the line."
            ::= { fpisdn 16 }

        fpIsdnStatus OBJECT-TYPE
            SYNTAX  INTEGER {
                          inService(1),      -- r   ok to place/recv calls
                          notOperational(2), -- r   not operational
                          startAutoSpid(3),  --   s start auto spid negot
                          stopAutoSpid(4),   --   s stop auto spid negot
                          autoSpidActive(5), -- r   searching for spids
                          validatingSpids(6),-- r   validating discovered spids
                          qualifyingSpids(7) -- r   validating existing spids
                            }
            ACCESS  read-write
            STATUS  mandatory
            DESCRIPTION
                    "This object sets/returns the service state for the
                     ISDN line."
            ::= { fpisdn 17 }

        fpIsdnAutoSpidCounter OBJECT-TYPE
            SYNTAX  INTEGER
            ACCESS  read-only
            STATUS  mandatory
            DESCRIPTION
                    "The spid index currently being tried when doing auto
                     spid detection."
            ::= { fpisdn 18 }

        fpIsdnSwitchTable OBJECT-TYPE
            SYNTAX  SEQUENCE OF FpIsdnSwitchEntry
            ACCESS  not-accessible
            STATUS  mandatory
            DESCRIPTION
                    "The switch table contains the switches supported
                     by this kernel."
            ::= { fpisdn 19 }

        fpIsdnSwitchEntry OBJECT-TYPE
            SYNTAX  FpIsdnSwitchEntry
            ACCESS  not-accessible
            STATUS  mandatory
            DESCRIPTION
                    "Each entry represents one switch type supported by
                     this kernel."
            INDEX   { fpIsdnSwitchTypeIndex }
            ::= { fpIsdnSwitchTable 1 }

        FpIsdnSwitchEntry ::=
              SEQUENCE {
                  fpIsdnSwitchTypeIndex
                      INTEGER
              }

        fpIsdnSwitchTypeIndex OBJECT-TYPE
            SYNTAX  INTEGER (1..32)
            ACCESS  read-only
            STATUS  mandatory
            DESCRIPTION
                    "Current switch type index."
            ::= { fpIsdnSwitchEntry 1 }

        --
        -- The FlowPoint system group
        --

        fpSysName OBJECT-TYPE
            SYNTAX  DisplayString (SIZE (0..50))
            ACCESS  read-write
            STATUS  mandatory
            DESCRIPTION
                    "An administratively-assigned name for this
                    managed node.  It will be the same name as the one
                    defined in MIB2. "
            ::= { fpsys 1 }

        fpSysMessage OBJECT-TYPE
            SYNTAX  DisplayString (SIZE (0..255))
            ACCESS  read-write
            STATUS  mandatory
            DESCRIPTION
                    "An administratively-assigned message for this
                    managed node. "
            ::= { fpsys 2 }

        fpSysPassword OBJECT-TYPE
            SYNTAX  DisplayString (SIZE (0..40))
            ACCESS  read-write
            STATUS  mandatory
            DESCRIPTION
                    "An administratively-assigned password for this
                    managed node.  The password will be used in the
                    authentication phase of PPP.  GENERR is returned
                    if not authorized to read the fpSysPassword."
            ::= { fpsys 3 }

        fpSysAuthen OBJECT-TYPE
            SYNTAX  AuthenProtoType
            ACCESS  read-write
            STATUS  mandatory
            DESCRIPTION
                    "An administratively-assigned authentication override
                    type for this managed node. This is normally set to
                    NONE, which means the normal rules apply. When set to
                    PAP, all the remote entries that have a setting of PAP
                    don't attempt to negotiate CHAP first, but propose
                    only PAP.  When set to CHAP, only CHAP authentication is
                    accepted by this node (this makes it easier than changing
                    all the remote entries to have their minimal level of
                    authentication set to CHAP)."
            ::= { fpsys 4 }

        fpSysOperation OBJECT-TYPE
            SYNTAX  INTEGER {
                            save(1),     -- save to FLASH memory
                            load(2),     -- load from FLASH (not recommended)
                            erase(3),    -- erase configuration in FLASH
                            reboot(4),   -- reboot after syncing file system
                            set-clock(5),-- set the RTC with fpSysXXX values.
                            reboot-like-factory(6), -- erase config files and reboot
                            reboot-like-new(7) -- erase config/autoexec files and reboot
                            }
            ACCESS  write-only
            STATUS  mandatory
            DESCRIPTION
                    "Use this object to save/load the system configuration
                    (only what is defined in this group) to/from FLASH memory,
                    or perform other control operation such as reboot."
            ::= { fpsys 5 }

        fpSysSoftwareVer OBJECT-TYPE
            SYNTAX  DisplayString (SIZE (0..40))
            ACCESS  read-only
            STATUS  mandatory
            DESCRIPTION
                    "Displays the software version run by the system."
            ::= { fpsys 6 }

        fpSysHardwareVer OBJECT-TYPE
            SYNTAX  DisplayString (SIZE (0..40))
            ACCESS  read-only
            STATUS  mandatory
            DESCRIPTION
                    "Displays the system model number, revision and serial
                    number. "
            ::= { fpsys 7 }

        fpLoginPassword OBJECT-TYPE
            SYNTAX  DisplayString (SIZE (0..40))
            ACCESS  read-write
            STATUS  mandatory
            DESCRIPTION
                    "Assign or change the administrator's password for
                    login.  Writing objects can only be performed when
                    logged-in, using this password.  To supply the password
                    for login purposes, use the fpLoginTable object in the
                    fplogin group.  GENERR is returned if not authorized to
                    read the fpLoginPassword."
            ::= { fpsys 8 }

        fpWriteTimeout OBJECT-TYPE
            SYNTAX  INTEGER (1..999)
            ACCESS  read-write
            STATUS  mandatory
            DESCRIPTION
                    "To set and retrieve a timeout value (in minutes) during
                    which a user logged in can modify objects. When setting
                    this value, the countdown restarts. The timer is first
                    started when the login password is supplied (see the
                    LoginTable object).  When the timer expires, a new login
                    must be performed or all writes to writable objects
                    return READONLY.

                    Default -- 10 minutes (until changed).
                    No security timeout -- set to 0."
            ::= { fpsys 9 }

        fpWriteTimer OBJECT-TYPE
            SYNTAX  INTEGER (0..999)
            ACCESS  read-only
            STATUS  mandatory
            DESCRIPTION
                    "This object retrieves the current security timer value.
                    It returns how many minutes are left (if any) before
                    a new login must be performed."
            ::= { fpsys 10 }

        fpCommunityName OBJECT-TYPE
            SYNTAX  DisplayString (SIZE (0..40))
            ACCESS  read-write
            STATUS  mandatory
            DESCRIPTION
                    "To change or retrieve the SNMP community name.
                    The default name is 'public'."
            ::= { fpsys 11 }

        fpInternetFireWall OBJECT-TYPE
            SYNTAX  INTEGER { enable(1), disable(2) }
            ACCESS  read-write
            STATUS  mandatory
            DESCRIPTION
                    "To enable or disable the internet firewall filter.
                    The filter discards any IP packet arriving from the
                    WAN with a source IP address belonging to the LAN."
            ::= { fpsys 12 }

        fpSysLogout OBJECT-TYPE
            SYNTAX  INTEGER
            ACCESS  write-only
            STATUS  mandatory
            DESCRIPTION
                    "Writing to this object prevents any change from any
                    SNMP manager (until logged in again).  Changes from
                    telnet and the console are controlled via the login
                    and logout commands, and are independent.
                    After a reboot, SNMP managers are logged out and
                    should log in before changing any configuration."
            ::= { fpsys 13 }

        fpIpxSupported OBJECT-TYPE
            SYNTAX  INTEGER { enable(1), disable(2) }
            ACCESS  read-only
            STATUS  mandatory
            DESCRIPTION
                    "Indicates whether or not IPX is supported in the
                    router software.  For compatibility with previous
                    non-IPX-capable builds, the manager should consider
                    that an error of NOSUCHNAME on this object means
                    that IPX is NOT supported. "
            ::= { fpsys 14 }

        fpSysCallerIdTable OBJECT-TYPE
            SYNTAX  SEQUENCE OF FpSysCallerIdEntry
            ACCESS  not-accessible
            STATUS  mandatory
            DESCRIPTION
                    "This table defines the types of connections for which
                    CallerID information should be verified."
            ::= { fpsys 15 }

        fpSysCallerIdEntry OBJECT-TYPE
            SYNTAX  FpSysCallerIdEntry
            ACCESS  not-accessible
            STATUS  mandatory
            DESCRIPTION
                    "An entry in the fpSysCallerIdTable specifies that
                    calls of the type used as an index, should be validated
                    by Caller ID verification (using dodCallerTable)."
            INDEX { dodCallIDType }
            ::= { fpSysCallerIdTable 1}

        FpSysCallerIdEntry ::=
            SEQUENCE {
                        fpCallerIdEnabled
                                INTEGER
                     }

        fpCallerIdEnabled OBJECT-TYPE
            SYNTAX  INTEGER { enable(1), disable(2) }
            ACCESS  read-write
            STATUS  mandatory
            DESCRIPTION
                    "Set this object to enable or disable CallerId
                    verification for the specified type of connection."
            ::= { fpSysCallerIdEntry 1 }

        fpMIBCompatibility OBJECT-TYPE
            SYNTAX  INTEGER { old(1), new(2) }
            ACCESS  read-only
            STATUS  mandatory
            DESCRIPTION
                    "Indicates that this private MIB is fully compatible
                    with RFC 1155.  For compatibility with previous
                    builds, the manager should consider that an error
                    of NOSUCHNAME on this object means that the 'old'
                    value applies, (meaning the enumeration of INTEGERs
                    are mostly zero-based instead of one-based)."
            ::= { fpsys 16 }

        fpPOTSInstalled OBJECT-TYPE
            SYNTAX  INTEGER { enable(1), disable(2) }
            ACCESS  read-only
            STATUS  mandatory
            DESCRIPTION
                    "Indicates whether or not POTS hardware is installed
                    AND is software supported.  For compatibility with
                    previous builds, the manager should consider that
                    an error of NOSUCHNAME on this object means that
                    POTS hardware and software are not available."
            ::= { fpsys 17 }

        fpSysLastLogEvent OBJECT-TYPE
            SYNTAX  DisplayString (SIZE (0..255))
            ACCESS  read-only
            STATUS  mandatory
            DESCRIPTION
                    "The last system event reported to the console. This
                    includes the timestamp, the subsystem and the actual
                    text message of the event."
            ::= { fpsys 18 }

        fpSysSingleUser OBJECT-TYPE
            SYNTAX  NetworkAddress
            ACCESS  read-write
            STATUS  mandatory
            DESCRIPTION
                    "This IP address used to define the single address to which
                    IP translation was to occur (one client system at a
                    time), or cancelling the translation when NULL.
                    Network Address Translation (NAT) and its ability to
                    define server mappings (with sysIPTranslationServerTable)
                    has rendered this object obsolete: this object is now always
                    returned as the IP address 0.0.0.0 and cannot be set to
                    anything else."
            ::= { fpsys 19 }

        fpSysYear OBJECT-TYPE
            SYNTAX  INTEGER
            ACCESS  write-only
            STATUS  mandatory
            DESCRIPTION
                    "Set this object to specify the year for the real time
                    clock, protected by a battery when the power is off.
                    When all the related parameters (fpSysYear, fpSysMonth,
                    fpSysDay, fpSysHour, fpSysMinute, fpSysSecond) are set,
                    set the fpSysOperation to set-clock(5)."
            ::= { fpsys 20 }

        fpSysMonth OBJECT-TYPE
            SYNTAX  INTEGER (1..12)
            ACCESS  write-only
            STATUS  mandatory
            DESCRIPTION
                    "Set this object to specify the month for the real time
                    clock, protected by a battery when the power is off.
                    When all the related parameters (fpSysYear, fpSysMonth,
                    fpSysDay, fpSysHour, fpSysMinute, fpSysSecond) are set,
                    set the fpSysOperation to set-clock(5)."
            ::= { fpsys 21 }

        fpSysDay OBJECT-TYPE
            SYNTAX  INTEGER (1..31)
            ACCESS  write-only
            STATUS  mandatory
            DESCRIPTION
                    "Set this object to specify the day for the real time
                    clock, protected by a battery when the power is off.
                    When all the related parameters (fpSysYear, fpSysMonth,
                    fpSysDay, fpSysHour, fpSysMinute, fpSysSecond) are set,
                    set the fpSysOperation to set-clock(5)."
            ::= { fpsys 22 }

        fpSysHour OBJECT-TYPE
            SYNTAX  INTEGER (0..23)
            ACCESS  write-only
            STATUS  mandatory
            DESCRIPTION
                    "Set this object to specify the hour for the real time
                    clock, protected by a battery when the power is off.
                    When all the related parameters (fpSysYear, fpSysMonth,
                    fpSysDay, fpSysHour, fpSysMinute, fpSysSecond) are set,
                    set the fpSysOperation to set-clock(5)."
            ::= { fpsys 23 }

        fpSysMinute OBJECT-TYPE
            SYNTAX  INTEGER (0..59)
            ACCESS  write-only
            STATUS  mandatory
            DESCRIPTION
                    "Set this object to specify the minutes for the real time
                    clock, protected by a battery when the power is off.
                    When all the related parameters (fpSysYear, fpSysMonth,
                    fpSysDay, fpSysHour, fpSysMinute, fpSysSecond) are set,
                    set the fpSysOperation to set-clock(5)."
            ::= { fpsys 24 }

        fpSysSecond OBJECT-TYPE
            SYNTAX  INTEGER (0..59)
            ACCESS  write-only
            STATUS  mandatory
            DESCRIPTION
                    "Set this object to specify the seconds for the real time
                    clock, protected by a battery when the power is off.
                    When all the related parameters (fpSysYear, fpSysMonth,
                    fpSysDay, fpSysHour, fpSysMinute, fpSysSecond) are set,
                    set the fpSysOperation to set-clock(5)."
            ::= { fpsys 25 }

        fpSysDefaultSingleUser  OBJECT-TYPE
            SYNTAX  NetworkAddress
            ACCESS  read-write
            STATUS  mandatory
            DESCRIPTION
                    "Network Address Translation (NAT) and its ability to
                    define server mappings (with sysIPTranslationServerTable)
                    has rendered this object obsolete.
                    For backwards compatibility purposes, this object still
                    allows to set the IP address of the client for which IP
                    address translation is to be performed by default.
                    However, to take effect, the configuration must be saved
                    (with fpEtherOperation=save(1)) and the system must be
                    restarted."
            ::= { fpsys 26 }

        fpSysBootpRelay  OBJECT-TYPE
            SYNTAX  NetworkAddress
            ACCESS  read-write
            STATUS  mandatory
            DESCRIPTION
                    "This object allows to get or set the IP address of the
                    DHCP/BOOTP Server when this router is acting as a Bootp
                    relay agent.  When set to 0.0.0.0, this router will not
                    act as a Bootp relay agent.
                    This setting is saved to non-volatile memory, with both
                    fpSysOperation=save(1) and fpEtherOperation=save(1)."
            ::= { fpsys 27 }

        fpSysKernelRevision  OBJECT-TYPE
            SYNTAX  INTEGER
            ACCESS  read-only
            STATUS  mandatory
            DESCRIPTION
                    "This object represents the number of times that the
                    source code got changed, possibly resulting in the support
                    of new features.  This number is intended to be used by
                    an SNMP manager to determine what features set is supported
                    by the kernel software (compared to what is expected as a
                    minimum). This objects differs from fpSysSoftwareVer which
                    is a string containing an administratively defined version."
            ::= { fpsys 28 }

        fpSysTelnetPort  OBJECT-TYPE
            SYNTAX  INTEGER (0..65535)
            ACCESS  read-write
            STATUS  mandatory
            DESCRIPTION
                    "The TCP port for reception of telnet connections to
                     the router.  Setting this value to zero disables
                     telnetting to the router.  This change requires a 
                     reboot to take affect."
            ::= { fpsys 29 }

        fpSysSNMPPort  OBJECT-TYPE
            SYNTAX  INTEGER (0..65535)
            ACCESS  read-write
            STATUS  mandatory
            DESCRIPTION
                    "The TCP port for reception of SNMP requests to
                     the router.  Setting this value to zero disables
                     SNMP management of the router.  This change requires a 
                     reboot to take affect."
            ::= { fpsys 30 }

        fpWAN2WANForwarding OBJECT-TYPE
            SYNTAX  INTEGER { enable(1), disable(2) }
            ACCESS  read-write
            STATUS  mandatory
            DESCRIPTION
                    "To enable or disable the forwarding of data traffic
                    from one wan link to another wan link."
            ::= { fpsys 31 }

        --
        -- Flowpoint System UDP Relay table
        --

        fpUdpRelayTable OBJECT-TYPE
            SYNTAX  SEQUENCE OF FpUdpRelayEntry
            ACCESS  not-accessible
            STATUS  mandatory
            DESCRIPTION
                    "This table defines UDP ports for which relaying should
                    should be performed when this UDP traffic is broadcast."
            ::= { fpsys 32 }

        fpUdpRelayEntry OBJECT-TYPE
            SYNTAX  FpUdpRelayEntry
            ACCESS  not-accessible
            STATUS  mandatory
            DESCRIPTION
                    "An entry in the fpUdpRelayTable specifies that UDP
                    packets which are broadcast to the specified ports
                    should be relayed to the specified IP address."
            INDEX {  
                    fpUdpRelayFirstPort,
                    fpUdpRelayLastPort,
                    fpUdpRelayIPAddress
                  }
            ::= { fpUdpRelayTable 1}

        FpUdpRelayEntry ::=
            SEQUENCE {
                        fpUdpRelayFirstPort
                              OCTET STRING (SIZE (2)),
                        fpUdpRelayLastPort
                              OCTET STRING (SIZE (2)),
                        fpUdpRelayIPAddress
                              IpAddress,
                        fpUdpRelayStatus
                              RowStatus
                     }

        fpUdpRelayFirstPort OBJECT-TYPE
            SYNTAX  OCTET STRING (SIZE (2))
            ACCESS  read-only
            STATUS  mandatory
            DESCRIPTION
                    "First UDP port of range of UDP ports which will be
                    relayed."
            ::= { fpUdpRelayEntry 1 }

        fpUdpRelayLastPort OBJECT-TYPE
            SYNTAX  OCTET STRING (SIZE (2))
            ACCESS  read-only
            STATUS  mandatory
            DESCRIPTION
                    "Last UDP port of range of UDP ports which will be
                    relayed."
            ::= { fpUdpRelayEntry 2 }

        fpUdpRelayIPAddress OBJECT-TYPE
            SYNTAX  IpAddress
            ACCESS  read-only
            STATUS  mandatory
            DESCRIPTION
                    "IP address to receive UDP broadcast traffic."
            ::= { fpUdpRelayEntry 3 }

        fpUdpRelayStatus OBJECT-TYPE
            SYNTAX RowStatus
            ACCESS read-write
            STATUS mandatory
            DESCRIPTION
                    "The status column used for creating, modifying, and
                     deleting instances of the columnar objects in this table."
            ::= { fpUdpRelayEntry 4 }

        fpOneWANConnection OBJECT-TYPE
            SYNTAX  INTEGER { enable(1), disable(2) }
            ACCESS  read-write
            STATUS  mandatory
            DESCRIPTION
                    "To enable or disable the bringing up of more than
                    one wan link at a time to different destinations."
            ::= { fpsys 33 }

        fpSysHTTPPort  OBJECT-TYPE
            SYNTAX  INTEGER (0..65535)
            ACCESS  read-write
            STATUS  mandatory
            DESCRIPTION
                    "The TCP port for reception of HTTP requests to
                     the router.  Setting this value to zero disables
                     HTTP management of the router.  This change requires a
                     reboot to take affect."
            ::= { fpsys 34 }

        fpDirectedBroadcasts  OBJECT-TYPE
            SYNTAX  INTEGER { enable(1), disable(2) }
            ACCESS  read-write
            STATUS  mandatory
            DESCRIPTION
                    "Enable/disable directed broadcasts to a directly
                    connected interface."
            ::= { fpsys 35 }

        fpBlockNetBIOSDefault OBJECT-TYPE
            SYNTAX  INTEGER { enable(1), disable(2) }
            ACCESS  read-write
            STATUS  mandatory
            DESCRIPTION
                    "To set the default when a new remote is created
                    that controls if the remote will block NetBIOS
                    traffic."
            ::= { fpsys 36 }

        fpSysFlashAvailable  OBJECT-TYPE
            SYNTAX  INTEGER
            ACCESS  read-only
            STATUS  mandatory
            DESCRIPTION
                    "This object represents the number of bytes of flash
                    available in the flash file system."
            ::= { fpsys 37 }

        --
        -- Flowpoint System Voice Table
        --

        fpVoiceTable OBJECT-TYPE
            SYNTAX  SEQUENCE OF FpVoiceEntry
            ACCESS  not-accessible
            STATUS  mandatory
            DESCRIPTION
                    "This table defines voice ports for voice routers."
            ::= { fpsys 38 }

        fpVoiceEntry OBJECT-TYPE
            SYNTAX  FpVoiceEntry
            ACCESS  not-accessible
            STATUS  mandatory
            DESCRIPTION
                    "An entry in the fpVoiceTable specifies voice
                    information for an voice router; such as the ATM PVC
                    or the Frame Relay DLCI."

            INDEX {  
                    fpVoiceIndex
                  }
            ::= { fpVoiceTable 1}

        FpVoiceEntry ::=
            SEQUENCE {
                        fpVoiceIndex
                              INTEGER,
                        fpVoicePort
                              DisplayString
                     }

        fpVoiceIndex OBJECT-TYPE
            SYNTAX  INTEGER (1..16)
            ACCESS  read-only
            STATUS  mandatory
            DESCRIPTION
                    "The voice port index number."
            ::= { fpVoiceEntry 1 }

        fpVoicePort  OBJECT-TYPE
            SYNTAX  DisplayString
            ACCESS  read-write
            STATUS  mandatory
            DESCRIPTION
                    "This object represents the ATM PVC or the Frame Relay
                     DLCI number for the voice port."
            ::= { fpVoiceEntry 2 }

        --
        -- Flowpoint System Echo Table
        --

        fpEchoTable OBJECT-TYPE
            SYNTAX  SEQUENCE OF FpEchoEntry
            ACCESS  not-accessible
            STATUS  deprecated
            DESCRIPTION
                    "This table defines echo ports."
            ::= { fpsys 39 }

        fpEchoEntry OBJECT-TYPE
            SYNTAX  FpEchoEntry
            ACCESS  not-accessible
            STATUS  deprecated
            DESCRIPTION
                    "An entry in the fpEchoTable specifies echo
                    information for a voice router; such as the ATM PVC
                    or the Frame Relay DLCI."

            INDEX {  
                    fpEchoIndex
                  }
            ::= { fpEchoTable 1}

        FpEchoEntry ::=
            SEQUENCE {
                        fpEchoIndex
                              INTEGER,
                        fpEchoPort
                              DisplayString
                     }

        fpEchoIndex OBJECT-TYPE
            SYNTAX  INTEGER (1..16)
            ACCESS  read-only
            STATUS  deprecated
            DESCRIPTION
                    "The echo port index number."
            ::= { fpEchoEntry 1 }

        fpEchoPort  OBJECT-TYPE
            SYNTAX  DisplayString
            ACCESS  read-write
            STATUS  deprecated
            DESCRIPTION
                    "This object represents the ATM PVC or the Frame Relay
                     DLCI number for the echo port."
            ::= { fpEchoEntry 2 }

        --
        -- Flowpoint System Options Table
        --

        fpOptionTable OBJECT-TYPE
            SYNTAX  SEQUENCE OF FpOptionEntry
            ACCESS  not-accessible
            STATUS  mandatory
            DESCRIPTION
                    "This table defines Kernel Options."
            ::= { fpsys 40 }

        fpOptionEntry OBJECT-TYPE
            SYNTAX  FpOptionEntry
            ACCESS  not-accessible
            STATUS  mandatory
            DESCRIPTION
                    "A string in the fpOptionTable specifies information
                    pertaining to options built into the kernel -and-
                    which options are available."

            INDEX {  
                    fpOptionIndex
                  }
            ::= { fpOptionTable 1}

        FpOptionEntry ::=
            SEQUENCE {
                        fpOptionIndex
                              INTEGER,
                        fpOptionString
                              DisplayString,
                        fpOptionAvailable
                              INTEGER
                      }

        fpOptionIndex OBJECT-TYPE
            SYNTAX  INTEGER
            ACCESS  read-only
            STATUS  mandatory
            DESCRIPTION
                    "An index number representing a line of options."
            ::= { fpOptionEntry 1 }

        fpOptionString  OBJECT-TYPE
            SYNTAX  DisplayString
            ACCESS  read-only
            STATUS  mandatory
            DESCRIPTION
                    "This object represents a an string for the option
                     built into the kernel."
            ::= { fpOptionEntry 2 }

        fpOptionAvailable OBJECT-TYPE
            SYNTAX  INTEGER { enable(1), disable(2) }
            ACCESS  read-only
            STATUS  mandatory
            DESCRIPTION
                    "Returns enable(1) if the option is available for use."
            ::= { fpOptionEntry 3 }

        --
        -- System login group
        --

        fpLoginTable OBJECT-TYPE
            SYNTAX  SEQUENCE OF FpLoginEntry
            ACCESS  not-accessible
            STATUS  mandatory
            DESCRIPTION
                    "This object returns the login status to the Manager. "
            ::= { fplogin 1 }

        fpLoginEntry OBJECT-TYPE
            SYNTAX  FpLoginEntry
            ACCESS  not-accessible
            STATUS  mandatory
            DESCRIPTION
                     ""
            INDEX { fpLoginPassword }
            ::= { fpLoginTable 1}

        FpLoginEntry ::=
            SEQUENCE {
                        fpLoginAction
                            INTEGER
                     }

        fpLoginAction OBJECT-TYPE
            SYNTAX  INTEGER { success(1), failure(2) }
            ACCESS  read-only
            STATUS  mandatory
            DESCRIPTION
                    "This object will return the login status to the Manager.
                    Use this object to login to system by giving the
                    administrator's password as index.  The login status are:
                    1 -- login OK.   Password matches with system's password.
                    2 -- login fail. Password mismatch."
            ::= { fpLoginEntry 1 }

        --
        -- WAN group, common to any WAN interfaces
        --

        fpWanTable OBJECT-TYPE
            SYNTAX  SEQUENCE OF FpWanEntry
            ACCESS  not-accessible
            STATUS  mandatory
            DESCRIPTION
                    "A list of WAN interface entries."
            ::= { fpWan 1 }

        fpWanEntry OBJECT-TYPE
            SYNTAX  FpWanEntry
            ACCESS  not-accessible
            STATUS  mandatory
            DESCRIPTION
                    "An interface entry containing objects at the
                    WAN layer..."
            INDEX   { fpWanIndex }
            ::= { fpWanTable 1 }

        FpWanEntry ::=
            SEQUENCE {
                        fpWanIndex
                            INTEGER,
                        fpWanInstantOutUtil
                              INTEGER,
                        fpWanInstantInUtil
                              INTEGER,
                        fpWanAvgOutUtil
                              INTEGER,
                        fpWanAvgInUtil
                              INTEGER,
                        fpWanRemoteName
                              DisplayString,
                        fpWanRemoteTime
                              INTEGER,
                        fpWanIfIndex
                              INTEGER,
                        fpWanOutSpeed
                              Gauge,
                        fpWanInSpeed
                              Gauge
                      }

        fpWanIndex OBJECT-TYPE
            SYNTAX  INTEGER (1..16)
            ACCESS  read-only
            STATUS  mandatory
            DESCRIPTION
                    "The interface index number."
            ::= { fpWanEntry 1 }

        fpWanInstantOutUtil OBJECT-TYPE
            SYNTAX  INTEGER (0..100)
            ACCESS  read-only
            STATUS  mandatory
            DESCRIPTION
                    "Intantaneous output bandwidth utilization,
                    from 0 to 100 (in 1% increments)."
            ::= { fpWanEntry 2 }

        fpWanInstantInUtil OBJECT-TYPE
            SYNTAX  INTEGER (0..100)
            ACCESS  read-only
            STATUS  mandatory
            DESCRIPTION
                    "Intantaneous input bandwidth utilization,
                    from 0 to 100 (in 1% increments)."
            ::= { fpWanEntry 3 }

        fpWanAvgOutUtil OBJECT-TYPE
            SYNTAX  INTEGER (0..100)
            ACCESS  read-only
            STATUS  mandatory
            DESCRIPTION
                    "Sliding average of output bandwidth utilization,
                    from 0 to 100 (in 1% increments)."
            ::= { fpWanEntry 4 }

        fpWanAvgInUtil OBJECT-TYPE
            SYNTAX  INTEGER (0..100)
            ACCESS  read-only
            STATUS  mandatory
            DESCRIPTION
                    "Sliding average of input bandwidth utilization,
                    from 0 to 100 (in 1% increments)."
            ::= { fpWanEntry 5 }

        fpWanRemoteName OBJECT-TYPE
            SYNTAX  DisplayString (SIZE (0..20))
            ACCESS  read-only
            STATUS  mandatory
            DESCRIPTION
                    "Name of user/destination that this port is
                    currently connected to, if known."
            ::= { fpWanEntry 6 }

        fpWanRemoteTime OBJECT-TYPE
            SYNTAX  INTEGER
            ACCESS  read-only
            STATUS  mandatory
            DESCRIPTION
                    "The number of seconds that we have been connected
                    to this particular remote across this WAN link."
            ::= { fpWanEntry 7 }

        fpWanIfIndex OBJECT-TYPE
              SYNTAX  INTEGER
              ACCESS  read-only
              STATUS  mandatory
              DESCRIPTION
                      "The corresponding MIB-II ifIndex for this interface"
            ::= { fpWanEntry 8 }

        fpWanOutSpeed OBJECT-TYPE
              SYNTAX  Gauge
              ACCESS  read-only
              STATUS  mandatory
              DESCRIPTION
                      "An estimate of the interface's current bandwidth
                      in bits per second, for the transmit side (relative
                      to this device)." 
            ::= { fpWanEntry 9 }

        fpWanInSpeed OBJECT-TYPE
              SYNTAX  Gauge
              ACCESS  read-only
              STATUS  mandatory
              DESCRIPTION
                      "An estimate of the interface's current bandwidth
                      in bits per second, for the receive side (relative
                      to this device)." 
            ::= { fpWanEntry 10 }


        --
        -- Operation for pots to save/load configuration data to/from
        -- FLASH memory.
        --

        potsOperation OBJECT-TYPE
            SYNTAX  INTEGER {
                              save(1),    -- save POTS data to FLASH
                              load(2),    -- load POTS data from FLASH
                              erase(3)    -- erase POTS data in FLASH
                            }
            ACCESS  write-only
            STATUS  mandatory
            DESCRIPTION
                    " Use this object to give commands to save, load or
                        erase POTS configuration in FLASH memory."
            ::= { fppots 1 }

        --
        -- Configuration and management data for the POTS interfaces
        --

        potsTable OBJECT-TYPE
            SYNTAX  SEQUENCE OF PotsEntry
            ACCESS  not-accessible
            STATUS  mandatory
            DESCRIPTION
                    "The table used to configure and manage the POTS
                    interfaces."
            ::= { fppots 2 }

        potsEntry OBJECT-TYPE
            SYNTAX  PotsEntry
            ACCESS  not-accessible
            STATUS  mandatory
            DESCRIPTION
                    ""
            INDEX { potsIndex }
            ::= { potsTable 1 }

        PotsEntry ::=
            SEQUENCE {
                        potsIndex
                                INTEGER,
                        potsEnabled
                                INTEGER,
                        potsOpMode
                                INTEGER,
                        potsPreemptMode
                                INTEGER,
                        potsAutoMode
                                INTEGER,
                        potsPhoneCnt
                                INTEGER,
                        potsLocalNumber
                                DisplayString (SIZE(0..30)),
                        potsRemoteNumber
                                DisplayString (SIZE(0..30)),
                        potsState
                                INTEGER,
                        potsIsdnChannel
                                INTEGER,
                        potsWanIndex
                                INTEGER
                     }

        potsIndex OBJECT-TYPE
            SYNTAX  INTEGER (1..2)
            ACCESS  read-only
            STATUS  mandatory
            DESCRIPTION
                    "Index used to access a potsEntry: maps to the
                    connectors marked POTS1 and POTS2."
            ::= { potsEntry 1 }

        potsEnabled OBJECT-TYPE
            SYNTAX  INTEGER { enable(1), disable(2) }
            ACCESS  read-write
            STATUS  mandatory
            DESCRIPTION
                    "Enable or disable the POTS functionality at the specified
                    connector."
            ::= { potsEntry 2 }

        potsOpMode OBJECT-TYPE
            SYNTAX  INTEGER {
                            both(1),    -- allow incoming and outgoing calls
                            answer(2),  -- allow incoming calls only
                            dial(3)     -- allow outgoing calls only
                            }
            ACCESS  read-write
            STATUS  mandatory
            DESCRIPTION
                    "Specifies the type of calls that should be handled by
                    this POTS interface. The default is to allow both incoming
                    and outgoing calls."
            ::= { potsEntry 3 }

        potsPreemptMode OBJECT-TYPE
            SYNTAX  INTEGER {
                            both(1),    -- always preempt data calls
                            in(2),      -- preempt data with incoming calls only
                            out(3),     -- preempt data with outgoing calls only
                            none(4)     -- never preempt a data call
                            }
            ACCESS  read-write
            STATUS  mandatory
            DESCRIPTION
                    "Specifies the behavior of analog calls versus data calls.
                    The default is both: voice calls always preempt data calls."
            ::= { potsEntry 4 }

        potsAutoMode OBJECT-TYPE
            SYNTAX  INTEGER {
                            both(1),    -- automatic preemption on all calls,
                            in(2),      -- automatic with incoming calls only
                            out(3),     -- automatic with outgoing calls only
                            none(4)     -- always ask operator
                            }
            ACCESS  read-write
            STATUS  mandatory
            DESCRIPTION
                    "Defines whether the preemption mode defined by
                    potsPreemptMode is to be performed automatically
                    or whether the user should be prompted first. This
                    only applies when the preemption of that type is allowed."
            ::= { potsEntry 5 }

        potsPhoneCnt OBJECT-TYPE
            SYNTAX  INTEGER (0..8)
            ACCESS  read-only
            STATUS  mandatory
            DESCRIPTION
                    "Indicates the number of phone numbers associated with
                    this POTS interface."
            ::= { potsEntry 6 }

        potsLocalNumber OBJECT-TYPE
            SYNTAX  DisplayString (SIZE(0..30))
            ACCESS  read-only
            STATUS  mandatory
            DESCRIPTION
                    "The local phone number used by this POTS interface during
                    the last analog call processed (incoming and outgoing)."
            ::= { potsEntry 7 }

        potsRemoteNumber OBJECT-TYPE
            SYNTAX  DisplayString (SIZE(0..30))
            ACCESS  read-only
            STATUS  mandatory
            DESCRIPTION
                    "The remote phone number used by this POTS interface during
                    the last analog call processed (outgoing and incoming when
                    caller ID is available)."
            ::= { potsEntry 8 }

        potsState OBJECT-TYPE
            SYNTAX  INTEGER {
                            other(1),           -- none of the following
                            not-available(2),   -- POTS interface disabled
                            idle(3),            -- on hook in idle state
                            wait-dialtone(4),   -- off hook waiting for dialtone
                            ringing(5),         -- incoming call
                            dialing(6),         -- outgoing call
                            proceeding(7),      -- waiting for call completion
                            connected-incoming(8),  -- incoming call established
                            connected-outgoing(9),  -- outgoing call established
                            disconnected(10),       -- call terminated
                            entering-ip-addr(11),   -- dialing in ip address
                            held-call(12)       -- held call
                            }
            ACCESS  read-only
            STATUS  mandatory
            DESCRIPTION
                    "Current state of this POTS interface."
            ::= { potsEntry 9}

        potsIsdnChannel OBJECT-TYPE
            SYNTAX  INTEGER (0..2)
            ACCESS  read-only
            STATUS  mandatory
            DESCRIPTION
                    "Indicates which ISDN channel (1 or 2) is associated with
                    this POTS interface for the duration of this call.
                    Additional information (like the clearing cause and
                    reason are available via the ISDN group variables. When
                    no ISDN channel is assigned to this POTS interface yet,
                    0 is returned"
            ::= { potsEntry 10 }

        potsWanIndex OBJECT-TYPE
            SYNTAX  INTEGER (0..2)
            ACCESS  read-only
            STATUS  mandatory
            DESCRIPTION
                    "Indicates which Wan interface (1 or 2) is associated with
                    this POTS interface for the duration of this call.
                    Additional information (like the duration of the call
                    is available via the WAN interface group variables. When
                    no WAN interface is mapped to this POTS interface yet,
                    0 is returned"
            ::= { potsEntry 11 }


        --
        -- Assignment of (local) phone numbers to POTS interfaces
        --

        potsPhoneTable OBJECT-TYPE
            SYNTAX  SEQUENCE OF PotsPhoneEntry
            ACCESS  not-accessible
            STATUS  mandatory
            DESCRIPTION
                    "The table used to associate phone numbers and POTS
                    interfaces."
            ::= { fppots 3 }

        potsPhoneEntry OBJECT-TYPE
            SYNTAX  PotsPhoneEntry
            ACCESS  not-accessible
            STATUS  mandatory
            DESCRIPTION
                    ""
            INDEX {
                    potsIndex,
                    potsPhoneNumber
                  }
            ::= { potsPhoneTable 1 }

        PotsPhoneEntry ::=
            SEQUENCE {
                        potsPhoneNumber
                                DisplayString (SIZE(0..30)),
                        potsPhoneOperation
                                INTEGER
                     }

        potsPhoneNumber OBJECT-TYPE
            SYNTAX  DisplayString (SIZE(0..30))
            ACCESS  read-only
            STATUS  mandatory
            DESCRIPTION
                    "A phone number associated with the specified POTS
                    interface, such that when an incoming analog call
                    arrives, that interface rings, if allowed. This is
                    used as an index into the POTS phone number table."
            ::= { potsPhoneEntry 1 }

        potsPhoneOperation OBJECT-TYPE
            SYNTAX  INTEGER { add(1), remove(2) }
            ACCESS  write-only
            STATUS  mandatory
            DESCRIPTION
                    "Perform a set on this object to add or remove the
                    association between the specified phone number and
                    the specified POTS interface."
            ::= { potsPhoneEntry 2 }


        --
        -- The Download/Upload group (TFTP operations)
        --

        fpDLForceOnBoot  OBJECT-TYPE
            SYNTAX  INTEGER
            ACCESS  read-write
            STATUS  mandatory
            DESCRIPTION
                    "When set to a 1, the system will request a
                     download, during the next system restart.
                     If no server is found and the current image
                     in flash memory is valid, the system will boot
                     using the flash-resident image."
            ::= { fpdownload 1 }

        fpDLCommitRAMToFlash  OBJECT-TYPE
            SYNTAX  INTEGER
            ACCESS  read-only
            STATUS  obsolete
            DESCRIPTION
                    "This object only exists for compatibility reasons."
            ::= { fpdownload 2 }

        fpDLInitiateColdBoot  OBJECT-TYPE
            SYNTAX  INTEGER
            ACCESS  read-write
            STATUS  mandatory
            DESCRIPTION
                    "When written with a 1, the boot software intiates a
                    system reboot.  All MIB variables used to control
                    the exact nature of the download should be set,
                    prior to activating a system reset.
                    A read always returns a 0."
            ::= { fpdownload 3 }

        fpDLTFTPRequestHost  OBJECT-TYPE
            SYNTAX  NetworkAddress
            ACCESS  read-write
            STATUS  mandatory
            DESCRIPTION
                    "The IP address of the server to be used, when
                    firmware is to be loaded across the network (network
                    boot)."
            ::= { fpdownload 4 }

        fpDLTFTPRequest  OBJECT-TYPE
            SYNTAX  DisplayString
            ACCESS  read-only
            STATUS  mandatory
            DESCRIPTION
                    "The filename requested of the server, when firmware
                    is to be loaded across the network (network boot)."
            ::= { fpdownload 5 }

        fpDLLastImageFilename  OBJECT-TYPE
            SYNTAX  DisplayString
            ACCESS  read-only
            STATUS  mandatory
            DESCRIPTION
                    "Filename of the last image to be successfully
                    loaded into memory."
            ::= { fpdownload 6 }

        fpDLLastServerIPAddress  OBJECT-TYPE
            SYNTAX  NetworkAddress
            ACCESS  read-only
            STATUS  mandatory
            DESCRIPTION
                    "The IP address of the server used to load the
                    present image in flash memory."
            ::= { fpdownload 7 }

        fpDLFlashSize  OBJECT-TYPE
            SYNTAX  INTEGER
            ACCESS  read-only
            STATUS  mandatory
            DESCRIPTION
                    "Denotes the size, in bytes, of flash memory con-
                    tained on this module."
            ::= { fpdownload 8 }

        fpDLFlashCount  OBJECT-TYPE
            SYNTAX  INTEGER
            ACCESS  read-only
            STATUS  mandatory
            DESCRIPTION
                    "Denotes the number of times that flash memory has
                    been reprogrammed.  This value is initialized to 1,
                    when the module is initially powered up."
            ::= { fpdownload 9 }

        fpDLFirmwareBase  OBJECT-TYPE
            SYNTAX  INTEGER
            ACCESS  read-only
            STATUS  mandatory
            DESCRIPTION
                    "Denotes the starting address of the firmware in
                    RAM."
            ::= { fpdownload 10 }

        fpDLFirmwareTop  OBJECT-TYPE
            SYNTAX  INTEGER
            ACCESS  read-only
            STATUS  mandatory
            DESCRIPTION
                    "Denotes the ending address of firmware in RAM."
            ::= { fpdownload 11 }

        fpDLFirmwareStart  OBJECT-TYPE
            SYNTAX  INTEGER
            ACCESS  read-only
            STATUS  mandatory
            DESCRIPTION
                    "Denotes the start address of the firmware, in RAM,
                    as established by the boot process."
            ::= { fpdownload 12 }

        fpDLBootRev  OBJECT-TYPE
            SYNTAX  OCTET STRING (SIZE(9))
            ACCESS  read-only
            STATUS  mandatory
            DESCRIPTION
                    "Denotes the revision of boot firmware in the module.
                    The first octets provides the version, and the
                    second provides the revision."
            ::= { fpdownload 13 }

        fpDLForceBootp  OBJECT-TYPE
            SYNTAX  INTEGER
            ACCESS  read-write
            STATUS  mandatory
            DESCRIPTION
                    "When set, this variable forces the client to send a
                    BOOTP request packet when rebooting.  The client will
                    make several attempts before timing out if a server
                    does not respond.  This variable stays set.  When set to
                    a 1 it should always be read as a one.  When set to zero
                    it should always be read as zero."
            ::= { fpdownload 14 }

        fpDLServerName   OBJECT-TYPE
            SYNTAX  OCTET STRING
            ACCESS  read-write
            STATUS  mandatory
            DESCRIPTION
                    "This OID is reserved for future use of the Bootp server
                    name.  This field can be used when a client wants to get
                    boot information from a particular bootp server."
            ::= { fpdownload 15 }

        fpDLOnLineDownLoad      OBJECT-TYPE
            SYNTAX  INTEGER {
                            normalOperation(1),
                            forceDownLoad(2),
                            forceDownLoadReset(3),
                            forceUpLoad(4),
                            forceRemove(5)
                            }
            ACCESS  read-write
            STATUS  mandatory
            DESCRIPTION
                    "During normal operation this object has the value of 1.
                    By setting this object to a value of forceDownLoad(2)
                    an online download will be performed.  By setting this
                    object to a value of forceDownLoadReset(3) an online
                    download will be performed and a reset will be forced
                    upon successful completion of the download.
                    The forceUpLoad(4) operation causes the local file
                    specified in fpDLLocalFileName to be uploaded to the TFTP
                    server fpDLNetAddress with the file name fpDLFileName.
                    The forceRemove(5) operation deletes the local file
                    specified in fpDLLocalFileName."
            ::= { fpdownload 16 }

        fpDLOperStatus  OBJECT-TYPE
            SYNTAX  INTEGER {
                            other(1),               -- none of the following
                            unknown(2),
                            normalOperation(3),
                            downLoadActive(4),
                            downLoadCompleteError(5),
                            upLoadActive(6),
                            upLoadCompleteError(7),
                            removeActive(8),
                            removeCompleteError(9)
                            }
            ACCESS  read-only
            STATUS  mandatory
            DESCRIPTION
                    "This object reflects the status of download/upload
                    operations.  A value of normalOperation(3) reflects
                    either a download was started but has finished normally
                    and no reset was specified or no download has been started.
                    A value of downLoadActive only appears while a download
                    is in progress.  A value of downLoadCompleteError reflects
                    that a download was started however an error was detected.
                    Similarly when an upload is in progress upLoadActive(6)
                    is returned and if an error occurs upLoadCompeteError(7)
                    is returned.  A value of removeActive(8) indicates that
                    a local file is being removed and removeCompleteError(9)
                    indicates a failure to remove the file."
            ::= { fpdownload 17 }

        fpDLNetAddress  OBJECT-TYPE
            SYNTAX  NetworkAddress
            ACCESS  read-write
            STATUS  mandatory
            DESCRIPTION
                    "IP Address of the server to be used when an image is to be
                    downloaded using the Runtime TFTP Download."
            ::= { fpdownload 18 }

        fpDLFileName    OBJECT-TYPE
            SYNTAX  DisplayString (SIZE (1..127))
            ACCESS  read-write
            STATUS  mandatory
            DESCRIPTION
                    "Filename requested of the server when an image is to be
                    downloaded using the Runtime TFTP Download.  This should
                    be a complete path filename."
            ::= { fpdownload 19 }

        fpDLErrorString OBJECT-TYPE
            SYNTAX  DisplayString
            ACCESS  read-only
            STATUS  mandatory
            DESCRIPTION
                    "If the value of fpDLOperStatus is downloadCompleteError(5)
                    or uploadCompleteError(7) then this object will provide a
                    more complete description of the error.  Otherwise this
                    object will be the zero length string."
            ::= { fpdownload 20 }

        fpDLTftpServerGatewayIPAddress  OBJECT-TYPE
            SYNTAX  NetworkAddress
            ACCESS  read-write
            STATUS  mandatory
            DESCRIPTION
                    "The IP address of the gateway/router which connects
                    this SNMP agent to the TFTP server (0.0.0.0 if none)."
            ::= { fpdownload 21 }

        fpDLBlockCount OBJECT-TYPE
            SYNTAX  INTEGER
            ACCESS  read-only
            STATUS  mandatory
            DESCRIPTION
                    "Current TFTP block count of an active session. If no
                    TFTP transfer is in progress, zero is returned."
            ::= { fpdownload 22 }

        fpDLBootPartitionStatus OBJECT-TYPE
            SYNTAX  INTEGER { good(1),
                              bad(2),
                              inProgress(3) }
            ACCESS  read-only
            STATUS  mandatory
            DESCRIPTION
                    "Status of the boot partition or paritions. A value of
                    good(1) indicates that all boot partitions contain a
                    valid checksum. A value of bad(2) indicates that one or
                    more boot partitions contain an invalid checksum and the
                    the image was not able to fix the invalid boot partition.
                    A value of inProgress(3) indicates that the image is
                    attempting to fix an invalid boot partition and this
                    status will change to either good(1) or bad(2)."
            ::= { fpdownload 23 }

        fpDLLocalFileName    OBJECT-TYPE
            SYNTAX  DisplayString (SIZE (1..12))
            ACCESS  read-write
            STATUS  mandatory
            DESCRIPTION
                    "Filename used on the local file system whenever a TFTP
                    download or upload is to be processed."
            ::= { fpdownload 24 }

        fpDLBootVersion  OBJECT-TYPE
        SYNTAX  DisplayString (SIZE(1..127))
        ACCESS  read-only
        STATUS  mandatory
        DESCRIPTION
            "Returns a string indicating the boot code version."
        ::= { fpdownload 25 }

        fpDLBootReason OBJECT-TYPE
        SYNTAX  INTEGER {
                  other(1),
                  power-up(2),
                  reset-switch(3),
                  software-reboot(4),
                  double-bus-fault(5),
                  hardware-watchdog(6),
                  loss-of-clock(7),
                  suicide(8)
                }
        ACCESS  read-only
        STATUS  mandatory
        DESCRIPTION
            "Reason for the last reboot."
        ::= { fpdownload 26 }

        --
        -- The System Server IP Translation Server table
        --

        sysIPTranslationServerTable OBJECT-TYPE
            SYNTAX  SEQUENCE OF SysIPTranslationServerEntry
            ACCESS  not-accessible
            STATUS  mandatory
            DESCRIPTION
                    "The IP Translation Server Table.  Used to select a
                    server when doing IP address translation."
            ::= { fpiptranslate 1 }

        sysIPTranslationServerEntry OBJECT-TYPE
            SYNTAX  SysIPTranslationServerEntry
            ACCESS  not-accessible
            STATUS  mandatory
            DESCRIPTION
                    ""
            INDEX {
                    sysIPTranslationServerIPAddress,
                    sysIPTranslationProtocol,
                    sysIPFirstTranslationPort
                  }
            ::= { sysIPTranslationServerTable 1 }

        SysIPTranslationServerEntry ::=
            SEQUENCE {
                        sysIPTranslationServerIPAddress
                              IpAddress,
                        sysIPTranslationProtocol
                              OCTET STRING (SIZE (1)),
                        sysIPFirstTranslationPort
                              OCTET STRING (SIZE (2)),
                        sysIPLastTranslationPort
                              OCTET STRING (SIZE (2)),
                        sysIPFirstPrivatePort
                              OCTET STRING (SIZE (2)),
                        sysIPTranslationStatus
                              RowStatus
                     }

        sysIPTranslationServerIPAddress OBJECT-TYPE
            SYNTAX  IpAddress
            ACCESS  read-only
            STATUS  mandatory
            DESCRIPTION
                    "The IP address of the Server when doing IP Address
                    translation. "
            ::= { sysIPTranslationServerEntry 1 }

        sysIPTranslationProtocol OBJECT-TYPE
            SYNTAX  OCTET STRING (SIZE (1))
            ACCESS  read-only
            STATUS  mandatory
            DESCRIPTION
                    "The protocol used by this Server."
            ::= { sysIPTranslationServerEntry 2 }

        sysIPFirstTranslationPort OBJECT-TYPE
            SYNTAX  OCTET STRING (SIZE (2))
            ACCESS  read-only
            STATUS  mandatory
            DESCRIPTION
                    "First public port in range used by this server.  
                    This port is what is referenced by the client.
                    A port of 0 is a wild-card signifying any port."
            ::= { sysIPTranslationServerEntry 3 }

        sysIPLastTranslationPort OBJECT-TYPE
            SYNTAX  OCTET STRING (SIZE (2))
            ACCESS  read-only
            STATUS  mandatory
            DESCRIPTION
                    "Last public port in range used by this server.
                    This port is the last port in range and is referenced
                    by the client..  This value must be greater than or equal 
                    first public port in range."
            ::= { sysIPTranslationServerEntry 4 }

        sysIPFirstPrivatePort OBJECT-TYPE
            SYNTAX  OCTET STRING (SIZE (2))
            ACCESS  read-only
            STATUS  mandatory
            DESCRIPTION
                    "This is the first private port in range as seen by the
                    server.  The public port range is mapped to this private
                    port range.  If the public port range is to be the same
                    as the private port range, this port should be the same
                    as the first public port."
            ::= { sysIPTranslationServerEntry 5 }

        sysIPTranslationStatus OBJECT-TYPE
            SYNTAX RowStatus
            ACCESS read-write
            STATUS mandatory
            DESCRIPTION
                    "The status column used for creating, modifying, and
                     deleting instances of the columnar objects in this table."
            ::= { sysIPTranslationServerEntry 6 }


        --
        -- The System NAT Host Mapping table
        --

        sysNatHostMappingTable OBJECT-TYPE
            SYNTAX  SEQUENCE OF SysNatHostMappingEntry
            ACCESS  not-accessible
            STATUS  mandatory
            DESCRIPTION
                    "The NAT Host Mapping Table.  Used to select a
                    NAT Host Mapping when doing IP address translation."
            ::= { fpiptranslate 2 }

        sysNatHostMappingEntry OBJECT-TYPE
            SYNTAX  SysNatHostMappingEntry
            ACCESS  not-accessible
            STATUS  mandatory
            DESCRIPTION
                    ""
            INDEX {
                    sysFirstPrivateIPAddress,
                    sysLastPrivateIPAddress,
                    sysFirstPublicIPAddress
                  }
            ::= { sysNatHostMappingTable 1 }

        SysNatHostMappingEntry ::=
            SEQUENCE {
                        sysFirstPrivateIPAddress
                              IpAddress,
                        sysLastPrivateIPAddress
                              IpAddress,
                        sysFirstPublicIPAddress
                              IpAddress,
                        sysNatHostMappingStatus
                              RowStatus
                     }

        sysFirstPrivateIPAddress OBJECT-TYPE
            SYNTAX  IpAddress
            ACCESS  read-only
            STATUS  mandatory
            DESCRIPTION
                    "The first private IP address which starts the range
                    of private IP addresses which are mapped to public
                    IP addresses."
            ::= { sysNatHostMappingEntry 1 }

        sysLastPrivateIPAddress OBJECT-TYPE
            SYNTAX  IpAddress
            ACCESS  read-only
            STATUS  mandatory
            DESCRIPTION
                    "The last private IP address which ends the range
                    of private IP addresses which are mapped to public
                    IP addresses."
            ::= { sysNatHostMappingEntry 2 }

        sysFirstPublicIPAddress OBJECT-TYPE
            SYNTAX  IpAddress
            ACCESS  read-only
            STATUS  mandatory
            DESCRIPTION
                    "The first public IP address which starts the range of
                    public IP Addresses which are mapped to private IP
                    addresses.  The last public IP address in the range
                    is calculated by counting the number of private IP
                    addresses in the private IP address range and creating
                    an equivalent number of IP addresses in the public
                    IP address range so there is a one to one mapping
                    of public IP addresses to private IP addresses."
            ::= { sysNatHostMappingEntry 3 }

        sysNatHostMappingStatus OBJECT-TYPE
            SYNTAX RowStatus
            ACCESS read-write
            STATUS mandatory
            DESCRIPTION
                    "The status column used for creating, modifying, and
                    deleting instances of the columnar objects in this table."
            ::= { sysNatHostMappingEntry 4 }


        --
        -- The DHCP Server
        --

        dhcpOperation OBJECT-TYPE
            SYNTAX  INTEGER {
                              save(1),    -- save DHCP data to FLASH
                              load(2),    -- load DHCP data from FLASH
                              erase(3),   -- erase DHCP data in FLASH
                              dhcpenable(4),  -- enable all DHCP subnets
                              dhcpdisable(5)  -- disable all DHCP subnets
                            }
            ACCESS  write-only
            STATUS  mandatory
            DESCRIPTION
                    " Use this object to give commands to save, load or
                        erase DHCP configuration in FLASH memory."
            ::= { fpdhcp 1 }

        --
        -- The DHCP Server Global TFTP Server/filename Info
        --

        dhcpGlobalTftpServer OBJECT-TYPE
            SYNTAX  IpAddress
            ACCESS  read-write
            STATUS  mandatory
            DESCRIPTION
                    "IP address for the TFTP server.  This global value is 
                     used as the next server for booting if the Subnet AND
                     Client lease do not have a TFTP server defined.
                     0.0.0.0 clears this entry."
            ::= { fpdhcp 2 }

        dhcpGlobalTftpFile OBJECT-TYPE
            SYNTAX  DisplayString (SIZE (0..255))
            ACCESS  read-write
            STATUS  mandatory
            DESCRIPTION
                    "Name of file for booting.  This value is used ONLY if
                     the global value for the TFTP server is set."
            ::= { fpdhcp 3 }

        --
        -- The DHCP Server Global Lease Time
        --

        dhcpGlobalLeaseTime OBJECT-TYPE
            SYNTAX  INTEGER
            ACCESS  read-write
            STATUS  mandatory
            DESCRIPTION
                    "Global Lease Time value in hours.  A value of 0 selects
                     the Default Lease Time."
            ::= { fpdhcp 4 }
        
        --
        -- The DHCP Server Option Code Table
        --

        dhcpCodeTable OBJECT-TYPE
            SYNTAX  SEQUENCE OF DhcpCodeEntry
            ACCESS  not-accessible
            STATUS  mandatory
            DESCRIPTION
                    "The table used to define DHCP option codes."
            ::= { fpdhcp 5 }

        dhcpCodeEntry OBJECT-TYPE
            SYNTAX  DhcpCodeEntry
            ACCESS  not-accessible
            STATUS  mandatory
            DESCRIPTION
                    ""
            INDEX { dhcpOptionCode }
            ::= { dhcpCodeTable 1 }

        DhcpCodeEntry ::=
              SEQUENCE {
                        dhcpOptionCode
                              INTEGER,
                        dhcpMinCount
                              INTEGER,
                        dhcpMaxCount
                              INTEGER,
                        dhcpOptionType
                              DhcpOptionType,
                        dhcpOptionCodeStatus
                              RowStatus
                       }            

        dhcpOptionCode OBJECT-TYPE
            SYNTAX  INTEGER (0..255)
            ACCESS  read-only
            STATUS  mandatory
            DESCRIPTION
                    "DHCP Defined Option Code."
            ::= { dhcpCodeEntry 1 }

        dhcpMinCount OBJECT-TYPE
            SYNTAX  INTEGER (0..255)
            ACCESS  read-only
            STATUS  mandatory
            DESCRIPTION
                    "Minimum allowed number of values for this option."
            ::= { dhcpCodeEntry 2 }

        dhcpMaxCount OBJECT-TYPE
            SYNTAX  INTEGER (0..255)
            ACCESS  read-only
            STATUS  mandatory
            DESCRIPTION
                    "Maximum allowed number of values for this option."
            ::= { dhcpCodeEntry 3 }

        dhcpOptionType OBJECT-TYPE
            SYNTAX  DhcpOptionType
            ACCESS  read-only
            STATUS  mandatory
            DESCRIPTION
                    "Values for this Option are of this type."
            ::= { dhcpCodeEntry 4 }

        dhcpOptionCodeStatus OBJECT-TYPE
            SYNTAX  RowStatus
            ACCESS  read-write
            STATUS  mandatory
            DESCRIPTION
                    "The status column used for creating, modifying, and
                     deleting instances of the columnar objects in this table."
            ::= { dhcpCodeEntry 5 }

        --
        -- The DHCP Server Global Option Value Table
        --

        dhcpGlobalValueTable OBJECT-TYPE
            SYNTAX  SEQUENCE OF DhcpGlobalValueEntry
            ACCESS  not-accessible
            STATUS  mandatory
            DESCRIPTION
                    "The table used to set or clear Global DHCP option values."
            ::= { fpdhcp 6 }

        dhcpGlobalValueEntry OBJECT-TYPE
            SYNTAX  DhcpGlobalValueEntry
            ACCESS  not-accessible
            STATUS  mandatory
            DESCRIPTION
                    ""
            INDEX { dhcpGlobalValueCode }
            ::= { dhcpGlobalValueTable 1 }

        DhcpGlobalValueEntry ::=
            SEQUENCE {
                        dhcpGlobalValueCode
                            INTEGER,
                        dhcpGlobalValueType
                            DhcpOptionType,
                        dhcpGlobalValue
                            OCTET STRING (SIZE (0..255)),
                        dhcpGlobalValueStatus
                            RowStatus
                     }

        dhcpGlobalValueCode OBJECT-TYPE
            SYNTAX  INTEGER (0..255)
            ACCESS  read-only
            STATUS  mandatory
            DESCRIPTION
                    "DHCP Option Code as defined in rfc1533."
            ::= { dhcpGlobalValueEntry 1 }

        dhcpGlobalValueType OBJECT-TYPE
            SYNTAX  DhcpOptionType
            ACCESS  read-only
            STATUS  mandatory
            DESCRIPTION
                    "Type of value for this DHCP Option Code."
            ::= { dhcpGlobalValueEntry 2 }

        dhcpGlobalValue OBJECT-TYPE
            SYNTAX  OCTET STRING (SIZE (0..255))
            ACCESS  read-write
            STATUS  mandatory
            DESCRIPTION
                    "Value for this DHCP Option."
            ::= { dhcpGlobalValueEntry 3 }

        dhcpGlobalValueStatus OBJECT-TYPE
            SYNTAX  RowStatus
            ACCESS  read-write
            STATUS  mandatory
            DESCRIPTION
                    "The status column used for creating, modifying, and
                     deleting instances of the columnar objects in this table."
            ::= { dhcpGlobalValueEntry 4 }

        --
        -- The DHCP Server Subnet Table
        --

        dhcpSubnetTable OBJECT-TYPE
            SYNTAX  SEQUENCE OF DhcpSubnetEntry
            ACCESS  not-accessible
            STATUS  mandatory
            DESCRIPTION
                    "The table used to set or clear DHCP subnet information."
            ::= { fpdhcp 7 }

        dhcpSubnetEntry OBJECT-TYPE
            SYNTAX  DhcpSubnetEntry
            ACCESS  not-accessible
            STATUS  mandatory
            DESCRIPTION
                    ""
            INDEX { dhcpSubnetAddress }
            ::= { dhcpSubnetTable 1 }

        DhcpSubnetEntry ::=
            SEQUENCE {
                        dhcpSubnetAddress
                            IpAddress,
                        dhcpSubnetMask
                            IpAddress,
                        dhcpSubnetFirstIpAddress
                            IpAddress,
                        dhcpSubnetLastIpAddress
                            IpAddress,
                        dhcpSubnetTftpServer
                            IpAddress,
                        dhcpSubnetTftpFile
                            DisplayString (SIZE (0..255)),
                        dhcpSubnetBootp
                            INTEGER,
                        dhcpSubnetLeaseTime
                            INTEGER,                        
                        dhcpSubnetStatus
                            RowStatus,
                        dhcpSubnetConflictActions
                            INTEGER
                     }

        dhcpSubnetAddress OBJECT-TYPE
            SYNTAX  IpAddress
            ACCESS  read-only
            STATUS  mandatory
            DESCRIPTION
                    "DHCP Subnet address."
            ::= { dhcpSubnetEntry 1 }

        dhcpSubnetMask OBJECT-TYPE
            SYNTAX  IpAddress
            ACCESS  read-write
            STATUS  mandatory
            DESCRIPTION
                    "DHCP Subnet Mask.  If the Subnet does NOT exist when
                     one attempts to set the Subnet Mask, the Subnet will
                     be automatically created."
            ::= { dhcpSubnetEntry 2 }

        dhcpSubnetFirstIpAddress OBJECT-TYPE
            SYNTAX  IpAddress
            ACCESS  read-write
            STATUS  mandatory
            DESCRIPTION
                    "First Ip Address in the Subnet Pool. 0.0.0.0 clears
                     both the First Ip Address and Last Ip Address."
            ::= { dhcpSubnetEntry 3 }

        dhcpSubnetLastIpAddress OBJECT-TYPE
            SYNTAX  IpAddress
            ACCESS  read-write
            STATUS  mandatory
            DESCRIPTION
                    "Last Ip Address in the Subnet Pool. 0.0.0.0 clears
                     both the First Ip Address and Last Ip Address."
            ::= { dhcpSubnetEntry 4 }

        --
        -- The DHCP Server Subnet TFTP Server/filename Info
        --

        dhcpSubnetTftpServer OBJECT-TYPE
            SYNTAX  IpAddress
            ACCESS  read-write
            STATUS  mandatory
            DESCRIPTION
                    "IP address for the TFTP server.  This Subnet value is 
                     used as the next server for booting if the Client
                     lease does not have a TFTP server defined.
                     0.0.0.0 clears this entry."
            ::= { dhcpSubnetEntry 5 }

        dhcpSubnetTftpFile OBJECT-TYPE
            SYNTAX  DisplayString (SIZE (0..255))
            ACCESS  read-write
            STATUS  mandatory
            DESCRIPTION
                    "Name of file for booting.  This value is used ONLY if
                     the Subnet value for the TFTP server is set."
            ::= { dhcpSubnetEntry 6 }

        dhcpSubnetBootp OBJECT-TYPE
            SYNTAX  INTEGER { allow(1), disallow(2) }
            ACCESS  read-write
            STATUS  mandatory
            DESCRIPTION
                    "Allow or Disallow servicing of Bootp requests for this
                     Subnet.  Default is Disallow.  A Client Lease within
                     this Subnet can still allow Bootp requests."
            ::= { dhcpSubnetEntry 7 }

        --
        -- The DHCP Server Subnet Lease Time
        --

        dhcpSubnetLeaseTime OBJECT-TYPE
            SYNTAX  INTEGER
            ACCESS  read-write
            STATUS  mandatory
            DESCRIPTION
                    "Subnet Default Lease Time value in hours.  A value
                     of 0 selects the Default Lease Time."
            ::= { dhcpSubnetEntry 8 }

        dhcpSubnetStatus OBJECT-TYPE
            SYNTAX  RowStatus
            ACCESS  read-write
            STATUS  mandatory
            DESCRIPTION
                    "The status column used for creating, modifying, and
                     deleting instances of the columnar objects in this table."
            ::= { dhcpSubnetEntry 9 }

        dhcpSubnetConflictActions OBJECT-TYPE
            SYNTAX  INTEGER { docontinue(1),
                              dostop(2)
                            }
            ACCESS  read-write
            STATUS  mandatory
            DESCRIPTION
                    "What this DHCP server should do with this subnet if this
                     subnet is for the local LAN and another DHCP server for
                     the local LAN exists."
            ::= { dhcpSubnetEntry 10 }

        --
        -- The DHCP Server Subnet Option Value Table
        --

        dhcpSubnetValueTable OBJECT-TYPE
            SYNTAX  SEQUENCE OF DhcpSubnetValueEntry
            ACCESS  not-accessible
            STATUS  mandatory
            DESCRIPTION
                    "The table used to set or clear Subnet DHCP option values."
            ::= { fpdhcp 8 }

        dhcpSubnetValueEntry OBJECT-TYPE
            SYNTAX  DhcpSubnetValueEntry
            ACCESS  not-accessible
            STATUS  mandatory
            DESCRIPTION
                    ""
            INDEX {
                    dhcpSubnetAddress,
                    dhcpSubnetValueCode
                  }
            ::= { dhcpSubnetValueTable 1 }

        DhcpSubnetValueEntry ::=
            SEQUENCE {
                        dhcpSubnetValueCode
                            INTEGER,
                        dhcpSubnetValueType
                            DhcpOptionType,
                        dhcpSubnetValue
                            OCTET STRING (SIZE (0..255)),
                        dhcpSubnetValueStatus
                            RowStatus
                     }

        dhcpSubnetValueCode OBJECT-TYPE
            SYNTAX  INTEGER (0..255)
            ACCESS  read-only
            STATUS  mandatory
            DESCRIPTION
                    "DHCP Option Code as defined in rfc1533."
            ::= { dhcpSubnetValueEntry 1 }

        dhcpSubnetValueType OBJECT-TYPE
            SYNTAX  DhcpOptionType
            ACCESS  read-only
            STATUS  mandatory
            DESCRIPTION
                    "Type of value for this DHCP Option Code."
            ::= { dhcpSubnetValueEntry 2 }

        dhcpSubnetValue OBJECT-TYPE
            SYNTAX  OCTET STRING (SIZE (0..255))
            ACCESS  read-write
            STATUS  mandatory
            DESCRIPTION
                    "Value for this DHCP Option."
            ::= { dhcpSubnetValueEntry 3 }

        dhcpSubnetValueStatus OBJECT-TYPE
            SYNTAX  RowStatus
            ACCESS  read-write
            STATUS  mandatory
            DESCRIPTION
                    "The status column used for creating, modifying, and
                     deleting instances of the columnar objects in this table."
            ::= { dhcpSubnetValueEntry 4 }

        --
        -- The DHCP Server Client Table
        --

        dhcpClientTable OBJECT-TYPE
            SYNTAX  SEQUENCE OF DhcpClientEntry
            ACCESS  not-accessible
            STATUS  mandatory
            DESCRIPTION
                    "The table used to set or clear DHCP Client Lease 
                     information."
            ::= { fpdhcp 9 }

        dhcpClientEntry OBJECT-TYPE
            SYNTAX  DhcpClientEntry
            ACCESS  not-accessible
            STATUS  mandatory
            DESCRIPTION
                    ""
            INDEX { dhcpClientAddress }
            ::= { dhcpClientTable 1 }

        DhcpClientEntry ::=
            SEQUENCE {
                        dhcpClientAddress
                            IpAddress,
                        dhcpClientTftpServer
                            IpAddress,
                        dhcpClientTftpFile
                            DisplayString (SIZE (0..255)),
                        dhcpClientBootp
                            INTEGER,
                        dhcpClientLeaseTime
                            INTEGER,
                        dhcpClientExpireTimeYear
                            INTEGER,
                        dhcpClientExpireTimeMonth
                            INTEGER (1..12),
                        dhcpClientExpireTimeDay
                            INTEGER (1..31),
                        dhcpClientExpireTimeHour
                            INTEGER (0..23),
                        dhcpClientExpireTimeMinute
                            INTEGER (0..59),
                        dhcpClientExpireTimeSecond
                            INTEGER (0..59),
                        dhcpClientStatus
                            RowStatus
                     }

        dhcpClientAddress OBJECT-TYPE
            SYNTAX  IpAddress
            ACCESS  read-only
            STATUS  mandatory
            DESCRIPTION
                    "DHCP Client Lease address.  To iterate through the
                     list of client entries for a particular subnet use
                     the subnet ip address as the index and attempt to
                     get the next entry."
            ::= { dhcpClientEntry 1 }

        --
        -- The DHCP Server Client TFTP Server/filename Info
        --

        dhcpClientTftpServer OBJECT-TYPE
            SYNTAX  IpAddress
            ACCESS  read-write
            STATUS  mandatory
            DESCRIPTION
                    "IP address for the TFTP server.  This Client value is 
                     used as the next server for booting.
                     0.0.0.0 clears this entry."
            ::= { dhcpClientEntry 2 }

        dhcpClientTftpFile OBJECT-TYPE
            SYNTAX  DisplayString (SIZE (0..255))
            ACCESS  read-write
            STATUS  mandatory
            DESCRIPTION
                    "Name of file for booting.  This value is used ONLY if
                     the Client value for the TFTP server is set."
            ::= { dhcpClientEntry 3 }

        dhcpClientBootp OBJECT-TYPE
            SYNTAX  INTEGER { allow(1), disallow(2) }
            ACCESS  read-write
            STATUS  mandatory
            DESCRIPTION
                    "Allow or Disallow servicing of Bootp requests for this
                     Subnet.  Default is Disallow.  If Enabled this Client
                     Lease will satisfy a Bootp request even if the Subnet
                     has Bootp Disallowed."
            ::= { dhcpClientEntry 4 }

        dhcpClientLeaseTime OBJECT-TYPE
            SYNTAX  INTEGER
            ACCESS  read-write
            STATUS  mandatory
            DESCRIPTION
                    "Client Default Lease Time value in hours.  A value
                     of 0 selects the Default Lease Time."
            ::= { dhcpClientEntry 5 }

        dhcpClientExpireTimeYear OBJECT-TYPE
            SYNTAX  INTEGER
            ACCESS  read-write
            STATUS  mandatory
            DESCRIPTION
                    "Time Client Lease expire time-year.  
                     If 0, entry is expired."
            ::= { dhcpClientEntry 6 }

        dhcpClientExpireTimeMonth OBJECT-TYPE
            SYNTAX  INTEGER (1..12)
            ACCESS  read-write
            STATUS  mandatory
            DESCRIPTION
                    "Time Client Lease expire time-month."
            ::= { dhcpClientEntry 7 }

        dhcpClientExpireTimeDay OBJECT-TYPE
            SYNTAX  INTEGER (1..31)
            ACCESS  read-write
            STATUS  mandatory
            DESCRIPTION
                    "Time Client Lease expire time-day."
            ::= { dhcpClientEntry 8 }

        dhcpClientExpireTimeHour OBJECT-TYPE
            SYNTAX  INTEGER (0..23)
            ACCESS  read-write
            STATUS  mandatory
            DESCRIPTION
                    "Time Client Lease expire time-hour."
            ::= { dhcpClientEntry 9 }

        dhcpClientExpireTimeMinute OBJECT-TYPE
            SYNTAX  INTEGER (0..59)
            ACCESS  read-write
            STATUS  mandatory
            DESCRIPTION
                    "Time Client Lease expire time-minute."
            ::= { dhcpClientEntry 10 }

        dhcpClientExpireTimeSecond OBJECT-TYPE
            SYNTAX  INTEGER (0..59)
            ACCESS  read-write
            STATUS  mandatory
            DESCRIPTION
                    "Time Client Lease expire time-second."
            ::= { dhcpClientEntry 11 }

        dhcpClientStatus OBJECT-TYPE
            SYNTAX  RowStatus
            ACCESS  read-write
            STATUS  mandatory
            DESCRIPTION
                    "The status column used for creating, modifying, and
                     deleting instances of the columnar objects in this table."
            ::= { dhcpClientEntry 12 }
        
        --
        -- The DHCP Server Client Option Value Table
        --

        dhcpClientValueTable OBJECT-TYPE
            SYNTAX  SEQUENCE OF DhcpClientValueEntry
            ACCESS  not-accessible
            STATUS  mandatory
            DESCRIPTION
                    "The table used to set or clear Client DHCP option values."
            ::= { fpdhcp 10 }

        dhcpClientValueEntry OBJECT-TYPE
            SYNTAX  DhcpClientValueEntry
            ACCESS  not-accessible
            STATUS  mandatory
            DESCRIPTION
                    ""
            INDEX {
                    dhcpClientAddress,
                    dhcpClientValueCode
                  }
            ::= { dhcpClientValueTable 1 }

        DhcpClientValueEntry ::=
            SEQUENCE {
                        dhcpClientValueCode
                            INTEGER,
                        dhcpClientValueType
                            DhcpOptionType,
                        dhcpClientValue
                            OCTET STRING (SIZE (0..255)),
                        dhcpClientValueStatus
                            RowStatus
                     }

        dhcpClientValueCode OBJECT-TYPE
            SYNTAX  INTEGER (0..255)
            ACCESS  read-only
            STATUS  mandatory
            DESCRIPTION
                    "DHCP Option Code as defined in rfc1533."
            ::= { dhcpClientValueEntry 1 }

        dhcpClientValueType OBJECT-TYPE
            SYNTAX  DhcpOptionType
            ACCESS  read-only
            STATUS  mandatory
            DESCRIPTION
                    "Type of value for this DHCP Option Code."
            ::= { dhcpClientValueEntry 2 }

        dhcpClientValue OBJECT-TYPE
            SYNTAX  OCTET STRING (SIZE (0..255))
            ACCESS  read-write
            STATUS  mandatory
            DESCRIPTION
                    "Value for this DHCP Option."
            ::= { dhcpClientValueEntry 3 }

        dhcpClientValueStatus OBJECT-TYPE
            SYNTAX  RowStatus
            ACCESS  read-write
            STATUS  mandatory
            DESCRIPTION
                    "The status column used for creating, modifying, and
                     deleting instances of the columnar objects in this table."
            ::= { dhcpClientValueEntry 4 }

        --
        --  File system table
        --
 
        fpDirTable OBJECT-TYPE
              SYNTAX  SEQUENCE OF FpDirEntry
              ACCESS  not-accessible
              STATUS  mandatory
              DESCRIPTION
                      "The directory Table contains the names and
                      sizes of the files in the file system."
              ::= { fpdir 1 }

        fpDirEntry OBJECT-TYPE
              SYNTAX  FpDirEntry
              ACCESS  not-accessible
              STATUS  mandatory
              DESCRIPTION
                      "Each entry contains the directory name in msdos
                       format; 8 character name, followed by a ., followed
                       by a 3 character extension. 
                       The file size is returned (in bytes)."
              INDEX   { fpDirIndex}
              ::= { fpDirTable 1 }

        FpDirEntry ::=
              SEQUENCE {
                  fpDirIndex
                      INTEGER, 
                  fpDirName
                      DisplayString (SIZE (0..12)),
                  fpDirSize
                      INTEGER
              }

        fpDirIndex  OBJECT-TYPE
            SYNTAX  INTEGER (1..128)
            ACCESS  read-only
            STATUS  mandatory
            DESCRIPTION
                    "A file number to read."
            ::= { fpDirEntry 1 }

        fpDirName  OBJECT-TYPE
            SYNTAX  DisplayString (SIZE (0..12))
            ACCESS  read-only
            STATUS  mandatory
            DESCRIPTION
                    "A textual description of the name of the file.
                    In the format 8.3 for dos."
            ::= { fpDirEntry 2 }

        fpDirSize  OBJECT-TYPE
            SYNTAX  INTEGER
            ACCESS  read-only
            STATUS  mandatory
            DESCRIPTION
                    "The size of the file in bytes."
            ::= { fpDirEntry 3 }

        --
        -- The ATM configuration group
        --

        atmOperation OBJECT-TYPE
            SYNTAX  INTEGER {
                              save(1),    -- save ATM data to FLASH
                              load(2),    -- load ATM data from FLASH
                              erase(3)    -- erase ATM data in FLASH
                            }
            ACCESS  write-only
            STATUS  mandatory
            DESCRIPTION
                    " Use this object to give commands to save, load or
                        erase ATM configuration in FLASH memory."
            ::= { fpatm 1 }

        --
        -- The FR configuration group
        --

        frOperation OBJECT-TYPE
            SYNTAX  INTEGER {
                              save(1),    -- save FR data to FLASH
                              load(2),    -- load FR data from FLASH
                              erase(3)    -- erase FR data in FLASH
                            }
            ACCESS  write-only
            STATUS  mandatory
            DESCRIPTION
                    " Use this object to give commands to save, load or
                        erase FR configuration in FLASH memory."
            ::= { fpfr 1 }

END
